AC-PM-Control-MIB DEFINITIONS ::= BEGIN


    IMPORTS
       

        OBJECT-TYPE, 
        MODULE-IDENTITY                             FROM SNMPv2-SMI
        TAddress, 
        DisplayString, 
        DateAndTime, TEXTUAL-CONVENTION             FROM SNMPv2-TC
        IpAddress                                   FROM RFC1155-SMI
        Unsigned32,
		Integer32,
		Counter32,
		Gauge32,
        enterprises                                 FROM SNMPv2-SMI
		SnmpAdminString								FROM SNMP-FRAMEWORK-MIB
		audioCodes,       
		acRegistrations,
		acGeneric, 
		acProducts,acBoardMibs,acPerformance		FROM AUDIOCODES-TYPES-MIB;

       
acPMControl  MODULE-IDENTITY       
    LAST-UPDATED "202005251028Z"          --Monday, May 25 2020
    ORGANIZATION "AudioCodes Ltd"
    CONTACT-INFO
    "Postal: Support
			 AudioCodes LTD
             1 Hayarden Street
             Airport City 
			 Lod, ISRAEL 70151
     Tel:    972-3-9764000
     Fax:    972-3-9764040
     Email:  support@audiocodes.com
     Web:    www.audiocodes.com"		
		

    DESCRIPTION       
    "The AC-PM-Control MIB offers performance monitoring
For the Control related elements in Audiocodes' devices.
The Configuration sub-tree is for configuring the interval
Period length for the entire AC-PM-Control MIB, and the 
different tables' thresholds.
The Data sub-tree presents the tables of monitored
elements.

Note  - for the entire MIB the value (-1) means the value
Asked for is either not supported or currently not relevant
(this is for when values asked for are for intervals not yet
recorded."

    REVISION     "202102160955Z"          --Tuesday, February 16 2021   
    DESCRIPTION  "obsoleted acPMControl"


    ::= {acPerformance 8}  








     acPMControlConfiguration OBJECT IDENTIFIER ::= {acPMControl 1}


     acPMControlConfigurationPeriodLength OBJECT-TYPE
       SYNTAX Unsigned32 (0..894780)
       MAX-ACCESS read-write
       STATUS obsolete
       DESCRIPTION
           "Length of monitoring intervals for entire MIB.
Time is in minutes.
Access: Instant."
       ::= {acPMControlConfiguration 1}



     acPMControlConfigurationResetTotalCounters OBJECT-TYPE
       SYNTAX INTEGER {
                  resetCountersDone(1)
,
                  resetTotalCounters(2)

                  }
       MAX-ACCESS read-write
       STATUS obsolete
       DESCRIPTION
           "Total-Counters Reset.  To reset the total counters, set the
value of this object to resetTotalCounters(2).
Access: Instant."
       ::= {acPMControlConfiguration 2}



     acPMCPConnectionAttributes OBJECT IDENTIFIER ::= {acPMControlConfiguration 32}


     acPMCPConnectionAttributesLifetimeHighThreshold OBJECT-TYPE
       SYNTAX Unsigned32 (0..2147483647)
       MAX-ACCESS read-write
       STATUS obsolete
       DESCRIPTION
           "High threshold.
Access: Instant."
       ::= {acPMCPConnectionAttributes 1}



     acPMCPConnectionAttributesLifetimeLowThreshold OBJECT-TYPE
       SYNTAX Unsigned32 (0..2147483647)
       MAX-ACCESS read-write
       STATUS obsolete
       DESCRIPTION
           "Low threshold.
Access: Instant."
       ::= {acPMCPConnectionAttributes 2}



     acPMCPConnectionAttributesStateHighThreshold OBJECT-TYPE
       SYNTAX Unsigned32 (0..2147483647)
       MAX-ACCESS read-write
       STATUS obsolete
       DESCRIPTION
           "High threshold.
Access: Instant."
       ::= {acPMCPConnectionAttributes 3}



     acPMCPConnectionAttributesStateLowThreshold OBJECT-TYPE
       SYNTAX Unsigned32 (0..2147483647)
       MAX-ACCESS read-write
       STATUS obsolete
       DESCRIPTION
           "Low threshold.
Access: Instant."
       ::= {acPMCPConnectionAttributes 4}



     acPMCPConnectionAttributesCommandCounterHighThreshold OBJECT-TYPE
       SYNTAX Unsigned32 (0..2147483647)
       MAX-ACCESS read-write
       STATUS obsolete
       DESCRIPTION
           "High threshold.
Access: Instant."
       ::= {acPMCPConnectionAttributes 5}



     acPMCPConnectionAttributesCommandCounterLowThreshold OBJECT-TYPE
       SYNTAX Unsigned32 (0..2147483647)
       MAX-ACCESS read-write
       STATUS obsolete
       DESCRIPTION
           "Low threshold.
Access: Instant."
       ::= {acPMCPConnectionAttributes 6}



     acPMCPConnectionAttributesRetransmissionCountHighThreshold OBJECT-TYPE
       SYNTAX Unsigned32 (0..2147483647)
       MAX-ACCESS read-write
       STATUS obsolete
       DESCRIPTION
           "High threshold.
Access: Instant."
       ::= {acPMCPConnectionAttributes 7}



     acPMCPConnectionAttributesRetransmissionCountLowThreshold OBJECT-TYPE
       SYNTAX Unsigned32 (0..2147483647)
       MAX-ACCESS read-write
       STATUS obsolete
       DESCRIPTION
           "Low threshold.
Access: Instant."
       ::= {acPMCPConnectionAttributes 8}



     acPMCPConnectionAttributesActiveContextCountHighThreshold OBJECT-TYPE
       SYNTAX Unsigned32 (0..2147483647)
       MAX-ACCESS read-write
       STATUS obsolete
       DESCRIPTION
           "High threshold.
Access: Instant."
       ::= {acPMCPConnectionAttributes 9}



     acPMCPConnectionAttributesActiveContextCountLowThreshold OBJECT-TYPE
       SYNTAX Unsigned32 (0..2147483647)
       MAX-ACCESS read-write
       STATUS obsolete
       DESCRIPTION
           "Low threshold.
Access: Instant."
       ::= {acPMCPConnectionAttributes 10}



     acPMCPConnectionAttributesCommandSuccessCountHighThreshold OBJECT-TYPE
       SYNTAX Unsigned32 (0..2147483647)
       MAX-ACCESS read-write
       STATUS obsolete
       DESCRIPTION
           "High threshold.
Access: Instant."
       ::= {acPMCPConnectionAttributes 11}



     acPMCPConnectionAttributesCommandSuccessCountLowThreshold OBJECT-TYPE
       SYNTAX Unsigned32 (0..2147483647)
       MAX-ACCESS read-write
       STATUS obsolete
       DESCRIPTION
           "Low threshold.
Access: Instant."
       ::= {acPMCPConnectionAttributes 12}



     acPMCPConnectionAttributesCommandFailureCountHighThreshold OBJECT-TYPE
       SYNTAX Unsigned32 (0..2147483647)
       MAX-ACCESS read-write
       STATUS obsolete
       DESCRIPTION
           "High threshold.
Access: Instant."
       ::= {acPMCPConnectionAttributes 13}



     acPMCPConnectionAttributesCommandFailureCountLowThreshold OBJECT-TYPE
       SYNTAX Unsigned32 (0..2147483647)
       MAX-ACCESS read-write
       STATUS obsolete
       DESCRIPTION
           "Low threshold.
Access: Instant."
       ::= {acPMCPConnectionAttributes 14}



     acPMCPConnectionAttributesCommandProcessTimeHighThreshold OBJECT-TYPE
       SYNTAX Unsigned32 (0..2147483647)
       MAX-ACCESS read-write
       STATUS obsolete
       DESCRIPTION
           "High threshold.
Access: Instant."
       ::= {acPMCPConnectionAttributes 15}



     acPMCPConnectionAttributesCommandProcessTimeLowThreshold OBJECT-TYPE
       SYNTAX Unsigned32 (0..2147483647)
       MAX-ACCESS read-write
       STATUS obsolete
       DESCRIPTION
           "Low threshold.
Access: Instant."
       ::= {acPMCPConnectionAttributes 16}



     acPMCPConnectionAttributesTransactionProcessTimerHighThreshold OBJECT-TYPE
       SYNTAX Unsigned32 (0..2147483647)
       MAX-ACCESS read-write
       STATUS obsolete
       DESCRIPTION
           "High threshold.
Access: Instant."
       ::= {acPMCPConnectionAttributes 17}



     acPMCPConnectionAttributesTransactionProcessTimerLowThreshold OBJECT-TYPE
       SYNTAX Unsigned32 (0..2147483647)
       MAX-ACCESS read-write
       STATUS obsolete
       DESCRIPTION
           "Low threshold.
Access: Instant."
       ::= {acPMCPConnectionAttributes 18}



     acPMMegacoAttributes OBJECT IDENTIFIER ::= {acPMControlConfiguration 33}


     acPMMegacoAttributesServiceChangeCountHighThreshold OBJECT-TYPE
       SYNTAX Unsigned32 (0..2147483647)
       MAX-ACCESS read-write
       STATUS obsolete
       DESCRIPTION
           "High threshold.
Access: Instant."
       ::= {acPMMegacoAttributes 1}



     acPMMegacoAttributesServiceChangeCountLowThreshold OBJECT-TYPE
       SYNTAX Unsigned32 (0..2147483647)
       MAX-ACCESS read-write
       STATUS obsolete
       DESCRIPTION
           "Low threshold.
Access: Instant."
       ::= {acPMMegacoAttributes 2}



     acPMMegacoAttributesCmdSuccessCountHighThreshold OBJECT-TYPE
       SYNTAX Unsigned32 (0..2147483647)
       MAX-ACCESS read-write
       STATUS obsolete
       DESCRIPTION
           "High threshold.
Access: Instant."
       ::= {acPMMegacoAttributes 3}



     acPMMegacoAttributesCmdSuccessCountLowThreshold OBJECT-TYPE
       SYNTAX Unsigned32 (0..2147483647)
       MAX-ACCESS read-write
       STATUS obsolete
       DESCRIPTION
           "Low threshold.
Access: Instant."
       ::= {acPMMegacoAttributes 4}



     acPMMegacoAttributesCmdFailureCountHighThreshold OBJECT-TYPE
       SYNTAX Unsigned32 (0..2147483647)
       MAX-ACCESS read-write
       STATUS obsolete
       DESCRIPTION
           "High threshold.
Access: Instant."
       ::= {acPMMegacoAttributes 5}



     acPMMegacoAttributesCmdFailureCountLowThreshold OBJECT-TYPE
       SYNTAX Unsigned32 (0..2147483647)
       MAX-ACCESS read-write
       STATUS obsolete
       DESCRIPTION
           "Low threshold.
Access: Instant."
       ::= {acPMMegacoAttributes 6}



     acPMSipAttributes OBJECT IDENTIFIER ::= {acPMControlConfiguration 34}


     acPMSipAttributesCallDurationHighThreshold OBJECT-TYPE
       SYNTAX Unsigned32 (0..2147483647)
       MAX-ACCESS read-write
       STATUS obsolete
       DESCRIPTION
           "High threshold.
Access: Instant."
       ::= {acPMSipAttributes 1}



     acPMSipAttributesCallDurationLowThreshold OBJECT-TYPE
       SYNTAX Unsigned32 (0..2147483647)
       MAX-ACCESS read-write
       STATUS obsolete
       DESCRIPTION
           "Low threshold.
Access: Instant."
       ::= {acPMSipAttributes 2}



     acPMSipAttributesTrunkGroupUtilizationHighThreshold OBJECT-TYPE
       SYNTAX Unsigned32 (0..2016)
       MAX-ACCESS read-write
       STATUS obsolete
       DESCRIPTION
           "High threshold.
Access: Instant."
       ::= {acPMSipAttributes 3}



     acPMSipAttributesTrunkGroupUtilizationLowThreshold OBJECT-TYPE
       SYNTAX Unsigned32 (0..2016)
       MAX-ACCESS read-write
       STATUS obsolete
       DESCRIPTION
           "Low threshold.
Access: Instant."
       ::= {acPMSipAttributes 4}



     acPMSipAttributesTrunkGroupPercentageUtilizationHighThreshold OBJECT-TYPE
       SYNTAX Unsigned32 (0..100)
       MAX-ACCESS read-write
       STATUS obsolete
       DESCRIPTION
           "High threshold.
Access: Instant."
       ::= {acPMSipAttributes 5}



     acPMSipAttributesTrunkGroupPercentageUtilizationLowThreshold OBJECT-TYPE
       SYNTAX Unsigned32 (0..100)
       MAX-ACCESS read-write
       STATUS obsolete
       DESCRIPTION
           "Low threshold.
Access: Instant."
       ::= {acPMSipAttributes 6}



     acPMSipAttributesTrunkGroupNoResourcesCallsHighThreshold OBJECT-TYPE
       SYNTAX Unsigned32 (0..2147483647)
       MAX-ACCESS read-write
       STATUS obsolete
       DESCRIPTION
           "High threshold.
Access: Instant."
       ::= {acPMSipAttributes 7}



     acPMSipAttributesTrunkGroupNoResourcesCallsLowThreshold OBJECT-TYPE
       SYNTAX Unsigned32 (0..2147483647)
       MAX-ACCESS read-write
       STATUS obsolete
       DESCRIPTION
           "Low threshold.
Access: Instant."
       ::= {acPMSipAttributes 8}



     acPMSipAttributesIPGroupInDialogsHighThreshold OBJECT-TYPE
       SYNTAX Unsigned32 (0..2147483647)
       MAX-ACCESS read-write
       STATUS obsolete
       DESCRIPTION
           "High threshold.
Access: Instant."
       ::= {acPMSipAttributes 9}



     acPMSipAttributesIPGroupInDialogsLowThreshold OBJECT-TYPE
       SYNTAX Unsigned32 (0..2147483647)
       MAX-ACCESS read-write
       STATUS obsolete
       DESCRIPTION
           "Low threshold.
Access: Instant."
       ::= {acPMSipAttributes 10}



     acPMSipAttributesIPGroupOutDialogsHighThreshold OBJECT-TYPE
       SYNTAX Unsigned32 (0..2147483647)
       MAX-ACCESS read-write
       STATUS obsolete
       DESCRIPTION
           "High threshold.
Access: Instant."
       ::= {acPMSipAttributes 11}



     acPMSipAttributesIPGroupOutDialogsLowThreshold OBJECT-TYPE
       SYNTAX Unsigned32 (0..2147483647)
       MAX-ACCESS read-write
       STATUS obsolete
       DESCRIPTION
           "Low threshold.
Access: Instant."
       ::= {acPMSipAttributes 12}



     acPMSipAttributesIPGroupInInviteDialogsHighThreshold OBJECT-TYPE
       SYNTAX Unsigned32 (0..2147483647)
       MAX-ACCESS read-write
       STATUS obsolete
       DESCRIPTION
           "High threshold.
Access: Instant."
       ::= {acPMSipAttributes 13}



     acPMSipAttributesIPGroupInInviteDialogsLowThreshold OBJECT-TYPE
       SYNTAX Unsigned32 (0..2147483647)
       MAX-ACCESS read-write
       STATUS obsolete
       DESCRIPTION
           "Low threshold.
Access: Instant."
       ::= {acPMSipAttributes 14}



     acPMSipAttributesIPGroupInSubscribeDialogsHighThreshold OBJECT-TYPE
       SYNTAX Unsigned32 (0..2147483647)
       MAX-ACCESS read-write
       STATUS obsolete
       DESCRIPTION
           "High threshold.
Access: Instant."
       ::= {acPMSipAttributes 15}



     acPMSipAttributesIPGroupInSubscribeDialogsLowThreshold OBJECT-TYPE
       SYNTAX Unsigned32 (0..2147483647)
       MAX-ACCESS read-write
       STATUS obsolete
       DESCRIPTION
           "Low threshold.
Access: Instant."
       ::= {acPMSipAttributes 16}



     acPMSipAttributesIPGroupInOtherDialogsHighThreshold OBJECT-TYPE
       SYNTAX Unsigned32 (0..2147483647)
       MAX-ACCESS read-write
       STATUS obsolete
       DESCRIPTION
           "High threshold.
Access: Instant."
       ::= {acPMSipAttributes 17}



     acPMSipAttributesIPGroupInOtherDialogsLowThreshold OBJECT-TYPE
       SYNTAX Unsigned32 (0..2147483647)
       MAX-ACCESS read-write
       STATUS obsolete
       DESCRIPTION
           "Low threshold.
Access: Instant."
       ::= {acPMSipAttributes 18}



     acPMSipAttributesIPGroupOutInviteDialogsHighThreshold OBJECT-TYPE
       SYNTAX Unsigned32 (0..2147483647)
       MAX-ACCESS read-write
       STATUS obsolete
       DESCRIPTION
           "High threshold.
Access: Instant."
       ::= {acPMSipAttributes 19}



     acPMSipAttributesIPGroupOutInviteDialogsLowThreshold OBJECT-TYPE
       SYNTAX Unsigned32 (0..2147483647)
       MAX-ACCESS read-write
       STATUS obsolete
       DESCRIPTION
           "Low threshold.
Access: Instant."
       ::= {acPMSipAttributes 20}



     acPMSipAttributesIPGroupOutSubscribeDialogsHighThreshold OBJECT-TYPE
       SYNTAX Unsigned32 (0..2147483647)
       MAX-ACCESS read-write
       STATUS obsolete
       DESCRIPTION
           "High threshold.
Access: Instant."
       ::= {acPMSipAttributes 21}



     acPMSipAttributesIPGroupOutSubscribeDialogsLowThreshold OBJECT-TYPE
       SYNTAX Unsigned32 (0..2147483647)
       MAX-ACCESS read-write
       STATUS obsolete
       DESCRIPTION
           "Low threshold.
Access: Instant."
       ::= {acPMSipAttributes 22}



     acPMSipAttributesIPGroupOutOtherDialogsHighThreshold OBJECT-TYPE
       SYNTAX Unsigned32 (0..2147483647)
       MAX-ACCESS read-write
       STATUS obsolete
       DESCRIPTION
           "High threshold.
Access: Instant."
       ::= {acPMSipAttributes 23}



     acPMSipAttributesIPGroupOutOtherDialogsLowThreshold OBJECT-TYPE
       SYNTAX Unsigned32 (0..2147483647)
       MAX-ACCESS read-write
       STATUS obsolete
       DESCRIPTION
           "Low threshold.
Access: Instant."
       ::= {acPMSipAttributes 24}



     acPMSipAttributesIPGroupINVITEDialogsHighThreshold OBJECT-TYPE
       SYNTAX Unsigned32 (0..2147483647)
       MAX-ACCESS read-write
       STATUS obsolete
       DESCRIPTION
           "High threshold.
Access: Instant."
       ::= {acPMSipAttributes 25}



     acPMSipAttributesIPGroupINVITEDialogsLowThreshold OBJECT-TYPE
       SYNTAX Unsigned32 (0..2147483647)
       MAX-ACCESS read-write
       STATUS obsolete
       DESCRIPTION
           "Low threshold.
Access: Instant."
       ::= {acPMSipAttributes 26}



     acPMSipAttributesIPGroupSubscribeDialogsHighThreshold OBJECT-TYPE
       SYNTAX Unsigned32 (0..2147483647)
       MAX-ACCESS read-write
       STATUS obsolete
       DESCRIPTION
           "High threshold.
Access: Instant."
       ::= {acPMSipAttributes 27}



     acPMSipAttributesIPGroupSubscribeDialogsLowThreshold OBJECT-TYPE
       SYNTAX Unsigned32 (0..2147483647)
       MAX-ACCESS read-write
       STATUS obsolete
       DESCRIPTION
           "Low threshold.
Access: Instant."
       ::= {acPMSipAttributes 28}



     acPMSipAttributesInvitedDialogsHighThreshold OBJECT-TYPE
       SYNTAX Unsigned32 (0..2147483647)
       MAX-ACCESS read-write
       STATUS obsolete
       DESCRIPTION
           "High threshold.
Access: Instant."
       ::= {acPMSipAttributes 29}



     acPMSipAttributesInvitedDialogsLowThreshold OBJECT-TYPE
       SYNTAX Unsigned32 (0..2147483647)
       MAX-ACCESS read-write
       STATUS obsolete
       DESCRIPTION
           "Low threshold.
Access: Instant."
       ::= {acPMSipAttributes 30}



     acPMSipAttributesInvitedSubscribeDialogHighThreshold OBJECT-TYPE
       SYNTAX Unsigned32 (0..2147483647)
       MAX-ACCESS read-write
       STATUS obsolete
       DESCRIPTION
           "High threshold.
Access: Instant."
       ::= {acPMSipAttributes 31}



     acPMSipAttributesInvitedSubscribeDialogLowThreshold OBJECT-TYPE
       SYNTAX Unsigned32 (0..2147483647)
       MAX-ACCESS read-write
       STATUS obsolete
       DESCRIPTION
           "Low threshold.
Access: Instant."
       ::= {acPMSipAttributes 32}



     acPMSipAttributesTrunkGroupAllTrunksBusyPercentageHighThreshold OBJECT-TYPE
       SYNTAX Unsigned32 (0..100)
       MAX-ACCESS read-write
       STATUS obsolete
       DESCRIPTION
           "High threshold.
Access: Instant."
       ::= {acPMSipAttributes 33}



     acPMSipAttributesTrunkGroupAllTrunksBusyPercentageLowThreshold OBJECT-TYPE
       SYNTAX Unsigned32 (0..100)
       MAX-ACCESS read-write
       STATUS obsolete
       DESCRIPTION
           "Low threshold.
Access: Instant."
       ::= {acPMSipAttributes 34}



     acPMSipAttributesActiveSIPTransactionsPerSecondHighThreshold OBJECT-TYPE
       SYNTAX Unsigned32 (0..2147483647)
       MAX-ACCESS read-write
       STATUS obsolete
       DESCRIPTION
           "High threshold.
Access: Instant."
       ::= {acPMSipAttributes 35}



     acPMSipAttributesActiveSIPTransactionsPerSecondLowThreshold OBJECT-TYPE
       SYNTAX Unsigned32 (0..2147483647)
       MAX-ACCESS read-write
       STATUS obsolete
       DESCRIPTION
           "Low threshold.
Access: Instant."
       ::= {acPMSipAttributes 36}



     acPMSipAttributesSBCAttemptedCallsHighThreshold OBJECT-TYPE
       SYNTAX Unsigned32 (0..2147483647)
       MAX-ACCESS read-write
       STATUS obsolete
       DESCRIPTION
           "High threshold.
Access: Instant."
       ::= {acPMSipAttributes 37}



     acPMSipAttributesSBCAttemptedCallsLowThreshold OBJECT-TYPE
       SYNTAX Unsigned32 (0..2147483647)
       MAX-ACCESS read-write
       STATUS obsolete
       DESCRIPTION
           "Low threshold.
Access: Instant."
       ::= {acPMSipAttributes 38}



     acPMSipAttributesSBCEstablishedCallsHighThreshold OBJECT-TYPE
       SYNTAX Unsigned32 (0..2147483647)
       MAX-ACCESS read-write
       STATUS obsolete
       DESCRIPTION
           "High threshold.
Access: Instant."
       ::= {acPMSipAttributes 39}



     acPMSipAttributesSBCEstablishedCallsLowThreshold OBJECT-TYPE
       SYNTAX Unsigned32 (0..2147483647)
       MAX-ACCESS read-write
       STATUS obsolete
       DESCRIPTION
           "Low threshold.
Access: Instant."
       ::= {acPMSipAttributes 40}



     acPMMediaRealmAttributes OBJECT IDENTIFIER ::= {acPMControlConfiguration 35}


     acPMMediaRealmAttributesMediaRealmBytesTxHighThreshold OBJECT-TYPE
       SYNTAX Unsigned32 (0..2147483647)
       MAX-ACCESS read-write
       STATUS obsolete
       DESCRIPTION
           "High threshold.
Access: Instant."
       ::= {acPMMediaRealmAttributes 1}



     acPMMediaRealmAttributesMediaRealmBytesTxLowThreshold OBJECT-TYPE
       SYNTAX Unsigned32 (0..2147483647)
       MAX-ACCESS read-write
       STATUS obsolete
       DESCRIPTION
           "Low threshold.
Access: Instant."
       ::= {acPMMediaRealmAttributes 2}



     acPMMediaRealmAttributesMediaRealmBytesRxHighThreshold OBJECT-TYPE
       SYNTAX Unsigned32 (0..2147483647)
       MAX-ACCESS read-write
       STATUS obsolete
       DESCRIPTION
           "High threshold.
Access: Instant."
       ::= {acPMMediaRealmAttributes 3}



     acPMMediaRealmAttributesMediaRealmBytesRxLowThreshold OBJECT-TYPE
       SYNTAX Unsigned32 (0..2147483647)
       MAX-ACCESS read-write
       STATUS obsolete
       DESCRIPTION
           "Low threshold.
Access: Instant."
       ::= {acPMMediaRealmAttributes 4}



     acPMMediaRealmAttributesMediaRealmPacketsTxHighThreshold OBJECT-TYPE
       SYNTAX Unsigned32 (0..2147483647)
       MAX-ACCESS read-write
       STATUS obsolete
       DESCRIPTION
           "High threshold.
Access: Instant."
       ::= {acPMMediaRealmAttributes 5}



     acPMMediaRealmAttributesMediaRealmPacketsTxLowThreshold OBJECT-TYPE
       SYNTAX Unsigned32 (0..2147483647)
       MAX-ACCESS read-write
       STATUS obsolete
       DESCRIPTION
           "Low threshold.
Access: Instant."
       ::= {acPMMediaRealmAttributes 6}



     acPMMediaRealmAttributesMediaRealmPacketsRxHighThreshold OBJECT-TYPE
       SYNTAX Unsigned32 (0..2147483647)
       MAX-ACCESS read-write
       STATUS obsolete
       DESCRIPTION
           "High threshold.
Access: Instant."
       ::= {acPMMediaRealmAttributes 7}



     acPMMediaRealmAttributesMediaRealmPacketsRxLowThreshold OBJECT-TYPE
       SYNTAX Unsigned32 (0..2147483647)
       MAX-ACCESS read-write
       STATUS obsolete
       DESCRIPTION
           "Low threshold.
Access: Instant."
       ::= {acPMMediaRealmAttributes 8}



     acPMMediaRealmAttributesVERealmPacketDelayHighThreshold OBJECT-TYPE
       SYNTAX Unsigned32 (0..2147483647)
       MAX-ACCESS read-write
       STATUS obsolete
       DESCRIPTION
           "High threshold.
Access: Instant."
       ::= {acPMMediaRealmAttributes 9}



     acPMMediaRealmAttributesVERealmPacketDelayLowThreshold OBJECT-TYPE
       SYNTAX Unsigned32 (0..2147483647)
       MAX-ACCESS read-write
       STATUS obsolete
       DESCRIPTION
           "Low threshold.
Access: Instant."
       ::= {acPMMediaRealmAttributes 10}



     acPMMediaRealmAttributesVERealmPacketJitterHighThreshold OBJECT-TYPE
       SYNTAX Unsigned32 (0..2147483647)
       MAX-ACCESS read-write
       STATUS obsolete
       DESCRIPTION
           "High threshold.
Access: Instant."
       ::= {acPMMediaRealmAttributes 11}



     acPMMediaRealmAttributesVERealmPacketJitterLowThreshold OBJECT-TYPE
       SYNTAX Unsigned32 (0..2147483647)
       MAX-ACCESS read-write
       STATUS obsolete
       DESCRIPTION
           "Low threshold.
Access: Instant."
       ::= {acPMMediaRealmAttributes 12}



     acPMMediaRealmAttributesRealmMOSHighThreshold OBJECT-TYPE
       SYNTAX Unsigned32 (0..2147483647)
       MAX-ACCESS read-write
       STATUS obsolete
       DESCRIPTION
           "High threshold.
Access: Instant."
       ::= {acPMMediaRealmAttributes 13}



     acPMMediaRealmAttributesRealmMOSLowThreshold OBJECT-TYPE
       SYNTAX Unsigned32 (0..2147483647)
       MAX-ACCESS read-write
       STATUS obsolete
       DESCRIPTION
           "Low threshold.
Access: Instant."
       ::= {acPMMediaRealmAttributes 14}



     acPMMediaRealmAttributesMediaRealmBwRxHighThreshold OBJECT-TYPE
       SYNTAX Unsigned32 (0..2147483647)
       MAX-ACCESS read-write
       STATUS obsolete
       DESCRIPTION
           "High threshold.
Access: Instant."
       ::= {acPMMediaRealmAttributes 15}



     acPMMediaRealmAttributesMediaRealmBwRxLowThreshold OBJECT-TYPE
       SYNTAX Unsigned32 (0..2147483647)
       MAX-ACCESS read-write
       STATUS obsolete
       DESCRIPTION
           "Low threshold.
Access: Instant."
       ::= {acPMMediaRealmAttributes 16}



     acPMMediaRealmAttributesMediaRealmBwTxHighThreshold OBJECT-TYPE
       SYNTAX Unsigned32 (0..2147483647)
       MAX-ACCESS read-write
       STATUS obsolete
       DESCRIPTION
           "High threshold.
Access: Instant."
       ::= {acPMMediaRealmAttributes 17}



     acPMMediaRealmAttributesMediaRealmBwTxLowThreshold OBJECT-TYPE
       SYNTAX Unsigned32 (0..2147483647)
       MAX-ACCESS read-write
       STATUS obsolete
       DESCRIPTION
           "Low threshold.
Access: Instant."
       ::= {acPMMediaRealmAttributes 18}



     acPMSbc OBJECT IDENTIFIER ::= {acPMControlConfiguration 36}


     acPMSbcIPGroupInCallEstablishedDurationHighThreshold OBJECT-TYPE
       SYNTAX Unsigned32 (0..2147483647)
       MAX-ACCESS read-write
       STATUS obsolete
       DESCRIPTION
           "High threshold.
Access: Instant."
       ::= {acPMSbc 1}



     acPMSbcIPGroupInCallEstablishedDurationLowThreshold OBJECT-TYPE
       SYNTAX Unsigned32 (0..2147483647)
       MAX-ACCESS read-write
       STATUS obsolete
       DESCRIPTION
           "Low threshold.
Access: Instant."
       ::= {acPMSbc 2}



     acPMSbcIPGroupOutCallEstablishedDurationHighThreshold OBJECT-TYPE
       SYNTAX Unsigned32 (0..2147483647)
       MAX-ACCESS read-write
       STATUS obsolete
       DESCRIPTION
           "High threshold.
Access: Instant."
       ::= {acPMSbc 3}



     acPMSbcIPGroupOutCallEstablishedDurationLowThreshold OBJECT-TYPE
       SYNTAX Unsigned32 (0..2147483647)
       MAX-ACCESS read-write
       STATUS obsolete
       DESCRIPTION
           "Low threshold.
Access: Instant."
       ::= {acPMSbc 4}



     acPMSbcIPGroupInAttemptedCallsHighThreshold OBJECT-TYPE
       SYNTAX Unsigned32 (0..2147483647)
       MAX-ACCESS read-write
       STATUS obsolete
       DESCRIPTION
           "High threshold.
Access: Instant."
       ::= {acPMSbc 5}



     acPMSbcIPGroupInAttemptedSubscribeDialogsHighThreshold OBJECT-TYPE
       SYNTAX Unsigned32 (0..2147483647)
       MAX-ACCESS read-write
       STATUS obsolete
       DESCRIPTION
           "High threshold.
Access: Instant."
       ::= {acPMSbc 6}



     acPMSbcIPGroupInAttemptedOtherDialogsHighThreshold OBJECT-TYPE
       SYNTAX Unsigned32 (0..2147483647)
       MAX-ACCESS read-write
       STATUS obsolete
       DESCRIPTION
           "High threshold.
Access: Instant."
       ::= {acPMSbc 7}



     acPMSbcIPGroupOutAttemptedCallsHighThreshold OBJECT-TYPE
       SYNTAX Unsigned32 (0..2147483647)
       MAX-ACCESS read-write
       STATUS obsolete
       DESCRIPTION
           "High threshold.
Access: Instant."
       ::= {acPMSbc 8}



     acPMSbcIPGroupOutAttemptedSubscribeDialogsHighThreshold OBJECT-TYPE
       SYNTAX Unsigned32 (0..2147483647)
       MAX-ACCESS read-write
       STATUS obsolete
       DESCRIPTION
           "High threshold.
Access: Instant."
       ::= {acPMSbc 9}



     acPMSbcIPGroupOutAttemptedOtherDialogsHighThreshold OBJECT-TYPE
       SYNTAX Unsigned32 (0..2147483647)
       MAX-ACCESS read-write
       STATUS obsolete
       DESCRIPTION
           "High threshold.
Access: Instant."
       ::= {acPMSbc 10}



     acPMSbcIPGroupRoutingFailedCallsHighThreshold OBJECT-TYPE
       SYNTAX Unsigned32 (0..2147483647)
       MAX-ACCESS read-write
       STATUS obsolete
       DESCRIPTION
           "High threshold.
Access: Instant."
       ::= {acPMSbc 11}



     acPMSbcIPGroupRoutingFailedSubscribeDialogsHighThreshold OBJECT-TYPE
       SYNTAX Unsigned32 (0..2147483647)
       MAX-ACCESS read-write
       STATUS obsolete
       DESCRIPTION
           "High threshold.
Access: Instant."
       ::= {acPMSbc 12}



     acPMSbcIPGroupRoutingFailedOtherDialogsHighThreshold OBJECT-TYPE
       SYNTAX Unsigned32 (0..2147483647)
       MAX-ACCESS read-write
       STATUS obsolete
       DESCRIPTION
           "High threshold.
Access: Instant."
       ::= {acPMSbc 13}



     acPMSbcIPGroupInAdmissionFailedCallsHighThreshold OBJECT-TYPE
       SYNTAX Unsigned32 (0..2147483647)
       MAX-ACCESS read-write
       STATUS obsolete
       DESCRIPTION
           "High threshold.
Access: Instant."
       ::= {acPMSbc 14}



     acPMSbcIPGroupInAdmissionFailedSubscribeDialogsHighThreshold OBJECT-TYPE
       SYNTAX Unsigned32 (0..2147483647)
       MAX-ACCESS read-write
       STATUS obsolete
       DESCRIPTION
           "High threshold.
Access: Instant."
       ::= {acPMSbc 15}



     acPMSbcIPGroupInAdmissionFailedOtherDialogsHighThreshold OBJECT-TYPE
       SYNTAX Unsigned32 (0..2147483647)
       MAX-ACCESS read-write
       STATUS obsolete
       DESCRIPTION
           "High threshold.
Access: Instant."
       ::= {acPMSbc 16}



     acPMSbcIPGroupOutAdmissionFailedCallsHighThreshold OBJECT-TYPE
       SYNTAX Unsigned32 (0..2147483647)
       MAX-ACCESS read-write
       STATUS obsolete
       DESCRIPTION
           "High threshold.
Access: Instant."
       ::= {acPMSbc 17}



     acPMSbcIPGroupOutAdmissionFailedSubscribeDialogsHighThreshold OBJECT-TYPE
       SYNTAX Unsigned32 (0..2147483647)
       MAX-ACCESS read-write
       STATUS obsolete
       DESCRIPTION
           "High threshold.
Access: Instant."
       ::= {acPMSbc 18}



     acPMSbcIPGroupOutAdmissionFailedOtherDialogsHighThreshold OBJECT-TYPE
       SYNTAX Unsigned32 (0..2147483647)
       MAX-ACCESS read-write
       STATUS obsolete
       DESCRIPTION
           "High threshold.
Access: Instant."
       ::= {acPMSbc 19}



     acPMSbcIPGroupInNoResourcesCallsHighThreshold OBJECT-TYPE
       SYNTAX Unsigned32 (0..2147483647)
       MAX-ACCESS read-write
       STATUS obsolete
       DESCRIPTION
           "High threshold.
Access: Instant."
       ::= {acPMSbc 20}



     acPMSbcIPGroupOutNoResourcesCallsHighThreshold OBJECT-TYPE
       SYNTAX Unsigned32 (0..2147483647)
       MAX-ACCESS read-write
       STATUS obsolete
       DESCRIPTION
           "High threshold.
Access: Instant."
       ::= {acPMSbc 21}



     acPMSbcIPGroupInNoMatchCallsHighThreshold OBJECT-TYPE
       SYNTAX Unsigned32 (0..2147483647)
       MAX-ACCESS read-write
       STATUS obsolete
       DESCRIPTION
           "High threshold.
Access: Instant."
       ::= {acPMSbc 22}



     acPMSbcIPGroupOutNoMatchCallsHighThreshold OBJECT-TYPE
       SYNTAX Unsigned32 (0..2147483647)
       MAX-ACCESS read-write
       STATUS obsolete
       DESCRIPTION
           "High threshold.
Access: Instant."
       ::= {acPMSbc 23}



     acPMSbcIPGroupInBusyCallsHighThreshold OBJECT-TYPE
       SYNTAX Unsigned32 (0..2147483647)
       MAX-ACCESS read-write
       STATUS obsolete
       DESCRIPTION
           "High threshold.
Access: Instant."
       ::= {acPMSbc 24}



     acPMSbcIPGroupOutBusyCallsHighThreshold OBJECT-TYPE
       SYNTAX Unsigned32 (0..2147483647)
       MAX-ACCESS read-write
       STATUS obsolete
       DESCRIPTION
           "High threshold.
Access: Instant."
       ::= {acPMSbc 25}



     acPMSbcIPGroupInNoAnswerCallsHighThreshold OBJECT-TYPE
       SYNTAX Unsigned32 (0..2147483647)
       MAX-ACCESS read-write
       STATUS obsolete
       DESCRIPTION
           "High threshold.
Access: Instant."
       ::= {acPMSbc 26}



     acPMSbcIPGroupOutNoAnswerCallsHighThreshold OBJECT-TYPE
       SYNTAX Unsigned32 (0..2147483647)
       MAX-ACCESS read-write
       STATUS obsolete
       DESCRIPTION
           "High threshold.
Access: Instant."
       ::= {acPMSbc 27}



     acPMSbcIPGroupInForwardedCallsHighThreshold OBJECT-TYPE
       SYNTAX Unsigned32 (0..2147483647)
       MAX-ACCESS read-write
       STATUS obsolete
       DESCRIPTION
           "High threshold.
Access: Instant."
       ::= {acPMSbc 28}



     acPMSbcIPGroupInForwardedSubscribeDialogsHighThreshold OBJECT-TYPE
       SYNTAX Unsigned32 (0..2147483647)
       MAX-ACCESS read-write
       STATUS obsolete
       DESCRIPTION
           "High threshold.
Access: Instant."
       ::= {acPMSbc 29}



     acPMSbcIPGroupInForwardedOtherDialogsHighThreshold OBJECT-TYPE
       SYNTAX Unsigned32 (0..2147483647)
       MAX-ACCESS read-write
       STATUS obsolete
       DESCRIPTION
           "High threshold.
Access: Instant."
       ::= {acPMSbc 30}



     acPMSbcIPGroupOutForwardedCallsHighThreshold OBJECT-TYPE
       SYNTAX Unsigned32 (0..2147483647)
       MAX-ACCESS read-write
       STATUS obsolete
       DESCRIPTION
           "High threshold.
Access: Instant."
       ::= {acPMSbc 31}



     acPMSbcIPGroupOutForwardedSubscribeDialogsHighThreshold OBJECT-TYPE
       SYNTAX Unsigned32 (0..2147483647)
       MAX-ACCESS read-write
       STATUS obsolete
       DESCRIPTION
           "High threshold.
Access: Instant."
       ::= {acPMSbc 32}



     acPMSbcIPGroupOutForwardedOtherDialogsHighThreshold OBJECT-TYPE
       SYNTAX Unsigned32 (0..2147483647)
       MAX-ACCESS read-write
       STATUS obsolete
       DESCRIPTION
           "High threshold.
Access: Instant."
       ::= {acPMSbc 33}



     acPMSbcIPGroupInGeneralFailedCallsHighThreshold OBJECT-TYPE
       SYNTAX Unsigned32 (0..2147483647)
       MAX-ACCESS read-write
       STATUS obsolete
       DESCRIPTION
           "High threshold.
Access: Instant."
       ::= {acPMSbc 34}



     acPMSbcIPGroupInGeneralFailedSubscribeDialogsHighThreshold OBJECT-TYPE
       SYNTAX Unsigned32 (0..2147483647)
       MAX-ACCESS read-write
       STATUS obsolete
       DESCRIPTION
           "High threshold.
Access: Instant."
       ::= {acPMSbc 35}



     acPMSbcIPGroupInGeneralFailedOtherDialogsHighThreshold OBJECT-TYPE
       SYNTAX Unsigned32 (0..2147483647)
       MAX-ACCESS read-write
       STATUS obsolete
       DESCRIPTION
           "High threshold.
Access: Instant."
       ::= {acPMSbc 36}



     acPMSbcIPGroupOutGeneralFailedCallsHighThreshold OBJECT-TYPE
       SYNTAX Unsigned32 (0..2147483647)
       MAX-ACCESS read-write
       STATUS obsolete
       DESCRIPTION
           "High threshold.
Access: Instant."
       ::= {acPMSbc 37}



     acPMSbcIPGroupOutGeneralFailedSubscribeDialogsHighThreshold OBJECT-TYPE
       SYNTAX Unsigned32 (0..2147483647)
       MAX-ACCESS read-write
       STATUS obsolete
       DESCRIPTION
           "High threshold.
Access: Instant."
       ::= {acPMSbc 38}



     acPMSbcIPGroupOutGeneralFailedOtherDialogsHighThreshold OBJECT-TYPE
       SYNTAX Unsigned32 (0..2147483647)
       MAX-ACCESS read-write
       STATUS obsolete
       DESCRIPTION
           "High threshold.
Access: Instant."
       ::= {acPMSbc 39}



     acPMSbcIPGroupInEstablishedCallsHighThreshold OBJECT-TYPE
       SYNTAX Unsigned32 (0..2147483647)
       MAX-ACCESS read-write
       STATUS obsolete
       DESCRIPTION
           "High threshold.
Access: Instant."
       ::= {acPMSbc 40}



     acPMSbcIPGroupInEstablishedSubscribeDialogsHighThreshold OBJECT-TYPE
       SYNTAX Unsigned32 (0..2147483647)
       MAX-ACCESS read-write
       STATUS obsolete
       DESCRIPTION
           "High threshold.
Access: Instant."
       ::= {acPMSbc 41}



     acPMSbcIPGroupInEstablishedOtherDialogsHighThreshold OBJECT-TYPE
       SYNTAX Unsigned32 (0..2147483647)
       MAX-ACCESS read-write
       STATUS obsolete
       DESCRIPTION
           "High threshold.
Access: Instant."
       ::= {acPMSbc 42}



     acPMSbcIPGroupOutEstablishedCallsHighThreshold OBJECT-TYPE
       SYNTAX Unsigned32 (0..2147483647)
       MAX-ACCESS read-write
       STATUS obsolete
       DESCRIPTION
           "High threshold.
Access: Instant."
       ::= {acPMSbc 43}



     acPMSbcIPGroupOutEstablishedSubscribeDialogsHighThreshold OBJECT-TYPE
       SYNTAX Unsigned32 (0..2147483647)
       MAX-ACCESS read-write
       STATUS obsolete
       DESCRIPTION
           "High threshold.
Access: Instant."
       ::= {acPMSbc 44}



     acPMSbcIPGroupOutEstablishedOtherDialogsHighThreshold OBJECT-TYPE
       SYNTAX Unsigned32 (0..2147483647)
       MAX-ACCESS read-write
       STATUS obsolete
       DESCRIPTION
           "High threshold.
Access: Instant."
       ::= {acPMSbc 45}



     acPMSbcIPGroupInAbnormallyTerminatedCallsHighThreshold OBJECT-TYPE
       SYNTAX Unsigned32 (0..2147483647)
       MAX-ACCESS read-write
       STATUS obsolete
       DESCRIPTION
           "High threshold.
Access: Instant."
       ::= {acPMSbc 46}



     acPMSbcIPGroupOutAbnormallyTerminatedCallsHighThreshold OBJECT-TYPE
       SYNTAX Unsigned32 (0..2147483647)
       MAX-ACCESS read-write
       STATUS obsolete
       DESCRIPTION
           "High threshold.
Access: Instant."
       ::= {acPMSbc 47}



     acPMSbcRegisteredUsersHighThreshold OBJECT-TYPE
       SYNTAX Unsigned32 (0..2147483647)
       MAX-ACCESS read-write
       STATUS obsolete
       DESCRIPTION
           "High threshold.
Access: Instant."
       ::= {acPMSbc 48}



     acPMSbcRegisteredUsersLowThreshold OBJECT-TYPE
       SYNTAX Unsigned32 (0..2147483647)
       MAX-ACCESS read-write
       STATUS obsolete
       DESCRIPTION
           "Low threshold.
Access: Instant."
       ::= {acPMSbc 49}



     acPMSbcMediaLegsHighThreshold OBJECT-TYPE
       SYNTAX Unsigned32 (0..2147483647)
       MAX-ACCESS read-write
       STATUS obsolete
       DESCRIPTION
           "High threshold.
Access: Instant."
       ::= {acPMSbc 50}



     acPMSbcMediaLegsLowThreshold OBJECT-TYPE
       SYNTAX Unsigned32 (0..2147483647)
       MAX-ACCESS read-write
       STATUS obsolete
       DESCRIPTION
           "Low threshold.
Access: Instant."
       ::= {acPMSbc 51}



     acPMSbcSBCTranscodingSessionsHighThreshold OBJECT-TYPE
       SYNTAX Unsigned32 (0..2147483647)
       MAX-ACCESS read-write
       STATUS obsolete
       DESCRIPTION
           "High threshold.
Access: Instant."
       ::= {acPMSbc 52}



     acPMSbcSBCTranscodingSessionsLowThreshold OBJECT-TYPE
       SYNTAX Unsigned32 (0..2147483647)
       MAX-ACCESS read-write
       STATUS obsolete
       DESCRIPTION
           "Low threshold.
Access: Instant."
       ::= {acPMSbc 53}



     acPMSbcSBCLadLegsHighThreshold OBJECT-TYPE
       SYNTAX Unsigned32 (0..2147483647)
       MAX-ACCESS read-write
       STATUS obsolete
       DESCRIPTION
           "High threshold.
Access: Instant."
       ::= {acPMSbc 54}



     acPMSbcSBCLadLegsLowThreshold OBJECT-TYPE
       SYNTAX Unsigned32 (0..2147483647)
       MAX-ACCESS read-write
       STATUS obsolete
       DESCRIPTION
           "Low threshold.
Access: Instant."
       ::= {acPMSbc 55}



     acPMControlData OBJECT IDENTIFIER ::= {acPMControl 2}


     acPMControlDataAcPMControlTimeFromStartOfInterval OBJECT-TYPE
       SYNTAX Unsigned32 (0..2147483647)
       MAX-ACCESS read-only
       STATUS obsolete
       DESCRIPTION
           "The time in seconds since the start of the current interval.
MIB specific."
       ::= {acPMControlData 1}



     acPMCPConnection OBJECT IDENTIFIER ::= {acPMControlData 31}


     -- ****************************************
     -- acPMCPConnectionLifetime table declaration
     -- ****************************************
     acPMCPConnectionLifetimeTable OBJECT-TYPE
       SYNTAX SEQUENCE OF AcPMCPConnectionLifetimeEntry
       MAX-ACCESS not-accessible
       STATUS obsolete
       DESCRIPTION
           "Connection lifetime in seconds."
       ::= {acPMCPConnection 1}



     -- ****************************************
     -- acPMCPConnectionLifetime table entry
     -- ****************************************
     acPMCPConnectionLifetimeEntry OBJECT-TYPE
       SYNTAX AcPMCPConnectionLifetimeEntry
       MAX-ACCESS not-accessible
       STATUS obsolete
       DESCRIPTION
           ""
       INDEX {acPMCPConnectionLifetimeInterval}
       ::= {acPMCPConnectionLifetimeTable 1}



     -- ****************************************
     -- acPMCPConnectionLifetime TABLE
     -- ****************************************
     AcPMCPConnectionLifetimeEntry ::= SEQUENCE {
       acPMCPConnectionLifetimeInterval                Unsigned32,
       acPMCPConnectionLifetimeVal                     Gauge32,
       acPMCPConnectionLifetimeAverage                 Integer32,
       acPMCPConnectionLifetimeMax                     Integer32,
       acPMCPConnectionLifetimeMin                     Integer32,
       acPMCPConnectionLifetimeVolume                  Counter32,
       acPMCPConnectionLifetimeTimeBelowLowThreshold   Integer32,
       acPMCPConnectionLifetimeTimeBetweenThresholds   Integer32,
       acPMCPConnectionLifetimeTimeAboveHighThreshold  Integer32,
       acPMCPConnectionLifetimeFullDayAverage          Integer32,
       acPMCPConnectionLifetimeTotal                   Integer32
     }



     acPMCPConnectionLifetimeInterval OBJECT-TYPE
       SYNTAX Unsigned32 (0..4)
       MAX-ACCESS not-accessible
       STATUS obsolete
       DESCRIPTION
           "Interval index.
0 - current period (incomplete monitoring - mid period).
1 - Last full period.
2 - One before last
3 - Two before last
4 - Three before last."
       ::= {acPMCPConnectionLifetimeEntry 1}



     acPMCPConnectionLifetimeVal OBJECT-TYPE
       SYNTAX Gauge32
       MAX-ACCESS read-only
       STATUS obsolete
       DESCRIPTION
           "Value of gauge or counter."
       ::= {acPMCPConnectionLifetimeEntry 2}



     acPMCPConnectionLifetimeAverage OBJECT-TYPE
       SYNTAX Integer32 (-1..2147483647)
       MAX-ACCESS read-only
       STATUS obsolete
       DESCRIPTION
           "Average value with in the period time."
       ::= {acPMCPConnectionLifetimeEntry 3}



     acPMCPConnectionLifetimeMax OBJECT-TYPE
       SYNTAX Integer32 (-1..2147483647)
       MAX-ACCESS read-only
       STATUS obsolete
       DESCRIPTION
           "Maximum value with in the period time."
       ::= {acPMCPConnectionLifetimeEntry 4}



     acPMCPConnectionLifetimeMin OBJECT-TYPE
       SYNTAX Integer32 (-1..2147483647)
       MAX-ACCESS read-only
       STATUS obsolete
       DESCRIPTION
           "Minimum value with in the period time."
       ::= {acPMCPConnectionLifetimeEntry 5}



     acPMCPConnectionLifetimeVolume OBJECT-TYPE
       SYNTAX Counter32
       MAX-ACCESS read-only
       STATUS obsolete
       DESCRIPTION
           "Activity volume."
       ::= {acPMCPConnectionLifetimeEntry 6}



     acPMCPConnectionLifetimeTimeBelowLowThreshold OBJECT-TYPE
       SYNTAX Integer32 (-1..100)
       MAX-ACCESS read-only
       STATUS obsolete
       DESCRIPTION
           "Percent of interval time for which gauge is below what was determined
as the low threshold."
       ::= {acPMCPConnectionLifetimeEntry 7}



     acPMCPConnectionLifetimeTimeBetweenThresholds OBJECT-TYPE
       SYNTAX Integer32 (-1..100)
       MAX-ACCESS read-only
       STATUS obsolete
       DESCRIPTION
           "Percent of interval time for which gauge is above what was determined
as the high threshold."
       ::= {acPMCPConnectionLifetimeEntry 8}



     acPMCPConnectionLifetimeTimeAboveHighThreshold OBJECT-TYPE
       SYNTAX Integer32 (-1..100)
       MAX-ACCESS read-only
       STATUS obsolete
       DESCRIPTION
           "Percent of interval time for which gauge is between what were
determined as the low and high thresholds."
       ::= {acPMCPConnectionLifetimeEntry 9}



     acPMCPConnectionLifetimeFullDayAverage OBJECT-TYPE
       SYNTAX Integer32 (-1..2147483647)
       MAX-ACCESS read-only
       STATUS obsolete
       DESCRIPTION
           "The average of full 24 hours."
       ::= {acPMCPConnectionLifetimeEntry 10}



     acPMCPConnectionLifetimeTotal OBJECT-TYPE
       SYNTAX Integer32 (-1..2147483647)
       MAX-ACCESS read-only
       STATUS obsolete
       DESCRIPTION
           "Total since last reset."
       ::= {acPMCPConnectionLifetimeEntry 11}



     -- ****************************************
     -- acPMCPConnectionState table declaration
     -- ****************************************
     acPMCPConnectionStateTable OBJECT-TYPE
       SYNTAX SEQUENCE OF AcPMCPConnectionStateEntry
       MAX-ACCESS not-accessible
       STATUS obsolete
       DESCRIPTION
           "MGC connection activity indicator."
       ::= {acPMCPConnection 2}



     -- ****************************************
     -- acPMCPConnectionState table entry
     -- ****************************************
     acPMCPConnectionStateEntry OBJECT-TYPE
       SYNTAX AcPMCPConnectionStateEntry
       MAX-ACCESS not-accessible
       STATUS obsolete
       DESCRIPTION
           ""
       INDEX {acPMCPConnectionStateInterval}
       ::= {acPMCPConnectionStateTable 1}



     -- ****************************************
     -- acPMCPConnectionState TABLE
     -- ****************************************
     AcPMCPConnectionStateEntry ::= SEQUENCE {
       acPMCPConnectionStateInterval                   Unsigned32,
       acPMCPConnectionStateChanges                    Gauge32,
       acPMCPConnectionStateActiveTime                 Integer32
     }



     acPMCPConnectionStateInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPConnectionStateEntry 1}



     acPMCPConnectionStateChanges OBJECT-TYPE
       SYNTAX Gauge32
       MAX-ACCESS read-only
       STATUS obsolete
       DESCRIPTION
           "Activity volume."
       ::= {acPMCPConnectionStateEntry 2}



     acPMCPConnectionStateActiveTime OBJECT-TYPE
       SYNTAX Integer32 (-1..100)
       MAX-ACCESS read-only
       STATUS obsolete
       DESCRIPTION
           "Percent of interval time for which gauge is between what were
determined as the low and high thresholds."
       ::= {acPMCPConnectionStateEntry 3}



     -- ****************************************
     -- acPMCPCommandCounter table declaration
     -- ****************************************
     acPMCPCommandCounterTable OBJECT-TYPE
       SYNTAX SEQUENCE OF AcPMCPCommandCounterEntry
       MAX-ACCESS not-accessible
       STATUS obsolete
       DESCRIPTION
           "MGC command/response counters. Index: 0=sent commands, 1=received commands"
       ::= {acPMCPConnection 3}



     -- ****************************************
     -- acPMCPCommandCounter table entry
     -- ****************************************
     acPMCPCommandCounterEntry OBJECT-TYPE
       SYNTAX AcPMCPCommandCounterEntry
       MAX-ACCESS not-accessible
       STATUS obsolete
       DESCRIPTION
           ""
       INDEX {acPMCPCommandCounterDirection,acPMCPCommandCounterInterval}
       ::= {acPMCPCommandCounterTable 1}



     -- ****************************************
     -- acPMCPCommandCounter TABLE
     -- ****************************************
     AcPMCPCommandCounterEntry ::= SEQUENCE {
       acPMCPCommandCounterDirection                   INTEGER,
       acPMCPCommandCounterInterval                    Unsigned32,
       acPMCPCommandCounterVal                         Counter32,
       acPMCPCommandCounterTotal                       Integer32
     }



     acPMCPCommandCounterDirection OBJECT-TYPE
       SYNTAX INTEGER {
                  tx(0)
,
                  rx(1)

                  }
       MAX-ACCESS not-accessible
       STATUS obsolete
       DESCRIPTION
           "Direction index.
 0 - transmit
 1 - receive."
       ::= {acPMCPCommandCounterEntry 1}



     acPMCPCommandCounterInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandCounterEntry 2}



     acPMCPCommandCounterVal OBJECT-TYPE
       SYNTAX Counter32
       MAX-ACCESS read-only
       STATUS obsolete
       DESCRIPTION
           "Value of gauge or counter."
       ::= {acPMCPCommandCounterEntry 3}



     acPMCPCommandCounterTotal OBJECT-TYPE
       SYNTAX Integer32 (-1..2147483647)
       MAX-ACCESS read-only
       STATUS obsolete
       DESCRIPTION
           "Total since last reset."
       ::= {acPMCPCommandCounterEntry 4}



     -- ****************************************
     -- acPMCPRetransmissionCount table declaration
     -- ****************************************
     acPMCPRetransmissionCountTable OBJECT-TYPE
       SYNTAX SEQUENCE OF AcPMCPRetransmissionCountEntry
       MAX-ACCESS not-accessible
       STATUS obsolete
       DESCRIPTION
           "Number of transaction retransmissions.
The first direction (tx(0)) counts the transactions sent from the board, 
while the second direction (rx(1)) counts the incoming retransmissions."
       ::= {acPMCPConnection 4}



     -- ****************************************
     -- acPMCPRetransmissionCount table entry
     -- ****************************************
     acPMCPRetransmissionCountEntry OBJECT-TYPE
       SYNTAX AcPMCPRetransmissionCountEntry
       MAX-ACCESS not-accessible
       STATUS obsolete
       DESCRIPTION
           ""
       INDEX {acPMCPRetransmissionCountDirection,acPMCPRetransmissionCountInterval}
       ::= {acPMCPRetransmissionCountTable 1}



     -- ****************************************
     -- acPMCPRetransmissionCount TABLE
     -- ****************************************
     AcPMCPRetransmissionCountEntry ::= SEQUENCE {
       acPMCPRetransmissionCountDirection              INTEGER,
       acPMCPRetransmissionCountInterval               Unsigned32,
       acPMCPRetransmissionCountVal                    Gauge32,
       acPMCPRetransmissionCountTotal                  Integer32
     }



     acPMCPRetransmissionCountDirection OBJECT-TYPE
       SYNTAX INTEGER {
                  tx(0)
,
                  rx(1)

                  }
       MAX-ACCESS not-accessible
       STATUS obsolete
       DESCRIPTION
           "Direction index.
 0 - transmit
 1 - receive."
       ::= {acPMCPRetransmissionCountEntry 1}



     acPMCPRetransmissionCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPRetransmissionCountEntry 2}



     acPMCPRetransmissionCountVal OBJECT-TYPE
       SYNTAX Gauge32
       MAX-ACCESS read-only
       STATUS obsolete
       DESCRIPTION
           "Value of gauge or counter."
       ::= {acPMCPRetransmissionCountEntry 3}



     acPMCPRetransmissionCountTotal OBJECT-TYPE
       SYNTAX Integer32 (-1..2147483647)
       MAX-ACCESS read-only
       STATUS obsolete
       DESCRIPTION
           "Total since last reset."
       ::= {acPMCPRetransmissionCountEntry 4}



     -- ****************************************
     -- acPMActiveContextCount table declaration
     -- ****************************************
     acPMActiveContextCountTable OBJECT-TYPE
       SYNTAX SEQUENCE OF AcPMActiveContextCountEntry
       MAX-ACCESS not-accessible
       STATUS obsolete
       DESCRIPTION
           "Number of active contexts"
       ::= {acPMCPConnection 5}



     -- ****************************************
     -- acPMActiveContextCount table entry
     -- ****************************************
     acPMActiveContextCountEntry OBJECT-TYPE
       SYNTAX AcPMActiveContextCountEntry
       MAX-ACCESS not-accessible
       STATUS obsolete
       DESCRIPTION
           ""
       INDEX {acPMActiveContextCountInterval}
       ::= {acPMActiveContextCountTable 1}



     -- ****************************************
     -- acPMActiveContextCount TABLE
     -- ****************************************
     AcPMActiveContextCountEntry ::= SEQUENCE {
       acPMActiveContextCountInterval                  Unsigned32,
       acPMActiveContextCountVal                       Gauge32,
       acPMActiveContextCountAverage                   Integer32,
       acPMActiveContextCountMax                       Integer32,
       acPMActiveContextCountMin                       Integer32,
       acPMActiveContextCountVolume                    Counter32,
       acPMActiveContextCountTimeBelowLowThreshold     Integer32,
       acPMActiveContextCountTimeBetweenThresholds     Integer32,
       acPMActiveContextCountTimeAboveHighThreshold    Integer32,
       acPMActiveContextCountFullDayAverage            Integer32,
       acPMActiveContextCountTotal                     Integer32
     }



     acPMActiveContextCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMActiveContextCountEntry 1}



     acPMActiveContextCountVal OBJECT-TYPE
       SYNTAX Gauge32
       MAX-ACCESS read-only
       STATUS obsolete
       DESCRIPTION
           "Value of gauge or counter."
       ::= {acPMActiveContextCountEntry 2}



     acPMActiveContextCountAverage OBJECT-TYPE
       SYNTAX Integer32 (-1..2147483647)
       MAX-ACCESS read-only
       STATUS obsolete
       DESCRIPTION
           "Average value with in the period time."
       ::= {acPMActiveContextCountEntry 3}



     acPMActiveContextCountMax OBJECT-TYPE
       SYNTAX Integer32 (-1..2147483647)
       MAX-ACCESS read-only
       STATUS obsolete
       DESCRIPTION
           "Maximum value with in the period time."
       ::= {acPMActiveContextCountEntry 4}



     acPMActiveContextCountMin OBJECT-TYPE
       SYNTAX Integer32 (-1..2147483647)
       MAX-ACCESS read-only
       STATUS obsolete
       DESCRIPTION
           "Minimum value with in the period time."
       ::= {acPMActiveContextCountEntry 5}



     acPMActiveContextCountVolume OBJECT-TYPE
       SYNTAX Counter32
       MAX-ACCESS read-only
       STATUS obsolete
       DESCRIPTION
           "Activity volume."
       ::= {acPMActiveContextCountEntry 6}



     acPMActiveContextCountTimeBelowLowThreshold OBJECT-TYPE
       SYNTAX Integer32 (-1..100)
       MAX-ACCESS read-only
       STATUS obsolete
       DESCRIPTION
           "Percent of interval time for which gauge is below what was determined
as the low threshold."
       ::= {acPMActiveContextCountEntry 7}



     acPMActiveContextCountTimeBetweenThresholds OBJECT-TYPE
       SYNTAX Integer32 (-1..100)
       MAX-ACCESS read-only
       STATUS obsolete
       DESCRIPTION
           "Percent of interval time for which gauge is above what was determined
as the high threshold."
       ::= {acPMActiveContextCountEntry 8}



     acPMActiveContextCountTimeAboveHighThreshold OBJECT-TYPE
       SYNTAX Integer32 (-1..100)
       MAX-ACCESS read-only
       STATUS obsolete
       DESCRIPTION
           "Percent of interval time for which gauge is between what were
determined as the low and high thresholds."
       ::= {acPMActiveContextCountEntry 9}



     acPMActiveContextCountFullDayAverage OBJECT-TYPE
       SYNTAX Integer32 (-1..2147483647)
       MAX-ACCESS read-only
       STATUS obsolete
       DESCRIPTION
           "The average of full 24 hours."
       ::= {acPMActiveContextCountEntry 10}



     acPMActiveContextCountTotal OBJECT-TYPE
       SYNTAX Integer32 (-1..2147483647)
       MAX-ACCESS read-only
       STATUS obsolete
       DESCRIPTION
           "Total since last reset."
       ::= {acPMActiveContextCountEntry 11}



     -- ****************************************
     -- acPMCPCommandSuccessCount table declaration
     -- ****************************************
     acPMCPCommandSuccessCountTable OBJECT-TYPE
       SYNTAX SEQUENCE OF AcPMCPCommandSuccessCountEntry
       MAX-ACCESS not-accessible
       STATUS obsolete
       DESCRIPTION
           "Number of successful commands, per command type. Index: 0=add, 1=move, 2=modify, 3=subtract, 4=SC, 5=AuditValue, 6=AuditCapabilities, 7=Notify"
       ::= {acPMCPConnection 6}



     -- ****************************************
     -- acPMCPCommandSuccessCount table entry
     -- ****************************************
     acPMCPCommandSuccessCountEntry OBJECT-TYPE
       SYNTAX AcPMCPCommandSuccessCountEntry
       MAX-ACCESS not-accessible
       STATUS obsolete
       DESCRIPTION
           ""
       INDEX {acPMCPCommandSuccessCountCommandType,acPMCPCommandSuccessCountInterval}
       ::= {acPMCPCommandSuccessCountTable 1}



     -- ****************************************
     -- acPMCPCommandSuccessCount TABLE
     -- ****************************************
     AcPMCPCommandSuccessCountEntry ::= SEQUENCE {
       acPMCPCommandSuccessCountCommandType            INTEGER,
       acPMCPCommandSuccessCountInterval               Unsigned32,
       acPMCPCommandSuccessCountVal                    Gauge32,
       acPMCPCommandSuccessCountTotal                  Integer32
     }



     acPMCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandSuccessCountEntry 1}



     acPMCPCommandSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandSuccessCountEntry 2}



     acPMCPCommandSuccessCountVal OBJECT-TYPE
       SYNTAX Gauge32
       MAX-ACCESS read-only
       STATUS obsolete
       DESCRIPTION
           "Value of gauge or counter."
       ::= {acPMCPCommandSuccessCountEntry 3}



     acPMCPCommandSuccessCountTotal OBJECT-TYPE
       SYNTAX Integer32 (-1..2147483647)
       MAX-ACCESS read-only
       STATUS obsolete
       DESCRIPTION
           "Total since last reset."
       ::= {acPMCPCommandSuccessCountEntry 4}



     -- ****************************************
     -- acPMCPCommandFailureCount table declaration
     -- ****************************************
     acPMCPCommandFailureCountTable OBJECT-TYPE
       SYNTAX SEQUENCE OF AcPMCPCommandFailureCountEntry
       MAX-ACCESS not-accessible
       STATUS obsolete
       DESCRIPTION
           "Number of failing commands, per command type. Index: 0=add, 1=move, 2=modify, 3=subtract, 4=SC, 5=AuditValue, 6=AuditCapabilities, 7=Notify"
       ::= {acPMCPConnection 7}



     -- ****************************************
     -- acPMCPCommandFailureCount table entry
     -- ****************************************
     acPMCPCommandFailureCountEntry OBJECT-TYPE
       SYNTAX AcPMCPCommandFailureCountEntry
       MAX-ACCESS not-accessible
       STATUS obsolete
       DESCRIPTION
           ""
       INDEX {acPMCPCommandFailureCountCommandType,acPMCPCommandFailureCountInterval}
       ::= {acPMCPCommandFailureCountTable 1}



     -- ****************************************
     -- acPMCPCommandFailureCount TABLE
     -- ****************************************
     AcPMCPCommandFailureCountEntry ::= SEQUENCE {
       acPMCPCommandFailureCountCommandType            INTEGER,
       acPMCPCommandFailureCountInterval               Unsigned32,
       acPMCPCommandFailureCountVal                    Gauge32,
       acPMCPCommandFailureCountTotal                  Integer32
     }



     acPMCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandFailureCountEntry 1}



     acPMCPCommandFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandFailureCountEntry 2}



     acPMCPCommandFailureCountVal OBJECT-TYPE
       SYNTAX Gauge32
       MAX-ACCESS read-only
       STATUS obsolete
       DESCRIPTION
           "Value of gauge or counter."
       ::= {acPMCPCommandFailureCountEntry 3}



     acPMCPCommandFailureCountTotal OBJECT-TYPE
       SYNTAX Integer32 (-1..2147483647)
       MAX-ACCESS read-only
       STATUS obsolete
       DESCRIPTION
           "Total since last reset."
       ::= {acPMCPCommandFailureCountEntry 4}



     -- ****************************************
     -- acPMcpCmdProcessTime table declaration
     -- ****************************************
     acPMcpCmdProcessTimeTable OBJECT-TYPE
       SYNTAX SEQUENCE OF AcPMcpCmdProcessTimeEntry
       MAX-ACCESS not-accessible
       STATUS obsolete
       DESCRIPTION
           "Processing time (in Microseconds), per command type."
       ::= {acPMCPConnection 8}



     -- ****************************************
     -- acPMcpCmdProcessTime table entry
     -- ****************************************
     acPMcpCmdProcessTimeEntry OBJECT-TYPE
       SYNTAX AcPMcpCmdProcessTimeEntry
       MAX-ACCESS not-accessible
       STATUS obsolete
       DESCRIPTION
           ""
       INDEX {acPMcpCmdProcessTimeInterval}
       ::= {acPMcpCmdProcessTimeTable 1}



     -- ****************************************
     -- acPMcpCmdProcessTime TABLE
     -- ****************************************
     AcPMcpCmdProcessTimeEntry ::= SEQUENCE {
       acPMcpCmdProcessTimeInterval                    Unsigned32,
       acPMcpCmdProcessTimeVal                         Gauge32,
       acPMcpCmdProcessTimeAverage                     Integer32,
       acPMcpCmdProcessTimeMax                         Integer32,
       acPMcpCmdProcessTimeMin                         Integer32,
       acPMcpCmdProcessTimeVolume                      Counter32,
       acPMcpCmdProcessTimeTimeBelowLowThreshold       Integer32,
       acPMcpCmdProcessTimeTimeBetweenThresholds       Integer32,
       acPMcpCmdProcessTimeTimeAboveHighThreshold      Integer32,
       acPMcpCmdProcessTimeFullDayAverage              Integer32,
       acPMcpCmdProcessTimeTotal                       Integer32
     }



     acPMcpCmdProcessTimeInterval OBJECT-TYPE
       SYNTAX Unsigned32 (0..2)
       MAX-ACCESS not-accessible
       STATUS obsolete
       DESCRIPTION
           "Interval index.
0 - current period (incomplete monitoring - mid period).
1 - Last full period.
2 - One before last."
       ::= {acPMcpCmdProcessTimeEntry 1}



     acPMcpCmdProcessTimeVal OBJECT-TYPE
       SYNTAX Gauge32
       MAX-ACCESS read-only
       STATUS obsolete
       DESCRIPTION
           "Value of gauge or counter."
       ::= {acPMcpCmdProcessTimeEntry 2}



     acPMcpCmdProcessTimeAverage OBJECT-TYPE
       SYNTAX Integer32 (-1..2147483647)
       MAX-ACCESS read-only
       STATUS obsolete
       DESCRIPTION
           "Average value with in the period time."
       ::= {acPMcpCmdProcessTimeEntry 3}



     acPMcpCmdProcessTimeMax OBJECT-TYPE
       SYNTAX Integer32 (-1..2147483647)
       MAX-ACCESS read-only
       STATUS obsolete
       DESCRIPTION
           "Maximum value with in the period time."
       ::= {acPMcpCmdProcessTimeEntry 4}



     acPMcpCmdProcessTimeMin OBJECT-TYPE
       SYNTAX Integer32 (-1..2147483647)
       MAX-ACCESS read-only
       STATUS obsolete
       DESCRIPTION
           "Minimum value with in the period time."
       ::= {acPMcpCmdProcessTimeEntry 5}



     acPMcpCmdProcessTimeVolume OBJECT-TYPE
       SYNTAX Counter32
       MAX-ACCESS read-only
       STATUS obsolete
       DESCRIPTION
           "Activity volume."
       ::= {acPMcpCmdProcessTimeEntry 6}



     acPMcpCmdProcessTimeTimeBelowLowThreshold OBJECT-TYPE
       SYNTAX Integer32 (-1..100)
       MAX-ACCESS read-only
       STATUS obsolete
       DESCRIPTION
           "Percent of interval time for which gauge is below what was determined
as the low threshold."
       ::= {acPMcpCmdProcessTimeEntry 7}



     acPMcpCmdProcessTimeTimeBetweenThresholds OBJECT-TYPE
       SYNTAX Integer32 (-1..100)
       MAX-ACCESS read-only
       STATUS obsolete
       DESCRIPTION
           "Percent of interval time for which gauge is above what was determined
as the high threshold."
       ::= {acPMcpCmdProcessTimeEntry 8}



     acPMcpCmdProcessTimeTimeAboveHighThreshold OBJECT-TYPE
       SYNTAX Integer32 (-1..100)
       MAX-ACCESS read-only
       STATUS obsolete
       DESCRIPTION
           "Percent of interval time for which gauge is between what were
determined as the low and high thresholds."
       ::= {acPMcpCmdProcessTimeEntry 9}



     acPMcpCmdProcessTimeFullDayAverage OBJECT-TYPE
       SYNTAX Integer32 (-1..2147483647)
       MAX-ACCESS read-only
       STATUS obsolete
       DESCRIPTION
           "The average of full 24 hours."
       ::= {acPMcpCmdProcessTimeEntry 10}



     acPMcpCmdProcessTimeTotal OBJECT-TYPE
       SYNTAX Integer32 (-1..2147483647)
       MAX-ACCESS read-only
       STATUS obsolete
       DESCRIPTION
           "Total since last reset."
       ::= {acPMcpCmdProcessTimeEntry 11}



     -- ****************************************
     -- acPMcpTransactionProcessTimer table declaration
     -- ****************************************
     acPMcpTransactionProcessTimerTable OBJECT-TYPE
       SYNTAX SEQUENCE OF AcPMcpTransactionProcessTimerEntry
       MAX-ACCESS not-accessible
       STATUS obsolete
       DESCRIPTION
           "Processing time (in Microseconds), For transaction request."
       ::= {acPMCPConnection 9}



     -- ****************************************
     -- acPMcpTransactionProcessTimer table entry
     -- ****************************************
     acPMcpTransactionProcessTimerEntry OBJECT-TYPE
       SYNTAX AcPMcpTransactionProcessTimerEntry
       MAX-ACCESS not-accessible
       STATUS obsolete
       DESCRIPTION
           ""
       INDEX {acPMcpTransactionProcessTimerInterval}
       ::= {acPMcpTransactionProcessTimerTable 1}



     -- ****************************************
     -- acPMcpTransactionProcessTimer TABLE
     -- ****************************************
     AcPMcpTransactionProcessTimerEntry ::= SEQUENCE {
       acPMcpTransactionProcessTimerInterval           Unsigned32,
       acPMcpTransactionProcessTimerVal                Gauge32,
       acPMcpTransactionProcessTimerAverage            Integer32,
       acPMcpTransactionProcessTimerMax                Integer32,
       acPMcpTransactionProcessTimerMin                Integer32,
       acPMcpTransactionProcessTimerVolume             Counter32,
       acPMcpTransactionProcessTimerTimeBelowLowThreshold 
                                                       Integer32,
       acPMcpTransactionProcessTimerTimeBetweenThresholds 
                                                       Integer32,
       acPMcpTransactionProcessTimerTimeAboveHighThreshold 
                                                       Integer32,
       acPMcpTransactionProcessTimerFullDayAverage     Integer32,
       acPMcpTransactionProcessTimerTotal              Integer32
     }



     acPMcpTransactionProcessTimerInterval OBJECT-TYPE
       SYNTAX Unsigned32 (0..2)
       MAX-ACCESS not-accessible
       STATUS obsolete
       DESCRIPTION
           "Interval index.
0 - current period (incomplete monitoring - mid period).
1 - Last full period.
2 - One before last."
       ::= {acPMcpTransactionProcessTimerEntry 1}



     acPMcpTransactionProcessTimerVal OBJECT-TYPE
       SYNTAX Gauge32
       MAX-ACCESS read-only
       STATUS obsolete
       DESCRIPTION
           "Value of gauge or counter."
       ::= {acPMcpTransactionProcessTimerEntry 2}



     acPMcpTransactionProcessTimerAverage OBJECT-TYPE
       SYNTAX Integer32 (-1..2147483647)
       MAX-ACCESS read-only
       STATUS obsolete
       DESCRIPTION
           "Average value with in the period time."
       ::= {acPMcpTransactionProcessTimerEntry 3}



     acPMcpTransactionProcessTimerMax OBJECT-TYPE
       SYNTAX Integer32 (-1..2147483647)
       MAX-ACCESS read-only
       STATUS obsolete
       DESCRIPTION
           "Maximum value with in the period time."
       ::= {acPMcpTransactionProcessTimerEntry 4}



     acPMcpTransactionProcessTimerMin OBJECT-TYPE
       SYNTAX Integer32 (-1..2147483647)
       MAX-ACCESS read-only
       STATUS obsolete
       DESCRIPTION
           "Minimum value with in the period time."
       ::= {acPMcpTransactionProcessTimerEntry 5}



     acPMcpTransactionProcessTimerVolume OBJECT-TYPE
       SYNTAX Counter32
       MAX-ACCESS read-only
       STATUS obsolete
       DESCRIPTION
           "Activity volume."
       ::= {acPMcpTransactionProcessTimerEntry 6}



     acPMcpTransactionProcessTimerTimeBelowLowThreshold OBJECT-TYPE
       SYNTAX Integer32 (-1..100)
       MAX-ACCESS read-only
       STATUS obsolete
       DESCRIPTION
           "Percent of interval time for which gauge is below what was determined
as the low threshold."
       ::= {acPMcpTransactionProcessTimerEntry 7}



     acPMcpTransactionProcessTimerTimeBetweenThresholds OBJECT-TYPE
       SYNTAX Integer32 (-1..100)
       MAX-ACCESS read-only
       STATUS obsolete
       DESCRIPTION
           "Percent of interval time for which gauge is above what was determined
as the high threshold."
       ::= {acPMcpTransactionProcessTimerEntry 8}



     acPMcpTransactionProcessTimerTimeAboveHighThreshold OBJECT-TYPE
       SYNTAX Integer32 (-1..100)
       MAX-ACCESS read-only
       STATUS obsolete
       DESCRIPTION
           "Percent of interval time for which gauge is between what were
determined as the low and high thresholds."
       ::= {acPMcpTransactionProcessTimerEntry 9}



     acPMcpTransactionProcessTimerFullDayAverage OBJECT-TYPE
       SYNTAX Integer32 (-1..2147483647)
       MAX-ACCESS read-only
       STATUS obsolete
       DESCRIPTION
           "The average of full 24 hours."
       ::= {acPMcpTransactionProcessTimerEntry 10}



     acPMcpTransactionProcessTimerTotal OBJECT-TYPE
       SYNTAX Integer32 (-1..2147483647)
       MAX-ACCESS read-only
       STATUS obsolete
       DESCRIPTION
           "Total since last reset."
       ::= {acPMcpTransactionProcessTimerEntry 11}



     -- ****************************************
     -- acPMCPCallAttemptsPerSec table declaration
     -- ****************************************
     acPMCPCallAttemptsPerSecTable OBJECT-TYPE
       SYNTAX SEQUENCE OF AcPMCPCallAttemptsPerSecEntry
       MAX-ACCESS not-accessible
       STATUS obsolete
       DESCRIPTION
           "Number of Call attempts (successful and unsuccessful)  for second"
       ::= {acPMCPConnection 10}



     -- ****************************************
     -- acPMCPCallAttemptsPerSec table entry
     -- ****************************************
     acPMCPCallAttemptsPerSecEntry OBJECT-TYPE
       SYNTAX AcPMCPCallAttemptsPerSecEntry
       MAX-ACCESS not-accessible
       STATUS obsolete
       DESCRIPTION
           ""
       INDEX {acPMCPCallAttemptsPerSecInterval}
       ::= {acPMCPCallAttemptsPerSecTable 1}



     -- ****************************************
     -- acPMCPCallAttemptsPerSec TABLE
     -- ****************************************
     AcPMCPCallAttemptsPerSecEntry ::= SEQUENCE {
       acPMCPCallAttemptsPerSecInterval                Unsigned32,
       acPMCPCallAttemptsPerSecVal                     Gauge32,
       acPMCPCallAttemptsPerSecAverage                 Integer32,
       acPMCPCallAttemptsPerSecMax                     Integer32,
       acPMCPCallAttemptsPerSecMin                     Integer32,
       acPMCPCallAttemptsPerSecVolume                  Counter32
     }



     acPMCPCallAttemptsPerSecInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCallAttemptsPerSecEntry 1}



     acPMCPCallAttemptsPerSecVal OBJECT-TYPE
       SYNTAX Gauge32
       MAX-ACCESS read-only
       STATUS obsolete
       DESCRIPTION
           "Value of gauge or counter."
       ::= {acPMCPCallAttemptsPerSecEntry 2}



     acPMCPCallAttemptsPerSecAverage OBJECT-TYPE
       SYNTAX Integer32 (-1..2147483647)
       MAX-ACCESS read-only
       STATUS obsolete
       DESCRIPTION
           "Average value with in the period time."
       ::= {acPMCPCallAttemptsPerSecEntry 3}



     acPMCPCallAttemptsPerSecMax OBJECT-TYPE
       SYNTAX Integer32 (-1..2147483647)
       MAX-ACCESS read-only
       STATUS obsolete
       DESCRIPTION
           "Maximum value with in the period time."
       ::= {acPMCPCallAttemptsPerSecEntry 4}



     acPMCPCallAttemptsPerSecMin OBJECT-TYPE
       SYNTAX Integer32 (-1..2147483647)
       MAX-ACCESS read-only
       STATUS obsolete
       DESCRIPTION
           "Minimum value with in the period time."
       ::= {acPMCPCallAttemptsPerSecEntry 5}



     acPMCPCallAttemptsPerSecVolume OBJECT-TYPE
       SYNTAX Counter32
       MAX-ACCESS read-only
       STATUS obsolete
       DESCRIPTION
           "Activity volume."
       ::= {acPMCPCallAttemptsPerSecEntry 6}



     acPMMegaco OBJECT IDENTIFIER ::= {acPMControlData 41}


     -- ****************************************
     -- acPMMegacoServiceChangeCount table declaration
     -- ****************************************
     acPMMegacoServiceChangeCountTable OBJECT-TYPE
       SYNTAX SEQUENCE OF AcPMMegacoServiceChangeCountEntry
       MAX-ACCESS not-accessible
       STATUS obsolete
       DESCRIPTION
           "Number of service changes, per method. Index: 0=FailOver, 1=Forced, 2=Graceful, 3=Restart, 4=Disconnected, 5=Handoff"
       ::= {acPMMegaco 1}



     -- ****************************************
     -- acPMMegacoServiceChangeCount table entry
     -- ****************************************
     acPMMegacoServiceChangeCountEntry OBJECT-TYPE
       SYNTAX AcPMMegacoServiceChangeCountEntry
       MAX-ACCESS not-accessible
       STATUS obsolete
       DESCRIPTION
           ""
       INDEX {acPMMegacoServiceChangeCountMethod,acPMMegacoServiceChangeCountInterval}
       ::= {acPMMegacoServiceChangeCountTable 1}



     -- ****************************************
     -- acPMMegacoServiceChangeCount TABLE
     -- ****************************************
     AcPMMegacoServiceChangeCountEntry ::= SEQUENCE {
       acPMMegacoServiceChangeCountMethod              INTEGER,
       acPMMegacoServiceChangeCountInterval            Unsigned32,
       acPMMegacoServiceChangeCountVal                 Gauge32
     }



     acPMMegacoServiceChangeCountMethod OBJECT-TYPE
       SYNTAX INTEGER {
                  failOver(0)
,
                  forced(1)
,
                  graceful(2)
,
                  restart(3)
,
                  disconnected(4)
,
                  handoff(5)

                  }
       MAX-ACCESS not-accessible
       STATUS obsolete
       DESCRIPTION
           "Method:
0=FailOver, 1=Forced, 2=Graceful, 3=Restart, 4=Disconnected,
5=Handoff."
       ::= {acPMMegacoServiceChangeCountEntry 1}



     acPMMegacoServiceChangeCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoServiceChangeCountEntry 2}



     acPMMegacoServiceChangeCountVal OBJECT-TYPE
       SYNTAX Gauge32
       MAX-ACCESS read-only
       STATUS obsolete
       DESCRIPTION
           "Value of gauge or counter."
       ::= {acPMMegacoServiceChangeCountEntry 3}



     -- ****************************************
     -- acPMCPCmdSuccessCount table declaration
     -- ****************************************
     acPMCPCmdSuccessCountTable OBJECT-TYPE
       SYNTAX SEQUENCE OF AcPMCPCmdSuccessCountEntry
       MAX-ACCESS not-accessible
       STATUS obsolete
       DESCRIPTION
           "Number of successful commands, per command type. Index: 0=add, 1=move, 2=modify, 3=subtract, 4=SC, 5=AuditValue, 6=AuditCapabilities, 7=Notify"
       ::= {acPMMegaco 2}



     -- ****************************************
     -- acPMCPCmdSuccessCount table entry
     -- ****************************************
     acPMCPCmdSuccessCountEntry OBJECT-TYPE
       SYNTAX AcPMCPCmdSuccessCountEntry
       MAX-ACCESS not-accessible
       STATUS obsolete
       DESCRIPTION
           ""
       INDEX {acPMCPCmdSuccessCountCommandType,acPMCPCmdSuccessCountInterval}
       ::= {acPMCPCmdSuccessCountTable 1}



     -- ****************************************
     -- acPMCPCmdSuccessCount TABLE
     -- ****************************************
     AcPMCPCmdSuccessCountEntry ::= SEQUENCE {
       acPMCPCmdSuccessCountCommandType                INTEGER,
       acPMCPCmdSuccessCountInterval                   Unsigned32,
       acPMCPCmdSuccessCountVal                        Gauge32,
       acPMCPCmdSuccessCountTotal                      Integer32
     }



     acPMCPCmdSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCmdSuccessCountEntry 1}



     acPMCPCmdSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCmdSuccessCountEntry 2}



     acPMCPCmdSuccessCountVal OBJECT-TYPE
       SYNTAX Gauge32
       MAX-ACCESS read-only
       STATUS obsolete
       DESCRIPTION
           "Value of gauge or counter."
       ::= {acPMCPCmdSuccessCountEntry 3}



     acPMCPCmdSuccessCountTotal OBJECT-TYPE
       SYNTAX Integer32 (-1..2147483647)
       MAX-ACCESS read-only
       STATUS obsolete
       DESCRIPTION
           "Total since last reset."
       ::= {acPMCPCmdSuccessCountEntry 4}



     -- ****************************************
     -- acPMCPCmdFailureCount table declaration
     -- ****************************************
     acPMCPCmdFailureCountTable OBJECT-TYPE
       SYNTAX SEQUENCE OF AcPMCPCmdFailureCountEntry
       MAX-ACCESS not-accessible
       STATUS obsolete
       DESCRIPTION
           "Number of failing commands, per command type. Index: 0=add, 1=move, 2=modify, 3=subtract, 4=SC, 5=AuditValue, 6=AuditCapabilities, 7=Notify"
       ::= {acPMMegaco 3}



     -- ****************************************
     -- acPMCPCmdFailureCount table entry
     -- ****************************************
     acPMCPCmdFailureCountEntry OBJECT-TYPE
       SYNTAX AcPMCPCmdFailureCountEntry
       MAX-ACCESS not-accessible
       STATUS obsolete
       DESCRIPTION
           ""
       INDEX {acPMCPCmdFailureCountCommandType,acPMCPCmdFailureCountInterval}
       ::= {acPMCPCmdFailureCountTable 1}



     -- ****************************************
     -- acPMCPCmdFailureCount TABLE
     -- ****************************************
     AcPMCPCmdFailureCountEntry ::= SEQUENCE {
       acPMCPCmdFailureCountCommandType                INTEGER,
       acPMCPCmdFailureCountInterval                   Unsigned32,
       acPMCPCmdFailureCountVal                        Gauge32,
       acPMCPCmdFailureCountTotal                      Integer32
     }



     acPMCPCmdFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCmdFailureCountEntry 1}



     acPMCPCmdFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCmdFailureCountEntry 2}



     acPMCPCmdFailureCountVal OBJECT-TYPE
       SYNTAX Gauge32
       MAX-ACCESS read-only
       STATUS obsolete
       DESCRIPTION
           "Value of gauge or counter."
       ::= {acPMCPCmdFailureCountEntry 3}



     acPMCPCmdFailureCountTotal OBJECT-TYPE
       SYNTAX Integer32 (-1..2147483647)
       MAX-ACCESS read-only
       STATUS obsolete
       DESCRIPTION
           "Total since last reset."
       ::= {acPMCPCmdFailureCountEntry 4}



     -- ****************************************
     -- acPMcpUMTSHandOverCount table declaration
     -- ****************************************
     acPMcpUMTSHandOverCountTable OBJECT-TYPE
       SYNTAX SEQUENCE OF AcPMcpUMTSHandOverCountEntry
       MAX-ACCESS not-accessible
       STATUS obsolete
       DESCRIPTION
           "Number of active channels per trunk (index: trunk number)."
       ::= {acPMMegaco 4}



     -- ****************************************
     -- acPMcpUMTSHandOverCount table entry
     -- ****************************************
     acPMcpUMTSHandOverCountEntry OBJECT-TYPE
       SYNTAX AcPMcpUMTSHandOverCountEntry
       MAX-ACCESS not-accessible
       STATUS obsolete
       DESCRIPTION
           ""
       INDEX {acPMcpUMTSHandOverCountInterval}
       ::= {acPMcpUMTSHandOverCountTable 1}



     -- ****************************************
     -- acPMcpUMTSHandOverCount TABLE
     -- ****************************************
     AcPMcpUMTSHandOverCountEntry ::= SEQUENCE {
       acPMcpUMTSHandOverCountInterval                 Unsigned32,
       acPMcpUMTSHandOverCountVal                      Gauge32
     }



     acPMcpUMTSHandOverCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMcpUMTSHandOverCountEntry 1}



     acPMcpUMTSHandOverCountVal OBJECT-TYPE
       SYNTAX Gauge32
       MAX-ACCESS read-only
       STATUS obsolete
       DESCRIPTION
           "Value of gauge or counter."
       ::= {acPMcpUMTSHandOverCountEntry 2}



     -- ****************************************
     -- acPMMegacoAddFailureCount table declaration
     -- ****************************************
     acPMMegacoAddFailureCountTable OBJECT-TYPE
       SYNTAX SEQUENCE OF AcPMMegacoAddFailureCountEntry
       MAX-ACCESS not-accessible
       STATUS obsolete
       DESCRIPTION
           "Number of Megaco failures for Add"
       ::= {acPMMegaco 5}



     -- ****************************************
     -- acPMMegacoAddFailureCount table entry
     -- ****************************************
     acPMMegacoAddFailureCountEntry OBJECT-TYPE
       SYNTAX AcPMMegacoAddFailureCountEntry
       MAX-ACCESS not-accessible
       STATUS obsolete
       DESCRIPTION
           ""
       INDEX {acPMMegacoAddFailureCountInterval}
       ::= {acPMMegacoAddFailureCountTable 1}



     -- ****************************************
     -- acPMMegacoAddFailureCount TABLE
     -- ****************************************
     AcPMMegacoAddFailureCountEntry ::= SEQUENCE {
       acPMMegacoAddFailureCountInterval               Unsigned32,
       acPMMegacoAddFailureCountVal                    Gauge32
     }



     acPMMegacoAddFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoAddFailureCountEntry 1}



     acPMMegacoAddFailureCountVal OBJECT-TYPE
       SYNTAX Gauge32
       MAX-ACCESS read-only
       STATUS obsolete
       DESCRIPTION
           "Value of gauge or counter."
       ::= {acPMMegacoAddFailureCountEntry 2}



     -- ****************************************
     -- acPMMegacoModifyFailureCount table declaration
     -- ****************************************
     acPMMegacoModifyFailureCountTable OBJECT-TYPE
       SYNTAX SEQUENCE OF AcPMMegacoModifyFailureCountEntry
       MAX-ACCESS not-accessible
       STATUS obsolete
       DESCRIPTION
           "Number of Megaco failures for Modify "
       ::= {acPMMegaco 6}



     -- ****************************************
     -- acPMMegacoModifyFailureCount table entry
     -- ****************************************
     acPMMegacoModifyFailureCountEntry OBJECT-TYPE
       SYNTAX AcPMMegacoModifyFailureCountEntry
       MAX-ACCESS not-accessible
       STATUS obsolete
       DESCRIPTION
           ""
       INDEX {acPMMegacoModifyFailureCountInterval}
       ::= {acPMMegacoModifyFailureCountTable 1}



     -- ****************************************
     -- acPMMegacoModifyFailureCount TABLE
     -- ****************************************
     AcPMMegacoModifyFailureCountEntry ::= SEQUENCE {
       acPMMegacoModifyFailureCountInterval            Unsigned32,
       acPMMegacoModifyFailureCountVal                 Gauge32
     }



     acPMMegacoModifyFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoModifyFailureCountEntry 1}



     acPMMegacoModifyFailureCountVal OBJECT-TYPE
       SYNTAX Gauge32
       MAX-ACCESS read-only
       STATUS obsolete
       DESCRIPTION
           "Value of gauge or counter."
       ::= {acPMMegacoModifyFailureCountEntry 2}



     -- ****************************************
     -- acPMMegacoSuccessfulAddWithLoopback table declaration
     -- ****************************************
     acPMMegacoSuccessfulAddWithLoopbackTable OBJECT-TYPE
       SYNTAX SEQUENCE OF AcPMMegacoSuccessfulAddWithLoopbackEntry
       MAX-ACCESS not-accessible
       STATUS obsolete
       DESCRIPTION
           "Number of successful Megaco Add commands with  loopback."
       ::= {acPMMegaco 7}



     -- ****************************************
     -- acPMMegacoSuccessfulAddWithLoopback table entry
     -- ****************************************
     acPMMegacoSuccessfulAddWithLoopbackEntry OBJECT-TYPE
       SYNTAX AcPMMegacoSuccessfulAddWithLoopbackEntry
       MAX-ACCESS not-accessible
       STATUS obsolete
       DESCRIPTION
           ""
       INDEX {acPMMegacoSuccessfulAddWithLoopbackInterval}
       ::= {acPMMegacoSuccessfulAddWithLoopbackTable 1}



     -- ****************************************
     -- acPMMegacoSuccessfulAddWithLoopback TABLE
     -- ****************************************
     AcPMMegacoSuccessfulAddWithLoopbackEntry ::= SEQUENCE {
       acPMMegacoSuccessfulAddWithLoopbackInterval     Unsigned32,
       acPMMegacoSuccessfulAddWithLoopbackVal          Gauge32
     }



     acPMMegacoSuccessfulAddWithLoopbackInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoSuccessfulAddWithLoopbackEntry 1}



     acPMMegacoSuccessfulAddWithLoopbackVal OBJECT-TYPE
       SYNTAX Gauge32
       MAX-ACCESS read-only
       STATUS obsolete
       DESCRIPTION
           "Value of gauge or counter."
       ::= {acPMMegacoSuccessfulAddWithLoopbackEntry 2}



     -- ****************************************
     -- acPMMegacoFailedAddWithLoopback table declaration
     -- ****************************************
     acPMMegacoFailedAddWithLoopbackTable OBJECT-TYPE
       SYNTAX SEQUENCE OF AcPMMegacoFailedAddWithLoopbackEntry
       MAX-ACCESS not-accessible
       STATUS obsolete
       DESCRIPTION
           "Number of failed  Megaco Add commands with  loopback."
       ::= {acPMMegaco 8}



     -- ****************************************
     -- acPMMegacoFailedAddWithLoopback table entry
     -- ****************************************
     acPMMegacoFailedAddWithLoopbackEntry OBJECT-TYPE
       SYNTAX AcPMMegacoFailedAddWithLoopbackEntry
       MAX-ACCESS not-accessible
       STATUS obsolete
       DESCRIPTION
           ""
       INDEX {acPMMegacoFailedAddWithLoopbackInterval}
       ::= {acPMMegacoFailedAddWithLoopbackTable 1}



     -- ****************************************
     -- acPMMegacoFailedAddWithLoopback TABLE
     -- ****************************************
     AcPMMegacoFailedAddWithLoopbackEntry ::= SEQUENCE {
       acPMMegacoFailedAddWithLoopbackInterval         Unsigned32,
       acPMMegacoFailedAddWithLoopbackVal              Gauge32
     }



     acPMMegacoFailedAddWithLoopbackInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoFailedAddWithLoopbackEntry 1}



     acPMMegacoFailedAddWithLoopbackVal OBJECT-TYPE
       SYNTAX Gauge32
       MAX-ACCESS read-only
       STATUS obsolete
       DESCRIPTION
           "Value of gauge or counter."
       ::= {acPMMegacoFailedAddWithLoopbackEntry 2}



     -- ****************************************
     -- acPMMegacoOutgoingCommandSuccessCount table declaration
     -- ****************************************
     acPMMegacoOutgoingCommandSuccessCountTable OBJECT-TYPE
       SYNTAX SEQUENCE OF AcPMMegacoOutgoingCommandSuccessCountEntry
       MAX-ACCESS not-accessible
       STATUS obsolete
       DESCRIPTION
           "Number of successful Megaco outgoing commands."
       ::= {acPMMegaco 9}



     -- ****************************************
     -- acPMMegacoOutgoingCommandSuccessCount table entry
     -- ****************************************
     acPMMegacoOutgoingCommandSuccessCountEntry OBJECT-TYPE
       SYNTAX AcPMMegacoOutgoingCommandSuccessCountEntry
       MAX-ACCESS not-accessible
       STATUS obsolete
       DESCRIPTION
           ""
       INDEX {acPMMegacoOutgoingCommandSuccessCountInterval}
       ::= {acPMMegacoOutgoingCommandSuccessCountTable 1}



     -- ****************************************
     -- acPMMegacoOutgoingCommandSuccessCount TABLE
     -- ****************************************
     AcPMMegacoOutgoingCommandSuccessCountEntry ::= SEQUENCE {
       acPMMegacoOutgoingCommandSuccessCountInterval   Unsigned32,
       acPMMegacoOutgoingCommandSuccessCountVal        Gauge32
     }



     acPMMegacoOutgoingCommandSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoOutgoingCommandSuccessCountEntry 1}



     acPMMegacoOutgoingCommandSuccessCountVal OBJECT-TYPE
       SYNTAX Gauge32
       MAX-ACCESS read-only
       STATUS obsolete
       DESCRIPTION
           "Value of gauge or counter."
       ::= {acPMMegacoOutgoingCommandSuccessCountEntry 2}



     -- ****************************************
     -- acPMMegacoOutgoingCommandFailureCount table declaration
     -- ****************************************
     acPMMegacoOutgoingCommandFailureCountTable OBJECT-TYPE
       SYNTAX SEQUENCE OF AcPMMegacoOutgoingCommandFailureCountEntry
       MAX-ACCESS not-accessible
       STATUS obsolete
       DESCRIPTION
           "Number of failed  Megaco  outgoing commands ."
       ::= {acPMMegaco 10}



     -- ****************************************
     -- acPMMegacoOutgoingCommandFailureCount table entry
     -- ****************************************
     acPMMegacoOutgoingCommandFailureCountEntry OBJECT-TYPE
       SYNTAX AcPMMegacoOutgoingCommandFailureCountEntry
       MAX-ACCESS not-accessible
       STATUS obsolete
       DESCRIPTION
           ""
       INDEX {acPMMegacoOutgoingCommandFailureCountInterval}
       ::= {acPMMegacoOutgoingCommandFailureCountTable 1}



     -- ****************************************
     -- acPMMegacoOutgoingCommandFailureCount TABLE
     -- ****************************************
     AcPMMegacoOutgoingCommandFailureCountEntry ::= SEQUENCE {
       acPMMegacoOutgoingCommandFailureCountInterval   Unsigned32,
       acPMMegacoOutgoingCommandFailureCountVal        Gauge32
     }



     acPMMegacoOutgoingCommandFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoOutgoingCommandFailureCountEntry 1}



     acPMMegacoOutgoingCommandFailureCountVal OBJECT-TYPE
       SYNTAX Gauge32
       MAX-ACCESS read-only
       STATUS obsolete
       DESCRIPTION
           "Value of gauge or counter."
       ::= {acPMMegacoOutgoingCommandFailureCountEntry 2}



     -- ****************************************
     -- acPMMegacoTransactionRequestsPerSec table declaration
     -- ****************************************
     acPMMegacoTransactionRequestsPerSecTable OBJECT-TYPE
       SYNTAX SEQUENCE OF AcPMMegacoTransactionRequestsPerSecEntry
       MAX-ACCESS not-accessible
       STATUS obsolete
       DESCRIPTION
           "Number of received Megaco transactions per second"
       ::= {acPMMegaco 11}



     -- ****************************************
     -- acPMMegacoTransactionRequestsPerSec table entry
     -- ****************************************
     acPMMegacoTransactionRequestsPerSecEntry OBJECT-TYPE
       SYNTAX AcPMMegacoTransactionRequestsPerSecEntry
       MAX-ACCESS not-accessible
       STATUS obsolete
       DESCRIPTION
           ""
       INDEX {acPMMegacoTransactionRequestsPerSecInterval}
       ::= {acPMMegacoTransactionRequestsPerSecTable 1}



     -- ****************************************
     -- acPMMegacoTransactionRequestsPerSec TABLE
     -- ****************************************
     AcPMMegacoTransactionRequestsPerSecEntry ::= SEQUENCE {
       acPMMegacoTransactionRequestsPerSecInterval     Unsigned32,
       acPMMegacoTransactionRequestsPerSecVal          Gauge32,
       acPMMegacoTransactionRequestsPerSecAverage      Integer32,
       acPMMegacoTransactionRequestsPerSecMax          Integer32,
       acPMMegacoTransactionRequestsPerSecMin          Integer32,
       acPMMegacoTransactionRequestsPerSecVolume       Counter32
     }



     acPMMegacoTransactionRequestsPerSecInterval OBJECT-TYPE
       SYNTAX Unsigned32 (0..2)
       MAX-ACCESS not-accessible
       STATUS obsolete
       DESCRIPTION
           "Interval index.
0 - current period (incomplete monitoring - mid period).
1 - Last full period.
2 - One before last."
       ::= {acPMMegacoTransactionRequestsPerSecEntry 1}



     acPMMegacoTransactionRequestsPerSecVal OBJECT-TYPE
       SYNTAX Gauge32
       MAX-ACCESS read-only
       STATUS obsolete
       DESCRIPTION
           "Value of gauge or counter."
       ::= {acPMMegacoTransactionRequestsPerSecEntry 2}



     acPMMegacoTransactionRequestsPerSecAverage OBJECT-TYPE
       SYNTAX Integer32 (-1..2147483647)
       MAX-ACCESS read-only
       STATUS obsolete
       DESCRIPTION
           "Average value with in the period time."
       ::= {acPMMegacoTransactionRequestsPerSecEntry 3}



     acPMMegacoTransactionRequestsPerSecMax OBJECT-TYPE
       SYNTAX Integer32 (-1..2147483647)
       MAX-ACCESS read-only
       STATUS obsolete
       DESCRIPTION
           "Maximum value with in the period time."
       ::= {acPMMegacoTransactionRequestsPerSecEntry 4}



     acPMMegacoTransactionRequestsPerSecMin OBJECT-TYPE
       SYNTAX Integer32 (-1..2147483647)
       MAX-ACCESS read-only
       STATUS obsolete
       DESCRIPTION
           "Minimum value with in the period time."
       ::= {acPMMegacoTransactionRequestsPerSecEntry 5}



     acPMMegacoTransactionRequestsPerSecVolume OBJECT-TYPE
       SYNTAX Counter32
       MAX-ACCESS read-only
       STATUS obsolete
       DESCRIPTION
           "Activity volume."
       ::= {acPMMegacoTransactionRequestsPerSecEntry 6}



     acPMMGCP OBJECT IDENTIFIER ::= {acPMControlData 51}


     -- ****************************************
     -- acPMMGCPRsipReasonCount table declaration
     -- ****************************************
     acPMMGCPRsipReasonCountTable OBJECT-TYPE
       SYNTAX SEQUENCE OF AcPMMGCPRsipReasonCountEntry
       MAX-ACCESS not-accessible
       STATUS obsolete
       DESCRIPTION
           "Number of RSIPs, per reason code."
       ::= {acPMMGCP 1}



     -- ****************************************
     -- acPMMGCPRsipReasonCount table entry
     -- ****************************************
     acPMMGCPRsipReasonCountEntry OBJECT-TYPE
       SYNTAX AcPMMGCPRsipReasonCountEntry
       MAX-ACCESS not-accessible
       STATUS obsolete
       DESCRIPTION
           ""
       INDEX {acPMMGCPRsipReasonCountReasonCode,acPMMGCPRsipReasonCountInterval}
       ::= {acPMMGCPRsipReasonCountTable 1}



     -- ****************************************
     -- acPMMGCPRsipReasonCount TABLE
     -- ****************************************
     AcPMMGCPRsipReasonCountEntry ::= SEQUENCE {
       acPMMGCPRsipReasonCountReasonCode               INTEGER,
       acPMMGCPRsipReasonCountInterval                 Unsigned32,
       acPMMGCPRsipReasonCountVal                      Counter32
     }



     acPMMGCPRsipReasonCountReasonCode OBJECT-TYPE
       SYNTAX INTEGER {
                  restart(0)
,
                  forced(1)
,
                  disconnected(2)
,
                  keepAlive(3)
,
                  graceful(4)
,
                  cancelGraceful(5)
,
                  resetBoard(6)
,
                  nonVoice(7)

                  }
       MAX-ACCESS not-accessible
       STATUS obsolete
       DESCRIPTION
           "Reason code. Index: 0=Restart, 1=Forced, 2=Disconnected, 3=KeepAlive,
4=Graceful, 5=CancelGraceful, 6=ResetBoard, 7=NonVoice."
       ::= {acPMMGCPRsipReasonCountEntry 1}



     acPMMGCPRsipReasonCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPRsipReasonCountEntry 2}



     acPMMGCPRsipReasonCountVal OBJECT-TYPE
       SYNTAX Counter32
       MAX-ACCESS read-only
       STATUS obsolete
       DESCRIPTION
           "Value of gauge or counter."
       ::= {acPMMGCPRsipReasonCountEntry 3}



     -- ****************************************
     -- acPMMGCPGeneratedDLCX table declaration
     -- ****************************************
     acPMMGCPGeneratedDLCXTable OBJECT-TYPE
       SYNTAX SEQUENCE OF AcPMMGCPGeneratedDLCXEntry
       MAX-ACCESS not-accessible
       STATUS obsolete
       DESCRIPTION
           "This parameter counts the number of gateway-generated DLCX commands (as opposed to DLCX commands received from the call-agent)."
       ::= {acPMMGCP 2}



     -- ****************************************
     -- acPMMGCPGeneratedDLCX table entry
     -- ****************************************
     acPMMGCPGeneratedDLCXEntry OBJECT-TYPE
       SYNTAX AcPMMGCPGeneratedDLCXEntry
       MAX-ACCESS not-accessible
       STATUS obsolete
       DESCRIPTION
           ""
       INDEX {acPMMGCPGeneratedDLCXInterval}
       ::= {acPMMGCPGeneratedDLCXTable 1}



     -- ****************************************
     -- acPMMGCPGeneratedDLCX TABLE
     -- ****************************************
     AcPMMGCPGeneratedDLCXEntry ::= SEQUENCE {
       acPMMGCPGeneratedDLCXInterval                   Unsigned32,
       acPMMGCPGeneratedDLCXVal                        Counter32
     }



     acPMMGCPGeneratedDLCXInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPGeneratedDLCXEntry 1}



     acPMMGCPGeneratedDLCXVal OBJECT-TYPE
       SYNTAX Counter32
       MAX-ACCESS read-only
       STATUS obsolete
       DESCRIPTION
           "Value of gauge or counter."
       ::= {acPMMGCPGeneratedDLCXEntry 2}



     -- ****************************************
     -- acPMMGCPCommandSuccessCount table declaration
     -- ****************************************
     acPMMGCPCommandSuccessCountTable OBJECT-TYPE
       SYNTAX SEQUENCE OF AcPMMGCPCommandSuccessCountEntry
       MAX-ACCESS not-accessible
       STATUS obsolete
       DESCRIPTION
           "Number of successful commands, per command type. Index: EPCF (0),CRCX (1),MDCX (2),DLCX (3),RQNT (4),NTFY (5),AUEP(6),AUCX (7),RSIP(8)."
       ::= {acPMMGCP 3}



     -- ****************************************
     -- acPMMGCPCommandSuccessCount table entry
     -- ****************************************
     acPMMGCPCommandSuccessCountEntry OBJECT-TYPE
       SYNTAX AcPMMGCPCommandSuccessCountEntry
       MAX-ACCESS not-accessible
       STATUS obsolete
       DESCRIPTION
           ""
       INDEX {acPMMGCPCommandSuccessCountCommandType,acPMMGCPCommandSuccessCountInterval}
       ::= {acPMMGCPCommandSuccessCountTable 1}



     -- ****************************************
     -- acPMMGCPCommandSuccessCount TABLE
     -- ****************************************
     AcPMMGCPCommandSuccessCountEntry ::= SEQUENCE {
       acPMMGCPCommandSuccessCountCommandType          INTEGER,
       acPMMGCPCommandSuccessCountInterval             Unsigned32,
       acPMMGCPCommandSuccessCountVal                  Gauge32,
       acPMMGCPCommandSuccessCountTotal                Integer32
     }



     acPMMGCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:EPCF (0),CRCX (1),MDCX (2),DLCX (3),RQNT (4),NTFY
(5),AUEP(6),AUCX (7),RSIP(8)."
       ::= {acPMMGCPCommandSuccessCountEntry 1}



     acPMMGCPCommandSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPCommandSuccessCountEntry 2}



     acPMMGCPCommandSuccessCountVal OBJECT-TYPE
       SYNTAX Gauge32
       MAX-ACCESS read-only
       STATUS obsolete
       DESCRIPTION
           "Value of gauge or counter."
       ::= {acPMMGCPCommandSuccessCountEntry 3}



     acPMMGCPCommandSuccessCountTotal OBJECT-TYPE
       SYNTAX Integer32 (-1..2147483647)
       MAX-ACCESS read-only
       STATUS obsolete
       DESCRIPTION
           "Total since last reset."
       ::= {acPMMGCPCommandSuccessCountEntry 4}



     -- ****************************************
     -- acPMMGCPCommandFailureCount table declaration
     -- ****************************************
     acPMMGCPCommandFailureCountTable OBJECT-TYPE
       SYNTAX SEQUENCE OF AcPMMGCPCommandFailureCountEntry
       MAX-ACCESS not-accessible
       STATUS obsolete
       DESCRIPTION
           "Number of failing commands, per command type. Index: EPCF (0),CRCX (1),MDCX (2),DLCX (3),RQNT (4),NTFY (5),AUEP(6),AUCX (7),RSIP(8)."
       ::= {acPMMGCP 4}



     -- ****************************************
     -- acPMMGCPCommandFailureCount table entry
     -- ****************************************
     acPMMGCPCommandFailureCountEntry OBJECT-TYPE
       SYNTAX AcPMMGCPCommandFailureCountEntry
       MAX-ACCESS not-accessible
       STATUS obsolete
       DESCRIPTION
           ""
       INDEX {acPMMGCPCommandFailureCountCommandType,acPMMGCPCommandFailureCountInterval}
       ::= {acPMMGCPCommandFailureCountTable 1}



     -- ****************************************
     -- acPMMGCPCommandFailureCount TABLE
     -- ****************************************
     AcPMMGCPCommandFailureCountEntry ::= SEQUENCE {
       acPMMGCPCommandFailureCountCommandType          INTEGER,
       acPMMGCPCommandFailureCountInterval             Unsigned32,
       acPMMGCPCommandFailureCountVal                  Gauge32,
       acPMMGCPCommandFailureCountTotal                Integer32
     }



     acPMMGCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:EPCF (0),CRCX (1),MDCX (2),DLCX (3),RQNT (4),NTFY
(5),AUEP(6),AUCX (7),RSIP(8)."
       ::= {acPMMGCPCommandFailureCountEntry 1}



     acPMMGCPCommandFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPCommandFailureCountEntry 2}



     acPMMGCPCommandFailureCountVal OBJECT-TYPE
       SYNTAX Gauge32
       MAX-ACCESS read-only
       STATUS obsolete
       DESCRIPTION
           "Value of gauge or counter."
       ::= {acPMMGCPCommandFailureCountEntry 3}



     acPMMGCPCommandFailureCountTotal OBJECT-TYPE
       SYNTAX Integer32 (-1..2147483647)
       MAX-ACCESS read-only
       STATUS obsolete
       DESCRIPTION
           "Total since last reset."
       ::= {acPMMGCPCommandFailureCountEntry 4}



     -- ****************************************
     -- acPMMGCPLoopbackCRCX table declaration
     -- ****************************************
     acPMMGCPLoopbackCRCXTable OBJECT-TYPE
       SYNTAX SEQUENCE OF AcPMMGCPLoopbackCRCXEntry
       MAX-ACCESS not-accessible
       STATUS obsolete
       DESCRIPTION
           ""
       ::= {acPMMGCP 5}



     -- ****************************************
     -- acPMMGCPLoopbackCRCX table entry
     -- ****************************************
     acPMMGCPLoopbackCRCXEntry OBJECT-TYPE
       SYNTAX AcPMMGCPLoopbackCRCXEntry
       MAX-ACCESS not-accessible
       STATUS obsolete
       DESCRIPTION
           ""
       INDEX {acPMMGCPLoopbackCRCXInterval}
       ::= {acPMMGCPLoopbackCRCXTable 1}



     -- ****************************************
     -- acPMMGCPLoopbackCRCX TABLE
     -- ****************************************
     AcPMMGCPLoopbackCRCXEntry ::= SEQUENCE {
       acPMMGCPLoopbackCRCXInterval                    Unsigned32,
       acPMMGCPLoopbackCRCXVal                         Counter32
     }



     acPMMGCPLoopbackCRCXInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPLoopbackCRCXEntry 1}



     acPMMGCPLoopbackCRCXVal OBJECT-TYPE
       SYNTAX Counter32
       MAX-ACCESS read-only
       STATUS obsolete
       DESCRIPTION
           "Value of gauge or counter."
       ::= {acPMMGCPLoopbackCRCXEntry 2}



     -- ****************************************
     -- acPMMGCPFailedLoopbackCRCX table declaration
     -- ****************************************
     acPMMGCPFailedLoopbackCRCXTable OBJECT-TYPE
       SYNTAX SEQUENCE OF AcPMMGCPFailedLoopbackCRCXEntry
       MAX-ACCESS not-accessible
       STATUS obsolete
       DESCRIPTION
           ""
       ::= {acPMMGCP 6}



     -- ****************************************
     -- acPMMGCPFailedLoopbackCRCX table entry
     -- ****************************************
     acPMMGCPFailedLoopbackCRCXEntry OBJECT-TYPE
       SYNTAX AcPMMGCPFailedLoopbackCRCXEntry
       MAX-ACCESS not-accessible
       STATUS obsolete
       DESCRIPTION
           ""
       INDEX {acPMMGCPFailedLoopbackCRCXInterval}
       ::= {acPMMGCPFailedLoopbackCRCXTable 1}



     -- ****************************************
     -- acPMMGCPFailedLoopbackCRCX TABLE
     -- ****************************************
     AcPMMGCPFailedLoopbackCRCXEntry ::= SEQUENCE {
       acPMMGCPFailedLoopbackCRCXInterval              Unsigned32,
       acPMMGCPFailedLoopbackCRCXVal                   Counter32
     }



     acPMMGCPFailedLoopbackCRCXInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPFailedLoopbackCRCXEntry 1}



     acPMMGCPFailedLoopbackCRCXVal OBJECT-TYPE
       SYNTAX Counter32
       MAX-ACCESS read-only
       STATUS obsolete
       DESCRIPTION
           "Value of gauge or counter."
       ::= {acPMMGCPFailedLoopbackCRCXEntry 2}



     -- ****************************************
     -- acPMMGCPGeneratedNTFY table declaration
     -- ****************************************
     acPMMGCPGeneratedNTFYTable OBJECT-TYPE
       SYNTAX SEQUENCE OF AcPMMGCPGeneratedNTFYEntry
       MAX-ACCESS not-accessible
       STATUS obsolete
       DESCRIPTION
           ""
       ::= {acPMMGCP 7}



     -- ****************************************
     -- acPMMGCPGeneratedNTFY table entry
     -- ****************************************
     acPMMGCPGeneratedNTFYEntry OBJECT-TYPE
       SYNTAX AcPMMGCPGeneratedNTFYEntry
       MAX-ACCESS not-accessible
       STATUS obsolete
       DESCRIPTION
           ""
       INDEX {acPMMGCPGeneratedNTFYInterval}
       ::= {acPMMGCPGeneratedNTFYTable 1}



     -- ****************************************
     -- acPMMGCPGeneratedNTFY TABLE
     -- ****************************************
     AcPMMGCPGeneratedNTFYEntry ::= SEQUENCE {
       acPMMGCPGeneratedNTFYInterval                   Unsigned32,
       acPMMGCPGeneratedNTFYVal                        Counter32
     }



     acPMMGCPGeneratedNTFYInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPGeneratedNTFYEntry 1}



     acPMMGCPGeneratedNTFYVal OBJECT-TYPE
       SYNTAX Counter32
       MAX-ACCESS read-only
       STATUS obsolete
       DESCRIPTION
           "Value of gauge or counter."
       ::= {acPMMGCPGeneratedNTFYEntry 2}



     -- ****************************************
     -- acPMMGCPFailedNTFYResponses table declaration
     -- ****************************************
     acPMMGCPFailedNTFYResponsesTable OBJECT-TYPE
       SYNTAX SEQUENCE OF AcPMMGCPFailedNTFYResponsesEntry
       MAX-ACCESS not-accessible
       STATUS obsolete
       DESCRIPTION
           ""
       ::= {acPMMGCP 8}



     -- ****************************************
     -- acPMMGCPFailedNTFYResponses table entry
     -- ****************************************
     acPMMGCPFailedNTFYResponsesEntry OBJECT-TYPE
       SYNTAX AcPMMGCPFailedNTFYResponsesEntry
       MAX-ACCESS not-accessible
       STATUS obsolete
       DESCRIPTION
           ""
       INDEX {acPMMGCPFailedNTFYResponsesInterval}
       ::= {acPMMGCPFailedNTFYResponsesTable 1}



     -- ****************************************
     -- acPMMGCPFailedNTFYResponses TABLE
     -- ****************************************
     AcPMMGCPFailedNTFYResponsesEntry ::= SEQUENCE {
       acPMMGCPFailedNTFYResponsesInterval             Unsigned32,
       acPMMGCPFailedNTFYResponsesVal                  Counter32
     }



     acPMMGCPFailedNTFYResponsesInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPFailedNTFYResponsesEntry 1}



     acPMMGCPFailedNTFYResponsesVal OBJECT-TYPE
       SYNTAX Counter32
       MAX-ACCESS read-only
       STATUS obsolete
       DESCRIPTION
           "Value of gauge or counter."
       ::= {acPMMGCPFailedNTFYResponsesEntry 2}



     -- ****************************************
     -- acPMMGCPFailedRSIPResponses table declaration
     -- ****************************************
     acPMMGCPFailedRSIPResponsesTable OBJECT-TYPE
       SYNTAX SEQUENCE OF AcPMMGCPFailedRSIPResponsesEntry
       MAX-ACCESS not-accessible
       STATUS obsolete
       DESCRIPTION
           ""
       ::= {acPMMGCP 9}



     -- ****************************************
     -- acPMMGCPFailedRSIPResponses table entry
     -- ****************************************
     acPMMGCPFailedRSIPResponsesEntry OBJECT-TYPE
       SYNTAX AcPMMGCPFailedRSIPResponsesEntry
       MAX-ACCESS not-accessible
       STATUS obsolete
       DESCRIPTION
           ""
       INDEX {acPMMGCPFailedRSIPResponsesInterval}
       ::= {acPMMGCPFailedRSIPResponsesTable 1}



     -- ****************************************
     -- acPMMGCPFailedRSIPResponses TABLE
     -- ****************************************
     AcPMMGCPFailedRSIPResponsesEntry ::= SEQUENCE {
       acPMMGCPFailedRSIPResponsesInterval             Unsigned32,
       acPMMGCPFailedRSIPResponsesVal                  Counter32
     }



     acPMMGCPFailedRSIPResponsesInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPFailedRSIPResponsesEntry 1}



     acPMMGCPFailedRSIPResponsesVal OBJECT-TYPE
       SYNTAX Counter32
       MAX-ACCESS read-only
       STATUS obsolete
       DESCRIPTION
           "Value of gauge or counter."
       ::= {acPMMGCPFailedRSIPResponsesEntry 2}



     -- ****************************************
     -- acPMMGCPFailedCRCXResponses table declaration
     -- ****************************************
     acPMMGCPFailedCRCXResponsesTable OBJECT-TYPE
       SYNTAX SEQUENCE OF AcPMMGCPFailedCRCXResponsesEntry
       MAX-ACCESS not-accessible
       STATUS obsolete
       DESCRIPTION
           "Number of failed responses to CRCX commands, per reason code."
       ::= {acPMMGCP 10}



     -- ****************************************
     -- acPMMGCPFailedCRCXResponses table entry
     -- ****************************************
     acPMMGCPFailedCRCXResponsesEntry OBJECT-TYPE
       SYNTAX AcPMMGCPFailedCRCXResponsesEntry
       MAX-ACCESS not-accessible
       STATUS obsolete
       DESCRIPTION
           ""
       INDEX {acPMMGCPFailedCRCXResponsesReasonCode,acPMMGCPFailedCRCXResponsesInterval}
       ::= {acPMMGCPFailedCRCXResponsesTable 1}



     -- ****************************************
     -- acPMMGCPFailedCRCXResponses TABLE
     -- ****************************************
     AcPMMGCPFailedCRCXResponsesEntry ::= SEQUENCE {
       acPMMGCPFailedCRCXResponsesReasonCode           INTEGER,
       acPMMGCPFailedCRCXResponsesInterval             Unsigned32,
       acPMMGCPFailedCRCXResponsesVal                  Counter32
     }



     acPMMGCPFailedCRCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS obsolete
       DESCRIPTION
           "Reason code Index. The Numbers at the values are as in the RFC."
       ::= {acPMMGCPFailedCRCXResponsesEntry 1}



     acPMMGCPFailedCRCXResponsesInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPFailedCRCXResponsesEntry 2}



     acPMMGCPFailedCRCXResponsesVal OBJECT-TYPE
       SYNTAX Counter32
       MAX-ACCESS read-only
       STATUS obsolete
       DESCRIPTION
           "Value of gauge or counter."
       ::= {acPMMGCPFailedCRCXResponsesEntry 3}



     -- ****************************************
     -- acPMMGCPFailedMDCXResponses table declaration
     -- ****************************************
     acPMMGCPFailedMDCXResponsesTable OBJECT-TYPE
       SYNTAX SEQUENCE OF AcPMMGCPFailedMDCXResponsesEntry
       MAX-ACCESS not-accessible
       STATUS obsolete
       DESCRIPTION
           "Number of failed responses to CRCX commands, per reason code."
       ::= {acPMMGCP 11}



     -- ****************************************
     -- acPMMGCPFailedMDCXResponses table entry
     -- ****************************************
     acPMMGCPFailedMDCXResponsesEntry OBJECT-TYPE
       SYNTAX AcPMMGCPFailedMDCXResponsesEntry
       MAX-ACCESS not-accessible
       STATUS obsolete
       DESCRIPTION
           ""
       INDEX {acPMMGCPFailedMDCXResponsesReasonCode,acPMMGCPFailedMDCXResponsesInterval}
       ::= {acPMMGCPFailedMDCXResponsesTable 1}



     -- ****************************************
     -- acPMMGCPFailedMDCXResponses TABLE
     -- ****************************************
     AcPMMGCPFailedMDCXResponsesEntry ::= SEQUENCE {
       acPMMGCPFailedMDCXResponsesReasonCode           INTEGER,
       acPMMGCPFailedMDCXResponsesInterval             Unsigned32,
       acPMMGCPFailedMDCXResponsesVal                  Counter32
     }



     acPMMGCPFailedMDCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS obsolete
       DESCRIPTION
           "Reason code Index. The Numbers at the values are as in the RFC."
       ::= {acPMMGCPFailedMDCXResponsesEntry 1}



     acPMMGCPFailedMDCXResponsesInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPFailedMDCXResponsesEntry 2}



     acPMMGCPFailedMDCXResponsesVal OBJECT-TYPE
       SYNTAX Counter32
       MAX-ACCESS read-only
       STATUS obsolete
       DESCRIPTION
           "Value of gauge or counter."
       ::= {acPMMGCPFailedMDCXResponsesEntry 3}



     -- ****************************************
     -- acPMMGCPGeneratedDLCXPerReasonCode table declaration
     -- ****************************************
     acPMMGCPGeneratedDLCXPerReasonCodeTable OBJECT-TYPE
       SYNTAX SEQUENCE OF AcPMMGCPGeneratedDLCXPerReasonCodeEntry
       MAX-ACCESS not-accessible
       STATUS obsolete
       DESCRIPTION
           "Number of gateway-generated DLCX commands per reason code. when you choose 0 its 900(ENDPOINT_MALFUNCTIONING) and so on."
       ::= {acPMMGCP 12}



     -- ****************************************
     -- acPMMGCPGeneratedDLCXPerReasonCode table entry
     -- ****************************************
     acPMMGCPGeneratedDLCXPerReasonCodeEntry OBJECT-TYPE
       SYNTAX AcPMMGCPGeneratedDLCXPerReasonCodeEntry
       MAX-ACCESS not-accessible
       STATUS obsolete
       DESCRIPTION
           ""
       INDEX {acPMMGCPGeneratedDLCXPerReasonCodeReasonCode,acPMMGCPGeneratedDLCXPerReasonCodeInterval}
       ::= {acPMMGCPGeneratedDLCXPerReasonCodeTable 1}



     -- ****************************************
     -- acPMMGCPGeneratedDLCXPerReasonCode TABLE
     -- ****************************************
     AcPMMGCPGeneratedDLCXPerReasonCodeEntry ::= SEQUENCE {
       acPMMGCPGeneratedDLCXPerReasonCodeReasonCode    INTEGER,
       acPMMGCPGeneratedDLCXPerReasonCodeInterval      Unsigned32,
       acPMMGCPGeneratedDLCXPerReasonCodeVal           Counter32
     }



     acPMMGCPGeneratedDLCXPerReasonCodeReasonCode OBJECT-TYPE
       SYNTAX INTEGER {
                  eNDPOINT-MALFUNCTIONING-900(0)
,
                  eNDPOINT-TAKEN-OUT-OF-SERVICE-901(1)
,
                  lOSS-OF-LOWER-LAYER-CONNECTIVITY-902(2)
,
                  qOS-RESOURCE-RESERVATION-WAS-LOST-903(3)
,
                  mANUAL-INTERVENTION-904(4)
,
                  fACILITY-FAILURE-905(5)

                  }
       MAX-ACCESS not-accessible
       STATUS obsolete
       DESCRIPTION
           "Reason code Index. The Numbers at the values are as in the RFC."
       ::= {acPMMGCPGeneratedDLCXPerReasonCodeEntry 1}



     acPMMGCPGeneratedDLCXPerReasonCodeInterval OBJECT-TYPE
       SYNTAX Unsigned32 (0..2)
       MAX-ACCESS not-accessible
       STATUS obsolete
       DESCRIPTION
           "Interval index.
0 - current period (incomplete monitoring - mid period).
1 - Last full period.
2 - One before last."
       ::= {acPMMGCPGeneratedDLCXPerReasonCodeEntry 2}



     acPMMGCPGeneratedDLCXPerReasonCodeVal OBJECT-TYPE
       SYNTAX Counter32
       MAX-ACCESS read-only
       STATUS obsolete
       DESCRIPTION
           "Value of gauge or counter."
       ::= {acPMMGCPGeneratedDLCXPerReasonCodeEntry 3}



     acPMSIP OBJECT IDENTIFIER ::= {acPMControlData 52}


     -- ****************************************
     -- acPMSIPAttemptedCalls table declaration
     -- ****************************************
     acPMSIPAttemptedCallsTable OBJECT-TYPE
       SYNTAX SEQUENCE OF AcPMSIPAttemptedCallsEntry
       MAX-ACCESS not-accessible
       STATUS obsolete
       DESCRIPTION
           "Number of attempted calls (Index 0 for TEL2IP and Index 1 for IP2TEL)"
       ::= {acPMSIP 1}



     -- ****************************************
     -- acPMSIPAttemptedCalls table entry
     -- ****************************************
     acPMSIPAttemptedCallsEntry OBJECT-TYPE
       SYNTAX AcPMSIPAttemptedCallsEntry
       MAX-ACCESS not-accessible
       STATUS obsolete
       DESCRIPTION
           ""
       INDEX {acPMSIPAttemptedCallsDirection,acPMSIPAttemptedCallsInterval}
       ::= {acPMSIPAttemptedCallsTable 1}



     -- ****************************************
     -- acPMSIPAttemptedCalls TABLE
     -- ****************************************
     AcPMSIPAttemptedCallsEntry ::= SEQUENCE {
       acPMSIPAttemptedCallsDirection                  INTEGER,
       acPMSIPAttemptedCallsInterval                   Unsigned32,
       acPMSIPAttemptedCallsVal                        Counter32
     }



     acPMSIPAttemptedCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPAttemptedCallsEntry 1}



     acPMSIPAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPAttemptedCallsEntry 2}



     acPMSIPAttemptedCallsVal OBJECT-TYPE
       SYNTAX Counter32
       MAX-ACCESS read-only
       STATUS obsolete
       DESCRIPTION
           "Value of gauge or counter."
       ::= {acPMSIPAttemptedCallsEntry 3}



     -- ****************************************
     -- acPMSIPCallDuration table declaration
     -- ****************************************
     acPMSIPCallDurationTable OBJECT-TYPE
       SYNTAX SEQUENCE OF AcPMSIPCallDurationEntry
       MAX-ACCESS not-accessible
       STATUS obsolete
       DESCRIPTION
           "Call Duration (Index 0 for Tel2IP and Index 1 for IP2Tel);The Total preprty gives the sum of all calls duration, while the Value property is for the last call only"
       ::= {acPMSIP 2}



     -- ****************************************
     -- acPMSIPCallDuration table entry
     -- ****************************************
     acPMSIPCallDurationEntry OBJECT-TYPE
       SYNTAX AcPMSIPCallDurationEntry
       MAX-ACCESS not-accessible
       STATUS obsolete
       DESCRIPTION
           ""
       INDEX {acPMSIPCallDurationDirection,acPMSIPCallDurationInterval}
       ::= {acPMSIPCallDurationTable 1}



     -- ****************************************
     -- acPMSIPCallDuration TABLE
     -- ****************************************
     AcPMSIPCallDurationEntry ::= SEQUENCE {
       acPMSIPCallDurationDirection                    INTEGER,
       acPMSIPCallDurationInterval                     Unsigned32,
       acPMSIPCallDurationVal                          Gauge32,
       acPMSIPCallDurationAverage                      Integer32,
       acPMSIPCallDurationMax                          Integer32,
       acPMSIPCallDurationMin                          Integer32,
       acPMSIPCallDurationVolume                       Counter32,
       acPMSIPCallDurationTimeBelowLowThreshold        Integer32,
       acPMSIPCallDurationTimeBetweenThresholds        Integer32,
       acPMSIPCallDurationTimeAboveHighThreshold       Integer32,
       acPMSIPCallDurationFullDayAverage               Integer32,
       acPMSIPCallDurationTotal                        Integer32
     }



     acPMSIPCallDurationDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPCallDurationEntry 1}



     acPMSIPCallDurationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPCallDurationEntry 2}



     acPMSIPCallDurationVal OBJECT-TYPE
       SYNTAX Gauge32
       MAX-ACCESS read-only
       STATUS obsolete
       DESCRIPTION
           "Value of gauge or counter."
       ::= {acPMSIPCallDurationEntry 3}



     acPMSIPCallDurationAverage OBJECT-TYPE
       SYNTAX Integer32 (-1..2147483647)
       MAX-ACCESS read-only
       STATUS obsolete
       DESCRIPTION
           "Average value with in the period time."
       ::= {acPMSIPCallDurationEntry 4}



     acPMSIPCallDurationMax OBJECT-TYPE
       SYNTAX Integer32 (-1..2147483647)
       MAX-ACCESS read-only
       STATUS obsolete
       DESCRIPTION
           "Maximum value with in the period time."
       ::= {acPMSIPCallDurationEntry 5}



     acPMSIPCallDurationMin OBJECT-TYPE
       SYNTAX Integer32 (-1..2147483647)
       MAX-ACCESS read-only
       STATUS obsolete
       DESCRIPTION
           "Minimum value with in the period time."
       ::= {acPMSIPCallDurationEntry 6}



     acPMSIPCallDurationVolume OBJECT-TYPE
       SYNTAX Counter32
       MAX-ACCESS read-only
       STATUS obsolete
       DESCRIPTION
           "Activity volume."
       ::= {acPMSIPCallDurationEntry 7}



     acPMSIPCallDurationTimeBelowLowThreshold OBJECT-TYPE
       SYNTAX Integer32 (-1..100)
       MAX-ACCESS read-only
       STATUS obsolete
       DESCRIPTION
           "Percent of interval time for which gauge is below what was determined
as the low threshold."
       ::= {acPMSIPCallDurationEntry 8}



     acPMSIPCallDurationTimeBetweenThresholds OBJECT-TYPE
       SYNTAX Integer32 (-1..100)
       MAX-ACCESS read-only
       STATUS obsolete
       DESCRIPTION
           "Percent of interval time for which gauge is above what was determined
as the high threshold."
       ::= {acPMSIPCallDurationEntry 9}



     acPMSIPCallDurationTimeAboveHighThreshold OBJECT-TYPE
       SYNTAX Integer32 (-1..100)
       MAX-ACCESS read-only
       STATUS obsolete
       DESCRIPTION
           "Percent of interval time for which gauge is between what were
determined as the low and high thresholds."
       ::= {acPMSIPCallDurationEntry 10}



     acPMSIPCallDurationFullDayAverage OBJECT-TYPE
       SYNTAX Integer32 (-1..2147483647)
       MAX-ACCESS read-only
       STATUS obsolete
       DESCRIPTION
           "The average of full 24 hours."
       ::= {acPMSIPCallDurationEntry 11}



     acPMSIPCallDurationTotal OBJECT-TYPE
       SYNTAX Integer32 (-1..2147483647)
       MAX-ACCESS read-only
       STATUS obsolete
       DESCRIPTION
           "Total since last reset."
       ::= {acPMSIPCallDurationEntry 12}



     -- ****************************************
     -- acPMSIPNoMatchCalls table declaration
     -- ****************************************
     acPMSIPNoMatchCallsTable OBJECT-TYPE
       SYNTAX SEQUENCE OF AcPMSIPNoMatchCallsEntry
       MAX-ACCESS not-accessible
       STATUS obsolete
       DESCRIPTION
           "Number of no match calls (Index 0 for TEL2IP and Index 1 for IP2TEL)"
       ::= {acPMSIP 3}



     -- ****************************************
     -- acPMSIPNoMatchCalls table entry
     -- ****************************************
     acPMSIPNoMatchCallsEntry OBJECT-TYPE
       SYNTAX AcPMSIPNoMatchCallsEntry
       MAX-ACCESS not-accessible
       STATUS obsolete
       DESCRIPTION
           ""
       INDEX {acPMSIPNoMatchCallsDirection,acPMSIPNoMatchCallsInterval}
       ::= {acPMSIPNoMatchCallsTable 1}



     -- ****************************************
     -- acPMSIPNoMatchCalls TABLE
     -- ****************************************
     AcPMSIPNoMatchCallsEntry ::= SEQUENCE {
       acPMSIPNoMatchCallsDirection                    INTEGER,
       acPMSIPNoMatchCallsInterval                     Unsigned32,
       acPMSIPNoMatchCallsVal                          Counter32
     }



     acPMSIPNoMatchCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPNoMatchCallsEntry 1}



     acPMSIPNoMatchCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPNoMatchCallsEntry 2}



     acPMSIPNoMatchCallsVal OBJECT-TYPE
       SYNTAX Counter32
       MAX-ACCESS read-only
       STATUS obsolete
       DESCRIPTION
           "Value of gauge or counter."
       ::= {acPMSIPNoMatchCallsEntry 3}



     -- ****************************************
     -- acPMSIPBusyCalls table declaration
     -- ****************************************
     acPMSIPBusyCallsTable OBJECT-TYPE
       SYNTAX SEQUENCE OF AcPMSIPBusyCallsEntry
       MAX-ACCESS not-accessible
       STATUS obsolete
       DESCRIPTION
           "Number of busy calls (Index 0 for TEL2IP and Index 1 for IP2TEL)"
       ::= {acPMSIP 4}



     -- ****************************************
     -- acPMSIPBusyCalls table entry
     -- ****************************************
     acPMSIPBusyCallsEntry OBJECT-TYPE
       SYNTAX AcPMSIPBusyCallsEntry
       MAX-ACCESS not-accessible
       STATUS obsolete
       DESCRIPTION
           ""
       INDEX {acPMSIPBusyCallsDirection,acPMSIPBusyCallsInterval}
       ::= {acPMSIPBusyCallsTable 1}



     -- ****************************************
     -- acPMSIPBusyCalls TABLE
     -- ****************************************
     AcPMSIPBusyCallsEntry ::= SEQUENCE {
       acPMSIPBusyCallsDirection                       INTEGER,
       acPMSIPBusyCallsInterval                        Unsigned32,
       acPMSIPBusyCallsVal                             Counter32
     }



     acPMSIPBusyCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPBusyCallsEntry 1}



     acPMSIPBusyCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPBusyCallsEntry 2}



     acPMSIPBusyCallsVal OBJECT-TYPE
       SYNTAX Counter32
       MAX-ACCESS read-only
       STATUS obsolete
       DESCRIPTION
           "Value of gauge or counter."
       ::= {acPMSIPBusyCallsEntry 3}



     -- ****************************************
     -- acPMSIPNoAnswerCalls table declaration
     -- ****************************************
     acPMSIPNoAnswerCallsTable OBJECT-TYPE
       SYNTAX SEQUENCE OF AcPMSIPNoAnswerCallsEntry
       MAX-ACCESS not-accessible
       STATUS obsolete
       DESCRIPTION
           "Number of no answer calls (Index 0 for TEL2IP and Index 1 for IP2TEL)"
       ::= {acPMSIP 5}



     -- ****************************************
     -- acPMSIPNoAnswerCalls table entry
     -- ****************************************
     acPMSIPNoAnswerCallsEntry OBJECT-TYPE
       SYNTAX AcPMSIPNoAnswerCallsEntry
       MAX-ACCESS not-accessible
       STATUS obsolete
       DESCRIPTION
           ""
       INDEX {acPMSIPNoAnswerCallsDirection,acPMSIPNoAnswerCallsInterval}
       ::= {acPMSIPNoAnswerCallsTable 1}



     -- ****************************************
     -- acPMSIPNoAnswerCalls TABLE
     -- ****************************************
     AcPMSIPNoAnswerCallsEntry ::= SEQUENCE {
       acPMSIPNoAnswerCallsDirection                   INTEGER,
       acPMSIPNoAnswerCallsInterval                    Unsigned32,
       acPMSIPNoAnswerCallsVal                         Counter32
     }



     acPMSIPNoAnswerCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPNoAnswerCallsEntry 1}



     acPMSIPNoAnswerCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPNoAnswerCallsEntry 2}



     acPMSIPNoAnswerCallsVal OBJECT-TYPE
       SYNTAX Counter32
       MAX-ACCESS read-only
       STATUS obsolete
       DESCRIPTION
           "Value of gauge or counter."
       ::= {acPMSIPNoAnswerCallsEntry 3}



     -- ****************************************
     -- acPMSIPNoRouteCalls table declaration
     -- ****************************************
     acPMSIPNoRouteCallsTable OBJECT-TYPE
       SYNTAX SEQUENCE OF AcPMSIPNoRouteCallsEntry
       MAX-ACCESS not-accessible
       STATUS obsolete
       DESCRIPTION
           "Number of no route calls (Index 0 for TEL2IP and Index 1 for IP2TEL)"
       ::= {acPMSIP 6}



     -- ****************************************
     -- acPMSIPNoRouteCalls table entry
     -- ****************************************
     acPMSIPNoRouteCallsEntry OBJECT-TYPE
       SYNTAX AcPMSIPNoRouteCallsEntry
       MAX-ACCESS not-accessible
       STATUS obsolete
       DESCRIPTION
           ""
       INDEX {acPMSIPNoRouteCallsDirection,acPMSIPNoRouteCallsInterval}
       ::= {acPMSIPNoRouteCallsTable 1}



     -- ****************************************
     -- acPMSIPNoRouteCalls TABLE
     -- ****************************************
     AcPMSIPNoRouteCallsEntry ::= SEQUENCE {
       acPMSIPNoRouteCallsDirection                    INTEGER,
       acPMSIPNoRouteCallsInterval                     Unsigned32,
       acPMSIPNoRouteCallsVal                          Counter32
     }



     acPMSIPNoRouteCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPNoRouteCallsEntry 1}



     acPMSIPNoRouteCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPNoRouteCallsEntry 2}



     acPMSIPNoRouteCallsVal OBJECT-TYPE
       SYNTAX Counter32
       MAX-ACCESS read-only
       STATUS obsolete
       DESCRIPTION
           "Value of gauge or counter."
       ::= {acPMSIPNoRouteCallsEntry 3}



     -- ****************************************
     -- acPMSIPFailCalls table declaration
     -- ****************************************
     acPMSIPFailCallsTable OBJECT-TYPE
       SYNTAX SEQUENCE OF AcPMSIPFailCallsEntry
       MAX-ACCESS not-accessible
       STATUS obsolete
       DESCRIPTION
           "Number of calls that failed because of other reasons (Index 0 for TEL2IP and Index 1 for IP2TEL)"
       ::= {acPMSIP 7}



     -- ****************************************
     -- acPMSIPFailCalls table entry
     -- ****************************************
     acPMSIPFailCallsEntry OBJECT-TYPE
       SYNTAX AcPMSIPFailCallsEntry
       MAX-ACCESS not-accessible
       STATUS obsolete
       DESCRIPTION
           ""
       INDEX {acPMSIPFailCallsDirection,acPMSIPFailCallsInterval}
       ::= {acPMSIPFailCallsTable 1}



     -- ****************************************
     -- acPMSIPFailCalls TABLE
     -- ****************************************
     AcPMSIPFailCallsEntry ::= SEQUENCE {
       acPMSIPFailCallsDirection                       INTEGER,
       acPMSIPFailCallsInterval                        Unsigned32,
       acPMSIPFailCallsVal                             Counter32
     }



     acPMSIPFailCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPFailCallsEntry 1}



     acPMSIPFailCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPFailCallsEntry 2}



     acPMSIPFailCallsVal OBJECT-TYPE
       SYNTAX Counter32
       MAX-ACCESS read-only
       STATUS obsolete
       DESCRIPTION
           "Value of gauge or counter."
       ::= {acPMSIPFailCallsEntry 3}



     -- ****************************************
     -- acPMSIPEstablishedCalls table declaration
     -- ****************************************
     acPMSIPEstablishedCallsTable OBJECT-TYPE
       SYNTAX SEQUENCE OF AcPMSIPEstablishedCallsEntry
       MAX-ACCESS not-accessible
       STATUS obsolete
       DESCRIPTION
           "Number of established calls (Index 0 for TEL2IP and Index 1 for IP2TEL)"
       ::= {acPMSIP 8}



     -- ****************************************
     -- acPMSIPEstablishedCalls table entry
     -- ****************************************
     acPMSIPEstablishedCallsEntry OBJECT-TYPE
       SYNTAX AcPMSIPEstablishedCallsEntry
       MAX-ACCESS not-accessible
       STATUS obsolete
       DESCRIPTION
           ""
       INDEX {acPMSIPEstablishedCallsDirection,acPMSIPEstablishedCallsInterval}
       ::= {acPMSIPEstablishedCallsTable 1}



     -- ****************************************
     -- acPMSIPEstablishedCalls TABLE
     -- ****************************************
     AcPMSIPEstablishedCallsEntry ::= SEQUENCE {
       acPMSIPEstablishedCallsDirection                INTEGER,
       acPMSIPEstablishedCallsInterval                 Unsigned32,
       acPMSIPEstablishedCallsVal                      Counter32
     }



     acPMSIPEstablishedCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPEstablishedCallsEntry 1}



     acPMSIPEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPEstablishedCallsEntry 2}



     acPMSIPEstablishedCallsVal OBJECT-TYPE
       SYNTAX Counter32
       MAX-ACCESS read-only
       STATUS obsolete
       DESCRIPTION
           "Value of gauge or counter."
       ::= {acPMSIPEstablishedCallsEntry 3}



     -- ****************************************
     -- acPMSIPFaxAttemptedCalls table declaration
     -- ****************************************
     acPMSIPFaxAttemptedCallsTable OBJECT-TYPE
       SYNTAX SEQUENCE OF AcPMSIPFaxAttemptedCallsEntry
       MAX-ACCESS not-accessible
       STATUS obsolete
       DESCRIPTION
           "Number of attempted fax calls (Index 0 for TEL2IP and Index 1 for IP2TEL)"
       ::= {acPMSIP 9}



     -- ****************************************
     -- acPMSIPFaxAttemptedCalls table entry
     -- ****************************************
     acPMSIPFaxAttemptedCallsEntry OBJECT-TYPE
       SYNTAX AcPMSIPFaxAttemptedCallsEntry
       MAX-ACCESS not-accessible
       STATUS obsolete
       DESCRIPTION
           ""
       INDEX {acPMSIPFaxAttemptedCallsDirection,acPMSIPFaxAttemptedCallsInterval}
       ::= {acPMSIPFaxAttemptedCallsTable 1}



     -- ****************************************
     -- acPMSIPFaxAttemptedCalls TABLE
     -- ****************************************
     AcPMSIPFaxAttemptedCallsEntry ::= SEQUENCE {
       acPMSIPFaxAttemptedCallsDirection               INTEGER,
       acPMSIPFaxAttemptedCallsInterval                Unsigned32,
       acPMSIPFaxAttemptedCallsVal                     Counter32
     }



     acPMSIPFaxAttemptedCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPFaxAttemptedCallsEntry 1}



     acPMSIPFaxAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPFaxAttemptedCallsEntry 2}



     acPMSIPFaxAttemptedCallsVal OBJECT-TYPE
       SYNTAX Counter32
       MAX-ACCESS read-only
       STATUS obsolete
       DESCRIPTION
           "Value of gauge or counter."
       ::= {acPMSIPFaxAttemptedCallsEntry 3}



     -- ****************************************
     -- acPMSIPFaxSuccessCalls table declaration
     -- ****************************************
     acPMSIPFaxSuccessCallsTable OBJECT-TYPE
       SYNTAX SEQUENCE OF AcPMSIPFaxSuccessCallsEntry
       MAX-ACCESS not-accessible
       STATUS obsolete
       DESCRIPTION
           "Number of success fax calls (Index 0 for TEL2IP and Index 1 for IP2TEL)"
       ::= {acPMSIP 10}



     -- ****************************************
     -- acPMSIPFaxSuccessCalls table entry
     -- ****************************************
     acPMSIPFaxSuccessCallsEntry OBJECT-TYPE
       SYNTAX AcPMSIPFaxSuccessCallsEntry
       MAX-ACCESS not-accessible
       STATUS obsolete
       DESCRIPTION
           ""
       INDEX {acPMSIPFaxSuccessCallsDirection,acPMSIPFaxSuccessCallsInterval}
       ::= {acPMSIPFaxSuccessCallsTable 1}



     -- ****************************************
     -- acPMSIPFaxSuccessCalls TABLE
     -- ****************************************
     AcPMSIPFaxSuccessCallsEntry ::= SEQUENCE {
       acPMSIPFaxSuccessCallsDirection                 INTEGER,
       acPMSIPFaxSuccessCallsInterval                  Unsigned32,
       acPMSIPFaxSuccessCallsVal                       Counter32
     }



     acPMSIPFaxSuccessCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPFaxSuccessCallsEntry 1}



     acPMSIPFaxSuccessCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPFaxSuccessCallsEntry 2}



     acPMSIPFaxSuccessCallsVal OBJECT-TYPE
       SYNTAX Counter32
       MAX-ACCESS read-only
       STATUS obsolete
       DESCRIPTION
           "Value of gauge or counter."
       ::= {acPMSIPFaxSuccessCallsEntry 3}



     -- ****************************************
     -- acPMSIPForwardedCalls table declaration
     -- ****************************************
     acPMSIPForwardedCallsTable OBJECT-TYPE
       SYNTAX SEQUENCE OF AcPMSIPForwardedCallsEntry
       MAX-ACCESS not-accessible
       STATUS obsolete
       DESCRIPTION
           "Number of calls released due to forwarding (Index 0 for TEL2IP and Index 1 for IP2TEL)"
       ::= {acPMSIP 11}



     -- ****************************************
     -- acPMSIPForwardedCalls table entry
     -- ****************************************
     acPMSIPForwardedCallsEntry OBJECT-TYPE
       SYNTAX AcPMSIPForwardedCallsEntry
       MAX-ACCESS not-accessible
       STATUS obsolete
       DESCRIPTION
           ""
       INDEX {acPMSIPForwardedCallsDirection,acPMSIPForwardedCallsInterval}
       ::= {acPMSIPForwardedCallsTable 1}



     -- ****************************************
     -- acPMSIPForwardedCalls TABLE
     -- ****************************************
     AcPMSIPForwardedCallsEntry ::= SEQUENCE {
       acPMSIPForwardedCallsDirection                  INTEGER,
       acPMSIPForwardedCallsInterval                   Unsigned32,
       acPMSIPForwardedCallsVal                        Counter32
     }



     acPMSIPForwardedCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPForwardedCallsEntry 1}



     acPMSIPForwardedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPForwardedCallsEntry 2}



     acPMSIPForwardedCallsVal OBJECT-TYPE
       SYNTAX Counter32
       MAX-ACCESS read-only
       STATUS obsolete
       DESCRIPTION
           "Value of gauge or counter."
       ::= {acPMSIPForwardedCallsEntry 3}



     -- ****************************************
     -- acPMSIPNoResourcesCalls table declaration
     -- ****************************************
     acPMSIPNoResourcesCallsTable OBJECT-TYPE
       SYNTAX SEQUENCE OF AcPMSIPNoResourcesCallsEntry
       MAX-ACCESS not-accessible
       STATUS obsolete
       DESCRIPTION
           "Number of calls released because of no resources (Index 0 for TEL2IP and Index 1 for IP2TEL)"
       ::= {acPMSIP 12}



     -- ****************************************
     -- acPMSIPNoResourcesCalls table entry
     -- ****************************************
     acPMSIPNoResourcesCallsEntry OBJECT-TYPE
       SYNTAX AcPMSIPNoResourcesCallsEntry
       MAX-ACCESS not-accessible
       STATUS obsolete
       DESCRIPTION
           ""
       INDEX {acPMSIPNoResourcesCallsDirection,acPMSIPNoResourcesCallsInterval}
       ::= {acPMSIPNoResourcesCallsTable 1}



     -- ****************************************
     -- acPMSIPNoResourcesCalls TABLE
     -- ****************************************
     AcPMSIPNoResourcesCallsEntry ::= SEQUENCE {
       acPMSIPNoResourcesCallsDirection                INTEGER,
       acPMSIPNoResourcesCallsInterval                 Unsigned32,
       acPMSIPNoResourcesCallsVal                      Counter32
     }



     acPMSIPNoResourcesCallsDirection OBJECT-TYPE
       SYNTAX INTEGER {
                  tel2IP(0)
,
                  iP2Tel(1)

                  }
       MAX-ACCESS not-accessible
       STATUS obsolete
       DESCRIPTION
           "Direction index - TEL2IP(0), IP2TEL(1)."
       ::= {acPMSIPNoResourcesCallsEntry 1}



     acPMSIPNoResourcesCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPNoResourcesCallsEntry 2}



     acPMSIPNoResourcesCallsVal OBJECT-TYPE
       SYNTAX Counter32
       MAX-ACCESS read-only
       STATUS obsolete
       DESCRIPTION
           "Value of gauge or counter."
       ::= {acPMSIPNoResourcesCallsEntry 3}



     -- ****************************************
     -- acPMSIPTel2IPTrunkEstablishedCalls table declaration
     -- ****************************************
     acPMSIPTel2IPTrunkEstablishedCallsTable OBJECT-TYPE
       SYNTAX SEQUENCE OF AcPMSIPTel2IPTrunkEstablishedCallsEntry
       MAX-ACCESS not-accessible
       STATUS obsolete
       DESCRIPTION
           "Number of Tel2IP established calls per trunk."
       ::= {acPMSIP 13}



     -- ****************************************
     -- acPMSIPTel2IPTrunkEstablishedCalls table entry
     -- ****************************************
     acPMSIPTel2IPTrunkEstablishedCallsEntry OBJECT-TYPE
       SYNTAX AcPMSIPTel2IPTrunkEstablishedCallsEntry
       MAX-ACCESS not-accessible
       STATUS obsolete
       DESCRIPTION
           ""
       INDEX {acPMSIPTel2IPTrunkEstablishedCallsTrunkNum,acPMSIPTel2IPTrunkEstablishedCallsInterval}
       ::= {acPMSIPTel2IPTrunkEstablishedCallsTable 1}



     -- ****************************************
     -- acPMSIPTel2IPTrunkEstablishedCalls TABLE
     -- ****************************************
     AcPMSIPTel2IPTrunkEstablishedCallsEntry ::= SEQUENCE {
       acPMSIPTel2IPTrunkEstablishedCallsTrunkNum      Unsigned32,
       acPMSIPTel2IPTrunkEstablishedCallsInterval      Unsigned32,
       acPMSIPTel2IPTrunkEstablishedCallsVal           Counter32
     }



     acPMSIPTel2IPTrunkEstablishedCallsTrunkNum OBJECT-TYPE
       SYNTAX Unsigned32 (0..83)
       MAX-ACCESS not-accessible
       STATUS obsolete
       DESCRIPTION
           "Trunk number.
0 is the first trunk."
       ::= {acPMSIPTel2IPTrunkEstablishedCallsEntry 1}



     acPMSIPTel2IPTrunkEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTel2IPTrunkEstablishedCallsEntry 2}



     acPMSIPTel2IPTrunkEstablishedCallsVal OBJECT-TYPE
       SYNTAX Counter32
       MAX-ACCESS read-only
       STATUS obsolete
       DESCRIPTION
           "Value of gauge or counter."
       ::= {acPMSIPTel2IPTrunkEstablishedCallsEntry 3}



     -- ****************************************
     -- acPMSIPIP2TelTrunkEstablishedCalls table declaration
     -- ****************************************
     acPMSIPIP2TelTrunkEstablishedCallsTable OBJECT-TYPE
       SYNTAX SEQUENCE OF AcPMSIPIP2TelTrunkEstablishedCallsEntry
       MAX-ACCESS not-accessible
       STATUS obsolete
       DESCRIPTION
           "Number of IP2Tel established calls per trunk."
       ::= {acPMSIP 14}



     -- ****************************************
     -- acPMSIPIP2TelTrunkEstablishedCalls table entry
     -- ****************************************
     acPMSIPIP2TelTrunkEstablishedCallsEntry OBJECT-TYPE
       SYNTAX AcPMSIPIP2TelTrunkEstablishedCallsEntry
       MAX-ACCESS not-accessible
       STATUS obsolete
       DESCRIPTION
           ""
       INDEX {acPMSIPIP2TelTrunkEstablishedCallsTrunkNum,acPMSIPIP2TelTrunkEstablishedCallsInterval}
       ::= {acPMSIPIP2TelTrunkEstablishedCallsTable 1}



     -- ****************************************
     -- acPMSIPIP2TelTrunkEstablishedCalls TABLE
     -- ****************************************
     AcPMSIPIP2TelTrunkEstablishedCallsEntry ::= SEQUENCE {
       acPMSIPIP2TelTrunkEstablishedCallsTrunkNum      Unsigned32,
       acPMSIPIP2TelTrunkEstablishedCallsInterval      Unsigned32,
       acPMSIPIP2TelTrunkEstablishedCallsVal           Counter32
     }



     acPMSIPIP2TelTrunkEstablishedCallsTrunkNum OBJECT-TYPE
       SYNTAX Unsigned32 (0..83)
       MAX-ACCESS not-accessible
       STATUS obsolete
       DESCRIPTION
           "Trunk number.
0 is the first trunk."
       ::= {acPMSIPIP2TelTrunkEstablishedCallsEntry 1}



     acPMSIPIP2TelTrunkEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIP2TelTrunkEstablishedCallsEntry 2}



     acPMSIPIP2TelTrunkEstablishedCallsVal OBJECT-TYPE
       SYNTAX Counter32
       MAX-ACCESS read-only
       STATUS obsolete
       DESCRIPTION
           "Value of gauge or counter."
       ::= {acPMSIPIP2TelTrunkEstablishedCallsEntry 3}



     -- ****************************************
     -- acPMSIPTel2IPTrunkGroupEstablishedCalls table declaration
     -- ****************************************
     acPMSIPTel2IPTrunkGroupEstablishedCallsTable OBJECT-TYPE
       SYNTAX SEQUENCE OF AcPMSIPTel2IPTrunkGroupEstablishedCallsEntry
       MAX-ACCESS not-accessible
       STATUS obsolete
       DESCRIPTION
           "Number of Tel2IP established calls per trunk group."
       ::= {acPMSIP 15}



     -- ****************************************
     -- acPMSIPTel2IPTrunkGroupEstablishedCalls table entry
     -- ****************************************
     acPMSIPTel2IPTrunkGroupEstablishedCallsEntry OBJECT-TYPE
       SYNTAX AcPMSIPTel2IPTrunkGroupEstablishedCallsEntry
       MAX-ACCESS not-accessible
       STATUS obsolete
       DESCRIPTION
           ""
       INDEX {acPMSIPTel2IPTrunkGroupEstablishedCallsGroupNum,acPMSIPTel2IPTrunkGroupEstablishedCallsInterval}
       ::= {acPMSIPTel2IPTrunkGroupEstablishedCallsTable 1}



     -- ****************************************
     -- acPMSIPTel2IPTrunkGroupEstablishedCalls TABLE
     -- ****************************************
     AcPMSIPTel2IPTrunkGroupEstablishedCallsEntry ::= SEQUENCE {
       acPMSIPTel2IPTrunkGroupEstablishedCallsGroupNum Unsigned32,
       acPMSIPTel2IPTrunkGroupEstablishedCallsInterval Unsigned32,
       acPMSIPTel2IPTrunkGroupEstablishedCallsVal      Counter32
     }



     acPMSIPTel2IPTrunkGroupEstablishedCallsGroupNum OBJECT-TYPE
       SYNTAX Unsigned32 (0..83)
       MAX-ACCESS not-accessible
       STATUS obsolete
       DESCRIPTION
           "Trunk Group number.
0 is the first trunk group."
       ::= {acPMSIPTel2IPTrunkGroupEstablishedCallsEntry 1}



     acPMSIPTel2IPTrunkGroupEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTel2IPTrunkGroupEstablishedCallsEntry 2}



     acPMSIPTel2IPTrunkGroupEstablishedCallsVal OBJECT-TYPE
       SYNTAX Counter32
       MAX-ACCESS read-only
       STATUS obsolete
       DESCRIPTION
           "Value of gauge or counter."
       ::= {acPMSIPTel2IPTrunkGroupEstablishedCallsEntry 3}



     -- ****************************************
     -- acPMSIPIP2TelTrunkGroupEstablishedCalls table declaration
     -- ****************************************
     acPMSIPIP2TelTrunkGroupEstablishedCallsTable OBJECT-TYPE
       SYNTAX SEQUENCE OF AcPMSIPIP2TelTrunkGroupEstablishedCallsEntry
       MAX-ACCESS not-accessible
       STATUS obsolete
       DESCRIPTION
           "Number of IP2Tel established calls per trunk group."
       ::= {acPMSIP 16}



     -- ****************************************
     -- acPMSIPIP2TelTrunkGroupEstablishedCalls table entry
     -- ****************************************
     acPMSIPIP2TelTrunkGroupEstablishedCallsEntry OBJECT-TYPE
       SYNTAX AcPMSIPIP2TelTrunkGroupEstablishedCallsEntry
       MAX-ACCESS not-accessible
       STATUS obsolete
       DESCRIPTION
           ""
       INDEX {acPMSIPIP2TelTrunkGroupEstablishedCallsGroupNum,acPMSIPIP2TelTrunkGroupEstablishedCallsInterval}
       ::= {acPMSIPIP2TelTrunkGroupEstablishedCallsTable 1}



     -- ****************************************
     -- acPMSIPIP2TelTrunkGroupEstablishedCalls TABLE
     -- ****************************************
     AcPMSIPIP2TelTrunkGroupEstablishedCallsEntry ::= SEQUENCE {
       acPMSIPIP2TelTrunkGroupEstablishedCallsGroupNum Unsigned32,
       acPMSIPIP2TelTrunkGroupEstablishedCallsInterval Unsigned32,
       acPMSIPIP2TelTrunkGroupEstablishedCallsVal      Counter32
     }



     acPMSIPIP2TelTrunkGroupEstablishedCallsGroupNum OBJECT-TYPE
       SYNTAX Unsigned32 (0..83)
       MAX-ACCESS not-accessible
       STATUS obsolete
       DESCRIPTION
           "Trunk Group number.
0 is the first trunk group."
       ::= {acPMSIPIP2TelTrunkGroupEstablishedCallsEntry 1}



     acPMSIPIP2TelTrunkGroupEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIP2TelTrunkGroupEstablishedCallsEntry 2}



     acPMSIPIP2TelTrunkGroupEstablishedCallsVal OBJECT-TYPE
       SYNTAX Counter32
       MAX-ACCESS read-only
       STATUS obsolete
       DESCRIPTION
           "Value of gauge or counter."
       ::= {acPMSIPIP2TelTrunkGroupEstablishedCallsEntry 3}



     -- ****************************************
     -- acPMSIPSRDDialogs table declaration
     -- ****************************************
     acPMSIPSRDDialogsTable OBJECT-TYPE
       SYNTAX SEQUENCE OF AcPMSIPSRDDialogsEntry
       MAX-ACCESS not-accessible
       STATUS obsolete
       DESCRIPTION
           "Performance Monitoring gwSRDDialogs setup"
       ::= {acPMSIP 17}



     -- ****************************************
     -- acPMSIPSRDDialogs table entry
     -- ****************************************
     acPMSIPSRDDialogsEntry OBJECT-TYPE
       SYNTAX AcPMSIPSRDDialogsEntry
       MAX-ACCESS not-accessible
       STATUS obsolete
       DESCRIPTION
           ""
       INDEX {acPMSIPSRDDialogsSrdNum,acPMSIPSRDDialogsInterval}
       ::= {acPMSIPSRDDialogsTable 1}



     -- ****************************************
     -- acPMSIPSRDDialogs TABLE
     -- ****************************************
     AcPMSIPSRDDialogsEntry ::= SEQUENCE {
       acPMSIPSRDDialogsSrdNum                         Unsigned32,
       acPMSIPSRDDialogsInterval                       Unsigned32,
       acPMSIPSRDDialogsVal                            Gauge32
     }



     acPMSIPSRDDialogsSrdNum OBJECT-TYPE
       SYNTAX Unsigned32 (0..600)
       MAX-ACCESS not-accessible
       STATUS obsolete
       DESCRIPTION
           "SRD number.
0 is the first SRD."
       ::= {acPMSIPSRDDialogsEntry 1}



     acPMSIPSRDDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSRDDialogsEntry 2}



     acPMSIPSRDDialogsVal OBJECT-TYPE
       SYNTAX Gauge32
       MAX-ACCESS read-only
       STATUS obsolete
       DESCRIPTION
           "Value of gauge or counter."
       ::= {acPMSIPSRDDialogsEntry 3}



     -- ****************************************
     -- acPMSIPSRDInviteDialogs table declaration
     -- ****************************************
     acPMSIPSRDInviteDialogsTable OBJECT-TYPE
       SYNTAX SEQUENCE OF AcPMSIPSRDInviteDialogsEntry
       MAX-ACCESS not-accessible
       STATUS obsolete
       DESCRIPTION
           "Performance Monitoring gwSRDSUBSCRIBEDialogs setup"
       ::= {acPMSIP 18}



     -- ****************************************
     -- acPMSIPSRDInviteDialogs table entry
     -- ****************************************
     acPMSIPSRDInviteDialogsEntry OBJECT-TYPE
       SYNTAX AcPMSIPSRDInviteDialogsEntry
       MAX-ACCESS not-accessible
       STATUS obsolete
       DESCRIPTION
           ""
       INDEX {acPMSIPSRDInviteDialogsSrdNum,acPMSIPSRDInviteDialogsInterval}
       ::= {acPMSIPSRDInviteDialogsTable 1}



     -- ****************************************
     -- acPMSIPSRDInviteDialogs TABLE
     -- ****************************************
     AcPMSIPSRDInviteDialogsEntry ::= SEQUENCE {
       acPMSIPSRDInviteDialogsSrdNum                   Unsigned32,
       acPMSIPSRDInviteDialogsInterval                 Unsigned32,
       acPMSIPSRDInviteDialogsVal                      Gauge32
     }



     acPMSIPSRDInviteDialogsSrdNum OBJECT-TYPE
       SYNTAX Unsigned32 (0..600)
       MAX-ACCESS not-accessible
       STATUS obsolete
       DESCRIPTION
           "SRD number.
0 is the first SRD."
       ::= {acPMSIPSRDInviteDialogsEntry 1}



     acPMSIPSRDInviteDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSRDInviteDialogsEntry 2}



     acPMSIPSRDInviteDialogsVal OBJECT-TYPE
       SYNTAX Gauge32
       MAX-ACCESS read-only
       STATUS obsolete
       DESCRIPTION
           "Value of gauge or counter."
       ::= {acPMSIPSRDInviteDialogsEntry 3}



     -- ****************************************
     -- acPMSIPSRDSubscribeDialogs table declaration
     -- ****************************************
     acPMSIPSRDSubscribeDialogsTable OBJECT-TYPE
       SYNTAX SEQUENCE OF AcPMSIPSRDSubscribeDialogsEntry
       MAX-ACCESS not-accessible
       STATUS obsolete
       DESCRIPTION
           "Performance Monitoring gwSRDSUBSCRIBEDialogs setup"
       ::= {acPMSIP 19}



     -- ****************************************
     -- acPMSIPSRDSubscribeDialogs table entry
     -- ****************************************
     acPMSIPSRDSubscribeDialogsEntry OBJECT-TYPE
       SYNTAX AcPMSIPSRDSubscribeDialogsEntry
       MAX-ACCESS not-accessible
       STATUS obsolete
       DESCRIPTION
           ""
       INDEX {acPMSIPSRDSubscribeDialogsSrdNum,acPMSIPSRDSubscribeDialogsInterval}
       ::= {acPMSIPSRDSubscribeDialogsTable 1}



     -- ****************************************
     -- acPMSIPSRDSubscribeDialogs TABLE
     -- ****************************************
     AcPMSIPSRDSubscribeDialogsEntry ::= SEQUENCE {
       acPMSIPSRDSubscribeDialogsSrdNum                Unsigned32,
       acPMSIPSRDSubscribeDialogsInterval              Unsigned32,
       acPMSIPSRDSubscribeDialogsVal                   Counter32
     }



     acPMSIPSRDSubscribeDialogsSrdNum OBJECT-TYPE
       SYNTAX Unsigned32 (0..600)
       MAX-ACCESS not-accessible
       STATUS obsolete
       DESCRIPTION
           "SRD number.
0 is the first SRD."
       ::= {acPMSIPSRDSubscribeDialogsEntry 1}



     acPMSIPSRDSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSRDSubscribeDialogsEntry 2}



     acPMSIPSRDSubscribeDialogsVal OBJECT-TYPE
       SYNTAX Counter32
       MAX-ACCESS read-only
       STATUS obsolete
       DESCRIPTION
           "Value of gauge or counter."
       ::= {acPMSIPSRDSubscribeDialogsEntry 3}



     -- ****************************************
     -- acPMSIPSRDOtherDialogs table declaration
     -- ****************************************
     acPMSIPSRDOtherDialogsTable OBJECT-TYPE
       SYNTAX SEQUENCE OF AcPMSIPSRDOtherDialogsEntry
       MAX-ACCESS not-accessible
       STATUS obsolete
       DESCRIPTION
           "Performance Monitoring gwSRDOtherDialogs setup"
       ::= {acPMSIP 20}



     -- ****************************************
     -- acPMSIPSRDOtherDialogs table entry
     -- ****************************************
     acPMSIPSRDOtherDialogsEntry OBJECT-TYPE
       SYNTAX AcPMSIPSRDOtherDialogsEntry
       MAX-ACCESS not-accessible
       STATUS obsolete
       DESCRIPTION
           ""
       INDEX {acPMSIPSRDOtherDialogsSrdNum,acPMSIPSRDOtherDialogsInterval}
       ::= {acPMSIPSRDOtherDialogsTable 1}



     -- ****************************************
     -- acPMSIPSRDOtherDialogs TABLE
     -- ****************************************
     AcPMSIPSRDOtherDialogsEntry ::= SEQUENCE {
       acPMSIPSRDOtherDialogsSrdNum                    Unsigned32,
       acPMSIPSRDOtherDialogsInterval                  Unsigned32,
       acPMSIPSRDOtherDialogsVal                       Counter32
     }



     acPMSIPSRDOtherDialogsSrdNum OBJECT-TYPE
       SYNTAX Unsigned32 (0..600)
       MAX-ACCESS not-accessible
       STATUS obsolete
       DESCRIPTION
           "SRD number.
0 is the first SRD."
       ::= {acPMSIPSRDOtherDialogsEntry 1}



     acPMSIPSRDOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSRDOtherDialogsEntry 2}



     acPMSIPSRDOtherDialogsVal OBJECT-TYPE
       SYNTAX Counter32
       MAX-ACCESS read-only
       STATUS obsolete
       DESCRIPTION
           "Value of gauge or counter."
       ::= {acPMSIPSRDOtherDialogsEntry 3}



     -- ****************************************
     -- acPMSIPIPGroupDialogs table declaration
     -- ****************************************
     acPMSIPIPGroupDialogsTable OBJECT-TYPE
       SYNTAX SEQUENCE OF AcPMSIPIPGroupDialogsEntry
       MAX-ACCESS not-accessible
       STATUS obsolete
       DESCRIPTION
           "Performance Monitoring gwIPGroupDialogs setup"
       ::= {acPMSIP 21}



     -- ****************************************
     -- acPMSIPIPGroupDialogs table entry
     -- ****************************************
     acPMSIPIPGroupDialogsEntry OBJECT-TYPE
       SYNTAX AcPMSIPIPGroupDialogsEntry
       MAX-ACCESS not-accessible
       STATUS obsolete
       DESCRIPTION
           ""
       INDEX {acPMSIPIPGroupDialogsIPGroupNum,acPMSIPIPGroupDialogsInterval}
       ::= {acPMSIPIPGroupDialogsTable 1}



     -- ****************************************
     -- acPMSIPIPGroupDialogs TABLE
     -- ****************************************
     AcPMSIPIPGroupDialogsEntry ::= SEQUENCE {
       acPMSIPIPGroupDialogsIPGroupNum                 Unsigned32,
       acPMSIPIPGroupDialogsInterval                   Unsigned32,
       acPMSIPIPGroupDialogsVal                        Gauge32
     }



     acPMSIPIPGroupDialogsIPGroupNum OBJECT-TYPE
       SYNTAX Unsigned32 (0..5000)
       MAX-ACCESS not-accessible
       STATUS obsolete
       DESCRIPTION
           "IP Group number.
0 is the first IP Group."
       ::= {acPMSIPIPGroupDialogsEntry 1}



     acPMSIPIPGroupDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupDialogsEntry 2}



     acPMSIPIPGroupDialogsVal OBJECT-TYPE
       SYNTAX Gauge32
       MAX-ACCESS read-only
       STATUS obsolete
       DESCRIPTION
           "Value of gauge or counter."
       ::= {acPMSIPIPGroupDialogsEntry 3}



     -- ****************************************
     -- acPMSIPIPGroupInviteDialogs table declaration
     -- ****************************************
     acPMSIPIPGroupInviteDialogsTable OBJECT-TYPE
       SYNTAX SEQUENCE OF AcPMSIPIPGroupInviteDialogsEntry
       MAX-ACCESS not-accessible
       STATUS obsolete
       DESCRIPTION
           "Performance Monitoring gwIPGroupINVITEDialogs setup"
       ::= {acPMSIP 22}



     -- ****************************************
     -- acPMSIPIPGroupInviteDialogs table entry
     -- ****************************************
     acPMSIPIPGroupInviteDialogsEntry OBJECT-TYPE
       SYNTAX AcPMSIPIPGroupInviteDialogsEntry
       MAX-ACCESS not-accessible
       STATUS obsolete
       DESCRIPTION
           ""
       INDEX {acPMSIPIPGroupInviteDialogsIPGroupNum,acPMSIPIPGroupInviteDialogsInterval}
       ::= {acPMSIPIPGroupInviteDialogsTable 1}



     -- ****************************************
     -- acPMSIPIPGroupInviteDialogs TABLE
     -- ****************************************
     AcPMSIPIPGroupInviteDialogsEntry ::= SEQUENCE {
       acPMSIPIPGroupInviteDialogsIPGroupNum           Unsigned32,
       acPMSIPIPGroupInviteDialogsInterval             Unsigned32,
       acPMSIPIPGroupInviteDialogsVal                  Gauge32,
       acPMSIPIPGroupInviteDialogsAverage              Unsigned32,
       acPMSIPIPGroupInviteDialogsMax                  Unsigned32,
       acPMSIPIPGroupInviteDialogsMin                  Unsigned32,
       acPMSIPIPGroupInviteDialogsTimeBelowLowThreshold 
                                                       Unsigned32,
       acPMSIPIPGroupInviteDialogsTimeBetweenThresholds 
                                                       Unsigned32,
       acPMSIPIPGroupInviteDialogsTimeAboveHighThreshold 
                                                       Unsigned32,
       acPMSIPIPGroupInviteDialogsTotal                Counter32
     }



     acPMSIPIPGroupInviteDialogsIPGroupNum OBJECT-TYPE
       SYNTAX Unsigned32 (0..5000)
       MAX-ACCESS not-accessible
       STATUS obsolete
       DESCRIPTION
           "IP Group number.
0 is the first IP Group."
       ::= {acPMSIPIPGroupInviteDialogsEntry 1}



     acPMSIPIPGroupInviteDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupInviteDialogsEntry 2}



     acPMSIPIPGroupInviteDialogsVal OBJECT-TYPE
       SYNTAX Gauge32
       MAX-ACCESS read-only
       STATUS obsolete
       DESCRIPTION
           "Value of gauge or counter."
       ::= {acPMSIPIPGroupInviteDialogsEntry 3}



     acPMSIPIPGroupInviteDialogsAverage OBJECT-TYPE
       SYNTAX Unsigned32 (0..2147483647)
       MAX-ACCESS read-only
       STATUS obsolete
       DESCRIPTION
           "Average value with in the period time."
       ::= {acPMSIPIPGroupInviteDialogsEntry 4}



     acPMSIPIPGroupInviteDialogsMax OBJECT-TYPE
       SYNTAX Unsigned32 (0..2147483647)
       MAX-ACCESS read-only
       STATUS obsolete
       DESCRIPTION
           "Maximum value with in the period time."
       ::= {acPMSIPIPGroupInviteDialogsEntry 5}



     acPMSIPIPGroupInviteDialogsMin OBJECT-TYPE
       SYNTAX Unsigned32 (0..2147483647)
       MAX-ACCESS read-only
       STATUS obsolete
       DESCRIPTION
           "Minimum value with in the period time."
       ::= {acPMSIPIPGroupInviteDialogsEntry 6}



     acPMSIPIPGroupInviteDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupInviteDialogsEntry 7}



     acPMSIPIPGroupInviteDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupInviteDialogsEntry 8}



     acPMSIPIPGroupInviteDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupInviteDialogsEntry 9}



     acPMSIPIPGroupInviteDialogsTotal OBJECT-TYPE
       SYNTAX Counter32
       MAX-ACCESS read-only
       STATUS obsolete
       DESCRIPTION
           "Total."
       ::= {acPMSIPIPGroupInviteDialogsEntry 10}



     -- ****************************************
     -- acPMSIPIPGroupSubscribeDialogs table declaration
     -- ****************************************
     acPMSIPIPGroupSubscribeDialogsTable OBJECT-TYPE
       SYNTAX SEQUENCE OF AcPMSIPIPGroupSubscribeDialogsEntry
       MAX-ACCESS not-accessible
       STATUS obsolete
       DESCRIPTION
           "Performance Monitoring gwIPGroupSUBSCRIBEDialogs setup"
       ::= {acPMSIP 23}



     -- ****************************************
     -- acPMSIPIPGroupSubscribeDialogs table entry
     -- ****************************************
     acPMSIPIPGroupSubscribeDialogsEntry OBJECT-TYPE
       SYNTAX AcPMSIPIPGroupSubscribeDialogsEntry
       MAX-ACCESS not-accessible
       STATUS obsolete
       DESCRIPTION
           ""
       INDEX {acPMSIPIPGroupSubscribeDialogsIPGroupNum,acPMSIPIPGroupSubscribeDialogsInterval}
       ::= {acPMSIPIPGroupSubscribeDialogsTable 1}



     -- ****************************************
     -- acPMSIPIPGroupSubscribeDialogs TABLE
     -- ****************************************
     AcPMSIPIPGroupSubscribeDialogsEntry ::= SEQUENCE {
       acPMSIPIPGroupSubscribeDialogsIPGroupNum        Unsigned32,
       acPMSIPIPGroupSubscribeDialogsInterval          Unsigned32,
       acPMSIPIPGroupSubscribeDialogsVal               Gauge32,
       acPMSIPIPGroupSubscribeDialogsAverage           Unsigned32,
       acPMSIPIPGroupSubscribeDialogsMax               Unsigned32,
       acPMSIPIPGroupSubscribeDialogsMin               Unsigned32,
       acPMSIPIPGroupSubscribeDialogsTimeBelowLowThreshold 
                                                       Unsigned32,
       acPMSIPIPGroupSubscribeDialogsTimeBetweenThresholds 
                                                       Unsigned32,
       acPMSIPIPGroupSubscribeDialogsTimeAboveHighThreshold 
                                                       Unsigned32,
       acPMSIPIPGroupSubscribeDialogsTotal             Counter32
     }



     acPMSIPIPGroupSubscribeDialogsIPGroupNum OBJECT-TYPE
       SYNTAX Unsigned32 (0..5000)
       MAX-ACCESS not-accessible
       STATUS obsolete
       DESCRIPTION
           "IP Group number.
0 is the first IP Group."
       ::= {acPMSIPIPGroupSubscribeDialogsEntry 1}



     acPMSIPIPGroupSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupSubscribeDialogsEntry 2}



     acPMSIPIPGroupSubscribeDialogsVal OBJECT-TYPE
       SYNTAX Gauge32
       MAX-ACCESS read-only
       STATUS obsolete
       DESCRIPTION
           "Value of gauge or counter."
       ::= {acPMSIPIPGroupSubscribeDialogsEntry 3}



     acPMSIPIPGroupSubscribeDialogsAverage OBJECT-TYPE
       SYNTAX Unsigned32 (0..2147483647)
       MAX-ACCESS read-only
       STATUS obsolete
       DESCRIPTION
           "Average value with in the period time."
       ::= {acPMSIPIPGroupSubscribeDialogsEntry 4}



     acPMSIPIPGroupSubscribeDialogsMax OBJECT-TYPE
       SYNTAX Unsigned32 (0..2147483647)
       MAX-ACCESS read-only
       STATUS obsolete
       DESCRIPTION
           "Maximum value with in the period time."
       ::= {acPMSIPIPGroupSubscribeDialogsEntry 5}



     acPMSIPIPGroupSubscribeDialogsMin OBJECT-TYPE
       SYNTAX Unsigned32 (0..2147483647)
       MAX-ACCESS read-only
       STATUS obsolete
       DESCRIPTION
           "Minimum value with in the period time."
       ::= {acPMSIPIPGroupSubscribeDialogsEntry 6}



     acPMSIPIPGroupSubscribeDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupSubscribeDialogsEntry 7}



     acPMSIPIPGroupSubscribeDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupSubscribeDialogsEntry 8}



     acPMSIPIPGroupSubscribeDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupSubscribeDialogsEntry 9}



     acPMSIPIPGroupSubscribeDialogsTotal OBJECT-TYPE
       SYNTAX Counter32
       MAX-ACCESS read-only
       STATUS obsolete
       DESCRIPTION
           "Total."
       ::= {acPMSIPIPGroupSubscribeDialogsEntry 10}



     -- ****************************************
     -- acPMSIPIPGroupOtherDialogs table declaration
     -- ****************************************
     acPMSIPIPGroupOtherDialogsTable OBJECT-TYPE
       SYNTAX SEQUENCE OF AcPMSIPIPGroupOtherDialogsEntry
       MAX-ACCESS not-accessible
       STATUS obsolete
       DESCRIPTION
           "Performance Monitoring gwIPGroupOtherDialogs setup"
       ::= {acPMSIP 24}



     -- ****************************************
     -- acPMSIPIPGroupOtherDialogs table entry
     -- ****************************************
     acPMSIPIPGroupOtherDialogsEntry OBJECT-TYPE
       SYNTAX AcPMSIPIPGroupOtherDialogsEntry
       MAX-ACCESS not-accessible
       STATUS obsolete
       DESCRIPTION
           ""
       INDEX {acPMSIPIPGroupOtherDialogsIPGroupNum,acPMSIPIPGroupOtherDialogsInterval}
       ::= {acPMSIPIPGroupOtherDialogsTable 1}



     -- ****************************************
     -- acPMSIPIPGroupOtherDialogs TABLE
     -- ****************************************
     AcPMSIPIPGroupOtherDialogsEntry ::= SEQUENCE {
       acPMSIPIPGroupOtherDialogsIPGroupNum            Unsigned32,
       acPMSIPIPGroupOtherDialogsInterval              Unsigned32,
       acPMSIPIPGroupOtherDialogsVal                   Counter32
     }



     acPMSIPIPGroupOtherDialogsIPGroupNum OBJECT-TYPE
       SYNTAX Unsigned32 (0..5000)
       MAX-ACCESS not-accessible
       STATUS obsolete
       DESCRIPTION
           "IP Group number.
0 is the first IP Group."
       ::= {acPMSIPIPGroupOtherDialogsEntry 1}



     acPMSIPIPGroupOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupOtherDialogsEntry 2}



     acPMSIPIPGroupOtherDialogsVal OBJECT-TYPE
       SYNTAX Counter32
       MAX-ACCESS read-only
       STATUS obsolete
       DESCRIPTION
           "Value of gauge or counter."
       ::= {acPMSIPIPGroupOtherDialogsEntry 3}



     -- ****************************************
     -- acPMSIPTrunkGroupAllTrunksBusy table declaration
     -- ****************************************
     acPMSIPTrunkGroupAllTrunksBusyTable OBJECT-TYPE
       SYNTAX SEQUENCE OF AcPMSIPTrunkGroupAllTrunksBusyEntry
       MAX-ACCESS not-accessible
       STATUS obsolete
       DESCRIPTION
           "Performance Monitoring gwTrunkGroupAllTrunksBusy setup"
       ::= {acPMSIP 25}



     -- ****************************************
     -- acPMSIPTrunkGroupAllTrunksBusy table entry
     -- ****************************************
     acPMSIPTrunkGroupAllTrunksBusyEntry OBJECT-TYPE
       SYNTAX AcPMSIPTrunkGroupAllTrunksBusyEntry
       MAX-ACCESS not-accessible
       STATUS obsolete
       DESCRIPTION
           ""
       INDEX {acPMSIPTrunkGroupAllTrunksBusyTrunkGroupNum,acPMSIPTrunkGroupAllTrunksBusyInterval}
       ::= {acPMSIPTrunkGroupAllTrunksBusyTable 1}



     -- ****************************************
     -- acPMSIPTrunkGroupAllTrunksBusy TABLE
     -- ****************************************
     AcPMSIPTrunkGroupAllTrunksBusyEntry ::= SEQUENCE {
       acPMSIPTrunkGroupAllTrunksBusyTrunkGroupNum     Unsigned32,
       acPMSIPTrunkGroupAllTrunksBusyInterval          Unsigned32,
       acPMSIPTrunkGroupAllTrunksBusyVal               Counter32
     }



     acPMSIPTrunkGroupAllTrunksBusyTrunkGroupNum OBJECT-TYPE
       SYNTAX Unsigned32 (0..83)
       MAX-ACCESS not-accessible
       STATUS obsolete
       DESCRIPTION
           "Trunk Group number.
0 is the first Trunk Group."
       ::= {acPMSIPTrunkGroupAllTrunksBusyEntry 1}



     acPMSIPTrunkGroupAllTrunksBusyInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupAllTrunksBusyEntry 2}



     acPMSIPTrunkGroupAllTrunksBusyVal OBJECT-TYPE
       SYNTAX Counter32
       MAX-ACCESS read-only
       STATUS obsolete
       DESCRIPTION
           "Counts the total duration (in seconds) for which all channels
of a specific Trunk Group were concurrently busy."
       ::= {acPMSIPTrunkGroupAllTrunksBusyEntry 3}



     -- ****************************************
     -- acPMSIPTrunkGroupUtilization table declaration
     -- ****************************************
     acPMSIPTrunkGroupUtilizationTable OBJECT-TYPE
       SYNTAX SEQUENCE OF AcPMSIPTrunkGroupUtilizationEntry
       MAX-ACCESS not-accessible
       STATUS obsolete
       DESCRIPTION
           "Processing time (in Microseconds), per command type."
       ::= {acPMSIP 26}



     -- ****************************************
     -- acPMSIPTrunkGroupUtilization table entry
     -- ****************************************
     acPMSIPTrunkGroupUtilizationEntry OBJECT-TYPE
       SYNTAX AcPMSIPTrunkGroupUtilizationEntry
       MAX-ACCESS not-accessible
       STATUS obsolete
       DESCRIPTION
           ""
       INDEX {acPMSIPTrunkGroupUtilizationTrunkGroupNum,acPMSIPTrunkGroupUtilizationInterval}
       ::= {acPMSIPTrunkGroupUtilizationTable 1}



     -- ****************************************
     -- acPMSIPTrunkGroupUtilization TABLE
     -- ****************************************
     AcPMSIPTrunkGroupUtilizationEntry ::= SEQUENCE {
       acPMSIPTrunkGroupUtilizationTrunkGroupNum       Unsigned32,
       acPMSIPTrunkGroupUtilizationInterval            Unsigned32,
       acPMSIPTrunkGroupUtilizationVal                 Gauge32,
       acPMSIPTrunkGroupUtilizationTimeBelowLowThreshold 
                                                       Unsigned32,
       acPMSIPTrunkGroupUtilizationTimeBetweenThresholds 
                                                       Unsigned32,
       acPMSIPTrunkGroupUtilizationTimeAboveHighThreshold 
                                                       Unsigned32,
       acPMSIPTrunkGroupUtilizationAverage             Unsigned32,
       acPMSIPTrunkGroupUtilizationMax                 Unsigned32,
       acPMSIPTrunkGroupUtilizationMin                 Unsigned32,
       acPMSIPTrunkGroupUtilizationFullDayAverage      Unsigned32
     }



     acPMSIPTrunkGroupUtilizationTrunkGroupNum OBJECT-TYPE
       SYNTAX Unsigned32 (0..83)
       MAX-ACCESS not-accessible
       STATUS obsolete
       DESCRIPTION
           "Trunk Group number.
0 is the first Trunk Group."
       ::= {acPMSIPTrunkGroupUtilizationEntry 1}



     acPMSIPTrunkGroupUtilizationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupUtilizationEntry 2}



     acPMSIPTrunkGroupUtilizationVal OBJECT-TYPE
       SYNTAX Gauge32
       MAX-ACCESS read-only
       STATUS obsolete
       DESCRIPTION
           "Value of gauge or counter."
       ::= {acPMSIPTrunkGroupUtilizationEntry 3}



     acPMSIPTrunkGroupUtilizationTimeBelowLowThreshold OBJECT-TYPE
       SYNTAX Unsigned32 (0..100)
       MAX-ACCESS read-only
       STATUS obsolete
       DESCRIPTION
           "Percent of interval time for which gauge is below what was determined
as the low threshold."
       ::= {acPMSIPTrunkGroupUtilizationEntry 4}



     acPMSIPTrunkGroupUtilizationTimeBetweenThresholds OBJECT-TYPE
       SYNTAX Unsigned32 (0..100)
       MAX-ACCESS read-only
       STATUS obsolete
       DESCRIPTION
           "Percent of interval time for which gauge is between what were
determined as the low and high thresholds."
       ::= {acPMSIPTrunkGroupUtilizationEntry 5}



     acPMSIPTrunkGroupUtilizationTimeAboveHighThreshold OBJECT-TYPE
       SYNTAX Unsigned32 (0..100)
       MAX-ACCESS read-only
       STATUS obsolete
       DESCRIPTION
           "Percent of interval time for which gauge is above what was determined
as the high threshold."
       ::= {acPMSIPTrunkGroupUtilizationEntry 6}



     acPMSIPTrunkGroupUtilizationAverage OBJECT-TYPE
       SYNTAX Unsigned32 (0..2016)
       MAX-ACCESS read-only
       STATUS obsolete
       DESCRIPTION
           "Average value with in the period time."
       ::= {acPMSIPTrunkGroupUtilizationEntry 7}



     acPMSIPTrunkGroupUtilizationMax OBJECT-TYPE
       SYNTAX Unsigned32 (0..2016)
       MAX-ACCESS read-only
       STATUS obsolete
       DESCRIPTION
           "Maximum value with in the period time."
       ::= {acPMSIPTrunkGroupUtilizationEntry 8}



     acPMSIPTrunkGroupUtilizationMin OBJECT-TYPE
       SYNTAX Unsigned32 (0..2016)
       MAX-ACCESS read-only
       STATUS obsolete
       DESCRIPTION
           "Minimum value with in the period time."
       ::= {acPMSIPTrunkGroupUtilizationEntry 9}



     acPMSIPTrunkGroupUtilizationFullDayAverage OBJECT-TYPE
       SYNTAX Unsigned32 (0..2016)
       MAX-ACCESS read-only
       STATUS obsolete
       DESCRIPTION
           "The average of full 24 hours."
       ::= {acPMSIPTrunkGroupUtilizationEntry 10}



     -- ****************************************
     -- acPMSIPTrunkGroupPercentageUtilization table declaration
     -- ****************************************
     acPMSIPTrunkGroupPercentageUtilizationTable OBJECT-TYPE
       SYNTAX SEQUENCE OF AcPMSIPTrunkGroupPercentageUtilizationEntry
       MAX-ACCESS not-accessible
       STATUS obsolete
       DESCRIPTION
           "Processing time (in Microseconds), per command type."
       ::= {acPMSIP 27}



     -- ****************************************
     -- acPMSIPTrunkGroupPercentageUtilization table entry
     -- ****************************************
     acPMSIPTrunkGroupPercentageUtilizationEntry OBJECT-TYPE
       SYNTAX AcPMSIPTrunkGroupPercentageUtilizationEntry
       MAX-ACCESS not-accessible
       STATUS obsolete
       DESCRIPTION
           ""
       INDEX {acPMSIPTrunkGroupPercentageUtilizationTrunkGroupNum,acPMSIPTrunkGroupPercentageUtilizationInterval}
       ::= {acPMSIPTrunkGroupPercentageUtilizationTable 1}



     -- ****************************************
     -- acPMSIPTrunkGroupPercentageUtilization TABLE
     -- ****************************************
     AcPMSIPTrunkGroupPercentageUtilizationEntry ::= SEQUENCE {
       acPMSIPTrunkGroupPercentageUtilizationTrunkGroupNum 
                                                       Unsigned32,
       acPMSIPTrunkGroupPercentageUtilizationInterval  Unsigned32,
       acPMSIPTrunkGroupPercentageUtilizationVal       Gauge32,
       acPMSIPTrunkGroupPercentageUtilizationTimeBelowLowThreshold 
                                                       Unsigned32,
       acPMSIPTrunkGroupPercentageUtilizationTimeBetweenThresholds 
                                                       Unsigned32,
       acPMSIPTrunkGroupPercentageUtilizationTimeAboveHighThreshold 
                                                       Unsigned32,
       acPMSIPTrunkGroupPercentageUtilizationAverage   Unsigned32,
       acPMSIPTrunkGroupPercentageUtilizationMax       Unsigned32,
       acPMSIPTrunkGroupPercentageUtilizationMin       Unsigned32,
       acPMSIPTrunkGroupPercentageUtilizationFullDayAverage 
                                                       Unsigned32
     }



     acPMSIPTrunkGroupPercentageUtilizationTrunkGroupNum OBJECT-TYPE
       SYNTAX Unsigned32 (0..83)
       MAX-ACCESS not-accessible
       STATUS obsolete
       DESCRIPTION
           "Trunk Group number.
0 is the first Trunk Group."
       ::= {acPMSIPTrunkGroupPercentageUtilizationEntry 1}



     acPMSIPTrunkGroupPercentageUtilizationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupPercentageUtilizationEntry 2}



     acPMSIPTrunkGroupPercentageUtilizationVal OBJECT-TYPE
       SYNTAX Gauge32
       MAX-ACCESS read-only
       STATUS obsolete
       DESCRIPTION
           "Current value of gauge in percentage."
       ::= {acPMSIPTrunkGroupPercentageUtilizationEntry 3}



     acPMSIPTrunkGroupPercentageUtilizationTimeBelowLowThreshold OBJECT-TYPE
       SYNTAX Unsigned32 (0..100)
       MAX-ACCESS read-only
       STATUS obsolete
       DESCRIPTION
           "Percent of interval time for which gauge is below what was determined
as the low threshold."
       ::= {acPMSIPTrunkGroupPercentageUtilizationEntry 4}



     acPMSIPTrunkGroupPercentageUtilizationTimeBetweenThresholds OBJECT-TYPE
       SYNTAX Unsigned32 (0..100)
       MAX-ACCESS read-only
       STATUS obsolete
       DESCRIPTION
           "Percent of interval time for which gauge is between what were
determined as the low and high thresholds."
       ::= {acPMSIPTrunkGroupPercentageUtilizationEntry 5}



     acPMSIPTrunkGroupPercentageUtilizationTimeAboveHighThreshold OBJECT-TYPE
       SYNTAX Unsigned32 (0..100)
       MAX-ACCESS read-only
       STATUS obsolete
       DESCRIPTION
           "Percent of interval time for which gauge is above what was determined
as the high threshold."
       ::= {acPMSIPTrunkGroupPercentageUtilizationEntry 6}



     acPMSIPTrunkGroupPercentageUtilizationAverage OBJECT-TYPE
       SYNTAX Unsigned32 (0..100)
       MAX-ACCESS read-only
       STATUS obsolete
       DESCRIPTION
           "Average percentage of utilization with in the period time."
       ::= {acPMSIPTrunkGroupPercentageUtilizationEntry 7}



     acPMSIPTrunkGroupPercentageUtilizationMax OBJECT-TYPE
       SYNTAX Unsigned32 (0..100)
       MAX-ACCESS read-only
       STATUS obsolete
       DESCRIPTION
           "Maximum percentage of utilization with in the period time."
       ::= {acPMSIPTrunkGroupPercentageUtilizationEntry 8}



     acPMSIPTrunkGroupPercentageUtilizationMin OBJECT-TYPE
       SYNTAX Unsigned32 (0..100)
       MAX-ACCESS read-only
       STATUS obsolete
       DESCRIPTION
           "Minimum percentage of utilization with in the period time."
       ::= {acPMSIPTrunkGroupPercentageUtilizationEntry 9}



     acPMSIPTrunkGroupPercentageUtilizationFullDayAverage OBJECT-TYPE
       SYNTAX Unsigned32 (0..100)
       MAX-ACCESS read-only
       STATUS obsolete
       DESCRIPTION
           "The average percentage of utilization with in the past 24 hours."
       ::= {acPMSIPTrunkGroupPercentageUtilizationEntry 10}



     -- ****************************************
     -- acPMSIPTrunkGroupNoResourcesCalls table declaration
     -- ****************************************
     acPMSIPTrunkGroupNoResourcesCallsTable OBJECT-TYPE
       SYNTAX SEQUENCE OF AcPMSIPTrunkGroupNoResourcesCallsEntry
       MAX-ACCESS not-accessible
       STATUS obsolete
       DESCRIPTION
           "Number of calls released because of no resources (Index for the Trunk Group ID)"
       ::= {acPMSIP 28}



     -- ****************************************
     -- acPMSIPTrunkGroupNoResourcesCalls table entry
     -- ****************************************
     acPMSIPTrunkGroupNoResourcesCallsEntry OBJECT-TYPE
       SYNTAX AcPMSIPTrunkGroupNoResourcesCallsEntry
       MAX-ACCESS not-accessible
       STATUS obsolete
       DESCRIPTION
           ""
       INDEX {acPMSIPTrunkGroupNoResourcesCallsTrunkGroupNum,acPMSIPTrunkGroupNoResourcesCallsInterval}
       ::= {acPMSIPTrunkGroupNoResourcesCallsTable 1}



     -- ****************************************
     -- acPMSIPTrunkGroupNoResourcesCalls TABLE
     -- ****************************************
     AcPMSIPTrunkGroupNoResourcesCallsEntry ::= SEQUENCE {
       acPMSIPTrunkGroupNoResourcesCallsTrunkGroupNum  Unsigned32,
       acPMSIPTrunkGroupNoResourcesCallsInterval       Unsigned32,
       acPMSIPTrunkGroupNoResourcesCallsVal            Counter32,
       acPMSIPTrunkGroupNoResourcesCallsTotal          Counter32
     }



     acPMSIPTrunkGroupNoResourcesCallsTrunkGroupNum OBJECT-TYPE
       SYNTAX Unsigned32 (0..83)
       MAX-ACCESS not-accessible
       STATUS obsolete
       DESCRIPTION
           "Trunk Group number.
0 is the first Trunk Group."
       ::= {acPMSIPTrunkGroupNoResourcesCallsEntry 1}



     acPMSIPTrunkGroupNoResourcesCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupNoResourcesCallsEntry 2}



     acPMSIPTrunkGroupNoResourcesCallsVal OBJECT-TYPE
       SYNTAX Counter32
       MAX-ACCESS read-only
       STATUS obsolete
       DESCRIPTION
           "Value of gauge or counter."
       ::= {acPMSIPTrunkGroupNoResourcesCallsEntry 3}



     acPMSIPTrunkGroupNoResourcesCallsTotal OBJECT-TYPE
       SYNTAX Counter32
       MAX-ACCESS read-only
       STATUS obsolete
       DESCRIPTION
           "Activity volume."
       ::= {acPMSIPTrunkGroupNoResourcesCallsEntry 4}



     -- ****************************************
     -- acPMSIPTrunkGroupCallDuration table declaration
     -- ****************************************
     acPMSIPTrunkGroupCallDurationTable OBJECT-TYPE
       SYNTAX SEQUENCE OF AcPMSIPTrunkGroupCallDurationEntry
       MAX-ACCESS not-accessible
       STATUS obsolete
       DESCRIPTION
           "Call Duration of Trunk Group"
       ::= {acPMSIP 29}



     -- ****************************************
     -- acPMSIPTrunkGroupCallDuration table entry
     -- ****************************************
     acPMSIPTrunkGroupCallDurationEntry OBJECT-TYPE
       SYNTAX AcPMSIPTrunkGroupCallDurationEntry
       MAX-ACCESS not-accessible
       STATUS obsolete
       DESCRIPTION
           ""
       INDEX {acPMSIPTrunkGroupCallDurationTrunkGroupNum,acPMSIPTrunkGroupCallDurationInterval}
       ::= {acPMSIPTrunkGroupCallDurationTable 1}



     -- ****************************************
     -- acPMSIPTrunkGroupCallDuration TABLE
     -- ****************************************
     AcPMSIPTrunkGroupCallDurationEntry ::= SEQUENCE {
       acPMSIPTrunkGroupCallDurationTrunkGroupNum      Unsigned32,
       acPMSIPTrunkGroupCallDurationInterval           Unsigned32,
       acPMSIPTrunkGroupCallDurationVal                Gauge32,
       acPMSIPTrunkGroupCallDurationAverage            Unsigned32,
       acPMSIPTrunkGroupCallDurationMax                Unsigned32,
       acPMSIPTrunkGroupCallDurationMin                Unsigned32,
       acPMSIPTrunkGroupCallDurationTotal              Counter32,
       acPMSIPTrunkGroupCallDurationFullDayAverage     Unsigned32
     }



     acPMSIPTrunkGroupCallDurationTrunkGroupNum OBJECT-TYPE
       SYNTAX Unsigned32 (0..83)
       MAX-ACCESS not-accessible
       STATUS obsolete
       DESCRIPTION
           "Trunk Group number.
0 is the first Trunk Group."
       ::= {acPMSIPTrunkGroupCallDurationEntry 1}



     acPMSIPTrunkGroupCallDurationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupCallDurationEntry 2}



     acPMSIPTrunkGroupCallDurationVal OBJECT-TYPE
       SYNTAX Gauge32
       MAX-ACCESS read-only
       STATUS obsolete
       DESCRIPTION
           "Value of gauge or counter."
       ::= {acPMSIPTrunkGroupCallDurationEntry 3}



     acPMSIPTrunkGroupCallDurationAverage OBJECT-TYPE
       SYNTAX Unsigned32 (0..2147483647)
       MAX-ACCESS read-only
       STATUS obsolete
       DESCRIPTION
           "Average value with in the period time."
       ::= {acPMSIPTrunkGroupCallDurationEntry 4}



     acPMSIPTrunkGroupCallDurationMax OBJECT-TYPE
       SYNTAX Unsigned32 (0..2147483647)
       MAX-ACCESS read-only
       STATUS obsolete
       DESCRIPTION
           "Maximum value with in the period time."
       ::= {acPMSIPTrunkGroupCallDurationEntry 5}



     acPMSIPTrunkGroupCallDurationMin OBJECT-TYPE
       SYNTAX Unsigned32 (0..2147483647)
       MAX-ACCESS read-only
       STATUS obsolete
       DESCRIPTION
           "Minimum value with in the period time."
       ::= {acPMSIPTrunkGroupCallDurationEntry 6}



     acPMSIPTrunkGroupCallDurationTotal OBJECT-TYPE
       SYNTAX Counter32
       MAX-ACCESS read-only
       STATUS obsolete
       DESCRIPTION
           "Sum duration of all calls of Trunk Group."
       ::= {acPMSIPTrunkGroupCallDurationEntry 7}



     acPMSIPTrunkGroupCallDurationFullDayAverage OBJECT-TYPE
       SYNTAX Unsigned32 (0..2147483647)
       MAX-ACCESS read-only
       STATUS obsolete
       DESCRIPTION
           "The average of full 24 hours."
       ::= {acPMSIPTrunkGroupCallDurationEntry 8}



     -- ****************************************
     -- acPMSIPIPGroupInDialogs table declaration
     -- ****************************************
     acPMSIPIPGroupInDialogsTable OBJECT-TYPE
       SYNTAX SEQUENCE OF AcPMSIPIPGroupInDialogsEntry
       MAX-ACCESS not-accessible
       STATUS obsolete
       DESCRIPTION
           "Number of incoming dialogs per IP group."
       ::= {acPMSIP 30}



     -- ****************************************
     -- acPMSIPIPGroupInDialogs table entry
     -- ****************************************
     acPMSIPIPGroupInDialogsEntry OBJECT-TYPE
       SYNTAX AcPMSIPIPGroupInDialogsEntry
       MAX-ACCESS not-accessible
       STATUS obsolete
       DESCRIPTION
           ""
       INDEX {acPMSIPIPGroupInDialogsIpGroup,acPMSIPIPGroupInDialogsInterval}
       ::= {acPMSIPIPGroupInDialogsTable 1}



     -- ****************************************
     -- acPMSIPIPGroupInDialogs TABLE
     -- ****************************************
     AcPMSIPIPGroupInDialogsEntry ::= SEQUENCE {
       acPMSIPIPGroupInDialogsIpGroup                  Unsigned32,
       acPMSIPIPGroupInDialogsInterval                 Unsigned32,
       acPMSIPIPGroupInDialogsVal                      Counter32
     }



     acPMSIPIPGroupInDialogsIpGroup OBJECT-TYPE
       SYNTAX Unsigned32 (0..5000)
       MAX-ACCESS not-accessible
       STATUS obsolete
       DESCRIPTION
           "IP Group number."
       ::= {acPMSIPIPGroupInDialogsEntry 1}



     acPMSIPIPGroupInDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupInDialogsEntry 2}



     acPMSIPIPGroupInDialogsVal OBJECT-TYPE
       SYNTAX Counter32
       MAX-ACCESS read-only
       STATUS obsolete
       DESCRIPTION
           "Value of gauge or counter."
       ::= {acPMSIPIPGroupInDialogsEntry 3}



     -- ****************************************
     -- acPMSIPIPGroupOutDialogs table declaration
     -- ****************************************
     acPMSIPIPGroupOutDialogsTable OBJECT-TYPE
       SYNTAX SEQUENCE OF AcPMSIPIPGroupOutDialogsEntry
       MAX-ACCESS not-accessible
       STATUS obsolete
       DESCRIPTION
           "Number of outgoing dialogs per IP group."
       ::= {acPMSIP 31}



     -- ****************************************
     -- acPMSIPIPGroupOutDialogs table entry
     -- ****************************************
     acPMSIPIPGroupOutDialogsEntry OBJECT-TYPE
       SYNTAX AcPMSIPIPGroupOutDialogsEntry
       MAX-ACCESS not-accessible
       STATUS obsolete
       DESCRIPTION
           ""
       INDEX {acPMSIPIPGroupOutDialogsIpGroup,acPMSIPIPGroupOutDialogsInterval}
       ::= {acPMSIPIPGroupOutDialogsTable 1}



     -- ****************************************
     -- acPMSIPIPGroupOutDialogs TABLE
     -- ****************************************
     AcPMSIPIPGroupOutDialogsEntry ::= SEQUENCE {
       acPMSIPIPGroupOutDialogsIpGroup                 Unsigned32,
       acPMSIPIPGroupOutDialogsInterval                Unsigned32,
       acPMSIPIPGroupOutDialogsVal                     Counter32
     }



     acPMSIPIPGroupOutDialogsIpGroup OBJECT-TYPE
       SYNTAX Unsigned32 (0..5000)
       MAX-ACCESS not-accessible
       STATUS obsolete
       DESCRIPTION
           "IP Group number."
       ::= {acPMSIPIPGroupOutDialogsEntry 1}



     acPMSIPIPGroupOutDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupOutDialogsEntry 2}



     acPMSIPIPGroupOutDialogsVal OBJECT-TYPE
       SYNTAX Counter32
       MAX-ACCESS read-only
       STATUS obsolete
       DESCRIPTION
           "Value of gauge or counter."
       ::= {acPMSIPIPGroupOutDialogsEntry 3}



     -- ****************************************
     -- acPMSIPIPGroupInInviteDialogs table declaration
     -- ****************************************
     acPMSIPIPGroupInInviteDialogsTable OBJECT-TYPE
       SYNTAX SEQUENCE OF AcPMSIPIPGroupInInviteDialogsEntry
       MAX-ACCESS not-accessible
       STATUS obsolete
       DESCRIPTION
           "Number of incoming INVITE dialogs per IP group."
       ::= {acPMSIP 32}



     -- ****************************************
     -- acPMSIPIPGroupInInviteDialogs table entry
     -- ****************************************
     acPMSIPIPGroupInInviteDialogsEntry OBJECT-TYPE
       SYNTAX AcPMSIPIPGroupInInviteDialogsEntry
       MAX-ACCESS not-accessible
       STATUS obsolete
       DESCRIPTION
           ""
       INDEX {acPMSIPIPGroupInInviteDialogsIpGroup,acPMSIPIPGroupInInviteDialogsInterval}
       ::= {acPMSIPIPGroupInInviteDialogsTable 1}



     -- ****************************************
     -- acPMSIPIPGroupInInviteDialogs TABLE
     -- ****************************************
     AcPMSIPIPGroupInInviteDialogsEntry ::= SEQUENCE {
       acPMSIPIPGroupInInviteDialogsIpGroup            Unsigned32,
       acPMSIPIPGroupInInviteDialogsInterval           Unsigned32,
       acPMSIPIPGroupInInviteDialogsVal                Gauge32,
       acPMSIPIPGroupInInviteDialogsAverage            Unsigned32,
       acPMSIPIPGroupInInviteDialogsMax                Unsigned32,
       acPMSIPIPGroupInInviteDialogsMin                Unsigned32,
       acPMSIPIPGroupInInviteDialogsTimeBelowLowThreshold 
                                                       Unsigned32,
       acPMSIPIPGroupInInviteDialogsTimeBetweenThresholds 
                                                       Unsigned32,
       acPMSIPIPGroupInInviteDialogsTimeAboveHighThreshold 
                                                       Unsigned32,
       acPMSIPIPGroupInInviteDialogsTotal              Counter32
     }



     acPMSIPIPGroupInInviteDialogsIpGroup OBJECT-TYPE
       SYNTAX Unsigned32 (0..5000)
       MAX-ACCESS not-accessible
       STATUS obsolete
       DESCRIPTION
           "IP Group number."
       ::= {acPMSIPIPGroupInInviteDialogsEntry 1}



     acPMSIPIPGroupInInviteDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupInInviteDialogsEntry 2}



     acPMSIPIPGroupInInviteDialogsVal OBJECT-TYPE
       SYNTAX Gauge32
       MAX-ACCESS read-only
       STATUS obsolete
       DESCRIPTION
           "Value of gauge or counter."
       ::= {acPMSIPIPGroupInInviteDialogsEntry 3}



     acPMSIPIPGroupInInviteDialogsAverage OBJECT-TYPE
       SYNTAX Unsigned32 (0..2147483647)
       MAX-ACCESS read-only
       STATUS obsolete
       DESCRIPTION
           "Average value with in the period time."
       ::= {acPMSIPIPGroupInInviteDialogsEntry 4}



     acPMSIPIPGroupInInviteDialogsMax OBJECT-TYPE
       SYNTAX Unsigned32 (0..2147483647)
       MAX-ACCESS read-only
       STATUS obsolete
       DESCRIPTION
           "Maximum value with in the period time."
       ::= {acPMSIPIPGroupInInviteDialogsEntry 5}



     acPMSIPIPGroupInInviteDialogsMin OBJECT-TYPE
       SYNTAX Unsigned32 (0..2147483647)
       MAX-ACCESS read-only
       STATUS obsolete
       DESCRIPTION
           "Minimum value with in the period time."
       ::= {acPMSIPIPGroupInInviteDialogsEntry 6}



     acPMSIPIPGroupInInviteDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupInInviteDialogsEntry 7}



     acPMSIPIPGroupInInviteDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupInInviteDialogsEntry 8}



     acPMSIPIPGroupInInviteDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupInInviteDialogsEntry 9}



     acPMSIPIPGroupInInviteDialogsTotal OBJECT-TYPE
       SYNTAX Counter32
       MAX-ACCESS read-only
       STATUS obsolete
       DESCRIPTION
           "Total."
       ::= {acPMSIPIPGroupInInviteDialogsEntry 10}



     -- ****************************************
     -- acPMSIPIPGroupInSubscribeDialogs table declaration
     -- ****************************************
     acPMSIPIPGroupInSubscribeDialogsTable OBJECT-TYPE
       SYNTAX SEQUENCE OF AcPMSIPIPGroupInSubscribeDialogsEntry
       MAX-ACCESS not-accessible
       STATUS obsolete
       DESCRIPTION
           "Number of incoming SUBSCRIBE dialogs per IP group."
       ::= {acPMSIP 33}



     -- ****************************************
     -- acPMSIPIPGroupInSubscribeDialogs table entry
     -- ****************************************
     acPMSIPIPGroupInSubscribeDialogsEntry OBJECT-TYPE
       SYNTAX AcPMSIPIPGroupInSubscribeDialogsEntry
       MAX-ACCESS not-accessible
       STATUS obsolete
       DESCRIPTION
           ""
       INDEX {acPMSIPIPGroupInSubscribeDialogsIpGroup,acPMSIPIPGroupInSubscribeDialogsInterval}
       ::= {acPMSIPIPGroupInSubscribeDialogsTable 1}



     -- ****************************************
     -- acPMSIPIPGroupInSubscribeDialogs TABLE
     -- ****************************************
     AcPMSIPIPGroupInSubscribeDialogsEntry ::= SEQUENCE {
       acPMSIPIPGroupInSubscribeDialogsIpGroup         Unsigned32,
       acPMSIPIPGroupInSubscribeDialogsInterval        Unsigned32,
       acPMSIPIPGroupInSubscribeDialogsVal             Gauge32,
       acPMSIPIPGroupInSubscribeDialogsAverage         Unsigned32,
       acPMSIPIPGroupInSubscribeDialogsMax             Unsigned32,
       acPMSIPIPGroupInSubscribeDialogsMin             Unsigned32,
       acPMSIPIPGroupInSubscribeDialogsTimeBelowLowThreshold 
                                                       Unsigned32,
       acPMSIPIPGroupInSubscribeDialogsTimeBetweenThresholds 
                                                       Unsigned32,
       acPMSIPIPGroupInSubscribeDialogsTimeAboveHighThreshold 
                                                       Unsigned32,
       acPMSIPIPGroupInSubscribeDialogsTotal           Counter32
     }



     acPMSIPIPGroupInSubscribeDialogsIpGroup OBJECT-TYPE
       SYNTAX Unsigned32 (0..5000)
       MAX-ACCESS not-accessible
       STATUS obsolete
       DESCRIPTION
           "IP Group number."
       ::= {acPMSIPIPGroupInSubscribeDialogsEntry 1}



     acPMSIPIPGroupInSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupInSubscribeDialogsEntry 2}



     acPMSIPIPGroupInSubscribeDialogsVal OBJECT-TYPE
       SYNTAX Gauge32
       MAX-ACCESS read-only
       STATUS obsolete
       DESCRIPTION
           "Value of gauge or counter."
       ::= {acPMSIPIPGroupInSubscribeDialogsEntry 3}



     acPMSIPIPGroupInSubscribeDialogsAverage OBJECT-TYPE
       SYNTAX Unsigned32 (0..2147483647)
       MAX-ACCESS read-only
       STATUS obsolete
       DESCRIPTION
           "Average value with in the period time."
       ::= {acPMSIPIPGroupInSubscribeDialogsEntry 4}



     acPMSIPIPGroupInSubscribeDialogsMax OBJECT-TYPE
       SYNTAX Unsigned32 (0..2147483647)
       MAX-ACCESS read-only
       STATUS obsolete
       DESCRIPTION
           "Maximum value with in the period time."
       ::= {acPMSIPIPGroupInSubscribeDialogsEntry 5}



     acPMSIPIPGroupInSubscribeDialogsMin OBJECT-TYPE
       SYNTAX Unsigned32 (0..2147483647)
       MAX-ACCESS read-only
       STATUS obsolete
       DESCRIPTION
           "Minimum value with in the period time."
       ::= {acPMSIPIPGroupInSubscribeDialogsEntry 6}



     acPMSIPIPGroupInSubscribeDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupInSubscribeDialogsEntry 7}



     acPMSIPIPGroupInSubscribeDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupInSubscribeDialogsEntry 8}



     acPMSIPIPGroupInSubscribeDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupInSubscribeDialogsEntry 9}



     acPMSIPIPGroupInSubscribeDialogsTotal OBJECT-TYPE
       SYNTAX Counter32
       MAX-ACCESS read-only
       STATUS obsolete
       DESCRIPTION
           "Total."
       ::= {acPMSIPIPGroupInSubscribeDialogsEntry 10}



     -- ****************************************
     -- acPMSIPIPGroupInOtherDialogs table declaration
     -- ****************************************
     acPMSIPIPGroupInOtherDialogsTable OBJECT-TYPE
       SYNTAX SEQUENCE OF AcPMSIPIPGroupInOtherDialogsEntry
       MAX-ACCESS not-accessible
       STATUS obsolete
       DESCRIPTION
           "Number of incoming other dialogs per IP group."
       ::= {acPMSIP 34}



     -- ****************************************
     -- acPMSIPIPGroupInOtherDialogs table entry
     -- ****************************************
     acPMSIPIPGroupInOtherDialogsEntry OBJECT-TYPE
       SYNTAX AcPMSIPIPGroupInOtherDialogsEntry
       MAX-ACCESS not-accessible
       STATUS obsolete
       DESCRIPTION
           ""
       INDEX {acPMSIPIPGroupInOtherDialogsIpGroup,acPMSIPIPGroupInOtherDialogsInterval}
       ::= {acPMSIPIPGroupInOtherDialogsTable 1}



     -- ****************************************
     -- acPMSIPIPGroupInOtherDialogs TABLE
     -- ****************************************
     AcPMSIPIPGroupInOtherDialogsEntry ::= SEQUENCE {
       acPMSIPIPGroupInOtherDialogsIpGroup             Unsigned32,
       acPMSIPIPGroupInOtherDialogsInterval            Unsigned32,
       acPMSIPIPGroupInOtherDialogsVal                 Counter32
     }



     acPMSIPIPGroupInOtherDialogsIpGroup OBJECT-TYPE
       SYNTAX Unsigned32 (0..5000)
       MAX-ACCESS not-accessible
       STATUS obsolete
       DESCRIPTION
           "IP Group number."
       ::= {acPMSIPIPGroupInOtherDialogsEntry 1}



     acPMSIPIPGroupInOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupInOtherDialogsEntry 2}



     acPMSIPIPGroupInOtherDialogsVal OBJECT-TYPE
       SYNTAX Counter32
       MAX-ACCESS read-only
       STATUS obsolete
       DESCRIPTION
           "Value of gauge or counter."
       ::= {acPMSIPIPGroupInOtherDialogsEntry 3}



     -- ****************************************
     -- acPMSIPIPGroupOutInviteDialogs table declaration
     -- ****************************************
     acPMSIPIPGroupOutInviteDialogsTable OBJECT-TYPE
       SYNTAX SEQUENCE OF AcPMSIPIPGroupOutInviteDialogsEntry
       MAX-ACCESS not-accessible
       STATUS obsolete
       DESCRIPTION
           "Number of outgoing INVITE dialogs per IP group."
       ::= {acPMSIP 35}



     -- ****************************************
     -- acPMSIPIPGroupOutInviteDialogs table entry
     -- ****************************************
     acPMSIPIPGroupOutInviteDialogsEntry OBJECT-TYPE
       SYNTAX AcPMSIPIPGroupOutInviteDialogsEntry
       MAX-ACCESS not-accessible
       STATUS obsolete
       DESCRIPTION
           ""
       INDEX {acPMSIPIPGroupOutInviteDialogsIpGroup,acPMSIPIPGroupOutInviteDialogsInterval}
       ::= {acPMSIPIPGroupOutInviteDialogsTable 1}



     -- ****************************************
     -- acPMSIPIPGroupOutInviteDialogs TABLE
     -- ****************************************
     AcPMSIPIPGroupOutInviteDialogsEntry ::= SEQUENCE {
       acPMSIPIPGroupOutInviteDialogsIpGroup           Unsigned32,
       acPMSIPIPGroupOutInviteDialogsInterval          Unsigned32,
       acPMSIPIPGroupOutInviteDialogsVal               Gauge32,
       acPMSIPIPGroupOutInviteDialogsAverage           Unsigned32,
       acPMSIPIPGroupOutInviteDialogsMax               Unsigned32,
       acPMSIPIPGroupOutInviteDialogsMin               Unsigned32,
       acPMSIPIPGroupOutInviteDialogsTimeBelowLowThreshold 
                                                       Unsigned32,
       acPMSIPIPGroupOutInviteDialogsTimeBetweenThresholds 
                                                       Unsigned32,
       acPMSIPIPGroupOutInviteDialogsTimeAboveHighThreshold 
                                                       Unsigned32,
       acPMSIPIPGroupOutInviteDialogsTotal             Counter32
     }



     acPMSIPIPGroupOutInviteDialogsIpGroup OBJECT-TYPE
       SYNTAX Unsigned32 (0..5000)
       MAX-ACCESS not-accessible
       STATUS obsolete
       DESCRIPTION
           "IP Group number."
       ::= {acPMSIPIPGroupOutInviteDialogsEntry 1}



     acPMSIPIPGroupOutInviteDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupOutInviteDialogsEntry 2}



     acPMSIPIPGroupOutInviteDialogsVal OBJECT-TYPE
       SYNTAX Gauge32
       MAX-ACCESS read-only
       STATUS obsolete
       DESCRIPTION
           "Value of gauge or counter."
       ::= {acPMSIPIPGroupOutInviteDialogsEntry 3}



     acPMSIPIPGroupOutInviteDialogsAverage OBJECT-TYPE
       SYNTAX Unsigned32 (0..2147483647)
       MAX-ACCESS read-only
       STATUS obsolete
       DESCRIPTION
           "Average value with in the period time."
       ::= {acPMSIPIPGroupOutInviteDialogsEntry 4}



     acPMSIPIPGroupOutInviteDialogsMax OBJECT-TYPE
       SYNTAX Unsigned32 (0..2147483647)
       MAX-ACCESS read-only
       STATUS obsolete
       DESCRIPTION
           "Maximum value with in the period time."
       ::= {acPMSIPIPGroupOutInviteDialogsEntry 5}



     acPMSIPIPGroupOutInviteDialogsMin OBJECT-TYPE
       SYNTAX Unsigned32 (0..2147483647)
       MAX-ACCESS read-only
       STATUS obsolete
       DESCRIPTION
           "Minimum value with in the period time."
       ::= {acPMSIPIPGroupOutInviteDialogsEntry 6}



     acPMSIPIPGroupOutInviteDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupOutInviteDialogsEntry 7}



     acPMSIPIPGroupOutInviteDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupOutInviteDialogsEntry 8}



     acPMSIPIPGroupOutInviteDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupOutInviteDialogsEntry 9}



     acPMSIPIPGroupOutInviteDialogsTotal OBJECT-TYPE
       SYNTAX Counter32
       MAX-ACCESS read-only
       STATUS obsolete
       DESCRIPTION
           "Total."
       ::= {acPMSIPIPGroupOutInviteDialogsEntry 10}



     -- ****************************************
     -- acPMSIPIPGroupOutSubscribeDialogs table declaration
     -- ****************************************
     acPMSIPIPGroupOutSubscribeDialogsTable OBJECT-TYPE
       SYNTAX SEQUENCE OF AcPMSIPIPGroupOutSubscribeDialogsEntry
       MAX-ACCESS not-accessible
       STATUS obsolete
       DESCRIPTION
           "Number of outgoing SUBSCRIBE dialogs per IP group."
       ::= {acPMSIP 36}



     -- ****************************************
     -- acPMSIPIPGroupOutSubscribeDialogs table entry
     -- ****************************************
     acPMSIPIPGroupOutSubscribeDialogsEntry OBJECT-TYPE
       SYNTAX AcPMSIPIPGroupOutSubscribeDialogsEntry
       MAX-ACCESS not-accessible
       STATUS obsolete
       DESCRIPTION
           ""
       INDEX {acPMSIPIPGroupOutSubscribeDialogsIpGroup,acPMSIPIPGroupOutSubscribeDialogsInterval}
       ::= {acPMSIPIPGroupOutSubscribeDialogsTable 1}



     -- ****************************************
     -- acPMSIPIPGroupOutSubscribeDialogs TABLE
     -- ****************************************
     AcPMSIPIPGroupOutSubscribeDialogsEntry ::= SEQUENCE {
       acPMSIPIPGroupOutSubscribeDialogsIpGroup        Unsigned32,
       acPMSIPIPGroupOutSubscribeDialogsInterval       Unsigned32,
       acPMSIPIPGroupOutSubscribeDialogsVal            Gauge32,
       acPMSIPIPGroupOutSubscribeDialogsAverage        Unsigned32,
       acPMSIPIPGroupOutSubscribeDialogsMax            Unsigned32,
       acPMSIPIPGroupOutSubscribeDialogsMin            Unsigned32,
       acPMSIPIPGroupOutSubscribeDialogsTimeBelowLowThreshold 
                                                       Unsigned32,
       acPMSIPIPGroupOutSubscribeDialogsTimeBetweenThresholds 
                                                       Unsigned32,
       acPMSIPIPGroupOutSubscribeDialogsTimeAboveHighThreshold 
                                                       Unsigned32,
       acPMSIPIPGroupOutSubscribeDialogsTotal          Counter32
     }



     acPMSIPIPGroupOutSubscribeDialogsIpGroup OBJECT-TYPE
       SYNTAX Unsigned32 (0..5000)
       MAX-ACCESS not-accessible
       STATUS obsolete
       DESCRIPTION
           "IP Group number."
       ::= {acPMSIPIPGroupOutSubscribeDialogsEntry 1}



     acPMSIPIPGroupOutSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupOutSubscribeDialogsEntry 2}



     acPMSIPIPGroupOutSubscribeDialogsVal OBJECT-TYPE
       SYNTAX Gauge32
       MAX-ACCESS read-only
       STATUS obsolete
       DESCRIPTION
           "Value of gauge or counter."
       ::= {acPMSIPIPGroupOutSubscribeDialogsEntry 3}



     acPMSIPIPGroupOutSubscribeDialogsAverage OBJECT-TYPE
       SYNTAX Unsigned32 (0..2147483647)
       MAX-ACCESS read-only
       STATUS obsolete
       DESCRIPTION
           "Average value with in the period time."
       ::= {acPMSIPIPGroupOutSubscribeDialogsEntry 4}



     acPMSIPIPGroupOutSubscribeDialogsMax OBJECT-TYPE
       SYNTAX Unsigned32 (0..2147483647)
       MAX-ACCESS read-only
       STATUS obsolete
       DESCRIPTION
           "Maximum value with in the period time."
       ::= {acPMSIPIPGroupOutSubscribeDialogsEntry 5}



     acPMSIPIPGroupOutSubscribeDialogsMin OBJECT-TYPE
       SYNTAX Unsigned32 (0..2147483647)
       MAX-ACCESS read-only
       STATUS obsolete
       DESCRIPTION
           "Minimum value with in the period time."
       ::= {acPMSIPIPGroupOutSubscribeDialogsEntry 6}



     acPMSIPIPGroupOutSubscribeDialogsTimeBelowLowThreshold OBJECT-TYPE
       SYNTAX Unsigned32 (0..100)
       MAX-ACCESS read-only
       STATUS obsolete
       DESCRIPTION
           "Percent of interval time for which gauge is below what was determined
as the low threshold."
       ::= {acPMSIPIPGroupOutSubscribeDialogsEntry 7}



     acPMSIPIPGroupOutSubscribeDialogsTimeBetweenThresholds OBJECT-TYPE
       SYNTAX Unsigned32 (0..100)
       MAX-ACCESS read-only
       STATUS obsolete
       DESCRIPTION
           "Percent of interval time for which gauge is between what were
determined as the low and high thresholds."
       ::= {acPMSIPIPGroupOutSubscribeDialogsEntry 8}



     acPMSIPIPGroupOutSubscribeDialogsTimeAboveHighThreshold OBJECT-TYPE
       SYNTAX Unsigned32 (0..100)
       MAX-ACCESS read-only
       STATUS obsolete
       DESCRIPTION
           "Percent of interval time for which gauge is above what was determined
as the high threshold."
       ::= {acPMSIPIPGroupOutSubscribeDialogsEntry 9}



     acPMSIPIPGroupOutSubscribeDialogsTotal OBJECT-TYPE
       SYNTAX Counter32
       MAX-ACCESS read-only
       STATUS obsolete
       DESCRIPTION
           "Total."
       ::= {acPMSIPIPGroupOutSubscribeDialogsEntry 10}



     -- ****************************************
     -- acPMSIPIPGroupOutOtherDialogs table declaration
     -- ****************************************
     acPMSIPIPGroupOutOtherDialogsTable OBJECT-TYPE
       SYNTAX SEQUENCE OF AcPMSIPIPGroupOutOtherDialogsEntry
       MAX-ACCESS not-accessible
       STATUS obsolete
       DESCRIPTION
           "Number of outgoing other dialogs per IP group."
       ::= {acPMSIP 37}



     -- ****************************************
     -- acPMSIPIPGroupOutOtherDialogs table entry
     -- ****************************************
     acPMSIPIPGroupOutOtherDialogsEntry OBJECT-TYPE
       SYNTAX AcPMSIPIPGroupOutOtherDialogsEntry
       MAX-ACCESS not-accessible
       STATUS obsolete
       DESCRIPTION
           ""
       INDEX {acPMSIPIPGroupOutOtherDialogsIpGroup,acPMSIPIPGroupOutOtherDialogsInterval}
       ::= {acPMSIPIPGroupOutOtherDialogsTable 1}



     -- ****************************************
     -- acPMSIPIPGroupOutOtherDialogs TABLE
     -- ****************************************
     AcPMSIPIPGroupOutOtherDialogsEntry ::= SEQUENCE {
       acPMSIPIPGroupOutOtherDialogsIpGroup            Unsigned32,
       acPMSIPIPGroupOutOtherDialogsInterval           Unsigned32,
       acPMSIPIPGroupOutOtherDialogsVal                Counter32
     }



     acPMSIPIPGroupOutOtherDialogsIpGroup OBJECT-TYPE
       SYNTAX Unsigned32 (0..5000)
       MAX-ACCESS not-accessible
       STATUS obsolete
       DESCRIPTION
           "IP Group number."
       ::= {acPMSIPIPGroupOutOtherDialogsEntry 1}



     acPMSIPIPGroupOutOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPIPGroupOutOtherDialogsEntry 2}



     acPMSIPIPGroupOutOtherDialogsVal OBJECT-TYPE
       SYNTAX Counter32
       MAX-ACCESS read-only
       STATUS obsolete
       DESCRIPTION
           "Value of gauge or counter."
       ::= {acPMSIPIPGroupOutOtherDialogsEntry 3}



     -- ****************************************
     -- acPMSIPInvitedDialogs table declaration
     -- ****************************************
     acPMSIPInvitedDialogsTable OBJECT-TYPE
       SYNTAX SEQUENCE OF AcPMSIPInvitedDialogsEntry
       MAX-ACCESS not-accessible
       STATUS obsolete
       DESCRIPTION
           "Number of INVITE dialogs."
       ::= {acPMSIP 38}



     -- ****************************************
     -- acPMSIPInvitedDialogs table entry
     -- ****************************************
     acPMSIPInvitedDialogsEntry OBJECT-TYPE
       SYNTAX AcPMSIPInvitedDialogsEntry
       MAX-ACCESS not-accessible
       STATUS obsolete
       DESCRIPTION
           ""
       INDEX {acPMSIPInvitedDialogsInterval}
       ::= {acPMSIPInvitedDialogsTable 1}



     -- ****************************************
     -- acPMSIPInvitedDialogs TABLE
     -- ****************************************
     AcPMSIPInvitedDialogsEntry ::= SEQUENCE {
       acPMSIPInvitedDialogsInterval                   Unsigned32,
       acPMSIPInvitedDialogsVal                        Counter32,
       acPMSIPInvitedDialogsAverage                    Unsigned32,
       acPMSIPInvitedDialogsMax                        Unsigned32,
       acPMSIPInvitedDialogsMin                        Unsigned32,
       acPMSIPInvitedDialogsTimeBelowLowThreshold      Unsigned32,
       acPMSIPInvitedDialogsTimeBetweenThresholds      Unsigned32,
       acPMSIPInvitedDialogsTimeAboveHighThreshold     Unsigned32,
       acPMSIPInvitedDialogsTotal                      Counter32
     }



     acPMSIPInvitedDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPInvitedDialogsEntry 1}



     acPMSIPInvitedDialogsVal OBJECT-TYPE
       SYNTAX Counter32
       MAX-ACCESS read-only
       STATUS obsolete
       DESCRIPTION
           "Value of gauge or counter."
       ::= {acPMSIPInvitedDialogsEntry 2}



     acPMSIPInvitedDialogsAverage OBJECT-TYPE
       SYNTAX Unsigned32 (0..2147483647)
       MAX-ACCESS read-only
       STATUS obsolete
       DESCRIPTION
           "Average value with in the period time."
       ::= {acPMSIPInvitedDialogsEntry 3}



     acPMSIPInvitedDialogsMax OBJECT-TYPE
       SYNTAX Unsigned32 (0..2147483647)
       MAX-ACCESS read-only
       STATUS obsolete
       DESCRIPTION
           "Maximum value with in the period time."
       ::= {acPMSIPInvitedDialogsEntry 4}



     acPMSIPInvitedDialogsMin OBJECT-TYPE
       SYNTAX Unsigned32 (0..2147483647)
       MAX-ACCESS read-only
       STATUS obsolete
       DESCRIPTION
           "Minimum value with in the period time."
       ::= {acPMSIPInvitedDialogsEntry 5}



     acPMSIPInvitedDialogsTimeBelowLowThreshold OBJECT-TYPE
       SYNTAX Unsigned32 (0..100)
       MAX-ACCESS read-only
       STATUS obsolete
       DESCRIPTION
           "Percent of interval time for which gauge is below what was determined
as the low threshold."
       ::= {acPMSIPInvitedDialogsEntry 6}



     acPMSIPInvitedDialogsTimeBetweenThresholds OBJECT-TYPE
       SYNTAX Unsigned32 (0..100)
       MAX-ACCESS read-only
       STATUS obsolete
       DESCRIPTION
           "Percent of interval time for which gauge is between what were
determined as the low and high thresholds."
       ::= {acPMSIPInvitedDialogsEntry 7}



     acPMSIPInvitedDialogsTimeAboveHighThreshold OBJECT-TYPE
       SYNTAX Unsigned32 (0..100)
       MAX-ACCESS read-only
       STATUS obsolete
       DESCRIPTION
           "Percent of interval time for which gauge is above what was determined
as the high threshold."
       ::= {acPMSIPInvitedDialogsEntry 8}



     acPMSIPInvitedDialogsTotal OBJECT-TYPE
       SYNTAX Counter32
       MAX-ACCESS read-only
       STATUS obsolete
       DESCRIPTION
           "Total."
       ::= {acPMSIPInvitedDialogsEntry 9}



     -- ****************************************
     -- acPMSIPSubscribeDialog table declaration
     -- ****************************************
     acPMSIPSubscribeDialogTable OBJECT-TYPE
       SYNTAX SEQUENCE OF AcPMSIPSubscribeDialogEntry
       MAX-ACCESS not-accessible
       STATUS obsolete
       DESCRIPTION
           "Number of SUBSCRIBE dialogs."
       ::= {acPMSIP 39}



     -- ****************************************
     -- acPMSIPSubscribeDialog table entry
     -- ****************************************
     acPMSIPSubscribeDialogEntry OBJECT-TYPE
       SYNTAX AcPMSIPSubscribeDialogEntry
       MAX-ACCESS not-accessible
       STATUS obsolete
       DESCRIPTION
           ""
       INDEX {acPMSIPSubscribeDialogInterval}
       ::= {acPMSIPSubscribeDialogTable 1}



     -- ****************************************
     -- acPMSIPSubscribeDialog TABLE
     -- ****************************************
     AcPMSIPSubscribeDialogEntry ::= SEQUENCE {
       acPMSIPSubscribeDialogInterval                  Unsigned32,
       acPMSIPSubscribeDialogVal                       Counter32,
       acPMSIPSubscribeDialogAverage                   Unsigned32,
       acPMSIPSubscribeDialogMax                       Unsigned32,
       acPMSIPSubscribeDialogMin                       Unsigned32,
       acPMSIPSubscribeDialogTimeBelowLowThreshold     Unsigned32,
       acPMSIPSubscribeDialogTimeBetweenThresholds     Unsigned32,
       acPMSIPSubscribeDialogTimeAboveHighThreshold    Unsigned32,
       acPMSIPSubscribeDialogTotal                     Counter32
     }



     acPMSIPSubscribeDialogInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSubscribeDialogEntry 1}



     acPMSIPSubscribeDialogVal OBJECT-TYPE
       SYNTAX Counter32
       MAX-ACCESS read-only
       STATUS obsolete
       DESCRIPTION
           "Value of gauge or counter."
       ::= {acPMSIPSubscribeDialogEntry 2}



     acPMSIPSubscribeDialogAverage OBJECT-TYPE
       SYNTAX Unsigned32 (0..2147483647)
       MAX-ACCESS read-only
       STATUS obsolete
       DESCRIPTION
           "Average value with in the period time."
       ::= {acPMSIPSubscribeDialogEntry 3}



     acPMSIPSubscribeDialogMax OBJECT-TYPE
       SYNTAX Unsigned32 (0..2147483647)
       MAX-ACCESS read-only
       STATUS obsolete
       DESCRIPTION
           "Maximum value with in the period time."
       ::= {acPMSIPSubscribeDialogEntry 4}



     acPMSIPSubscribeDialogMin OBJECT-TYPE
       SYNTAX Unsigned32 (0..2147483647)
       MAX-ACCESS read-only
       STATUS obsolete
       DESCRIPTION
           "Minimum value with in the period time."
       ::= {acPMSIPSubscribeDialogEntry 5}



     acPMSIPSubscribeDialogTimeBelowLowThreshold OBJECT-TYPE
       SYNTAX Unsigned32 (0..100)
       MAX-ACCESS read-only
       STATUS obsolete
       DESCRIPTION
           "Percent of interval time for which gauge is below what was determined
as the low threshold."
       ::= {acPMSIPSubscribeDialogEntry 6}



     acPMSIPSubscribeDialogTimeBetweenThresholds OBJECT-TYPE
       SYNTAX Unsigned32 (0..100)
       MAX-ACCESS read-only
       STATUS obsolete
       DESCRIPTION
           "Percent of interval time for which gauge is between what were
determined as the low and high thresholds."
       ::= {acPMSIPSubscribeDialogEntry 7}



     acPMSIPSubscribeDialogTimeAboveHighThreshold OBJECT-TYPE
       SYNTAX Unsigned32 (0..100)
       MAX-ACCESS read-only
       STATUS obsolete
       DESCRIPTION
           "Percent of interval time for which gauge is above what was determined
as the high threshold."
       ::= {acPMSIPSubscribeDialogEntry 8}



     acPMSIPSubscribeDialogTotal OBJECT-TYPE
       SYNTAX Counter32
       MAX-ACCESS read-only
       STATUS obsolete
       DESCRIPTION
           "Total."
       ::= {acPMSIPSubscribeDialogEntry 9}



     -- ****************************************
     -- acPMSIPTrunkGroupAllTrunksBusyPercentage table declaration
     -- ****************************************
     acPMSIPTrunkGroupAllTrunksBusyPercentageTable OBJECT-TYPE
       SYNTAX SEQUENCE OF AcPMSIPTrunkGroupAllTrunksBusyPercentageEntry
       MAX-ACCESS not-accessible
       STATUS obsolete
       DESCRIPTION
           "Performance Monitoring gwTrunkGroupAllTrunksBusyPercentage setup"
       ::= {acPMSIP 40}



     -- ****************************************
     -- acPMSIPTrunkGroupAllTrunksBusyPercentage table entry
     -- ****************************************
     acPMSIPTrunkGroupAllTrunksBusyPercentageEntry OBJECT-TYPE
       SYNTAX AcPMSIPTrunkGroupAllTrunksBusyPercentageEntry
       MAX-ACCESS not-accessible
       STATUS obsolete
       DESCRIPTION
           ""
       INDEX {acPMSIPTrunkGroupAllTrunksBusyPercentageTrunkGroupNum,acPMSIPTrunkGroupAllTrunksBusyPercentageInterval}
       ::= {acPMSIPTrunkGroupAllTrunksBusyPercentageTable 1}



     -- ****************************************
     -- acPMSIPTrunkGroupAllTrunksBusyPercentage TABLE
     -- ****************************************
     AcPMSIPTrunkGroupAllTrunksBusyPercentageEntry ::= SEQUENCE {
       acPMSIPTrunkGroupAllTrunksBusyPercentageTrunkGroupNum 
                                                       Unsigned32,
       acPMSIPTrunkGroupAllTrunksBusyPercentageInterval 
                                                       Unsigned32,
       acPMSIPTrunkGroupAllTrunksBusyPercentageVal     Gauge32
     }



     acPMSIPTrunkGroupAllTrunksBusyPercentageTrunkGroupNum OBJECT-TYPE
       SYNTAX Unsigned32 (0..83)
       MAX-ACCESS not-accessible
       STATUS obsolete
       DESCRIPTION
           "Trunk Group number.
0 is the first Trunk Group."
       ::= {acPMSIPTrunkGroupAllTrunksBusyPercentageEntry 1}



     acPMSIPTrunkGroupAllTrunksBusyPercentageInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPTrunkGroupAllTrunksBusyPercentageEntry 2}



     acPMSIPTrunkGroupAllTrunksBusyPercentageVal OBJECT-TYPE
       SYNTAX Gauge32
       MAX-ACCESS read-only
       STATUS obsolete
       DESCRIPTION
           "Indicates the percentage of the previous interval (15-minute)
for which all the trunks were busy. Note: value of current
interval (acPMSIPTrunkGroupAllTrunksBusyPercentageInterval
= 0) is always equal to value of the previous interval."
       ::= {acPMSIPTrunkGroupAllTrunksBusyPercentageEntry 3}



     -- ****************************************
     -- acPMSIPActiveSIPTransactionsPerSecond table declaration
     -- ****************************************
     acPMSIPActiveSIPTransactionsPerSecondTable OBJECT-TYPE
       SYNTAX SEQUENCE OF AcPMSIPActiveSIPTransactionsPerSecondEntry
       MAX-ACCESS not-accessible
       STATUS obsolete
       DESCRIPTION
           "Performance Monitoring gwActiveSIPTransactionsPerSecond"
       ::= {acPMSIP 41}



     -- ****************************************
     -- acPMSIPActiveSIPTransactionsPerSecond table entry
     -- ****************************************
     acPMSIPActiveSIPTransactionsPerSecondEntry OBJECT-TYPE
       SYNTAX AcPMSIPActiveSIPTransactionsPerSecondEntry
       MAX-ACCESS not-accessible
       STATUS obsolete
       DESCRIPTION
           ""
       INDEX {acPMSIPActiveSIPTransactionsPerSecondDirection,acPMSIPActiveSIPTransactionsPerSecondInterval}
       ::= {acPMSIPActiveSIPTransactionsPerSecondTable 1}



     -- ****************************************
     -- acPMSIPActiveSIPTransactionsPerSecond TABLE
     -- ****************************************
     AcPMSIPActiveSIPTransactionsPerSecondEntry ::= SEQUENCE {
       acPMSIPActiveSIPTransactionsPerSecondDirection  INTEGER,
       acPMSIPActiveSIPTransactionsPerSecondInterval   Unsigned32,
       acPMSIPActiveSIPTransactionsPerSecondVal        Gauge32
     }



     acPMSIPActiveSIPTransactionsPerSecondDirection OBJECT-TYPE
       SYNTAX INTEGER {
                  tx(0)
,
                  rx(1)

                  }
       MAX-ACCESS not-accessible
       STATUS obsolete
       DESCRIPTION
           "Direction index - tx(0), rx(1)."
       ::= {acPMSIPActiveSIPTransactionsPerSecondEntry 1}



     acPMSIPActiveSIPTransactionsPerSecondInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPActiveSIPTransactionsPerSecondEntry 2}



     acPMSIPActiveSIPTransactionsPerSecondVal OBJECT-TYPE
       SYNTAX Gauge32
       MAX-ACCESS read-only
       STATUS obsolete
       DESCRIPTION
           "Indicates the number of active SIP incoming transactions (0)
and outgoing (1) transaction in the system."
       ::= {acPMSIPActiveSIPTransactionsPerSecondEntry 3}



     -- ****************************************
     -- acPMSIPSBCAttemptedCalls table declaration
     -- ****************************************
     acPMSIPSBCAttemptedCallsTable OBJECT-TYPE
       SYNTAX SEQUENCE OF AcPMSIPSBCAttemptedCallsEntry
       MAX-ACCESS not-accessible
       STATUS obsolete
       DESCRIPTION
           "Performance Monitoring gwSBCAttemptedCalls"
       ::= {acPMSIP 42}



     -- ****************************************
     -- acPMSIPSBCAttemptedCalls table entry
     -- ****************************************
     acPMSIPSBCAttemptedCallsEntry OBJECT-TYPE
       SYNTAX AcPMSIPSBCAttemptedCallsEntry
       MAX-ACCESS not-accessible
       STATUS obsolete
       DESCRIPTION
           ""
       INDEX {acPMSIPSBCAttemptedCallsInterval}
       ::= {acPMSIPSBCAttemptedCallsTable 1}



     -- ****************************************
     -- acPMSIPSBCAttemptedCalls TABLE
     -- ****************************************
     AcPMSIPSBCAttemptedCallsEntry ::= SEQUENCE {
       acPMSIPSBCAttemptedCallsInterval                Unsigned32,
       acPMSIPSBCAttemptedCallsVal                     Counter32,
       acPMSIPSBCAttemptedCallsAverage                 Unsigned32,
       acPMSIPSBCAttemptedCallsMax                     Unsigned32,
       acPMSIPSBCAttemptedCallsMin                     Unsigned32,
       acPMSIPSBCAttemptedCallsTimeBelowLowThreshold   Unsigned32,
       acPMSIPSBCAttemptedCallsTimeBetweenThresholds   Unsigned32,
       acPMSIPSBCAttemptedCallsTimeAboveHighThreshold  Unsigned32,
       acPMSIPSBCAttemptedCallsTotal                   Counter32
     }



     acPMSIPSBCAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSBCAttemptedCallsEntry 1}



     acPMSIPSBCAttemptedCallsVal OBJECT-TYPE
       SYNTAX Counter32
       MAX-ACCESS read-only
       STATUS obsolete
       DESCRIPTION
           "Indicates the number of call attempts."
       ::= {acPMSIPSBCAttemptedCallsEntry 2}



     acPMSIPSBCAttemptedCallsAverage OBJECT-TYPE
       SYNTAX Unsigned32 (0..2147483647)
       MAX-ACCESS read-only
       STATUS obsolete
       DESCRIPTION
           "Average value with in the period time."
       ::= {acPMSIPSBCAttemptedCallsEntry 3}



     acPMSIPSBCAttemptedCallsMax OBJECT-TYPE
       SYNTAX Unsigned32 (0..2147483647)
       MAX-ACCESS read-only
       STATUS obsolete
       DESCRIPTION
           "Maximum value with in the period time."
       ::= {acPMSIPSBCAttemptedCallsEntry 4}



     acPMSIPSBCAttemptedCallsMin OBJECT-TYPE
       SYNTAX Unsigned32 (0..2147483647)
       MAX-ACCESS read-only
       STATUS obsolete
       DESCRIPTION
           "Minimum value with in the period time."
       ::= {acPMSIPSBCAttemptedCallsEntry 5}



     acPMSIPSBCAttemptedCallsTimeBelowLowThreshold OBJECT-TYPE
       SYNTAX Unsigned32 (0..100)
       MAX-ACCESS read-only
       STATUS obsolete
       DESCRIPTION
           "Percent of interval time for which gauge is below what was determined
as the low threshold."
       ::= {acPMSIPSBCAttemptedCallsEntry 6}



     acPMSIPSBCAttemptedCallsTimeBetweenThresholds OBJECT-TYPE
       SYNTAX Unsigned32 (0..100)
       MAX-ACCESS read-only
       STATUS obsolete
       DESCRIPTION
           "Percent of interval time for which gauge is between what were
determined as the low and high thresholds."
       ::= {acPMSIPSBCAttemptedCallsEntry 7}



     acPMSIPSBCAttemptedCallsTimeAboveHighThreshold OBJECT-TYPE
       SYNTAX Unsigned32 (0..100)
       MAX-ACCESS read-only
       STATUS obsolete
       DESCRIPTION
           "Percent of interval time for which gauge is above what was determined
as the high threshold."
       ::= {acPMSIPSBCAttemptedCallsEntry 8}



     acPMSIPSBCAttemptedCallsTotal OBJECT-TYPE
       SYNTAX Counter32
       MAX-ACCESS read-only
       STATUS obsolete
       DESCRIPTION
           "Total."
       ::= {acPMSIPSBCAttemptedCallsEntry 9}



     -- ****************************************
     -- acPMSIPSBCEstablishedCalls table declaration
     -- ****************************************
     acPMSIPSBCEstablishedCallsTable OBJECT-TYPE
       SYNTAX SEQUENCE OF AcPMSIPSBCEstablishedCallsEntry
       MAX-ACCESS not-accessible
       STATUS obsolete
       DESCRIPTION
           "Performance Monitoring gwSBCEstablishedCalls"
       ::= {acPMSIP 43}



     -- ****************************************
     -- acPMSIPSBCEstablishedCalls table entry
     -- ****************************************
     acPMSIPSBCEstablishedCallsEntry OBJECT-TYPE
       SYNTAX AcPMSIPSBCEstablishedCallsEntry
       MAX-ACCESS not-accessible
       STATUS obsolete
       DESCRIPTION
           ""
       INDEX {acPMSIPSBCEstablishedCallsInterval}
       ::= {acPMSIPSBCEstablishedCallsTable 1}



     -- ****************************************
     -- acPMSIPSBCEstablishedCalls TABLE
     -- ****************************************
     AcPMSIPSBCEstablishedCallsEntry ::= SEQUENCE {
       acPMSIPSBCEstablishedCallsInterval              Unsigned32,
       acPMSIPSBCEstablishedCallsVal                   Gauge32,
       acPMSIPSBCEstablishedCallsAverage               Unsigned32,
       acPMSIPSBCEstablishedCallsMax                   Unsigned32,
       acPMSIPSBCEstablishedCallsMin                   Unsigned32,
       acPMSIPSBCEstablishedCallsTimeBelowLowThreshold Unsigned32,
       acPMSIPSBCEstablishedCallsTimeBetweenThresholds Unsigned32,
       acPMSIPSBCEstablishedCallsTimeAboveHighThreshold 
                                                       Unsigned32,
       acPMSIPSBCEstablishedCallsTotal                 Counter32
     }



     acPMSIPSBCEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPSBCEstablishedCallsEntry 1}



     acPMSIPSBCEstablishedCallsVal OBJECT-TYPE
       SYNTAX Gauge32
       MAX-ACCESS read-only
       STATUS obsolete
       DESCRIPTION
           "Indicates the number of call attempts."
       ::= {acPMSIPSBCEstablishedCallsEntry 2}



     acPMSIPSBCEstablishedCallsAverage OBJECT-TYPE
       SYNTAX Unsigned32 (0..2147483647)
       MAX-ACCESS read-only
       STATUS obsolete
       DESCRIPTION
           "Average value with in the period time."
       ::= {acPMSIPSBCEstablishedCallsEntry 3}



     acPMSIPSBCEstablishedCallsMax OBJECT-TYPE
       SYNTAX Unsigned32 (0..2147483647)
       MAX-ACCESS read-only
       STATUS obsolete
       DESCRIPTION
           "Maximum value with in the period time."
       ::= {acPMSIPSBCEstablishedCallsEntry 4}



     acPMSIPSBCEstablishedCallsMin OBJECT-TYPE
       SYNTAX Unsigned32 (0..2147483647)
       MAX-ACCESS read-only
       STATUS obsolete
       DESCRIPTION
           "Minimum value with in the period time."
       ::= {acPMSIPSBCEstablishedCallsEntry 5}



     acPMSIPSBCEstablishedCallsTimeBelowLowThreshold OBJECT-TYPE
       SYNTAX Unsigned32 (0..100)
       MAX-ACCESS read-only
       STATUS obsolete
       DESCRIPTION
           "Percent of interval time for which gauge is below what was determined
as the low threshold."
       ::= {acPMSIPSBCEstablishedCallsEntry 6}



     acPMSIPSBCEstablishedCallsTimeBetweenThresholds OBJECT-TYPE
       SYNTAX Unsigned32 (0..100)
       MAX-ACCESS read-only
       STATUS obsolete
       DESCRIPTION
           "Percent of interval time for which gauge is between what were
determined as the low and high thresholds."
       ::= {acPMSIPSBCEstablishedCallsEntry 7}



     acPMSIPSBCEstablishedCallsTimeAboveHighThreshold OBJECT-TYPE
       SYNTAX Unsigned32 (0..100)
       MAX-ACCESS read-only
       STATUS obsolete
       DESCRIPTION
           "Percent of interval time for which gauge is above what was determined
as the high threshold."
       ::= {acPMSIPSBCEstablishedCallsEntry 8}



     acPMSIPSBCEstablishedCallsTotal OBJECT-TYPE
       SYNTAX Counter32
       MAX-ACCESS read-only
       STATUS obsolete
       DESCRIPTION
           "Total."
       ::= {acPMSIPSBCEstablishedCallsEntry 9}



     acPMMediaRealm  OBJECT IDENTIFIER ::= {acPMControlData 53}


     -- ****************************************
     -- acPMMediaRealmBytesTx table declaration
     -- ****************************************
     acPMMediaRealmBytesTxTable OBJECT-TYPE
       SYNTAX SEQUENCE OF AcPMMediaRealmBytesTxEntry
       MAX-ACCESS not-accessible
       STATUS obsolete
       DESCRIPTION
           "Performance Monitoring MediaRealmBytesTx"
       ::= {acPMMediaRealm  1}



     -- ****************************************
     -- acPMMediaRealmBytesTx table entry
     -- ****************************************
     acPMMediaRealmBytesTxEntry OBJECT-TYPE
       SYNTAX AcPMMediaRealmBytesTxEntry
       MAX-ACCESS not-accessible
       STATUS obsolete
       DESCRIPTION
           ""
       INDEX {acPMMediaRealmBytesTxMediaRealmNum,acPMMediaRealmBytesTxInterval}
       ::= {acPMMediaRealmBytesTxTable 1}



     -- ****************************************
     -- acPMMediaRealmBytesTx TABLE
     -- ****************************************
     AcPMMediaRealmBytesTxEntry ::= SEQUENCE {
       acPMMediaRealmBytesTxMediaRealmNum              Unsigned32,
       acPMMediaRealmBytesTxInterval                   Unsigned32,
       acPMMediaRealmBytesTxVal                        Counter32,
       acPMMediaRealmBytesTxVolume                     Counter32
     }



     acPMMediaRealmBytesTxMediaRealmNum OBJECT-TYPE
       SYNTAX Unsigned32 (0..63)
       MAX-ACCESS not-accessible
       STATUS obsolete
       DESCRIPTION
           "Media Realm number.
0 is the first Media Realm."
       ::= {acPMMediaRealmBytesTxEntry 1}



     acPMMediaRealmBytesTxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmBytesTxEntry 2}



     acPMMediaRealmBytesTxVal OBJECT-TYPE
       SYNTAX Counter32
       MAX-ACCESS read-only
       STATUS obsolete
       DESCRIPTION
           "Value of gauge or counter."
       ::= {acPMMediaRealmBytesTxEntry 3}



     acPMMediaRealmBytesTxVolume OBJECT-TYPE
       SYNTAX Counter32
       MAX-ACCESS read-only
       STATUS obsolete
       DESCRIPTION
           "Activity volume."
       ::= {acPMMediaRealmBytesTxEntry 4}



     -- ****************************************
     -- acPMMediaRealmBytesRx table declaration
     -- ****************************************
     acPMMediaRealmBytesRxTable OBJECT-TYPE
       SYNTAX SEQUENCE OF AcPMMediaRealmBytesRxEntry
       MAX-ACCESS not-accessible
       STATUS obsolete
       DESCRIPTION
           "Performance Monitoring MediaRealmBytesRx"
       ::= {acPMMediaRealm  2}



     -- ****************************************
     -- acPMMediaRealmBytesRx table entry
     -- ****************************************
     acPMMediaRealmBytesRxEntry OBJECT-TYPE
       SYNTAX AcPMMediaRealmBytesRxEntry
       MAX-ACCESS not-accessible
       STATUS obsolete
       DESCRIPTION
           ""
       INDEX {acPMMediaRealmBytesRxMediaRealmNum,acPMMediaRealmBytesRxInterval}
       ::= {acPMMediaRealmBytesRxTable 1}



     -- ****************************************
     -- acPMMediaRealmBytesRx TABLE
     -- ****************************************
     AcPMMediaRealmBytesRxEntry ::= SEQUENCE {
       acPMMediaRealmBytesRxMediaRealmNum              Unsigned32,
       acPMMediaRealmBytesRxInterval                   Unsigned32,
       acPMMediaRealmBytesRxVal                        Counter32,
       acPMMediaRealmBytesRxVolume                     Counter32
     }



     acPMMediaRealmBytesRxMediaRealmNum OBJECT-TYPE
       SYNTAX Unsigned32 (0..63)
       MAX-ACCESS not-accessible
       STATUS obsolete
       DESCRIPTION
           "Media Realm number.
0 is the first Media Realm."
       ::= {acPMMediaRealmBytesRxEntry 1}



     acPMMediaRealmBytesRxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmBytesRxEntry 2}



     acPMMediaRealmBytesRxVal OBJECT-TYPE
       SYNTAX Counter32
       MAX-ACCESS read-only
       STATUS obsolete
       DESCRIPTION
           "Value of gauge or counter."
       ::= {acPMMediaRealmBytesRxEntry 3}



     acPMMediaRealmBytesRxVolume OBJECT-TYPE
       SYNTAX Counter32
       MAX-ACCESS read-only
       STATUS obsolete
       DESCRIPTION
           "Activity volume."
       ::= {acPMMediaRealmBytesRxEntry 4}



     -- ****************************************
     -- acPMMediaRealmPacketsTx table declaration
     -- ****************************************
     acPMMediaRealmPacketsTxTable OBJECT-TYPE
       SYNTAX SEQUENCE OF AcPMMediaRealmPacketsTxEntry
       MAX-ACCESS not-accessible
       STATUS obsolete
       DESCRIPTION
           "Performance Monitoring MediaRealmPacketsTx"
       ::= {acPMMediaRealm  3}



     -- ****************************************
     -- acPMMediaRealmPacketsTx table entry
     -- ****************************************
     acPMMediaRealmPacketsTxEntry OBJECT-TYPE
       SYNTAX AcPMMediaRealmPacketsTxEntry
       MAX-ACCESS not-accessible
       STATUS obsolete
       DESCRIPTION
           ""
       INDEX {acPMMediaRealmPacketsTxMediaRealmNum,acPMMediaRealmPacketsTxInterval}
       ::= {acPMMediaRealmPacketsTxTable 1}



     -- ****************************************
     -- acPMMediaRealmPacketsTx TABLE
     -- ****************************************
     AcPMMediaRealmPacketsTxEntry ::= SEQUENCE {
       acPMMediaRealmPacketsTxMediaRealmNum            Unsigned32,
       acPMMediaRealmPacketsTxInterval                 Unsigned32,
       acPMMediaRealmPacketsTxVal                      Counter32,
       acPMMediaRealmPacketsTxVolume                   Counter32
     }



     acPMMediaRealmPacketsTxMediaRealmNum OBJECT-TYPE
       SYNTAX Unsigned32 (0..63)
       MAX-ACCESS not-accessible
       STATUS obsolete
       DESCRIPTION
           "Media Realm number.
0 is the first Media Realm."
       ::= {acPMMediaRealmPacketsTxEntry 1}



     acPMMediaRealmPacketsTxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmPacketsTxEntry 2}



     acPMMediaRealmPacketsTxVal OBJECT-TYPE
       SYNTAX Counter32
       MAX-ACCESS read-only
       STATUS obsolete
       DESCRIPTION
           "Value of gauge or counter."
       ::= {acPMMediaRealmPacketsTxEntry 3}



     acPMMediaRealmPacketsTxVolume OBJECT-TYPE
       SYNTAX Counter32
       MAX-ACCESS read-only
       STATUS obsolete
       DESCRIPTION
           "Activity volume."
       ::= {acPMMediaRealmPacketsTxEntry 4}



     -- ****************************************
     -- acPMMediaRealmPacketsRx table declaration
     -- ****************************************
     acPMMediaRealmPacketsRxTable OBJECT-TYPE
       SYNTAX SEQUENCE OF AcPMMediaRealmPacketsRxEntry
       MAX-ACCESS not-accessible
       STATUS obsolete
       DESCRIPTION
           "Performance Monitoring MediaRealmPacketsRx"
       ::= {acPMMediaRealm  4}



     -- ****************************************
     -- acPMMediaRealmPacketsRx table entry
     -- ****************************************
     acPMMediaRealmPacketsRxEntry OBJECT-TYPE
       SYNTAX AcPMMediaRealmPacketsRxEntry
       MAX-ACCESS not-accessible
       STATUS obsolete
       DESCRIPTION
           ""
       INDEX {acPMMediaRealmPacketsRxMediaRealmNum,acPMMediaRealmPacketsRxInterval}
       ::= {acPMMediaRealmPacketsRxTable 1}



     -- ****************************************
     -- acPMMediaRealmPacketsRx TABLE
     -- ****************************************
     AcPMMediaRealmPacketsRxEntry ::= SEQUENCE {
       acPMMediaRealmPacketsRxMediaRealmNum            Unsigned32,
       acPMMediaRealmPacketsRxInterval                 Unsigned32,
       acPMMediaRealmPacketsRxVal                      Counter32,
       acPMMediaRealmPacketsRxVolume                   Counter32
     }



     acPMMediaRealmPacketsRxMediaRealmNum OBJECT-TYPE
       SYNTAX Unsigned32 (0..63)
       MAX-ACCESS not-accessible
       STATUS obsolete
       DESCRIPTION
           "Media Realm number.
0 is the first Media Realm."
       ::= {acPMMediaRealmPacketsRxEntry 1}



     acPMMediaRealmPacketsRxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmPacketsRxEntry 2}



     acPMMediaRealmPacketsRxVal OBJECT-TYPE
       SYNTAX Counter32
       MAX-ACCESS read-only
       STATUS obsolete
       DESCRIPTION
           "Value of gauge or counter."
       ::= {acPMMediaRealmPacketsRxEntry 3}



     acPMMediaRealmPacketsRxVolume OBJECT-TYPE
       SYNTAX Counter32
       MAX-ACCESS read-only
       STATUS obsolete
       DESCRIPTION
           "Activity volume."
       ::= {acPMMediaRealmPacketsRxEntry 4}



     -- ****************************************
     -- acPMMediaRealmVERealmPacketDelay table declaration
     -- ****************************************
     acPMMediaRealmVERealmPacketDelayTable OBJECT-TYPE
       SYNTAX SEQUENCE OF AcPMMediaRealmVERealmPacketDelayEntry
       MAX-ACCESS not-accessible
       STATUS obsolete
       DESCRIPTION
           "Performance Monitoring VERealmPacketDelay"
       ::= {acPMMediaRealm  5}



     -- ****************************************
     -- acPMMediaRealmVERealmPacketDelay table entry
     -- ****************************************
     acPMMediaRealmVERealmPacketDelayEntry OBJECT-TYPE
       SYNTAX AcPMMediaRealmVERealmPacketDelayEntry
       MAX-ACCESS not-accessible
       STATUS obsolete
       DESCRIPTION
           ""
       INDEX {acPMMediaRealmVERealmPacketDelayMediaRealmNum,acPMMediaRealmVERealmPacketDelayInterval}
       ::= {acPMMediaRealmVERealmPacketDelayTable 1}



     -- ****************************************
     -- acPMMediaRealmVERealmPacketDelay TABLE
     -- ****************************************
     AcPMMediaRealmVERealmPacketDelayEntry ::= SEQUENCE {
       acPMMediaRealmVERealmPacketDelayMediaRealmNum   Unsigned32,
       acPMMediaRealmVERealmPacketDelayInterval        Unsigned32,
       acPMMediaRealmVERealmPacketDelayVal             Counter32,
       acPMMediaRealmVERealmPacketDelayAverage         Integer32,
       acPMMediaRealmVERealmPacketDelayMax             Integer32,
       acPMMediaRealmVERealmPacketDelayMin             Integer32
     }



     acPMMediaRealmVERealmPacketDelayMediaRealmNum OBJECT-TYPE
       SYNTAX Unsigned32 (0..63)
       MAX-ACCESS not-accessible
       STATUS obsolete
       DESCRIPTION
           "Media Realm number.
0 is the first Media Realm."
       ::= {acPMMediaRealmVERealmPacketDelayEntry 1}



     acPMMediaRealmVERealmPacketDelayInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmVERealmPacketDelayEntry 2}



     acPMMediaRealmVERealmPacketDelayVal OBJECT-TYPE
       SYNTAX Counter32
       MAX-ACCESS read-only
       STATUS obsolete
       DESCRIPTION
           "Value of gauge or counter."
       ::= {acPMMediaRealmVERealmPacketDelayEntry 3}



     acPMMediaRealmVERealmPacketDelayAverage OBJECT-TYPE
       SYNTAX Integer32 (-1..2150000000)
       MAX-ACCESS read-only
       STATUS obsolete
       DESCRIPTION
           "Average value with in the period time."
       ::= {acPMMediaRealmVERealmPacketDelayEntry 4}



     acPMMediaRealmVERealmPacketDelayMax OBJECT-TYPE
       SYNTAX Integer32 (-1..2150000000)
       MAX-ACCESS read-only
       STATUS obsolete
       DESCRIPTION
           "Maximum value with in the period time."
       ::= {acPMMediaRealmVERealmPacketDelayEntry 5}



     acPMMediaRealmVERealmPacketDelayMin OBJECT-TYPE
       SYNTAX Integer32 (-1..2150000000)
       MAX-ACCESS read-only
       STATUS obsolete
       DESCRIPTION
           "Minimum value with in the period time."
       ::= {acPMMediaRealmVERealmPacketDelayEntry 6}



     -- ****************************************
     -- acPMMediaRealmVERealmPacketJitter table declaration
     -- ****************************************
     acPMMediaRealmVERealmPacketJitterTable OBJECT-TYPE
       SYNTAX SEQUENCE OF AcPMMediaRealmVERealmPacketJitterEntry
       MAX-ACCESS not-accessible
       STATUS obsolete
       DESCRIPTION
           "Performance Monitoring VERealmPacketJitter"
       ::= {acPMMediaRealm  6}



     -- ****************************************
     -- acPMMediaRealmVERealmPacketJitter table entry
     -- ****************************************
     acPMMediaRealmVERealmPacketJitterEntry OBJECT-TYPE
       SYNTAX AcPMMediaRealmVERealmPacketJitterEntry
       MAX-ACCESS not-accessible
       STATUS obsolete
       DESCRIPTION
           ""
       INDEX {acPMMediaRealmVERealmPacketJitterMediaRealmNum,acPMMediaRealmVERealmPacketJitterInterval}
       ::= {acPMMediaRealmVERealmPacketJitterTable 1}



     -- ****************************************
     -- acPMMediaRealmVERealmPacketJitter TABLE
     -- ****************************************
     AcPMMediaRealmVERealmPacketJitterEntry ::= SEQUENCE {
       acPMMediaRealmVERealmPacketJitterMediaRealmNum  Unsigned32,
       acPMMediaRealmVERealmPacketJitterInterval       Unsigned32,
       acPMMediaRealmVERealmPacketJitterVal            Counter32,
       acPMMediaRealmVERealmPacketJitterAverage        Integer32,
       acPMMediaRealmVERealmPacketJitterMax            Integer32,
       acPMMediaRealmVERealmPacketJitterMin            Integer32
     }



     acPMMediaRealmVERealmPacketJitterMediaRealmNum OBJECT-TYPE
       SYNTAX Unsigned32 (0..63)
       MAX-ACCESS not-accessible
       STATUS obsolete
       DESCRIPTION
           "Media Realm number.
0 is the first Media Realm."
       ::= {acPMMediaRealmVERealmPacketJitterEntry 1}



     acPMMediaRealmVERealmPacketJitterInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmVERealmPacketJitterEntry 2}



     acPMMediaRealmVERealmPacketJitterVal OBJECT-TYPE
       SYNTAX Counter32
       MAX-ACCESS read-only
       STATUS obsolete
       DESCRIPTION
           "Value of gauge or counter."
       ::= {acPMMediaRealmVERealmPacketJitterEntry 3}



     acPMMediaRealmVERealmPacketJitterAverage OBJECT-TYPE
       SYNTAX Integer32 (-1..2150000000)
       MAX-ACCESS read-only
       STATUS obsolete
       DESCRIPTION
           "Average value with in the period time."
       ::= {acPMMediaRealmVERealmPacketJitterEntry 4}



     acPMMediaRealmVERealmPacketJitterMax OBJECT-TYPE
       SYNTAX Integer32 (-1..2150000000)
       MAX-ACCESS read-only
       STATUS obsolete
       DESCRIPTION
           "Maximum value with in the period time."
       ::= {acPMMediaRealmVERealmPacketJitterEntry 5}



     acPMMediaRealmVERealmPacketJitterMin OBJECT-TYPE
       SYNTAX Integer32 (-1..2150000000)
       MAX-ACCESS read-only
       STATUS obsolete
       DESCRIPTION
           "Minimum value with in the period time."
       ::= {acPMMediaRealmVERealmPacketJitterEntry 6}



     -- ****************************************
     -- acPMMediaRealmRealmMOS table declaration
     -- ****************************************
     acPMMediaRealmRealmMOSTable OBJECT-TYPE
       SYNTAX SEQUENCE OF AcPMMediaRealmRealmMOSEntry
       MAX-ACCESS not-accessible
       STATUS obsolete
       DESCRIPTION
           "Performance Monitoring RealmMOS"
       ::= {acPMMediaRealm  7}



     -- ****************************************
     -- acPMMediaRealmRealmMOS table entry
     -- ****************************************
     acPMMediaRealmRealmMOSEntry OBJECT-TYPE
       SYNTAX AcPMMediaRealmRealmMOSEntry
       MAX-ACCESS not-accessible
       STATUS obsolete
       DESCRIPTION
           ""
       INDEX {acPMMediaRealmRealmMOSMediaRealmNum,acPMMediaRealmRealmMOSInterval}
       ::= {acPMMediaRealmRealmMOSTable 1}



     -- ****************************************
     -- acPMMediaRealmRealmMOS TABLE
     -- ****************************************
     AcPMMediaRealmRealmMOSEntry ::= SEQUENCE {
       acPMMediaRealmRealmMOSMediaRealmNum             Unsigned32,
       acPMMediaRealmRealmMOSInterval                  Unsigned32,
       acPMMediaRealmRealmMOSVal                       Counter32,
       acPMMediaRealmRealmMOSAverage                   Integer32,
       acPMMediaRealmRealmMOSMax                       Integer32,
       acPMMediaRealmRealmMOSMin                       Integer32
     }



     acPMMediaRealmRealmMOSMediaRealmNum OBJECT-TYPE
       SYNTAX Unsigned32 (0..63)
       MAX-ACCESS not-accessible
       STATUS obsolete
       DESCRIPTION
           "Media Realm number.
0 is the first Media Realm."
       ::= {acPMMediaRealmRealmMOSEntry 1}



     acPMMediaRealmRealmMOSInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmRealmMOSEntry 2}



     acPMMediaRealmRealmMOSVal OBJECT-TYPE
       SYNTAX Counter32
       MAX-ACCESS read-only
       STATUS obsolete
       DESCRIPTION
           "Value of gauge or counter."
       ::= {acPMMediaRealmRealmMOSEntry 3}



     acPMMediaRealmRealmMOSAverage OBJECT-TYPE
       SYNTAX Integer32 (-1..2150000000)
       MAX-ACCESS read-only
       STATUS obsolete
       DESCRIPTION
           "Average value with in the period time."
       ::= {acPMMediaRealmRealmMOSEntry 4}



     acPMMediaRealmRealmMOSMax OBJECT-TYPE
       SYNTAX Integer32 (-1..2150000000)
       MAX-ACCESS read-only
       STATUS obsolete
       DESCRIPTION
           "Maximum value with in the period time."
       ::= {acPMMediaRealmRealmMOSEntry 5}



     acPMMediaRealmRealmMOSMin OBJECT-TYPE
       SYNTAX Integer32 (-1..2150000000)
       MAX-ACCESS read-only
       STATUS obsolete
       DESCRIPTION
           "Minimum value with in the period time."
       ::= {acPMMediaRealmRealmMOSEntry 6}



     -- ****************************************
     -- acPMMediaRealmBwRx table declaration
     -- ****************************************
     acPMMediaRealmBwRxTable OBJECT-TYPE
       SYNTAX SEQUENCE OF AcPMMediaRealmBwRxEntry
       MAX-ACCESS not-accessible
       STATUS obsolete
       DESCRIPTION
           "Performance Monitoring MediaRealmBwRx"
       ::= {acPMMediaRealm  8}



     -- ****************************************
     -- acPMMediaRealmBwRx table entry
     -- ****************************************
     acPMMediaRealmBwRxEntry OBJECT-TYPE
       SYNTAX AcPMMediaRealmBwRxEntry
       MAX-ACCESS not-accessible
       STATUS obsolete
       DESCRIPTION
           ""
       INDEX {acPMMediaRealmBwRxMediaRealmNum,acPMMediaRealmBwRxInterval}
       ::= {acPMMediaRealmBwRxTable 1}



     -- ****************************************
     -- acPMMediaRealmBwRx TABLE
     -- ****************************************
     AcPMMediaRealmBwRxEntry ::= SEQUENCE {
       acPMMediaRealmBwRxMediaRealmNum                 Unsigned32,
       acPMMediaRealmBwRxInterval                      Unsigned32,
       acPMMediaRealmBwRxVal                           Counter32,
       acPMMediaRealmBwRxAverage                       Integer32,
       acPMMediaRealmBwRxMax                           Integer32,
       acPMMediaRealmBwRxMin                           Integer32,
       acPMMediaRealmBwRxTimeBelowLowThreshold         Integer32,
       acPMMediaRealmBwRxTimeBetweenThresholds         Integer32,
       acPMMediaRealmBwRxTimeAboveHighThreshold        Integer32,
       acPMMediaRealmBwRxFullDayAverage                Integer32,
       acPMMediaRealmBwRxTotal                         Counter32
     }



     acPMMediaRealmBwRxMediaRealmNum OBJECT-TYPE
       SYNTAX Unsigned32 (0..63)
       MAX-ACCESS not-accessible
       STATUS obsolete
       DESCRIPTION
           "Media Realm number.
0 is the first Media Realm."
       ::= {acPMMediaRealmBwRxEntry 1}



     acPMMediaRealmBwRxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmBwRxEntry 2}



     acPMMediaRealmBwRxVal OBJECT-TYPE
       SYNTAX Counter32
       MAX-ACCESS read-only
       STATUS obsolete
       DESCRIPTION
           "Value of gauge or counter."
       ::= {acPMMediaRealmBwRxEntry 3}



     acPMMediaRealmBwRxAverage OBJECT-TYPE
       SYNTAX Integer32 (-1..2150000000)
       MAX-ACCESS read-only
       STATUS obsolete
       DESCRIPTION
           "Average value with in the period time."
       ::= {acPMMediaRealmBwRxEntry 4}



     acPMMediaRealmBwRxMax OBJECT-TYPE
       SYNTAX Integer32 (-1..2150000000)
       MAX-ACCESS read-only
       STATUS obsolete
       DESCRIPTION
           "Maximum value with in the period time."
       ::= {acPMMediaRealmBwRxEntry 5}



     acPMMediaRealmBwRxMin OBJECT-TYPE
       SYNTAX Integer32 (-1..2150000000)
       MAX-ACCESS read-only
       STATUS obsolete
       DESCRIPTION
           "Minimum value with in the period time."
       ::= {acPMMediaRealmBwRxEntry 6}



     acPMMediaRealmBwRxTimeBelowLowThreshold OBJECT-TYPE
       SYNTAX Integer32 (-1..100)
       MAX-ACCESS read-only
       STATUS obsolete
       DESCRIPTION
           "Percent of interval time for which gauge is below what was determined
as the low threshold."
       ::= {acPMMediaRealmBwRxEntry 7}



     acPMMediaRealmBwRxTimeBetweenThresholds OBJECT-TYPE
       SYNTAX Integer32 (-1..100)
       MAX-ACCESS read-only
       STATUS obsolete
       DESCRIPTION
           "Percent of interval time for which gauge is above what was determined
as the high threshold."
       ::= {acPMMediaRealmBwRxEntry 8}



     acPMMediaRealmBwRxTimeAboveHighThreshold OBJECT-TYPE
       SYNTAX Integer32 (-1..100)
       MAX-ACCESS read-only
       STATUS obsolete
       DESCRIPTION
           "Percent of interval time for which gauge is between what were
determined as the low and high thresholds."
       ::= {acPMMediaRealmBwRxEntry 9}



     acPMMediaRealmBwRxFullDayAverage OBJECT-TYPE
       SYNTAX Integer32 (-1..2150000000)
       MAX-ACCESS read-only
       STATUS obsolete
       DESCRIPTION
           "The average of full 24 hours."
       ::= {acPMMediaRealmBwRxEntry 10}



     acPMMediaRealmBwRxTotal OBJECT-TYPE
       SYNTAX Counter32
       MAX-ACCESS read-only
       STATUS obsolete
       DESCRIPTION
           "Activity volume."
       ::= {acPMMediaRealmBwRxEntry 11}



     -- ****************************************
     -- acPMMediaRealmBwTx table declaration
     -- ****************************************
     acPMMediaRealmBwTxTable OBJECT-TYPE
       SYNTAX SEQUENCE OF AcPMMediaRealmBwTxEntry
       MAX-ACCESS not-accessible
       STATUS obsolete
       DESCRIPTION
           "Performance Monitoring MediaRealmBwTx"
       ::= {acPMMediaRealm  9}



     -- ****************************************
     -- acPMMediaRealmBwTx table entry
     -- ****************************************
     acPMMediaRealmBwTxEntry OBJECT-TYPE
       SYNTAX AcPMMediaRealmBwTxEntry
       MAX-ACCESS not-accessible
       STATUS obsolete
       DESCRIPTION
           ""
       INDEX {acPMMediaRealmBwTxMediaRealmNum,acPMMediaRealmBwTxInterval}
       ::= {acPMMediaRealmBwTxTable 1}



     -- ****************************************
     -- acPMMediaRealmBwTx TABLE
     -- ****************************************
     AcPMMediaRealmBwTxEntry ::= SEQUENCE {
       acPMMediaRealmBwTxMediaRealmNum                 Unsigned32,
       acPMMediaRealmBwTxInterval                      Unsigned32,
       acPMMediaRealmBwTxVal                           Counter32,
       acPMMediaRealmBwTxAverage                       Integer32,
       acPMMediaRealmBwTxMax                           Integer32,
       acPMMediaRealmBwTxMin                           Integer32,
       acPMMediaRealmBwTxTimeBelowLowThreshold         Integer32,
       acPMMediaRealmBwTxTimeBetweenThresholds         Integer32,
       acPMMediaRealmBwTxTimeAboveHighThreshold        Integer32,
       acPMMediaRealmBwTxFullDayAverage                Integer32,
       acPMMediaRealmBwTxTotal                         Counter32
     }



     acPMMediaRealmBwTxMediaRealmNum OBJECT-TYPE
       SYNTAX Unsigned32 (0..63)
       MAX-ACCESS not-accessible
       STATUS obsolete
       DESCRIPTION
           "Media Realm number.
0 is the first Media Realm."
       ::= {acPMMediaRealmBwTxEntry 1}



     acPMMediaRealmBwTxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmBwTxEntry 2}



     acPMMediaRealmBwTxVal OBJECT-TYPE
       SYNTAX Counter32
       MAX-ACCESS read-only
       STATUS obsolete
       DESCRIPTION
           "Value of gauge or counter."
       ::= {acPMMediaRealmBwTxEntry 3}



     acPMMediaRealmBwTxAverage OBJECT-TYPE
       SYNTAX Integer32 (-1..2150000000)
       MAX-ACCESS read-only
       STATUS obsolete
       DESCRIPTION
           "Average value with in the period time."
       ::= {acPMMediaRealmBwTxEntry 4}



     acPMMediaRealmBwTxMax OBJECT-TYPE
       SYNTAX Integer32 (-1..2150000000)
       MAX-ACCESS read-only
       STATUS obsolete
       DESCRIPTION
           "Maximum value with in the period time."
       ::= {acPMMediaRealmBwTxEntry 5}



     acPMMediaRealmBwTxMin OBJECT-TYPE
       SYNTAX Integer32 (-1..2150000000)
       MAX-ACCESS read-only
       STATUS obsolete
       DESCRIPTION
           "Minimum value with in the period time."
       ::= {acPMMediaRealmBwTxEntry 6}



     acPMMediaRealmBwTxTimeBelowLowThreshold OBJECT-TYPE
       SYNTAX Integer32 (-1..100)
       MAX-ACCESS read-only
       STATUS obsolete
       DESCRIPTION
           "Percent of interval time for which gauge is below what was determined
as the low threshold."
       ::= {acPMMediaRealmBwTxEntry 7}



     acPMMediaRealmBwTxTimeBetweenThresholds OBJECT-TYPE
       SYNTAX Integer32 (-1..100)
       MAX-ACCESS read-only
       STATUS obsolete
       DESCRIPTION
           "Percent of interval time for which gauge is above what was determined
as the high threshold."
       ::= {acPMMediaRealmBwTxEntry 8}



     acPMMediaRealmBwTxTimeAboveHighThreshold OBJECT-TYPE
       SYNTAX Integer32 (-1..100)
       MAX-ACCESS read-only
       STATUS obsolete
       DESCRIPTION
           "Percent of interval time for which gauge is between what were
determined as the low and high thresholds."
       ::= {acPMMediaRealmBwTxEntry 9}



     acPMMediaRealmBwTxFullDayAverage OBJECT-TYPE
       SYNTAX Integer32 (-1..2150000000)
       MAX-ACCESS read-only
       STATUS obsolete
       DESCRIPTION
           "The average of full 24 hours."
       ::= {acPMMediaRealmBwTxEntry 10}



     acPMMediaRealmBwTxTotal OBJECT-TYPE
       SYNTAX Counter32
       MAX-ACCESS read-only
       STATUS obsolete
       DESCRIPTION
           "Activity volume."
       ::= {acPMMediaRealmBwTxEntry 11}



     -- ****************************************
     -- acPMMediaRealmPacketLossRx table declaration
     -- ****************************************
     acPMMediaRealmPacketLossRxTable OBJECT-TYPE
       SYNTAX SEQUENCE OF AcPMMediaRealmPacketLossRxEntry
       MAX-ACCESS not-accessible
       STATUS obsolete
       DESCRIPTION
           "Performance Monitoring MediaRealmPacketLossRx"
       ::= {acPMMediaRealm  10}



     -- ****************************************
     -- acPMMediaRealmPacketLossRx table entry
     -- ****************************************
     acPMMediaRealmPacketLossRxEntry OBJECT-TYPE
       SYNTAX AcPMMediaRealmPacketLossRxEntry
       MAX-ACCESS not-accessible
       STATUS obsolete
       DESCRIPTION
           ""
       INDEX {acPMMediaRealmPacketLossRxMediaRealmNum,acPMMediaRealmPacketLossRxInterval}
       ::= {acPMMediaRealmPacketLossRxTable 1}



     -- ****************************************
     -- acPMMediaRealmPacketLossRx TABLE
     -- ****************************************
     AcPMMediaRealmPacketLossRxEntry ::= SEQUENCE {
       acPMMediaRealmPacketLossRxMediaRealmNum         Unsigned32,
       acPMMediaRealmPacketLossRxInterval              Unsigned32,
       acPMMediaRealmPacketLossRxVal                   Counter32,
       acPMMediaRealmPacketLossRxVolume                Counter32
     }



     acPMMediaRealmPacketLossRxMediaRealmNum OBJECT-TYPE
       SYNTAX Unsigned32 (0..63)
       MAX-ACCESS not-accessible
       STATUS obsolete
       DESCRIPTION
           "Media Realm number.
0 is the first Media Realm."
       ::= {acPMMediaRealmPacketLossRxEntry 1}



     acPMMediaRealmPacketLossRxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmPacketLossRxEntry 2}



     acPMMediaRealmPacketLossRxVal OBJECT-TYPE
       SYNTAX Counter32
       MAX-ACCESS read-only
       STATUS obsolete
       DESCRIPTION
           "Value of gauge or counter."
       ::= {acPMMediaRealmPacketLossRxEntry 3}



     acPMMediaRealmPacketLossRxVolume OBJECT-TYPE
       SYNTAX Counter32
       MAX-ACCESS read-only
       STATUS obsolete
       DESCRIPTION
           "Activity volume."
       ::= {acPMMediaRealmPacketLossRxEntry 4}



     -- ****************************************
     -- acPMMediaRealmPacketLossTx table declaration
     -- ****************************************
     acPMMediaRealmPacketLossTxTable OBJECT-TYPE
       SYNTAX SEQUENCE OF AcPMMediaRealmPacketLossTxEntry
       MAX-ACCESS not-accessible
       STATUS obsolete
       DESCRIPTION
           "Performance Monitoring MediaRealmPacketLossTx"
       ::= {acPMMediaRealm  11}



     -- ****************************************
     -- acPMMediaRealmPacketLossTx table entry
     -- ****************************************
     acPMMediaRealmPacketLossTxEntry OBJECT-TYPE
       SYNTAX AcPMMediaRealmPacketLossTxEntry
       MAX-ACCESS not-accessible
       STATUS obsolete
       DESCRIPTION
           ""
       INDEX {acPMMediaRealmPacketLossTxMediaRealmNum,acPMMediaRealmPacketLossTxInterval}
       ::= {acPMMediaRealmPacketLossTxTable 1}



     -- ****************************************
     -- acPMMediaRealmPacketLossTx TABLE
     -- ****************************************
     AcPMMediaRealmPacketLossTxEntry ::= SEQUENCE {
       acPMMediaRealmPacketLossTxMediaRealmNum         Unsigned32,
       acPMMediaRealmPacketLossTxInterval              Unsigned32,
       acPMMediaRealmPacketLossTxVal                   Counter32,
       acPMMediaRealmPacketLossTxVolume                Counter32
     }



     acPMMediaRealmPacketLossTxMediaRealmNum OBJECT-TYPE
       SYNTAX Unsigned32 (0..63)
       MAX-ACCESS not-accessible
       STATUS obsolete
       DESCRIPTION
           "Media Realm number.
0 is the first Media Realm."
       ::= {acPMMediaRealmPacketLossTxEntry 1}



     acPMMediaRealmPacketLossTxInterval OBJECT-TYPE
       SYNTAX Unsigned32 (0..2)
       MAX-ACCESS not-accessible
       STATUS obsolete
       DESCRIPTION
           "Interval index.
0 - current period (incomplete monitoring - mid period).
1 - Last full period.
2 - One before last."
       ::= {acPMMediaRealmPacketLossTxEntry 2}



     acPMMediaRealmPacketLossTxVal OBJECT-TYPE
       SYNTAX Counter32
       MAX-ACCESS read-only
       STATUS obsolete
       DESCRIPTION
           "Value of gauge or counter."
       ::= {acPMMediaRealmPacketLossTxEntry 3}



     acPMMediaRealmPacketLossTxVolume OBJECT-TYPE
       SYNTAX Counter32
       MAX-ACCESS read-only
       STATUS obsolete
       DESCRIPTION
           "Activity volume."
       ::= {acPMMediaRealmPacketLossTxEntry 4}



     acPMSbcData OBJECT IDENTIFIER ::= {acPMControlData 54}


     -- ****************************************
     -- acPMSIPGroupInCallEstablishedDuration table declaration
     -- ****************************************
     acPMSIPGroupInCallEstablishedDurationTable OBJECT-TYPE
       SYNTAX SEQUENCE OF AcPMSIPGroupInCallEstablishedDurationEntry
       MAX-ACCESS not-accessible
       STATUS obsolete
       DESCRIPTION
           "Last incoming call duration per IP group."
       ::= {acPMSbcData 1}



     -- ****************************************
     -- acPMSIPGroupInCallEstablishedDuration table entry
     -- ****************************************
     acPMSIPGroupInCallEstablishedDurationEntry OBJECT-TYPE
       SYNTAX AcPMSIPGroupInCallEstablishedDurationEntry
       MAX-ACCESS not-accessible
       STATUS obsolete
       DESCRIPTION
           ""
       INDEX {acPMSIPGroupInCallEstablishedDurationIpGroup,acPMSIPGroupInCallEstablishedDurationInterval}
       ::= {acPMSIPGroupInCallEstablishedDurationTable 1}



     -- ****************************************
     -- acPMSIPGroupInCallEstablishedDuration TABLE
     -- ****************************************
     AcPMSIPGroupInCallEstablishedDurationEntry ::= SEQUENCE {
       acPMSIPGroupInCallEstablishedDurationIpGroup    Unsigned32,
       acPMSIPGroupInCallEstablishedDurationInterval   Unsigned32,
       acPMSIPGroupInCallEstablishedDurationVal        Counter32
     }



     acPMSIPGroupInCallEstablishedDurationIpGroup OBJECT-TYPE
       SYNTAX Unsigned32 (0..5000)
       MAX-ACCESS not-accessible
       STATUS obsolete
       DESCRIPTION
           "IP Group number."
       ::= {acPMSIPGroupInCallEstablishedDurationEntry 1}



     acPMSIPGroupInCallEstablishedDurationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSIPGroupInCallEstablishedDurationEntry 2}



     acPMSIPGroupInCallEstablishedDurationVal OBJECT-TYPE
       SYNTAX Counter32
       MAX-ACCESS read-only
       STATUS obsolete
       DESCRIPTION
           "Value of gauge or counter."
       ::= {acPMSIPGroupInCallEstablishedDurationEntry 3}



     -- ****************************************
     -- acPMSBCIPGroupOutCallEstablishedDuration table declaration
     -- ****************************************
     acPMSBCIPGroupOutCallEstablishedDurationTable OBJECT-TYPE
       SYNTAX SEQUENCE OF AcPMSBCIPGroupOutCallEstablishedDurationEntry
       MAX-ACCESS not-accessible
       STATUS obsolete
       DESCRIPTION
           "Last outgoing call duration per IP group."
       ::= {acPMSbcData 2}



     -- ****************************************
     -- acPMSBCIPGroupOutCallEstablishedDuration table entry
     -- ****************************************
     acPMSBCIPGroupOutCallEstablishedDurationEntry OBJECT-TYPE
       SYNTAX AcPMSBCIPGroupOutCallEstablishedDurationEntry
       MAX-ACCESS not-accessible
       STATUS obsolete
       DESCRIPTION
           ""
       INDEX {acPMSBCIPGroupOutCallEstablishedDurationIpGroup,acPMSBCIPGroupOutCallEstablishedDurationInterval}
       ::= {acPMSBCIPGroupOutCallEstablishedDurationTable 1}



     -- ****************************************
     -- acPMSBCIPGroupOutCallEstablishedDuration TABLE
     -- ****************************************
     AcPMSBCIPGroupOutCallEstablishedDurationEntry ::= SEQUENCE {
       acPMSBCIPGroupOutCallEstablishedDurationIpGroup Unsigned32,
       acPMSBCIPGroupOutCallEstablishedDurationInterval 
                                                       Unsigned32,
       acPMSBCIPGroupOutCallEstablishedDurationVal     Counter32
     }



     acPMSBCIPGroupOutCallEstablishedDurationIpGroup OBJECT-TYPE
       SYNTAX Unsigned32 (0..5000)
       MAX-ACCESS not-accessible
       STATUS obsolete
       DESCRIPTION
           "IP Group number."
       ::= {acPMSBCIPGroupOutCallEstablishedDurationEntry 1}



     acPMSBCIPGroupOutCallEstablishedDurationInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutCallEstablishedDurationEntry 2}



     acPMSBCIPGroupOutCallEstablishedDurationVal OBJECT-TYPE
       SYNTAX Counter32
       MAX-ACCESS read-only
       STATUS obsolete
       DESCRIPTION
           "Value of gauge or counter."
       ::= {acPMSBCIPGroupOutCallEstablishedDurationEntry 3}



     -- ****************************************
     -- acPMSBCIPGroupInAttemptedCalls table declaration
     -- ****************************************
     acPMSBCIPGroupInAttemptedCallsTable OBJECT-TYPE
       SYNTAX SEQUENCE OF AcPMSBCIPGroupInAttemptedCallsEntry
       MAX-ACCESS not-accessible
       STATUS obsolete
       DESCRIPTION
           "Number of incoming call attempts per IP group."
       ::= {acPMSbcData 3}



     -- ****************************************
     -- acPMSBCIPGroupInAttemptedCalls table entry
     -- ****************************************
     acPMSBCIPGroupInAttemptedCallsEntry OBJECT-TYPE
       SYNTAX AcPMSBCIPGroupInAttemptedCallsEntry
       MAX-ACCESS not-accessible
       STATUS obsolete
       DESCRIPTION
           ""
       INDEX {acPMSBCIPGroupInAttemptedCallsIpGroup,acPMSBCIPGroupInAttemptedCallsInterval}
       ::= {acPMSBCIPGroupInAttemptedCallsTable 1}



     -- ****************************************
     -- acPMSBCIPGroupInAttemptedCalls TABLE
     -- ****************************************
     AcPMSBCIPGroupInAttemptedCallsEntry ::= SEQUENCE {
       acPMSBCIPGroupInAttemptedCallsIpGroup           Unsigned32,
       acPMSBCIPGroupInAttemptedCallsInterval          Unsigned32,
       acPMSBCIPGroupInAttemptedCallsVal               Counter32,
       acPMSBCIPGroupInAttemptedCallsTotal             Counter32
     }



     acPMSBCIPGroupInAttemptedCallsIpGroup OBJECT-TYPE
       SYNTAX Unsigned32 (0..5000)
       MAX-ACCESS not-accessible
       STATUS obsolete
       DESCRIPTION
           "."
       ::= {acPMSBCIPGroupInAttemptedCallsEntry 1}



     acPMSBCIPGroupInAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAttemptedCallsEntry 2}



     acPMSBCIPGroupInAttemptedCallsVal OBJECT-TYPE
       SYNTAX Counter32
       MAX-ACCESS read-only
       STATUS obsolete
       DESCRIPTION
           "Value of gauge or counter."
       ::= {acPMSBCIPGroupInAttemptedCallsEntry 3}



     acPMSBCIPGroupInAttemptedCallsTotal OBJECT-TYPE
       SYNTAX Counter32
       MAX-ACCESS read-only
       STATUS obsolete
       DESCRIPTION
           "Activity volume."
       ::= {acPMSBCIPGroupInAttemptedCallsEntry 4}



     -- ****************************************
     -- acPMSBCIPGroupInAttemptedSubscribeDialogs table declaration
     -- ****************************************
     acPMSBCIPGroupInAttemptedSubscribeDialogsTable OBJECT-TYPE
       SYNTAX SEQUENCE OF AcPMSBCIPGroupInAttemptedSubscribeDialogsEntry
       MAX-ACCESS not-accessible
       STATUS obsolete
       DESCRIPTION
           "Number of incoming SUBSCRIBE dialog attempts per IP group."
       ::= {acPMSbcData 4}



     -- ****************************************
     -- acPMSBCIPGroupInAttemptedSubscribeDialogs table entry
     -- ****************************************
     acPMSBCIPGroupInAttemptedSubscribeDialogsEntry OBJECT-TYPE
       SYNTAX AcPMSBCIPGroupInAttemptedSubscribeDialogsEntry
       MAX-ACCESS not-accessible
       STATUS obsolete
       DESCRIPTION
           ""
       INDEX {acPMSBCIPGroupInAttemptedSubscribeDialogsIpGroup,acPMSBCIPGroupInAttemptedSubscribeDialogsInterval}
       ::= {acPMSBCIPGroupInAttemptedSubscribeDialogsTable 1}



     -- ****************************************
     -- acPMSBCIPGroupInAttemptedSubscribeDialogs TABLE
     -- ****************************************
     AcPMSBCIPGroupInAttemptedSubscribeDialogsEntry ::= SEQUENCE {
       acPMSBCIPGroupInAttemptedSubscribeDialogsIpGroup 
                                                       Unsigned32,
       acPMSBCIPGroupInAttemptedSubscribeDialogsInterval 
                                                       Unsigned32,
       acPMSBCIPGroupInAttemptedSubscribeDialogsVal    Gauge32,
       acPMSBCIPGroupInAttemptedSubscribeDialogsTotal  Counter32
     }



     acPMSBCIPGroupInAttemptedSubscribeDialogsIpGroup OBJECT-TYPE
       SYNTAX Unsigned32 (0..5000)
       MAX-ACCESS not-accessible
       STATUS obsolete
       DESCRIPTION
           "."
       ::= {acPMSBCIPGroupInAttemptedSubscribeDialogsEntry 1}



     acPMSBCIPGroupInAttemptedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAttemptedSubscribeDialogsEntry 2}



     acPMSBCIPGroupInAttemptedSubscribeDialogsVal OBJECT-TYPE
       SYNTAX Gauge32
       MAX-ACCESS read-only
       STATUS obsolete
       DESCRIPTION
           "Value of gauge or counter."
       ::= {acPMSBCIPGroupInAttemptedSubscribeDialogsEntry 3}



     acPMSBCIPGroupInAttemptedSubscribeDialogsTotal OBJECT-TYPE
       SYNTAX Counter32
       MAX-ACCESS read-only
       STATUS obsolete
       DESCRIPTION
           "Activity volume."
       ::= {acPMSBCIPGroupInAttemptedSubscribeDialogsEntry 4}



     -- ****************************************
     -- acPMSBCIPGroupInAttemptedOtherDialogs table declaration
     -- ****************************************
     acPMSBCIPGroupInAttemptedOtherDialogsTable OBJECT-TYPE
       SYNTAX SEQUENCE OF AcPMSBCIPGroupInAttemptedOtherDialogsEntry
       MAX-ACCESS not-accessible
       STATUS obsolete
       DESCRIPTION
           "Number of incoming other dialog attempts per IP group."
       ::= {acPMSbcData 5}



     -- ****************************************
     -- acPMSBCIPGroupInAttemptedOtherDialogs table entry
     -- ****************************************
     acPMSBCIPGroupInAttemptedOtherDialogsEntry OBJECT-TYPE
       SYNTAX AcPMSBCIPGroupInAttemptedOtherDialogsEntry
       MAX-ACCESS not-accessible
       STATUS obsolete
       DESCRIPTION
           ""
       INDEX {acPMSBCIPGroupInAttemptedOtherDialogsIpGroup,acPMSBCIPGroupInAttemptedOtherDialogsInterval}
       ::= {acPMSBCIPGroupInAttemptedOtherDialogsTable 1}



     -- ****************************************
     -- acPMSBCIPGroupInAttemptedOtherDialogs TABLE
     -- ****************************************
     AcPMSBCIPGroupInAttemptedOtherDialogsEntry ::= SEQUENCE {
       acPMSBCIPGroupInAttemptedOtherDialogsIpGroup    Unsigned32,
       acPMSBCIPGroupInAttemptedOtherDialogsInterval   Unsigned32,
       acPMSBCIPGroupInAttemptedOtherDialogsVal        Gauge32,
       acPMSBCIPGroupInAttemptedOtherDialogsTotal      Counter32
     }



     acPMSBCIPGroupInAttemptedOtherDialogsIpGroup OBJECT-TYPE
       SYNTAX Unsigned32 (0..5000)
       MAX-ACCESS not-accessible
       STATUS obsolete
       DESCRIPTION
           "."
       ::= {acPMSBCIPGroupInAttemptedOtherDialogsEntry 1}



     acPMSBCIPGroupInAttemptedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAttemptedOtherDialogsEntry 2}



     acPMSBCIPGroupInAttemptedOtherDialogsVal OBJECT-TYPE
       SYNTAX Gauge32
       MAX-ACCESS read-only
       STATUS obsolete
       DESCRIPTION
           "Value of gauge or counter."
       ::= {acPMSBCIPGroupInAttemptedOtherDialogsEntry 3}



     acPMSBCIPGroupInAttemptedOtherDialogsTotal OBJECT-TYPE
       SYNTAX Counter32
       MAX-ACCESS read-only
       STATUS obsolete
       DESCRIPTION
           "Activity volume."
       ::= {acPMSBCIPGroupInAttemptedOtherDialogsEntry 4}



     -- ****************************************
     -- acPMSBCIPGroupOutAttemptedCalls table declaration
     -- ****************************************
     acPMSBCIPGroupOutAttemptedCallsTable OBJECT-TYPE
       SYNTAX SEQUENCE OF AcPMSBCIPGroupOutAttemptedCallsEntry
       MAX-ACCESS not-accessible
       STATUS obsolete
       DESCRIPTION
           "Number of outgoing call attempts per IP group."
       ::= {acPMSbcData 6}



     -- ****************************************
     -- acPMSBCIPGroupOutAttemptedCalls table entry
     -- ****************************************
     acPMSBCIPGroupOutAttemptedCallsEntry OBJECT-TYPE
       SYNTAX AcPMSBCIPGroupOutAttemptedCallsEntry
       MAX-ACCESS not-accessible
       STATUS obsolete
       DESCRIPTION
           ""
       INDEX {acPMSBCIPGroupOutAttemptedCallsIpGroup,acPMSBCIPGroupOutAttemptedCallsInterval}
       ::= {acPMSBCIPGroupOutAttemptedCallsTable 1}



     -- ****************************************
     -- acPMSBCIPGroupOutAttemptedCalls TABLE
     -- ****************************************
     AcPMSBCIPGroupOutAttemptedCallsEntry ::= SEQUENCE {
       acPMSBCIPGroupOutAttemptedCallsIpGroup          Unsigned32,
       acPMSBCIPGroupOutAttemptedCallsInterval         Unsigned32,
       acPMSBCIPGroupOutAttemptedCallsVal              Counter32,
       acPMSBCIPGroupOutAttemptedCallsTotal            Counter32
     }



     acPMSBCIPGroupOutAttemptedCallsIpGroup OBJECT-TYPE
       SYNTAX Unsigned32 (0..5000)
       MAX-ACCESS not-accessible
       STATUS obsolete
       DESCRIPTION
           "."
       ::= {acPMSBCIPGroupOutAttemptedCallsEntry 1}



     acPMSBCIPGroupOutAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAttemptedCallsEntry 2}



     acPMSBCIPGroupOutAttemptedCallsVal OBJECT-TYPE
       SYNTAX Counter32
       MAX-ACCESS read-only
       STATUS obsolete
       DESCRIPTION
           "Value of gauge or counter."
       ::= {acPMSBCIPGroupOutAttemptedCallsEntry 3}



     acPMSBCIPGroupOutAttemptedCallsTotal OBJECT-TYPE
       SYNTAX Counter32
       MAX-ACCESS read-only
       STATUS obsolete
       DESCRIPTION
           "Activity volume."
       ::= {acPMSBCIPGroupOutAttemptedCallsEntry 4}



     -- ****************************************
     -- acPMSBCIPGroupOutAttemptedSubscribeDialogs table declaration
     -- ****************************************
     acPMSBCIPGroupOutAttemptedSubscribeDialogsTable OBJECT-TYPE
       SYNTAX SEQUENCE OF AcPMSBCIPGroupOutAttemptedSubscribeDialogsEntry
       MAX-ACCESS not-accessible
       STATUS obsolete
       DESCRIPTION
           "Number of outgoing SUBSCRIBE dialog attempts per IP group."
       ::= {acPMSbcData 7}



     -- ****************************************
     -- acPMSBCIPGroupOutAttemptedSubscribeDialogs table entry
     -- ****************************************
     acPMSBCIPGroupOutAttemptedSubscribeDialogsEntry OBJECT-TYPE
       SYNTAX AcPMSBCIPGroupOutAttemptedSubscribeDialogsEntry
       MAX-ACCESS not-accessible
       STATUS obsolete
       DESCRIPTION
           ""
       INDEX {acPMSBCIPGroupOutAttemptedSubscribeDialogsIpGroup,acPMSBCIPGroupOutAttemptedSubscribeDialogsInterval}
       ::= {acPMSBCIPGroupOutAttemptedSubscribeDialogsTable 1}



     -- ****************************************
     -- acPMSBCIPGroupOutAttemptedSubscribeDialogs TABLE
     -- ****************************************
     AcPMSBCIPGroupOutAttemptedSubscribeDialogsEntry ::= SEQUENCE {
       acPMSBCIPGroupOutAttemptedSubscribeDialogsIpGroup 
                                                       Unsigned32,
       acPMSBCIPGroupOutAttemptedSubscribeDialogsInterval 
                                                       Unsigned32,
       acPMSBCIPGroupOutAttemptedSubscribeDialogsVal   Gauge32,
       acPMSBCIPGroupOutAttemptedSubscribeDialogsTotal Counter32
     }



     acPMSBCIPGroupOutAttemptedSubscribeDialogsIpGroup OBJECT-TYPE
       SYNTAX Unsigned32 (0..5000)
       MAX-ACCESS not-accessible
       STATUS obsolete
       DESCRIPTION
           "."
       ::= {acPMSBCIPGroupOutAttemptedSubscribeDialogsEntry 1}



     acPMSBCIPGroupOutAttemptedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAttemptedSubscribeDialogsEntry 2}



     acPMSBCIPGroupOutAttemptedSubscribeDialogsVal OBJECT-TYPE
       SYNTAX Gauge32
       MAX-ACCESS read-only
       STATUS obsolete
       DESCRIPTION
           "Value of gauge or counter."
       ::= {acPMSBCIPGroupOutAttemptedSubscribeDialogsEntry 3}



     acPMSBCIPGroupOutAttemptedSubscribeDialogsTotal OBJECT-TYPE
       SYNTAX Counter32
       MAX-ACCESS read-only
       STATUS obsolete
       DESCRIPTION
           "Activity volume."
       ::= {acPMSBCIPGroupOutAttemptedSubscribeDialogsEntry 4}



     -- ****************************************
     -- acPMSBCIPGroupOutAttemptedOtherDialogs table declaration
     -- ****************************************
     acPMSBCIPGroupOutAttemptedOtherDialogsTable OBJECT-TYPE
       SYNTAX SEQUENCE OF AcPMSBCIPGroupOutAttemptedOtherDialogsEntry
       MAX-ACCESS not-accessible
       STATUS obsolete
       DESCRIPTION
           "Number of outgoing other dialog attempts per IP group."
       ::= {acPMSbcData 8}



     -- ****************************************
     -- acPMSBCIPGroupOutAttemptedOtherDialogs table entry
     -- ****************************************
     acPMSBCIPGroupOutAttemptedOtherDialogsEntry OBJECT-TYPE
       SYNTAX AcPMSBCIPGroupOutAttemptedOtherDialogsEntry
       MAX-ACCESS not-accessible
       STATUS obsolete
       DESCRIPTION
           ""
       INDEX {acPMSBCIPGroupOutAttemptedOtherDialogsIpGroup,acPMSBCIPGroupOutAttemptedOtherDialogsInterval}
       ::= {acPMSBCIPGroupOutAttemptedOtherDialogsTable 1}



     -- ****************************************
     -- acPMSBCIPGroupOutAttemptedOtherDialogs TABLE
     -- ****************************************
     AcPMSBCIPGroupOutAttemptedOtherDialogsEntry ::= SEQUENCE {
       acPMSBCIPGroupOutAttemptedOtherDialogsIpGroup   Unsigned32,
       acPMSBCIPGroupOutAttemptedOtherDialogsInterval  Unsigned32,
       acPMSBCIPGroupOutAttemptedOtherDialogsVal       Gauge32,
       acPMSBCIPGroupOutAttemptedOtherDialogsTotal     Counter32
     }



     acPMSBCIPGroupOutAttemptedOtherDialogsIpGroup OBJECT-TYPE
       SYNTAX Unsigned32 (0..5000)
       MAX-ACCESS not-accessible
       STATUS obsolete
       DESCRIPTION
           "."
       ::= {acPMSBCIPGroupOutAttemptedOtherDialogsEntry 1}



     acPMSBCIPGroupOutAttemptedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAttemptedOtherDialogsEntry 2}



     acPMSBCIPGroupOutAttemptedOtherDialogsVal OBJECT-TYPE
       SYNTAX Gauge32
       MAX-ACCESS read-only
       STATUS obsolete
       DESCRIPTION
           "Value of gauge or counter."
       ::= {acPMSBCIPGroupOutAttemptedOtherDialogsEntry 3}



     acPMSBCIPGroupOutAttemptedOtherDialogsTotal OBJECT-TYPE
       SYNTAX Counter32
       MAX-ACCESS read-only
       STATUS obsolete
       DESCRIPTION
           "Activity volume."
       ::= {acPMSBCIPGroupOutAttemptedOtherDialogsEntry 4}



     -- ****************************************
     -- acPMSBCIPGroupRoutingFailedCalls table declaration
     -- ****************************************
     acPMSBCIPGroupRoutingFailedCallsTable OBJECT-TYPE
       SYNTAX SEQUENCE OF AcPMSBCIPGroupRoutingFailedCallsEntry
       MAX-ACCESS not-accessible
       STATUS obsolete
       DESCRIPTION
           "Number of call routing failures per IP group."
       ::= {acPMSbcData 9}



     -- ****************************************
     -- acPMSBCIPGroupRoutingFailedCalls table entry
     -- ****************************************
     acPMSBCIPGroupRoutingFailedCallsEntry OBJECT-TYPE
       SYNTAX AcPMSBCIPGroupRoutingFailedCallsEntry
       MAX-ACCESS not-accessible
       STATUS obsolete
       DESCRIPTION
           ""
       INDEX {acPMSBCIPGroupRoutingFailedCallsIpGroup,acPMSBCIPGroupRoutingFailedCallsInterval}
       ::= {acPMSBCIPGroupRoutingFailedCallsTable 1}



     -- ****************************************
     -- acPMSBCIPGroupRoutingFailedCalls TABLE
     -- ****************************************
     AcPMSBCIPGroupRoutingFailedCallsEntry ::= SEQUENCE {
       acPMSBCIPGroupRoutingFailedCallsIpGroup         Unsigned32,
       acPMSBCIPGroupRoutingFailedCallsInterval        Unsigned32,
       acPMSBCIPGroupRoutingFailedCallsVal             Gauge32,
       acPMSBCIPGroupRoutingFailedCallsTotal           Counter32
     }



     acPMSBCIPGroupRoutingFailedCallsIpGroup OBJECT-TYPE
       SYNTAX Unsigned32 (0..5000)
       MAX-ACCESS not-accessible
       STATUS obsolete
       DESCRIPTION
           "."
       ::= {acPMSBCIPGroupRoutingFailedCallsEntry 1}



     acPMSBCIPGroupRoutingFailedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupRoutingFailedCallsEntry 2}



     acPMSBCIPGroupRoutingFailedCallsVal OBJECT-TYPE
       SYNTAX Gauge32
       MAX-ACCESS read-only
       STATUS obsolete
       DESCRIPTION
           "Value of gauge or counter."
       ::= {acPMSBCIPGroupRoutingFailedCallsEntry 3}



     acPMSBCIPGroupRoutingFailedCallsTotal OBJECT-TYPE
       SYNTAX Counter32
       MAX-ACCESS read-only
       STATUS obsolete
       DESCRIPTION
           "Activity volume."
       ::= {acPMSBCIPGroupRoutingFailedCallsEntry 4}



     -- ****************************************
     -- acPMSBCIPGroupRoutingFailedSubscribeDialogs table declaration
     -- ****************************************
     acPMSBCIPGroupRoutingFailedSubscribeDialogsTable OBJECT-TYPE
       SYNTAX SEQUENCE OF AcPMSBCIPGroupRoutingFailedSubscribeDialogsEntry
       MAX-ACCESS not-accessible
       STATUS obsolete
       DESCRIPTION
           "Number of SUBSCRIBE dialog routing failures per IP group."
       ::= {acPMSbcData 10}



     -- ****************************************
     -- acPMSBCIPGroupRoutingFailedSubscribeDialogs table entry
     -- ****************************************
     acPMSBCIPGroupRoutingFailedSubscribeDialogsEntry OBJECT-TYPE
       SYNTAX AcPMSBCIPGroupRoutingFailedSubscribeDialogsEntry
       MAX-ACCESS not-accessible
       STATUS obsolete
       DESCRIPTION
           ""
       INDEX {acPMSBCIPGroupRoutingFailedSubscribeDialogsIpGroup,acPMSBCIPGroupRoutingFailedSubscribeDialogsInterval}
       ::= {acPMSBCIPGroupRoutingFailedSubscribeDialogsTable 1}



     -- ****************************************
     -- acPMSBCIPGroupRoutingFailedSubscribeDialogs TABLE
     -- ****************************************
     AcPMSBCIPGroupRoutingFailedSubscribeDialogsEntry ::= SEQUENCE {
       acPMSBCIPGroupRoutingFailedSubscribeDialogsIpGroup 
                                                       Unsigned32,
       acPMSBCIPGroupRoutingFailedSubscribeDialogsInterval 
                                                       Unsigned32,
       acPMSBCIPGroupRoutingFailedSubscribeDialogsVal  Gauge32,
       acPMSBCIPGroupRoutingFailedSubscribeDialogsTotal 
                                                       Counter32
     }



     acPMSBCIPGroupRoutingFailedSubscribeDialogsIpGroup OBJECT-TYPE
       SYNTAX Unsigned32 (0..5000)
       MAX-ACCESS not-accessible
       STATUS obsolete
       DESCRIPTION
           "."
       ::= {acPMSBCIPGroupRoutingFailedSubscribeDialogsEntry 1}



     acPMSBCIPGroupRoutingFailedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupRoutingFailedSubscribeDialogsEntry 2}



     acPMSBCIPGroupRoutingFailedSubscribeDialogsVal OBJECT-TYPE
       SYNTAX Gauge32
       MAX-ACCESS read-only
       STATUS obsolete
       DESCRIPTION
           "Value of gauge or counter."
       ::= {acPMSBCIPGroupRoutingFailedSubscribeDialogsEntry 3}



     acPMSBCIPGroupRoutingFailedSubscribeDialogsTotal OBJECT-TYPE
       SYNTAX Counter32
       MAX-ACCESS read-only
       STATUS obsolete
       DESCRIPTION
           "Activity volume."
       ::= {acPMSBCIPGroupRoutingFailedSubscribeDialogsEntry 4}



     -- ****************************************
     -- acPMSBCIPGroupRoutingFailedOtherDialogs table declaration
     -- ****************************************
     acPMSBCIPGroupRoutingFailedOtherDialogsTable OBJECT-TYPE
       SYNTAX SEQUENCE OF AcPMSBCIPGroupRoutingFailedOtherDialogsEntry
       MAX-ACCESS not-accessible
       STATUS obsolete
       DESCRIPTION
           "Number of other dialog routing failures per IP group."
       ::= {acPMSbcData 11}



     -- ****************************************
     -- acPMSBCIPGroupRoutingFailedOtherDialogs table entry
     -- ****************************************
     acPMSBCIPGroupRoutingFailedOtherDialogsEntry OBJECT-TYPE
       SYNTAX AcPMSBCIPGroupRoutingFailedOtherDialogsEntry
       MAX-ACCESS not-accessible
       STATUS obsolete
       DESCRIPTION
           ""
       INDEX {acPMSBCIPGroupRoutingFailedOtherDialogsIpGroup,acPMSBCIPGroupRoutingFailedOtherDialogsInterval}
       ::= {acPMSBCIPGroupRoutingFailedOtherDialogsTable 1}



     -- ****************************************
     -- acPMSBCIPGroupRoutingFailedOtherDialogs TABLE
     -- ****************************************
     AcPMSBCIPGroupRoutingFailedOtherDialogsEntry ::= SEQUENCE {
       acPMSBCIPGroupRoutingFailedOtherDialogsIpGroup  Unsigned32,
       acPMSBCIPGroupRoutingFailedOtherDialogsInterval Unsigned32,
       acPMSBCIPGroupRoutingFailedOtherDialogsVal      Gauge32,
       acPMSBCIPGroupRoutingFailedOtherDialogsTotal    Counter32
     }



     acPMSBCIPGroupRoutingFailedOtherDialogsIpGroup OBJECT-TYPE
       SYNTAX Unsigned32 (0..5000)
       MAX-ACCESS not-accessible
       STATUS obsolete
       DESCRIPTION
           "."
       ::= {acPMSBCIPGroupRoutingFailedOtherDialogsEntry 1}



     acPMSBCIPGroupRoutingFailedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupRoutingFailedOtherDialogsEntry 2}



     acPMSBCIPGroupRoutingFailedOtherDialogsVal OBJECT-TYPE
       SYNTAX Gauge32
       MAX-ACCESS read-only
       STATUS obsolete
       DESCRIPTION
           "Value of gauge or counter."
       ::= {acPMSBCIPGroupRoutingFailedOtherDialogsEntry 3}



     acPMSBCIPGroupRoutingFailedOtherDialogsTotal OBJECT-TYPE
       SYNTAX Counter32
       MAX-ACCESS read-only
       STATUS obsolete
       DESCRIPTION
           "Activity volume."
       ::= {acPMSBCIPGroupRoutingFailedOtherDialogsEntry 4}



     -- ****************************************
     -- acPMSBCIPGroupInAdmissionFailedCalls table declaration
     -- ****************************************
     acPMSBCIPGroupInAdmissionFailedCallsTable OBJECT-TYPE
       SYNTAX SEQUENCE OF AcPMSBCIPGroupInAdmissionFailedCallsEntry
       MAX-ACCESS not-accessible
       STATUS obsolete
       DESCRIPTION
           "Number of incoming call admission failures per IP group."
       ::= {acPMSbcData 12}



     -- ****************************************
     -- acPMSBCIPGroupInAdmissionFailedCalls table entry
     -- ****************************************
     acPMSBCIPGroupInAdmissionFailedCallsEntry OBJECT-TYPE
       SYNTAX AcPMSBCIPGroupInAdmissionFailedCallsEntry
       MAX-ACCESS not-accessible
       STATUS obsolete
       DESCRIPTION
           ""
       INDEX {acPMSBCIPGroupInAdmissionFailedCallsIpGroup,acPMSBCIPGroupInAdmissionFailedCallsInterval}
       ::= {acPMSBCIPGroupInAdmissionFailedCallsTable 1}



     -- ****************************************
     -- acPMSBCIPGroupInAdmissionFailedCalls TABLE
     -- ****************************************
     AcPMSBCIPGroupInAdmissionFailedCallsEntry ::= SEQUENCE {
       acPMSBCIPGroupInAdmissionFailedCallsIpGroup     Unsigned32,
       acPMSBCIPGroupInAdmissionFailedCallsInterval    Unsigned32,
       acPMSBCIPGroupInAdmissionFailedCallsVal         Gauge32,
       acPMSBCIPGroupInAdmissionFailedCallsTotal       Counter32
     }



     acPMSBCIPGroupInAdmissionFailedCallsIpGroup OBJECT-TYPE
       SYNTAX Unsigned32 (0..5000)
       MAX-ACCESS not-accessible
       STATUS obsolete
       DESCRIPTION
           "."
       ::= {acPMSBCIPGroupInAdmissionFailedCallsEntry 1}



     acPMSBCIPGroupInAdmissionFailedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAdmissionFailedCallsEntry 2}



     acPMSBCIPGroupInAdmissionFailedCallsVal OBJECT-TYPE
       SYNTAX Gauge32
       MAX-ACCESS read-only
       STATUS obsolete
       DESCRIPTION
           "Value of gauge or counter."
       ::= {acPMSBCIPGroupInAdmissionFailedCallsEntry 3}



     acPMSBCIPGroupInAdmissionFailedCallsTotal OBJECT-TYPE
       SYNTAX Counter32
       MAX-ACCESS read-only
       STATUS obsolete
       DESCRIPTION
           "Activity volume."
       ::= {acPMSBCIPGroupInAdmissionFailedCallsEntry 4}



     -- ****************************************
     -- acPMSBCIPGroupInAdmissionFailedSubscribeDialogs table declaration
     -- ****************************************
     acPMSBCIPGroupInAdmissionFailedSubscribeDialogsTable OBJECT-TYPE
       SYNTAX SEQUENCE OF AcPMSBCIPGroupInAdmissionFailedSubscribeDialogsEntry
       MAX-ACCESS not-accessible
       STATUS obsolete
       DESCRIPTION
           "Number of incoming SUBSCRIBE dialog admission failures per IP group."
       ::= {acPMSbcData 13}



     -- ****************************************
     -- acPMSBCIPGroupInAdmissionFailedSubscribeDialogs table entry
     -- ****************************************
     acPMSBCIPGroupInAdmissionFailedSubscribeDialogsEntry OBJECT-TYPE
       SYNTAX AcPMSBCIPGroupInAdmissionFailedSubscribeDialogsEntry
       MAX-ACCESS not-accessible
       STATUS obsolete
       DESCRIPTION
           ""
       INDEX {acPMSBCIPGroupInAdmissionFailedSubscribeDialogsIpGroup,acPMSBCIPGroupInAdmissionFailedSubscribeDialogsInterval}
       ::= {acPMSBCIPGroupInAdmissionFailedSubscribeDialogsTable 1}



     -- ****************************************
     -- acPMSBCIPGroupInAdmissionFailedSubscribeDialogs TABLE
     -- ****************************************
     AcPMSBCIPGroupInAdmissionFailedSubscribeDialogsEntry ::= SEQUENCE {
       acPMSBCIPGroupInAdmissionFailedSubscribeDialogsIpGroup 
                                                       Unsigned32,
       acPMSBCIPGroupInAdmissionFailedSubscribeDialogsInterval 
                                                       Unsigned32,
       acPMSBCIPGroupInAdmissionFailedSubscribeDialogsVal 
                                                       Gauge32,
       acPMSBCIPGroupInAdmissionFailedSubscribeDialogsTotal 
                                                       Counter32
     }



     acPMSBCIPGroupInAdmissionFailedSubscribeDialogsIpGroup OBJECT-TYPE
       SYNTAX Unsigned32 (0..5000)
       MAX-ACCESS not-accessible
       STATUS obsolete
       DESCRIPTION
           "."
       ::= {acPMSBCIPGroupInAdmissionFailedSubscribeDialogsEntry 1}



     acPMSBCIPGroupInAdmissionFailedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAdmissionFailedSubscribeDialogsEntry 2}



     acPMSBCIPGroupInAdmissionFailedSubscribeDialogsVal OBJECT-TYPE
       SYNTAX Gauge32
       MAX-ACCESS read-only
       STATUS obsolete
       DESCRIPTION
           "Value of gauge or counter."
       ::= {acPMSBCIPGroupInAdmissionFailedSubscribeDialogsEntry 3}



     acPMSBCIPGroupInAdmissionFailedSubscribeDialogsTotal OBJECT-TYPE
       SYNTAX Counter32
       MAX-ACCESS read-only
       STATUS obsolete
       DESCRIPTION
           "Activity volume."
       ::= {acPMSBCIPGroupInAdmissionFailedSubscribeDialogsEntry 4}



     -- ****************************************
     -- acPMSBCIPGroupInAdmissionFailedOtherDialogs table declaration
     -- ****************************************
     acPMSBCIPGroupInAdmissionFailedOtherDialogsTable OBJECT-TYPE
       SYNTAX SEQUENCE OF AcPMSBCIPGroupInAdmissionFailedOtherDialogsEntry
       MAX-ACCESS not-accessible
       STATUS obsolete
       DESCRIPTION
           "Number of incoming other dialog admission failures per IP group."
       ::= {acPMSbcData 14}



     -- ****************************************
     -- acPMSBCIPGroupInAdmissionFailedOtherDialogs table entry
     -- ****************************************
     acPMSBCIPGroupInAdmissionFailedOtherDialogsEntry OBJECT-TYPE
       SYNTAX AcPMSBCIPGroupInAdmissionFailedOtherDialogsEntry
       MAX-ACCESS not-accessible
       STATUS obsolete
       DESCRIPTION
           ""
       INDEX {acPMSBCIPGroupInAdmissionFailedOtherDialogsIpGroup,acPMSBCIPGroupInAdmissionFailedOtherDialogsInterval}
       ::= {acPMSBCIPGroupInAdmissionFailedOtherDialogsTable 1}



     -- ****************************************
     -- acPMSBCIPGroupInAdmissionFailedOtherDialogs TABLE
     -- ****************************************
     AcPMSBCIPGroupInAdmissionFailedOtherDialogsEntry ::= SEQUENCE {
       acPMSBCIPGroupInAdmissionFailedOtherDialogsIpGroup 
                                                       Unsigned32,
       acPMSBCIPGroupInAdmissionFailedOtherDialogsInterval 
                                                       Unsigned32,
       acPMSBCIPGroupInAdmissionFailedOtherDialogsVal  Gauge32,
       acPMSBCIPGroupInAdmissionFailedOtherDialogsTotal 
                                                       Counter32
     }



     acPMSBCIPGroupInAdmissionFailedOtherDialogsIpGroup OBJECT-TYPE
       SYNTAX Unsigned32 (0..5000)
       MAX-ACCESS not-accessible
       STATUS obsolete
       DESCRIPTION
           "."
       ::= {acPMSBCIPGroupInAdmissionFailedOtherDialogsEntry 1}



     acPMSBCIPGroupInAdmissionFailedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAdmissionFailedOtherDialogsEntry 2}



     acPMSBCIPGroupInAdmissionFailedOtherDialogsVal OBJECT-TYPE
       SYNTAX Gauge32
       MAX-ACCESS read-only
       STATUS obsolete
       DESCRIPTION
           "Value of gauge or counter."
       ::= {acPMSBCIPGroupInAdmissionFailedOtherDialogsEntry 3}



     acPMSBCIPGroupInAdmissionFailedOtherDialogsTotal OBJECT-TYPE
       SYNTAX Counter32
       MAX-ACCESS read-only
       STATUS obsolete
       DESCRIPTION
           "Activity volume."
       ::= {acPMSBCIPGroupInAdmissionFailedOtherDialogsEntry 4}



     -- ****************************************
     -- acPMSBCIPGroupOutAdmissionFailedCalls table declaration
     -- ****************************************
     acPMSBCIPGroupOutAdmissionFailedCallsTable OBJECT-TYPE
       SYNTAX SEQUENCE OF AcPMSBCIPGroupOutAdmissionFailedCallsEntry
       MAX-ACCESS not-accessible
       STATUS obsolete
       DESCRIPTION
           "Number of outgoing call admission failures per IP group"
       ::= {acPMSbcData 15}



     -- ****************************************
     -- acPMSBCIPGroupOutAdmissionFailedCalls table entry
     -- ****************************************
     acPMSBCIPGroupOutAdmissionFailedCallsEntry OBJECT-TYPE
       SYNTAX AcPMSBCIPGroupOutAdmissionFailedCallsEntry
       MAX-ACCESS not-accessible
       STATUS obsolete
       DESCRIPTION
           ""
       INDEX {acPMSBCIPGroupOutAdmissionFailedCallsIpGroup,acPMSBCIPGroupOutAdmissionFailedCallsInterval}
       ::= {acPMSBCIPGroupOutAdmissionFailedCallsTable 1}



     -- ****************************************
     -- acPMSBCIPGroupOutAdmissionFailedCalls TABLE
     -- ****************************************
     AcPMSBCIPGroupOutAdmissionFailedCallsEntry ::= SEQUENCE {
       acPMSBCIPGroupOutAdmissionFailedCallsIpGroup    Unsigned32,
       acPMSBCIPGroupOutAdmissionFailedCallsInterval   Unsigned32,
       acPMSBCIPGroupOutAdmissionFailedCallsVal        Gauge32,
       acPMSBCIPGroupOutAdmissionFailedCallsTotal      Counter32
     }



     acPMSBCIPGroupOutAdmissionFailedCallsIpGroup OBJECT-TYPE
       SYNTAX Unsigned32 (0..5000)
       MAX-ACCESS not-accessible
       STATUS obsolete
       DESCRIPTION
           "."
       ::= {acPMSBCIPGroupOutAdmissionFailedCallsEntry 1}



     acPMSBCIPGroupOutAdmissionFailedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAdmissionFailedCallsEntry 2}



     acPMSBCIPGroupOutAdmissionFailedCallsVal OBJECT-TYPE
       SYNTAX Gauge32
       MAX-ACCESS read-only
       STATUS obsolete
       DESCRIPTION
           "Value of gauge or counter."
       ::= {acPMSBCIPGroupOutAdmissionFailedCallsEntry 3}



     acPMSBCIPGroupOutAdmissionFailedCallsTotal OBJECT-TYPE
       SYNTAX Counter32
       MAX-ACCESS read-only
       STATUS obsolete
       DESCRIPTION
           "Activity volume."
       ::= {acPMSBCIPGroupOutAdmissionFailedCallsEntry 4}



     -- ****************************************
     -- acPMSBCIPGroupOutAdmissionFailedSubscribeDialogs table declaration
     -- ****************************************
     acPMSBCIPGroupOutAdmissionFailedSubscribeDialogsTable OBJECT-TYPE
       SYNTAX SEQUENCE OF AcPMSBCIPGroupOutAdmissionFailedSubscribeDialogsEntry
       MAX-ACCESS not-accessible
       STATUS obsolete
       DESCRIPTION
           "Number of outgoing SUBSCRIBE dialog admission failures per IP group."
       ::= {acPMSbcData 16}



     -- ****************************************
     -- acPMSBCIPGroupOutAdmissionFailedSubscribeDialogs table entry
     -- ****************************************
     acPMSBCIPGroupOutAdmissionFailedSubscribeDialogsEntry OBJECT-TYPE
       SYNTAX AcPMSBCIPGroupOutAdmissionFailedSubscribeDialogsEntry
       MAX-ACCESS not-accessible
       STATUS obsolete
       DESCRIPTION
           ""
       INDEX {acPMSBCIPGroupOutAdmissionFailedSubscribeDialogsIpGroup,acPMSBCIPGroupOutAdmissionFailedSubscribeDialogsInterval}
       ::= {acPMSBCIPGroupOutAdmissionFailedSubscribeDialogsTable 1}



     -- ****************************************
     -- acPMSBCIPGroupOutAdmissionFailedSubscribeDialogs TABLE
     -- ****************************************
     AcPMSBCIPGroupOutAdmissionFailedSubscribeDialogsEntry ::= SEQUENCE {
       acPMSBCIPGroupOutAdmissionFailedSubscribeDialogsIpGroup 
                                                       Unsigned32,
       acPMSBCIPGroupOutAdmissionFailedSubscribeDialogsInterval 
                                                       Unsigned32,
       acPMSBCIPGroupOutAdmissionFailedSubscribeDialogsVal 
                                                       Gauge32,
       acPMSBCIPGroupOutAdmissionFailedSubscribeDialogsTotal 
                                                       Counter32
     }



     acPMSBCIPGroupOutAdmissionFailedSubscribeDialogsIpGroup OBJECT-TYPE
       SYNTAX Unsigned32 (0..5000)
       MAX-ACCESS not-accessible
       STATUS obsolete
       DESCRIPTION
           "."
       ::= {acPMSBCIPGroupOutAdmissionFailedSubscribeDialogsEntry 1}



     acPMSBCIPGroupOutAdmissionFailedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAdmissionFailedSubscribeDialogsEntry 2}



     acPMSBCIPGroupOutAdmissionFailedSubscribeDialogsVal OBJECT-TYPE
       SYNTAX Gauge32
       MAX-ACCESS read-only
       STATUS obsolete
       DESCRIPTION
           "Value of gauge or counter."
       ::= {acPMSBCIPGroupOutAdmissionFailedSubscribeDialogsEntry 3}



     acPMSBCIPGroupOutAdmissionFailedSubscribeDialogsTotal OBJECT-TYPE
       SYNTAX Counter32
       MAX-ACCESS read-only
       STATUS obsolete
       DESCRIPTION
           "Activity volume."
       ::= {acPMSBCIPGroupOutAdmissionFailedSubscribeDialogsEntry 4}



     -- ****************************************
     -- acPMSBCIPGroupOutAdmissionFailedOtherDialogs table declaration
     -- ****************************************
     acPMSBCIPGroupOutAdmissionFailedOtherDialogsTable OBJECT-TYPE
       SYNTAX SEQUENCE OF AcPMSBCIPGroupOutAdmissionFailedOtherDialogsEntry
       MAX-ACCESS not-accessible
       STATUS obsolete
       DESCRIPTION
           "Number of outgoing other dialog admission failures per IP group."
       ::= {acPMSbcData 17}



     -- ****************************************
     -- acPMSBCIPGroupOutAdmissionFailedOtherDialogs table entry
     -- ****************************************
     acPMSBCIPGroupOutAdmissionFailedOtherDialogsEntry OBJECT-TYPE
       SYNTAX AcPMSBCIPGroupOutAdmissionFailedOtherDialogsEntry
       MAX-ACCESS not-accessible
       STATUS obsolete
       DESCRIPTION
           ""
       INDEX {acPMSBCIPGroupOutAdmissionFailedOtherDialogsIpGroup,acPMSBCIPGroupOutAdmissionFailedOtherDialogsInterval}
       ::= {acPMSBCIPGroupOutAdmissionFailedOtherDialogsTable 1}



     -- ****************************************
     -- acPMSBCIPGroupOutAdmissionFailedOtherDialogs TABLE
     -- ****************************************
     AcPMSBCIPGroupOutAdmissionFailedOtherDialogsEntry ::= SEQUENCE {
       acPMSBCIPGroupOutAdmissionFailedOtherDialogsIpGroup 
                                                       Unsigned32,
       acPMSBCIPGroupOutAdmissionFailedOtherDialogsInterval 
                                                       Unsigned32,
       acPMSBCIPGroupOutAdmissionFailedOtherDialogsVal Gauge32,
       acPMSBCIPGroupOutAdmissionFailedOtherDialogsTotal 
                                                       Counter32
     }



     acPMSBCIPGroupOutAdmissionFailedOtherDialogsIpGroup OBJECT-TYPE
       SYNTAX Unsigned32 (0..5000)
       MAX-ACCESS not-accessible
       STATUS obsolete
       DESCRIPTION
           "."
       ::= {acPMSBCIPGroupOutAdmissionFailedOtherDialogsEntry 1}



     acPMSBCIPGroupOutAdmissionFailedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAdmissionFailedOtherDialogsEntry 2}



     acPMSBCIPGroupOutAdmissionFailedOtherDialogsVal OBJECT-TYPE
       SYNTAX Gauge32
       MAX-ACCESS read-only
       STATUS obsolete
       DESCRIPTION
           "Value of gauge or counter."
       ::= {acPMSBCIPGroupOutAdmissionFailedOtherDialogsEntry 3}



     acPMSBCIPGroupOutAdmissionFailedOtherDialogsTotal OBJECT-TYPE
       SYNTAX Counter32
       MAX-ACCESS read-only
       STATUS obsolete
       DESCRIPTION
           "Activity volume."
       ::= {acPMSBCIPGroupOutAdmissionFailedOtherDialogsEntry 4}



     -- ****************************************
     -- acPMSBCIPGroupInNoResourcesCalls table declaration
     -- ****************************************
     acPMSBCIPGroupInNoResourcesCallsTable OBJECT-TYPE
       SYNTAX SEQUENCE OF AcPMSBCIPGroupInNoResourcesCallsEntry
       MAX-ACCESS not-accessible
       STATUS obsolete
       DESCRIPTION
           "Number of incoming call resource allocation failures per IP group."
       ::= {acPMSbcData 18}



     -- ****************************************
     -- acPMSBCIPGroupInNoResourcesCalls table entry
     -- ****************************************
     acPMSBCIPGroupInNoResourcesCallsEntry OBJECT-TYPE
       SYNTAX AcPMSBCIPGroupInNoResourcesCallsEntry
       MAX-ACCESS not-accessible
       STATUS obsolete
       DESCRIPTION
           ""
       INDEX {acPMSBCIPGroupInNoResourcesCallsIpGroup,acPMSBCIPGroupInNoResourcesCallsInterval}
       ::= {acPMSBCIPGroupInNoResourcesCallsTable 1}



     -- ****************************************
     -- acPMSBCIPGroupInNoResourcesCalls TABLE
     -- ****************************************
     AcPMSBCIPGroupInNoResourcesCallsEntry ::= SEQUENCE {
       acPMSBCIPGroupInNoResourcesCallsIpGroup         Unsigned32,
       acPMSBCIPGroupInNoResourcesCallsInterval        Unsigned32,
       acPMSBCIPGroupInNoResourcesCallsVal             Gauge32,
       acPMSBCIPGroupInNoResourcesCallsTotal           Counter32
     }



     acPMSBCIPGroupInNoResourcesCallsIpGroup OBJECT-TYPE
       SYNTAX Unsigned32 (0..5000)
       MAX-ACCESS not-accessible
       STATUS obsolete
       DESCRIPTION
           "."
       ::= {acPMSBCIPGroupInNoResourcesCallsEntry 1}



     acPMSBCIPGroupInNoResourcesCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInNoResourcesCallsEntry 2}



     acPMSBCIPGroupInNoResourcesCallsVal OBJECT-TYPE
       SYNTAX Gauge32
       MAX-ACCESS read-only
       STATUS obsolete
       DESCRIPTION
           "Value of gauge or counter."
       ::= {acPMSBCIPGroupInNoResourcesCallsEntry 3}



     acPMSBCIPGroupInNoResourcesCallsTotal OBJECT-TYPE
       SYNTAX Counter32
       MAX-ACCESS read-only
       STATUS obsolete
       DESCRIPTION
           "Activity volume."
       ::= {acPMSBCIPGroupInNoResourcesCallsEntry 4}



     -- ****************************************
     -- acPMSBCIPGroupOutNoResourcesCalls table declaration
     -- ****************************************
     acPMSBCIPGroupOutNoResourcesCallsTable OBJECT-TYPE
       SYNTAX SEQUENCE OF AcPMSBCIPGroupOutNoResourcesCallsEntry
       MAX-ACCESS not-accessible
       STATUS obsolete
       DESCRIPTION
           "Number of outgoing call resource allocation failures per IP group."
       ::= {acPMSbcData 19}



     -- ****************************************
     -- acPMSBCIPGroupOutNoResourcesCalls table entry
     -- ****************************************
     acPMSBCIPGroupOutNoResourcesCallsEntry OBJECT-TYPE
       SYNTAX AcPMSBCIPGroupOutNoResourcesCallsEntry
       MAX-ACCESS not-accessible
       STATUS obsolete
       DESCRIPTION
           ""
       INDEX {acPMSBCIPGroupOutNoResourcesCallsIpGroup,acPMSBCIPGroupOutNoResourcesCallsInterval}
       ::= {acPMSBCIPGroupOutNoResourcesCallsTable 1}



     -- ****************************************
     -- acPMSBCIPGroupOutNoResourcesCalls TABLE
     -- ****************************************
     AcPMSBCIPGroupOutNoResourcesCallsEntry ::= SEQUENCE {
       acPMSBCIPGroupOutNoResourcesCallsIpGroup        Unsigned32,
       acPMSBCIPGroupOutNoResourcesCallsInterval       Unsigned32,
       acPMSBCIPGroupOutNoResourcesCallsVal            Gauge32,
       acPMSBCIPGroupOutNoResourcesCallsTotal          Counter32
     }



     acPMSBCIPGroupOutNoResourcesCallsIpGroup OBJECT-TYPE
       SYNTAX Unsigned32 (0..5000)
       MAX-ACCESS not-accessible
       STATUS obsolete
       DESCRIPTION
           "."
       ::= {acPMSBCIPGroupOutNoResourcesCallsEntry 1}



     acPMSBCIPGroupOutNoResourcesCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutNoResourcesCallsEntry 2}



     acPMSBCIPGroupOutNoResourcesCallsVal OBJECT-TYPE
       SYNTAX Gauge32
       MAX-ACCESS read-only
       STATUS obsolete
       DESCRIPTION
           "Value of gauge or counter."
       ::= {acPMSBCIPGroupOutNoResourcesCallsEntry 3}



     acPMSBCIPGroupOutNoResourcesCallsTotal OBJECT-TYPE
       SYNTAX Counter32
       MAX-ACCESS read-only
       STATUS obsolete
       DESCRIPTION
           "Activity volume."
       ::= {acPMSBCIPGroupOutNoResourcesCallsEntry 4}



     -- ****************************************
     -- acPMSBCIPGroupInNoMatchCalls table declaration
     -- ****************************************
     acPMSBCIPGroupInNoMatchCallsTable OBJECT-TYPE
       SYNTAX SEQUENCE OF AcPMSBCIPGroupInNoMatchCallsEntry
       MAX-ACCESS not-accessible
       STATUS obsolete
       DESCRIPTION
           "Number of incoming call media negotiation failures per IP group."
       ::= {acPMSbcData 20}



     -- ****************************************
     -- acPMSBCIPGroupInNoMatchCalls table entry
     -- ****************************************
     acPMSBCIPGroupInNoMatchCallsEntry OBJECT-TYPE
       SYNTAX AcPMSBCIPGroupInNoMatchCallsEntry
       MAX-ACCESS not-accessible
       STATUS obsolete
       DESCRIPTION
           ""
       INDEX {acPMSBCIPGroupInNoMatchCallsIpGroup,acPMSBCIPGroupInNoMatchCallsInterval}
       ::= {acPMSBCIPGroupInNoMatchCallsTable 1}



     -- ****************************************
     -- acPMSBCIPGroupInNoMatchCalls TABLE
     -- ****************************************
     AcPMSBCIPGroupInNoMatchCallsEntry ::= SEQUENCE {
       acPMSBCIPGroupInNoMatchCallsIpGroup             Unsigned32,
       acPMSBCIPGroupInNoMatchCallsInterval            Unsigned32,
       acPMSBCIPGroupInNoMatchCallsVal                 Gauge32,
       acPMSBCIPGroupInNoMatchCallsTotal               Counter32
     }



     acPMSBCIPGroupInNoMatchCallsIpGroup OBJECT-TYPE
       SYNTAX Unsigned32 (0..5000)
       MAX-ACCESS not-accessible
       STATUS obsolete
       DESCRIPTION
           "."
       ::= {acPMSBCIPGroupInNoMatchCallsEntry 1}



     acPMSBCIPGroupInNoMatchCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInNoMatchCallsEntry 2}



     acPMSBCIPGroupInNoMatchCallsVal OBJECT-TYPE
       SYNTAX Gauge32
       MAX-ACCESS read-only
       STATUS obsolete
       DESCRIPTION
           "Value of gauge or counter."
       ::= {acPMSBCIPGroupInNoMatchCallsEntry 3}



     acPMSBCIPGroupInNoMatchCallsTotal OBJECT-TYPE
       SYNTAX Counter32
       MAX-ACCESS read-only
       STATUS obsolete
       DESCRIPTION
           "Activity volume."
       ::= {acPMSBCIPGroupInNoMatchCallsEntry 4}



     -- ****************************************
     -- acPMSBCIPGroupOutNoMatchCalls table declaration
     -- ****************************************
     acPMSBCIPGroupOutNoMatchCallsTable OBJECT-TYPE
       SYNTAX SEQUENCE OF AcPMSBCIPGroupOutNoMatchCallsEntry
       MAX-ACCESS not-accessible
       STATUS obsolete
       DESCRIPTION
           "Number of outgoing call media negotiation failures per IP group."
       ::= {acPMSbcData 21}



     -- ****************************************
     -- acPMSBCIPGroupOutNoMatchCalls table entry
     -- ****************************************
     acPMSBCIPGroupOutNoMatchCallsEntry OBJECT-TYPE
       SYNTAX AcPMSBCIPGroupOutNoMatchCallsEntry
       MAX-ACCESS not-accessible
       STATUS obsolete
       DESCRIPTION
           ""
       INDEX {acPMSBCIPGroupOutNoMatchCallsIpGroup,acPMSBCIPGroupOutNoMatchCallsInterval}
       ::= {acPMSBCIPGroupOutNoMatchCallsTable 1}



     -- ****************************************
     -- acPMSBCIPGroupOutNoMatchCalls TABLE
     -- ****************************************
     AcPMSBCIPGroupOutNoMatchCallsEntry ::= SEQUENCE {
       acPMSBCIPGroupOutNoMatchCallsIpGroup            Unsigned32,
       acPMSBCIPGroupOutNoMatchCallsInterval           Unsigned32,
       acPMSBCIPGroupOutNoMatchCallsVal                Gauge32,
       acPMSBCIPGroupOutNoMatchCallsTotal              Counter32
     }



     acPMSBCIPGroupOutNoMatchCallsIpGroup OBJECT-TYPE
       SYNTAX Unsigned32 (0..5000)
       MAX-ACCESS not-accessible
       STATUS obsolete
       DESCRIPTION
           "."
       ::= {acPMSBCIPGroupOutNoMatchCallsEntry 1}



     acPMSBCIPGroupOutNoMatchCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutNoMatchCallsEntry 2}



     acPMSBCIPGroupOutNoMatchCallsVal OBJECT-TYPE
       SYNTAX Gauge32
       MAX-ACCESS read-only
       STATUS obsolete
       DESCRIPTION
           "Value of gauge or counter."
       ::= {acPMSBCIPGroupOutNoMatchCallsEntry 3}



     acPMSBCIPGroupOutNoMatchCallsTotal OBJECT-TYPE
       SYNTAX Counter32
       MAX-ACCESS read-only
       STATUS obsolete
       DESCRIPTION
           "Activity volume."
       ::= {acPMSBCIPGroupOutNoMatchCallsEntry 4}



     -- ****************************************
     -- acPMSBCIPGroupInBusyCalls table declaration
     -- ****************************************
     acPMSBCIPGroupInBusyCallsTable OBJECT-TYPE
       SYNTAX SEQUENCE OF AcPMSBCIPGroupInBusyCallsEntry
       MAX-ACCESS not-accessible
       STATUS obsolete
       DESCRIPTION
           "Number of incoming busy calls per IP group."
       ::= {acPMSbcData 22}



     -- ****************************************
     -- acPMSBCIPGroupInBusyCalls table entry
     -- ****************************************
     acPMSBCIPGroupInBusyCallsEntry OBJECT-TYPE
       SYNTAX AcPMSBCIPGroupInBusyCallsEntry
       MAX-ACCESS not-accessible
       STATUS obsolete
       DESCRIPTION
           ""
       INDEX {acPMSBCIPGroupInBusyCallsIpGroup,acPMSBCIPGroupInBusyCallsInterval}
       ::= {acPMSBCIPGroupInBusyCallsTable 1}



     -- ****************************************
     -- acPMSBCIPGroupInBusyCalls TABLE
     -- ****************************************
     AcPMSBCIPGroupInBusyCallsEntry ::= SEQUENCE {
       acPMSBCIPGroupInBusyCallsIpGroup                Unsigned32,
       acPMSBCIPGroupInBusyCallsInterval               Unsigned32,
       acPMSBCIPGroupInBusyCallsVal                    Gauge32,
       acPMSBCIPGroupInBusyCallsTotal                  Counter32
     }



     acPMSBCIPGroupInBusyCallsIpGroup OBJECT-TYPE
       SYNTAX Unsigned32 (0..5000)
       MAX-ACCESS not-accessible
       STATUS obsolete
       DESCRIPTION
           "."
       ::= {acPMSBCIPGroupInBusyCallsEntry 1}



     acPMSBCIPGroupInBusyCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInBusyCallsEntry 2}



     acPMSBCIPGroupInBusyCallsVal OBJECT-TYPE
       SYNTAX Gauge32
       MAX-ACCESS read-only
       STATUS obsolete
       DESCRIPTION
           "Value of gauge or counter."
       ::= {acPMSBCIPGroupInBusyCallsEntry 3}



     acPMSBCIPGroupInBusyCallsTotal OBJECT-TYPE
       SYNTAX Counter32
       MAX-ACCESS read-only
       STATUS obsolete
       DESCRIPTION
           "Activity volume."
       ::= {acPMSBCIPGroupInBusyCallsEntry 4}



     -- ****************************************
     -- acPMSBCIPGroupOutBusyCalls table declaration
     -- ****************************************
     acPMSBCIPGroupOutBusyCallsTable OBJECT-TYPE
       SYNTAX SEQUENCE OF AcPMSBCIPGroupOutBusyCallsEntry
       MAX-ACCESS not-accessible
       STATUS obsolete
       DESCRIPTION
           "Number of outgoing busy calls per IP group."
       ::= {acPMSbcData 23}



     -- ****************************************
     -- acPMSBCIPGroupOutBusyCalls table entry
     -- ****************************************
     acPMSBCIPGroupOutBusyCallsEntry OBJECT-TYPE
       SYNTAX AcPMSBCIPGroupOutBusyCallsEntry
       MAX-ACCESS not-accessible
       STATUS obsolete
       DESCRIPTION
           ""
       INDEX {acPMSBCIPGroupOutBusyCallsIpGroup,acPMSBCIPGroupOutBusyCallsInterval}
       ::= {acPMSBCIPGroupOutBusyCallsTable 1}



     -- ****************************************
     -- acPMSBCIPGroupOutBusyCalls TABLE
     -- ****************************************
     AcPMSBCIPGroupOutBusyCallsEntry ::= SEQUENCE {
       acPMSBCIPGroupOutBusyCallsIpGroup               Unsigned32,
       acPMSBCIPGroupOutBusyCallsInterval              Unsigned32,
       acPMSBCIPGroupOutBusyCallsVal                   Gauge32,
       acPMSBCIPGroupOutBusyCallsTotal                 Counter32
     }



     acPMSBCIPGroupOutBusyCallsIpGroup OBJECT-TYPE
       SYNTAX Unsigned32 (0..5000)
       MAX-ACCESS not-accessible
       STATUS obsolete
       DESCRIPTION
           "."
       ::= {acPMSBCIPGroupOutBusyCallsEntry 1}



     acPMSBCIPGroupOutBusyCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutBusyCallsEntry 2}



     acPMSBCIPGroupOutBusyCallsVal OBJECT-TYPE
       SYNTAX Gauge32
       MAX-ACCESS read-only
       STATUS obsolete
       DESCRIPTION
           "Value of gauge or counter."
       ::= {acPMSBCIPGroupOutBusyCallsEntry 3}



     acPMSBCIPGroupOutBusyCallsTotal OBJECT-TYPE
       SYNTAX Counter32
       MAX-ACCESS read-only
       STATUS obsolete
       DESCRIPTION
           "Activity volume."
       ::= {acPMSBCIPGroupOutBusyCallsEntry 4}



     -- ****************************************
     -- acPMSBCIPGroupInNoAnswerCalls table declaration
     -- ****************************************
     acPMSBCIPGroupInNoAnswerCallsTable OBJECT-TYPE
       SYNTAX SEQUENCE OF AcPMSBCIPGroupInNoAnswerCallsEntry
       MAX-ACCESS not-accessible
       STATUS obsolete
       DESCRIPTION
           "Number of incoming no answer calls per IP group."
       ::= {acPMSbcData 24}



     -- ****************************************
     -- acPMSBCIPGroupInNoAnswerCalls table entry
     -- ****************************************
     acPMSBCIPGroupInNoAnswerCallsEntry OBJECT-TYPE
       SYNTAX AcPMSBCIPGroupInNoAnswerCallsEntry
       MAX-ACCESS not-accessible
       STATUS obsolete
       DESCRIPTION
           ""
       INDEX {acPMSBCIPGroupInNoAnswerCallsIpGroup,acPMSBCIPGroupInNoAnswerCallsInterval}
       ::= {acPMSBCIPGroupInNoAnswerCallsTable 1}



     -- ****************************************
     -- acPMSBCIPGroupInNoAnswerCalls TABLE
     -- ****************************************
     AcPMSBCIPGroupInNoAnswerCallsEntry ::= SEQUENCE {
       acPMSBCIPGroupInNoAnswerCallsIpGroup            Unsigned32,
       acPMSBCIPGroupInNoAnswerCallsInterval           Unsigned32,
       acPMSBCIPGroupInNoAnswerCallsVal                Gauge32,
       acPMSBCIPGroupInNoAnswerCallsTotal              Counter32
     }



     acPMSBCIPGroupInNoAnswerCallsIpGroup OBJECT-TYPE
       SYNTAX Unsigned32 (0..5000)
       MAX-ACCESS not-accessible
       STATUS obsolete
       DESCRIPTION
           "."
       ::= {acPMSBCIPGroupInNoAnswerCallsEntry 1}



     acPMSBCIPGroupInNoAnswerCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInNoAnswerCallsEntry 2}



     acPMSBCIPGroupInNoAnswerCallsVal OBJECT-TYPE
       SYNTAX Gauge32
       MAX-ACCESS read-only
       STATUS obsolete
       DESCRIPTION
           "Value of gauge or counter."
       ::= {acPMSBCIPGroupInNoAnswerCallsEntry 3}



     acPMSBCIPGroupInNoAnswerCallsTotal OBJECT-TYPE
       SYNTAX Counter32
       MAX-ACCESS read-only
       STATUS obsolete
       DESCRIPTION
           "Activity volume."
       ::= {acPMSBCIPGroupInNoAnswerCallsEntry 4}



     -- ****************************************
     -- acPMSBCIPGroupOutNoAnswerCalls table declaration
     -- ****************************************
     acPMSBCIPGroupOutNoAnswerCallsTable OBJECT-TYPE
       SYNTAX SEQUENCE OF AcPMSBCIPGroupOutNoAnswerCallsEntry
       MAX-ACCESS not-accessible
       STATUS obsolete
       DESCRIPTION
           "Number of outgoing no answer calls per IP group."
       ::= {acPMSbcData 25}



     -- ****************************************
     -- acPMSBCIPGroupOutNoAnswerCalls table entry
     -- ****************************************
     acPMSBCIPGroupOutNoAnswerCallsEntry OBJECT-TYPE
       SYNTAX AcPMSBCIPGroupOutNoAnswerCallsEntry
       MAX-ACCESS not-accessible
       STATUS obsolete
       DESCRIPTION
           ""
       INDEX {acPMSBCIPGroupOutNoAnswerCallsIpGroup,acPMSBCIPGroupOutNoAnswerCallsInterval}
       ::= {acPMSBCIPGroupOutNoAnswerCallsTable 1}



     -- ****************************************
     -- acPMSBCIPGroupOutNoAnswerCalls TABLE
     -- ****************************************
     AcPMSBCIPGroupOutNoAnswerCallsEntry ::= SEQUENCE {
       acPMSBCIPGroupOutNoAnswerCallsIpGroup           Unsigned32,
       acPMSBCIPGroupOutNoAnswerCallsInterval          Unsigned32,
       acPMSBCIPGroupOutNoAnswerCallsVal               Gauge32,
       acPMSBCIPGroupOutNoAnswerCallsTotal             Counter32
     }



     acPMSBCIPGroupOutNoAnswerCallsIpGroup OBJECT-TYPE
       SYNTAX Unsigned32 (0..5000)
       MAX-ACCESS not-accessible
       STATUS obsolete
       DESCRIPTION
           "."
       ::= {acPMSBCIPGroupOutNoAnswerCallsEntry 1}



     acPMSBCIPGroupOutNoAnswerCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutNoAnswerCallsEntry 2}



     acPMSBCIPGroupOutNoAnswerCallsVal OBJECT-TYPE
       SYNTAX Gauge32
       MAX-ACCESS read-only
       STATUS obsolete
       DESCRIPTION
           "Value of gauge or counter."
       ::= {acPMSBCIPGroupOutNoAnswerCallsEntry 3}



     acPMSBCIPGroupOutNoAnswerCallsTotal OBJECT-TYPE
       SYNTAX Counter32
       MAX-ACCESS read-only
       STATUS obsolete
       DESCRIPTION
           "Activity volume."
       ::= {acPMSBCIPGroupOutNoAnswerCallsEntry 4}



     -- ****************************************
     -- acPMSBCIPGroupInForwardedCalls table declaration
     -- ****************************************
     acPMSBCIPGroupInForwardedCallsTable OBJECT-TYPE
       SYNTAX SEQUENCE OF AcPMSBCIPGroupInForwardedCallsEntry
       MAX-ACCESS not-accessible
       STATUS obsolete
       DESCRIPTION
           "Number of incoming forwarded calls per IP group."
       ::= {acPMSbcData 26}



     -- ****************************************
     -- acPMSBCIPGroupInForwardedCalls table entry
     -- ****************************************
     acPMSBCIPGroupInForwardedCallsEntry OBJECT-TYPE
       SYNTAX AcPMSBCIPGroupInForwardedCallsEntry
       MAX-ACCESS not-accessible
       STATUS obsolete
       DESCRIPTION
           ""
       INDEX {acPMSBCIPGroupInForwardedCallsIpGroup,acPMSBCIPGroupInForwardedCallsInterval}
       ::= {acPMSBCIPGroupInForwardedCallsTable 1}



     -- ****************************************
     -- acPMSBCIPGroupInForwardedCalls TABLE
     -- ****************************************
     AcPMSBCIPGroupInForwardedCallsEntry ::= SEQUENCE {
       acPMSBCIPGroupInForwardedCallsIpGroup           Unsigned32,
       acPMSBCIPGroupInForwardedCallsInterval          Unsigned32,
       acPMSBCIPGroupInForwardedCallsVal               Gauge32,
       acPMSBCIPGroupInForwardedCallsTotal             Counter32
     }



     acPMSBCIPGroupInForwardedCallsIpGroup OBJECT-TYPE
       SYNTAX Unsigned32 (0..5000)
       MAX-ACCESS not-accessible
       STATUS obsolete
       DESCRIPTION
           "."
       ::= {acPMSBCIPGroupInForwardedCallsEntry 1}



     acPMSBCIPGroupInForwardedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInForwardedCallsEntry 2}



     acPMSBCIPGroupInForwardedCallsVal OBJECT-TYPE
       SYNTAX Gauge32
       MAX-ACCESS read-only
       STATUS obsolete
       DESCRIPTION
           "Value of gauge or counter."
       ::= {acPMSBCIPGroupInForwardedCallsEntry 3}



     acPMSBCIPGroupInForwardedCallsTotal OBJECT-TYPE
       SYNTAX Counter32
       MAX-ACCESS read-only
       STATUS obsolete
       DESCRIPTION
           "Activity volume."
       ::= {acPMSBCIPGroupInForwardedCallsEntry 4}



     -- ****************************************
     -- acPMSBCIPGroupInForwardedSubscribeDialogs table declaration
     -- ****************************************
     acPMSBCIPGroupInForwardedSubscribeDialogsTable OBJECT-TYPE
       SYNTAX SEQUENCE OF AcPMSBCIPGroupInForwardedSubscribeDialogsEntry
       MAX-ACCESS not-accessible
       STATUS obsolete
       DESCRIPTION
           "Number of incoming SUBSCRIBE forwarded dialogs per IP group."
       ::= {acPMSbcData 27}



     -- ****************************************
     -- acPMSBCIPGroupInForwardedSubscribeDialogs table entry
     -- ****************************************
     acPMSBCIPGroupInForwardedSubscribeDialogsEntry OBJECT-TYPE
       SYNTAX AcPMSBCIPGroupInForwardedSubscribeDialogsEntry
       MAX-ACCESS not-accessible
       STATUS obsolete
       DESCRIPTION
           ""
       INDEX {acPMSBCIPGroupInForwardedSubscribeDialogsIpGroup,acPMSBCIPGroupInForwardedSubscribeDialogsInterval}
       ::= {acPMSBCIPGroupInForwardedSubscribeDialogsTable 1}



     -- ****************************************
     -- acPMSBCIPGroupInForwardedSubscribeDialogs TABLE
     -- ****************************************
     AcPMSBCIPGroupInForwardedSubscribeDialogsEntry ::= SEQUENCE {
       acPMSBCIPGroupInForwardedSubscribeDialogsIpGroup 
                                                       Unsigned32,
       acPMSBCIPGroupInForwardedSubscribeDialogsInterval 
                                                       Unsigned32,
       acPMSBCIPGroupInForwardedSubscribeDialogsVal    Gauge32,
       acPMSBCIPGroupInForwardedSubscribeDialogsTotal  Counter32
     }



     acPMSBCIPGroupInForwardedSubscribeDialogsIpGroup OBJECT-TYPE
       SYNTAX Unsigned32 (0..5000)
       MAX-ACCESS not-accessible
       STATUS obsolete
       DESCRIPTION
           "."
       ::= {acPMSBCIPGroupInForwardedSubscribeDialogsEntry 1}



     acPMSBCIPGroupInForwardedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInForwardedSubscribeDialogsEntry 2}



     acPMSBCIPGroupInForwardedSubscribeDialogsVal OBJECT-TYPE
       SYNTAX Gauge32
       MAX-ACCESS read-only
       STATUS obsolete
       DESCRIPTION
           "Value of gauge or counter."
       ::= {acPMSBCIPGroupInForwardedSubscribeDialogsEntry 3}



     acPMSBCIPGroupInForwardedSubscribeDialogsTotal OBJECT-TYPE
       SYNTAX Counter32
       MAX-ACCESS read-only
       STATUS obsolete
       DESCRIPTION
           "Activity volume."
       ::= {acPMSBCIPGroupInForwardedSubscribeDialogsEntry 4}



     -- ****************************************
     -- acPMSBCIPGroupInForwardedOtherDialogs table declaration
     -- ****************************************
     acPMSBCIPGroupInForwardedOtherDialogsTable OBJECT-TYPE
       SYNTAX SEQUENCE OF AcPMSBCIPGroupInForwardedOtherDialogsEntry
       MAX-ACCESS not-accessible
       STATUS obsolete
       DESCRIPTION
           "Number of incoming other forwarded dialogs per IP group."
       ::= {acPMSbcData 28}



     -- ****************************************
     -- acPMSBCIPGroupInForwardedOtherDialogs table entry
     -- ****************************************
     acPMSBCIPGroupInForwardedOtherDialogsEntry OBJECT-TYPE
       SYNTAX AcPMSBCIPGroupInForwardedOtherDialogsEntry
       MAX-ACCESS not-accessible
       STATUS obsolete
       DESCRIPTION
           ""
       INDEX {acPMSBCIPGroupInForwardedOtherDialogsIpGroup,acPMSBCIPGroupInForwardedOtherDialogsInterval}
       ::= {acPMSBCIPGroupInForwardedOtherDialogsTable 1}



     -- ****************************************
     -- acPMSBCIPGroupInForwardedOtherDialogs TABLE
     -- ****************************************
     AcPMSBCIPGroupInForwardedOtherDialogsEntry ::= SEQUENCE {
       acPMSBCIPGroupInForwardedOtherDialogsIpGroup    Unsigned32,
       acPMSBCIPGroupInForwardedOtherDialogsInterval   Unsigned32,
       acPMSBCIPGroupInForwardedOtherDialogsVal        Gauge32,
       acPMSBCIPGroupInForwardedOtherDialogsTotal      Counter32
     }



     acPMSBCIPGroupInForwardedOtherDialogsIpGroup OBJECT-TYPE
       SYNTAX Unsigned32 (0..5000)
       MAX-ACCESS not-accessible
       STATUS obsolete
       DESCRIPTION
           "."
       ::= {acPMSBCIPGroupInForwardedOtherDialogsEntry 1}



     acPMSBCIPGroupInForwardedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInForwardedOtherDialogsEntry 2}



     acPMSBCIPGroupInForwardedOtherDialogsVal OBJECT-TYPE
       SYNTAX Gauge32
       MAX-ACCESS read-only
       STATUS obsolete
       DESCRIPTION
           "Value of gauge or counter."
       ::= {acPMSBCIPGroupInForwardedOtherDialogsEntry 3}



     acPMSBCIPGroupInForwardedOtherDialogsTotal OBJECT-TYPE
       SYNTAX Counter32
       MAX-ACCESS read-only
       STATUS obsolete
       DESCRIPTION
           "Activity volume."
       ::= {acPMSBCIPGroupInForwardedOtherDialogsEntry 4}



     -- ****************************************
     -- acPMSBCIPGroupOutForwardedCalls table declaration
     -- ****************************************
     acPMSBCIPGroupOutForwardedCallsTable OBJECT-TYPE
       SYNTAX SEQUENCE OF AcPMSBCIPGroupOutForwardedCallsEntry
       MAX-ACCESS not-accessible
       STATUS obsolete
       DESCRIPTION
           "Number of outgoing forwarded calls per IP group."
       ::= {acPMSbcData 29}



     -- ****************************************
     -- acPMSBCIPGroupOutForwardedCalls table entry
     -- ****************************************
     acPMSBCIPGroupOutForwardedCallsEntry OBJECT-TYPE
       SYNTAX AcPMSBCIPGroupOutForwardedCallsEntry
       MAX-ACCESS not-accessible
       STATUS obsolete
       DESCRIPTION
           ""
       INDEX {acPMSBCIPGroupOutForwardedCallsIpGroup,acPMSBCIPGroupOutForwardedCallsInterval}
       ::= {acPMSBCIPGroupOutForwardedCallsTable 1}



     -- ****************************************
     -- acPMSBCIPGroupOutForwardedCalls TABLE
     -- ****************************************
     AcPMSBCIPGroupOutForwardedCallsEntry ::= SEQUENCE {
       acPMSBCIPGroupOutForwardedCallsIpGroup          Unsigned32,
       acPMSBCIPGroupOutForwardedCallsInterval         Unsigned32,
       acPMSBCIPGroupOutForwardedCallsVal              Gauge32,
       acPMSBCIPGroupOutForwardedCallsTotal            Counter32
     }



     acPMSBCIPGroupOutForwardedCallsIpGroup OBJECT-TYPE
       SYNTAX Unsigned32 (0..5000)
       MAX-ACCESS not-accessible
       STATUS obsolete
       DESCRIPTION
           "."
       ::= {acPMSBCIPGroupOutForwardedCallsEntry 1}



     acPMSBCIPGroupOutForwardedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutForwardedCallsEntry 2}



     acPMSBCIPGroupOutForwardedCallsVal OBJECT-TYPE
       SYNTAX Gauge32
       MAX-ACCESS read-only
       STATUS obsolete
       DESCRIPTION
           "Value of gauge or counter."
       ::= {acPMSBCIPGroupOutForwardedCallsEntry 3}



     acPMSBCIPGroupOutForwardedCallsTotal OBJECT-TYPE
       SYNTAX Counter32
       MAX-ACCESS read-only
       STATUS obsolete
       DESCRIPTION
           "Activity volume."
       ::= {acPMSBCIPGroupOutForwardedCallsEntry 4}



     -- ****************************************
     -- acPMSBCIPGroupOutForwardedSubscribeDialogs table declaration
     -- ****************************************
     acPMSBCIPGroupOutForwardedSubscribeDialogsTable OBJECT-TYPE
       SYNTAX SEQUENCE OF AcPMSBCIPGroupOutForwardedSubscribeDialogsEntry
       MAX-ACCESS not-accessible
       STATUS obsolete
       DESCRIPTION
           "Number of outgoing SUBSCRIBE forwarded dialogs per IP group."
       ::= {acPMSbcData 30}



     -- ****************************************
     -- acPMSBCIPGroupOutForwardedSubscribeDialogs table entry
     -- ****************************************
     acPMSBCIPGroupOutForwardedSubscribeDialogsEntry OBJECT-TYPE
       SYNTAX AcPMSBCIPGroupOutForwardedSubscribeDialogsEntry
       MAX-ACCESS not-accessible
       STATUS obsolete
       DESCRIPTION
           ""
       INDEX {acPMSBCIPGroupOutForwardedSubscribeDialogsIpGroup,acPMSBCIPGroupOutForwardedSubscribeDialogsInterval}
       ::= {acPMSBCIPGroupOutForwardedSubscribeDialogsTable 1}



     -- ****************************************
     -- acPMSBCIPGroupOutForwardedSubscribeDialogs TABLE
     -- ****************************************
     AcPMSBCIPGroupOutForwardedSubscribeDialogsEntry ::= SEQUENCE {
       acPMSBCIPGroupOutForwardedSubscribeDialogsIpGroup 
                                                       Unsigned32,
       acPMSBCIPGroupOutForwardedSubscribeDialogsInterval 
                                                       Unsigned32,
       acPMSBCIPGroupOutForwardedSubscribeDialogsVal   Gauge32,
       acPMSBCIPGroupOutForwardedSubscribeDialogsTotal Counter32
     }



     acPMSBCIPGroupOutForwardedSubscribeDialogsIpGroup OBJECT-TYPE
       SYNTAX Unsigned32 (0..5000)
       MAX-ACCESS not-accessible
       STATUS obsolete
       DESCRIPTION
           "."
       ::= {acPMSBCIPGroupOutForwardedSubscribeDialogsEntry 1}



     acPMSBCIPGroupOutForwardedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutForwardedSubscribeDialogsEntry 2}



     acPMSBCIPGroupOutForwardedSubscribeDialogsVal OBJECT-TYPE
       SYNTAX Gauge32
       MAX-ACCESS read-only
       STATUS obsolete
       DESCRIPTION
           "Value of gauge or counter."
       ::= {acPMSBCIPGroupOutForwardedSubscribeDialogsEntry 3}



     acPMSBCIPGroupOutForwardedSubscribeDialogsTotal OBJECT-TYPE
       SYNTAX Counter32
       MAX-ACCESS read-only
       STATUS obsolete
       DESCRIPTION
           "Activity volume."
       ::= {acPMSBCIPGroupOutForwardedSubscribeDialogsEntry 4}



     -- ****************************************
     -- acPMSBCIPGroupOutForwardedOtherDialogs table declaration
     -- ****************************************
     acPMSBCIPGroupOutForwardedOtherDialogsTable OBJECT-TYPE
       SYNTAX SEQUENCE OF AcPMSBCIPGroupOutForwardedOtherDialogsEntry
       MAX-ACCESS not-accessible
       STATUS obsolete
       DESCRIPTION
           "Number of outgoing other forwarded dialogs per IP group."
       ::= {acPMSbcData 31}



     -- ****************************************
     -- acPMSBCIPGroupOutForwardedOtherDialogs table entry
     -- ****************************************
     acPMSBCIPGroupOutForwardedOtherDialogsEntry OBJECT-TYPE
       SYNTAX AcPMSBCIPGroupOutForwardedOtherDialogsEntry
       MAX-ACCESS not-accessible
       STATUS obsolete
       DESCRIPTION
           ""
       INDEX {acPMSBCIPGroupOutForwardedOtherDialogsIpGroup,acPMSBCIPGroupOutForwardedOtherDialogsInterval}
       ::= {acPMSBCIPGroupOutForwardedOtherDialogsTable 1}



     -- ****************************************
     -- acPMSBCIPGroupOutForwardedOtherDialogs TABLE
     -- ****************************************
     AcPMSBCIPGroupOutForwardedOtherDialogsEntry ::= SEQUENCE {
       acPMSBCIPGroupOutForwardedOtherDialogsIpGroup   Unsigned32,
       acPMSBCIPGroupOutForwardedOtherDialogsInterval  Unsigned32,
       acPMSBCIPGroupOutForwardedOtherDialogsVal       Gauge32,
       acPMSBCIPGroupOutForwardedOtherDialogsTotal     Counter32
     }



     acPMSBCIPGroupOutForwardedOtherDialogsIpGroup OBJECT-TYPE
       SYNTAX Unsigned32 (0..5000)
       MAX-ACCESS not-accessible
       STATUS obsolete
       DESCRIPTION
           "."
       ::= {acPMSBCIPGroupOutForwardedOtherDialogsEntry 1}



     acPMSBCIPGroupOutForwardedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutForwardedOtherDialogsEntry 2}



     acPMSBCIPGroupOutForwardedOtherDialogsVal OBJECT-TYPE
       SYNTAX Gauge32
       MAX-ACCESS read-only
       STATUS obsolete
       DESCRIPTION
           "Value of gauge or counter."
       ::= {acPMSBCIPGroupOutForwardedOtherDialogsEntry 3}



     acPMSBCIPGroupOutForwardedOtherDialogsTotal OBJECT-TYPE
       SYNTAX Counter32
       MAX-ACCESS read-only
       STATUS obsolete
       DESCRIPTION
           "Activity volume."
       ::= {acPMSBCIPGroupOutForwardedOtherDialogsEntry 4}



     -- ****************************************
     -- acPMSBCIPGroupInGeneralFailedCalls table declaration
     -- ****************************************
     acPMSBCIPGroupInGeneralFailedCallsTable OBJECT-TYPE
       SYNTAX SEQUENCE OF AcPMSBCIPGroupInGeneralFailedCallsEntry
       MAX-ACCESS not-accessible
       STATUS obsolete
       DESCRIPTION
           "Number of incoming general call failures per IP group."
       ::= {acPMSbcData 32}



     -- ****************************************
     -- acPMSBCIPGroupInGeneralFailedCalls table entry
     -- ****************************************
     acPMSBCIPGroupInGeneralFailedCallsEntry OBJECT-TYPE
       SYNTAX AcPMSBCIPGroupInGeneralFailedCallsEntry
       MAX-ACCESS not-accessible
       STATUS obsolete
       DESCRIPTION
           ""
       INDEX {acPMSBCIPGroupInGeneralFailedCallsIpGroup,acPMSBCIPGroupInGeneralFailedCallsInterval}
       ::= {acPMSBCIPGroupInGeneralFailedCallsTable 1}



     -- ****************************************
     -- acPMSBCIPGroupInGeneralFailedCalls TABLE
     -- ****************************************
     AcPMSBCIPGroupInGeneralFailedCallsEntry ::= SEQUENCE {
       acPMSBCIPGroupInGeneralFailedCallsIpGroup       Unsigned32,
       acPMSBCIPGroupInGeneralFailedCallsInterval      Unsigned32,
       acPMSBCIPGroupInGeneralFailedCallsVal           Gauge32,
       acPMSBCIPGroupInGeneralFailedCallsTotal         Counter32
     }



     acPMSBCIPGroupInGeneralFailedCallsIpGroup OBJECT-TYPE
       SYNTAX Unsigned32 (0..5000)
       MAX-ACCESS not-accessible
       STATUS obsolete
       DESCRIPTION
           "."
       ::= {acPMSBCIPGroupInGeneralFailedCallsEntry 1}



     acPMSBCIPGroupInGeneralFailedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInGeneralFailedCallsEntry 2}



     acPMSBCIPGroupInGeneralFailedCallsVal OBJECT-TYPE
       SYNTAX Gauge32
       MAX-ACCESS read-only
       STATUS obsolete
       DESCRIPTION
           "Value of gauge or counter."
       ::= {acPMSBCIPGroupInGeneralFailedCallsEntry 3}



     acPMSBCIPGroupInGeneralFailedCallsTotal OBJECT-TYPE
       SYNTAX Counter32
       MAX-ACCESS read-only
       STATUS obsolete
       DESCRIPTION
           "Activity volume."
       ::= {acPMSBCIPGroupInGeneralFailedCallsEntry 4}



     -- ****************************************
     -- acPMSBCIPGroupInGeneralFailedSubscribeDialogs table declaration
     -- ****************************************
     acPMSBCIPGroupInGeneralFailedSubscribeDialogsTable OBJECT-TYPE
       SYNTAX SEQUENCE OF AcPMSBCIPGroupInGeneralFailedSubscribeDialogsEntry
       MAX-ACCESS not-accessible
       STATUS obsolete
       DESCRIPTION
           "Number of incoming SUBSCRIBE general dialog failures per IP group."
       ::= {acPMSbcData 33}



     -- ****************************************
     -- acPMSBCIPGroupInGeneralFailedSubscribeDialogs table entry
     -- ****************************************
     acPMSBCIPGroupInGeneralFailedSubscribeDialogsEntry OBJECT-TYPE
       SYNTAX AcPMSBCIPGroupInGeneralFailedSubscribeDialogsEntry
       MAX-ACCESS not-accessible
       STATUS obsolete
       DESCRIPTION
           ""
       INDEX {acPMSBCIPGroupInGeneralFailedSubscribeDialogsIpGroup,acPMSBCIPGroupInGeneralFailedSubscribeDialogsInterval}
       ::= {acPMSBCIPGroupInGeneralFailedSubscribeDialogsTable 1}



     -- ****************************************
     -- acPMSBCIPGroupInGeneralFailedSubscribeDialogs TABLE
     -- ****************************************
     AcPMSBCIPGroupInGeneralFailedSubscribeDialogsEntry ::= SEQUENCE {
       acPMSBCIPGroupInGeneralFailedSubscribeDialogsIpGroup 
                                                       Unsigned32,
       acPMSBCIPGroupInGeneralFailedSubscribeDialogsInterval 
                                                       Unsigned32,
       acPMSBCIPGroupInGeneralFailedSubscribeDialogsVal 
                                                       Gauge32,
       acPMSBCIPGroupInGeneralFailedSubscribeDialogsTotal 
                                                       Counter32
     }



     acPMSBCIPGroupInGeneralFailedSubscribeDialogsIpGroup OBJECT-TYPE
       SYNTAX Unsigned32 (0..5000)
       MAX-ACCESS not-accessible
       STATUS obsolete
       DESCRIPTION
           "."
       ::= {acPMSBCIPGroupInGeneralFailedSubscribeDialogsEntry 1}



     acPMSBCIPGroupInGeneralFailedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInGeneralFailedSubscribeDialogsEntry 2}



     acPMSBCIPGroupInGeneralFailedSubscribeDialogsVal OBJECT-TYPE
       SYNTAX Gauge32
       MAX-ACCESS read-only
       STATUS obsolete
       DESCRIPTION
           "Value of gauge or counter."
       ::= {acPMSBCIPGroupInGeneralFailedSubscribeDialogsEntry 3}



     acPMSBCIPGroupInGeneralFailedSubscribeDialogsTotal OBJECT-TYPE
       SYNTAX Counter32
       MAX-ACCESS read-only
       STATUS obsolete
       DESCRIPTION
           "Activity volume."
       ::= {acPMSBCIPGroupInGeneralFailedSubscribeDialogsEntry 4}



     -- ****************************************
     -- acPMSBCIPGroupInGeneralFailedOtherDialogs table declaration
     -- ****************************************
     acPMSBCIPGroupInGeneralFailedOtherDialogsTable OBJECT-TYPE
       SYNTAX SEQUENCE OF AcPMSBCIPGroupInGeneralFailedOtherDialogsEntry
       MAX-ACCESS not-accessible
       STATUS obsolete
       DESCRIPTION
           "Number of incoming other general dialog failures per IP group."
       ::= {acPMSbcData 34}



     -- ****************************************
     -- acPMSBCIPGroupInGeneralFailedOtherDialogs table entry
     -- ****************************************
     acPMSBCIPGroupInGeneralFailedOtherDialogsEntry OBJECT-TYPE
       SYNTAX AcPMSBCIPGroupInGeneralFailedOtherDialogsEntry
       MAX-ACCESS not-accessible
       STATUS obsolete
       DESCRIPTION
           ""
       INDEX {acPMSBCIPGroupInGeneralFailedOtherDialogsIpGroup,acPMSBCIPGroupInGeneralFailedOtherDialogsInterval}
       ::= {acPMSBCIPGroupInGeneralFailedOtherDialogsTable 1}



     -- ****************************************
     -- acPMSBCIPGroupInGeneralFailedOtherDialogs TABLE
     -- ****************************************
     AcPMSBCIPGroupInGeneralFailedOtherDialogsEntry ::= SEQUENCE {
       acPMSBCIPGroupInGeneralFailedOtherDialogsIpGroup 
                                                       Unsigned32,
       acPMSBCIPGroupInGeneralFailedOtherDialogsInterval 
                                                       Unsigned32,
       acPMSBCIPGroupInGeneralFailedOtherDialogsVal    Gauge32,
       acPMSBCIPGroupInGeneralFailedOtherDialogsTotal  Counter32
     }



     acPMSBCIPGroupInGeneralFailedOtherDialogsIpGroup OBJECT-TYPE
       SYNTAX Unsigned32 (0..5000)
       MAX-ACCESS not-accessible
       STATUS obsolete
       DESCRIPTION
           "."
       ::= {acPMSBCIPGroupInGeneralFailedOtherDialogsEntry 1}



     acPMSBCIPGroupInGeneralFailedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInGeneralFailedOtherDialogsEntry 2}



     acPMSBCIPGroupInGeneralFailedOtherDialogsVal OBJECT-TYPE
       SYNTAX Gauge32
       MAX-ACCESS read-only
       STATUS obsolete
       DESCRIPTION
           "Value of gauge or counter."
       ::= {acPMSBCIPGroupInGeneralFailedOtherDialogsEntry 3}



     acPMSBCIPGroupInGeneralFailedOtherDialogsTotal OBJECT-TYPE
       SYNTAX Counter32
       MAX-ACCESS read-only
       STATUS obsolete
       DESCRIPTION
           "Activity volume."
       ::= {acPMSBCIPGroupInGeneralFailedOtherDialogsEntry 4}



     -- ****************************************
     -- acPMSBCIPGroupOutGeneralFailedCalls table declaration
     -- ****************************************
     acPMSBCIPGroupOutGeneralFailedCallsTable OBJECT-TYPE
       SYNTAX SEQUENCE OF AcPMSBCIPGroupOutGeneralFailedCallsEntry
       MAX-ACCESS not-accessible
       STATUS obsolete
       DESCRIPTION
           "Number of outgoing general call failures per IP group."
       ::= {acPMSbcData 35}



     -- ****************************************
     -- acPMSBCIPGroupOutGeneralFailedCalls table entry
     -- ****************************************
     acPMSBCIPGroupOutGeneralFailedCallsEntry OBJECT-TYPE
       SYNTAX AcPMSBCIPGroupOutGeneralFailedCallsEntry
       MAX-ACCESS not-accessible
       STATUS obsolete
       DESCRIPTION
           ""
       INDEX {acPMSBCIPGroupOutGeneralFailedCallsIpGroup,acPMSBCIPGroupOutGeneralFailedCallsInterval}
       ::= {acPMSBCIPGroupOutGeneralFailedCallsTable 1}



     -- ****************************************
     -- acPMSBCIPGroupOutGeneralFailedCalls TABLE
     -- ****************************************
     AcPMSBCIPGroupOutGeneralFailedCallsEntry ::= SEQUENCE {
       acPMSBCIPGroupOutGeneralFailedCallsIpGroup      Unsigned32,
       acPMSBCIPGroupOutGeneralFailedCallsInterval     Unsigned32,
       acPMSBCIPGroupOutGeneralFailedCallsVal          Gauge32,
       acPMSBCIPGroupOutGeneralFailedCallsTotal        Counter32
     }



     acPMSBCIPGroupOutGeneralFailedCallsIpGroup OBJECT-TYPE
       SYNTAX Unsigned32 (0..5000)
       MAX-ACCESS not-accessible
       STATUS obsolete
       DESCRIPTION
           "."
       ::= {acPMSBCIPGroupOutGeneralFailedCallsEntry 1}



     acPMSBCIPGroupOutGeneralFailedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutGeneralFailedCallsEntry 2}



     acPMSBCIPGroupOutGeneralFailedCallsVal OBJECT-TYPE
       SYNTAX Gauge32
       MAX-ACCESS read-only
       STATUS obsolete
       DESCRIPTION
           "Value of gauge or counter."
       ::= {acPMSBCIPGroupOutGeneralFailedCallsEntry 3}



     acPMSBCIPGroupOutGeneralFailedCallsTotal OBJECT-TYPE
       SYNTAX Counter32
       MAX-ACCESS read-only
       STATUS obsolete
       DESCRIPTION
           "Activity volume."
       ::= {acPMSBCIPGroupOutGeneralFailedCallsEntry 4}



     -- ****************************************
     -- acPMSBCIPGroupOutGeneralFailedSubscribeDialogs table declaration
     -- ****************************************
     acPMSBCIPGroupOutGeneralFailedSubscribeDialogsTable OBJECT-TYPE
       SYNTAX SEQUENCE OF AcPMSBCIPGroupOutGeneralFailedSubscribeDialogsEntry
       MAX-ACCESS not-accessible
       STATUS obsolete
       DESCRIPTION
           "Number of outgoing SUBSCRIBE general dialog failures per IP group."
       ::= {acPMSbcData 36}



     -- ****************************************
     -- acPMSBCIPGroupOutGeneralFailedSubscribeDialogs table entry
     -- ****************************************
     acPMSBCIPGroupOutGeneralFailedSubscribeDialogsEntry OBJECT-TYPE
       SYNTAX AcPMSBCIPGroupOutGeneralFailedSubscribeDialogsEntry
       MAX-ACCESS not-accessible
       STATUS obsolete
       DESCRIPTION
           ""
       INDEX {acPMSBCIPGroupOutGeneralFailedSubscribeDialogsIpGroup,acPMSBCIPGroupOutGeneralFailedSubscribeDialogsInterval}
       ::= {acPMSBCIPGroupOutGeneralFailedSubscribeDialogsTable 1}



     -- ****************************************
     -- acPMSBCIPGroupOutGeneralFailedSubscribeDialogs TABLE
     -- ****************************************
     AcPMSBCIPGroupOutGeneralFailedSubscribeDialogsEntry ::= SEQUENCE {
       acPMSBCIPGroupOutGeneralFailedSubscribeDialogsIpGroup 
                                                       Unsigned32,
       acPMSBCIPGroupOutGeneralFailedSubscribeDialogsInterval 
                                                       Unsigned32,
       acPMSBCIPGroupOutGeneralFailedSubscribeDialogsVal 
                                                       Gauge32,
       acPMSBCIPGroupOutGeneralFailedSubscribeDialogsTotal 
                                                       Counter32
     }



     acPMSBCIPGroupOutGeneralFailedSubscribeDialogsIpGroup OBJECT-TYPE
       SYNTAX Unsigned32 (0..5000)
       MAX-ACCESS not-accessible
       STATUS obsolete
       DESCRIPTION
           "."
       ::= {acPMSBCIPGroupOutGeneralFailedSubscribeDialogsEntry 1}



     acPMSBCIPGroupOutGeneralFailedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutGeneralFailedSubscribeDialogsEntry 2}



     acPMSBCIPGroupOutGeneralFailedSubscribeDialogsVal OBJECT-TYPE
       SYNTAX Gauge32
       MAX-ACCESS read-only
       STATUS obsolete
       DESCRIPTION
           "Value of gauge or counter."
       ::= {acPMSBCIPGroupOutGeneralFailedSubscribeDialogsEntry 3}



     acPMSBCIPGroupOutGeneralFailedSubscribeDialogsTotal OBJECT-TYPE
       SYNTAX Counter32
       MAX-ACCESS read-only
       STATUS obsolete
       DESCRIPTION
           "Activity volume."
       ::= {acPMSBCIPGroupOutGeneralFailedSubscribeDialogsEntry 4}



     -- ****************************************
     -- acPMSBCIPGroupOutGeneralFailedOtherDialogs table declaration
     -- ****************************************
     acPMSBCIPGroupOutGeneralFailedOtherDialogsTable OBJECT-TYPE
       SYNTAX SEQUENCE OF AcPMSBCIPGroupOutGeneralFailedOtherDialogsEntry
       MAX-ACCESS not-accessible
       STATUS obsolete
       DESCRIPTION
           "Number of outgoing other general dialog failures per IP group."
       ::= {acPMSbcData 37}



     -- ****************************************
     -- acPMSBCIPGroupOutGeneralFailedOtherDialogs table entry
     -- ****************************************
     acPMSBCIPGroupOutGeneralFailedOtherDialogsEntry OBJECT-TYPE
       SYNTAX AcPMSBCIPGroupOutGeneralFailedOtherDialogsEntry
       MAX-ACCESS not-accessible
       STATUS obsolete
       DESCRIPTION
           ""
       INDEX {acPMSBCIPGroupOutGeneralFailedOtherDialogsIpGroup,acPMSBCIPGroupOutGeneralFailedOtherDialogsInterval}
       ::= {acPMSBCIPGroupOutGeneralFailedOtherDialogsTable 1}



     -- ****************************************
     -- acPMSBCIPGroupOutGeneralFailedOtherDialogs TABLE
     -- ****************************************
     AcPMSBCIPGroupOutGeneralFailedOtherDialogsEntry ::= SEQUENCE {
       acPMSBCIPGroupOutGeneralFailedOtherDialogsIpGroup 
                                                       Unsigned32,
       acPMSBCIPGroupOutGeneralFailedOtherDialogsInterval 
                                                       Unsigned32,
       acPMSBCIPGroupOutGeneralFailedOtherDialogsVal   Gauge32,
       acPMSBCIPGroupOutGeneralFailedOtherDialogsTotal Counter32
     }



     acPMSBCIPGroupOutGeneralFailedOtherDialogsIpGroup OBJECT-TYPE
       SYNTAX Unsigned32 (0..5000)
       MAX-ACCESS not-accessible
       STATUS obsolete
       DESCRIPTION
           "."
       ::= {acPMSBCIPGroupOutGeneralFailedOtherDialogsEntry 1}



     acPMSBCIPGroupOutGeneralFailedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutGeneralFailedOtherDialogsEntry 2}



     acPMSBCIPGroupOutGeneralFailedOtherDialogsVal OBJECT-TYPE
       SYNTAX Gauge32
       MAX-ACCESS read-only
       STATUS obsolete
       DESCRIPTION
           "Value of gauge or counter."
       ::= {acPMSBCIPGroupOutGeneralFailedOtherDialogsEntry 3}



     acPMSBCIPGroupOutGeneralFailedOtherDialogsTotal OBJECT-TYPE
       SYNTAX Counter32
       MAX-ACCESS read-only
       STATUS obsolete
       DESCRIPTION
           "Activity volume."
       ::= {acPMSBCIPGroupOutGeneralFailedOtherDialogsEntry 4}



     -- ****************************************
     -- acPMSBCIPGroupInEstablishedCalls table declaration
     -- ****************************************
     acPMSBCIPGroupInEstablishedCallsTable OBJECT-TYPE
       SYNTAX SEQUENCE OF AcPMSBCIPGroupInEstablishedCallsEntry
       MAX-ACCESS not-accessible
       STATUS obsolete
       DESCRIPTION
           "Number of incoming established calls per IP group."
       ::= {acPMSbcData 38}



     -- ****************************************
     -- acPMSBCIPGroupInEstablishedCalls table entry
     -- ****************************************
     acPMSBCIPGroupInEstablishedCallsEntry OBJECT-TYPE
       SYNTAX AcPMSBCIPGroupInEstablishedCallsEntry
       MAX-ACCESS not-accessible
       STATUS obsolete
       DESCRIPTION
           ""
       INDEX {acPMSBCIPGroupInEstablishedCallsIpGroup,acPMSBCIPGroupInEstablishedCallsInterval}
       ::= {acPMSBCIPGroupInEstablishedCallsTable 1}



     -- ****************************************
     -- acPMSBCIPGroupInEstablishedCalls TABLE
     -- ****************************************
     AcPMSBCIPGroupInEstablishedCallsEntry ::= SEQUENCE {
       acPMSBCIPGroupInEstablishedCallsIpGroup         Unsigned32,
       acPMSBCIPGroupInEstablishedCallsInterval        Unsigned32,
       acPMSBCIPGroupInEstablishedCallsVal             Counter32,
       acPMSBCIPGroupInEstablishedCallsTotal           Counter32
     }



     acPMSBCIPGroupInEstablishedCallsIpGroup OBJECT-TYPE
       SYNTAX Unsigned32 (0..5000)
       MAX-ACCESS not-accessible
       STATUS obsolete
       DESCRIPTION
           "."
       ::= {acPMSBCIPGroupInEstablishedCallsEntry 1}



     acPMSBCIPGroupInEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInEstablishedCallsEntry 2}



     acPMSBCIPGroupInEstablishedCallsVal OBJECT-TYPE
       SYNTAX Counter32
       MAX-ACCESS read-only
       STATUS obsolete
       DESCRIPTION
           "Value of gauge or counter."
       ::= {acPMSBCIPGroupInEstablishedCallsEntry 3}



     acPMSBCIPGroupInEstablishedCallsTotal OBJECT-TYPE
       SYNTAX Counter32
       MAX-ACCESS read-only
       STATUS obsolete
       DESCRIPTION
           "Activity volume."
       ::= {acPMSBCIPGroupInEstablishedCallsEntry 4}



     -- ****************************************
     -- acPMSBCIPGroupInEstablishedSubscribeDialogs table declaration
     -- ****************************************
     acPMSBCIPGroupInEstablishedSubscribeDialogsTable OBJECT-TYPE
       SYNTAX SEQUENCE OF AcPMSBCIPGroupInEstablishedSubscribeDialogsEntry
       MAX-ACCESS not-accessible
       STATUS obsolete
       DESCRIPTION
           "Number of incoming SUBSCRIBE established dialogs per IP group."
       ::= {acPMSbcData 39}



     -- ****************************************
     -- acPMSBCIPGroupInEstablishedSubscribeDialogs table entry
     -- ****************************************
     acPMSBCIPGroupInEstablishedSubscribeDialogsEntry OBJECT-TYPE
       SYNTAX AcPMSBCIPGroupInEstablishedSubscribeDialogsEntry
       MAX-ACCESS not-accessible
       STATUS obsolete
       DESCRIPTION
           ""
       INDEX {acPMSBCIPGroupInEstablishedSubscribeDialogsIpGroup,acPMSBCIPGroupInEstablishedSubscribeDialogsInterval}
       ::= {acPMSBCIPGroupInEstablishedSubscribeDialogsTable 1}



     -- ****************************************
     -- acPMSBCIPGroupInEstablishedSubscribeDialogs TABLE
     -- ****************************************
     AcPMSBCIPGroupInEstablishedSubscribeDialogsEntry ::= SEQUENCE {
       acPMSBCIPGroupInEstablishedSubscribeDialogsIpGroup 
                                                       Unsigned32,
       acPMSBCIPGroupInEstablishedSubscribeDialogsInterval 
                                                       Unsigned32,
       acPMSBCIPGroupInEstablishedSubscribeDialogsVal  Gauge32,
       acPMSBCIPGroupInEstablishedSubscribeDialogsTotal 
                                                       Counter32
     }



     acPMSBCIPGroupInEstablishedSubscribeDialogsIpGroup OBJECT-TYPE
       SYNTAX Unsigned32 (0..5000)
       MAX-ACCESS not-accessible
       STATUS obsolete
       DESCRIPTION
           "."
       ::= {acPMSBCIPGroupInEstablishedSubscribeDialogsEntry 1}



     acPMSBCIPGroupInEstablishedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInEstablishedSubscribeDialogsEntry 2}



     acPMSBCIPGroupInEstablishedSubscribeDialogsVal OBJECT-TYPE
       SYNTAX Gauge32
       MAX-ACCESS read-only
       STATUS obsolete
       DESCRIPTION
           "Value of gauge or counter."
       ::= {acPMSBCIPGroupInEstablishedSubscribeDialogsEntry 3}



     acPMSBCIPGroupInEstablishedSubscribeDialogsTotal OBJECT-TYPE
       SYNTAX Counter32
       MAX-ACCESS read-only
       STATUS obsolete
       DESCRIPTION
           "Activity volume."
       ::= {acPMSBCIPGroupInEstablishedSubscribeDialogsEntry 4}



     -- ****************************************
     -- acPMSBCIPGroupInEstablishedOtherDialogs table declaration
     -- ****************************************
     acPMSBCIPGroupInEstablishedOtherDialogsTable OBJECT-TYPE
       SYNTAX SEQUENCE OF AcPMSBCIPGroupInEstablishedOtherDialogsEntry
       MAX-ACCESS not-accessible
       STATUS obsolete
       DESCRIPTION
           "Number of incoming other established dialogs per IP group."
       ::= {acPMSbcData 40}



     -- ****************************************
     -- acPMSBCIPGroupInEstablishedOtherDialogs table entry
     -- ****************************************
     acPMSBCIPGroupInEstablishedOtherDialogsEntry OBJECT-TYPE
       SYNTAX AcPMSBCIPGroupInEstablishedOtherDialogsEntry
       MAX-ACCESS not-accessible
       STATUS obsolete
       DESCRIPTION
           ""
       INDEX {acPMSBCIPGroupInEstablishedOtherDialogsIpGroup,acPMSBCIPGroupInEstablishedOtherDialogsInterval}
       ::= {acPMSBCIPGroupInEstablishedOtherDialogsTable 1}



     -- ****************************************
     -- acPMSBCIPGroupInEstablishedOtherDialogs TABLE
     -- ****************************************
     AcPMSBCIPGroupInEstablishedOtherDialogsEntry ::= SEQUENCE {
       acPMSBCIPGroupInEstablishedOtherDialogsIpGroup  Unsigned32,
       acPMSBCIPGroupInEstablishedOtherDialogsInterval Unsigned32,
       acPMSBCIPGroupInEstablishedOtherDialogsVal      Gauge32,
       acPMSBCIPGroupInEstablishedOtherDialogsTotal    Counter32
     }



     acPMSBCIPGroupInEstablishedOtherDialogsIpGroup OBJECT-TYPE
       SYNTAX Unsigned32 (0..5000)
       MAX-ACCESS not-accessible
       STATUS obsolete
       DESCRIPTION
           "."
       ::= {acPMSBCIPGroupInEstablishedOtherDialogsEntry 1}



     acPMSBCIPGroupInEstablishedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInEstablishedOtherDialogsEntry 2}



     acPMSBCIPGroupInEstablishedOtherDialogsVal OBJECT-TYPE
       SYNTAX Gauge32
       MAX-ACCESS read-only
       STATUS obsolete
       DESCRIPTION
           "Value of gauge or counter."
       ::= {acPMSBCIPGroupInEstablishedOtherDialogsEntry 3}



     acPMSBCIPGroupInEstablishedOtherDialogsTotal OBJECT-TYPE
       SYNTAX Counter32
       MAX-ACCESS read-only
       STATUS obsolete
       DESCRIPTION
           "Activity volume."
       ::= {acPMSBCIPGroupInEstablishedOtherDialogsEntry 4}



     -- ****************************************
     -- acPMSBCIPGroupOutEstablishedCalls table declaration
     -- ****************************************
     acPMSBCIPGroupOutEstablishedCallsTable OBJECT-TYPE
       SYNTAX SEQUENCE OF AcPMSBCIPGroupOutEstablishedCallsEntry
       MAX-ACCESS not-accessible
       STATUS obsolete
       DESCRIPTION
           "Number of outgoing established calls per IP group."
       ::= {acPMSbcData 41}



     -- ****************************************
     -- acPMSBCIPGroupOutEstablishedCalls table entry
     -- ****************************************
     acPMSBCIPGroupOutEstablishedCallsEntry OBJECT-TYPE
       SYNTAX AcPMSBCIPGroupOutEstablishedCallsEntry
       MAX-ACCESS not-accessible
       STATUS obsolete
       DESCRIPTION
           ""
       INDEX {acPMSBCIPGroupOutEstablishedCallsIpGroup,acPMSBCIPGroupOutEstablishedCallsInterval}
       ::= {acPMSBCIPGroupOutEstablishedCallsTable 1}



     -- ****************************************
     -- acPMSBCIPGroupOutEstablishedCalls TABLE
     -- ****************************************
     AcPMSBCIPGroupOutEstablishedCallsEntry ::= SEQUENCE {
       acPMSBCIPGroupOutEstablishedCallsIpGroup        Unsigned32,
       acPMSBCIPGroupOutEstablishedCallsInterval       Unsigned32,
       acPMSBCIPGroupOutEstablishedCallsVal            Counter32,
       acPMSBCIPGroupOutEstablishedCallsTotal          Counter32
     }



     acPMSBCIPGroupOutEstablishedCallsIpGroup OBJECT-TYPE
       SYNTAX Unsigned32 (0..5000)
       MAX-ACCESS not-accessible
       STATUS obsolete
       DESCRIPTION
           "."
       ::= {acPMSBCIPGroupOutEstablishedCallsEntry 1}



     acPMSBCIPGroupOutEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutEstablishedCallsEntry 2}



     acPMSBCIPGroupOutEstablishedCallsVal OBJECT-TYPE
       SYNTAX Counter32
       MAX-ACCESS read-only
       STATUS obsolete
       DESCRIPTION
           "Value of gauge or counter."
       ::= {acPMSBCIPGroupOutEstablishedCallsEntry 3}



     acPMSBCIPGroupOutEstablishedCallsTotal OBJECT-TYPE
       SYNTAX Counter32
       MAX-ACCESS read-only
       STATUS obsolete
       DESCRIPTION
           "Activity volume."
       ::= {acPMSBCIPGroupOutEstablishedCallsEntry 4}



     -- ****************************************
     -- acPMSBCIPGroupOutEstablishedSubscribeDialogs table declaration
     -- ****************************************
     acPMSBCIPGroupOutEstablishedSubscribeDialogsTable OBJECT-TYPE
       SYNTAX SEQUENCE OF AcPMSBCIPGroupOutEstablishedSubscribeDialogsEntry
       MAX-ACCESS not-accessible
       STATUS obsolete
       DESCRIPTION
           "Number of outgoing SUBSCRIBE established dialogs per IP group."
       ::= {acPMSbcData 42}



     -- ****************************************
     -- acPMSBCIPGroupOutEstablishedSubscribeDialogs table entry
     -- ****************************************
     acPMSBCIPGroupOutEstablishedSubscribeDialogsEntry OBJECT-TYPE
       SYNTAX AcPMSBCIPGroupOutEstablishedSubscribeDialogsEntry
       MAX-ACCESS not-accessible
       STATUS obsolete
       DESCRIPTION
           ""
       INDEX {acPMSBCIPGroupOutEstablishedSubscribeDialogsIpGroup,acPMSBCIPGroupOutEstablishedSubscribeDialogsInterval}
       ::= {acPMSBCIPGroupOutEstablishedSubscribeDialogsTable 1}



     -- ****************************************
     -- acPMSBCIPGroupOutEstablishedSubscribeDialogs TABLE
     -- ****************************************
     AcPMSBCIPGroupOutEstablishedSubscribeDialogsEntry ::= SEQUENCE {
       acPMSBCIPGroupOutEstablishedSubscribeDialogsIpGroup 
                                                       Unsigned32,
       acPMSBCIPGroupOutEstablishedSubscribeDialogsInterval 
                                                       Unsigned32,
       acPMSBCIPGroupOutEstablishedSubscribeDialogsVal Gauge32,
       acPMSBCIPGroupOutEstablishedSubscribeDialogsTotal 
                                                       Counter32
     }



     acPMSBCIPGroupOutEstablishedSubscribeDialogsIpGroup OBJECT-TYPE
       SYNTAX Unsigned32 (0..5000)
       MAX-ACCESS not-accessible
       STATUS obsolete
       DESCRIPTION
           "."
       ::= {acPMSBCIPGroupOutEstablishedSubscribeDialogsEntry 1}



     acPMSBCIPGroupOutEstablishedSubscribeDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutEstablishedSubscribeDialogsEntry 2}



     acPMSBCIPGroupOutEstablishedSubscribeDialogsVal OBJECT-TYPE
       SYNTAX Gauge32
       MAX-ACCESS read-only
       STATUS obsolete
       DESCRIPTION
           "Value of gauge or counter."
       ::= {acPMSBCIPGroupOutEstablishedSubscribeDialogsEntry 3}



     acPMSBCIPGroupOutEstablishedSubscribeDialogsTotal OBJECT-TYPE
       SYNTAX Counter32
       MAX-ACCESS read-only
       STATUS obsolete
       DESCRIPTION
           "Activity volume."
       ::= {acPMSBCIPGroupOutEstablishedSubscribeDialogsEntry 4}



     -- ****************************************
     -- acPMSBCIPGroupOutEstablishedOtherDialogs table declaration
     -- ****************************************
     acPMSBCIPGroupOutEstablishedOtherDialogsTable OBJECT-TYPE
       SYNTAX SEQUENCE OF AcPMSBCIPGroupOutEstablishedOtherDialogsEntry
       MAX-ACCESS not-accessible
       STATUS obsolete
       DESCRIPTION
           "Number of outgoing other established dialogs per IP group."
       ::= {acPMSbcData 43}



     -- ****************************************
     -- acPMSBCIPGroupOutEstablishedOtherDialogs table entry
     -- ****************************************
     acPMSBCIPGroupOutEstablishedOtherDialogsEntry OBJECT-TYPE
       SYNTAX AcPMSBCIPGroupOutEstablishedOtherDialogsEntry
       MAX-ACCESS not-accessible
       STATUS obsolete
       DESCRIPTION
           ""
       INDEX {acPMSBCIPGroupOutEstablishedOtherDialogsIpGroup,acPMSBCIPGroupOutEstablishedOtherDialogsInterval}
       ::= {acPMSBCIPGroupOutEstablishedOtherDialogsTable 1}



     -- ****************************************
     -- acPMSBCIPGroupOutEstablishedOtherDialogs TABLE
     -- ****************************************
     AcPMSBCIPGroupOutEstablishedOtherDialogsEntry ::= SEQUENCE {
       acPMSBCIPGroupOutEstablishedOtherDialogsIpGroup Unsigned32,
       acPMSBCIPGroupOutEstablishedOtherDialogsInterval 
                                                       Unsigned32,
       acPMSBCIPGroupOutEstablishedOtherDialogsVal     Gauge32,
       acPMSBCIPGroupOutEstablishedOtherDialogsTotal   Counter32
     }



     acPMSBCIPGroupOutEstablishedOtherDialogsIpGroup OBJECT-TYPE
       SYNTAX Unsigned32 (0..5000)
       MAX-ACCESS not-accessible
       STATUS obsolete
       DESCRIPTION
           "."
       ::= {acPMSBCIPGroupOutEstablishedOtherDialogsEntry 1}



     acPMSBCIPGroupOutEstablishedOtherDialogsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutEstablishedOtherDialogsEntry 2}



     acPMSBCIPGroupOutEstablishedOtherDialogsVal OBJECT-TYPE
       SYNTAX Gauge32
       MAX-ACCESS read-only
       STATUS obsolete
       DESCRIPTION
           "Value of gauge or counter."
       ::= {acPMSBCIPGroupOutEstablishedOtherDialogsEntry 3}



     acPMSBCIPGroupOutEstablishedOtherDialogsTotal OBJECT-TYPE
       SYNTAX Counter32
       MAX-ACCESS read-only
       STATUS obsolete
       DESCRIPTION
           "Activity volume."
       ::= {acPMSBCIPGroupOutEstablishedOtherDialogsEntry 4}



     -- ****************************************
     -- acPMSBCIPGroupInAbnormallyTerminatedCalls table declaration
     -- ****************************************
     acPMSBCIPGroupInAbnormallyTerminatedCallsTable OBJECT-TYPE
       SYNTAX SEQUENCE OF AcPMSBCIPGroupInAbnormallyTerminatedCallsEntry
       MAX-ACCESS not-accessible
       STATUS obsolete
       DESCRIPTION
           "Number of incoming abnormally terminated calls per IP group."
       ::= {acPMSbcData 44}



     -- ****************************************
     -- acPMSBCIPGroupInAbnormallyTerminatedCalls table entry
     -- ****************************************
     acPMSBCIPGroupInAbnormallyTerminatedCallsEntry OBJECT-TYPE
       SYNTAX AcPMSBCIPGroupInAbnormallyTerminatedCallsEntry
       MAX-ACCESS not-accessible
       STATUS obsolete
       DESCRIPTION
           ""
       INDEX {acPMSBCIPGroupInAbnormallyTerminatedCallsIpGroup,acPMSBCIPGroupInAbnormallyTerminatedCallsInterval}
       ::= {acPMSBCIPGroupInAbnormallyTerminatedCallsTable 1}



     -- ****************************************
     -- acPMSBCIPGroupInAbnormallyTerminatedCalls TABLE
     -- ****************************************
     AcPMSBCIPGroupInAbnormallyTerminatedCallsEntry ::= SEQUENCE {
       acPMSBCIPGroupInAbnormallyTerminatedCallsIpGroup 
                                                       Unsigned32,
       acPMSBCIPGroupInAbnormallyTerminatedCallsInterval 
                                                       Unsigned32,
       acPMSBCIPGroupInAbnormallyTerminatedCallsVal    Gauge32,
       acPMSBCIPGroupInAbnormallyTerminatedCallsTotal  Counter32
     }



     acPMSBCIPGroupInAbnormallyTerminatedCallsIpGroup OBJECT-TYPE
       SYNTAX Unsigned32 (0..5000)
       MAX-ACCESS not-accessible
       STATUS obsolete
       DESCRIPTION
           "."
       ::= {acPMSBCIPGroupInAbnormallyTerminatedCallsEntry 1}



     acPMSBCIPGroupInAbnormallyTerminatedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAbnormallyTerminatedCallsEntry 2}



     acPMSBCIPGroupInAbnormallyTerminatedCallsVal OBJECT-TYPE
       SYNTAX Gauge32
       MAX-ACCESS read-only
       STATUS obsolete
       DESCRIPTION
           "Value of gauge or counter."
       ::= {acPMSBCIPGroupInAbnormallyTerminatedCallsEntry 3}



     acPMSBCIPGroupInAbnormallyTerminatedCallsTotal OBJECT-TYPE
       SYNTAX Counter32
       MAX-ACCESS read-only
       STATUS obsolete
       DESCRIPTION
           "Activity volume."
       ::= {acPMSBCIPGroupInAbnormallyTerminatedCallsEntry 4}



     -- ****************************************
     -- acPMSBCIPGroupOutAbnormallyTerminatedCalls table declaration
     -- ****************************************
     acPMSBCIPGroupOutAbnormallyTerminatedCallsTable OBJECT-TYPE
       SYNTAX SEQUENCE OF AcPMSBCIPGroupOutAbnormallyTerminatedCallsEntry
       MAX-ACCESS not-accessible
       STATUS obsolete
       DESCRIPTION
           "Number of outgoing abnormally terminated calls per IP group."
       ::= {acPMSbcData 45}



     -- ****************************************
     -- acPMSBCIPGroupOutAbnormallyTerminatedCalls table entry
     -- ****************************************
     acPMSBCIPGroupOutAbnormallyTerminatedCallsEntry OBJECT-TYPE
       SYNTAX AcPMSBCIPGroupOutAbnormallyTerminatedCallsEntry
       MAX-ACCESS not-accessible
       STATUS obsolete
       DESCRIPTION
           ""
       INDEX {acPMSBCIPGroupOutAbnormallyTerminatedCallsIpGroup,acPMSBCIPGroupOutAbnormallyTerminatedCallsInterval}
       ::= {acPMSBCIPGroupOutAbnormallyTerminatedCallsTable 1}



     -- ****************************************
     -- acPMSBCIPGroupOutAbnormallyTerminatedCalls TABLE
     -- ****************************************
     AcPMSBCIPGroupOutAbnormallyTerminatedCallsEntry ::= SEQUENCE {
       acPMSBCIPGroupOutAbnormallyTerminatedCallsIpGroup 
                                                       Unsigned32,
       acPMSBCIPGroupOutAbnormallyTerminatedCallsInterval 
                                                       Unsigned32,
       acPMSBCIPGroupOutAbnormallyTerminatedCallsVal   Gauge32,
       acPMSBCIPGroupOutAbnormallyTerminatedCallsTotal Counter32
     }



     acPMSBCIPGroupOutAbnormallyTerminatedCallsIpGroup OBJECT-TYPE
       SYNTAX Unsigned32 (0..5000)
       MAX-ACCESS not-accessible
       STATUS obsolete
       DESCRIPTION
           "."
       ::= {acPMSBCIPGroupOutAbnormallyTerminatedCallsEntry 1}



     acPMSBCIPGroupOutAbnormallyTerminatedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAbnormallyTerminatedCallsEntry 2}



     acPMSBCIPGroupOutAbnormallyTerminatedCallsVal OBJECT-TYPE
       SYNTAX Gauge32
       MAX-ACCESS read-only
       STATUS obsolete
       DESCRIPTION
           "Value of gauge or counter."
       ::= {acPMSBCIPGroupOutAbnormallyTerminatedCallsEntry 3}



     acPMSBCIPGroupOutAbnormallyTerminatedCallsTotal OBJECT-TYPE
       SYNTAX Counter32
       MAX-ACCESS read-only
       STATUS obsolete
       DESCRIPTION
           "Activity volume."
       ::= {acPMSBCIPGroupOutAbnormallyTerminatedCallsEntry 4}



     -- ****************************************
     -- acPMSBCRegisteredUsers table declaration
     -- ****************************************
     acPMSBCRegisteredUsersTable OBJECT-TYPE
       SYNTAX SEQUENCE OF AcPMSBCRegisteredUsersEntry
       MAX-ACCESS not-accessible
       STATUS obsolete
       DESCRIPTION
           "Number of registered users in SBC."
       ::= {acPMSbcData 46}



     -- ****************************************
     -- acPMSBCRegisteredUsers table entry
     -- ****************************************
     acPMSBCRegisteredUsersEntry OBJECT-TYPE
       SYNTAX AcPMSBCRegisteredUsersEntry
       MAX-ACCESS not-accessible
       STATUS obsolete
       DESCRIPTION
           ""
       INDEX {acPMSBCRegisteredUsersInterval}
       ::= {acPMSBCRegisteredUsersTable 1}



     -- ****************************************
     -- acPMSBCRegisteredUsers TABLE
     -- ****************************************
     AcPMSBCRegisteredUsersEntry ::= SEQUENCE {
       acPMSBCRegisteredUsersInterval                  Unsigned32,
       acPMSBCRegisteredUsersVal                       Gauge32,
       acPMSBCRegisteredUsersAverage                   Unsigned32,
       acPMSBCRegisteredUsersMax                       Unsigned32,
       acPMSBCRegisteredUsersMin                       Unsigned32,
       acPMSBCRegisteredUsersTimeBelowLowThreshold     Unsigned32,
       acPMSBCRegisteredUsersTimeBetweenThresholds     Unsigned32,
       acPMSBCRegisteredUsersTimeAboveHighThreshold    Unsigned32,
       acPMSBCRegisteredUsersTotal                     Counter32
     }



     acPMSBCRegisteredUsersInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCRegisteredUsersEntry 1}



     acPMSBCRegisteredUsersVal OBJECT-TYPE
       SYNTAX Gauge32
       MAX-ACCESS read-only
       STATUS obsolete
       DESCRIPTION
           "Value of gauge or counter."
       ::= {acPMSBCRegisteredUsersEntry 2}



     acPMSBCRegisteredUsersAverage OBJECT-TYPE
       SYNTAX Unsigned32 (0..2147483647)
       MAX-ACCESS read-only
       STATUS obsolete
       DESCRIPTION
           "Average value with in the period time."
       ::= {acPMSBCRegisteredUsersEntry 3}



     acPMSBCRegisteredUsersMax OBJECT-TYPE
       SYNTAX Unsigned32 (0..2147483647)
       MAX-ACCESS read-only
       STATUS obsolete
       DESCRIPTION
           "Maximum value with in the period time."
       ::= {acPMSBCRegisteredUsersEntry 4}



     acPMSBCRegisteredUsersMin OBJECT-TYPE
       SYNTAX Unsigned32 (0..2147483647)
       MAX-ACCESS read-only
       STATUS obsolete
       DESCRIPTION
           "Minimum value with in the period time."
       ::= {acPMSBCRegisteredUsersEntry 5}



     acPMSBCRegisteredUsersTimeBelowLowThreshold OBJECT-TYPE
       SYNTAX Unsigned32 (0..100)
       MAX-ACCESS read-only
       STATUS obsolete
       DESCRIPTION
           "Percent of interval time for which gauge is below what was determined
as the low threshold."
       ::= {acPMSBCRegisteredUsersEntry 6}



     acPMSBCRegisteredUsersTimeBetweenThresholds OBJECT-TYPE
       SYNTAX Unsigned32 (0..100)
       MAX-ACCESS read-only
       STATUS obsolete
       DESCRIPTION
           "Percent of interval time for which gauge is between what were
determined as the low and high thresholds."
       ::= {acPMSBCRegisteredUsersEntry 7}



     acPMSBCRegisteredUsersTimeAboveHighThreshold OBJECT-TYPE
       SYNTAX Unsigned32 (0..100)
       MAX-ACCESS read-only
       STATUS obsolete
       DESCRIPTION
           "Percent of interval time for which gauge is above what was determined
as the high threshold."
       ::= {acPMSBCRegisteredUsersEntry 8}



     acPMSBCRegisteredUsersTotal OBJECT-TYPE
       SYNTAX Counter32
       MAX-ACCESS read-only
       STATUS obsolete
       DESCRIPTION
           "Total."
       ::= {acPMSBCRegisteredUsersEntry 9}



     -- ****************************************
     -- acPMSBCMediaLegs table declaration
     -- ****************************************
     acPMSBCMediaLegsTable OBJECT-TYPE
       SYNTAX SEQUENCE OF AcPMSBCMediaLegsEntry
       MAX-ACCESS not-accessible
       STATUS obsolete
       DESCRIPTION
           "Number of RTP legs."
       ::= {acPMSbcData 47}



     -- ****************************************
     -- acPMSBCMediaLegs table entry
     -- ****************************************
     acPMSBCMediaLegsEntry OBJECT-TYPE
       SYNTAX AcPMSBCMediaLegsEntry
       MAX-ACCESS not-accessible
       STATUS obsolete
       DESCRIPTION
           ""
       INDEX {acPMSBCMediaLegsInterval}
       ::= {acPMSBCMediaLegsTable 1}



     -- ****************************************
     -- acPMSBCMediaLegs TABLE
     -- ****************************************
     AcPMSBCMediaLegsEntry ::= SEQUENCE {
       acPMSBCMediaLegsInterval                        Unsigned32,
       acPMSBCMediaLegsVal                             Gauge32,
       acPMSBCMediaLegsAverage                         Unsigned32,
       acPMSBCMediaLegsMax                             Unsigned32,
       acPMSBCMediaLegsMin                             Unsigned32,
       acPMSBCMediaLegsTimeBelowLowThreshold           Unsigned32,
       acPMSBCMediaLegsTimeBetweenThresholds           Unsigned32,
       acPMSBCMediaLegsTimeAboveHighThreshold          Unsigned32,
       acPMSBCMediaLegsTotal                           Counter32
     }



     acPMSBCMediaLegsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCMediaLegsEntry 1}



     acPMSBCMediaLegsVal OBJECT-TYPE
       SYNTAX Gauge32
       MAX-ACCESS read-only
       STATUS obsolete
       DESCRIPTION
           "Value of gauge or counter."
       ::= {acPMSBCMediaLegsEntry 2}



     acPMSBCMediaLegsAverage OBJECT-TYPE
       SYNTAX Unsigned32 (0..2147483647)
       MAX-ACCESS read-only
       STATUS obsolete
       DESCRIPTION
           "Average value with in the period time."
       ::= {acPMSBCMediaLegsEntry 3}



     acPMSBCMediaLegsMax OBJECT-TYPE
       SYNTAX Unsigned32 (0..2147483647)
       MAX-ACCESS read-only
       STATUS obsolete
       DESCRIPTION
           "Maximum value with in the period time."
       ::= {acPMSBCMediaLegsEntry 4}



     acPMSBCMediaLegsMin OBJECT-TYPE
       SYNTAX Unsigned32 (0..2147483647)
       MAX-ACCESS read-only
       STATUS obsolete
       DESCRIPTION
           "Minimum value with in the period time."
       ::= {acPMSBCMediaLegsEntry 5}



     acPMSBCMediaLegsTimeBelowLowThreshold OBJECT-TYPE
       SYNTAX Unsigned32 (0..100)
       MAX-ACCESS read-only
       STATUS obsolete
       DESCRIPTION
           "Percent of interval time for which gauge is below what was determined
as the low threshold."
       ::= {acPMSBCMediaLegsEntry 6}



     acPMSBCMediaLegsTimeBetweenThresholds OBJECT-TYPE
       SYNTAX Unsigned32 (0..100)
       MAX-ACCESS read-only
       STATUS obsolete
       DESCRIPTION
           "Percent of interval time for which gauge is between what were
determined as the low and high thresholds."
       ::= {acPMSBCMediaLegsEntry 7}



     acPMSBCMediaLegsTimeAboveHighThreshold OBJECT-TYPE
       SYNTAX Unsigned32 (0..100)
       MAX-ACCESS read-only
       STATUS obsolete
       DESCRIPTION
           "Percent of interval time for which gauge is above what was determined
as the high threshold."
       ::= {acPMSBCMediaLegsEntry 8}



     acPMSBCMediaLegsTotal OBJECT-TYPE
       SYNTAX Counter32
       MAX-ACCESS read-only
       STATUS obsolete
       DESCRIPTION
           "Total."
       ::= {acPMSBCMediaLegsEntry 9}



     -- ****************************************
     -- acPMSBCTranscodingSessions table declaration
     -- ****************************************
     acPMSBCTranscodingSessionsTable OBJECT-TYPE
       SYNTAX SEQUENCE OF AcPMSBCTranscodingSessionsEntry
       MAX-ACCESS not-accessible
       STATUS obsolete
       DESCRIPTION
           "number of transcoding sessions in SBC."
       ::= {acPMSbcData 48}



     -- ****************************************
     -- acPMSBCTranscodingSessions table entry
     -- ****************************************
     acPMSBCTranscodingSessionsEntry OBJECT-TYPE
       SYNTAX AcPMSBCTranscodingSessionsEntry
       MAX-ACCESS not-accessible
       STATUS obsolete
       DESCRIPTION
           ""
       INDEX {acPMSBCTranscodingSessionsInterval}
       ::= {acPMSBCTranscodingSessionsTable 1}



     -- ****************************************
     -- acPMSBCTranscodingSessions TABLE
     -- ****************************************
     AcPMSBCTranscodingSessionsEntry ::= SEQUENCE {
       acPMSBCTranscodingSessionsInterval              Unsigned32,
       acPMSBCTranscodingSessionsVal                   Gauge32,
       acPMSBCTranscodingSessionsAverage               Unsigned32,
       acPMSBCTranscodingSessionsMax                   Unsigned32,
       acPMSBCTranscodingSessionsMin                   Unsigned32,
       acPMSBCTranscodingSessionsTimeBelowLowThreshold Unsigned32,
       acPMSBCTranscodingSessionsTimeBetweenThresholds Unsigned32,
       acPMSBCTranscodingSessionsTimeAboveHighThreshold 
                                                       Unsigned32,
       acPMSBCTranscodingSessionsTotal                 Counter32
     }



     acPMSBCTranscodingSessionsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCTranscodingSessionsEntry 1}



     acPMSBCTranscodingSessionsVal OBJECT-TYPE
       SYNTAX Gauge32
       MAX-ACCESS read-only
       STATUS obsolete
       DESCRIPTION
           "Value of gauge or counter."
       ::= {acPMSBCTranscodingSessionsEntry 2}



     acPMSBCTranscodingSessionsAverage OBJECT-TYPE
       SYNTAX Unsigned32 (0..2147483647)
       MAX-ACCESS read-only
       STATUS obsolete
       DESCRIPTION
           "Average value with in the period time."
       ::= {acPMSBCTranscodingSessionsEntry 3}



     acPMSBCTranscodingSessionsMax OBJECT-TYPE
       SYNTAX Unsigned32 (0..2147483647)
       MAX-ACCESS read-only
       STATUS obsolete
       DESCRIPTION
           "Maximum value with in the period time."
       ::= {acPMSBCTranscodingSessionsEntry 4}



     acPMSBCTranscodingSessionsMin OBJECT-TYPE
       SYNTAX Unsigned32 (0..2147483647)
       MAX-ACCESS read-only
       STATUS obsolete
       DESCRIPTION
           "Minimum value with in the period time."
       ::= {acPMSBCTranscodingSessionsEntry 5}



     acPMSBCTranscodingSessionsTimeBelowLowThreshold OBJECT-TYPE
       SYNTAX Unsigned32 (0..100)
       MAX-ACCESS read-only
       STATUS obsolete
       DESCRIPTION
           "Percent of interval time for which gauge is below what was determined
as the low threshold."
       ::= {acPMSBCTranscodingSessionsEntry 6}



     acPMSBCTranscodingSessionsTimeBetweenThresholds OBJECT-TYPE
       SYNTAX Unsigned32 (0..100)
       MAX-ACCESS read-only
       STATUS obsolete
       DESCRIPTION
           "Percent of interval time for which gauge is between what were
determined as the low and high thresholds."
       ::= {acPMSBCTranscodingSessionsEntry 7}



     acPMSBCTranscodingSessionsTimeAboveHighThreshold OBJECT-TYPE
       SYNTAX Unsigned32 (0..100)
       MAX-ACCESS read-only
       STATUS obsolete
       DESCRIPTION
           "Percent of interval time for which gauge is above what was determined
as the high threshold."
       ::= {acPMSBCTranscodingSessionsEntry 8}



     acPMSBCTranscodingSessionsTotal OBJECT-TYPE
       SYNTAX Counter32
       MAX-ACCESS read-only
       STATUS obsolete
       DESCRIPTION
           "Total."
       ::= {acPMSBCTranscodingSessionsEntry 9}



     -- ****************************************
     -- acPMSBCAsr table declaration
     -- ****************************************
     acPMSBCAsrTable OBJECT-TYPE
       SYNTAX SEQUENCE OF AcPMSBCAsrEntry
       MAX-ACCESS not-accessible
       STATUS obsolete
       DESCRIPTION
           "Current ASR global."
       ::= {acPMSbcData 49}



     -- ****************************************
     -- acPMSBCAsr table entry
     -- ****************************************
     acPMSBCAsrEntry OBJECT-TYPE
       SYNTAX AcPMSBCAsrEntry
       MAX-ACCESS not-accessible
       STATUS obsolete
       DESCRIPTION
           ""
       INDEX {acPMSBCAsrInterval}
       ::= {acPMSBCAsrTable 1}



     -- ****************************************
     -- acPMSBCAsr TABLE
     -- ****************************************
     AcPMSBCAsrEntry ::= SEQUENCE {
       acPMSBCAsrInterval                              Unsigned32,
       acPMSBCAsrVal                                   Gauge32,
       acPMSBCAsrAverage                               Unsigned32,
       acPMSBCAsrMax                                   Unsigned32,
       acPMSBCAsrMin                                   Unsigned32
     }



     acPMSBCAsrInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCAsrEntry 1}



     acPMSBCAsrVal OBJECT-TYPE
       SYNTAX Gauge32
       MAX-ACCESS read-only
       STATUS obsolete
       DESCRIPTION
           "Value of gauge or counter."
       ::= {acPMSBCAsrEntry 2}



     acPMSBCAsrAverage OBJECT-TYPE
       SYNTAX Unsigned32 (0..2147483647)
       MAX-ACCESS read-only
       STATUS obsolete
       DESCRIPTION
           "Average value with in the period time."
       ::= {acPMSBCAsrEntry 3}



     acPMSBCAsrMax OBJECT-TYPE
       SYNTAX Unsigned32 (0..2147483647)
       MAX-ACCESS read-only
       STATUS obsolete
       DESCRIPTION
           "Maximum value with in the period time."
       ::= {acPMSBCAsrEntry 4}



     acPMSBCAsrMin OBJECT-TYPE
       SYNTAX Unsigned32 (0..2147483647)
       MAX-ACCESS read-only
       STATUS obsolete
       DESCRIPTION
           "Minimum value with in the period time."
       ::= {acPMSBCAsrEntry 5}



     -- ****************************************
     -- acPMSBCIPGroupAsr table declaration
     -- ****************************************
     acPMSBCIPGroupAsrTable OBJECT-TYPE
       SYNTAX SEQUENCE OF AcPMSBCIPGroupAsrEntry
       MAX-ACCESS not-accessible
       STATUS obsolete
       DESCRIPTION
           "Current ASR per Ipgroup."
       ::= {acPMSbcData 50}



     -- ****************************************
     -- acPMSBCIPGroupAsr table entry
     -- ****************************************
     acPMSBCIPGroupAsrEntry OBJECT-TYPE
       SYNTAX AcPMSBCIPGroupAsrEntry
       MAX-ACCESS not-accessible
       STATUS obsolete
       DESCRIPTION
           ""
       INDEX {acPMSBCIPGroupAsrIndex,acPMSBCIPGroupAsrInterval}
       ::= {acPMSBCIPGroupAsrTable 1}



     -- ****************************************
     -- acPMSBCIPGroupAsr TABLE
     -- ****************************************
     AcPMSBCIPGroupAsrEntry ::= SEQUENCE {
       acPMSBCIPGroupAsrIndex                          Unsigned32,
       acPMSBCIPGroupAsrInterval                       Unsigned32,
       acPMSBCIPGroupAsrVal                            Gauge32,
       acPMSBCIPGroupAsrAverage                        Unsigned32,
       acPMSBCIPGroupAsrMax                            Unsigned32,
       acPMSBCIPGroupAsrMin                            Unsigned32
     }



     acPMSBCIPGroupAsrIndex OBJECT-TYPE
       SYNTAX Unsigned32 (0..1500)
       MAX-ACCESS not-accessible
       STATUS obsolete
       DESCRIPTION
           "IP Group number."
       ::= {acPMSBCIPGroupAsrEntry 1}



     acPMSBCIPGroupAsrInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupAsrEntry 2}



     acPMSBCIPGroupAsrVal OBJECT-TYPE
       SYNTAX Gauge32
       MAX-ACCESS read-only
       STATUS obsolete
       DESCRIPTION
           "Value of gauge or counter."
       ::= {acPMSBCIPGroupAsrEntry 3}



     acPMSBCIPGroupAsrAverage OBJECT-TYPE
       SYNTAX Unsigned32 (0..2147483647)
       MAX-ACCESS read-only
       STATUS obsolete
       DESCRIPTION
           "Average value with in the period time."
       ::= {acPMSBCIPGroupAsrEntry 4}



     acPMSBCIPGroupAsrMax OBJECT-TYPE
       SYNTAX Unsigned32 (0..2147483647)
       MAX-ACCESS read-only
       STATUS obsolete
       DESCRIPTION
           "Maximum value with in the period time."
       ::= {acPMSBCIPGroupAsrEntry 5}



     acPMSBCIPGroupAsrMin OBJECT-TYPE
       SYNTAX Unsigned32 (0..2147483647)
       MAX-ACCESS read-only
       STATUS obsolete
       DESCRIPTION
           "Minimum value with in the period time."
       ::= {acPMSBCIPGroupAsrEntry 6}



     -- ****************************************
     -- acPMSBCSrdAsr table declaration
     -- ****************************************
     acPMSBCSrdAsrTable OBJECT-TYPE
       SYNTAX SEQUENCE OF AcPMSBCSrdAsrEntry
       MAX-ACCESS not-accessible
       STATUS obsolete
       DESCRIPTION
           "Current ASR per SRD."
       ::= {acPMSbcData 51}



     -- ****************************************
     -- acPMSBCSrdAsr table entry
     -- ****************************************
     acPMSBCSrdAsrEntry OBJECT-TYPE
       SYNTAX AcPMSBCSrdAsrEntry
       MAX-ACCESS not-accessible
       STATUS obsolete
       DESCRIPTION
           ""
       INDEX {acPMSBCSrdAsrIndex,acPMSBCSrdAsrInterval}
       ::= {acPMSBCSrdAsrTable 1}



     -- ****************************************
     -- acPMSBCSrdAsr TABLE
     -- ****************************************
     AcPMSBCSrdAsrEntry ::= SEQUENCE {
       acPMSBCSrdAsrIndex                              Unsigned32,
       acPMSBCSrdAsrInterval                           Unsigned32,
       acPMSBCSrdAsrVal                                Gauge32,
       acPMSBCSrdAsrAverage                            Unsigned32,
       acPMSBCSrdAsrMax                                Unsigned32,
       acPMSBCSrdAsrMin                                Unsigned32
     }



     acPMSBCSrdAsrIndex OBJECT-TYPE
       SYNTAX Unsigned32 (0..600)
       MAX-ACCESS not-accessible
       STATUS obsolete
       DESCRIPTION
           "SRD number.
0 is the first SRD."
       ::= {acPMSBCSrdAsrEntry 1}



     acPMSBCSrdAsrInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSrdAsrEntry 2}



     acPMSBCSrdAsrVal OBJECT-TYPE
       SYNTAX Gauge32
       MAX-ACCESS read-only
       STATUS obsolete
       DESCRIPTION
           "Value of gauge or counter."
       ::= {acPMSBCSrdAsrEntry 3}



     acPMSBCSrdAsrAverage OBJECT-TYPE
       SYNTAX Unsigned32 (0..2147483647)
       MAX-ACCESS read-only
       STATUS obsolete
       DESCRIPTION
           "Average value with in the period time."
       ::= {acPMSBCSrdAsrEntry 4}



     acPMSBCSrdAsrMax OBJECT-TYPE
       SYNTAX Unsigned32 (0..2147483647)
       MAX-ACCESS read-only
       STATUS obsolete
       DESCRIPTION
           "Maximum value with in the period time."
       ::= {acPMSBCSrdAsrEntry 5}



     acPMSBCSrdAsrMin OBJECT-TYPE
       SYNTAX Unsigned32 (0..2147483647)
       MAX-ACCESS read-only
       STATUS obsolete
       DESCRIPTION
           "Minimum value with in the period time."
       ::= {acPMSBCSrdAsrEntry 6}



     -- ****************************************
     -- acPMSBCAcd table declaration
     -- ****************************************
     acPMSBCAcdTable OBJECT-TYPE
       SYNTAX SEQUENCE OF AcPMSBCAcdEntry
       MAX-ACCESS not-accessible
       STATUS obsolete
       DESCRIPTION
           "Current ACD global."
       ::= {acPMSbcData 52}



     -- ****************************************
     -- acPMSBCAcd table entry
     -- ****************************************
     acPMSBCAcdEntry OBJECT-TYPE
       SYNTAX AcPMSBCAcdEntry
       MAX-ACCESS not-accessible
       STATUS obsolete
       DESCRIPTION
           ""
       INDEX {acPMSBCAcdInterval}
       ::= {acPMSBCAcdTable 1}



     -- ****************************************
     -- acPMSBCAcd TABLE
     -- ****************************************
     AcPMSBCAcdEntry ::= SEQUENCE {
       acPMSBCAcdInterval                              Unsigned32,
       acPMSBCAcdVal                                   Gauge32,
       acPMSBCAcdAverage                               Unsigned32,
       acPMSBCAcdMax                                   Unsigned32,
       acPMSBCAcdMin                                   Unsigned32
     }



     acPMSBCAcdInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCAcdEntry 1}



     acPMSBCAcdVal OBJECT-TYPE
       SYNTAX Gauge32
       MAX-ACCESS read-only
       STATUS obsolete
       DESCRIPTION
           "Value of gauge or counter."
       ::= {acPMSBCAcdEntry 2}



     acPMSBCAcdAverage OBJECT-TYPE
       SYNTAX Unsigned32 (0..2147483647)
       MAX-ACCESS read-only
       STATUS obsolete
       DESCRIPTION
           "Average value with in the period time."
       ::= {acPMSBCAcdEntry 3}



     acPMSBCAcdMax OBJECT-TYPE
       SYNTAX Unsigned32 (0..2147483647)
       MAX-ACCESS read-only
       STATUS obsolete
       DESCRIPTION
           "Maximum value with in the period time."
       ::= {acPMSBCAcdEntry 4}



     acPMSBCAcdMin OBJECT-TYPE
       SYNTAX Unsigned32 (0..2147483647)
       MAX-ACCESS read-only
       STATUS obsolete
       DESCRIPTION
           "Minimum value with in the period time."
       ::= {acPMSBCAcdEntry 5}



     -- ****************************************
     -- acPMSBCIPGroupAcd table declaration
     -- ****************************************
     acPMSBCIPGroupAcdTable OBJECT-TYPE
       SYNTAX SEQUENCE OF AcPMSBCIPGroupAcdEntry
       MAX-ACCESS not-accessible
       STATUS obsolete
       DESCRIPTION
           "Current ACD per Ipgroup."
       ::= {acPMSbcData 53}



     -- ****************************************
     -- acPMSBCIPGroupAcd table entry
     -- ****************************************
     acPMSBCIPGroupAcdEntry OBJECT-TYPE
       SYNTAX AcPMSBCIPGroupAcdEntry
       MAX-ACCESS not-accessible
       STATUS obsolete
       DESCRIPTION
           ""
       INDEX {acPMSBCIPGroupAcdIndex,acPMSBCIPGroupAcdInterval}
       ::= {acPMSBCIPGroupAcdTable 1}



     -- ****************************************
     -- acPMSBCIPGroupAcd TABLE
     -- ****************************************
     AcPMSBCIPGroupAcdEntry ::= SEQUENCE {
       acPMSBCIPGroupAcdIndex                          Unsigned32,
       acPMSBCIPGroupAcdInterval                       Unsigned32,
       acPMSBCIPGroupAcdVal                            Gauge32,
       acPMSBCIPGroupAcdAverage                        Unsigned32,
       acPMSBCIPGroupAcdMax                            Unsigned32,
       acPMSBCIPGroupAcdMin                            Unsigned32
     }



     acPMSBCIPGroupAcdIndex OBJECT-TYPE
       SYNTAX Unsigned32 (0..1500)
       MAX-ACCESS not-accessible
       STATUS obsolete
       DESCRIPTION
           "IP Group number."
       ::= {acPMSBCIPGroupAcdEntry 1}



     acPMSBCIPGroupAcdInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupAcdEntry 2}



     acPMSBCIPGroupAcdVal OBJECT-TYPE
       SYNTAX Gauge32
       MAX-ACCESS read-only
       STATUS obsolete
       DESCRIPTION
           "Value of gauge or counter."
       ::= {acPMSBCIPGroupAcdEntry 3}



     acPMSBCIPGroupAcdAverage OBJECT-TYPE
       SYNTAX Unsigned32 (0..2147483647)
       MAX-ACCESS read-only
       STATUS obsolete
       DESCRIPTION
           "Average value with in the period time."
       ::= {acPMSBCIPGroupAcdEntry 4}



     acPMSBCIPGroupAcdMax OBJECT-TYPE
       SYNTAX Unsigned32 (0..2147483647)
       MAX-ACCESS read-only
       STATUS obsolete
       DESCRIPTION
           "Maximum value with in the period time."
       ::= {acPMSBCIPGroupAcdEntry 5}



     acPMSBCIPGroupAcdMin OBJECT-TYPE
       SYNTAX Unsigned32 (0..2147483647)
       MAX-ACCESS read-only
       STATUS obsolete
       DESCRIPTION
           "Minimum value with in the period time."
       ::= {acPMSBCIPGroupAcdEntry 6}



     -- ****************************************
     -- acPMSBCSrdAcd table declaration
     -- ****************************************
     acPMSBCSrdAcdTable OBJECT-TYPE
       SYNTAX SEQUENCE OF AcPMSBCSrdAcdEntry
       MAX-ACCESS not-accessible
       STATUS obsolete
       DESCRIPTION
           "Current ACD per SRD."
       ::= {acPMSbcData 54}



     -- ****************************************
     -- acPMSBCSrdAcd table entry
     -- ****************************************
     acPMSBCSrdAcdEntry OBJECT-TYPE
       SYNTAX AcPMSBCSrdAcdEntry
       MAX-ACCESS not-accessible
       STATUS obsolete
       DESCRIPTION
           ""
       INDEX {acPMSBCSrdAcdIndex,acPMSBCSrdAcdInterval}
       ::= {acPMSBCSrdAcdTable 1}



     -- ****************************************
     -- acPMSBCSrdAcd TABLE
     -- ****************************************
     AcPMSBCSrdAcdEntry ::= SEQUENCE {
       acPMSBCSrdAcdIndex                              Unsigned32,
       acPMSBCSrdAcdInterval                           Unsigned32,
       acPMSBCSrdAcdVal                                Gauge32,
       acPMSBCSrdAcdAverage                            Unsigned32,
       acPMSBCSrdAcdMax                                Unsigned32,
       acPMSBCSrdAcdMin                                Unsigned32
     }



     acPMSBCSrdAcdIndex OBJECT-TYPE
       SYNTAX Unsigned32 (0..600)
       MAX-ACCESS not-accessible
       STATUS obsolete
       DESCRIPTION
           "SRD number.
0 is the first SRD."
       ::= {acPMSBCSrdAcdEntry 1}



     acPMSBCSrdAcdInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSrdAcdEntry 2}



     acPMSBCSrdAcdVal OBJECT-TYPE
       SYNTAX Gauge32
       MAX-ACCESS read-only
       STATUS obsolete
       DESCRIPTION
           "Value of gauge or counter."
       ::= {acPMSBCSrdAcdEntry 3}



     acPMSBCSrdAcdAverage OBJECT-TYPE
       SYNTAX Unsigned32 (0..2147483647)
       MAX-ACCESS read-only
       STATUS obsolete
       DESCRIPTION
           "Average value with in the period time."
       ::= {acPMSBCSrdAcdEntry 4}



     acPMSBCSrdAcdMax OBJECT-TYPE
       SYNTAX Unsigned32 (0..2147483647)
       MAX-ACCESS read-only
       STATUS obsolete
       DESCRIPTION
           "Maximum value with in the period time."
       ::= {acPMSBCSrdAcdEntry 5}



     acPMSBCSrdAcdMin OBJECT-TYPE
       SYNTAX Unsigned32 (0..2147483647)
       MAX-ACCESS read-only
       STATUS obsolete
       DESCRIPTION
           "Minimum value with in the period time."
       ::= {acPMSBCSrdAcdEntry 6}



     -- ****************************************
     -- acPMSBCNer table declaration
     -- ****************************************
     acPMSBCNerTable OBJECT-TYPE
       SYNTAX SEQUENCE OF AcPMSBCNerEntry
       MAX-ACCESS not-accessible
       STATUS obsolete
       DESCRIPTION
           "Current NER global."
       ::= {acPMSbcData 55}



     -- ****************************************
     -- acPMSBCNer table entry
     -- ****************************************
     acPMSBCNerEntry OBJECT-TYPE
       SYNTAX AcPMSBCNerEntry
       MAX-ACCESS not-accessible
       STATUS obsolete
       DESCRIPTION
           ""
       INDEX {acPMSBCNerInterval}
       ::= {acPMSBCNerTable 1}



     -- ****************************************
     -- acPMSBCNer TABLE
     -- ****************************************
     AcPMSBCNerEntry ::= SEQUENCE {
       acPMSBCNerInterval                              Unsigned32,
       acPMSBCNerVal                                   Gauge32,
       acPMSBCNerAverage                               Unsigned32,
       acPMSBCNerMax                                   Unsigned32,
       acPMSBCNerMin                                   Unsigned32
     }



     acPMSBCNerInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCNerEntry 1}



     acPMSBCNerVal OBJECT-TYPE
       SYNTAX Gauge32
       MAX-ACCESS read-only
       STATUS obsolete
       DESCRIPTION
           "Value of gauge or counter."
       ::= {acPMSBCNerEntry 2}



     acPMSBCNerAverage OBJECT-TYPE
       SYNTAX Unsigned32 (0..2147483647)
       MAX-ACCESS read-only
       STATUS obsolete
       DESCRIPTION
           "Average value with in the period time."
       ::= {acPMSBCNerEntry 3}



     acPMSBCNerMax OBJECT-TYPE
       SYNTAX Unsigned32 (0..2147483647)
       MAX-ACCESS read-only
       STATUS obsolete
       DESCRIPTION
           "Maximum value with in the period time."
       ::= {acPMSBCNerEntry 4}



     acPMSBCNerMin OBJECT-TYPE
       SYNTAX Unsigned32 (0..2147483647)
       MAX-ACCESS read-only
       STATUS obsolete
       DESCRIPTION
           "Minimum value with in the period time."
       ::= {acPMSBCNerEntry 5}



     -- ****************************************
     -- acPMSBCIPGroupNer table declaration
     -- ****************************************
     acPMSBCIPGroupNerTable OBJECT-TYPE
       SYNTAX SEQUENCE OF AcPMSBCIPGroupNerEntry
       MAX-ACCESS not-accessible
       STATUS obsolete
       DESCRIPTION
           "Current NER per Ipgroup."
       ::= {acPMSbcData 56}



     -- ****************************************
     -- acPMSBCIPGroupNer table entry
     -- ****************************************
     acPMSBCIPGroupNerEntry OBJECT-TYPE
       SYNTAX AcPMSBCIPGroupNerEntry
       MAX-ACCESS not-accessible
       STATUS obsolete
       DESCRIPTION
           ""
       INDEX {acPMSBCIPGroupNerIndex,acPMSBCIPGroupNerInterval}
       ::= {acPMSBCIPGroupNerTable 1}



     -- ****************************************
     -- acPMSBCIPGroupNer TABLE
     -- ****************************************
     AcPMSBCIPGroupNerEntry ::= SEQUENCE {
       acPMSBCIPGroupNerIndex                          Unsigned32,
       acPMSBCIPGroupNerInterval                       Unsigned32,
       acPMSBCIPGroupNerVal                            Gauge32,
       acPMSBCIPGroupNerAverage                        Unsigned32,
       acPMSBCIPGroupNerMax                            Unsigned32,
       acPMSBCIPGroupNerMin                            Unsigned32
     }



     acPMSBCIPGroupNerIndex OBJECT-TYPE
       SYNTAX Unsigned32 (0..1500)
       MAX-ACCESS not-accessible
       STATUS obsolete
       DESCRIPTION
           "IP Group number."
       ::= {acPMSBCIPGroupNerEntry 1}



     acPMSBCIPGroupNerInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupNerEntry 2}



     acPMSBCIPGroupNerVal OBJECT-TYPE
       SYNTAX Gauge32
       MAX-ACCESS read-only
       STATUS obsolete
       DESCRIPTION
           "Value of gauge or counter."
       ::= {acPMSBCIPGroupNerEntry 3}



     acPMSBCIPGroupNerAverage OBJECT-TYPE
       SYNTAX Unsigned32 (0..2147483647)
       MAX-ACCESS read-only
       STATUS obsolete
       DESCRIPTION
           "Average value with in the period time."
       ::= {acPMSBCIPGroupNerEntry 4}



     acPMSBCIPGroupNerMax OBJECT-TYPE
       SYNTAX Unsigned32 (0..2147483647)
       MAX-ACCESS read-only
       STATUS obsolete
       DESCRIPTION
           "Maximum value with in the period time."
       ::= {acPMSBCIPGroupNerEntry 5}



     acPMSBCIPGroupNerMin OBJECT-TYPE
       SYNTAX Unsigned32 (0..2147483647)
       MAX-ACCESS read-only
       STATUS obsolete
       DESCRIPTION
           "Minimum value with in the period time."
       ::= {acPMSBCIPGroupNerEntry 6}



     -- ****************************************
     -- acPMSBCSrdNer table declaration
     -- ****************************************
     acPMSBCSrdNerTable OBJECT-TYPE
       SYNTAX SEQUENCE OF AcPMSBCSrdNerEntry
       MAX-ACCESS not-accessible
       STATUS obsolete
       DESCRIPTION
           "Current NER per SRD."
       ::= {acPMSbcData 57}



     -- ****************************************
     -- acPMSBCSrdNer table entry
     -- ****************************************
     acPMSBCSrdNerEntry OBJECT-TYPE
       SYNTAX AcPMSBCSrdNerEntry
       MAX-ACCESS not-accessible
       STATUS obsolete
       DESCRIPTION
           ""
       INDEX {acPMSBCSrdNerIndex,acPMSBCSrdNerInterval}
       ::= {acPMSBCSrdNerTable 1}



     -- ****************************************
     -- acPMSBCSrdNer TABLE
     -- ****************************************
     AcPMSBCSrdNerEntry ::= SEQUENCE {
       acPMSBCSrdNerIndex                              Unsigned32,
       acPMSBCSrdNerInterval                           Unsigned32,
       acPMSBCSrdNerVal                                Gauge32,
       acPMSBCSrdNerAverage                            Unsigned32,
       acPMSBCSrdNerMax                                Unsigned32,
       acPMSBCSrdNerMin                                Unsigned32
     }



     acPMSBCSrdNerIndex OBJECT-TYPE
       SYNTAX Unsigned32 (0..600)
       MAX-ACCESS not-accessible
       STATUS obsolete
       DESCRIPTION
           "SRD number.
0 is the first SRD."
       ::= {acPMSBCSrdNerEntry 1}



     acPMSBCSrdNerInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSrdNerEntry 2}



     acPMSBCSrdNerVal OBJECT-TYPE
       SYNTAX Gauge32
       MAX-ACCESS read-only
       STATUS obsolete
       DESCRIPTION
           "Value of gauge or counter."
       ::= {acPMSBCSrdNerEntry 3}



     acPMSBCSrdNerAverage OBJECT-TYPE
       SYNTAX Unsigned32 (0..2147483647)
       MAX-ACCESS read-only
       STATUS obsolete
       DESCRIPTION
           "Average value with in the period time."
       ::= {acPMSBCSrdNerEntry 4}



     acPMSBCSrdNerMax OBJECT-TYPE
       SYNTAX Unsigned32 (0..2147483647)
       MAX-ACCESS read-only
       STATUS obsolete
       DESCRIPTION
           "Maximum value with in the period time."
       ::= {acPMSBCSrdNerEntry 5}



     acPMSBCSrdNerMin OBJECT-TYPE
       SYNTAX Unsigned32 (0..2147483647)
       MAX-ACCESS read-only
       STATUS obsolete
       DESCRIPTION
           "Minimum value with in the period time."
       ::= {acPMSBCSrdNerEntry 6}



     -- ****************************************
     -- acPMSBCLadLegs table declaration
     -- ****************************************
     acPMSBCLadLegsTable OBJECT-TYPE
       SYNTAX SEQUENCE OF AcPMSBCLadLegsEntry
       MAX-ACCESS not-accessible
       STATUS obsolete
       DESCRIPTION
           "Number of LAD legs used."
       ::= {acPMSbcData 58}



     -- ****************************************
     -- acPMSBCLadLegs table entry
     -- ****************************************
     acPMSBCLadLegsEntry OBJECT-TYPE
       SYNTAX AcPMSBCLadLegsEntry
       MAX-ACCESS not-accessible
       STATUS obsolete
       DESCRIPTION
           ""
       INDEX {acPMSBCLadLegsInterval}
       ::= {acPMSBCLadLegsTable 1}



     -- ****************************************
     -- acPMSBCLadLegs TABLE
     -- ****************************************
     AcPMSBCLadLegsEntry ::= SEQUENCE {
       acPMSBCLadLegsInterval                          Unsigned32,
       acPMSBCLadLegsVal                               Counter32,
       acPMSBCLadLegsAverage                           Unsigned32,
       acPMSBCLadLegsMax                               Unsigned32,
       acPMSBCLadLegsMin                               Unsigned32
     }



     acPMSBCLadLegsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCLadLegsEntry 1}



     acPMSBCLadLegsVal OBJECT-TYPE
       SYNTAX Counter32
       MAX-ACCESS read-only
       STATUS obsolete
       DESCRIPTION
           "Value of gauge or counter."
       ::= {acPMSBCLadLegsEntry 2}



     acPMSBCLadLegsAverage OBJECT-TYPE
       SYNTAX Unsigned32 (0..2147483647)
       MAX-ACCESS read-only
       STATUS obsolete
       DESCRIPTION
           "Average value with in the period time."
       ::= {acPMSBCLadLegsEntry 3}



     acPMSBCLadLegsMax OBJECT-TYPE
       SYNTAX Unsigned32 (0..2147483647)
       MAX-ACCESS read-only
       STATUS obsolete
       DESCRIPTION
           "Maximum value with in the period time."
       ::= {acPMSBCLadLegsEntry 4}



     acPMSBCLadLegsMin OBJECT-TYPE
       SYNTAX Unsigned32 (0..2147483647)
       MAX-ACCESS read-only
       STATUS obsolete
       DESCRIPTION
           "Minimum value with in the period time."
       ::= {acPMSBCLadLegsEntry 5}



     -- ****************************************
     -- acPMSBCInCaps table declaration
     -- ****************************************
     acPMSBCInCapsTable OBJECT-TYPE
       SYNTAX SEQUENCE OF AcPMSBCInCapsEntry
       MAX-ACCESS not-accessible
       STATUS obsolete
       DESCRIPTION
           "Total No of CAPS (calls per second) in incoming leg."
       ::= {acPMSbcData 59}



     -- ****************************************
     -- acPMSBCInCaps table entry
     -- ****************************************
     acPMSBCInCapsEntry OBJECT-TYPE
       SYNTAX AcPMSBCInCapsEntry
       MAX-ACCESS not-accessible
       STATUS obsolete
       DESCRIPTION
           ""
       INDEX {acPMSBCInCapsInterval}
       ::= {acPMSBCInCapsTable 1}



     -- ****************************************
     -- acPMSBCInCaps TABLE
     -- ****************************************
     AcPMSBCInCapsEntry ::= SEQUENCE {
       acPMSBCInCapsInterval                           Unsigned32,
       acPMSBCInCapsVal                                Gauge32,
       acPMSBCInCapsAverage                            Unsigned32,
       acPMSBCInCapsMax                                Unsigned32,
       acPMSBCInCapsMin                                Unsigned32
     }



     acPMSBCInCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInCapsEntry 1}



     acPMSBCInCapsVal OBJECT-TYPE
       SYNTAX Gauge32
       MAX-ACCESS read-only
       STATUS obsolete
       DESCRIPTION
           "Value of gauge or counter."
       ::= {acPMSBCInCapsEntry 2}



     acPMSBCInCapsAverage OBJECT-TYPE
       SYNTAX Unsigned32 (0..2147483647)
       MAX-ACCESS read-only
       STATUS obsolete
       DESCRIPTION
           "Average value with in the period time."
       ::= {acPMSBCInCapsEntry 3}



     acPMSBCInCapsMax OBJECT-TYPE
       SYNTAX Unsigned32 (0..2147483647)
       MAX-ACCESS read-only
       STATUS obsolete
       DESCRIPTION
           "Maximum value with in the period time."
       ::= {acPMSBCInCapsEntry 4}



     acPMSBCInCapsMin OBJECT-TYPE
       SYNTAX Unsigned32 (0..2147483647)
       MAX-ACCESS read-only
       STATUS obsolete
       DESCRIPTION
           "Minimum value with in the period time."
       ::= {acPMSBCInCapsEntry 5}



     -- ****************************************
     -- acPMSBCOutCaps table declaration
     -- ****************************************
     acPMSBCOutCapsTable OBJECT-TYPE
       SYNTAX SEQUENCE OF AcPMSBCOutCapsEntry
       MAX-ACCESS not-accessible
       STATUS obsolete
       DESCRIPTION
           "Total No of CAPS (calls per second) in outoging leg."
       ::= {acPMSbcData 60}



     -- ****************************************
     -- acPMSBCOutCaps table entry
     -- ****************************************
     acPMSBCOutCapsEntry OBJECT-TYPE
       SYNTAX AcPMSBCOutCapsEntry
       MAX-ACCESS not-accessible
       STATUS obsolete
       DESCRIPTION
           ""
       INDEX {acPMSBCOutCapsInterval}
       ::= {acPMSBCOutCapsTable 1}



     -- ****************************************
     -- acPMSBCOutCaps TABLE
     -- ****************************************
     AcPMSBCOutCapsEntry ::= SEQUENCE {
       acPMSBCOutCapsInterval                          Unsigned32,
       acPMSBCOutCapsVal                               Gauge32,
       acPMSBCOutCapsAverage                           Unsigned32,
       acPMSBCOutCapsMax                               Unsigned32,
       acPMSBCOutCapsMin                               Unsigned32
     }



     acPMSBCOutCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutCapsEntry 1}



     acPMSBCOutCapsVal OBJECT-TYPE
       SYNTAX Gauge32
       MAX-ACCESS read-only
       STATUS obsolete
       DESCRIPTION
           "Value of gauge or counter."
       ::= {acPMSBCOutCapsEntry 2}



     acPMSBCOutCapsAverage OBJECT-TYPE
       SYNTAX Unsigned32 (0..2147483647)
       MAX-ACCESS read-only
       STATUS obsolete
       DESCRIPTION
           "Average value with in the period time."
       ::= {acPMSBCOutCapsEntry 3}



     acPMSBCOutCapsMax OBJECT-TYPE
       SYNTAX Unsigned32 (0..2147483647)
       MAX-ACCESS read-only
       STATUS obsolete
       DESCRIPTION
           "Maximum value with in the period time."
       ::= {acPMSBCOutCapsEntry 4}



     acPMSBCOutCapsMin OBJECT-TYPE
       SYNTAX Unsigned32 (0..2147483647)
       MAX-ACCESS read-only
       STATUS obsolete
       DESCRIPTION
           "Minimum value with in the period time."
       ::= {acPMSBCOutCapsEntry 5}



     -- ****************************************
     -- acPMSBCIPGroupInCaps table declaration
     -- ****************************************
     acPMSBCIPGroupInCapsTable OBJECT-TYPE
       SYNTAX SEQUENCE OF AcPMSBCIPGroupInCapsEntry
       MAX-ACCESS not-accessible
       STATUS obsolete
       DESCRIPTION
           "Total No of CAPS (calls per second) in incoming leg per IpGroup."
       ::= {acPMSbcData 61}



     -- ****************************************
     -- acPMSBCIPGroupInCaps table entry
     -- ****************************************
     acPMSBCIPGroupInCapsEntry OBJECT-TYPE
       SYNTAX AcPMSBCIPGroupInCapsEntry
       MAX-ACCESS not-accessible
       STATUS obsolete
       DESCRIPTION
           ""
       INDEX {acPMSBCIPGroupInCapsIndex,acPMSBCIPGroupInCapsInterval}
       ::= {acPMSBCIPGroupInCapsTable 1}



     -- ****************************************
     -- acPMSBCIPGroupInCaps TABLE
     -- ****************************************
     AcPMSBCIPGroupInCapsEntry ::= SEQUENCE {
       acPMSBCIPGroupInCapsIndex                       Unsigned32,
       acPMSBCIPGroupInCapsInterval                    Unsigned32,
       acPMSBCIPGroupInCapsVal                         Gauge32,
       acPMSBCIPGroupInCapsAverage                     Unsigned32,
       acPMSBCIPGroupInCapsMax                         Unsigned32,
       acPMSBCIPGroupInCapsMin                         Unsigned32
     }



     acPMSBCIPGroupInCapsIndex OBJECT-TYPE
       SYNTAX Unsigned32 (0..1500)
       MAX-ACCESS not-accessible
       STATUS obsolete
       DESCRIPTION
           "IP Group number."
       ::= {acPMSBCIPGroupInCapsEntry 1}



     acPMSBCIPGroupInCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInCapsEntry 2}



     acPMSBCIPGroupInCapsVal OBJECT-TYPE
       SYNTAX Gauge32
       MAX-ACCESS read-only
       STATUS obsolete
       DESCRIPTION
           "Value of gauge or counter."
       ::= {acPMSBCIPGroupInCapsEntry 3}



     acPMSBCIPGroupInCapsAverage OBJECT-TYPE
       SYNTAX Unsigned32 (0..2147483647)
       MAX-ACCESS read-only
       STATUS obsolete
       DESCRIPTION
           "Average value with in the period time."
       ::= {acPMSBCIPGroupInCapsEntry 4}



     acPMSBCIPGroupInCapsMax OBJECT-TYPE
       SYNTAX Unsigned32 (0..2147483647)
       MAX-ACCESS read-only
       STATUS obsolete
       DESCRIPTION
           "Maximum value with in the period time."
       ::= {acPMSBCIPGroupInCapsEntry 5}



     acPMSBCIPGroupInCapsMin OBJECT-TYPE
       SYNTAX Unsigned32 (0..2147483647)
       MAX-ACCESS read-only
       STATUS obsolete
       DESCRIPTION
           "Minimum value with in the period time."
       ::= {acPMSBCIPGroupInCapsEntry 6}



     -- ****************************************
     -- acPMSBCIPGroupOutCaps table declaration
     -- ****************************************
     acPMSBCIPGroupOutCapsTable OBJECT-TYPE
       SYNTAX SEQUENCE OF AcPMSBCIPGroupOutCapsEntry
       MAX-ACCESS not-accessible
       STATUS obsolete
       DESCRIPTION
           "Total No of CAPS (calls per second) in outgoing leg per IpGroup."
       ::= {acPMSbcData 62}



     -- ****************************************
     -- acPMSBCIPGroupOutCaps table entry
     -- ****************************************
     acPMSBCIPGroupOutCapsEntry OBJECT-TYPE
       SYNTAX AcPMSBCIPGroupOutCapsEntry
       MAX-ACCESS not-accessible
       STATUS obsolete
       DESCRIPTION
           ""
       INDEX {acPMSBCIPGroupOutCapsIndex,acPMSBCIPGroupOutCapsInterval}
       ::= {acPMSBCIPGroupOutCapsTable 1}



     -- ****************************************
     -- acPMSBCIPGroupOutCaps TABLE
     -- ****************************************
     AcPMSBCIPGroupOutCapsEntry ::= SEQUENCE {
       acPMSBCIPGroupOutCapsIndex                      Unsigned32,
       acPMSBCIPGroupOutCapsInterval                   Unsigned32,
       acPMSBCIPGroupOutCapsVal                        Gauge32,
       acPMSBCIPGroupOutCapsAverage                    Unsigned32,
       acPMSBCIPGroupOutCapsMax                        Unsigned32,
       acPMSBCIPGroupOutCapsMin                        Unsigned32
     }



     acPMSBCIPGroupOutCapsIndex OBJECT-TYPE
       SYNTAX Unsigned32 (0..1500)
       MAX-ACCESS not-accessible
       STATUS obsolete
       DESCRIPTION
           "IP Group number."
       ::= {acPMSBCIPGroupOutCapsEntry 1}



     acPMSBCIPGroupOutCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutCapsEntry 2}



     acPMSBCIPGroupOutCapsVal OBJECT-TYPE
       SYNTAX Gauge32
       MAX-ACCESS read-only
       STATUS obsolete
       DESCRIPTION
           "Value of gauge or counter."
       ::= {acPMSBCIPGroupOutCapsEntry 3}



     acPMSBCIPGroupOutCapsAverage OBJECT-TYPE
       SYNTAX Unsigned32 (0..2147483647)
       MAX-ACCESS read-only
       STATUS obsolete
       DESCRIPTION
           "Average value with in the period time."
       ::= {acPMSBCIPGroupOutCapsEntry 4}



     acPMSBCIPGroupOutCapsMax OBJECT-TYPE
       SYNTAX Unsigned32 (0..2147483647)
       MAX-ACCESS read-only
       STATUS obsolete
       DESCRIPTION
           "Maximum value with in the period time."
       ::= {acPMSBCIPGroupOutCapsEntry 5}



     acPMSBCIPGroupOutCapsMin OBJECT-TYPE
       SYNTAX Unsigned32 (0..2147483647)
       MAX-ACCESS read-only
       STATUS obsolete
       DESCRIPTION
           "Minimum value with in the period time."
       ::= {acPMSBCIPGroupOutCapsEntry 6}



     -- ****************************************
     -- acPMSBCSrdInCaps table declaration
     -- ****************************************
     acPMSBCSrdInCapsTable OBJECT-TYPE
       SYNTAX SEQUENCE OF AcPMSBCSrdInCapsEntry
       MAX-ACCESS not-accessible
       STATUS obsolete
       DESCRIPTION
           "Total No of CAPS (calls per second) in incoming leg per SRD."
       ::= {acPMSbcData 63}



     -- ****************************************
     -- acPMSBCSrdInCaps table entry
     -- ****************************************
     acPMSBCSrdInCapsEntry OBJECT-TYPE
       SYNTAX AcPMSBCSrdInCapsEntry
       MAX-ACCESS not-accessible
       STATUS obsolete
       DESCRIPTION
           ""
       INDEX {acPMSBCSrdInCapsIndex,acPMSBCSrdInCapsInterval}
       ::= {acPMSBCSrdInCapsTable 1}



     -- ****************************************
     -- acPMSBCSrdInCaps TABLE
     -- ****************************************
     AcPMSBCSrdInCapsEntry ::= SEQUENCE {
       acPMSBCSrdInCapsIndex                           Unsigned32,
       acPMSBCSrdInCapsInterval                        Unsigned32,
       acPMSBCSrdInCapsVal                             Gauge32,
       acPMSBCSrdInCapsAverage                         Unsigned32,
       acPMSBCSrdInCapsMax                             Unsigned32,
       acPMSBCSrdInCapsMin                             Unsigned32
     }



     acPMSBCSrdInCapsIndex OBJECT-TYPE
       SYNTAX Unsigned32 (0..600)
       MAX-ACCESS not-accessible
       STATUS obsolete
       DESCRIPTION
           "SRD number.
0 is the first SRD."
       ::= {acPMSBCSrdInCapsEntry 1}



     acPMSBCSrdInCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSrdInCapsEntry 2}



     acPMSBCSrdInCapsVal OBJECT-TYPE
       SYNTAX Gauge32
       MAX-ACCESS read-only
       STATUS obsolete
       DESCRIPTION
           "Value of gauge or counter."
       ::= {acPMSBCSrdInCapsEntry 3}



     acPMSBCSrdInCapsAverage OBJECT-TYPE
       SYNTAX Unsigned32 (0..2147483647)
       MAX-ACCESS read-only
       STATUS obsolete
       DESCRIPTION
           "Average value with in the period time."
       ::= {acPMSBCSrdInCapsEntry 4}



     acPMSBCSrdInCapsMax OBJECT-TYPE
       SYNTAX Unsigned32 (0..2147483647)
       MAX-ACCESS read-only
       STATUS obsolete
       DESCRIPTION
           "Maximum value with in the period time."
       ::= {acPMSBCSrdInCapsEntry 5}



     acPMSBCSrdInCapsMin OBJECT-TYPE
       SYNTAX Unsigned32 (0..2147483647)
       MAX-ACCESS read-only
       STATUS obsolete
       DESCRIPTION
           "Minimum value with in the period time."
       ::= {acPMSBCSrdInCapsEntry 6}



     -- ****************************************
     -- acPMSBCSrdOutCaps table declaration
     -- ****************************************
     acPMSBCSrdOutCapsTable OBJECT-TYPE
       SYNTAX SEQUENCE OF AcPMSBCSrdOutCapsEntry
       MAX-ACCESS not-accessible
       STATUS obsolete
       DESCRIPTION
           "Total No of CAPS (calls per second) in outgoing leg per SRD."
       ::= {acPMSbcData 64}



     -- ****************************************
     -- acPMSBCSrdOutCaps table entry
     -- ****************************************
     acPMSBCSrdOutCapsEntry OBJECT-TYPE
       SYNTAX AcPMSBCSrdOutCapsEntry
       MAX-ACCESS not-accessible
       STATUS obsolete
       DESCRIPTION
           ""
       INDEX {acPMSBCSrdOutCapsIndex,acPMSBCSrdOutCapsInterval}
       ::= {acPMSBCSrdOutCapsTable 1}



     -- ****************************************
     -- acPMSBCSrdOutCaps TABLE
     -- ****************************************
     AcPMSBCSrdOutCapsEntry ::= SEQUENCE {
       acPMSBCSrdOutCapsIndex                          Unsigned32,
       acPMSBCSrdOutCapsInterval                       Unsigned32,
       acPMSBCSrdOutCapsVal                            Gauge32,
       acPMSBCSrdOutCapsAverage                        Unsigned32,
       acPMSBCSrdOutCapsMax                            Unsigned32,
       acPMSBCSrdOutCapsMin                            Unsigned32
     }



     acPMSBCSrdOutCapsIndex OBJECT-TYPE
       SYNTAX Unsigned32 (0..600)
       MAX-ACCESS not-accessible
       STATUS obsolete
       DESCRIPTION
           "SRD number.
0 is the first SRD."
       ::= {acPMSBCSrdOutCapsEntry 1}



     acPMSBCSrdOutCapsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSrdOutCapsEntry 2}



     acPMSBCSrdOutCapsVal OBJECT-TYPE
       SYNTAX Gauge32
       MAX-ACCESS read-only
       STATUS obsolete
       DESCRIPTION
           "Value of gauge or counter."
       ::= {acPMSBCSrdOutCapsEntry 3}



     acPMSBCSrdOutCapsAverage OBJECT-TYPE
       SYNTAX Unsigned32 (0..2147483647)
       MAX-ACCESS read-only
       STATUS obsolete
       DESCRIPTION
           "Average value with in the period time."
       ::= {acPMSBCSrdOutCapsEntry 4}



     acPMSBCSrdOutCapsMax OBJECT-TYPE
       SYNTAX Unsigned32 (0..2147483647)
       MAX-ACCESS read-only
       STATUS obsolete
       DESCRIPTION
           "Maximum value with in the period time."
       ::= {acPMSBCSrdOutCapsEntry 5}



     acPMSBCSrdOutCapsMin OBJECT-TYPE
       SYNTAX Unsigned32 (0..2147483647)
       MAX-ACCESS read-only
       STATUS obsolete
       DESCRIPTION
           "Minimum value with in the period time."
       ::= {acPMSBCSrdOutCapsEntry 6}



     -- ****************************************
     -- acPMSBCInAttemptedCalls table declaration
     -- ****************************************
     acPMSBCInAttemptedCallsTable OBJECT-TYPE
       SYNTAX SEQUENCE OF AcPMSBCInAttemptedCallsEntry
       MAX-ACCESS not-accessible
       STATUS obsolete
       DESCRIPTION
           "Number of incoming call attempts."
       ::= {acPMSbcData 65}



     -- ****************************************
     -- acPMSBCInAttemptedCalls table entry
     -- ****************************************
     acPMSBCInAttemptedCallsEntry OBJECT-TYPE
       SYNTAX AcPMSBCInAttemptedCallsEntry
       MAX-ACCESS not-accessible
       STATUS obsolete
       DESCRIPTION
           ""
       INDEX {acPMSBCInAttemptedCallsInterval}
       ::= {acPMSBCInAttemptedCallsTable 1}



     -- ****************************************
     -- acPMSBCInAttemptedCalls TABLE
     -- ****************************************
     AcPMSBCInAttemptedCallsEntry ::= SEQUENCE {
       acPMSBCInAttemptedCallsInterval                 Unsigned32,
       acPMSBCInAttemptedCallsVal                      Counter32,
       acPMSBCInAttemptedCallsTotal                    Counter32
     }



     acPMSBCInAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInAttemptedCallsEntry 1}



     acPMSBCInAttemptedCallsVal OBJECT-TYPE
       SYNTAX Counter32
       MAX-ACCESS read-only
       STATUS obsolete
       DESCRIPTION
           "Value of gauge or counter."
       ::= {acPMSBCInAttemptedCallsEntry 2}



     acPMSBCInAttemptedCallsTotal OBJECT-TYPE
       SYNTAX Counter32
       MAX-ACCESS read-only
       STATUS obsolete
       DESCRIPTION
           "Activity volume."
       ::= {acPMSBCInAttemptedCallsEntry 3}



     -- ****************************************
     -- acPMSBCSRDInAttemptedCalls table declaration
     -- ****************************************
     acPMSBCSRDInAttemptedCallsTable OBJECT-TYPE
       SYNTAX SEQUENCE OF AcPMSBCSRDInAttemptedCallsEntry
       MAX-ACCESS not-accessible
       STATUS obsolete
       DESCRIPTION
           "Number of incoming call attempts per SRD."
       ::= {acPMSbcData 66}



     -- ****************************************
     -- acPMSBCSRDInAttemptedCalls table entry
     -- ****************************************
     acPMSBCSRDInAttemptedCallsEntry OBJECT-TYPE
       SYNTAX AcPMSBCSRDInAttemptedCallsEntry
       MAX-ACCESS not-accessible
       STATUS obsolete
       DESCRIPTION
           ""
       INDEX {acPMSBCSRDInAttemptedCallsSrdID,acPMSBCSRDInAttemptedCallsInterval}
       ::= {acPMSBCSRDInAttemptedCallsTable 1}



     -- ****************************************
     -- acPMSBCSRDInAttemptedCalls TABLE
     -- ****************************************
     AcPMSBCSRDInAttemptedCallsEntry ::= SEQUENCE {
       acPMSBCSRDInAttemptedCallsSrdID                 Unsigned32,
       acPMSBCSRDInAttemptedCallsInterval              Unsigned32,
       acPMSBCSRDInAttemptedCallsVal                   Counter32,
       acPMSBCSRDInAttemptedCallsTotal                 Counter32
     }



     acPMSBCSRDInAttemptedCallsSrdID OBJECT-TYPE
       SYNTAX Unsigned32 (0..600)
       MAX-ACCESS not-accessible
       STATUS obsolete
       DESCRIPTION
           "."
       ::= {acPMSBCSRDInAttemptedCallsEntry 1}



     acPMSBCSRDInAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInAttemptedCallsEntry 2}



     acPMSBCSRDInAttemptedCallsVal OBJECT-TYPE
       SYNTAX Counter32
       MAX-ACCESS read-only
       STATUS obsolete
       DESCRIPTION
           "Value of gauge or counter."
       ::= {acPMSBCSRDInAttemptedCallsEntry 3}



     acPMSBCSRDInAttemptedCallsTotal OBJECT-TYPE
       SYNTAX Counter32
       MAX-ACCESS read-only
       STATUS obsolete
       DESCRIPTION
           "Activity volume."
       ::= {acPMSBCSRDInAttemptedCallsEntry 4}



     -- ****************************************
     -- acPMSBCOutAttemptedCalls table declaration
     -- ****************************************
     acPMSBCOutAttemptedCallsTable OBJECT-TYPE
       SYNTAX SEQUENCE OF AcPMSBCOutAttemptedCallsEntry
       MAX-ACCESS not-accessible
       STATUS obsolete
       DESCRIPTION
           "Number of outgoing call attempts."
       ::= {acPMSbcData 67}



     -- ****************************************
     -- acPMSBCOutAttemptedCalls table entry
     -- ****************************************
     acPMSBCOutAttemptedCallsEntry OBJECT-TYPE
       SYNTAX AcPMSBCOutAttemptedCallsEntry
       MAX-ACCESS not-accessible
       STATUS obsolete
       DESCRIPTION
           ""
       INDEX {acPMSBCOutAttemptedCallsInterval}
       ::= {acPMSBCOutAttemptedCallsTable 1}



     -- ****************************************
     -- acPMSBCOutAttemptedCalls TABLE
     -- ****************************************
     AcPMSBCOutAttemptedCallsEntry ::= SEQUENCE {
       acPMSBCOutAttemptedCallsInterval                Unsigned32,
       acPMSBCOutAttemptedCallsVal                     Counter32,
       acPMSBCOutAttemptedCallsTotal                   Counter32
     }



     acPMSBCOutAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutAttemptedCallsEntry 1}



     acPMSBCOutAttemptedCallsVal OBJECT-TYPE
       SYNTAX Counter32
       MAX-ACCESS read-only
       STATUS obsolete
       DESCRIPTION
           "Value of gauge or counter."
       ::= {acPMSBCOutAttemptedCallsEntry 2}



     acPMSBCOutAttemptedCallsTotal OBJECT-TYPE
       SYNTAX Counter32
       MAX-ACCESS read-only
       STATUS obsolete
       DESCRIPTION
           "Activity volume."
       ::= {acPMSBCOutAttemptedCallsEntry 3}



     -- ****************************************
     -- acPMSBCSRDOutAttemptedCalls table declaration
     -- ****************************************
     acPMSBCSRDOutAttemptedCallsTable OBJECT-TYPE
       SYNTAX SEQUENCE OF AcPMSBCSRDOutAttemptedCallsEntry
       MAX-ACCESS not-accessible
       STATUS obsolete
       DESCRIPTION
           "Number of outgoing call attempts per SRD."
       ::= {acPMSbcData 68}



     -- ****************************************
     -- acPMSBCSRDOutAttemptedCalls table entry
     -- ****************************************
     acPMSBCSRDOutAttemptedCallsEntry OBJECT-TYPE
       SYNTAX AcPMSBCSRDOutAttemptedCallsEntry
       MAX-ACCESS not-accessible
       STATUS obsolete
       DESCRIPTION
           ""
       INDEX {acPMSBCSRDOutAttemptedCallsSrdID,acPMSBCSRDOutAttemptedCallsInterval}
       ::= {acPMSBCSRDOutAttemptedCallsTable 1}



     -- ****************************************
     -- acPMSBCSRDOutAttemptedCalls TABLE
     -- ****************************************
     AcPMSBCSRDOutAttemptedCallsEntry ::= SEQUENCE {
       acPMSBCSRDOutAttemptedCallsSrdID                Unsigned32,
       acPMSBCSRDOutAttemptedCallsInterval             Unsigned32,
       acPMSBCSRDOutAttemptedCallsVal                  Counter32,
       acPMSBCSRDOutAttemptedCallsTotal                Counter32
     }



     acPMSBCSRDOutAttemptedCallsSrdID OBJECT-TYPE
       SYNTAX Unsigned32 (0..600)
       MAX-ACCESS not-accessible
       STATUS obsolete
       DESCRIPTION
           "."
       ::= {acPMSBCSRDOutAttemptedCallsEntry 1}



     acPMSBCSRDOutAttemptedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutAttemptedCallsEntry 2}



     acPMSBCSRDOutAttemptedCallsVal OBJECT-TYPE
       SYNTAX Counter32
       MAX-ACCESS read-only
       STATUS obsolete
       DESCRIPTION
           "Value of gauge or counter."
       ::= {acPMSBCSRDOutAttemptedCallsEntry 3}



     acPMSBCSRDOutAttemptedCallsTotal OBJECT-TYPE
       SYNTAX Counter32
       MAX-ACCESS read-only
       STATUS obsolete
       DESCRIPTION
           "Activity volume."
       ::= {acPMSBCSRDOutAttemptedCallsEntry 4}



     -- ****************************************
     -- acPMSBCInEstablishedCalls table declaration
     -- ****************************************
     acPMSBCInEstablishedCallsTable OBJECT-TYPE
       SYNTAX SEQUENCE OF AcPMSBCInEstablishedCallsEntry
       MAX-ACCESS not-accessible
       STATUS obsolete
       DESCRIPTION
           "Number of incoming established calls."
       ::= {acPMSbcData 69}



     -- ****************************************
     -- acPMSBCInEstablishedCalls table entry
     -- ****************************************
     acPMSBCInEstablishedCallsEntry OBJECT-TYPE
       SYNTAX AcPMSBCInEstablishedCallsEntry
       MAX-ACCESS not-accessible
       STATUS obsolete
       DESCRIPTION
           ""
       INDEX {acPMSBCInEstablishedCallsInterval}
       ::= {acPMSBCInEstablishedCallsTable 1}



     -- ****************************************
     -- acPMSBCInEstablishedCalls TABLE
     -- ****************************************
     AcPMSBCInEstablishedCallsEntry ::= SEQUENCE {
       acPMSBCInEstablishedCallsInterval               Unsigned32,
       acPMSBCInEstablishedCallsVal                    Counter32,
       acPMSBCInEstablishedCallsTotal                  Counter32
     }



     acPMSBCInEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInEstablishedCallsEntry 1}



     acPMSBCInEstablishedCallsVal OBJECT-TYPE
       SYNTAX Counter32
       MAX-ACCESS read-only
       STATUS obsolete
       DESCRIPTION
           "Value of gauge or counter."
       ::= {acPMSBCInEstablishedCallsEntry 2}



     acPMSBCInEstablishedCallsTotal OBJECT-TYPE
       SYNTAX Counter32
       MAX-ACCESS read-only
       STATUS obsolete
       DESCRIPTION
           "Activity volume."
       ::= {acPMSBCInEstablishedCallsEntry 3}



     -- ****************************************
     -- acPMSBCSRDInEstablishedCalls table declaration
     -- ****************************************
     acPMSBCSRDInEstablishedCallsTable OBJECT-TYPE
       SYNTAX SEQUENCE OF AcPMSBCSRDInEstablishedCallsEntry
       MAX-ACCESS not-accessible
       STATUS obsolete
       DESCRIPTION
           "Number of incoming established calls per SRD."
       ::= {acPMSbcData 70}



     -- ****************************************
     -- acPMSBCSRDInEstablishedCalls table entry
     -- ****************************************
     acPMSBCSRDInEstablishedCallsEntry OBJECT-TYPE
       SYNTAX AcPMSBCSRDInEstablishedCallsEntry
       MAX-ACCESS not-accessible
       STATUS obsolete
       DESCRIPTION
           ""
       INDEX {acPMSBCSRDInEstablishedCallsSrdID,acPMSBCSRDInEstablishedCallsInterval}
       ::= {acPMSBCSRDInEstablishedCallsTable 1}



     -- ****************************************
     -- acPMSBCSRDInEstablishedCalls TABLE
     -- ****************************************
     AcPMSBCSRDInEstablishedCallsEntry ::= SEQUENCE {
       acPMSBCSRDInEstablishedCallsSrdID               Unsigned32,
       acPMSBCSRDInEstablishedCallsInterval            Unsigned32,
       acPMSBCSRDInEstablishedCallsVal                 Counter32,
       acPMSBCSRDInEstablishedCallsTotal               Counter32
     }



     acPMSBCSRDInEstablishedCallsSrdID OBJECT-TYPE
       SYNTAX Unsigned32 (0..600)
       MAX-ACCESS not-accessible
       STATUS obsolete
       DESCRIPTION
           "."
       ::= {acPMSBCSRDInEstablishedCallsEntry 1}



     acPMSBCSRDInEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInEstablishedCallsEntry 2}



     acPMSBCSRDInEstablishedCallsVal OBJECT-TYPE
       SYNTAX Counter32
       MAX-ACCESS read-only
       STATUS obsolete
       DESCRIPTION
           "Value of gauge or counter."
       ::= {acPMSBCSRDInEstablishedCallsEntry 3}



     acPMSBCSRDInEstablishedCallsTotal OBJECT-TYPE
       SYNTAX Counter32
       MAX-ACCESS read-only
       STATUS obsolete
       DESCRIPTION
           "Activity volume."
       ::= {acPMSBCSRDInEstablishedCallsEntry 4}



     -- ****************************************
     -- acPMSBCOutEstablishedCalls table declaration
     -- ****************************************
     acPMSBCOutEstablishedCallsTable OBJECT-TYPE
       SYNTAX SEQUENCE OF AcPMSBCOutEstablishedCallsEntry
       MAX-ACCESS not-accessible
       STATUS obsolete
       DESCRIPTION
           "Number of outgoing established calls."
       ::= {acPMSbcData 71}



     -- ****************************************
     -- acPMSBCOutEstablishedCalls table entry
     -- ****************************************
     acPMSBCOutEstablishedCallsEntry OBJECT-TYPE
       SYNTAX AcPMSBCOutEstablishedCallsEntry
       MAX-ACCESS not-accessible
       STATUS obsolete
       DESCRIPTION
           ""
       INDEX {acPMSBCOutEstablishedCallsInterval}
       ::= {acPMSBCOutEstablishedCallsTable 1}



     -- ****************************************
     -- acPMSBCOutEstablishedCalls TABLE
     -- ****************************************
     AcPMSBCOutEstablishedCallsEntry ::= SEQUENCE {
       acPMSBCOutEstablishedCallsInterval              Unsigned32,
       acPMSBCOutEstablishedCallsVal                   Counter32,
       acPMSBCOutEstablishedCallsTotal                 Counter32
     }



     acPMSBCOutEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutEstablishedCallsEntry 1}



     acPMSBCOutEstablishedCallsVal OBJECT-TYPE
       SYNTAX Counter32
       MAX-ACCESS read-only
       STATUS obsolete
       DESCRIPTION
           "Value of gauge or counter."
       ::= {acPMSBCOutEstablishedCallsEntry 2}



     acPMSBCOutEstablishedCallsTotal OBJECT-TYPE
       SYNTAX Counter32
       MAX-ACCESS read-only
       STATUS obsolete
       DESCRIPTION
           "Activity volume."
       ::= {acPMSBCOutEstablishedCallsEntry 3}



     -- ****************************************
     -- acPMSBCSRDOutEstablishedCalls table declaration
     -- ****************************************
     acPMSBCSRDOutEstablishedCallsTable OBJECT-TYPE
       SYNTAX SEQUENCE OF AcPMSBCSRDOutEstablishedCallsEntry
       MAX-ACCESS not-accessible
       STATUS obsolete
       DESCRIPTION
           "Number of incoming established calls per SRD."
       ::= {acPMSbcData 72}



     -- ****************************************
     -- acPMSBCSRDOutEstablishedCalls table entry
     -- ****************************************
     acPMSBCSRDOutEstablishedCallsEntry OBJECT-TYPE
       SYNTAX AcPMSBCSRDOutEstablishedCallsEntry
       MAX-ACCESS not-accessible
       STATUS obsolete
       DESCRIPTION
           ""
       INDEX {acPMSBCSRDOutEstablishedCallsSrdID,acPMSBCSRDOutEstablishedCallsInterval}
       ::= {acPMSBCSRDOutEstablishedCallsTable 1}



     -- ****************************************
     -- acPMSBCSRDOutEstablishedCalls TABLE
     -- ****************************************
     AcPMSBCSRDOutEstablishedCallsEntry ::= SEQUENCE {
       acPMSBCSRDOutEstablishedCallsSrdID              Unsigned32,
       acPMSBCSRDOutEstablishedCallsInterval           Unsigned32,
       acPMSBCSRDOutEstablishedCallsVal                Counter32,
       acPMSBCSRDOutEstablishedCallsTotal              Counter32
     }



     acPMSBCSRDOutEstablishedCallsSrdID OBJECT-TYPE
       SYNTAX Unsigned32 (0..600)
       MAX-ACCESS not-accessible
       STATUS obsolete
       DESCRIPTION
           "."
       ::= {acPMSBCSRDOutEstablishedCallsEntry 1}



     acPMSBCSRDOutEstablishedCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutEstablishedCallsEntry 2}



     acPMSBCSRDOutEstablishedCallsVal OBJECT-TYPE
       SYNTAX Counter32
       MAX-ACCESS read-only
       STATUS obsolete
       DESCRIPTION
           "Value of gauge or counter."
       ::= {acPMSBCSRDOutEstablishedCallsEntry 3}



     acPMSBCSRDOutEstablishedCallsTotal OBJECT-TYPE
       SYNTAX Counter32
       MAX-ACCESS read-only
       STATUS obsolete
       DESCRIPTION
           "Activity volume."
       ::= {acPMSBCSRDOutEstablishedCallsEntry 4}



     acPMSBCBrokenConnectionPMs OBJECT IDENTIFIER ::= {acPMSbcData 151}


     -- ****************************************
     -- acPMSBCMediaBrokenConnectionCalls table declaration
     -- ****************************************
     acPMSBCMediaBrokenConnectionCallsTable OBJECT-TYPE
       SYNTAX SEQUENCE OF AcPMSBCMediaBrokenConnectionCallsEntry
       MAX-ACCESS not-accessible
       STATUS obsolete
       DESCRIPTION
           "PM SBC Media Broken Connection Calls"
       ::= {acPMSBCBrokenConnectionPMs 1}



     -- ****************************************
     -- acPMSBCMediaBrokenConnectionCalls table entry
     -- ****************************************
     acPMSBCMediaBrokenConnectionCallsEntry OBJECT-TYPE
       SYNTAX AcPMSBCMediaBrokenConnectionCallsEntry
       MAX-ACCESS not-accessible
       STATUS obsolete
       DESCRIPTION
           ""
       INDEX {acPMSBCMediaBrokenConnectionCallsInterval}
       ::= {acPMSBCMediaBrokenConnectionCallsTable 1}



     -- ****************************************
     -- acPMSBCMediaBrokenConnectionCalls TABLE
     -- ****************************************
     AcPMSBCMediaBrokenConnectionCallsEntry ::= SEQUENCE {
       acPMSBCMediaBrokenConnectionCallsInterval       Unsigned32,
       acPMSBCMediaBrokenConnectionCallsVal            Counter32
     }



     acPMSBCMediaBrokenConnectionCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCMediaBrokenConnectionCallsEntry 1}



     acPMSBCMediaBrokenConnectionCallsVal OBJECT-TYPE
       SYNTAX Counter32
       MAX-ACCESS read-only
       STATUS obsolete
       DESCRIPTION
           "Value of gauge or counter."
       ::= {acPMSBCMediaBrokenConnectionCallsEntry 2}



     -- ****************************************
     -- acPMSBCSRDMediaBrokenConnectionCalls table declaration
     -- ****************************************
     acPMSBCSRDMediaBrokenConnectionCallsTable OBJECT-TYPE
       SYNTAX SEQUENCE OF AcPMSBCSRDMediaBrokenConnectionCallsEntry
       MAX-ACCESS not-accessible
       STATUS obsolete
       DESCRIPTION
           "PM SBC  Media Broken Connection Calls"
       ::= {acPMSBCBrokenConnectionPMs 2}



     -- ****************************************
     -- acPMSBCSRDMediaBrokenConnectionCalls table entry
     -- ****************************************
     acPMSBCSRDMediaBrokenConnectionCallsEntry OBJECT-TYPE
       SYNTAX AcPMSBCSRDMediaBrokenConnectionCallsEntry
       MAX-ACCESS not-accessible
       STATUS obsolete
       DESCRIPTION
           ""
       INDEX {acPMSBCSRDMediaBrokenConnectionCallsIndex,acPMSBCSRDMediaBrokenConnectionCallsInterval}
       ::= {acPMSBCSRDMediaBrokenConnectionCallsTable 1}



     -- ****************************************
     -- acPMSBCSRDMediaBrokenConnectionCalls TABLE
     -- ****************************************
     AcPMSBCSRDMediaBrokenConnectionCallsEntry ::= SEQUENCE {
       acPMSBCSRDMediaBrokenConnectionCallsIndex       Unsigned32,
       acPMSBCSRDMediaBrokenConnectionCallsInterval    Unsigned32,
       acPMSBCSRDMediaBrokenConnectionCallsVal         Counter32
     }



     acPMSBCSRDMediaBrokenConnectionCallsIndex OBJECT-TYPE
       SYNTAX Unsigned32 (0..600)
       MAX-ACCESS not-accessible
       STATUS obsolete
       DESCRIPTION
           "SRD number.
0 is the first SRD."
       ::= {acPMSBCSRDMediaBrokenConnectionCallsEntry 1}



     acPMSBCSRDMediaBrokenConnectionCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDMediaBrokenConnectionCallsEntry 2}



     acPMSBCSRDMediaBrokenConnectionCallsVal OBJECT-TYPE
       SYNTAX Counter32
       MAX-ACCESS read-only
       STATUS obsolete
       DESCRIPTION
           "Value of gauge or counter."
       ::= {acPMSBCSRDMediaBrokenConnectionCallsEntry 3}



     -- ****************************************
     -- acPMSBCIPGroupMediaBrokenConnectionCalls table declaration
     -- ****************************************
     acPMSBCIPGroupMediaBrokenConnectionCallsTable OBJECT-TYPE
       SYNTAX SEQUENCE OF AcPMSBCIPGroupMediaBrokenConnectionCallsEntry
       MAX-ACCESS not-accessible
       STATUS obsolete
       DESCRIPTION
           "PM SBC IP Group Media Broken Connection Calls"
       ::= {acPMSBCBrokenConnectionPMs 3}



     -- ****************************************
     -- acPMSBCIPGroupMediaBrokenConnectionCalls table entry
     -- ****************************************
     acPMSBCIPGroupMediaBrokenConnectionCallsEntry OBJECT-TYPE
       SYNTAX AcPMSBCIPGroupMediaBrokenConnectionCallsEntry
       MAX-ACCESS not-accessible
       STATUS obsolete
       DESCRIPTION
           ""
       INDEX {acPMSBCIPGroupMediaBrokenConnectionCallsIndex,acPMSBCIPGroupMediaBrokenConnectionCallsInterval}
       ::= {acPMSBCIPGroupMediaBrokenConnectionCallsTable 1}



     -- ****************************************
     -- acPMSBCIPGroupMediaBrokenConnectionCalls TABLE
     -- ****************************************
     AcPMSBCIPGroupMediaBrokenConnectionCallsEntry ::= SEQUENCE {
       acPMSBCIPGroupMediaBrokenConnectionCallsIndex   Unsigned32,
       acPMSBCIPGroupMediaBrokenConnectionCallsInterval 
                                                       Unsigned32,
       acPMSBCIPGroupMediaBrokenConnectionCallsVal     Counter32
     }



     acPMSBCIPGroupMediaBrokenConnectionCallsIndex OBJECT-TYPE
       SYNTAX Unsigned32 (0..5000)
       MAX-ACCESS not-accessible
       STATUS obsolete
       DESCRIPTION
           "IP Group number."
       ::= {acPMSBCIPGroupMediaBrokenConnectionCallsEntry 1}



     acPMSBCIPGroupMediaBrokenConnectionCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupMediaBrokenConnectionCallsEntry 2}



     acPMSBCIPGroupMediaBrokenConnectionCallsVal OBJECT-TYPE
       SYNTAX Counter32
       MAX-ACCESS read-only
       STATUS obsolete
       DESCRIPTION
           "Value of gauge or counter."
       ::= {acPMSBCIPGroupMediaBrokenConnectionCallsEntry 3}



     acPMSBCShortCallsPMs OBJECT IDENTIFIER ::= {acPMSbcData 152}


     -- ****************************************
     -- acPMSBCInShortCalls table declaration
     -- ****************************************
     acPMSBCInShortCallsTable OBJECT-TYPE
       SYNTAX SEQUENCE OF AcPMSBCInShortCallsEntry
       MAX-ACCESS not-accessible
       STATUS obsolete
       DESCRIPTION
           "Number of incoming calls with short duration"
       ::= {acPMSBCShortCallsPMs 1}



     -- ****************************************
     -- acPMSBCInShortCalls table entry
     -- ****************************************
     acPMSBCInShortCallsEntry OBJECT-TYPE
       SYNTAX AcPMSBCInShortCallsEntry
       MAX-ACCESS not-accessible
       STATUS obsolete
       DESCRIPTION
           ""
       INDEX {acPMSBCInShortCallsInterval}
       ::= {acPMSBCInShortCallsTable 1}



     -- ****************************************
     -- acPMSBCInShortCalls TABLE
     -- ****************************************
     AcPMSBCInShortCallsEntry ::= SEQUENCE {
       acPMSBCInShortCallsInterval                     Unsigned32,
       acPMSBCInShortCallsVal                          Counter32
     }



     acPMSBCInShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInShortCallsEntry 1}



     acPMSBCInShortCallsVal OBJECT-TYPE
       SYNTAX Counter32
       MAX-ACCESS read-only
       STATUS obsolete
       DESCRIPTION
           "Value of gauge or counter."
       ::= {acPMSBCInShortCallsEntry 2}



     -- ****************************************
     -- acPMSBCOutShortCalls table declaration
     -- ****************************************
     acPMSBCOutShortCallsTable OBJECT-TYPE
       SYNTAX SEQUENCE OF AcPMSBCOutShortCallsEntry
       MAX-ACCESS not-accessible
       STATUS obsolete
       DESCRIPTION
           "Number of outgoing calls with short duration"
       ::= {acPMSBCShortCallsPMs 2}



     -- ****************************************
     -- acPMSBCOutShortCalls table entry
     -- ****************************************
     acPMSBCOutShortCallsEntry OBJECT-TYPE
       SYNTAX AcPMSBCOutShortCallsEntry
       MAX-ACCESS not-accessible
       STATUS obsolete
       DESCRIPTION
           ""
       INDEX {acPMSBCOutShortCallsInterval}
       ::= {acPMSBCOutShortCallsTable 1}



     -- ****************************************
     -- acPMSBCOutShortCalls TABLE
     -- ****************************************
     AcPMSBCOutShortCallsEntry ::= SEQUENCE {
       acPMSBCOutShortCallsInterval                    Unsigned32,
       acPMSBCOutShortCallsVal                         Counter32
     }



     acPMSBCOutShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutShortCallsEntry 1}



     acPMSBCOutShortCallsVal OBJECT-TYPE
       SYNTAX Counter32
       MAX-ACCESS read-only
       STATUS obsolete
       DESCRIPTION
           "Value of gauge or counter."
       ::= {acPMSBCOutShortCallsEntry 2}



     -- ****************************************
     -- acPMSBCSRDInShortCalls table declaration
     -- ****************************************
     acPMSBCSRDInShortCallsTable OBJECT-TYPE
       SYNTAX SEQUENCE OF AcPMSBCSRDInShortCallsEntry
       MAX-ACCESS not-accessible
       STATUS obsolete
       DESCRIPTION
           "Number of incoming calls with short duration per SRD"
       ::= {acPMSBCShortCallsPMs 3}



     -- ****************************************
     -- acPMSBCSRDInShortCalls table entry
     -- ****************************************
     acPMSBCSRDInShortCallsEntry OBJECT-TYPE
       SYNTAX AcPMSBCSRDInShortCallsEntry
       MAX-ACCESS not-accessible
       STATUS obsolete
       DESCRIPTION
           ""
       INDEX {acPMSBCSRDInShortCallsIndex,acPMSBCSRDInShortCallsInterval}
       ::= {acPMSBCSRDInShortCallsTable 1}



     -- ****************************************
     -- acPMSBCSRDInShortCalls TABLE
     -- ****************************************
     AcPMSBCSRDInShortCallsEntry ::= SEQUENCE {
       acPMSBCSRDInShortCallsIndex                     Unsigned32,
       acPMSBCSRDInShortCallsInterval                  Unsigned32,
       acPMSBCSRDInShortCallsVal                       Counter32
     }



     acPMSBCSRDInShortCallsIndex OBJECT-TYPE
       SYNTAX Unsigned32 (0..600)
       MAX-ACCESS not-accessible
       STATUS obsolete
       DESCRIPTION
           "SRD number.
0 is the first SRD."
       ::= {acPMSBCSRDInShortCallsEntry 1}



     acPMSBCSRDInShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInShortCallsEntry 2}



     acPMSBCSRDInShortCallsVal OBJECT-TYPE
       SYNTAX Counter32
       MAX-ACCESS read-only
       STATUS obsolete
       DESCRIPTION
           "Value of gauge or counter."
       ::= {acPMSBCSRDInShortCallsEntry 3}



     -- ****************************************
     -- acPMSBCSRDOutShortCalls table declaration
     -- ****************************************
     acPMSBCSRDOutShortCallsTable OBJECT-TYPE
       SYNTAX SEQUENCE OF AcPMSBCSRDOutShortCallsEntry
       MAX-ACCESS not-accessible
       STATUS obsolete
       DESCRIPTION
           "Number of outgoing calls with short duration per SRD"
       ::= {acPMSBCShortCallsPMs 4}



     -- ****************************************
     -- acPMSBCSRDOutShortCalls table entry
     -- ****************************************
     acPMSBCSRDOutShortCallsEntry OBJECT-TYPE
       SYNTAX AcPMSBCSRDOutShortCallsEntry
       MAX-ACCESS not-accessible
       STATUS obsolete
       DESCRIPTION
           ""
       INDEX {acPMSBCSRDOutShortCallsIndex,acPMSBCSRDOutShortCallsInterval}
       ::= {acPMSBCSRDOutShortCallsTable 1}



     -- ****************************************
     -- acPMSBCSRDOutShortCalls TABLE
     -- ****************************************
     AcPMSBCSRDOutShortCallsEntry ::= SEQUENCE {
       acPMSBCSRDOutShortCallsIndex                    Unsigned32,
       acPMSBCSRDOutShortCallsInterval                 Unsigned32,
       acPMSBCSRDOutShortCallsVal                      Counter32
     }



     acPMSBCSRDOutShortCallsIndex OBJECT-TYPE
       SYNTAX Unsigned32 (0..600)
       MAX-ACCESS not-accessible
       STATUS obsolete
       DESCRIPTION
           "SRD number.
0 is the first SRD."
       ::= {acPMSBCSRDOutShortCallsEntry 1}



     acPMSBCSRDOutShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutShortCallsEntry 2}



     acPMSBCSRDOutShortCallsVal OBJECT-TYPE
       SYNTAX Counter32
       MAX-ACCESS read-only
       STATUS obsolete
       DESCRIPTION
           "Value of gauge or counter."
       ::= {acPMSBCSRDOutShortCallsEntry 3}



     -- ****************************************
     -- acPMSBCIPGroupInShortCalls table declaration
     -- ****************************************
     acPMSBCIPGroupInShortCallsTable OBJECT-TYPE
       SYNTAX SEQUENCE OF AcPMSBCIPGroupInShortCallsEntry
       MAX-ACCESS not-accessible
       STATUS obsolete
       DESCRIPTION
           "Number of incoming calls with short duration per IP Group"
       ::= {acPMSBCShortCallsPMs 5}



     -- ****************************************
     -- acPMSBCIPGroupInShortCalls table entry
     -- ****************************************
     acPMSBCIPGroupInShortCallsEntry OBJECT-TYPE
       SYNTAX AcPMSBCIPGroupInShortCallsEntry
       MAX-ACCESS not-accessible
       STATUS obsolete
       DESCRIPTION
           ""
       INDEX {acPMSBCIPGroupInShortCallsIndex,acPMSBCIPGroupInShortCallsInterval}
       ::= {acPMSBCIPGroupInShortCallsTable 1}



     -- ****************************************
     -- acPMSBCIPGroupInShortCalls TABLE
     -- ****************************************
     AcPMSBCIPGroupInShortCallsEntry ::= SEQUENCE {
       acPMSBCIPGroupInShortCallsIndex                 Unsigned32,
       acPMSBCIPGroupInShortCallsInterval              Unsigned32,
       acPMSBCIPGroupInShortCallsVal                   Counter32
     }



     acPMSBCIPGroupInShortCallsIndex OBJECT-TYPE
       SYNTAX Unsigned32 (0..5000)
       MAX-ACCESS not-accessible
       STATUS obsolete
       DESCRIPTION
           "IP Group number."
       ::= {acPMSBCIPGroupInShortCallsEntry 1}



     acPMSBCIPGroupInShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInShortCallsEntry 2}



     acPMSBCIPGroupInShortCallsVal OBJECT-TYPE
       SYNTAX Counter32
       MAX-ACCESS read-only
       STATUS obsolete
       DESCRIPTION
           "Value of gauge or counter."
       ::= {acPMSBCIPGroupInShortCallsEntry 3}



     -- ****************************************
     -- acPMSBCIPGroupOutShortCalls table declaration
     -- ****************************************
     acPMSBCIPGroupOutShortCallsTable OBJECT-TYPE
       SYNTAX SEQUENCE OF AcPMSBCIPGroupOutShortCallsEntry
       MAX-ACCESS not-accessible
       STATUS obsolete
       DESCRIPTION
           "Number of outgoing calls with short duration per IP Group"
       ::= {acPMSBCShortCallsPMs 6}



     -- ****************************************
     -- acPMSBCIPGroupOutShortCalls table entry
     -- ****************************************
     acPMSBCIPGroupOutShortCallsEntry OBJECT-TYPE
       SYNTAX AcPMSBCIPGroupOutShortCallsEntry
       MAX-ACCESS not-accessible
       STATUS obsolete
       DESCRIPTION
           ""
       INDEX {acPMSBCIPGroupOutShortCallsIndex,acPMSBCIPGroupOutShortCallsInterval}
       ::= {acPMSBCIPGroupOutShortCallsTable 1}



     -- ****************************************
     -- acPMSBCIPGroupOutShortCalls TABLE
     -- ****************************************
     AcPMSBCIPGroupOutShortCallsEntry ::= SEQUENCE {
       acPMSBCIPGroupOutShortCallsIndex                Unsigned32,
       acPMSBCIPGroupOutShortCallsInterval             Unsigned32,
       acPMSBCIPGroupOutShortCallsVal                  Counter32
     }



     acPMSBCIPGroupOutShortCallsIndex OBJECT-TYPE
       SYNTAX Unsigned32 (0..5000)
       MAX-ACCESS not-accessible
       STATUS obsolete
       DESCRIPTION
           "IP Group number."
       ::= {acPMSBCIPGroupOutShortCallsEntry 1}



     acPMSBCIPGroupOutShortCallsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutShortCallsEntry 2}



     acPMSBCIPGroupOutShortCallsVal OBJECT-TYPE
       SYNTAX Counter32
       MAX-ACCESS read-only
       STATUS obsolete
       DESCRIPTION
           "Value of gauge or counter."
       ::= {acPMSBCIPGroupOutShortCallsEntry 3}



     acPMSBCAttemptedRegistrationsPMs OBJECT IDENTIFIER ::= {acPMSbcData 153}


     -- ****************************************
     -- acPMSBCInAttemptedRegistrations table declaration
     -- ****************************************
     acPMSBCInAttemptedRegistrationsTable OBJECT-TYPE
       SYNTAX SEQUENCE OF AcPMSBCInAttemptedRegistrationsEntry
       MAX-ACCESS not-accessible
       STATUS obsolete
       DESCRIPTION
           "Number of incoming SBC registration attempts."
       ::= {acPMSBCAttemptedRegistrationsPMs 1}



     -- ****************************************
     -- acPMSBCInAttemptedRegistrations table entry
     -- ****************************************
     acPMSBCInAttemptedRegistrationsEntry OBJECT-TYPE
       SYNTAX AcPMSBCInAttemptedRegistrationsEntry
       MAX-ACCESS not-accessible
       STATUS obsolete
       DESCRIPTION
           ""
       INDEX {acPMSBCInAttemptedRegistrationsInterval}
       ::= {acPMSBCInAttemptedRegistrationsTable 1}



     -- ****************************************
     -- acPMSBCInAttemptedRegistrations TABLE
     -- ****************************************
     AcPMSBCInAttemptedRegistrationsEntry ::= SEQUENCE {
       acPMSBCInAttemptedRegistrationsInterval         Unsigned32,
       acPMSBCInAttemptedRegistrationsVal              Counter32
     }



     acPMSBCInAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInAttemptedRegistrationsEntry 1}



     acPMSBCInAttemptedRegistrationsVal OBJECT-TYPE
       SYNTAX Counter32
       MAX-ACCESS read-only
       STATUS obsolete
       DESCRIPTION
           "Value of gauge or counter."
       ::= {acPMSBCInAttemptedRegistrationsEntry 2}



     -- ****************************************
     -- acPMSBCOutAttemptedRegistrations table declaration
     -- ****************************************
     acPMSBCOutAttemptedRegistrationsTable OBJECT-TYPE
       SYNTAX SEQUENCE OF AcPMSBCOutAttemptedRegistrationsEntry
       MAX-ACCESS not-accessible
       STATUS obsolete
       DESCRIPTION
           "Number of outgoing SBC registration attempts."
       ::= {acPMSBCAttemptedRegistrationsPMs 2}



     -- ****************************************
     -- acPMSBCOutAttemptedRegistrations table entry
     -- ****************************************
     acPMSBCOutAttemptedRegistrationsEntry OBJECT-TYPE
       SYNTAX AcPMSBCOutAttemptedRegistrationsEntry
       MAX-ACCESS not-accessible
       STATUS obsolete
       DESCRIPTION
           ""
       INDEX {acPMSBCOutAttemptedRegistrationsInterval}
       ::= {acPMSBCOutAttemptedRegistrationsTable 1}



     -- ****************************************
     -- acPMSBCOutAttemptedRegistrations TABLE
     -- ****************************************
     AcPMSBCOutAttemptedRegistrationsEntry ::= SEQUENCE {
       acPMSBCOutAttemptedRegistrationsInterval        Unsigned32,
       acPMSBCOutAttemptedRegistrationsVal             Counter32
     }



     acPMSBCOutAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutAttemptedRegistrationsEntry 1}



     acPMSBCOutAttemptedRegistrationsVal OBJECT-TYPE
       SYNTAX Counter32
       MAX-ACCESS read-only
       STATUS obsolete
       DESCRIPTION
           "Value of gauge or counter."
       ::= {acPMSBCOutAttemptedRegistrationsEntry 2}



     -- ****************************************
     -- acPMSBCSRDInAttemptedRegistrations table declaration
     -- ****************************************
     acPMSBCSRDInAttemptedRegistrationsTable OBJECT-TYPE
       SYNTAX SEQUENCE OF AcPMSBCSRDInAttemptedRegistrationsEntry
       MAX-ACCESS not-accessible
       STATUS obsolete
       DESCRIPTION
           "Number of incoming SBC registration attempts per SRD."
       ::= {acPMSBCAttemptedRegistrationsPMs 3}



     -- ****************************************
     -- acPMSBCSRDInAttemptedRegistrations table entry
     -- ****************************************
     acPMSBCSRDInAttemptedRegistrationsEntry OBJECT-TYPE
       SYNTAX AcPMSBCSRDInAttemptedRegistrationsEntry
       MAX-ACCESS not-accessible
       STATUS obsolete
       DESCRIPTION
           ""
       INDEX {acPMSBCSRDInAttemptedRegistrationsIndex,acPMSBCSRDInAttemptedRegistrationsInterval}
       ::= {acPMSBCSRDInAttemptedRegistrationsTable 1}



     -- ****************************************
     -- acPMSBCSRDInAttemptedRegistrations TABLE
     -- ****************************************
     AcPMSBCSRDInAttemptedRegistrationsEntry ::= SEQUENCE {
       acPMSBCSRDInAttemptedRegistrationsIndex         Unsigned32,
       acPMSBCSRDInAttemptedRegistrationsInterval      Unsigned32,
       acPMSBCSRDInAttemptedRegistrationsVal           Counter32
     }



     acPMSBCSRDInAttemptedRegistrationsIndex OBJECT-TYPE
       SYNTAX Unsigned32 (0..600)
       MAX-ACCESS not-accessible
       STATUS obsolete
       DESCRIPTION
           "SRD number.
0 is the first SRD."
       ::= {acPMSBCSRDInAttemptedRegistrationsEntry 1}



     acPMSBCSRDInAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInAttemptedRegistrationsEntry 2}



     acPMSBCSRDInAttemptedRegistrationsVal OBJECT-TYPE
       SYNTAX Counter32
       MAX-ACCESS read-only
       STATUS obsolete
       DESCRIPTION
           "Value of gauge or counter."
       ::= {acPMSBCSRDInAttemptedRegistrationsEntry 3}



     -- ****************************************
     -- acPMSBCSRDOutAttemptedRegistrations table declaration
     -- ****************************************
     acPMSBCSRDOutAttemptedRegistrationsTable OBJECT-TYPE
       SYNTAX SEQUENCE OF AcPMSBCSRDOutAttemptedRegistrationsEntry
       MAX-ACCESS not-accessible
       STATUS obsolete
       DESCRIPTION
           "Number of outgoing SBC registration attempts per SRD."
       ::= {acPMSBCAttemptedRegistrationsPMs 4}



     -- ****************************************
     -- acPMSBCSRDOutAttemptedRegistrations table entry
     -- ****************************************
     acPMSBCSRDOutAttemptedRegistrationsEntry OBJECT-TYPE
       SYNTAX AcPMSBCSRDOutAttemptedRegistrationsEntry
       MAX-ACCESS not-accessible
       STATUS obsolete
       DESCRIPTION
           ""
       INDEX {acPMSBCSRDOutAttemptedRegistrationsIndex,acPMSBCSRDOutAttemptedRegistrationsInterval}
       ::= {acPMSBCSRDOutAttemptedRegistrationsTable 1}



     -- ****************************************
     -- acPMSBCSRDOutAttemptedRegistrations TABLE
     -- ****************************************
     AcPMSBCSRDOutAttemptedRegistrationsEntry ::= SEQUENCE {
       acPMSBCSRDOutAttemptedRegistrationsIndex        Unsigned32,
       acPMSBCSRDOutAttemptedRegistrationsInterval     Unsigned32,
       acPMSBCSRDOutAttemptedRegistrationsVal          Counter32
     }



     acPMSBCSRDOutAttemptedRegistrationsIndex OBJECT-TYPE
       SYNTAX Unsigned32 (0..600)
       MAX-ACCESS not-accessible
       STATUS obsolete
       DESCRIPTION
           "SRD number.
0 is the first SRD."
       ::= {acPMSBCSRDOutAttemptedRegistrationsEntry 1}



     acPMSBCSRDOutAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutAttemptedRegistrationsEntry 2}



     acPMSBCSRDOutAttemptedRegistrationsVal OBJECT-TYPE
       SYNTAX Counter32
       MAX-ACCESS read-only
       STATUS obsolete
       DESCRIPTION
           "Value of gauge or counter."
       ::= {acPMSBCSRDOutAttemptedRegistrationsEntry 3}



     -- ****************************************
     -- acPMSBCIPGroupInAttemptedRegistrations table declaration
     -- ****************************************
     acPMSBCIPGroupInAttemptedRegistrationsTable OBJECT-TYPE
       SYNTAX SEQUENCE OF AcPMSBCIPGroupInAttemptedRegistrationsEntry
       MAX-ACCESS not-accessible
       STATUS obsolete
       DESCRIPTION
           "Number of incoming SBC registration attempts per IP group."
       ::= {acPMSBCAttemptedRegistrationsPMs 5}



     -- ****************************************
     -- acPMSBCIPGroupInAttemptedRegistrations table entry
     -- ****************************************
     acPMSBCIPGroupInAttemptedRegistrationsEntry OBJECT-TYPE
       SYNTAX AcPMSBCIPGroupInAttemptedRegistrationsEntry
       MAX-ACCESS not-accessible
       STATUS obsolete
       DESCRIPTION
           ""
       INDEX {acPMSBCIPGroupInAttemptedRegistrationsIndex,acPMSBCIPGroupInAttemptedRegistrationsInterval}
       ::= {acPMSBCIPGroupInAttemptedRegistrationsTable 1}



     -- ****************************************
     -- acPMSBCIPGroupInAttemptedRegistrations TABLE
     -- ****************************************
     AcPMSBCIPGroupInAttemptedRegistrationsEntry ::= SEQUENCE {
       acPMSBCIPGroupInAttemptedRegistrationsIndex     Unsigned32,
       acPMSBCIPGroupInAttemptedRegistrationsInterval  Unsigned32,
       acPMSBCIPGroupInAttemptedRegistrationsVal       Counter32
     }



     acPMSBCIPGroupInAttemptedRegistrationsIndex OBJECT-TYPE
       SYNTAX Unsigned32 (0..5000)
       MAX-ACCESS not-accessible
       STATUS obsolete
       DESCRIPTION
           "IP Group number."
       ::= {acPMSBCIPGroupInAttemptedRegistrationsEntry 1}



     acPMSBCIPGroupInAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInAttemptedRegistrationsEntry 2}



     acPMSBCIPGroupInAttemptedRegistrationsVal OBJECT-TYPE
       SYNTAX Counter32
       MAX-ACCESS read-only
       STATUS obsolete
       DESCRIPTION
           "Value of gauge or counter."
       ::= {acPMSBCIPGroupInAttemptedRegistrationsEntry 3}



     -- ****************************************
     -- acPMSBCIPGroupOutAttemptedRegistrations table declaration
     -- ****************************************
     acPMSBCIPGroupOutAttemptedRegistrationsTable OBJECT-TYPE
       SYNTAX SEQUENCE OF AcPMSBCIPGroupOutAttemptedRegistrationsEntry
       MAX-ACCESS not-accessible
       STATUS obsolete
       DESCRIPTION
           "Number of outgoing SBC registration attempts per IP group."
       ::= {acPMSBCAttemptedRegistrationsPMs 6}



     -- ****************************************
     -- acPMSBCIPGroupOutAttemptedRegistrations table entry
     -- ****************************************
     acPMSBCIPGroupOutAttemptedRegistrationsEntry OBJECT-TYPE
       SYNTAX AcPMSBCIPGroupOutAttemptedRegistrationsEntry
       MAX-ACCESS not-accessible
       STATUS obsolete
       DESCRIPTION
           ""
       INDEX {acPMSBCIPGroupOutAttemptedRegistrationsIndex,acPMSBCIPGroupOutAttemptedRegistrationsInterval}
       ::= {acPMSBCIPGroupOutAttemptedRegistrationsTable 1}



     -- ****************************************
     -- acPMSBCIPGroupOutAttemptedRegistrations TABLE
     -- ****************************************
     AcPMSBCIPGroupOutAttemptedRegistrationsEntry ::= SEQUENCE {
       acPMSBCIPGroupOutAttemptedRegistrationsIndex    Unsigned32,
       acPMSBCIPGroupOutAttemptedRegistrationsInterval Unsigned32,
       acPMSBCIPGroupOutAttemptedRegistrationsVal      Counter32
     }



     acPMSBCIPGroupOutAttemptedRegistrationsIndex OBJECT-TYPE
       SYNTAX Unsigned32 (0..5000)
       MAX-ACCESS not-accessible
       STATUS obsolete
       DESCRIPTION
           "IP Group number."
       ::= {acPMSBCIPGroupOutAttemptedRegistrationsEntry 1}



     acPMSBCIPGroupOutAttemptedRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutAttemptedRegistrationsEntry 2}



     acPMSBCIPGroupOutAttemptedRegistrationsVal OBJECT-TYPE
       SYNTAX Counter32
       MAX-ACCESS read-only
       STATUS obsolete
       DESCRIPTION
           "Value of gauge or counter."
       ::= {acPMSBCIPGroupOutAttemptedRegistrationsEntry 3}



     acPMSBCSuccessfulRegistrationsPMs OBJECT IDENTIFIER ::= {acPMSbcData 154}


     -- ****************************************
     -- acPMSBCInSuccessfulRegistrations table declaration
     -- ****************************************
     acPMSBCInSuccessfulRegistrationsTable OBJECT-TYPE
       SYNTAX SEQUENCE OF AcPMSBCInSuccessfulRegistrationsEntry
       MAX-ACCESS not-accessible
       STATUS obsolete
       DESCRIPTION
           "Number of incoming successfull SBC registrations."
       ::= {acPMSBCSuccessfulRegistrationsPMs 1}



     -- ****************************************
     -- acPMSBCInSuccessfulRegistrations table entry
     -- ****************************************
     acPMSBCInSuccessfulRegistrationsEntry OBJECT-TYPE
       SYNTAX AcPMSBCInSuccessfulRegistrationsEntry
       MAX-ACCESS not-accessible
       STATUS obsolete
       DESCRIPTION
           ""
       INDEX {acPMSBCInSuccessfulRegistrationsInterval}
       ::= {acPMSBCInSuccessfulRegistrationsTable 1}



     -- ****************************************
     -- acPMSBCInSuccessfulRegistrations TABLE
     -- ****************************************
     AcPMSBCInSuccessfulRegistrationsEntry ::= SEQUENCE {
       acPMSBCInSuccessfulRegistrationsInterval        Unsigned32,
       acPMSBCInSuccessfulRegistrationsVal             Counter32
     }



     acPMSBCInSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInSuccessfulRegistrationsEntry 1}



     acPMSBCInSuccessfulRegistrationsVal OBJECT-TYPE
       SYNTAX Counter32
       MAX-ACCESS read-only
       STATUS obsolete
       DESCRIPTION
           "Value of gauge or counter."
       ::= {acPMSBCInSuccessfulRegistrationsEntry 2}



     -- ****************************************
     -- acPMSBCOutSuccessfulRegistrations table declaration
     -- ****************************************
     acPMSBCOutSuccessfulRegistrationsTable OBJECT-TYPE
       SYNTAX SEQUENCE OF AcPMSBCOutSuccessfulRegistrationsEntry
       MAX-ACCESS not-accessible
       STATUS obsolete
       DESCRIPTION
           "Number of outgoing successfull SBC registrations."
       ::= {acPMSBCSuccessfulRegistrationsPMs 2}



     -- ****************************************
     -- acPMSBCOutSuccessfulRegistrations table entry
     -- ****************************************
     acPMSBCOutSuccessfulRegistrationsEntry OBJECT-TYPE
       SYNTAX AcPMSBCOutSuccessfulRegistrationsEntry
       MAX-ACCESS not-accessible
       STATUS obsolete
       DESCRIPTION
           ""
       INDEX {acPMSBCOutSuccessfulRegistrationsInterval}
       ::= {acPMSBCOutSuccessfulRegistrationsTable 1}



     -- ****************************************
     -- acPMSBCOutSuccessfulRegistrations TABLE
     -- ****************************************
     AcPMSBCOutSuccessfulRegistrationsEntry ::= SEQUENCE {
       acPMSBCOutSuccessfulRegistrationsInterval       Unsigned32,
       acPMSBCOutSuccessfulRegistrationsVal            Counter32
     }



     acPMSBCOutSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutSuccessfulRegistrationsEntry 1}



     acPMSBCOutSuccessfulRegistrationsVal OBJECT-TYPE
       SYNTAX Counter32
       MAX-ACCESS read-only
       STATUS obsolete
       DESCRIPTION
           "Value of gauge or counter."
       ::= {acPMSBCOutSuccessfulRegistrationsEntry 2}



     -- ****************************************
     -- acPMSBCSRDInSuccessfulRegistrations table declaration
     -- ****************************************
     acPMSBCSRDInSuccessfulRegistrationsTable OBJECT-TYPE
       SYNTAX SEQUENCE OF AcPMSBCSRDInSuccessfulRegistrationsEntry
       MAX-ACCESS not-accessible
       STATUS obsolete
       DESCRIPTION
           "Number of incoming successfull SBC registrations per SRD."
       ::= {acPMSBCSuccessfulRegistrationsPMs 3}



     -- ****************************************
     -- acPMSBCSRDInSuccessfulRegistrations table entry
     -- ****************************************
     acPMSBCSRDInSuccessfulRegistrationsEntry OBJECT-TYPE
       SYNTAX AcPMSBCSRDInSuccessfulRegistrationsEntry
       MAX-ACCESS not-accessible
       STATUS obsolete
       DESCRIPTION
           ""
       INDEX {acPMSBCSRDInSuccessfulRegistrationsIndex,acPMSBCSRDInSuccessfulRegistrationsInterval}
       ::= {acPMSBCSRDInSuccessfulRegistrationsTable 1}



     -- ****************************************
     -- acPMSBCSRDInSuccessfulRegistrations TABLE
     -- ****************************************
     AcPMSBCSRDInSuccessfulRegistrationsEntry ::= SEQUENCE {
       acPMSBCSRDInSuccessfulRegistrationsIndex        Unsigned32,
       acPMSBCSRDInSuccessfulRegistrationsInterval     Unsigned32,
       acPMSBCSRDInSuccessfulRegistrationsVal          Counter32
     }



     acPMSBCSRDInSuccessfulRegistrationsIndex OBJECT-TYPE
       SYNTAX Unsigned32 (0..600)
       MAX-ACCESS not-accessible
       STATUS obsolete
       DESCRIPTION
           "SRD number.
0 is the first SRD."
       ::= {acPMSBCSRDInSuccessfulRegistrationsEntry 1}



     acPMSBCSRDInSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInSuccessfulRegistrationsEntry 2}



     acPMSBCSRDInSuccessfulRegistrationsVal OBJECT-TYPE
       SYNTAX Counter32
       MAX-ACCESS read-only
       STATUS obsolete
       DESCRIPTION
           "Value of gauge or counter."
       ::= {acPMSBCSRDInSuccessfulRegistrationsEntry 3}



     -- ****************************************
     -- acPMSBCSRDOutSuccessfulRegistrations table declaration
     -- ****************************************
     acPMSBCSRDOutSuccessfulRegistrationsTable OBJECT-TYPE
       SYNTAX SEQUENCE OF AcPMSBCSRDOutSuccessfulRegistrationsEntry
       MAX-ACCESS not-accessible
       STATUS obsolete
       DESCRIPTION
           "Number of outgoing successfull SBC registrations per SRD."
       ::= {acPMSBCSuccessfulRegistrationsPMs 4}



     -- ****************************************
     -- acPMSBCSRDOutSuccessfulRegistrations table entry
     -- ****************************************
     acPMSBCSRDOutSuccessfulRegistrationsEntry OBJECT-TYPE
       SYNTAX AcPMSBCSRDOutSuccessfulRegistrationsEntry
       MAX-ACCESS not-accessible
       STATUS obsolete
       DESCRIPTION
           ""
       INDEX {acPMSBCSRDOutSuccessfulRegistrationsIndex,acPMSBCSRDOutSuccessfulRegistrationsInterval}
       ::= {acPMSBCSRDOutSuccessfulRegistrationsTable 1}



     -- ****************************************
     -- acPMSBCSRDOutSuccessfulRegistrations TABLE
     -- ****************************************
     AcPMSBCSRDOutSuccessfulRegistrationsEntry ::= SEQUENCE {
       acPMSBCSRDOutSuccessfulRegistrationsIndex       Unsigned32,
       acPMSBCSRDOutSuccessfulRegistrationsInterval    Unsigned32,
       acPMSBCSRDOutSuccessfulRegistrationsVal         Counter32
     }



     acPMSBCSRDOutSuccessfulRegistrationsIndex OBJECT-TYPE
       SYNTAX Unsigned32 (0..600)
       MAX-ACCESS not-accessible
       STATUS obsolete
       DESCRIPTION
           "SRD number.
0 is the first SRD."
       ::= {acPMSBCSRDOutSuccessfulRegistrationsEntry 1}



     acPMSBCSRDOutSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutSuccessfulRegistrationsEntry 2}



     acPMSBCSRDOutSuccessfulRegistrationsVal OBJECT-TYPE
       SYNTAX Counter32
       MAX-ACCESS read-only
       STATUS obsolete
       DESCRIPTION
           "Value of gauge or counter."
       ::= {acPMSBCSRDOutSuccessfulRegistrationsEntry 3}



     -- ****************************************
     -- acPMSBCIPGroupInSuccessfulRegistrations table declaration
     -- ****************************************
     acPMSBCIPGroupInSuccessfulRegistrationsTable OBJECT-TYPE
       SYNTAX SEQUENCE OF AcPMSBCIPGroupInSuccessfulRegistrationsEntry
       MAX-ACCESS not-accessible
       STATUS obsolete
       DESCRIPTION
           "Number of incoming successfull SBC registrations per IP group."
       ::= {acPMSBCSuccessfulRegistrationsPMs 5}



     -- ****************************************
     -- acPMSBCIPGroupInSuccessfulRegistrations table entry
     -- ****************************************
     acPMSBCIPGroupInSuccessfulRegistrationsEntry OBJECT-TYPE
       SYNTAX AcPMSBCIPGroupInSuccessfulRegistrationsEntry
       MAX-ACCESS not-accessible
       STATUS obsolete
       DESCRIPTION
           ""
       INDEX {acPMSBCIPGroupInSuccessfulRegistrationsIndex,acPMSBCIPGroupInSuccessfulRegistrationsInterval}
       ::= {acPMSBCIPGroupInSuccessfulRegistrationsTable 1}



     -- ****************************************
     -- acPMSBCIPGroupInSuccessfulRegistrations TABLE
     -- ****************************************
     AcPMSBCIPGroupInSuccessfulRegistrationsEntry ::= SEQUENCE {
       acPMSBCIPGroupInSuccessfulRegistrationsIndex    Unsigned32,
       acPMSBCIPGroupInSuccessfulRegistrationsInterval Unsigned32,
       acPMSBCIPGroupInSuccessfulRegistrationsVal      Counter32
     }



     acPMSBCIPGroupInSuccessfulRegistrationsIndex OBJECT-TYPE
       SYNTAX Unsigned32 (0..5000)
       MAX-ACCESS not-accessible
       STATUS obsolete
       DESCRIPTION
           "IP Group number."
       ::= {acPMSBCIPGroupInSuccessfulRegistrationsEntry 1}



     acPMSBCIPGroupInSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInSuccessfulRegistrationsEntry 2}



     acPMSBCIPGroupInSuccessfulRegistrationsVal OBJECT-TYPE
       SYNTAX Counter32
       MAX-ACCESS read-only
       STATUS obsolete
       DESCRIPTION
           "Value of gauge or counter."
       ::= {acPMSBCIPGroupInSuccessfulRegistrationsEntry 3}



     -- ****************************************
     -- acPMSBCIPGroupOutSuccessfulRegistrations table declaration
     -- ****************************************
     acPMSBCIPGroupOutSuccessfulRegistrationsTable OBJECT-TYPE
       SYNTAX SEQUENCE OF AcPMSBCIPGroupOutSuccessfulRegistrationsEntry
       MAX-ACCESS not-accessible
       STATUS obsolete
       DESCRIPTION
           "Number of outgoing successfull SBC registrations per IP group."
       ::= {acPMSBCSuccessfulRegistrationsPMs 6}



     -- ****************************************
     -- acPMSBCIPGroupOutSuccessfulRegistrations table entry
     -- ****************************************
     acPMSBCIPGroupOutSuccessfulRegistrationsEntry OBJECT-TYPE
       SYNTAX AcPMSBCIPGroupOutSuccessfulRegistrationsEntry
       MAX-ACCESS not-accessible
       STATUS obsolete
       DESCRIPTION
           ""
       INDEX {acPMSBCIPGroupOutSuccessfulRegistrationsIndex,acPMSBCIPGroupOutSuccessfulRegistrationsInterval}
       ::= {acPMSBCIPGroupOutSuccessfulRegistrationsTable 1}



     -- ****************************************
     -- acPMSBCIPGroupOutSuccessfulRegistrations TABLE
     -- ****************************************
     AcPMSBCIPGroupOutSuccessfulRegistrationsEntry ::= SEQUENCE {
       acPMSBCIPGroupOutSuccessfulRegistrationsIndex   Unsigned32,
       acPMSBCIPGroupOutSuccessfulRegistrationsInterval 
                                                       Unsigned32,
       acPMSBCIPGroupOutSuccessfulRegistrationsVal     Counter32
     }



     acPMSBCIPGroupOutSuccessfulRegistrationsIndex OBJECT-TYPE
       SYNTAX Unsigned32 (0..5000)
       MAX-ACCESS not-accessible
       STATUS obsolete
       DESCRIPTION
           "IP Group number."
       ::= {acPMSBCIPGroupOutSuccessfulRegistrationsEntry 1}



     acPMSBCIPGroupOutSuccessfulRegistrationsInterval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutSuccessfulRegistrationsEntry 2}



     acPMSBCIPGroupOutSuccessfulRegistrationsVal OBJECT-TYPE
       SYNTAX Counter32
       MAX-ACCESS read-only
       STATUS obsolete
       DESCRIPTION
           "Value of gauge or counter."
       ::= {acPMSBCIPGroupOutSuccessfulRegistrationsEntry 3}



     acPMSBCUserDefinedFailuresPMs OBJECT IDENTIFIER ::= {acPMSbcData 155}


     acPMSBCUserDefinedFailures1 OBJECT IDENTIFIER ::= {acPMSBCUserDefinedFailuresPMs 1}


     -- ****************************************
     -- acPMSBCInUserDefinedFailures1 table declaration
     -- ****************************************
     acPMSBCInUserDefinedFailures1Table OBJECT-TYPE
       SYNTAX SEQUENCE OF AcPMSBCInUserDefinedFailures1Entry
       MAX-ACCESS not-accessible
       STATUS obsolete
       DESCRIPTION
           "Number of user defined failures 1 for incoming dialogs (System global)"
       ::= {acPMSBCUserDefinedFailures1 1}



     -- ****************************************
     -- acPMSBCInUserDefinedFailures1 table entry
     -- ****************************************
     acPMSBCInUserDefinedFailures1Entry OBJECT-TYPE
       SYNTAX AcPMSBCInUserDefinedFailures1Entry
       MAX-ACCESS not-accessible
       STATUS obsolete
       DESCRIPTION
           ""
       INDEX {acPMSBCInUserDefinedFailures1Interval}
       ::= {acPMSBCInUserDefinedFailures1Table 1}



     -- ****************************************
     -- acPMSBCInUserDefinedFailures1 TABLE
     -- ****************************************
     AcPMSBCInUserDefinedFailures1Entry ::= SEQUENCE {
       acPMSBCInUserDefinedFailures1Interval           Unsigned32,
       acPMSBCInUserDefinedFailures1Val                Counter32
     }



     acPMSBCInUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures1Entry 1}



     acPMSBCInUserDefinedFailures1Val OBJECT-TYPE
       SYNTAX Counter32
       MAX-ACCESS read-only
       STATUS obsolete
       DESCRIPTION
           "Value of gauge or counter."
       ::= {acPMSBCInUserDefinedFailures1Entry 2}



     -- ****************************************
     -- acPMSBCOutUserDefinedFailures1 table declaration
     -- ****************************************
     acPMSBCOutUserDefinedFailures1Table OBJECT-TYPE
       SYNTAX SEQUENCE OF AcPMSBCOutUserDefinedFailures1Entry
       MAX-ACCESS not-accessible
       STATUS obsolete
       DESCRIPTION
           "Number of user defined failures 1 for outgoing dialogs (System global)"
       ::= {acPMSBCUserDefinedFailures1 2}



     -- ****************************************
     -- acPMSBCOutUserDefinedFailures1 table entry
     -- ****************************************
     acPMSBCOutUserDefinedFailures1Entry OBJECT-TYPE
       SYNTAX AcPMSBCOutUserDefinedFailures1Entry
       MAX-ACCESS not-accessible
       STATUS obsolete
       DESCRIPTION
           ""
       INDEX {acPMSBCOutUserDefinedFailures1Interval}
       ::= {acPMSBCOutUserDefinedFailures1Table 1}



     -- ****************************************
     -- acPMSBCOutUserDefinedFailures1 TABLE
     -- ****************************************
     AcPMSBCOutUserDefinedFailures1Entry ::= SEQUENCE {
       acPMSBCOutUserDefinedFailures1Interval          Unsigned32,
       acPMSBCOutUserDefinedFailures1Val               Counter32
     }



     acPMSBCOutUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures1Entry 1}



     acPMSBCOutUserDefinedFailures1Val OBJECT-TYPE
       SYNTAX Counter32
       MAX-ACCESS read-only
       STATUS obsolete
       DESCRIPTION
           "Value of gauge or counter."
       ::= {acPMSBCOutUserDefinedFailures1Entry 2}



     -- ****************************************
     -- acPMSBCSRDInUserDefinedFailures1 table declaration
     -- ****************************************
     acPMSBCSRDInUserDefinedFailures1Table OBJECT-TYPE
       SYNTAX SEQUENCE OF AcPMSBCSRDInUserDefinedFailures1Entry
       MAX-ACCESS not-accessible
       STATUS obsolete
       DESCRIPTION
           "Number of user defined failures 1 for incoming dialogs per SRD"
       ::= {acPMSBCUserDefinedFailures1 3}



     -- ****************************************
     -- acPMSBCSRDInUserDefinedFailures1 table entry
     -- ****************************************
     acPMSBCSRDInUserDefinedFailures1Entry OBJECT-TYPE
       SYNTAX AcPMSBCSRDInUserDefinedFailures1Entry
       MAX-ACCESS not-accessible
       STATUS obsolete
       DESCRIPTION
           ""
       INDEX {acPMSBCSRDInUserDefinedFailures1SrdID,acPMSBCSRDInUserDefinedFailures1Interval}
       ::= {acPMSBCSRDInUserDefinedFailures1Table 1}



     -- ****************************************
     -- acPMSBCSRDInUserDefinedFailures1 TABLE
     -- ****************************************
     AcPMSBCSRDInUserDefinedFailures1Entry ::= SEQUENCE {
       acPMSBCSRDInUserDefinedFailures1SrdID           Unsigned32,
       acPMSBCSRDInUserDefinedFailures1Interval        Unsigned32,
       acPMSBCSRDInUserDefinedFailures1Val             Counter32
     }



     acPMSBCSRDInUserDefinedFailures1SrdID OBJECT-TYPE
       SYNTAX Unsigned32 (0..600)
       MAX-ACCESS not-accessible
       STATUS obsolete
       DESCRIPTION
           "SRD number.
0 is the first SRD."
       ::= {acPMSBCSRDInUserDefinedFailures1Entry 1}



     acPMSBCSRDInUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures1Entry 2}



     acPMSBCSRDInUserDefinedFailures1Val OBJECT-TYPE
       SYNTAX Counter32
       MAX-ACCESS read-only
       STATUS obsolete
       DESCRIPTION
           "Value of gauge or counter."
       ::= {acPMSBCSRDInUserDefinedFailures1Entry 3}



     -- ****************************************
     -- acPMSBCSRDOutUserDefinedFailures1 table declaration
     -- ****************************************
     acPMSBCSRDOutUserDefinedFailures1Table OBJECT-TYPE
       SYNTAX SEQUENCE OF AcPMSBCSRDOutUserDefinedFailures1Entry
       MAX-ACCESS not-accessible
       STATUS obsolete
       DESCRIPTION
           "Number of user defined failures 1 for outgoing dialogs per SRD"
       ::= {acPMSBCUserDefinedFailures1 4}



     -- ****************************************
     -- acPMSBCSRDOutUserDefinedFailures1 table entry
     -- ****************************************
     acPMSBCSRDOutUserDefinedFailures1Entry OBJECT-TYPE
       SYNTAX AcPMSBCSRDOutUserDefinedFailures1Entry
       MAX-ACCESS not-accessible
       STATUS obsolete
       DESCRIPTION
           ""
       INDEX {acPMSBCSRDOutUserDefinedFailures1SrdID,acPMSBCSRDOutUserDefinedFailures1Interval}
       ::= {acPMSBCSRDOutUserDefinedFailures1Table 1}



     -- ****************************************
     -- acPMSBCSRDOutUserDefinedFailures1 TABLE
     -- ****************************************
     AcPMSBCSRDOutUserDefinedFailures1Entry ::= SEQUENCE {
       acPMSBCSRDOutUserDefinedFailures1SrdID          Unsigned32,
       acPMSBCSRDOutUserDefinedFailures1Interval       Unsigned32,
       acPMSBCSRDOutUserDefinedFailures1Val            Counter32
     }



     acPMSBCSRDOutUserDefinedFailures1SrdID OBJECT-TYPE
       SYNTAX Unsigned32 (0..600)
       MAX-ACCESS not-accessible
       STATUS obsolete
       DESCRIPTION
           "SRD number.
0 is the first SRD."
       ::= {acPMSBCSRDOutUserDefinedFailures1Entry 1}



     acPMSBCSRDOutUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures1Entry 2}



     acPMSBCSRDOutUserDefinedFailures1Val OBJECT-TYPE
       SYNTAX Counter32
       MAX-ACCESS read-only
       STATUS obsolete
       DESCRIPTION
           "Value of gauge or counter."
       ::= {acPMSBCSRDOutUserDefinedFailures1Entry 3}



     -- ****************************************
     -- acPMSBCIPGroupInUserDefinedFailures1 table declaration
     -- ****************************************
     acPMSBCIPGroupInUserDefinedFailures1Table OBJECT-TYPE
       SYNTAX SEQUENCE OF AcPMSBCIPGroupInUserDefinedFailures1Entry
       MAX-ACCESS not-accessible
       STATUS obsolete
       DESCRIPTION
           "Number of user defined failures 1 for incoming dialogs per IP Group"
       ::= {acPMSBCUserDefinedFailures1 5}



     -- ****************************************
     -- acPMSBCIPGroupInUserDefinedFailures1 table entry
     -- ****************************************
     acPMSBCIPGroupInUserDefinedFailures1Entry OBJECT-TYPE
       SYNTAX AcPMSBCIPGroupInUserDefinedFailures1Entry
       MAX-ACCESS not-accessible
       STATUS obsolete
       DESCRIPTION
           ""
       INDEX {acPMSBCIPGroupInUserDefinedFailures1IPGroupID,acPMSBCIPGroupInUserDefinedFailures1Interval}
       ::= {acPMSBCIPGroupInUserDefinedFailures1Table 1}



     -- ****************************************
     -- acPMSBCIPGroupInUserDefinedFailures1 TABLE
     -- ****************************************
     AcPMSBCIPGroupInUserDefinedFailures1Entry ::= SEQUENCE {
       acPMSBCIPGroupInUserDefinedFailures1IPGroupID   Unsigned32,
       acPMSBCIPGroupInUserDefinedFailures1Interval    Unsigned32,
       acPMSBCIPGroupInUserDefinedFailures1Val         Counter32
     }



     acPMSBCIPGroupInUserDefinedFailures1IPGroupID OBJECT-TYPE
       SYNTAX Unsigned32 (0..5000)
       MAX-ACCESS not-accessible
       STATUS obsolete
       DESCRIPTION
           "IP Group number."
       ::= {acPMSBCIPGroupInUserDefinedFailures1Entry 1}



     acPMSBCIPGroupInUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures1Entry 2}



     acPMSBCIPGroupInUserDefinedFailures1Val OBJECT-TYPE
       SYNTAX Counter32
       MAX-ACCESS read-only
       STATUS obsolete
       DESCRIPTION
           "Value of gauge or counter."
       ::= {acPMSBCIPGroupInUserDefinedFailures1Entry 3}



     -- ****************************************
     -- acPMSBCIPGroupOutUserDefinedFailures1 table declaration
     -- ****************************************
     acPMSBCIPGroupOutUserDefinedFailures1Table OBJECT-TYPE
       SYNTAX SEQUENCE OF AcPMSBCIPGroupOutUserDefinedFailures1Entry
       MAX-ACCESS not-accessible
       STATUS obsolete
       DESCRIPTION
           "Number of user defined failures 1 for outgoing dialogs per IP Group"
       ::= {acPMSBCUserDefinedFailures1 6}



     -- ****************************************
     -- acPMSBCIPGroupOutUserDefinedFailures1 table entry
     -- ****************************************
     acPMSBCIPGroupOutUserDefinedFailures1Entry OBJECT-TYPE
       SYNTAX AcPMSBCIPGroupOutUserDefinedFailures1Entry
       MAX-ACCESS not-accessible
       STATUS obsolete
       DESCRIPTION
           ""
       INDEX {acPMSBCIPGroupOutUserDefinedFailures1IPGroupID,acPMSBCIPGroupOutUserDefinedFailures1Interval}
       ::= {acPMSBCIPGroupOutUserDefinedFailures1Table 1}



     -- ****************************************
     -- acPMSBCIPGroupOutUserDefinedFailures1 TABLE
     -- ****************************************
     AcPMSBCIPGroupOutUserDefinedFailures1Entry ::= SEQUENCE {
       acPMSBCIPGroupOutUserDefinedFailures1IPGroupID  Unsigned32,
       acPMSBCIPGroupOutUserDefinedFailures1Interval   Unsigned32,
       acPMSBCIPGroupOutUserDefinedFailures1Val        Counter32
     }



     acPMSBCIPGroupOutUserDefinedFailures1IPGroupID OBJECT-TYPE
       SYNTAX Unsigned32 (0..5000)
       MAX-ACCESS not-accessible
       STATUS obsolete
       DESCRIPTION
           "IP Group number."
       ::= {acPMSBCIPGroupOutUserDefinedFailures1Entry 1}



     acPMSBCIPGroupOutUserDefinedFailures1Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures1Entry 2}



     acPMSBCIPGroupOutUserDefinedFailures1Val OBJECT-TYPE
       SYNTAX Counter32
       MAX-ACCESS read-only
       STATUS obsolete
       DESCRIPTION
           "Value of gauge or counter."
       ::= {acPMSBCIPGroupOutUserDefinedFailures1Entry 3}



     acPMSBCUserDefinedFailures2 OBJECT IDENTIFIER ::= {acPMSBCUserDefinedFailuresPMs 2}


     -- ****************************************
     -- acPMSBCInUserDefinedFailures2 table declaration
     -- ****************************************
     acPMSBCInUserDefinedFailures2Table OBJECT-TYPE
       SYNTAX SEQUENCE OF AcPMSBCInUserDefinedFailures2Entry
       MAX-ACCESS not-accessible
       STATUS obsolete
       DESCRIPTION
           "Number of user defined failures 2 for incoming dialogs (System global)"
       ::= {acPMSBCUserDefinedFailures2 1}



     -- ****************************************
     -- acPMSBCInUserDefinedFailures2 table entry
     -- ****************************************
     acPMSBCInUserDefinedFailures2Entry OBJECT-TYPE
       SYNTAX AcPMSBCInUserDefinedFailures2Entry
       MAX-ACCESS not-accessible
       STATUS obsolete
       DESCRIPTION
           ""
       INDEX {acPMSBCInUserDefinedFailures2Interval}
       ::= {acPMSBCInUserDefinedFailures2Table 1}



     -- ****************************************
     -- acPMSBCInUserDefinedFailures2 TABLE
     -- ****************************************
     AcPMSBCInUserDefinedFailures2Entry ::= SEQUENCE {
       acPMSBCInUserDefinedFailures2Interval           Unsigned32,
       acPMSBCInUserDefinedFailures2Val                Counter32
     }



     acPMSBCInUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures2Entry 1}



     acPMSBCInUserDefinedFailures2Val OBJECT-TYPE
       SYNTAX Counter32
       MAX-ACCESS read-only
       STATUS obsolete
       DESCRIPTION
           "Value of gauge or counter."
       ::= {acPMSBCInUserDefinedFailures2Entry 2}



     -- ****************************************
     -- acPMSBCOutUserDefinedFailures2 table declaration
     -- ****************************************
     acPMSBCOutUserDefinedFailures2Table OBJECT-TYPE
       SYNTAX SEQUENCE OF AcPMSBCOutUserDefinedFailures2Entry
       MAX-ACCESS not-accessible
       STATUS obsolete
       DESCRIPTION
           "Number of user defined failures 2 for outgoing dialogs (System global)"
       ::= {acPMSBCUserDefinedFailures2 2}



     -- ****************************************
     -- acPMSBCOutUserDefinedFailures2 table entry
     -- ****************************************
     acPMSBCOutUserDefinedFailures2Entry OBJECT-TYPE
       SYNTAX AcPMSBCOutUserDefinedFailures2Entry
       MAX-ACCESS not-accessible
       STATUS obsolete
       DESCRIPTION
           ""
       INDEX {acPMSBCOutUserDefinedFailures2Interval}
       ::= {acPMSBCOutUserDefinedFailures2Table 1}



     -- ****************************************
     -- acPMSBCOutUserDefinedFailures2 TABLE
     -- ****************************************
     AcPMSBCOutUserDefinedFailures2Entry ::= SEQUENCE {
       acPMSBCOutUserDefinedFailures2Interval          Unsigned32,
       acPMSBCOutUserDefinedFailures2Val               Counter32
     }



     acPMSBCOutUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures2Entry 1}



     acPMSBCOutUserDefinedFailures2Val OBJECT-TYPE
       SYNTAX Counter32
       MAX-ACCESS read-only
       STATUS obsolete
       DESCRIPTION
           "Value of gauge or counter."
       ::= {acPMSBCOutUserDefinedFailures2Entry 2}



     -- ****************************************
     -- acPMSBCSRDInUserDefinedFailures2 table declaration
     -- ****************************************
     acPMSBCSRDInUserDefinedFailures2Table OBJECT-TYPE
       SYNTAX SEQUENCE OF AcPMSBCSRDInUserDefinedFailures2Entry
       MAX-ACCESS not-accessible
       STATUS obsolete
       DESCRIPTION
           "Number of user defined failures 2 for incoming dialogs per SRD"
       ::= {acPMSBCUserDefinedFailures2 3}



     -- ****************************************
     -- acPMSBCSRDInUserDefinedFailures2 table entry
     -- ****************************************
     acPMSBCSRDInUserDefinedFailures2Entry OBJECT-TYPE
       SYNTAX AcPMSBCSRDInUserDefinedFailures2Entry
       MAX-ACCESS not-accessible
       STATUS obsolete
       DESCRIPTION
           ""
       INDEX {acPMSBCSRDInUserDefinedFailures2SrdID,acPMSBCSRDInUserDefinedFailures2Interval}
       ::= {acPMSBCSRDInUserDefinedFailures2Table 1}



     -- ****************************************
     -- acPMSBCSRDInUserDefinedFailures2 TABLE
     -- ****************************************
     AcPMSBCSRDInUserDefinedFailures2Entry ::= SEQUENCE {
       acPMSBCSRDInUserDefinedFailures2SrdID           Unsigned32,
       acPMSBCSRDInUserDefinedFailures2Interval        Unsigned32,
       acPMSBCSRDInUserDefinedFailures2Val             Counter32
     }



     acPMSBCSRDInUserDefinedFailures2SrdID OBJECT-TYPE
       SYNTAX Unsigned32 (0..600)
       MAX-ACCESS not-accessible
       STATUS obsolete
       DESCRIPTION
           "SRD number.
0 is the first SRD."
       ::= {acPMSBCSRDInUserDefinedFailures2Entry 1}



     acPMSBCSRDInUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures2Entry 2}



     acPMSBCSRDInUserDefinedFailures2Val OBJECT-TYPE
       SYNTAX Counter32
       MAX-ACCESS read-only
       STATUS obsolete
       DESCRIPTION
           "Value of gauge or counter."
       ::= {acPMSBCSRDInUserDefinedFailures2Entry 3}



     -- ****************************************
     -- acPMSBCSRDOutUserDefinedFailures2 table declaration
     -- ****************************************
     acPMSBCSRDOutUserDefinedFailures2Table OBJECT-TYPE
       SYNTAX SEQUENCE OF AcPMSBCSRDOutUserDefinedFailures2Entry
       MAX-ACCESS not-accessible
       STATUS obsolete
       DESCRIPTION
           "Number of user defined failures 2 for outgoing dialogs per SRD"
       ::= {acPMSBCUserDefinedFailures2 4}



     -- ****************************************
     -- acPMSBCSRDOutUserDefinedFailures2 table entry
     -- ****************************************
     acPMSBCSRDOutUserDefinedFailures2Entry OBJECT-TYPE
       SYNTAX AcPMSBCSRDOutUserDefinedFailures2Entry
       MAX-ACCESS not-accessible
       STATUS obsolete
       DESCRIPTION
           ""
       INDEX {acPMSBCSRDOutUserDefinedFailures2SrdID,acPMSBCSRDOutUserDefinedFailures2Interval}
       ::= {acPMSBCSRDOutUserDefinedFailures2Table 1}



     -- ****************************************
     -- acPMSBCSRDOutUserDefinedFailures2 TABLE
     -- ****************************************
     AcPMSBCSRDOutUserDefinedFailures2Entry ::= SEQUENCE {
       acPMSBCSRDOutUserDefinedFailures2SrdID          Unsigned32,
       acPMSBCSRDOutUserDefinedFailures2Interval       Unsigned32,
       acPMSBCSRDOutUserDefinedFailures2Val            Counter32
     }



     acPMSBCSRDOutUserDefinedFailures2SrdID OBJECT-TYPE
       SYNTAX Unsigned32 (0..600)
       MAX-ACCESS not-accessible
       STATUS obsolete
       DESCRIPTION
           "SRD number.
0 is the first SRD."
       ::= {acPMSBCSRDOutUserDefinedFailures2Entry 1}



     acPMSBCSRDOutUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures2Entry 2}



     acPMSBCSRDOutUserDefinedFailures2Val OBJECT-TYPE
       SYNTAX Counter32
       MAX-ACCESS read-only
       STATUS obsolete
       DESCRIPTION
           "Value of gauge or counter."
       ::= {acPMSBCSRDOutUserDefinedFailures2Entry 3}



     -- ****************************************
     -- acPMSBCIPGroupInUserDefinedFailures2 table declaration
     -- ****************************************
     acPMSBCIPGroupInUserDefinedFailures2Table OBJECT-TYPE
       SYNTAX SEQUENCE OF AcPMSBCIPGroupInUserDefinedFailures2Entry
       MAX-ACCESS not-accessible
       STATUS obsolete
       DESCRIPTION
           "Number of user defined failures 2 for incoming dialogs per IP Group"
       ::= {acPMSBCUserDefinedFailures2 5}



     -- ****************************************
     -- acPMSBCIPGroupInUserDefinedFailures2 table entry
     -- ****************************************
     acPMSBCIPGroupInUserDefinedFailures2Entry OBJECT-TYPE
       SYNTAX AcPMSBCIPGroupInUserDefinedFailures2Entry
       MAX-ACCESS not-accessible
       STATUS obsolete
       DESCRIPTION
           ""
       INDEX {acPMSBCIPGroupInUserDefinedFailures2IPGroupID,acPMSBCIPGroupInUserDefinedFailures2Interval}
       ::= {acPMSBCIPGroupInUserDefinedFailures2Table 1}



     -- ****************************************
     -- acPMSBCIPGroupInUserDefinedFailures2 TABLE
     -- ****************************************
     AcPMSBCIPGroupInUserDefinedFailures2Entry ::= SEQUENCE {
       acPMSBCIPGroupInUserDefinedFailures2IPGroupID   Unsigned32,
       acPMSBCIPGroupInUserDefinedFailures2Interval    Unsigned32,
       acPMSBCIPGroupInUserDefinedFailures2Val         Counter32
     }



     acPMSBCIPGroupInUserDefinedFailures2IPGroupID OBJECT-TYPE
       SYNTAX Unsigned32 (0..5000)
       MAX-ACCESS not-accessible
       STATUS obsolete
       DESCRIPTION
           "IP Group number."
       ::= {acPMSBCIPGroupInUserDefinedFailures2Entry 1}



     acPMSBCIPGroupInUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures2Entry 2}



     acPMSBCIPGroupInUserDefinedFailures2Val OBJECT-TYPE
       SYNTAX Counter32
       MAX-ACCESS read-only
       STATUS obsolete
       DESCRIPTION
           "Value of gauge or counter."
       ::= {acPMSBCIPGroupInUserDefinedFailures2Entry 3}



     -- ****************************************
     -- acPMSBCIPGroupOutUserDefinedFailures2 table declaration
     -- ****************************************
     acPMSBCIPGroupOutUserDefinedFailures2Table OBJECT-TYPE
       SYNTAX SEQUENCE OF AcPMSBCIPGroupOutUserDefinedFailures2Entry
       MAX-ACCESS not-accessible
       STATUS obsolete
       DESCRIPTION
           "Number of user defined failures 2 for outgoing dialogs per IP Group"
       ::= {acPMSBCUserDefinedFailures2 6}



     -- ****************************************
     -- acPMSBCIPGroupOutUserDefinedFailures2 table entry
     -- ****************************************
     acPMSBCIPGroupOutUserDefinedFailures2Entry OBJECT-TYPE
       SYNTAX AcPMSBCIPGroupOutUserDefinedFailures2Entry
       MAX-ACCESS not-accessible
       STATUS obsolete
       DESCRIPTION
           ""
       INDEX {acPMSBCIPGroupOutUserDefinedFailures2IPGroupID,acPMSBCIPGroupOutUserDefinedFailures2Interval}
       ::= {acPMSBCIPGroupOutUserDefinedFailures2Table 1}



     -- ****************************************
     -- acPMSBCIPGroupOutUserDefinedFailures2 TABLE
     -- ****************************************
     AcPMSBCIPGroupOutUserDefinedFailures2Entry ::= SEQUENCE {
       acPMSBCIPGroupOutUserDefinedFailures2IPGroupID  Unsigned32,
       acPMSBCIPGroupOutUserDefinedFailures2Interval   Unsigned32,
       acPMSBCIPGroupOutUserDefinedFailures2Val        Counter32
     }



     acPMSBCIPGroupOutUserDefinedFailures2IPGroupID OBJECT-TYPE
       SYNTAX Unsigned32 (0..5000)
       MAX-ACCESS not-accessible
       STATUS obsolete
       DESCRIPTION
           "IP Group number."
       ::= {acPMSBCIPGroupOutUserDefinedFailures2Entry 1}



     acPMSBCIPGroupOutUserDefinedFailures2Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures2Entry 2}



     acPMSBCIPGroupOutUserDefinedFailures2Val OBJECT-TYPE
       SYNTAX Counter32
       MAX-ACCESS read-only
       STATUS obsolete
       DESCRIPTION
           "Value of gauge or counter."
       ::= {acPMSBCIPGroupOutUserDefinedFailures2Entry 3}



     acPMSBCUserDefinedFailures3 OBJECT IDENTIFIER ::= {acPMSBCUserDefinedFailuresPMs 3}


     -- ****************************************
     -- acPMSBCInUserDefinedFailures3 table declaration
     -- ****************************************
     acPMSBCInUserDefinedFailures3Table OBJECT-TYPE
       SYNTAX SEQUENCE OF AcPMSBCInUserDefinedFailures3Entry
       MAX-ACCESS not-accessible
       STATUS obsolete
       DESCRIPTION
           "Number of user defined failures 3 for incoming dialogs (System global)"
       ::= {acPMSBCUserDefinedFailures3 1}



     -- ****************************************
     -- acPMSBCInUserDefinedFailures3 table entry
     -- ****************************************
     acPMSBCInUserDefinedFailures3Entry OBJECT-TYPE
       SYNTAX AcPMSBCInUserDefinedFailures3Entry
       MAX-ACCESS not-accessible
       STATUS obsolete
       DESCRIPTION
           ""
       INDEX {acPMSBCInUserDefinedFailures3Interval}
       ::= {acPMSBCInUserDefinedFailures3Table 1}



     -- ****************************************
     -- acPMSBCInUserDefinedFailures3 TABLE
     -- ****************************************
     AcPMSBCInUserDefinedFailures3Entry ::= SEQUENCE {
       acPMSBCInUserDefinedFailures3Interval           Unsigned32,
       acPMSBCInUserDefinedFailures3Val                Counter32
     }



     acPMSBCInUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures3Entry 1}



     acPMSBCInUserDefinedFailures3Val OBJECT-TYPE
       SYNTAX Counter32
       MAX-ACCESS read-only
       STATUS obsolete
       DESCRIPTION
           "Value of gauge or counter."
       ::= {acPMSBCInUserDefinedFailures3Entry 2}



     -- ****************************************
     -- acPMSBCOutUserDefinedFailures3 table declaration
     -- ****************************************
     acPMSBCOutUserDefinedFailures3Table OBJECT-TYPE
       SYNTAX SEQUENCE OF AcPMSBCOutUserDefinedFailures3Entry
       MAX-ACCESS not-accessible
       STATUS obsolete
       DESCRIPTION
           "Number of user defined Failures 3 for outgoing dialogs (System global)"
       ::= {acPMSBCUserDefinedFailures3 2}



     -- ****************************************
     -- acPMSBCOutUserDefinedFailures3 table entry
     -- ****************************************
     acPMSBCOutUserDefinedFailures3Entry OBJECT-TYPE
       SYNTAX AcPMSBCOutUserDefinedFailures3Entry
       MAX-ACCESS not-accessible
       STATUS obsolete
       DESCRIPTION
           ""
       INDEX {acPMSBCOutUserDefinedFailures3Interval}
       ::= {acPMSBCOutUserDefinedFailures3Table 1}



     -- ****************************************
     -- acPMSBCOutUserDefinedFailures3 TABLE
     -- ****************************************
     AcPMSBCOutUserDefinedFailures3Entry ::= SEQUENCE {
       acPMSBCOutUserDefinedFailures3Interval          Unsigned32,
       acPMSBCOutUserDefinedFailures3Val               Counter32
     }



     acPMSBCOutUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures3Entry 1}



     acPMSBCOutUserDefinedFailures3Val OBJECT-TYPE
       SYNTAX Counter32
       MAX-ACCESS read-only
       STATUS obsolete
       DESCRIPTION
           "Value of gauge or counter."
       ::= {acPMSBCOutUserDefinedFailures3Entry 2}



     -- ****************************************
     -- acPMSBCSRDInUserDefinedFailures3 table declaration
     -- ****************************************
     acPMSBCSRDInUserDefinedFailures3Table OBJECT-TYPE
       SYNTAX SEQUENCE OF AcPMSBCSRDInUserDefinedFailures3Entry
       MAX-ACCESS not-accessible
       STATUS obsolete
       DESCRIPTION
           "Number of user defined Failures 3 for incoming dialogs per SRD"
       ::= {acPMSBCUserDefinedFailures3 3}



     -- ****************************************
     -- acPMSBCSRDInUserDefinedFailures3 table entry
     -- ****************************************
     acPMSBCSRDInUserDefinedFailures3Entry OBJECT-TYPE
       SYNTAX AcPMSBCSRDInUserDefinedFailures3Entry
       MAX-ACCESS not-accessible
       STATUS obsolete
       DESCRIPTION
           ""
       INDEX {acPMSBCSRDInUserDefinedFailures3SrdID,acPMSBCSRDInUserDefinedFailures3Interval}
       ::= {acPMSBCSRDInUserDefinedFailures3Table 1}



     -- ****************************************
     -- acPMSBCSRDInUserDefinedFailures3 TABLE
     -- ****************************************
     AcPMSBCSRDInUserDefinedFailures3Entry ::= SEQUENCE {
       acPMSBCSRDInUserDefinedFailures3SrdID           Unsigned32,
       acPMSBCSRDInUserDefinedFailures3Interval        Unsigned32,
       acPMSBCSRDInUserDefinedFailures3Val             Counter32
     }



     acPMSBCSRDInUserDefinedFailures3SrdID OBJECT-TYPE
       SYNTAX Unsigned32 (0..600)
       MAX-ACCESS not-accessible
       STATUS obsolete
       DESCRIPTION
           "SRD number.
0 is the first SRD."
       ::= {acPMSBCSRDInUserDefinedFailures3Entry 1}



     acPMSBCSRDInUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures3Entry 2}



     acPMSBCSRDInUserDefinedFailures3Val OBJECT-TYPE
       SYNTAX Counter32
       MAX-ACCESS read-only
       STATUS obsolete
       DESCRIPTION
           "Value of gauge or counter."
       ::= {acPMSBCSRDInUserDefinedFailures3Entry 3}



     -- ****************************************
     -- acPMSBCSRDOutUserDefinedFailures3 table declaration
     -- ****************************************
     acPMSBCSRDOutUserDefinedFailures3Table OBJECT-TYPE
       SYNTAX SEQUENCE OF AcPMSBCSRDOutUserDefinedFailures3Entry
       MAX-ACCESS not-accessible
       STATUS obsolete
       DESCRIPTION
           "Number of user defined Failures 3 for outgoing dialogs per SRD"
       ::= {acPMSBCUserDefinedFailures3 4}



     -- ****************************************
     -- acPMSBCSRDOutUserDefinedFailures3 table entry
     -- ****************************************
     acPMSBCSRDOutUserDefinedFailures3Entry OBJECT-TYPE
       SYNTAX AcPMSBCSRDOutUserDefinedFailures3Entry
       MAX-ACCESS not-accessible
       STATUS obsolete
       DESCRIPTION
           ""
       INDEX {acPMSBCSRDOutUserDefinedFailures3SrdID,acPMSBCSRDOutUserDefinedFailures3Interval}
       ::= {acPMSBCSRDOutUserDefinedFailures3Table 1}



     -- ****************************************
     -- acPMSBCSRDOutUserDefinedFailures3 TABLE
     -- ****************************************
     AcPMSBCSRDOutUserDefinedFailures3Entry ::= SEQUENCE {
       acPMSBCSRDOutUserDefinedFailures3SrdID          Unsigned32,
       acPMSBCSRDOutUserDefinedFailures3Interval       Unsigned32,
       acPMSBCSRDOutUserDefinedFailures3Val            Counter32
     }



     acPMSBCSRDOutUserDefinedFailures3SrdID OBJECT-TYPE
       SYNTAX Unsigned32 (0..600)
       MAX-ACCESS not-accessible
       STATUS obsolete
       DESCRIPTION
           "SRD number.
0 is the first SRD."
       ::= {acPMSBCSRDOutUserDefinedFailures3Entry 1}



     acPMSBCSRDOutUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures3Entry 2}



     acPMSBCSRDOutUserDefinedFailures3Val OBJECT-TYPE
       SYNTAX Counter32
       MAX-ACCESS read-only
       STATUS obsolete
       DESCRIPTION
           "Value of gauge or counter."
       ::= {acPMSBCSRDOutUserDefinedFailures3Entry 3}



     -- ****************************************
     -- acPMSBCIPGroupInUserDefinedFailures3 table declaration
     -- ****************************************
     acPMSBCIPGroupInUserDefinedFailures3Table OBJECT-TYPE
       SYNTAX SEQUENCE OF AcPMSBCIPGroupInUserDefinedFailures3Entry
       MAX-ACCESS not-accessible
       STATUS obsolete
       DESCRIPTION
           "Number of user defined Failures 3 for incoming dialogs per IP Group"
       ::= {acPMSBCUserDefinedFailures3 5}



     -- ****************************************
     -- acPMSBCIPGroupInUserDefinedFailures3 table entry
     -- ****************************************
     acPMSBCIPGroupInUserDefinedFailures3Entry OBJECT-TYPE
       SYNTAX AcPMSBCIPGroupInUserDefinedFailures3Entry
       MAX-ACCESS not-accessible
       STATUS obsolete
       DESCRIPTION
           ""
       INDEX {acPMSBCIPGroupInUserDefinedFailures3IPGroupID,acPMSBCIPGroupInUserDefinedFailures3Interval}
       ::= {acPMSBCIPGroupInUserDefinedFailures3Table 1}



     -- ****************************************
     -- acPMSBCIPGroupInUserDefinedFailures3 TABLE
     -- ****************************************
     AcPMSBCIPGroupInUserDefinedFailures3Entry ::= SEQUENCE {
       acPMSBCIPGroupInUserDefinedFailures3IPGroupID   Unsigned32,
       acPMSBCIPGroupInUserDefinedFailures3Interval    Unsigned32,
       acPMSBCIPGroupInUserDefinedFailures3Val         Counter32
     }



     acPMSBCIPGroupInUserDefinedFailures3IPGroupID OBJECT-TYPE
       SYNTAX Unsigned32 (0..5000)
       MAX-ACCESS not-accessible
       STATUS obsolete
       DESCRIPTION
           "IP Group number."
       ::= {acPMSBCIPGroupInUserDefinedFailures3Entry 1}



     acPMSBCIPGroupInUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures3Entry 2}



     acPMSBCIPGroupInUserDefinedFailures3Val OBJECT-TYPE
       SYNTAX Counter32
       MAX-ACCESS read-only
       STATUS obsolete
       DESCRIPTION
           "Value of gauge or counter."
       ::= {acPMSBCIPGroupInUserDefinedFailures3Entry 3}



     -- ****************************************
     -- acPMSBCIPGroupOutUserDefinedFailures3 table declaration
     -- ****************************************
     acPMSBCIPGroupOutUserDefinedFailures3Table OBJECT-TYPE
       SYNTAX SEQUENCE OF AcPMSBCIPGroupOutUserDefinedFailures3Entry
       MAX-ACCESS not-accessible
       STATUS obsolete
       DESCRIPTION
           "Number of user defined Failures 3 for outgoing dialogs per IP Group"
       ::= {acPMSBCUserDefinedFailures3 6}



     -- ****************************************
     -- acPMSBCIPGroupOutUserDefinedFailures3 table entry
     -- ****************************************
     acPMSBCIPGroupOutUserDefinedFailures3Entry OBJECT-TYPE
       SYNTAX AcPMSBCIPGroupOutUserDefinedFailures3Entry
       MAX-ACCESS not-accessible
       STATUS obsolete
       DESCRIPTION
           ""
       INDEX {acPMSBCIPGroupOutUserDefinedFailures3IPGroupID,acPMSBCIPGroupOutUserDefinedFailures3Interval}
       ::= {acPMSBCIPGroupOutUserDefinedFailures3Table 1}



     -- ****************************************
     -- acPMSBCIPGroupOutUserDefinedFailures3 TABLE
     -- ****************************************
     AcPMSBCIPGroupOutUserDefinedFailures3Entry ::= SEQUENCE {
       acPMSBCIPGroupOutUserDefinedFailures3IPGroupID  Unsigned32,
       acPMSBCIPGroupOutUserDefinedFailures3Interval   Unsigned32,
       acPMSBCIPGroupOutUserDefinedFailures3Val        Counter32
     }



     acPMSBCIPGroupOutUserDefinedFailures3IPGroupID OBJECT-TYPE
       SYNTAX Unsigned32 (0..5000)
       MAX-ACCESS not-accessible
       STATUS obsolete
       DESCRIPTION
           "IP Group number."
       ::= {acPMSBCIPGroupOutUserDefinedFailures3Entry 1}



     acPMSBCIPGroupOutUserDefinedFailures3Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures3Entry 2}



     acPMSBCIPGroupOutUserDefinedFailures3Val OBJECT-TYPE
       SYNTAX Counter32
       MAX-ACCESS read-only
       STATUS obsolete
       DESCRIPTION
           "Value of gauge or counter."
       ::= {acPMSBCIPGroupOutUserDefinedFailures3Entry 3}



     acPMSBCUserDefinedFailures4 OBJECT IDENTIFIER ::= {acPMSBCUserDefinedFailuresPMs 4}


     -- ****************************************
     -- acPMSBCInUserDefinedFailures4 table declaration
     -- ****************************************
     acPMSBCInUserDefinedFailures4Table OBJECT-TYPE
       SYNTAX SEQUENCE OF AcPMSBCInUserDefinedFailures4Entry
       MAX-ACCESS not-accessible
       STATUS obsolete
       DESCRIPTION
           "Number of user defined failures 4 for incoming dialogs (System global)"
       ::= {acPMSBCUserDefinedFailures4 1}



     -- ****************************************
     -- acPMSBCInUserDefinedFailures4 table entry
     -- ****************************************
     acPMSBCInUserDefinedFailures4Entry OBJECT-TYPE
       SYNTAX AcPMSBCInUserDefinedFailures4Entry
       MAX-ACCESS not-accessible
       STATUS obsolete
       DESCRIPTION
           ""
       INDEX {acPMSBCInUserDefinedFailures4Interval}
       ::= {acPMSBCInUserDefinedFailures4Table 1}



     -- ****************************************
     -- acPMSBCInUserDefinedFailures4 TABLE
     -- ****************************************
     AcPMSBCInUserDefinedFailures4Entry ::= SEQUENCE {
       acPMSBCInUserDefinedFailures4Interval           Unsigned32,
       acPMSBCInUserDefinedFailures4Val                Counter32
     }



     acPMSBCInUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures4Entry 1}



     acPMSBCInUserDefinedFailures4Val OBJECT-TYPE
       SYNTAX Counter32
       MAX-ACCESS read-only
       STATUS obsolete
       DESCRIPTION
           "Value of gauge or counter."
       ::= {acPMSBCInUserDefinedFailures4Entry 2}



     -- ****************************************
     -- acPMSBCOutUserDefinedFailures4 table declaration
     -- ****************************************
     acPMSBCOutUserDefinedFailures4Table OBJECT-TYPE
       SYNTAX SEQUENCE OF AcPMSBCOutUserDefinedFailures4Entry
       MAX-ACCESS not-accessible
       STATUS obsolete
       DESCRIPTION
           "Number of user defined Failures 4 for outgoing dialogs (System global)"
       ::= {acPMSBCUserDefinedFailures4 2}



     -- ****************************************
     -- acPMSBCOutUserDefinedFailures4 table entry
     -- ****************************************
     acPMSBCOutUserDefinedFailures4Entry OBJECT-TYPE
       SYNTAX AcPMSBCOutUserDefinedFailures4Entry
       MAX-ACCESS not-accessible
       STATUS obsolete
       DESCRIPTION
           ""
       INDEX {acPMSBCOutUserDefinedFailures4Interval}
       ::= {acPMSBCOutUserDefinedFailures4Table 1}



     -- ****************************************
     -- acPMSBCOutUserDefinedFailures4 TABLE
     -- ****************************************
     AcPMSBCOutUserDefinedFailures4Entry ::= SEQUENCE {
       acPMSBCOutUserDefinedFailures4Interval          Unsigned32,
       acPMSBCOutUserDefinedFailures4Val               Counter32
     }



     acPMSBCOutUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures4Entry 1}



     acPMSBCOutUserDefinedFailures4Val OBJECT-TYPE
       SYNTAX Counter32
       MAX-ACCESS read-only
       STATUS obsolete
       DESCRIPTION
           "Value of gauge or counter."
       ::= {acPMSBCOutUserDefinedFailures4Entry 2}



     -- ****************************************
     -- acPMSBCSRDInUserDefinedFailures4 table declaration
     -- ****************************************
     acPMSBCSRDInUserDefinedFailures4Table OBJECT-TYPE
       SYNTAX SEQUENCE OF AcPMSBCSRDInUserDefinedFailures4Entry
       MAX-ACCESS not-accessible
       STATUS obsolete
       DESCRIPTION
           "Number of user defined Failures 4 for incoming dialogs per SRD"
       ::= {acPMSBCUserDefinedFailures4 3}



     -- ****************************************
     -- acPMSBCSRDInUserDefinedFailures4 table entry
     -- ****************************************
     acPMSBCSRDInUserDefinedFailures4Entry OBJECT-TYPE
       SYNTAX AcPMSBCSRDInUserDefinedFailures4Entry
       MAX-ACCESS not-accessible
       STATUS obsolete
       DESCRIPTION
           ""
       INDEX {acPMSBCSRDInUserDefinedFailures4SrdID,acPMSBCSRDInUserDefinedFailures4Interval}
       ::= {acPMSBCSRDInUserDefinedFailures4Table 1}



     -- ****************************************
     -- acPMSBCSRDInUserDefinedFailures4 TABLE
     -- ****************************************
     AcPMSBCSRDInUserDefinedFailures4Entry ::= SEQUENCE {
       acPMSBCSRDInUserDefinedFailures4SrdID           Unsigned32,
       acPMSBCSRDInUserDefinedFailures4Interval        Unsigned32,
       acPMSBCSRDInUserDefinedFailures4Val             Counter32
     }



     acPMSBCSRDInUserDefinedFailures4SrdID OBJECT-TYPE
       SYNTAX Unsigned32 (0..600)
       MAX-ACCESS not-accessible
       STATUS obsolete
       DESCRIPTION
           "SRD number.
0 is the first SRD."
       ::= {acPMSBCSRDInUserDefinedFailures4Entry 1}



     acPMSBCSRDInUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures4Entry 2}



     acPMSBCSRDInUserDefinedFailures4Val OBJECT-TYPE
       SYNTAX Counter32
       MAX-ACCESS read-only
       STATUS obsolete
       DESCRIPTION
           "Value of gauge or counter."
       ::= {acPMSBCSRDInUserDefinedFailures4Entry 3}



     -- ****************************************
     -- acPMSBCSRDOutUserDefinedFailures4 table declaration
     -- ****************************************
     acPMSBCSRDOutUserDefinedFailures4Table OBJECT-TYPE
       SYNTAX SEQUENCE OF AcPMSBCSRDOutUserDefinedFailures4Entry
       MAX-ACCESS not-accessible
       STATUS obsolete
       DESCRIPTION
           "Number of user defined Failures 4 for outgoing dialogs per SRD"
       ::= {acPMSBCUserDefinedFailures4 4}



     -- ****************************************
     -- acPMSBCSRDOutUserDefinedFailures4 table entry
     -- ****************************************
     acPMSBCSRDOutUserDefinedFailures4Entry OBJECT-TYPE
       SYNTAX AcPMSBCSRDOutUserDefinedFailures4Entry
       MAX-ACCESS not-accessible
       STATUS obsolete
       DESCRIPTION
           ""
       INDEX {acPMSBCSRDOutUserDefinedFailures4SrdID,acPMSBCSRDOutUserDefinedFailures4Interval}
       ::= {acPMSBCSRDOutUserDefinedFailures4Table 1}



     -- ****************************************
     -- acPMSBCSRDOutUserDefinedFailures4 TABLE
     -- ****************************************
     AcPMSBCSRDOutUserDefinedFailures4Entry ::= SEQUENCE {
       acPMSBCSRDOutUserDefinedFailures4SrdID          Unsigned32,
       acPMSBCSRDOutUserDefinedFailures4Interval       Unsigned32,
       acPMSBCSRDOutUserDefinedFailures4Val            Counter32
     }



     acPMSBCSRDOutUserDefinedFailures4SrdID OBJECT-TYPE
       SYNTAX Unsigned32 (0..600)
       MAX-ACCESS not-accessible
       STATUS obsolete
       DESCRIPTION
           "SRD number.
0 is the first SRD."
       ::= {acPMSBCSRDOutUserDefinedFailures4Entry 1}



     acPMSBCSRDOutUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures4Entry 2}



     acPMSBCSRDOutUserDefinedFailures4Val OBJECT-TYPE
       SYNTAX Counter32
       MAX-ACCESS read-only
       STATUS obsolete
       DESCRIPTION
           "Value of gauge or counter."
       ::= {acPMSBCSRDOutUserDefinedFailures4Entry 3}



     -- ****************************************
     -- acPMSBCIPGroupInUserDefinedFailures4 table declaration
     -- ****************************************
     acPMSBCIPGroupInUserDefinedFailures4Table OBJECT-TYPE
       SYNTAX SEQUENCE OF AcPMSBCIPGroupInUserDefinedFailures4Entry
       MAX-ACCESS not-accessible
       STATUS obsolete
       DESCRIPTION
           "Number of user defined Failures 4 for incoming dialogs per IP Group"
       ::= {acPMSBCUserDefinedFailures4 5}



     -- ****************************************
     -- acPMSBCIPGroupInUserDefinedFailures4 table entry
     -- ****************************************
     acPMSBCIPGroupInUserDefinedFailures4Entry OBJECT-TYPE
       SYNTAX AcPMSBCIPGroupInUserDefinedFailures4Entry
       MAX-ACCESS not-accessible
       STATUS obsolete
       DESCRIPTION
           ""
       INDEX {acPMSBCIPGroupInUserDefinedFailures4IPGroupID,acPMSBCIPGroupInUserDefinedFailures4Interval}
       ::= {acPMSBCIPGroupInUserDefinedFailures4Table 1}



     -- ****************************************
     -- acPMSBCIPGroupInUserDefinedFailures4 TABLE
     -- ****************************************
     AcPMSBCIPGroupInUserDefinedFailures4Entry ::= SEQUENCE {
       acPMSBCIPGroupInUserDefinedFailures4IPGroupID   Unsigned32,
       acPMSBCIPGroupInUserDefinedFailures4Interval    Unsigned32,
       acPMSBCIPGroupInUserDefinedFailures4Val         Counter32
     }



     acPMSBCIPGroupInUserDefinedFailures4IPGroupID OBJECT-TYPE
       SYNTAX Unsigned32 (0..5000)
       MAX-ACCESS not-accessible
       STATUS obsolete
       DESCRIPTION
           "IP Group number."
       ::= {acPMSBCIPGroupInUserDefinedFailures4Entry 1}



     acPMSBCIPGroupInUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures4Entry 2}



     acPMSBCIPGroupInUserDefinedFailures4Val OBJECT-TYPE
       SYNTAX Counter32
       MAX-ACCESS read-only
       STATUS obsolete
       DESCRIPTION
           "Value of gauge or counter."
       ::= {acPMSBCIPGroupInUserDefinedFailures4Entry 3}



     -- ****************************************
     -- acPMSBCIPGroupOutUserDefinedFailures4 table declaration
     -- ****************************************
     acPMSBCIPGroupOutUserDefinedFailures4Table OBJECT-TYPE
       SYNTAX SEQUENCE OF AcPMSBCIPGroupOutUserDefinedFailures4Entry
       MAX-ACCESS not-accessible
       STATUS obsolete
       DESCRIPTION
           "Number of user defined Failures 4 for outgoing dialogs per IP Group"
       ::= {acPMSBCUserDefinedFailures4 6}



     -- ****************************************
     -- acPMSBCIPGroupOutUserDefinedFailures4 table entry
     -- ****************************************
     acPMSBCIPGroupOutUserDefinedFailures4Entry OBJECT-TYPE
       SYNTAX AcPMSBCIPGroupOutUserDefinedFailures4Entry
       MAX-ACCESS not-accessible
       STATUS obsolete
       DESCRIPTION
           ""
       INDEX {acPMSBCIPGroupOutUserDefinedFailures4IPGroupID,acPMSBCIPGroupOutUserDefinedFailures4Interval}
       ::= {acPMSBCIPGroupOutUserDefinedFailures4Table 1}



     -- ****************************************
     -- acPMSBCIPGroupOutUserDefinedFailures4 TABLE
     -- ****************************************
     AcPMSBCIPGroupOutUserDefinedFailures4Entry ::= SEQUENCE {
       acPMSBCIPGroupOutUserDefinedFailures4IPGroupID  Unsigned32,
       acPMSBCIPGroupOutUserDefinedFailures4Interval   Unsigned32,
       acPMSBCIPGroupOutUserDefinedFailures4Val        Counter32
     }



     acPMSBCIPGroupOutUserDefinedFailures4IPGroupID OBJECT-TYPE
       SYNTAX Unsigned32 (0..5000)
       MAX-ACCESS not-accessible
       STATUS obsolete
       DESCRIPTION
           "IP Group number."
       ::= {acPMSBCIPGroupOutUserDefinedFailures4Entry 1}



     acPMSBCIPGroupOutUserDefinedFailures4Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures4Entry 2}



     acPMSBCIPGroupOutUserDefinedFailures4Val OBJECT-TYPE
       SYNTAX Counter32
       MAX-ACCESS read-only
       STATUS obsolete
       DESCRIPTION
           "Value of gauge or counter."
       ::= {acPMSBCIPGroupOutUserDefinedFailures4Entry 3}



     acPMSBCUserDefinedFailures5 OBJECT IDENTIFIER ::= {acPMSBCUserDefinedFailuresPMs 5}


     -- ****************************************
     -- acPMSBCInUserDefinedFailures5 table declaration
     -- ****************************************
     acPMSBCInUserDefinedFailures5Table OBJECT-TYPE
       SYNTAX SEQUENCE OF AcPMSBCInUserDefinedFailures5Entry
       MAX-ACCESS not-accessible
       STATUS obsolete
       DESCRIPTION
           "Number of user defined failures 5 for incoming dialogs (System global)"
       ::= {acPMSBCUserDefinedFailures5 1}



     -- ****************************************
     -- acPMSBCInUserDefinedFailures5 table entry
     -- ****************************************
     acPMSBCInUserDefinedFailures5Entry OBJECT-TYPE
       SYNTAX AcPMSBCInUserDefinedFailures5Entry
       MAX-ACCESS not-accessible
       STATUS obsolete
       DESCRIPTION
           ""
       INDEX {acPMSBCInUserDefinedFailures5Interval}
       ::= {acPMSBCInUserDefinedFailures5Table 1}



     -- ****************************************
     -- acPMSBCInUserDefinedFailures5 TABLE
     -- ****************************************
     AcPMSBCInUserDefinedFailures5Entry ::= SEQUENCE {
       acPMSBCInUserDefinedFailures5Interval           Unsigned32,
       acPMSBCInUserDefinedFailures5Val                Counter32
     }



     acPMSBCInUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures5Entry 1}



     acPMSBCInUserDefinedFailures5Val OBJECT-TYPE
       SYNTAX Counter32
       MAX-ACCESS read-only
       STATUS obsolete
       DESCRIPTION
           "Value of gauge or counter."
       ::= {acPMSBCInUserDefinedFailures5Entry 2}



     -- ****************************************
     -- acPMSBCOutUserDefinedFailures5 table declaration
     -- ****************************************
     acPMSBCOutUserDefinedFailures5Table OBJECT-TYPE
       SYNTAX SEQUENCE OF AcPMSBCOutUserDefinedFailures5Entry
       MAX-ACCESS not-accessible
       STATUS obsolete
       DESCRIPTION
           "Number of user defined Failures 5 for outgoing dialogs (System global)"
       ::= {acPMSBCUserDefinedFailures5 2}



     -- ****************************************
     -- acPMSBCOutUserDefinedFailures5 table entry
     -- ****************************************
     acPMSBCOutUserDefinedFailures5Entry OBJECT-TYPE
       SYNTAX AcPMSBCOutUserDefinedFailures5Entry
       MAX-ACCESS not-accessible
       STATUS obsolete
       DESCRIPTION
           ""
       INDEX {acPMSBCOutUserDefinedFailures5Interval}
       ::= {acPMSBCOutUserDefinedFailures5Table 1}



     -- ****************************************
     -- acPMSBCOutUserDefinedFailures5 TABLE
     -- ****************************************
     AcPMSBCOutUserDefinedFailures5Entry ::= SEQUENCE {
       acPMSBCOutUserDefinedFailures5Interval          Unsigned32,
       acPMSBCOutUserDefinedFailures5Val               Counter32
     }



     acPMSBCOutUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures5Entry 1}



     acPMSBCOutUserDefinedFailures5Val OBJECT-TYPE
       SYNTAX Counter32
       MAX-ACCESS read-only
       STATUS obsolete
       DESCRIPTION
           "Value of gauge or counter."
       ::= {acPMSBCOutUserDefinedFailures5Entry 2}



     -- ****************************************
     -- acPMSBCSRDInUserDefinedFailures5 table declaration
     -- ****************************************
     acPMSBCSRDInUserDefinedFailures5Table OBJECT-TYPE
       SYNTAX SEQUENCE OF AcPMSBCSRDInUserDefinedFailures5Entry
       MAX-ACCESS not-accessible
       STATUS obsolete
       DESCRIPTION
           "Number of user defined Failures 5 for incoming dialogs per SRD"
       ::= {acPMSBCUserDefinedFailures5 3}



     -- ****************************************
     -- acPMSBCSRDInUserDefinedFailures5 table entry
     -- ****************************************
     acPMSBCSRDInUserDefinedFailures5Entry OBJECT-TYPE
       SYNTAX AcPMSBCSRDInUserDefinedFailures5Entry
       MAX-ACCESS not-accessible
       STATUS obsolete
       DESCRIPTION
           ""
       INDEX {acPMSBCSRDInUserDefinedFailures5SrdID,acPMSBCSRDInUserDefinedFailures5Interval}
       ::= {acPMSBCSRDInUserDefinedFailures5Table 1}



     -- ****************************************
     -- acPMSBCSRDInUserDefinedFailures5 TABLE
     -- ****************************************
     AcPMSBCSRDInUserDefinedFailures5Entry ::= SEQUENCE {
       acPMSBCSRDInUserDefinedFailures5SrdID           Unsigned32,
       acPMSBCSRDInUserDefinedFailures5Interval        Unsigned32,
       acPMSBCSRDInUserDefinedFailures5Val             Counter32
     }



     acPMSBCSRDInUserDefinedFailures5SrdID OBJECT-TYPE
       SYNTAX Unsigned32 (0..600)
       MAX-ACCESS not-accessible
       STATUS obsolete
       DESCRIPTION
           "SRD number.
0 is the first SRD."
       ::= {acPMSBCSRDInUserDefinedFailures5Entry 1}



     acPMSBCSRDInUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures5Entry 2}



     acPMSBCSRDInUserDefinedFailures5Val OBJECT-TYPE
       SYNTAX Counter32
       MAX-ACCESS read-only
       STATUS obsolete
       DESCRIPTION
           "Value of gauge or counter."
       ::= {acPMSBCSRDInUserDefinedFailures5Entry 3}



     -- ****************************************
     -- acPMSBCSRDOutUserDefinedFailures5 table declaration
     -- ****************************************
     acPMSBCSRDOutUserDefinedFailures5Table OBJECT-TYPE
       SYNTAX SEQUENCE OF AcPMSBCSRDOutUserDefinedFailures5Entry
       MAX-ACCESS not-accessible
       STATUS obsolete
       DESCRIPTION
           "Number of user defined Failures 5 for outgoing dialogs per SRD"
       ::= {acPMSBCUserDefinedFailures5 4}



     -- ****************************************
     -- acPMSBCSRDOutUserDefinedFailures5 table entry
     -- ****************************************
     acPMSBCSRDOutUserDefinedFailures5Entry OBJECT-TYPE
       SYNTAX AcPMSBCSRDOutUserDefinedFailures5Entry
       MAX-ACCESS not-accessible
       STATUS obsolete
       DESCRIPTION
           ""
       INDEX {acPMSBCSRDOutUserDefinedFailures5SrdID,acPMSBCSRDOutUserDefinedFailures5Interval}
       ::= {acPMSBCSRDOutUserDefinedFailures5Table 1}



     -- ****************************************
     -- acPMSBCSRDOutUserDefinedFailures5 TABLE
     -- ****************************************
     AcPMSBCSRDOutUserDefinedFailures5Entry ::= SEQUENCE {
       acPMSBCSRDOutUserDefinedFailures5SrdID          Unsigned32,
       acPMSBCSRDOutUserDefinedFailures5Interval       Unsigned32,
       acPMSBCSRDOutUserDefinedFailures5Val            Counter32
     }



     acPMSBCSRDOutUserDefinedFailures5SrdID OBJECT-TYPE
       SYNTAX Unsigned32 (0..600)
       MAX-ACCESS not-accessible
       STATUS obsolete
       DESCRIPTION
           "SRD number.
0 is the first SRD."
       ::= {acPMSBCSRDOutUserDefinedFailures5Entry 1}



     acPMSBCSRDOutUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures5Entry 2}



     acPMSBCSRDOutUserDefinedFailures5Val OBJECT-TYPE
       SYNTAX Counter32
       MAX-ACCESS read-only
       STATUS obsolete
       DESCRIPTION
           "Value of gauge or counter."
       ::= {acPMSBCSRDOutUserDefinedFailures5Entry 3}



     -- ****************************************
     -- acPMSBCIPGroupInUserDefinedFailures5 table declaration
     -- ****************************************
     acPMSBCIPGroupInUserDefinedFailures5Table OBJECT-TYPE
       SYNTAX SEQUENCE OF AcPMSBCIPGroupInUserDefinedFailures5Entry
       MAX-ACCESS not-accessible
       STATUS obsolete
       DESCRIPTION
           "Number of user defined Failures 5 for incoming dialogs per IP Group"
       ::= {acPMSBCUserDefinedFailures5 5}



     -- ****************************************
     -- acPMSBCIPGroupInUserDefinedFailures5 table entry
     -- ****************************************
     acPMSBCIPGroupInUserDefinedFailures5Entry OBJECT-TYPE
       SYNTAX AcPMSBCIPGroupInUserDefinedFailures5Entry
       MAX-ACCESS not-accessible
       STATUS obsolete
       DESCRIPTION
           ""
       INDEX {acPMSBCIPGroupInUserDefinedFailures5IPGroupID,acPMSBCIPGroupInUserDefinedFailures5Interval}
       ::= {acPMSBCIPGroupInUserDefinedFailures5Table 1}



     -- ****************************************
     -- acPMSBCIPGroupInUserDefinedFailures5 TABLE
     -- ****************************************
     AcPMSBCIPGroupInUserDefinedFailures5Entry ::= SEQUENCE {
       acPMSBCIPGroupInUserDefinedFailures5IPGroupID   Unsigned32,
       acPMSBCIPGroupInUserDefinedFailures5Interval    Unsigned32,
       acPMSBCIPGroupInUserDefinedFailures5Val         Counter32
     }



     acPMSBCIPGroupInUserDefinedFailures5IPGroupID OBJECT-TYPE
       SYNTAX Unsigned32 (0..5000)
       MAX-ACCESS not-accessible
       STATUS obsolete
       DESCRIPTION
           "IP Group number."
       ::= {acPMSBCIPGroupInUserDefinedFailures5Entry 1}



     acPMSBCIPGroupInUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures5Entry 2}



     acPMSBCIPGroupInUserDefinedFailures5Val OBJECT-TYPE
       SYNTAX Counter32
       MAX-ACCESS read-only
       STATUS obsolete
       DESCRIPTION
           "Value of gauge or counter."
       ::= {acPMSBCIPGroupInUserDefinedFailures5Entry 3}



     -- ****************************************
     -- acPMSBCIPGroupOutUserDefinedFailures5 table declaration
     -- ****************************************
     acPMSBCIPGroupOutUserDefinedFailures5Table OBJECT-TYPE
       SYNTAX SEQUENCE OF AcPMSBCIPGroupOutUserDefinedFailures5Entry
       MAX-ACCESS not-accessible
       STATUS obsolete
       DESCRIPTION
           "Number of user defined Failures 5 for outgoing dialogs per IP Group"
       ::= {acPMSBCUserDefinedFailures5 6}



     -- ****************************************
     -- acPMSBCIPGroupOutUserDefinedFailures5 table entry
     -- ****************************************
     acPMSBCIPGroupOutUserDefinedFailures5Entry OBJECT-TYPE
       SYNTAX AcPMSBCIPGroupOutUserDefinedFailures5Entry
       MAX-ACCESS not-accessible
       STATUS obsolete
       DESCRIPTION
           ""
       INDEX {acPMSBCIPGroupOutUserDefinedFailures5IPGroupID,acPMSBCIPGroupOutUserDefinedFailures5Interval}
       ::= {acPMSBCIPGroupOutUserDefinedFailures5Table 1}



     -- ****************************************
     -- acPMSBCIPGroupOutUserDefinedFailures5 TABLE
     -- ****************************************
     AcPMSBCIPGroupOutUserDefinedFailures5Entry ::= SEQUENCE {
       acPMSBCIPGroupOutUserDefinedFailures5IPGroupID  Unsigned32,
       acPMSBCIPGroupOutUserDefinedFailures5Interval   Unsigned32,
       acPMSBCIPGroupOutUserDefinedFailures5Val        Counter32
     }



     acPMSBCIPGroupOutUserDefinedFailures5IPGroupID OBJECT-TYPE
       SYNTAX Unsigned32 (0..5000)
       MAX-ACCESS not-accessible
       STATUS obsolete
       DESCRIPTION
           "IP Group number."
       ::= {acPMSBCIPGroupOutUserDefinedFailures5Entry 1}



     acPMSBCIPGroupOutUserDefinedFailures5Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures5Entry 2}



     acPMSBCIPGroupOutUserDefinedFailures5Val OBJECT-TYPE
       SYNTAX Counter32
       MAX-ACCESS read-only
       STATUS obsolete
       DESCRIPTION
           "Value of gauge or counter."
       ::= {acPMSBCIPGroupOutUserDefinedFailures5Entry 3}



     acPMSBCUserDefinedFailures6 OBJECT IDENTIFIER ::= {acPMSBCUserDefinedFailuresPMs 6}


     -- ****************************************
     -- acPMSBCInUserDefinedFailures6 table declaration
     -- ****************************************
     acPMSBCInUserDefinedFailures6Table OBJECT-TYPE
       SYNTAX SEQUENCE OF AcPMSBCInUserDefinedFailures6Entry
       MAX-ACCESS not-accessible
       STATUS obsolete
       DESCRIPTION
           "Number of user defined failures 6 for incoming dialogs (System global)"
       ::= {acPMSBCUserDefinedFailures6 1}



     -- ****************************************
     -- acPMSBCInUserDefinedFailures6 table entry
     -- ****************************************
     acPMSBCInUserDefinedFailures6Entry OBJECT-TYPE
       SYNTAX AcPMSBCInUserDefinedFailures6Entry
       MAX-ACCESS not-accessible
       STATUS obsolete
       DESCRIPTION
           ""
       INDEX {acPMSBCInUserDefinedFailures6Interval}
       ::= {acPMSBCInUserDefinedFailures6Table 1}



     -- ****************************************
     -- acPMSBCInUserDefinedFailures6 TABLE
     -- ****************************************
     AcPMSBCInUserDefinedFailures6Entry ::= SEQUENCE {
       acPMSBCInUserDefinedFailures6Interval           Unsigned32,
       acPMSBCInUserDefinedFailures6Val                Counter32
     }



     acPMSBCInUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures6Entry 1}



     acPMSBCInUserDefinedFailures6Val OBJECT-TYPE
       SYNTAX Counter32
       MAX-ACCESS read-only
       STATUS obsolete
       DESCRIPTION
           "Value of gauge or counter."
       ::= {acPMSBCInUserDefinedFailures6Entry 2}



     -- ****************************************
     -- acPMSBCOutUserDefinedFailures6 table declaration
     -- ****************************************
     acPMSBCOutUserDefinedFailures6Table OBJECT-TYPE
       SYNTAX SEQUENCE OF AcPMSBCOutUserDefinedFailures6Entry
       MAX-ACCESS not-accessible
       STATUS obsolete
       DESCRIPTION
           "Number of user defined Failures 6 for outgoing dialogs (System global)"
       ::= {acPMSBCUserDefinedFailures6 2}



     -- ****************************************
     -- acPMSBCOutUserDefinedFailures6 table entry
     -- ****************************************
     acPMSBCOutUserDefinedFailures6Entry OBJECT-TYPE
       SYNTAX AcPMSBCOutUserDefinedFailures6Entry
       MAX-ACCESS not-accessible
       STATUS obsolete
       DESCRIPTION
           ""
       INDEX {acPMSBCOutUserDefinedFailures6Interval}
       ::= {acPMSBCOutUserDefinedFailures6Table 1}



     -- ****************************************
     -- acPMSBCOutUserDefinedFailures6 TABLE
     -- ****************************************
     AcPMSBCOutUserDefinedFailures6Entry ::= SEQUENCE {
       acPMSBCOutUserDefinedFailures6Interval          Unsigned32,
       acPMSBCOutUserDefinedFailures6Val               Counter32
     }



     acPMSBCOutUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures6Entry 1}



     acPMSBCOutUserDefinedFailures6Val OBJECT-TYPE
       SYNTAX Counter32
       MAX-ACCESS read-only
       STATUS obsolete
       DESCRIPTION
           "Value of gauge or counter."
       ::= {acPMSBCOutUserDefinedFailures6Entry 2}



     -- ****************************************
     -- acPMSBCSRDInUserDefinedFailures6 table declaration
     -- ****************************************
     acPMSBCSRDInUserDefinedFailures6Table OBJECT-TYPE
       SYNTAX SEQUENCE OF AcPMSBCSRDInUserDefinedFailures6Entry
       MAX-ACCESS not-accessible
       STATUS obsolete
       DESCRIPTION
           "Number of user defined Failures 6 for incoming dialogs per SRD"
       ::= {acPMSBCUserDefinedFailures6 3}



     -- ****************************************
     -- acPMSBCSRDInUserDefinedFailures6 table entry
     -- ****************************************
     acPMSBCSRDInUserDefinedFailures6Entry OBJECT-TYPE
       SYNTAX AcPMSBCSRDInUserDefinedFailures6Entry
       MAX-ACCESS not-accessible
       STATUS obsolete
       DESCRIPTION
           ""
       INDEX {acPMSBCSRDInUserDefinedFailures6SrdID,acPMSBCSRDInUserDefinedFailures6Interval}
       ::= {acPMSBCSRDInUserDefinedFailures6Table 1}



     -- ****************************************
     -- acPMSBCSRDInUserDefinedFailures6 TABLE
     -- ****************************************
     AcPMSBCSRDInUserDefinedFailures6Entry ::= SEQUENCE {
       acPMSBCSRDInUserDefinedFailures6SrdID           Unsigned32,
       acPMSBCSRDInUserDefinedFailures6Interval        Unsigned32,
       acPMSBCSRDInUserDefinedFailures6Val             Counter32
     }



     acPMSBCSRDInUserDefinedFailures6SrdID OBJECT-TYPE
       SYNTAX Unsigned32 (0..600)
       MAX-ACCESS not-accessible
       STATUS obsolete
       DESCRIPTION
           "SRD number.
0 is the first SRD."
       ::= {acPMSBCSRDInUserDefinedFailures6Entry 1}



     acPMSBCSRDInUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures6Entry 2}



     acPMSBCSRDInUserDefinedFailures6Val OBJECT-TYPE
       SYNTAX Counter32
       MAX-ACCESS read-only
       STATUS obsolete
       DESCRIPTION
           "Value of gauge or counter."
       ::= {acPMSBCSRDInUserDefinedFailures6Entry 3}



     -- ****************************************
     -- acPMSBCSRDOutUserDefinedFailures6 table declaration
     -- ****************************************
     acPMSBCSRDOutUserDefinedFailures6Table OBJECT-TYPE
       SYNTAX SEQUENCE OF AcPMSBCSRDOutUserDefinedFailures6Entry
       MAX-ACCESS not-accessible
       STATUS obsolete
       DESCRIPTION
           "Number of user defined Failures 6 for outgoing dialogs per SRD"
       ::= {acPMSBCUserDefinedFailures6 4}



     -- ****************************************
     -- acPMSBCSRDOutUserDefinedFailures6 table entry
     -- ****************************************
     acPMSBCSRDOutUserDefinedFailures6Entry OBJECT-TYPE
       SYNTAX AcPMSBCSRDOutUserDefinedFailures6Entry
       MAX-ACCESS not-accessible
       STATUS obsolete
       DESCRIPTION
           ""
       INDEX {acPMSBCSRDOutUserDefinedFailures6SrdID,acPMSBCSRDOutUserDefinedFailures6Interval}
       ::= {acPMSBCSRDOutUserDefinedFailures6Table 1}



     -- ****************************************
     -- acPMSBCSRDOutUserDefinedFailures6 TABLE
     -- ****************************************
     AcPMSBCSRDOutUserDefinedFailures6Entry ::= SEQUENCE {
       acPMSBCSRDOutUserDefinedFailures6SrdID          Unsigned32,
       acPMSBCSRDOutUserDefinedFailures6Interval       Unsigned32,
       acPMSBCSRDOutUserDefinedFailures6Val            Counter32
     }



     acPMSBCSRDOutUserDefinedFailures6SrdID OBJECT-TYPE
       SYNTAX Unsigned32 (0..600)
       MAX-ACCESS not-accessible
       STATUS obsolete
       DESCRIPTION
           "SRD number.
0 is the first SRD."
       ::= {acPMSBCSRDOutUserDefinedFailures6Entry 1}



     acPMSBCSRDOutUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures6Entry 2}



     acPMSBCSRDOutUserDefinedFailures6Val OBJECT-TYPE
       SYNTAX Counter32
       MAX-ACCESS read-only
       STATUS obsolete
       DESCRIPTION
           "Value of gauge or counter."
       ::= {acPMSBCSRDOutUserDefinedFailures6Entry 3}



     -- ****************************************
     -- acPMSBCIPGroupInUserDefinedFailures6 table declaration
     -- ****************************************
     acPMSBCIPGroupInUserDefinedFailures6Table OBJECT-TYPE
       SYNTAX SEQUENCE OF AcPMSBCIPGroupInUserDefinedFailures6Entry
       MAX-ACCESS not-accessible
       STATUS obsolete
       DESCRIPTION
           "Number of user defined Failures 6 for incoming dialogs per IP Group"
       ::= {acPMSBCUserDefinedFailures6 5}



     -- ****************************************
     -- acPMSBCIPGroupInUserDefinedFailures6 table entry
     -- ****************************************
     acPMSBCIPGroupInUserDefinedFailures6Entry OBJECT-TYPE
       SYNTAX AcPMSBCIPGroupInUserDefinedFailures6Entry
       MAX-ACCESS not-accessible
       STATUS obsolete
       DESCRIPTION
           ""
       INDEX {acPMSBCIPGroupInUserDefinedFailures6IPGroupID,acPMSBCIPGroupInUserDefinedFailures6Interval}
       ::= {acPMSBCIPGroupInUserDefinedFailures6Table 1}



     -- ****************************************
     -- acPMSBCIPGroupInUserDefinedFailures6 TABLE
     -- ****************************************
     AcPMSBCIPGroupInUserDefinedFailures6Entry ::= SEQUENCE {
       acPMSBCIPGroupInUserDefinedFailures6IPGroupID   Unsigned32,
       acPMSBCIPGroupInUserDefinedFailures6Interval    Unsigned32,
       acPMSBCIPGroupInUserDefinedFailures6Val         Counter32
     }



     acPMSBCIPGroupInUserDefinedFailures6IPGroupID OBJECT-TYPE
       SYNTAX Unsigned32 (0..5000)
       MAX-ACCESS not-accessible
       STATUS obsolete
       DESCRIPTION
           "IP Group number."
       ::= {acPMSBCIPGroupInUserDefinedFailures6Entry 1}



     acPMSBCIPGroupInUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures6Entry 2}



     acPMSBCIPGroupInUserDefinedFailures6Val OBJECT-TYPE
       SYNTAX Counter32
       MAX-ACCESS read-only
       STATUS obsolete
       DESCRIPTION
           "Value of gauge or counter."
       ::= {acPMSBCIPGroupInUserDefinedFailures6Entry 3}



     -- ****************************************
     -- acPMSBCIPGroupOutUserDefinedFailures6 table declaration
     -- ****************************************
     acPMSBCIPGroupOutUserDefinedFailures6Table OBJECT-TYPE
       SYNTAX SEQUENCE OF AcPMSBCIPGroupOutUserDefinedFailures6Entry
       MAX-ACCESS not-accessible
       STATUS obsolete
       DESCRIPTION
           "Number of user defined Failures 6 for outgoing dialogs per IP Group"
       ::= {acPMSBCUserDefinedFailures6 6}



     -- ****************************************
     -- acPMSBCIPGroupOutUserDefinedFailures6 table entry
     -- ****************************************
     acPMSBCIPGroupOutUserDefinedFailures6Entry OBJECT-TYPE
       SYNTAX AcPMSBCIPGroupOutUserDefinedFailures6Entry
       MAX-ACCESS not-accessible
       STATUS obsolete
       DESCRIPTION
           ""
       INDEX {acPMSBCIPGroupOutUserDefinedFailures6IPGroupID,acPMSBCIPGroupOutUserDefinedFailures6Interval}
       ::= {acPMSBCIPGroupOutUserDefinedFailures6Table 1}



     -- ****************************************
     -- acPMSBCIPGroupOutUserDefinedFailures6 TABLE
     -- ****************************************
     AcPMSBCIPGroupOutUserDefinedFailures6Entry ::= SEQUENCE {
       acPMSBCIPGroupOutUserDefinedFailures6IPGroupID  Unsigned32,
       acPMSBCIPGroupOutUserDefinedFailures6Interval   Unsigned32,
       acPMSBCIPGroupOutUserDefinedFailures6Val        Counter32
     }



     acPMSBCIPGroupOutUserDefinedFailures6IPGroupID OBJECT-TYPE
       SYNTAX Unsigned32 (0..5000)
       MAX-ACCESS not-accessible
       STATUS obsolete
       DESCRIPTION
           "IP Group number."
       ::= {acPMSBCIPGroupOutUserDefinedFailures6Entry 1}



     acPMSBCIPGroupOutUserDefinedFailures6Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures6Entry 2}



     acPMSBCIPGroupOutUserDefinedFailures6Val OBJECT-TYPE
       SYNTAX Counter32
       MAX-ACCESS read-only
       STATUS obsolete
       DESCRIPTION
           "Value of gauge or counter."
       ::= {acPMSBCIPGroupOutUserDefinedFailures6Entry 3}



     acPMSBCUserDefinedFailures7 OBJECT IDENTIFIER ::= {acPMSBCUserDefinedFailuresPMs 7}


     -- ****************************************
     -- acPMSBCInUserDefinedFailures7 table declaration
     -- ****************************************
     acPMSBCInUserDefinedFailures7Table OBJECT-TYPE
       SYNTAX SEQUENCE OF AcPMSBCInUserDefinedFailures7Entry
       MAX-ACCESS not-accessible
       STATUS obsolete
       DESCRIPTION
           "Number of user defined failures 7 for incoming dialogs (System global)"
       ::= {acPMSBCUserDefinedFailures7 1}



     -- ****************************************
     -- acPMSBCInUserDefinedFailures7 table entry
     -- ****************************************
     acPMSBCInUserDefinedFailures7Entry OBJECT-TYPE
       SYNTAX AcPMSBCInUserDefinedFailures7Entry
       MAX-ACCESS not-accessible
       STATUS obsolete
       DESCRIPTION
           ""
       INDEX {acPMSBCInUserDefinedFailures7Interval}
       ::= {acPMSBCInUserDefinedFailures7Table 1}



     -- ****************************************
     -- acPMSBCInUserDefinedFailures7 TABLE
     -- ****************************************
     AcPMSBCInUserDefinedFailures7Entry ::= SEQUENCE {
       acPMSBCInUserDefinedFailures7Interval           Unsigned32,
       acPMSBCInUserDefinedFailures7Val                Counter32
     }



     acPMSBCInUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures7Entry 1}



     acPMSBCInUserDefinedFailures7Val OBJECT-TYPE
       SYNTAX Counter32
       MAX-ACCESS read-only
       STATUS obsolete
       DESCRIPTION
           "Value of gauge or counter."
       ::= {acPMSBCInUserDefinedFailures7Entry 2}



     -- ****************************************
     -- acPMSBCOutUserDefinedFailures7 table declaration
     -- ****************************************
     acPMSBCOutUserDefinedFailures7Table OBJECT-TYPE
       SYNTAX SEQUENCE OF AcPMSBCOutUserDefinedFailures7Entry
       MAX-ACCESS not-accessible
       STATUS obsolete
       DESCRIPTION
           "Number of user defined Failures 7 for outgoing dialogs (System global)"
       ::= {acPMSBCUserDefinedFailures7 2}



     -- ****************************************
     -- acPMSBCOutUserDefinedFailures7 table entry
     -- ****************************************
     acPMSBCOutUserDefinedFailures7Entry OBJECT-TYPE
       SYNTAX AcPMSBCOutUserDefinedFailures7Entry
       MAX-ACCESS not-accessible
       STATUS obsolete
       DESCRIPTION
           ""
       INDEX {acPMSBCOutUserDefinedFailures7Interval}
       ::= {acPMSBCOutUserDefinedFailures7Table 1}



     -- ****************************************
     -- acPMSBCOutUserDefinedFailures7 TABLE
     -- ****************************************
     AcPMSBCOutUserDefinedFailures7Entry ::= SEQUENCE {
       acPMSBCOutUserDefinedFailures7Interval          Unsigned32,
       acPMSBCOutUserDefinedFailures7Val               Counter32
     }



     acPMSBCOutUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures7Entry 1}



     acPMSBCOutUserDefinedFailures7Val OBJECT-TYPE
       SYNTAX Counter32
       MAX-ACCESS read-only
       STATUS obsolete
       DESCRIPTION
           "Value of gauge or counter."
       ::= {acPMSBCOutUserDefinedFailures7Entry 2}



     -- ****************************************
     -- acPMSBCSRDInUserDefinedFailures7 table declaration
     -- ****************************************
     acPMSBCSRDInUserDefinedFailures7Table OBJECT-TYPE
       SYNTAX SEQUENCE OF AcPMSBCSRDInUserDefinedFailures7Entry
       MAX-ACCESS not-accessible
       STATUS obsolete
       DESCRIPTION
           "Number of user defined Failures 7 for incoming dialogs per SRD"
       ::= {acPMSBCUserDefinedFailures7 3}



     -- ****************************************
     -- acPMSBCSRDInUserDefinedFailures7 table entry
     -- ****************************************
     acPMSBCSRDInUserDefinedFailures7Entry OBJECT-TYPE
       SYNTAX AcPMSBCSRDInUserDefinedFailures7Entry
       MAX-ACCESS not-accessible
       STATUS obsolete
       DESCRIPTION
           ""
       INDEX {acPMSBCSRDInUserDefinedFailures7SrdID,acPMSBCSRDInUserDefinedFailures7Interval}
       ::= {acPMSBCSRDInUserDefinedFailures7Table 1}



     -- ****************************************
     -- acPMSBCSRDInUserDefinedFailures7 TABLE
     -- ****************************************
     AcPMSBCSRDInUserDefinedFailures7Entry ::= SEQUENCE {
       acPMSBCSRDInUserDefinedFailures7SrdID           Unsigned32,
       acPMSBCSRDInUserDefinedFailures7Interval        Unsigned32,
       acPMSBCSRDInUserDefinedFailures7Val             Counter32
     }



     acPMSBCSRDInUserDefinedFailures7SrdID OBJECT-TYPE
       SYNTAX Unsigned32 (0..600)
       MAX-ACCESS not-accessible
       STATUS obsolete
       DESCRIPTION
           "SRD number.
0 is the first SRD."
       ::= {acPMSBCSRDInUserDefinedFailures7Entry 1}



     acPMSBCSRDInUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures7Entry 2}



     acPMSBCSRDInUserDefinedFailures7Val OBJECT-TYPE
       SYNTAX Counter32
       MAX-ACCESS read-only
       STATUS obsolete
       DESCRIPTION
           "Value of gauge or counter."
       ::= {acPMSBCSRDInUserDefinedFailures7Entry 3}



     -- ****************************************
     -- acPMSBCSRDOutUserDefinedFailures7 table declaration
     -- ****************************************
     acPMSBCSRDOutUserDefinedFailures7Table OBJECT-TYPE
       SYNTAX SEQUENCE OF AcPMSBCSRDOutUserDefinedFailures7Entry
       MAX-ACCESS not-accessible
       STATUS obsolete
       DESCRIPTION
           "Number of user defined Failures 7 for outgoing dialogs per SRD"
       ::= {acPMSBCUserDefinedFailures7 4}



     -- ****************************************
     -- acPMSBCSRDOutUserDefinedFailures7 table entry
     -- ****************************************
     acPMSBCSRDOutUserDefinedFailures7Entry OBJECT-TYPE
       SYNTAX AcPMSBCSRDOutUserDefinedFailures7Entry
       MAX-ACCESS not-accessible
       STATUS obsolete
       DESCRIPTION
           ""
       INDEX {acPMSBCSRDOutUserDefinedFailures7SrdID,acPMSBCSRDOutUserDefinedFailures7Interval}
       ::= {acPMSBCSRDOutUserDefinedFailures7Table 1}



     -- ****************************************
     -- acPMSBCSRDOutUserDefinedFailures7 TABLE
     -- ****************************************
     AcPMSBCSRDOutUserDefinedFailures7Entry ::= SEQUENCE {
       acPMSBCSRDOutUserDefinedFailures7SrdID          Unsigned32,
       acPMSBCSRDOutUserDefinedFailures7Interval       Unsigned32,
       acPMSBCSRDOutUserDefinedFailures7Val            Counter32
     }



     acPMSBCSRDOutUserDefinedFailures7SrdID OBJECT-TYPE
       SYNTAX Unsigned32 (0..600)
       MAX-ACCESS not-accessible
       STATUS obsolete
       DESCRIPTION
           "SRD number.
0 is the first SRD."
       ::= {acPMSBCSRDOutUserDefinedFailures7Entry 1}



     acPMSBCSRDOutUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures7Entry 2}



     acPMSBCSRDOutUserDefinedFailures7Val OBJECT-TYPE
       SYNTAX Counter32
       MAX-ACCESS read-only
       STATUS obsolete
       DESCRIPTION
           "Value of gauge or counter."
       ::= {acPMSBCSRDOutUserDefinedFailures7Entry 3}



     -- ****************************************
     -- acPMSBCIPGroupInUserDefinedFailures7 table declaration
     -- ****************************************
     acPMSBCIPGroupInUserDefinedFailures7Table OBJECT-TYPE
       SYNTAX SEQUENCE OF AcPMSBCIPGroupInUserDefinedFailures7Entry
       MAX-ACCESS not-accessible
       STATUS obsolete
       DESCRIPTION
           "Number of user defined Failures 7 for incoming dialogs per IP Group"
       ::= {acPMSBCUserDefinedFailures7 5}



     -- ****************************************
     -- acPMSBCIPGroupInUserDefinedFailures7 table entry
     -- ****************************************
     acPMSBCIPGroupInUserDefinedFailures7Entry OBJECT-TYPE
       SYNTAX AcPMSBCIPGroupInUserDefinedFailures7Entry
       MAX-ACCESS not-accessible
       STATUS obsolete
       DESCRIPTION
           ""
       INDEX {acPMSBCIPGroupInUserDefinedFailures7IPGroupID,acPMSBCIPGroupInUserDefinedFailures7Interval}
       ::= {acPMSBCIPGroupInUserDefinedFailures7Table 1}



     -- ****************************************
     -- acPMSBCIPGroupInUserDefinedFailures7 TABLE
     -- ****************************************
     AcPMSBCIPGroupInUserDefinedFailures7Entry ::= SEQUENCE {
       acPMSBCIPGroupInUserDefinedFailures7IPGroupID   Unsigned32,
       acPMSBCIPGroupInUserDefinedFailures7Interval    Unsigned32,
       acPMSBCIPGroupInUserDefinedFailures7Val         Counter32
     }



     acPMSBCIPGroupInUserDefinedFailures7IPGroupID OBJECT-TYPE
       SYNTAX Unsigned32 (0..5000)
       MAX-ACCESS not-accessible
       STATUS obsolete
       DESCRIPTION
           "IP Group number."
       ::= {acPMSBCIPGroupInUserDefinedFailures7Entry 1}



     acPMSBCIPGroupInUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures7Entry 2}



     acPMSBCIPGroupInUserDefinedFailures7Val OBJECT-TYPE
       SYNTAX Counter32
       MAX-ACCESS read-only
       STATUS obsolete
       DESCRIPTION
           "Value of gauge or counter."
       ::= {acPMSBCIPGroupInUserDefinedFailures7Entry 3}



     -- ****************************************
     -- acPMSBCIPGroupOutUserDefinedFailures7 table declaration
     -- ****************************************
     acPMSBCIPGroupOutUserDefinedFailures7Table OBJECT-TYPE
       SYNTAX SEQUENCE OF AcPMSBCIPGroupOutUserDefinedFailures7Entry
       MAX-ACCESS not-accessible
       STATUS obsolete
       DESCRIPTION
           "Number of user defined Failures 7 for outgoing dialogs per IP Group"
       ::= {acPMSBCUserDefinedFailures7 6}



     -- ****************************************
     -- acPMSBCIPGroupOutUserDefinedFailures7 table entry
     -- ****************************************
     acPMSBCIPGroupOutUserDefinedFailures7Entry OBJECT-TYPE
       SYNTAX AcPMSBCIPGroupOutUserDefinedFailures7Entry
       MAX-ACCESS not-accessible
       STATUS obsolete
       DESCRIPTION
           ""
       INDEX {acPMSBCIPGroupOutUserDefinedFailures7IPGroupID,acPMSBCIPGroupOutUserDefinedFailures7Interval}
       ::= {acPMSBCIPGroupOutUserDefinedFailures7Table 1}



     -- ****************************************
     -- acPMSBCIPGroupOutUserDefinedFailures7 TABLE
     -- ****************************************
     AcPMSBCIPGroupOutUserDefinedFailures7Entry ::= SEQUENCE {
       acPMSBCIPGroupOutUserDefinedFailures7IPGroupID  Unsigned32,
       acPMSBCIPGroupOutUserDefinedFailures7Interval   Unsigned32,
       acPMSBCIPGroupOutUserDefinedFailures7Val        Counter32
     }



     acPMSBCIPGroupOutUserDefinedFailures7IPGroupID OBJECT-TYPE
       SYNTAX Unsigned32 (0..5000)
       MAX-ACCESS not-accessible
       STATUS obsolete
       DESCRIPTION
           "IP Group number."
       ::= {acPMSBCIPGroupOutUserDefinedFailures7Entry 1}



     acPMSBCIPGroupOutUserDefinedFailures7Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures7Entry 2}



     acPMSBCIPGroupOutUserDefinedFailures7Val OBJECT-TYPE
       SYNTAX Counter32
       MAX-ACCESS read-only
       STATUS obsolete
       DESCRIPTION
           "Value of gauge or counter."
       ::= {acPMSBCIPGroupOutUserDefinedFailures7Entry 3}



     acPMSBCUserDefinedFailures8 OBJECT IDENTIFIER ::= {acPMSBCUserDefinedFailuresPMs 8}


     -- ****************************************
     -- acPMSBCInUserDefinedFailures8 table declaration
     -- ****************************************
     acPMSBCInUserDefinedFailures8Table OBJECT-TYPE
       SYNTAX SEQUENCE OF AcPMSBCInUserDefinedFailures8Entry
       MAX-ACCESS not-accessible
       STATUS obsolete
       DESCRIPTION
           "Number of user defined failures 8 for incoming dialogs (System global)"
       ::= {acPMSBCUserDefinedFailures8 1}



     -- ****************************************
     -- acPMSBCInUserDefinedFailures8 table entry
     -- ****************************************
     acPMSBCInUserDefinedFailures8Entry OBJECT-TYPE
       SYNTAX AcPMSBCInUserDefinedFailures8Entry
       MAX-ACCESS not-accessible
       STATUS obsolete
       DESCRIPTION
           ""
       INDEX {acPMSBCInUserDefinedFailures8Interval}
       ::= {acPMSBCInUserDefinedFailures8Table 1}



     -- ****************************************
     -- acPMSBCInUserDefinedFailures8 TABLE
     -- ****************************************
     AcPMSBCInUserDefinedFailures8Entry ::= SEQUENCE {
       acPMSBCInUserDefinedFailures8Interval           Unsigned32,
       acPMSBCInUserDefinedFailures8Val                Counter32
     }



     acPMSBCInUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures8Entry 1}



     acPMSBCInUserDefinedFailures8Val OBJECT-TYPE
       SYNTAX Counter32
       MAX-ACCESS read-only
       STATUS obsolete
       DESCRIPTION
           "Value of gauge or counter."
       ::= {acPMSBCInUserDefinedFailures8Entry 2}



     -- ****************************************
     -- acPMSBCOutUserDefinedFailures8 table declaration
     -- ****************************************
     acPMSBCOutUserDefinedFailures8Table OBJECT-TYPE
       SYNTAX SEQUENCE OF AcPMSBCOutUserDefinedFailures8Entry
       MAX-ACCESS not-accessible
       STATUS obsolete
       DESCRIPTION
           "Number of user defined Failures 8 for outgoing dialogs (System global)"
       ::= {acPMSBCUserDefinedFailures8 2}



     -- ****************************************
     -- acPMSBCOutUserDefinedFailures8 table entry
     -- ****************************************
     acPMSBCOutUserDefinedFailures8Entry OBJECT-TYPE
       SYNTAX AcPMSBCOutUserDefinedFailures8Entry
       MAX-ACCESS not-accessible
       STATUS obsolete
       DESCRIPTION
           ""
       INDEX {acPMSBCOutUserDefinedFailures8Interval}
       ::= {acPMSBCOutUserDefinedFailures8Table 1}



     -- ****************************************
     -- acPMSBCOutUserDefinedFailures8 TABLE
     -- ****************************************
     AcPMSBCOutUserDefinedFailures8Entry ::= SEQUENCE {
       acPMSBCOutUserDefinedFailures8Interval          Unsigned32,
       acPMSBCOutUserDefinedFailures8Val               Counter32
     }



     acPMSBCOutUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures8Entry 1}



     acPMSBCOutUserDefinedFailures8Val OBJECT-TYPE
       SYNTAX Counter32
       MAX-ACCESS read-only
       STATUS obsolete
       DESCRIPTION
           "Value of gauge or counter."
       ::= {acPMSBCOutUserDefinedFailures8Entry 2}



     -- ****************************************
     -- acPMSBCSRDInUserDefinedFailures8 table declaration
     -- ****************************************
     acPMSBCSRDInUserDefinedFailures8Table OBJECT-TYPE
       SYNTAX SEQUENCE OF AcPMSBCSRDInUserDefinedFailures8Entry
       MAX-ACCESS not-accessible
       STATUS obsolete
       DESCRIPTION
           "Number of user defined Failures 8 for incoming dialogs per SRD"
       ::= {acPMSBCUserDefinedFailures8 3}



     -- ****************************************
     -- acPMSBCSRDInUserDefinedFailures8 table entry
     -- ****************************************
     acPMSBCSRDInUserDefinedFailures8Entry OBJECT-TYPE
       SYNTAX AcPMSBCSRDInUserDefinedFailures8Entry
       MAX-ACCESS not-accessible
       STATUS obsolete
       DESCRIPTION
           ""
       INDEX {acPMSBCSRDInUserDefinedFailures8SrdID,acPMSBCSRDInUserDefinedFailures8Interval}
       ::= {acPMSBCSRDInUserDefinedFailures8Table 1}



     -- ****************************************
     -- acPMSBCSRDInUserDefinedFailures8 TABLE
     -- ****************************************
     AcPMSBCSRDInUserDefinedFailures8Entry ::= SEQUENCE {
       acPMSBCSRDInUserDefinedFailures8SrdID           Unsigned32,
       acPMSBCSRDInUserDefinedFailures8Interval        Unsigned32,
       acPMSBCSRDInUserDefinedFailures8Val             Counter32
     }



     acPMSBCSRDInUserDefinedFailures8SrdID OBJECT-TYPE
       SYNTAX Unsigned32 (0..600)
       MAX-ACCESS not-accessible
       STATUS obsolete
       DESCRIPTION
           "SRD number.
0 is the first SRD."
       ::= {acPMSBCSRDInUserDefinedFailures8Entry 1}



     acPMSBCSRDInUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures8Entry 2}



     acPMSBCSRDInUserDefinedFailures8Val OBJECT-TYPE
       SYNTAX Counter32
       MAX-ACCESS read-only
       STATUS obsolete
       DESCRIPTION
           "Value of gauge or counter."
       ::= {acPMSBCSRDInUserDefinedFailures8Entry 3}



     -- ****************************************
     -- acPMSBCSRDOutUserDefinedFailures8 table declaration
     -- ****************************************
     acPMSBCSRDOutUserDefinedFailures8Table OBJECT-TYPE
       SYNTAX SEQUENCE OF AcPMSBCSRDOutUserDefinedFailures8Entry
       MAX-ACCESS not-accessible
       STATUS obsolete
       DESCRIPTION
           "Number of user defined Failures 8 for outgoing dialogs per SRD"
       ::= {acPMSBCUserDefinedFailures8 4}



     -- ****************************************
     -- acPMSBCSRDOutUserDefinedFailures8 table entry
     -- ****************************************
     acPMSBCSRDOutUserDefinedFailures8Entry OBJECT-TYPE
       SYNTAX AcPMSBCSRDOutUserDefinedFailures8Entry
       MAX-ACCESS not-accessible
       STATUS obsolete
       DESCRIPTION
           ""
       INDEX {acPMSBCSRDOutUserDefinedFailures8SrdID,acPMSBCSRDOutUserDefinedFailures8Interval}
       ::= {acPMSBCSRDOutUserDefinedFailures8Table 1}



     -- ****************************************
     -- acPMSBCSRDOutUserDefinedFailures8 TABLE
     -- ****************************************
     AcPMSBCSRDOutUserDefinedFailures8Entry ::= SEQUENCE {
       acPMSBCSRDOutUserDefinedFailures8SrdID          Unsigned32,
       acPMSBCSRDOutUserDefinedFailures8Interval       Unsigned32,
       acPMSBCSRDOutUserDefinedFailures8Val            Counter32
     }



     acPMSBCSRDOutUserDefinedFailures8SrdID OBJECT-TYPE
       SYNTAX Unsigned32 (0..600)
       MAX-ACCESS not-accessible
       STATUS obsolete
       DESCRIPTION
           "SRD number.
0 is the first SRD."
       ::= {acPMSBCSRDOutUserDefinedFailures8Entry 1}



     acPMSBCSRDOutUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures8Entry 2}



     acPMSBCSRDOutUserDefinedFailures8Val OBJECT-TYPE
       SYNTAX Counter32
       MAX-ACCESS read-only
       STATUS obsolete
       DESCRIPTION
           "Value of gauge or counter."
       ::= {acPMSBCSRDOutUserDefinedFailures8Entry 3}



     -- ****************************************
     -- acPMSBCIPGroupInUserDefinedFailures8 table declaration
     -- ****************************************
     acPMSBCIPGroupInUserDefinedFailures8Table OBJECT-TYPE
       SYNTAX SEQUENCE OF AcPMSBCIPGroupInUserDefinedFailures8Entry
       MAX-ACCESS not-accessible
       STATUS obsolete
       DESCRIPTION
           "Number of user defined Failures 8 for incoming dialogs per IP Group"
       ::= {acPMSBCUserDefinedFailures8 5}



     -- ****************************************
     -- acPMSBCIPGroupInUserDefinedFailures8 table entry
     -- ****************************************
     acPMSBCIPGroupInUserDefinedFailures8Entry OBJECT-TYPE
       SYNTAX AcPMSBCIPGroupInUserDefinedFailures8Entry
       MAX-ACCESS not-accessible
       STATUS obsolete
       DESCRIPTION
           ""
       INDEX {acPMSBCIPGroupInUserDefinedFailures8IPGroupID,acPMSBCIPGroupInUserDefinedFailures8Interval}
       ::= {acPMSBCIPGroupInUserDefinedFailures8Table 1}



     -- ****************************************
     -- acPMSBCIPGroupInUserDefinedFailures8 TABLE
     -- ****************************************
     AcPMSBCIPGroupInUserDefinedFailures8Entry ::= SEQUENCE {
       acPMSBCIPGroupInUserDefinedFailures8IPGroupID   Unsigned32,
       acPMSBCIPGroupInUserDefinedFailures8Interval    Unsigned32,
       acPMSBCIPGroupInUserDefinedFailures8Val         Counter32
     }



     acPMSBCIPGroupInUserDefinedFailures8IPGroupID OBJECT-TYPE
       SYNTAX Unsigned32 (0..5000)
       MAX-ACCESS not-accessible
       STATUS obsolete
       DESCRIPTION
           "IP Group number."
       ::= {acPMSBCIPGroupInUserDefinedFailures8Entry 1}



     acPMSBCIPGroupInUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures8Entry 2}



     acPMSBCIPGroupInUserDefinedFailures8Val OBJECT-TYPE
       SYNTAX Counter32
       MAX-ACCESS read-only
       STATUS obsolete
       DESCRIPTION
           "Value of gauge or counter."
       ::= {acPMSBCIPGroupInUserDefinedFailures8Entry 3}



     -- ****************************************
     -- acPMSBCIPGroupOutUserDefinedFailures8 table declaration
     -- ****************************************
     acPMSBCIPGroupOutUserDefinedFailures8Table OBJECT-TYPE
       SYNTAX SEQUENCE OF AcPMSBCIPGroupOutUserDefinedFailures8Entry
       MAX-ACCESS not-accessible
       STATUS obsolete
       DESCRIPTION
           "Number of user defined Failures 8 for outgoing dialogs per IP Group"
       ::= {acPMSBCUserDefinedFailures8 6}



     -- ****************************************
     -- acPMSBCIPGroupOutUserDefinedFailures8 table entry
     -- ****************************************
     acPMSBCIPGroupOutUserDefinedFailures8Entry OBJECT-TYPE
       SYNTAX AcPMSBCIPGroupOutUserDefinedFailures8Entry
       MAX-ACCESS not-accessible
       STATUS obsolete
       DESCRIPTION
           ""
       INDEX {acPMSBCIPGroupOutUserDefinedFailures8IPGroupID,acPMSBCIPGroupOutUserDefinedFailures8Interval}
       ::= {acPMSBCIPGroupOutUserDefinedFailures8Table 1}



     -- ****************************************
     -- acPMSBCIPGroupOutUserDefinedFailures8 TABLE
     -- ****************************************
     AcPMSBCIPGroupOutUserDefinedFailures8Entry ::= SEQUENCE {
       acPMSBCIPGroupOutUserDefinedFailures8IPGroupID  Unsigned32,
       acPMSBCIPGroupOutUserDefinedFailures8Interval   Unsigned32,
       acPMSBCIPGroupOutUserDefinedFailures8Val        Counter32
     }



     acPMSBCIPGroupOutUserDefinedFailures8IPGroupID OBJECT-TYPE
       SYNTAX Unsigned32 (0..5000)
       MAX-ACCESS not-accessible
       STATUS obsolete
       DESCRIPTION
           "IP Group number."
       ::= {acPMSBCIPGroupOutUserDefinedFailures8Entry 1}



     acPMSBCIPGroupOutUserDefinedFailures8Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures8Entry 2}



     acPMSBCIPGroupOutUserDefinedFailures8Val OBJECT-TYPE
       SYNTAX Counter32
       MAX-ACCESS read-only
       STATUS obsolete
       DESCRIPTION
           "Value of gauge or counter."
       ::= {acPMSBCIPGroupOutUserDefinedFailures8Entry 3}



     acPMSBCUserDefinedFailures9 OBJECT IDENTIFIER ::= {acPMSBCUserDefinedFailuresPMs 9}


     -- ****************************************
     -- acPMSBCInUserDefinedFailures9 table declaration
     -- ****************************************
     acPMSBCInUserDefinedFailures9Table OBJECT-TYPE
       SYNTAX SEQUENCE OF AcPMSBCInUserDefinedFailures9Entry
       MAX-ACCESS not-accessible
       STATUS obsolete
       DESCRIPTION
           "Number of user defined failures 9 for incoming dialogs (System global)"
       ::= {acPMSBCUserDefinedFailures9 1}



     -- ****************************************
     -- acPMSBCInUserDefinedFailures9 table entry
     -- ****************************************
     acPMSBCInUserDefinedFailures9Entry OBJECT-TYPE
       SYNTAX AcPMSBCInUserDefinedFailures9Entry
       MAX-ACCESS not-accessible
       STATUS obsolete
       DESCRIPTION
           ""
       INDEX {acPMSBCInUserDefinedFailures9Interval}
       ::= {acPMSBCInUserDefinedFailures9Table 1}



     -- ****************************************
     -- acPMSBCInUserDefinedFailures9 TABLE
     -- ****************************************
     AcPMSBCInUserDefinedFailures9Entry ::= SEQUENCE {
       acPMSBCInUserDefinedFailures9Interval           Unsigned32,
       acPMSBCInUserDefinedFailures9Val                Counter32
     }



     acPMSBCInUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures9Entry 1}



     acPMSBCInUserDefinedFailures9Val OBJECT-TYPE
       SYNTAX Counter32
       MAX-ACCESS read-only
       STATUS obsolete
       DESCRIPTION
           "Value of gauge or counter."
       ::= {acPMSBCInUserDefinedFailures9Entry 2}



     -- ****************************************
     -- acPMSBCOutUserDefinedFailures9 table declaration
     -- ****************************************
     acPMSBCOutUserDefinedFailures9Table OBJECT-TYPE
       SYNTAX SEQUENCE OF AcPMSBCOutUserDefinedFailures9Entry
       MAX-ACCESS not-accessible
       STATUS obsolete
       DESCRIPTION
           "Number of user defined Failures 9 for outgoing dialogs (System global)"
       ::= {acPMSBCUserDefinedFailures9 2}



     -- ****************************************
     -- acPMSBCOutUserDefinedFailures9 table entry
     -- ****************************************
     acPMSBCOutUserDefinedFailures9Entry OBJECT-TYPE
       SYNTAX AcPMSBCOutUserDefinedFailures9Entry
       MAX-ACCESS not-accessible
       STATUS obsolete
       DESCRIPTION
           ""
       INDEX {acPMSBCOutUserDefinedFailures9Interval}
       ::= {acPMSBCOutUserDefinedFailures9Table 1}



     -- ****************************************
     -- acPMSBCOutUserDefinedFailures9 TABLE
     -- ****************************************
     AcPMSBCOutUserDefinedFailures9Entry ::= SEQUENCE {
       acPMSBCOutUserDefinedFailures9Interval          Unsigned32,
       acPMSBCOutUserDefinedFailures9Val               Counter32
     }



     acPMSBCOutUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures9Entry 1}



     acPMSBCOutUserDefinedFailures9Val OBJECT-TYPE
       SYNTAX Counter32
       MAX-ACCESS read-only
       STATUS obsolete
       DESCRIPTION
           "Value of gauge or counter."
       ::= {acPMSBCOutUserDefinedFailures9Entry 2}



     -- ****************************************
     -- acPMSBCSRDInUserDefinedFailures9 table declaration
     -- ****************************************
     acPMSBCSRDInUserDefinedFailures9Table OBJECT-TYPE
       SYNTAX SEQUENCE OF AcPMSBCSRDInUserDefinedFailures9Entry
       MAX-ACCESS not-accessible
       STATUS obsolete
       DESCRIPTION
           "Number of user defined Failures 9 for incoming dialogs per SRD"
       ::= {acPMSBCUserDefinedFailures9 3}



     -- ****************************************
     -- acPMSBCSRDInUserDefinedFailures9 table entry
     -- ****************************************
     acPMSBCSRDInUserDefinedFailures9Entry OBJECT-TYPE
       SYNTAX AcPMSBCSRDInUserDefinedFailures9Entry
       MAX-ACCESS not-accessible
       STATUS obsolete
       DESCRIPTION
           ""
       INDEX {acPMSBCSRDInUserDefinedFailures9SrdID,acPMSBCSRDInUserDefinedFailures9Interval}
       ::= {acPMSBCSRDInUserDefinedFailures9Table 1}



     -- ****************************************
     -- acPMSBCSRDInUserDefinedFailures9 TABLE
     -- ****************************************
     AcPMSBCSRDInUserDefinedFailures9Entry ::= SEQUENCE {
       acPMSBCSRDInUserDefinedFailures9SrdID           Unsigned32,
       acPMSBCSRDInUserDefinedFailures9Interval        Unsigned32,
       acPMSBCSRDInUserDefinedFailures9Val             Counter32
     }



     acPMSBCSRDInUserDefinedFailures9SrdID OBJECT-TYPE
       SYNTAX Unsigned32 (0..600)
       MAX-ACCESS not-accessible
       STATUS obsolete
       DESCRIPTION
           "SRD number.
0 is the first SRD."
       ::= {acPMSBCSRDInUserDefinedFailures9Entry 1}



     acPMSBCSRDInUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures9Entry 2}



     acPMSBCSRDInUserDefinedFailures9Val OBJECT-TYPE
       SYNTAX Counter32
       MAX-ACCESS read-only
       STATUS obsolete
       DESCRIPTION
           "Value of gauge or counter."
       ::= {acPMSBCSRDInUserDefinedFailures9Entry 3}



     -- ****************************************
     -- acPMSBCSRDOutUserDefinedFailures9 table declaration
     -- ****************************************
     acPMSBCSRDOutUserDefinedFailures9Table OBJECT-TYPE
       SYNTAX SEQUENCE OF AcPMSBCSRDOutUserDefinedFailures9Entry
       MAX-ACCESS not-accessible
       STATUS obsolete
       DESCRIPTION
           "Number of user defined Failures 9 for outgoing dialogs per SRD"
       ::= {acPMSBCUserDefinedFailures9 4}



     -- ****************************************
     -- acPMSBCSRDOutUserDefinedFailures9 table entry
     -- ****************************************
     acPMSBCSRDOutUserDefinedFailures9Entry OBJECT-TYPE
       SYNTAX AcPMSBCSRDOutUserDefinedFailures9Entry
       MAX-ACCESS not-accessible
       STATUS obsolete
       DESCRIPTION
           ""
       INDEX {acPMSBCSRDOutUserDefinedFailures9SrdID,acPMSBCSRDOutUserDefinedFailures9Interval}
       ::= {acPMSBCSRDOutUserDefinedFailures9Table 1}



     -- ****************************************
     -- acPMSBCSRDOutUserDefinedFailures9 TABLE
     -- ****************************************
     AcPMSBCSRDOutUserDefinedFailures9Entry ::= SEQUENCE {
       acPMSBCSRDOutUserDefinedFailures9SrdID          Unsigned32,
       acPMSBCSRDOutUserDefinedFailures9Interval       Unsigned32,
       acPMSBCSRDOutUserDefinedFailures9Val            Counter32
     }



     acPMSBCSRDOutUserDefinedFailures9SrdID OBJECT-TYPE
       SYNTAX Unsigned32 (0..600)
       MAX-ACCESS not-accessible
       STATUS obsolete
       DESCRIPTION
           "SRD number.
0 is the first SRD."
       ::= {acPMSBCSRDOutUserDefinedFailures9Entry 1}



     acPMSBCSRDOutUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures9Entry 2}



     acPMSBCSRDOutUserDefinedFailures9Val OBJECT-TYPE
       SYNTAX Counter32
       MAX-ACCESS read-only
       STATUS obsolete
       DESCRIPTION
           "Value of gauge or counter."
       ::= {acPMSBCSRDOutUserDefinedFailures9Entry 3}



     -- ****************************************
     -- acPMSBCIPGroupInUserDefinedFailures9 table declaration
     -- ****************************************
     acPMSBCIPGroupInUserDefinedFailures9Table OBJECT-TYPE
       SYNTAX SEQUENCE OF AcPMSBCIPGroupInUserDefinedFailures9Entry
       MAX-ACCESS not-accessible
       STATUS obsolete
       DESCRIPTION
           "Number of user defined Failures 9 for incoming dialogs per IP Group"
       ::= {acPMSBCUserDefinedFailures9 5}



     -- ****************************************
     -- acPMSBCIPGroupInUserDefinedFailures9 table entry
     -- ****************************************
     acPMSBCIPGroupInUserDefinedFailures9Entry OBJECT-TYPE
       SYNTAX AcPMSBCIPGroupInUserDefinedFailures9Entry
       MAX-ACCESS not-accessible
       STATUS obsolete
       DESCRIPTION
           ""
       INDEX {acPMSBCIPGroupInUserDefinedFailures9IPGroupID,acPMSBCIPGroupInUserDefinedFailures9Interval}
       ::= {acPMSBCIPGroupInUserDefinedFailures9Table 1}



     -- ****************************************
     -- acPMSBCIPGroupInUserDefinedFailures9 TABLE
     -- ****************************************
     AcPMSBCIPGroupInUserDefinedFailures9Entry ::= SEQUENCE {
       acPMSBCIPGroupInUserDefinedFailures9IPGroupID   Unsigned32,
       acPMSBCIPGroupInUserDefinedFailures9Interval    Unsigned32,
       acPMSBCIPGroupInUserDefinedFailures9Val         Counter32
     }



     acPMSBCIPGroupInUserDefinedFailures9IPGroupID OBJECT-TYPE
       SYNTAX Unsigned32 (0..5000)
       MAX-ACCESS not-accessible
       STATUS obsolete
       DESCRIPTION
           "IP Group number."
       ::= {acPMSBCIPGroupInUserDefinedFailures9Entry 1}



     acPMSBCIPGroupInUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures9Entry 2}



     acPMSBCIPGroupInUserDefinedFailures9Val OBJECT-TYPE
       SYNTAX Counter32
       MAX-ACCESS read-only
       STATUS obsolete
       DESCRIPTION
           "Value of gauge or counter."
       ::= {acPMSBCIPGroupInUserDefinedFailures9Entry 3}



     -- ****************************************
     -- acPMSBCIPGroupOutUserDefinedFailures9 table declaration
     -- ****************************************
     acPMSBCIPGroupOutUserDefinedFailures9Table OBJECT-TYPE
       SYNTAX SEQUENCE OF AcPMSBCIPGroupOutUserDefinedFailures9Entry
       MAX-ACCESS not-accessible
       STATUS obsolete
       DESCRIPTION
           "Number of user defined Failures 9 for outgoing dialogs per IP Group"
       ::= {acPMSBCUserDefinedFailures9 6}



     -- ****************************************
     -- acPMSBCIPGroupOutUserDefinedFailures9 table entry
     -- ****************************************
     acPMSBCIPGroupOutUserDefinedFailures9Entry OBJECT-TYPE
       SYNTAX AcPMSBCIPGroupOutUserDefinedFailures9Entry
       MAX-ACCESS not-accessible
       STATUS obsolete
       DESCRIPTION
           ""
       INDEX {acPMSBCIPGroupOutUserDefinedFailures9IPGroupID,acPMSBCIPGroupOutUserDefinedFailures9Interval}
       ::= {acPMSBCIPGroupOutUserDefinedFailures9Table 1}



     -- ****************************************
     -- acPMSBCIPGroupOutUserDefinedFailures9 TABLE
     -- ****************************************
     AcPMSBCIPGroupOutUserDefinedFailures9Entry ::= SEQUENCE {
       acPMSBCIPGroupOutUserDefinedFailures9IPGroupID  Unsigned32,
       acPMSBCIPGroupOutUserDefinedFailures9Interval   Unsigned32,
       acPMSBCIPGroupOutUserDefinedFailures9Val        Counter32
     }



     acPMSBCIPGroupOutUserDefinedFailures9IPGroupID OBJECT-TYPE
       SYNTAX Unsigned32 (0..5000)
       MAX-ACCESS not-accessible
       STATUS obsolete
       DESCRIPTION
           "IP Group number."
       ::= {acPMSBCIPGroupOutUserDefinedFailures9Entry 1}



     acPMSBCIPGroupOutUserDefinedFailures9Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures9Entry 2}



     acPMSBCIPGroupOutUserDefinedFailures9Val OBJECT-TYPE
       SYNTAX Counter32
       MAX-ACCESS read-only
       STATUS obsolete
       DESCRIPTION
           "Value of gauge or counter."
       ::= {acPMSBCIPGroupOutUserDefinedFailures9Entry 3}



     acPMSBCUserDefinedFailures10 OBJECT IDENTIFIER ::= {acPMSBCUserDefinedFailuresPMs 10}


     -- ****************************************
     -- acPMSBCInUserDefinedFailures10 table declaration
     -- ****************************************
     acPMSBCInUserDefinedFailures10Table OBJECT-TYPE
       SYNTAX SEQUENCE OF AcPMSBCInUserDefinedFailures10Entry
       MAX-ACCESS not-accessible
       STATUS obsolete
       DESCRIPTION
           "Number of user defined failures 10 for incoming dialogs (System global)"
       ::= {acPMSBCUserDefinedFailures10 1}



     -- ****************************************
     -- acPMSBCInUserDefinedFailures10 table entry
     -- ****************************************
     acPMSBCInUserDefinedFailures10Entry OBJECT-TYPE
       SYNTAX AcPMSBCInUserDefinedFailures10Entry
       MAX-ACCESS not-accessible
       STATUS obsolete
       DESCRIPTION
           ""
       INDEX {acPMSBCInUserDefinedFailures10Interval}
       ::= {acPMSBCInUserDefinedFailures10Table 1}



     -- ****************************************
     -- acPMSBCInUserDefinedFailures10 TABLE
     -- ****************************************
     AcPMSBCInUserDefinedFailures10Entry ::= SEQUENCE {
       acPMSBCInUserDefinedFailures10Interval          Unsigned32,
       acPMSBCInUserDefinedFailures10Val               Counter32
     }



     acPMSBCInUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures10Entry 1}



     acPMSBCInUserDefinedFailures10Val OBJECT-TYPE
       SYNTAX Counter32
       MAX-ACCESS read-only
       STATUS obsolete
       DESCRIPTION
           "Value of gauge or counter."
       ::= {acPMSBCInUserDefinedFailures10Entry 2}



     -- ****************************************
     -- acPMSBCOutUserDefinedFailures10 table declaration
     -- ****************************************
     acPMSBCOutUserDefinedFailures10Table OBJECT-TYPE
       SYNTAX SEQUENCE OF AcPMSBCOutUserDefinedFailures10Entry
       MAX-ACCESS not-accessible
       STATUS obsolete
       DESCRIPTION
           "Number of user defined Failures 10 for outgoing dialogs (System global)"
       ::= {acPMSBCUserDefinedFailures10 2}



     -- ****************************************
     -- acPMSBCOutUserDefinedFailures10 table entry
     -- ****************************************
     acPMSBCOutUserDefinedFailures10Entry OBJECT-TYPE
       SYNTAX AcPMSBCOutUserDefinedFailures10Entry
       MAX-ACCESS not-accessible
       STATUS obsolete
       DESCRIPTION
           ""
       INDEX {acPMSBCOutUserDefinedFailures10Interval}
       ::= {acPMSBCOutUserDefinedFailures10Table 1}



     -- ****************************************
     -- acPMSBCOutUserDefinedFailures10 TABLE
     -- ****************************************
     AcPMSBCOutUserDefinedFailures10Entry ::= SEQUENCE {
       acPMSBCOutUserDefinedFailures10Interval         Unsigned32,
       acPMSBCOutUserDefinedFailures10Val              Counter32
     }



     acPMSBCOutUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures10Entry 1}



     acPMSBCOutUserDefinedFailures10Val OBJECT-TYPE
       SYNTAX Counter32
       MAX-ACCESS read-only
       STATUS obsolete
       DESCRIPTION
           "Value of gauge or counter."
       ::= {acPMSBCOutUserDefinedFailures10Entry 2}



     -- ****************************************
     -- acPMSBCSRDInUserDefinedFailures10 table declaration
     -- ****************************************
     acPMSBCSRDInUserDefinedFailures10Table OBJECT-TYPE
       SYNTAX SEQUENCE OF AcPMSBCSRDInUserDefinedFailures10Entry
       MAX-ACCESS not-accessible
       STATUS obsolete
       DESCRIPTION
           "Number of user defined Failures 10 for incoming dialogs per SRD"
       ::= {acPMSBCUserDefinedFailures10 3}



     -- ****************************************
     -- acPMSBCSRDInUserDefinedFailures10 table entry
     -- ****************************************
     acPMSBCSRDInUserDefinedFailures10Entry OBJECT-TYPE
       SYNTAX AcPMSBCSRDInUserDefinedFailures10Entry
       MAX-ACCESS not-accessible
       STATUS obsolete
       DESCRIPTION
           ""
       INDEX {acPMSBCSRDInUserDefinedFailures10SrdID,acPMSBCSRDInUserDefinedFailures10Interval}
       ::= {acPMSBCSRDInUserDefinedFailures10Table 1}



     -- ****************************************
     -- acPMSBCSRDInUserDefinedFailures10 TABLE
     -- ****************************************
     AcPMSBCSRDInUserDefinedFailures10Entry ::= SEQUENCE {
       acPMSBCSRDInUserDefinedFailures10SrdID          Unsigned32,
       acPMSBCSRDInUserDefinedFailures10Interval       Unsigned32,
       acPMSBCSRDInUserDefinedFailures10Val            Counter32
     }



     acPMSBCSRDInUserDefinedFailures10SrdID OBJECT-TYPE
       SYNTAX Unsigned32 (0..600)
       MAX-ACCESS not-accessible
       STATUS obsolete
       DESCRIPTION
           "SRD number.
0 is the first SRD."
       ::= {acPMSBCSRDInUserDefinedFailures10Entry 1}



     acPMSBCSRDInUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures10Entry 2}



     acPMSBCSRDInUserDefinedFailures10Val OBJECT-TYPE
       SYNTAX Counter32
       MAX-ACCESS read-only
       STATUS obsolete
       DESCRIPTION
           "Value of gauge or counter."
       ::= {acPMSBCSRDInUserDefinedFailures10Entry 3}



     -- ****************************************
     -- acPMSBCSRDOutUserDefinedFailures10 table declaration
     -- ****************************************
     acPMSBCSRDOutUserDefinedFailures10Table OBJECT-TYPE
       SYNTAX SEQUENCE OF AcPMSBCSRDOutUserDefinedFailures10Entry
       MAX-ACCESS not-accessible
       STATUS obsolete
       DESCRIPTION
           "Number of user defined Failures 10 for outgoing dialogs per SRD"
       ::= {acPMSBCUserDefinedFailures10 4}



     -- ****************************************
     -- acPMSBCSRDOutUserDefinedFailures10 table entry
     -- ****************************************
     acPMSBCSRDOutUserDefinedFailures10Entry OBJECT-TYPE
       SYNTAX AcPMSBCSRDOutUserDefinedFailures10Entry
       MAX-ACCESS not-accessible
       STATUS obsolete
       DESCRIPTION
           ""
       INDEX {acPMSBCSRDOutUserDefinedFailures10SrdID,acPMSBCSRDOutUserDefinedFailures10Interval}
       ::= {acPMSBCSRDOutUserDefinedFailures10Table 1}



     -- ****************************************
     -- acPMSBCSRDOutUserDefinedFailures10 TABLE
     -- ****************************************
     AcPMSBCSRDOutUserDefinedFailures10Entry ::= SEQUENCE {
       acPMSBCSRDOutUserDefinedFailures10SrdID         Unsigned32,
       acPMSBCSRDOutUserDefinedFailures10Interval      Unsigned32,
       acPMSBCSRDOutUserDefinedFailures10Val           Counter32
     }



     acPMSBCSRDOutUserDefinedFailures10SrdID OBJECT-TYPE
       SYNTAX Unsigned32 (0..600)
       MAX-ACCESS not-accessible
       STATUS obsolete
       DESCRIPTION
           "SRD number.
0 is the first SRD."
       ::= {acPMSBCSRDOutUserDefinedFailures10Entry 1}



     acPMSBCSRDOutUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures10Entry 2}



     acPMSBCSRDOutUserDefinedFailures10Val OBJECT-TYPE
       SYNTAX Counter32
       MAX-ACCESS read-only
       STATUS obsolete
       DESCRIPTION
           "Value of gauge or counter."
       ::= {acPMSBCSRDOutUserDefinedFailures10Entry 3}



     -- ****************************************
     -- acPMSBCIPGroupInUserDefinedFailures10 table declaration
     -- ****************************************
     acPMSBCIPGroupInUserDefinedFailures10Table OBJECT-TYPE
       SYNTAX SEQUENCE OF AcPMSBCIPGroupInUserDefinedFailures10Entry
       MAX-ACCESS not-accessible
       STATUS obsolete
       DESCRIPTION
           "Number of user defined Failures 10 for incoming dialogs per IP Group"
       ::= {acPMSBCUserDefinedFailures10 5}



     -- ****************************************
     -- acPMSBCIPGroupInUserDefinedFailures10 table entry
     -- ****************************************
     acPMSBCIPGroupInUserDefinedFailures10Entry OBJECT-TYPE
       SYNTAX AcPMSBCIPGroupInUserDefinedFailures10Entry
       MAX-ACCESS not-accessible
       STATUS obsolete
       DESCRIPTION
           ""
       INDEX {acPMSBCIPGroupInUserDefinedFailures10IPGroupID,acPMSBCIPGroupInUserDefinedFailures10Interval}
       ::= {acPMSBCIPGroupInUserDefinedFailures10Table 1}



     -- ****************************************
     -- acPMSBCIPGroupInUserDefinedFailures10 TABLE
     -- ****************************************
     AcPMSBCIPGroupInUserDefinedFailures10Entry ::= SEQUENCE {
       acPMSBCIPGroupInUserDefinedFailures10IPGroupID  Unsigned32,
       acPMSBCIPGroupInUserDefinedFailures10Interval   Unsigned32,
       acPMSBCIPGroupInUserDefinedFailures10Val        Counter32
     }



     acPMSBCIPGroupInUserDefinedFailures10IPGroupID OBJECT-TYPE
       SYNTAX Unsigned32 (0..5000)
       MAX-ACCESS not-accessible
       STATUS obsolete
       DESCRIPTION
           "IP Group number."
       ::= {acPMSBCIPGroupInUserDefinedFailures10Entry 1}



     acPMSBCIPGroupInUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures10Entry 2}



     acPMSBCIPGroupInUserDefinedFailures10Val OBJECT-TYPE
       SYNTAX Counter32
       MAX-ACCESS read-only
       STATUS obsolete
       DESCRIPTION
           "Value of gauge or counter."
       ::= {acPMSBCIPGroupInUserDefinedFailures10Entry 3}



     -- ****************************************
     -- acPMSBCIPGroupOutUserDefinedFailures10 table declaration
     -- ****************************************
     acPMSBCIPGroupOutUserDefinedFailures10Table OBJECT-TYPE
       SYNTAX SEQUENCE OF AcPMSBCIPGroupOutUserDefinedFailures10Entry
       MAX-ACCESS not-accessible
       STATUS obsolete
       DESCRIPTION
           "Number of user defined Failures 10 for outgoing dialogs per IP Group"
       ::= {acPMSBCUserDefinedFailures10 6}



     -- ****************************************
     -- acPMSBCIPGroupOutUserDefinedFailures10 table entry
     -- ****************************************
     acPMSBCIPGroupOutUserDefinedFailures10Entry OBJECT-TYPE
       SYNTAX AcPMSBCIPGroupOutUserDefinedFailures10Entry
       MAX-ACCESS not-accessible
       STATUS obsolete
       DESCRIPTION
           ""
       INDEX {acPMSBCIPGroupOutUserDefinedFailures10IPGroupID,acPMSBCIPGroupOutUserDefinedFailures10Interval}
       ::= {acPMSBCIPGroupOutUserDefinedFailures10Table 1}



     -- ****************************************
     -- acPMSBCIPGroupOutUserDefinedFailures10 TABLE
     -- ****************************************
     AcPMSBCIPGroupOutUserDefinedFailures10Entry ::= SEQUENCE {
       acPMSBCIPGroupOutUserDefinedFailures10IPGroupID Unsigned32,
       acPMSBCIPGroupOutUserDefinedFailures10Interval  Unsigned32,
       acPMSBCIPGroupOutUserDefinedFailures10Val       Counter32
     }



     acPMSBCIPGroupOutUserDefinedFailures10IPGroupID OBJECT-TYPE
       SYNTAX Unsigned32 (0..5000)
       MAX-ACCESS not-accessible
       STATUS obsolete
       DESCRIPTION
           "IP Group number."
       ::= {acPMSBCIPGroupOutUserDefinedFailures10Entry 1}



     acPMSBCIPGroupOutUserDefinedFailures10Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures10Entry 2}



     acPMSBCIPGroupOutUserDefinedFailures10Val OBJECT-TYPE
       SYNTAX Counter32
       MAX-ACCESS read-only
       STATUS obsolete
       DESCRIPTION
           "Value of gauge or counter."
       ::= {acPMSBCIPGroupOutUserDefinedFailures10Entry 3}



     acPMSBCUserDefinedFailures11 OBJECT IDENTIFIER ::= {acPMSBCUserDefinedFailuresPMs 11}


     -- ****************************************
     -- acPMSBCInUserDefinedFailures11 table declaration
     -- ****************************************
     acPMSBCInUserDefinedFailures11Table OBJECT-TYPE
       SYNTAX SEQUENCE OF AcPMSBCInUserDefinedFailures11Entry
       MAX-ACCESS not-accessible
       STATUS obsolete
       DESCRIPTION
           "Number of user defined failures 11 for incoming dialogs (System global)"
       ::= {acPMSBCUserDefinedFailures11 1}



     -- ****************************************
     -- acPMSBCInUserDefinedFailures11 table entry
     -- ****************************************
     acPMSBCInUserDefinedFailures11Entry OBJECT-TYPE
       SYNTAX AcPMSBCInUserDefinedFailures11Entry
       MAX-ACCESS not-accessible
       STATUS obsolete
       DESCRIPTION
           ""
       INDEX {acPMSBCInUserDefinedFailures11Interval}
       ::= {acPMSBCInUserDefinedFailures11Table 1}



     -- ****************************************
     -- acPMSBCInUserDefinedFailures11 TABLE
     -- ****************************************
     AcPMSBCInUserDefinedFailures11Entry ::= SEQUENCE {
       acPMSBCInUserDefinedFailures11Interval          Unsigned32,
       acPMSBCInUserDefinedFailures11Val               Counter32
     }



     acPMSBCInUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures11Entry 1}



     acPMSBCInUserDefinedFailures11Val OBJECT-TYPE
       SYNTAX Counter32
       MAX-ACCESS read-only
       STATUS obsolete
       DESCRIPTION
           "Value of gauge or counter."
       ::= {acPMSBCInUserDefinedFailures11Entry 2}



     -- ****************************************
     -- acPMSBCOutUserDefinedFailures11 table declaration
     -- ****************************************
     acPMSBCOutUserDefinedFailures11Table OBJECT-TYPE
       SYNTAX SEQUENCE OF AcPMSBCOutUserDefinedFailures11Entry
       MAX-ACCESS not-accessible
       STATUS obsolete
       DESCRIPTION
           "Number of user defined Failures 11 for outgoing dialogs (System global)"
       ::= {acPMSBCUserDefinedFailures11 2}



     -- ****************************************
     -- acPMSBCOutUserDefinedFailures11 table entry
     -- ****************************************
     acPMSBCOutUserDefinedFailures11Entry OBJECT-TYPE
       SYNTAX AcPMSBCOutUserDefinedFailures11Entry
       MAX-ACCESS not-accessible
       STATUS obsolete
       DESCRIPTION
           ""
       INDEX {acPMSBCOutUserDefinedFailures11Interval}
       ::= {acPMSBCOutUserDefinedFailures11Table 1}



     -- ****************************************
     -- acPMSBCOutUserDefinedFailures11 TABLE
     -- ****************************************
     AcPMSBCOutUserDefinedFailures11Entry ::= SEQUENCE {
       acPMSBCOutUserDefinedFailures11Interval         Unsigned32,
       acPMSBCOutUserDefinedFailures11Val              Counter32
     }



     acPMSBCOutUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures11Entry 1}



     acPMSBCOutUserDefinedFailures11Val OBJECT-TYPE
       SYNTAX Counter32
       MAX-ACCESS read-only
       STATUS obsolete
       DESCRIPTION
           "Value of gauge or counter."
       ::= {acPMSBCOutUserDefinedFailures11Entry 2}



     -- ****************************************
     -- acPMSBCSRDInUserDefinedFailures11 table declaration
     -- ****************************************
     acPMSBCSRDInUserDefinedFailures11Table OBJECT-TYPE
       SYNTAX SEQUENCE OF AcPMSBCSRDInUserDefinedFailures11Entry
       MAX-ACCESS not-accessible
       STATUS obsolete
       DESCRIPTION
           "Number of user defined Failures 11 for incoming dialogs per SRD"
       ::= {acPMSBCUserDefinedFailures11 3}



     -- ****************************************
     -- acPMSBCSRDInUserDefinedFailures11 table entry
     -- ****************************************
     acPMSBCSRDInUserDefinedFailures11Entry OBJECT-TYPE
       SYNTAX AcPMSBCSRDInUserDefinedFailures11Entry
       MAX-ACCESS not-accessible
       STATUS obsolete
       DESCRIPTION
           ""
       INDEX {acPMSBCSRDInUserDefinedFailures11SrdID,acPMSBCSRDInUserDefinedFailures11Interval}
       ::= {acPMSBCSRDInUserDefinedFailures11Table 1}



     -- ****************************************
     -- acPMSBCSRDInUserDefinedFailures11 TABLE
     -- ****************************************
     AcPMSBCSRDInUserDefinedFailures11Entry ::= SEQUENCE {
       acPMSBCSRDInUserDefinedFailures11SrdID          Unsigned32,
       acPMSBCSRDInUserDefinedFailures11Interval       Unsigned32,
       acPMSBCSRDInUserDefinedFailures11Val            Counter32
     }



     acPMSBCSRDInUserDefinedFailures11SrdID OBJECT-TYPE
       SYNTAX Unsigned32 (0..600)
       MAX-ACCESS not-accessible
       STATUS obsolete
       DESCRIPTION
           "SRD number.
0 is the first SRD."
       ::= {acPMSBCSRDInUserDefinedFailures11Entry 1}



     acPMSBCSRDInUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures11Entry 2}



     acPMSBCSRDInUserDefinedFailures11Val OBJECT-TYPE
       SYNTAX Counter32
       MAX-ACCESS read-only
       STATUS obsolete
       DESCRIPTION
           "Value of gauge or counter."
       ::= {acPMSBCSRDInUserDefinedFailures11Entry 3}



     -- ****************************************
     -- acPMSBCSRDOutUserDefinedFailures11 table declaration
     -- ****************************************
     acPMSBCSRDOutUserDefinedFailures11Table OBJECT-TYPE
       SYNTAX SEQUENCE OF AcPMSBCSRDOutUserDefinedFailures11Entry
       MAX-ACCESS not-accessible
       STATUS obsolete
       DESCRIPTION
           "Number of user defined Failures 11 for outgoing dialogs per SRD"
       ::= {acPMSBCUserDefinedFailures11 4}



     -- ****************************************
     -- acPMSBCSRDOutUserDefinedFailures11 table entry
     -- ****************************************
     acPMSBCSRDOutUserDefinedFailures11Entry OBJECT-TYPE
       SYNTAX AcPMSBCSRDOutUserDefinedFailures11Entry
       MAX-ACCESS not-accessible
       STATUS obsolete
       DESCRIPTION
           ""
       INDEX {acPMSBCSRDOutUserDefinedFailures11SrdID,acPMSBCSRDOutUserDefinedFailures11Interval}
       ::= {acPMSBCSRDOutUserDefinedFailures11Table 1}



     -- ****************************************
     -- acPMSBCSRDOutUserDefinedFailures11 TABLE
     -- ****************************************
     AcPMSBCSRDOutUserDefinedFailures11Entry ::= SEQUENCE {
       acPMSBCSRDOutUserDefinedFailures11SrdID         Unsigned32,
       acPMSBCSRDOutUserDefinedFailures11Interval      Unsigned32,
       acPMSBCSRDOutUserDefinedFailures11Val           Counter32
     }



     acPMSBCSRDOutUserDefinedFailures11SrdID OBJECT-TYPE
       SYNTAX Unsigned32 (0..600)
       MAX-ACCESS not-accessible
       STATUS obsolete
       DESCRIPTION
           "SRD number.
0 is the first SRD."
       ::= {acPMSBCSRDOutUserDefinedFailures11Entry 1}



     acPMSBCSRDOutUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures11Entry 2}



     acPMSBCSRDOutUserDefinedFailures11Val OBJECT-TYPE
       SYNTAX Counter32
       MAX-ACCESS read-only
       STATUS obsolete
       DESCRIPTION
           "Value of gauge or counter."
       ::= {acPMSBCSRDOutUserDefinedFailures11Entry 3}



     -- ****************************************
     -- acPMSBCIPGroupInUserDefinedFailures11 table declaration
     -- ****************************************
     acPMSBCIPGroupInUserDefinedFailures11Table OBJECT-TYPE
       SYNTAX SEQUENCE OF AcPMSBCIPGroupInUserDefinedFailures11Entry
       MAX-ACCESS not-accessible
       STATUS obsolete
       DESCRIPTION
           "Number of user defined Failures 11 for incoming dialogs per IP Group"
       ::= {acPMSBCUserDefinedFailures11 5}



     -- ****************************************
     -- acPMSBCIPGroupInUserDefinedFailures11 table entry
     -- ****************************************
     acPMSBCIPGroupInUserDefinedFailures11Entry OBJECT-TYPE
       SYNTAX AcPMSBCIPGroupInUserDefinedFailures11Entry
       MAX-ACCESS not-accessible
       STATUS obsolete
       DESCRIPTION
           ""
       INDEX {acPMSBCIPGroupInUserDefinedFailures11IPGroupID,acPMSBCIPGroupInUserDefinedFailures11Interval}
       ::= {acPMSBCIPGroupInUserDefinedFailures11Table 1}



     -- ****************************************
     -- acPMSBCIPGroupInUserDefinedFailures11 TABLE
     -- ****************************************
     AcPMSBCIPGroupInUserDefinedFailures11Entry ::= SEQUENCE {
       acPMSBCIPGroupInUserDefinedFailures11IPGroupID  Unsigned32,
       acPMSBCIPGroupInUserDefinedFailures11Interval   Unsigned32,
       acPMSBCIPGroupInUserDefinedFailures11Val        Counter32
     }



     acPMSBCIPGroupInUserDefinedFailures11IPGroupID OBJECT-TYPE
       SYNTAX Unsigned32 (0..5000)
       MAX-ACCESS not-accessible
       STATUS obsolete
       DESCRIPTION
           "IP Group number."
       ::= {acPMSBCIPGroupInUserDefinedFailures11Entry 1}



     acPMSBCIPGroupInUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures11Entry 2}



     acPMSBCIPGroupInUserDefinedFailures11Val OBJECT-TYPE
       SYNTAX Counter32
       MAX-ACCESS read-only
       STATUS obsolete
       DESCRIPTION
           "Value of gauge or counter."
       ::= {acPMSBCIPGroupInUserDefinedFailures11Entry 3}



     -- ****************************************
     -- acPMSBCIPGroupOutUserDefinedFailures11 table declaration
     -- ****************************************
     acPMSBCIPGroupOutUserDefinedFailures11Table OBJECT-TYPE
       SYNTAX SEQUENCE OF AcPMSBCIPGroupOutUserDefinedFailures11Entry
       MAX-ACCESS not-accessible
       STATUS obsolete
       DESCRIPTION
           "Number of user defined Failures 11 for outgoing dialogs per IP Group"
       ::= {acPMSBCUserDefinedFailures11 6}



     -- ****************************************
     -- acPMSBCIPGroupOutUserDefinedFailures11 table entry
     -- ****************************************
     acPMSBCIPGroupOutUserDefinedFailures11Entry OBJECT-TYPE
       SYNTAX AcPMSBCIPGroupOutUserDefinedFailures11Entry
       MAX-ACCESS not-accessible
       STATUS obsolete
       DESCRIPTION
           ""
       INDEX {acPMSBCIPGroupOutUserDefinedFailures11IPGroupID,acPMSBCIPGroupOutUserDefinedFailures11Interval}
       ::= {acPMSBCIPGroupOutUserDefinedFailures11Table 1}



     -- ****************************************
     -- acPMSBCIPGroupOutUserDefinedFailures11 TABLE
     -- ****************************************
     AcPMSBCIPGroupOutUserDefinedFailures11Entry ::= SEQUENCE {
       acPMSBCIPGroupOutUserDefinedFailures11IPGroupID Unsigned32,
       acPMSBCIPGroupOutUserDefinedFailures11Interval  Unsigned32,
       acPMSBCIPGroupOutUserDefinedFailures11Val       Counter32
     }



     acPMSBCIPGroupOutUserDefinedFailures11IPGroupID OBJECT-TYPE
       SYNTAX Unsigned32 (0..5000)
       MAX-ACCESS not-accessible
       STATUS obsolete
       DESCRIPTION
           "IP Group number."
       ::= {acPMSBCIPGroupOutUserDefinedFailures11Entry 1}



     acPMSBCIPGroupOutUserDefinedFailures11Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures11Entry 2}



     acPMSBCIPGroupOutUserDefinedFailures11Val OBJECT-TYPE
       SYNTAX Counter32
       MAX-ACCESS read-only
       STATUS obsolete
       DESCRIPTION
           "Value of gauge or counter."
       ::= {acPMSBCIPGroupOutUserDefinedFailures11Entry 3}



     acPMSBCUserDefinedFailures12 OBJECT IDENTIFIER ::= {acPMSBCUserDefinedFailuresPMs 12}


     -- ****************************************
     -- acPMSBCInUserDefinedFailures12 table declaration
     -- ****************************************
     acPMSBCInUserDefinedFailures12Table OBJECT-TYPE
       SYNTAX SEQUENCE OF AcPMSBCInUserDefinedFailures12Entry
       MAX-ACCESS not-accessible
       STATUS obsolete
       DESCRIPTION
           "Number of user defined failures 12 for incoming dialogs (System global)"
       ::= {acPMSBCUserDefinedFailures12 1}



     -- ****************************************
     -- acPMSBCInUserDefinedFailures12 table entry
     -- ****************************************
     acPMSBCInUserDefinedFailures12Entry OBJECT-TYPE
       SYNTAX AcPMSBCInUserDefinedFailures12Entry
       MAX-ACCESS not-accessible
       STATUS obsolete
       DESCRIPTION
           ""
       INDEX {acPMSBCInUserDefinedFailures12Interval}
       ::= {acPMSBCInUserDefinedFailures12Table 1}



     -- ****************************************
     -- acPMSBCInUserDefinedFailures12 TABLE
     -- ****************************************
     AcPMSBCInUserDefinedFailures12Entry ::= SEQUENCE {
       acPMSBCInUserDefinedFailures12Interval          Unsigned32,
       acPMSBCInUserDefinedFailures12Val               Counter32
     }



     acPMSBCInUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures12Entry 1}



     acPMSBCInUserDefinedFailures12Val OBJECT-TYPE
       SYNTAX Counter32
       MAX-ACCESS read-only
       STATUS obsolete
       DESCRIPTION
           "Value of gauge or counter."
       ::= {acPMSBCInUserDefinedFailures12Entry 2}



     -- ****************************************
     -- acPMSBCOutUserDefinedFailures12 table declaration
     -- ****************************************
     acPMSBCOutUserDefinedFailures12Table OBJECT-TYPE
       SYNTAX SEQUENCE OF AcPMSBCOutUserDefinedFailures12Entry
       MAX-ACCESS not-accessible
       STATUS obsolete
       DESCRIPTION
           "Number of user defined Failures 12 for outgoing dialogs (System global)"
       ::= {acPMSBCUserDefinedFailures12 2}



     -- ****************************************
     -- acPMSBCOutUserDefinedFailures12 table entry
     -- ****************************************
     acPMSBCOutUserDefinedFailures12Entry OBJECT-TYPE
       SYNTAX AcPMSBCOutUserDefinedFailures12Entry
       MAX-ACCESS not-accessible
       STATUS obsolete
       DESCRIPTION
           ""
       INDEX {acPMSBCOutUserDefinedFailures12Interval}
       ::= {acPMSBCOutUserDefinedFailures12Table 1}



     -- ****************************************
     -- acPMSBCOutUserDefinedFailures12 TABLE
     -- ****************************************
     AcPMSBCOutUserDefinedFailures12Entry ::= SEQUENCE {
       acPMSBCOutUserDefinedFailures12Interval         Unsigned32,
       acPMSBCOutUserDefinedFailures12Val              Counter32
     }



     acPMSBCOutUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures12Entry 1}



     acPMSBCOutUserDefinedFailures12Val OBJECT-TYPE
       SYNTAX Counter32
       MAX-ACCESS read-only
       STATUS obsolete
       DESCRIPTION
           "Value of gauge or counter."
       ::= {acPMSBCOutUserDefinedFailures12Entry 2}



     -- ****************************************
     -- acPMSBCSRDInUserDefinedFailures12 table declaration
     -- ****************************************
     acPMSBCSRDInUserDefinedFailures12Table OBJECT-TYPE
       SYNTAX SEQUENCE OF AcPMSBCSRDInUserDefinedFailures12Entry
       MAX-ACCESS not-accessible
       STATUS obsolete
       DESCRIPTION
           "Number of user defined Failures 12 for incoming dialogs per SRD"
       ::= {acPMSBCUserDefinedFailures12 3}



     -- ****************************************
     -- acPMSBCSRDInUserDefinedFailures12 table entry
     -- ****************************************
     acPMSBCSRDInUserDefinedFailures12Entry OBJECT-TYPE
       SYNTAX AcPMSBCSRDInUserDefinedFailures12Entry
       MAX-ACCESS not-accessible
       STATUS obsolete
       DESCRIPTION
           ""
       INDEX {acPMSBCSRDInUserDefinedFailures12SrdID,acPMSBCSRDInUserDefinedFailures12Interval}
       ::= {acPMSBCSRDInUserDefinedFailures12Table 1}



     -- ****************************************
     -- acPMSBCSRDInUserDefinedFailures12 TABLE
     -- ****************************************
     AcPMSBCSRDInUserDefinedFailures12Entry ::= SEQUENCE {
       acPMSBCSRDInUserDefinedFailures12SrdID          Unsigned32,
       acPMSBCSRDInUserDefinedFailures12Interval       Unsigned32,
       acPMSBCSRDInUserDefinedFailures12Val            Counter32
     }



     acPMSBCSRDInUserDefinedFailures12SrdID OBJECT-TYPE
       SYNTAX Unsigned32 (0..600)
       MAX-ACCESS not-accessible
       STATUS obsolete
       DESCRIPTION
           "SRD number.
0 is the first SRD."
       ::= {acPMSBCSRDInUserDefinedFailures12Entry 1}



     acPMSBCSRDInUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures12Entry 2}



     acPMSBCSRDInUserDefinedFailures12Val OBJECT-TYPE
       SYNTAX Counter32
       MAX-ACCESS read-only
       STATUS obsolete
       DESCRIPTION
           "Value of gauge or counter."
       ::= {acPMSBCSRDInUserDefinedFailures12Entry 3}



     -- ****************************************
     -- acPMSBCSRDOutUserDefinedFailures12 table declaration
     -- ****************************************
     acPMSBCSRDOutUserDefinedFailures12Table OBJECT-TYPE
       SYNTAX SEQUENCE OF AcPMSBCSRDOutUserDefinedFailures12Entry
       MAX-ACCESS not-accessible
       STATUS obsolete
       DESCRIPTION
           "Number of user defined Failures 12 for outgoing dialogs per SRD"
       ::= {acPMSBCUserDefinedFailures12 4}



     -- ****************************************
     -- acPMSBCSRDOutUserDefinedFailures12 table entry
     -- ****************************************
     acPMSBCSRDOutUserDefinedFailures12Entry OBJECT-TYPE
       SYNTAX AcPMSBCSRDOutUserDefinedFailures12Entry
       MAX-ACCESS not-accessible
       STATUS obsolete
       DESCRIPTION
           ""
       INDEX {acPMSBCSRDOutUserDefinedFailures12SrdID,acPMSBCSRDOutUserDefinedFailures12Interval}
       ::= {acPMSBCSRDOutUserDefinedFailures12Table 1}



     -- ****************************************
     -- acPMSBCSRDOutUserDefinedFailures12 TABLE
     -- ****************************************
     AcPMSBCSRDOutUserDefinedFailures12Entry ::= SEQUENCE {
       acPMSBCSRDOutUserDefinedFailures12SrdID         Unsigned32,
       acPMSBCSRDOutUserDefinedFailures12Interval      Unsigned32,
       acPMSBCSRDOutUserDefinedFailures12Val           Counter32
     }



     acPMSBCSRDOutUserDefinedFailures12SrdID OBJECT-TYPE
       SYNTAX Unsigned32 (0..600)
       MAX-ACCESS not-accessible
       STATUS obsolete
       DESCRIPTION
           "SRD number.
0 is the first SRD."
       ::= {acPMSBCSRDOutUserDefinedFailures12Entry 1}



     acPMSBCSRDOutUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures12Entry 2}



     acPMSBCSRDOutUserDefinedFailures12Val OBJECT-TYPE
       SYNTAX Counter32
       MAX-ACCESS read-only
       STATUS obsolete
       DESCRIPTION
           "Value of gauge or counter."
       ::= {acPMSBCSRDOutUserDefinedFailures12Entry 3}



     -- ****************************************
     -- acPMSBCIPGroupInUserDefinedFailures12 table declaration
     -- ****************************************
     acPMSBCIPGroupInUserDefinedFailures12Table OBJECT-TYPE
       SYNTAX SEQUENCE OF AcPMSBCIPGroupInUserDefinedFailures12Entry
       MAX-ACCESS not-accessible
       STATUS obsolete
       DESCRIPTION
           "Number of user defined Failures 12 for incoming dialogs per IP Group"
       ::= {acPMSBCUserDefinedFailures12 5}



     -- ****************************************
     -- acPMSBCIPGroupInUserDefinedFailures12 table entry
     -- ****************************************
     acPMSBCIPGroupInUserDefinedFailures12Entry OBJECT-TYPE
       SYNTAX AcPMSBCIPGroupInUserDefinedFailures12Entry
       MAX-ACCESS not-accessible
       STATUS obsolete
       DESCRIPTION
           ""
       INDEX {acPMSBCIPGroupInUserDefinedFailures12IPGroupID,acPMSBCIPGroupInUserDefinedFailures12Interval}
       ::= {acPMSBCIPGroupInUserDefinedFailures12Table 1}



     -- ****************************************
     -- acPMSBCIPGroupInUserDefinedFailures12 TABLE
     -- ****************************************
     AcPMSBCIPGroupInUserDefinedFailures12Entry ::= SEQUENCE {
       acPMSBCIPGroupInUserDefinedFailures12IPGroupID  Unsigned32,
       acPMSBCIPGroupInUserDefinedFailures12Interval   Unsigned32,
       acPMSBCIPGroupInUserDefinedFailures12Val        Counter32
     }



     acPMSBCIPGroupInUserDefinedFailures12IPGroupID OBJECT-TYPE
       SYNTAX Unsigned32 (0..5000)
       MAX-ACCESS not-accessible
       STATUS obsolete
       DESCRIPTION
           "IP Group number."
       ::= {acPMSBCIPGroupInUserDefinedFailures12Entry 1}



     acPMSBCIPGroupInUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures12Entry 2}



     acPMSBCIPGroupInUserDefinedFailures12Val OBJECT-TYPE
       SYNTAX Counter32
       MAX-ACCESS read-only
       STATUS obsolete
       DESCRIPTION
           "Value of gauge or counter."
       ::= {acPMSBCIPGroupInUserDefinedFailures12Entry 3}



     -- ****************************************
     -- acPMSBCIPGroupOutUserDefinedFailures12 table declaration
     -- ****************************************
     acPMSBCIPGroupOutUserDefinedFailures12Table OBJECT-TYPE
       SYNTAX SEQUENCE OF AcPMSBCIPGroupOutUserDefinedFailures12Entry
       MAX-ACCESS not-accessible
       STATUS obsolete
       DESCRIPTION
           "Number of user defined Failures 12 for outgoing dialogs per IP Group"
       ::= {acPMSBCUserDefinedFailures12 6}



     -- ****************************************
     -- acPMSBCIPGroupOutUserDefinedFailures12 table entry
     -- ****************************************
     acPMSBCIPGroupOutUserDefinedFailures12Entry OBJECT-TYPE
       SYNTAX AcPMSBCIPGroupOutUserDefinedFailures12Entry
       MAX-ACCESS not-accessible
       STATUS obsolete
       DESCRIPTION
           ""
       INDEX {acPMSBCIPGroupOutUserDefinedFailures12IPGroupID,acPMSBCIPGroupOutUserDefinedFailures12Interval}
       ::= {acPMSBCIPGroupOutUserDefinedFailures12Table 1}



     -- ****************************************
     -- acPMSBCIPGroupOutUserDefinedFailures12 TABLE
     -- ****************************************
     AcPMSBCIPGroupOutUserDefinedFailures12Entry ::= SEQUENCE {
       acPMSBCIPGroupOutUserDefinedFailures12IPGroupID Unsigned32,
       acPMSBCIPGroupOutUserDefinedFailures12Interval  Unsigned32,
       acPMSBCIPGroupOutUserDefinedFailures12Val       Counter32
     }



     acPMSBCIPGroupOutUserDefinedFailures12IPGroupID OBJECT-TYPE
       SYNTAX Unsigned32 (0..5000)
       MAX-ACCESS not-accessible
       STATUS obsolete
       DESCRIPTION
           "IP Group number."
       ::= {acPMSBCIPGroupOutUserDefinedFailures12Entry 1}



     acPMSBCIPGroupOutUserDefinedFailures12Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures12Entry 2}



     acPMSBCIPGroupOutUserDefinedFailures12Val OBJECT-TYPE
       SYNTAX Counter32
       MAX-ACCESS read-only
       STATUS obsolete
       DESCRIPTION
           "Value of gauge or counter."
       ::= {acPMSBCIPGroupOutUserDefinedFailures12Entry 3}



     acPMSBCUserDefinedFailures13 OBJECT IDENTIFIER ::= {acPMSBCUserDefinedFailuresPMs 13}


     -- ****************************************
     -- acPMSBCInUserDefinedFailures13 table declaration
     -- ****************************************
     acPMSBCInUserDefinedFailures13Table OBJECT-TYPE
       SYNTAX SEQUENCE OF AcPMSBCInUserDefinedFailures13Entry
       MAX-ACCESS not-accessible
       STATUS obsolete
       DESCRIPTION
           "Number of user defined failures 13 for incoming dialogs (System global)"
       ::= {acPMSBCUserDefinedFailures13 1}



     -- ****************************************
     -- acPMSBCInUserDefinedFailures13 table entry
     -- ****************************************
     acPMSBCInUserDefinedFailures13Entry OBJECT-TYPE
       SYNTAX AcPMSBCInUserDefinedFailures13Entry
       MAX-ACCESS not-accessible
       STATUS obsolete
       DESCRIPTION
           ""
       INDEX {acPMSBCInUserDefinedFailures13Interval}
       ::= {acPMSBCInUserDefinedFailures13Table 1}



     -- ****************************************
     -- acPMSBCInUserDefinedFailures13 TABLE
     -- ****************************************
     AcPMSBCInUserDefinedFailures13Entry ::= SEQUENCE {
       acPMSBCInUserDefinedFailures13Interval          Unsigned32,
       acPMSBCInUserDefinedFailures13Val               Counter32
     }



     acPMSBCInUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures13Entry 1}



     acPMSBCInUserDefinedFailures13Val OBJECT-TYPE
       SYNTAX Counter32
       MAX-ACCESS read-only
       STATUS obsolete
       DESCRIPTION
           "Value of gauge or counter."
       ::= {acPMSBCInUserDefinedFailures13Entry 2}



     -- ****************************************
     -- acPMSBCOutUserDefinedFailures13 table declaration
     -- ****************************************
     acPMSBCOutUserDefinedFailures13Table OBJECT-TYPE
       SYNTAX SEQUENCE OF AcPMSBCOutUserDefinedFailures13Entry
       MAX-ACCESS not-accessible
       STATUS obsolete
       DESCRIPTION
           "Number of user defined Failures 13 for outgoing dialogs (System global)"
       ::= {acPMSBCUserDefinedFailures13 2}



     -- ****************************************
     -- acPMSBCOutUserDefinedFailures13 table entry
     -- ****************************************
     acPMSBCOutUserDefinedFailures13Entry OBJECT-TYPE
       SYNTAX AcPMSBCOutUserDefinedFailures13Entry
       MAX-ACCESS not-accessible
       STATUS obsolete
       DESCRIPTION
           ""
       INDEX {acPMSBCOutUserDefinedFailures13Interval}
       ::= {acPMSBCOutUserDefinedFailures13Table 1}



     -- ****************************************
     -- acPMSBCOutUserDefinedFailures13 TABLE
     -- ****************************************
     AcPMSBCOutUserDefinedFailures13Entry ::= SEQUENCE {
       acPMSBCOutUserDefinedFailures13Interval         Unsigned32,
       acPMSBCOutUserDefinedFailures13Val              Counter32
     }



     acPMSBCOutUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures13Entry 1}



     acPMSBCOutUserDefinedFailures13Val OBJECT-TYPE
       SYNTAX Counter32
       MAX-ACCESS read-only
       STATUS obsolete
       DESCRIPTION
           "Value of gauge or counter."
       ::= {acPMSBCOutUserDefinedFailures13Entry 2}



     -- ****************************************
     -- acPMSBCSRDInUserDefinedFailures13 table declaration
     -- ****************************************
     acPMSBCSRDInUserDefinedFailures13Table OBJECT-TYPE
       SYNTAX SEQUENCE OF AcPMSBCSRDInUserDefinedFailures13Entry
       MAX-ACCESS not-accessible
       STATUS obsolete
       DESCRIPTION
           "Number of user defined Failures 13 for incoming dialogs per SRD"
       ::= {acPMSBCUserDefinedFailures13 3}



     -- ****************************************
     -- acPMSBCSRDInUserDefinedFailures13 table entry
     -- ****************************************
     acPMSBCSRDInUserDefinedFailures13Entry OBJECT-TYPE
       SYNTAX AcPMSBCSRDInUserDefinedFailures13Entry
       MAX-ACCESS not-accessible
       STATUS obsolete
       DESCRIPTION
           ""
       INDEX {acPMSBCSRDInUserDefinedFailures13SrdID,acPMSBCSRDInUserDefinedFailures13Interval}
       ::= {acPMSBCSRDInUserDefinedFailures13Table 1}



     -- ****************************************
     -- acPMSBCSRDInUserDefinedFailures13 TABLE
     -- ****************************************
     AcPMSBCSRDInUserDefinedFailures13Entry ::= SEQUENCE {
       acPMSBCSRDInUserDefinedFailures13SrdID          Unsigned32,
       acPMSBCSRDInUserDefinedFailures13Interval       Unsigned32,
       acPMSBCSRDInUserDefinedFailures13Val            Counter32
     }



     acPMSBCSRDInUserDefinedFailures13SrdID OBJECT-TYPE
       SYNTAX Unsigned32 (0..600)
       MAX-ACCESS not-accessible
       STATUS obsolete
       DESCRIPTION
           "SRD number.
0 is the first SRD."
       ::= {acPMSBCSRDInUserDefinedFailures13Entry 1}



     acPMSBCSRDInUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures13Entry 2}



     acPMSBCSRDInUserDefinedFailures13Val OBJECT-TYPE
       SYNTAX Counter32
       MAX-ACCESS read-only
       STATUS obsolete
       DESCRIPTION
           "Value of gauge or counter."
       ::= {acPMSBCSRDInUserDefinedFailures13Entry 3}



     -- ****************************************
     -- acPMSBCSRDOutUserDefinedFailures13 table declaration
     -- ****************************************
     acPMSBCSRDOutUserDefinedFailures13Table OBJECT-TYPE
       SYNTAX SEQUENCE OF AcPMSBCSRDOutUserDefinedFailures13Entry
       MAX-ACCESS not-accessible
       STATUS obsolete
       DESCRIPTION
           "Number of user defined Failures 13 for outgoing dialogs per SRD"
       ::= {acPMSBCUserDefinedFailures13 4}



     -- ****************************************
     -- acPMSBCSRDOutUserDefinedFailures13 table entry
     -- ****************************************
     acPMSBCSRDOutUserDefinedFailures13Entry OBJECT-TYPE
       SYNTAX AcPMSBCSRDOutUserDefinedFailures13Entry
       MAX-ACCESS not-accessible
       STATUS obsolete
       DESCRIPTION
           ""
       INDEX {acPMSBCSRDOutUserDefinedFailures13SrdID,acPMSBCSRDOutUserDefinedFailures13Interval}
       ::= {acPMSBCSRDOutUserDefinedFailures13Table 1}



     -- ****************************************
     -- acPMSBCSRDOutUserDefinedFailures13 TABLE
     -- ****************************************
     AcPMSBCSRDOutUserDefinedFailures13Entry ::= SEQUENCE {
       acPMSBCSRDOutUserDefinedFailures13SrdID         Unsigned32,
       acPMSBCSRDOutUserDefinedFailures13Interval      Unsigned32,
       acPMSBCSRDOutUserDefinedFailures13Val           Counter32
     }



     acPMSBCSRDOutUserDefinedFailures13SrdID OBJECT-TYPE
       SYNTAX Unsigned32 (0..600)
       MAX-ACCESS not-accessible
       STATUS obsolete
       DESCRIPTION
           "SRD number.
0 is the first SRD."
       ::= {acPMSBCSRDOutUserDefinedFailures13Entry 1}



     acPMSBCSRDOutUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures13Entry 2}



     acPMSBCSRDOutUserDefinedFailures13Val OBJECT-TYPE
       SYNTAX Counter32
       MAX-ACCESS read-only
       STATUS obsolete
       DESCRIPTION
           "Value of gauge or counter."
       ::= {acPMSBCSRDOutUserDefinedFailures13Entry 3}



     -- ****************************************
     -- acPMSBCIPGroupInUserDefinedFailures13 table declaration
     -- ****************************************
     acPMSBCIPGroupInUserDefinedFailures13Table OBJECT-TYPE
       SYNTAX SEQUENCE OF AcPMSBCIPGroupInUserDefinedFailures13Entry
       MAX-ACCESS not-accessible
       STATUS obsolete
       DESCRIPTION
           "Number of user defined Failures 13 for incoming dialogs per IP Group"
       ::= {acPMSBCUserDefinedFailures13 5}



     -- ****************************************
     -- acPMSBCIPGroupInUserDefinedFailures13 table entry
     -- ****************************************
     acPMSBCIPGroupInUserDefinedFailures13Entry OBJECT-TYPE
       SYNTAX AcPMSBCIPGroupInUserDefinedFailures13Entry
       MAX-ACCESS not-accessible
       STATUS obsolete
       DESCRIPTION
           ""
       INDEX {acPMSBCIPGroupInUserDefinedFailures13IPGroupID,acPMSBCIPGroupInUserDefinedFailures13Interval}
       ::= {acPMSBCIPGroupInUserDefinedFailures13Table 1}



     -- ****************************************
     -- acPMSBCIPGroupInUserDefinedFailures13 TABLE
     -- ****************************************
     AcPMSBCIPGroupInUserDefinedFailures13Entry ::= SEQUENCE {
       acPMSBCIPGroupInUserDefinedFailures13IPGroupID  Unsigned32,
       acPMSBCIPGroupInUserDefinedFailures13Interval   Unsigned32,
       acPMSBCIPGroupInUserDefinedFailures13Val        Counter32
     }



     acPMSBCIPGroupInUserDefinedFailures13IPGroupID OBJECT-TYPE
       SYNTAX Unsigned32 (0..5000)
       MAX-ACCESS not-accessible
       STATUS obsolete
       DESCRIPTION
           "IP Group number."
       ::= {acPMSBCIPGroupInUserDefinedFailures13Entry 1}



     acPMSBCIPGroupInUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures13Entry 2}



     acPMSBCIPGroupInUserDefinedFailures13Val OBJECT-TYPE
       SYNTAX Counter32
       MAX-ACCESS read-only
       STATUS obsolete
       DESCRIPTION
           "Value of gauge or counter."
       ::= {acPMSBCIPGroupInUserDefinedFailures13Entry 3}



     -- ****************************************
     -- acPMSBCIPGroupOutUserDefinedFailures13 table declaration
     -- ****************************************
     acPMSBCIPGroupOutUserDefinedFailures13Table OBJECT-TYPE
       SYNTAX SEQUENCE OF AcPMSBCIPGroupOutUserDefinedFailures13Entry
       MAX-ACCESS not-accessible
       STATUS obsolete
       DESCRIPTION
           "Number of user defined Failures 13 for outgoing dialogs per IP Group"
       ::= {acPMSBCUserDefinedFailures13 6}



     -- ****************************************
     -- acPMSBCIPGroupOutUserDefinedFailures13 table entry
     -- ****************************************
     acPMSBCIPGroupOutUserDefinedFailures13Entry OBJECT-TYPE
       SYNTAX AcPMSBCIPGroupOutUserDefinedFailures13Entry
       MAX-ACCESS not-accessible
       STATUS obsolete
       DESCRIPTION
           ""
       INDEX {acPMSBCIPGroupOutUserDefinedFailures13IPGroupID,acPMSBCIPGroupOutUserDefinedFailures13Interval}
       ::= {acPMSBCIPGroupOutUserDefinedFailures13Table 1}



     -- ****************************************
     -- acPMSBCIPGroupOutUserDefinedFailures13 TABLE
     -- ****************************************
     AcPMSBCIPGroupOutUserDefinedFailures13Entry ::= SEQUENCE {
       acPMSBCIPGroupOutUserDefinedFailures13IPGroupID Unsigned32,
       acPMSBCIPGroupOutUserDefinedFailures13Interval  Unsigned32,
       acPMSBCIPGroupOutUserDefinedFailures13Val       Counter32
     }



     acPMSBCIPGroupOutUserDefinedFailures13IPGroupID OBJECT-TYPE
       SYNTAX Unsigned32 (0..5000)
       MAX-ACCESS not-accessible
       STATUS obsolete
       DESCRIPTION
           "IP Group number."
       ::= {acPMSBCIPGroupOutUserDefinedFailures13Entry 1}



     acPMSBCIPGroupOutUserDefinedFailures13Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures13Entry 2}



     acPMSBCIPGroupOutUserDefinedFailures13Val OBJECT-TYPE
       SYNTAX Counter32
       MAX-ACCESS read-only
       STATUS obsolete
       DESCRIPTION
           "Value of gauge or counter."
       ::= {acPMSBCIPGroupOutUserDefinedFailures13Entry 3}



     acPMSBCUserDefinedFailures14 OBJECT IDENTIFIER ::= {acPMSBCUserDefinedFailuresPMs 14}


     -- ****************************************
     -- acPMSBCInUserDefinedFailures14 table declaration
     -- ****************************************
     acPMSBCInUserDefinedFailures14Table OBJECT-TYPE
       SYNTAX SEQUENCE OF AcPMSBCInUserDefinedFailures14Entry
       MAX-ACCESS not-accessible
       STATUS obsolete
       DESCRIPTION
           "Number of user defined failures 14 for incoming dialogs (System global)"
       ::= {acPMSBCUserDefinedFailures14 1}



     -- ****************************************
     -- acPMSBCInUserDefinedFailures14 table entry
     -- ****************************************
     acPMSBCInUserDefinedFailures14Entry OBJECT-TYPE
       SYNTAX AcPMSBCInUserDefinedFailures14Entry
       MAX-ACCESS not-accessible
       STATUS obsolete
       DESCRIPTION
           ""
       INDEX {acPMSBCInUserDefinedFailures14Interval}
       ::= {acPMSBCInUserDefinedFailures14Table 1}



     -- ****************************************
     -- acPMSBCInUserDefinedFailures14 TABLE
     -- ****************************************
     AcPMSBCInUserDefinedFailures14Entry ::= SEQUENCE {
       acPMSBCInUserDefinedFailures14Interval          Unsigned32,
       acPMSBCInUserDefinedFailures14Val               Counter32
     }



     acPMSBCInUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures14Entry 1}



     acPMSBCInUserDefinedFailures14Val OBJECT-TYPE
       SYNTAX Counter32
       MAX-ACCESS read-only
       STATUS obsolete
       DESCRIPTION
           "Value of gauge or counter."
       ::= {acPMSBCInUserDefinedFailures14Entry 2}



     -- ****************************************
     -- acPMSBCOutUserDefinedFailures14 table declaration
     -- ****************************************
     acPMSBCOutUserDefinedFailures14Table OBJECT-TYPE
       SYNTAX SEQUENCE OF AcPMSBCOutUserDefinedFailures14Entry
       MAX-ACCESS not-accessible
       STATUS obsolete
       DESCRIPTION
           "Number of user defined Failures 14 for outgoing dialogs (System global)"
       ::= {acPMSBCUserDefinedFailures14 2}



     -- ****************************************
     -- acPMSBCOutUserDefinedFailures14 table entry
     -- ****************************************
     acPMSBCOutUserDefinedFailures14Entry OBJECT-TYPE
       SYNTAX AcPMSBCOutUserDefinedFailures14Entry
       MAX-ACCESS not-accessible
       STATUS obsolete
       DESCRIPTION
           ""
       INDEX {acPMSBCOutUserDefinedFailures14Interval}
       ::= {acPMSBCOutUserDefinedFailures14Table 1}



     -- ****************************************
     -- acPMSBCOutUserDefinedFailures14 TABLE
     -- ****************************************
     AcPMSBCOutUserDefinedFailures14Entry ::= SEQUENCE {
       acPMSBCOutUserDefinedFailures14Interval         Unsigned32,
       acPMSBCOutUserDefinedFailures14Val              Counter32
     }



     acPMSBCOutUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures14Entry 1}



     acPMSBCOutUserDefinedFailures14Val OBJECT-TYPE
       SYNTAX Counter32
       MAX-ACCESS read-only
       STATUS obsolete
       DESCRIPTION
           "Value of gauge or counter."
       ::= {acPMSBCOutUserDefinedFailures14Entry 2}



     -- ****************************************
     -- acPMSBCSRDInUserDefinedFailures14 table declaration
     -- ****************************************
     acPMSBCSRDInUserDefinedFailures14Table OBJECT-TYPE
       SYNTAX SEQUENCE OF AcPMSBCSRDInUserDefinedFailures14Entry
       MAX-ACCESS not-accessible
       STATUS obsolete
       DESCRIPTION
           "Number of user defined Failures 14 for incoming dialogs per SRD"
       ::= {acPMSBCUserDefinedFailures14 3}



     -- ****************************************
     -- acPMSBCSRDInUserDefinedFailures14 table entry
     -- ****************************************
     acPMSBCSRDInUserDefinedFailures14Entry OBJECT-TYPE
       SYNTAX AcPMSBCSRDInUserDefinedFailures14Entry
       MAX-ACCESS not-accessible
       STATUS obsolete
       DESCRIPTION
           ""
       INDEX {acPMSBCSRDInUserDefinedFailures14SrdID,acPMSBCSRDInUserDefinedFailures14Interval}
       ::= {acPMSBCSRDInUserDefinedFailures14Table 1}



     -- ****************************************
     -- acPMSBCSRDInUserDefinedFailures14 TABLE
     -- ****************************************
     AcPMSBCSRDInUserDefinedFailures14Entry ::= SEQUENCE {
       acPMSBCSRDInUserDefinedFailures14SrdID          Unsigned32,
       acPMSBCSRDInUserDefinedFailures14Interval       Unsigned32,
       acPMSBCSRDInUserDefinedFailures14Val            Counter32
     }



     acPMSBCSRDInUserDefinedFailures14SrdID OBJECT-TYPE
       SYNTAX Unsigned32 (0..600)
       MAX-ACCESS not-accessible
       STATUS obsolete
       DESCRIPTION
           "SRD number.
0 is the first SRD."
       ::= {acPMSBCSRDInUserDefinedFailures14Entry 1}



     acPMSBCSRDInUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures14Entry 2}



     acPMSBCSRDInUserDefinedFailures14Val OBJECT-TYPE
       SYNTAX Counter32
       MAX-ACCESS read-only
       STATUS obsolete
       DESCRIPTION
           "Value of gauge or counter."
       ::= {acPMSBCSRDInUserDefinedFailures14Entry 3}



     -- ****************************************
     -- acPMSBCSRDOutUserDefinedFailures14 table declaration
     -- ****************************************
     acPMSBCSRDOutUserDefinedFailures14Table OBJECT-TYPE
       SYNTAX SEQUENCE OF AcPMSBCSRDOutUserDefinedFailures14Entry
       MAX-ACCESS not-accessible
       STATUS obsolete
       DESCRIPTION
           "Number of user defined Failures 14 for outgoing dialogs per SRD"
       ::= {acPMSBCUserDefinedFailures14 4}



     -- ****************************************
     -- acPMSBCSRDOutUserDefinedFailures14 table entry
     -- ****************************************
     acPMSBCSRDOutUserDefinedFailures14Entry OBJECT-TYPE
       SYNTAX AcPMSBCSRDOutUserDefinedFailures14Entry
       MAX-ACCESS not-accessible
       STATUS obsolete
       DESCRIPTION
           ""
       INDEX {acPMSBCSRDOutUserDefinedFailures14SrdID,acPMSBCSRDOutUserDefinedFailures14Interval}
       ::= {acPMSBCSRDOutUserDefinedFailures14Table 1}



     -- ****************************************
     -- acPMSBCSRDOutUserDefinedFailures14 TABLE
     -- ****************************************
     AcPMSBCSRDOutUserDefinedFailures14Entry ::= SEQUENCE {
       acPMSBCSRDOutUserDefinedFailures14SrdID         Unsigned32,
       acPMSBCSRDOutUserDefinedFailures14Interval      Unsigned32,
       acPMSBCSRDOutUserDefinedFailures14Val           Counter32
     }



     acPMSBCSRDOutUserDefinedFailures14SrdID OBJECT-TYPE
       SYNTAX Unsigned32 (0..600)
       MAX-ACCESS not-accessible
       STATUS obsolete
       DESCRIPTION
           "SRD number.
0 is the first SRD."
       ::= {acPMSBCSRDOutUserDefinedFailures14Entry 1}



     acPMSBCSRDOutUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures14Entry 2}



     acPMSBCSRDOutUserDefinedFailures14Val OBJECT-TYPE
       SYNTAX Counter32
       MAX-ACCESS read-only
       STATUS obsolete
       DESCRIPTION
           "Value of gauge or counter."
       ::= {acPMSBCSRDOutUserDefinedFailures14Entry 3}



     -- ****************************************
     -- acPMSBCIPGroupInUserDefinedFailures14 table declaration
     -- ****************************************
     acPMSBCIPGroupInUserDefinedFailures14Table OBJECT-TYPE
       SYNTAX SEQUENCE OF AcPMSBCIPGroupInUserDefinedFailures14Entry
       MAX-ACCESS not-accessible
       STATUS obsolete
       DESCRIPTION
           "Number of user defined Failures 14 for incoming dialogs per IP Group"
       ::= {acPMSBCUserDefinedFailures14 5}



     -- ****************************************
     -- acPMSBCIPGroupInUserDefinedFailures14 table entry
     -- ****************************************
     acPMSBCIPGroupInUserDefinedFailures14Entry OBJECT-TYPE
       SYNTAX AcPMSBCIPGroupInUserDefinedFailures14Entry
       MAX-ACCESS not-accessible
       STATUS obsolete
       DESCRIPTION
           ""
       INDEX {acPMSBCIPGroupInUserDefinedFailures14IPGroupID,acPMSBCIPGroupInUserDefinedFailures14Interval}
       ::= {acPMSBCIPGroupInUserDefinedFailures14Table 1}



     -- ****************************************
     -- acPMSBCIPGroupInUserDefinedFailures14 TABLE
     -- ****************************************
     AcPMSBCIPGroupInUserDefinedFailures14Entry ::= SEQUENCE {
       acPMSBCIPGroupInUserDefinedFailures14IPGroupID  Unsigned32,
       acPMSBCIPGroupInUserDefinedFailures14Interval   Unsigned32,
       acPMSBCIPGroupInUserDefinedFailures14Val        Counter32
     }



     acPMSBCIPGroupInUserDefinedFailures14IPGroupID OBJECT-TYPE
       SYNTAX Unsigned32 (0..5000)
       MAX-ACCESS not-accessible
       STATUS obsolete
       DESCRIPTION
           "IP Group number."
       ::= {acPMSBCIPGroupInUserDefinedFailures14Entry 1}



     acPMSBCIPGroupInUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures14Entry 2}



     acPMSBCIPGroupInUserDefinedFailures14Val OBJECT-TYPE
       SYNTAX Counter32
       MAX-ACCESS read-only
       STATUS obsolete
       DESCRIPTION
           "Value of gauge or counter."
       ::= {acPMSBCIPGroupInUserDefinedFailures14Entry 3}



     -- ****************************************
     -- acPMSBCIPGroupOutUserDefinedFailures14 table declaration
     -- ****************************************
     acPMSBCIPGroupOutUserDefinedFailures14Table OBJECT-TYPE
       SYNTAX SEQUENCE OF AcPMSBCIPGroupOutUserDefinedFailures14Entry
       MAX-ACCESS not-accessible
       STATUS obsolete
       DESCRIPTION
           "Number of user defined Failures 14 for outgoing dialogs per IP Group"
       ::= {acPMSBCUserDefinedFailures14 6}



     -- ****************************************
     -- acPMSBCIPGroupOutUserDefinedFailures14 table entry
     -- ****************************************
     acPMSBCIPGroupOutUserDefinedFailures14Entry OBJECT-TYPE
       SYNTAX AcPMSBCIPGroupOutUserDefinedFailures14Entry
       MAX-ACCESS not-accessible
       STATUS obsolete
       DESCRIPTION
           ""
       INDEX {acPMSBCIPGroupOutUserDefinedFailures14IPGroupID,acPMSBCIPGroupOutUserDefinedFailures14Interval}
       ::= {acPMSBCIPGroupOutUserDefinedFailures14Table 1}



     -- ****************************************
     -- acPMSBCIPGroupOutUserDefinedFailures14 TABLE
     -- ****************************************
     AcPMSBCIPGroupOutUserDefinedFailures14Entry ::= SEQUENCE {
       acPMSBCIPGroupOutUserDefinedFailures14IPGroupID Unsigned32,
       acPMSBCIPGroupOutUserDefinedFailures14Interval  Unsigned32,
       acPMSBCIPGroupOutUserDefinedFailures14Val       Counter32
     }



     acPMSBCIPGroupOutUserDefinedFailures14IPGroupID OBJECT-TYPE
       SYNTAX Unsigned32 (0..5000)
       MAX-ACCESS not-accessible
       STATUS obsolete
       DESCRIPTION
           "IP Group number."
       ::= {acPMSBCIPGroupOutUserDefinedFailures14Entry 1}



     acPMSBCIPGroupOutUserDefinedFailures14Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures14Entry 2}



     acPMSBCIPGroupOutUserDefinedFailures14Val OBJECT-TYPE
       SYNTAX Counter32
       MAX-ACCESS read-only
       STATUS obsolete
       DESCRIPTION
           "Value of gauge or counter."
       ::= {acPMSBCIPGroupOutUserDefinedFailures14Entry 3}



     acPMSBCUserDefinedFailures15 OBJECT IDENTIFIER ::= {acPMSBCUserDefinedFailuresPMs 15}


     -- ****************************************
     -- acPMSBCInUserDefinedFailures15 table declaration
     -- ****************************************
     acPMSBCInUserDefinedFailures15Table OBJECT-TYPE
       SYNTAX SEQUENCE OF AcPMSBCInUserDefinedFailures15Entry
       MAX-ACCESS not-accessible
       STATUS obsolete
       DESCRIPTION
           "Number of user defined failures 15 for incoming dialogs (System global)"
       ::= {acPMSBCUserDefinedFailures15 1}



     -- ****************************************
     -- acPMSBCInUserDefinedFailures15 table entry
     -- ****************************************
     acPMSBCInUserDefinedFailures15Entry OBJECT-TYPE
       SYNTAX AcPMSBCInUserDefinedFailures15Entry
       MAX-ACCESS not-accessible
       STATUS obsolete
       DESCRIPTION
           ""
       INDEX {acPMSBCInUserDefinedFailures15Interval}
       ::= {acPMSBCInUserDefinedFailures15Table 1}



     -- ****************************************
     -- acPMSBCInUserDefinedFailures15 TABLE
     -- ****************************************
     AcPMSBCInUserDefinedFailures15Entry ::= SEQUENCE {
       acPMSBCInUserDefinedFailures15Interval          Unsigned32,
       acPMSBCInUserDefinedFailures15Val               Counter32
     }



     acPMSBCInUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures15Entry 1}



     acPMSBCInUserDefinedFailures15Val OBJECT-TYPE
       SYNTAX Counter32
       MAX-ACCESS read-only
       STATUS obsolete
       DESCRIPTION
           "Value of gauge or counter."
       ::= {acPMSBCInUserDefinedFailures15Entry 2}



     -- ****************************************
     -- acPMSBCOutUserDefinedFailures15 table declaration
     -- ****************************************
     acPMSBCOutUserDefinedFailures15Table OBJECT-TYPE
       SYNTAX SEQUENCE OF AcPMSBCOutUserDefinedFailures15Entry
       MAX-ACCESS not-accessible
       STATUS obsolete
       DESCRIPTION
           "Number of user defined Failures 15 for outgoing dialogs (System global)"
       ::= {acPMSBCUserDefinedFailures15 2}



     -- ****************************************
     -- acPMSBCOutUserDefinedFailures15 table entry
     -- ****************************************
     acPMSBCOutUserDefinedFailures15Entry OBJECT-TYPE
       SYNTAX AcPMSBCOutUserDefinedFailures15Entry
       MAX-ACCESS not-accessible
       STATUS obsolete
       DESCRIPTION
           ""
       INDEX {acPMSBCOutUserDefinedFailures15Interval}
       ::= {acPMSBCOutUserDefinedFailures15Table 1}



     -- ****************************************
     -- acPMSBCOutUserDefinedFailures15 TABLE
     -- ****************************************
     AcPMSBCOutUserDefinedFailures15Entry ::= SEQUENCE {
       acPMSBCOutUserDefinedFailures15Interval         Unsigned32,
       acPMSBCOutUserDefinedFailures15Val              Counter32
     }



     acPMSBCOutUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures15Entry 1}



     acPMSBCOutUserDefinedFailures15Val OBJECT-TYPE
       SYNTAX Counter32
       MAX-ACCESS read-only
       STATUS obsolete
       DESCRIPTION
           "Value of gauge or counter."
       ::= {acPMSBCOutUserDefinedFailures15Entry 2}



     -- ****************************************
     -- acPMSBCSRDInUserDefinedFailures15 table declaration
     -- ****************************************
     acPMSBCSRDInUserDefinedFailures15Table OBJECT-TYPE
       SYNTAX SEQUENCE OF AcPMSBCSRDInUserDefinedFailures15Entry
       MAX-ACCESS not-accessible
       STATUS obsolete
       DESCRIPTION
           "Number of user defined Failures 15 for incoming dialogs per SRD"
       ::= {acPMSBCUserDefinedFailures15 3}



     -- ****************************************
     -- acPMSBCSRDInUserDefinedFailures15 table entry
     -- ****************************************
     acPMSBCSRDInUserDefinedFailures15Entry OBJECT-TYPE
       SYNTAX AcPMSBCSRDInUserDefinedFailures15Entry
       MAX-ACCESS not-accessible
       STATUS obsolete
       DESCRIPTION
           ""
       INDEX {acPMSBCSRDInUserDefinedFailures15SrdID,acPMSBCSRDInUserDefinedFailures15Interval}
       ::= {acPMSBCSRDInUserDefinedFailures15Table 1}



     -- ****************************************
     -- acPMSBCSRDInUserDefinedFailures15 TABLE
     -- ****************************************
     AcPMSBCSRDInUserDefinedFailures15Entry ::= SEQUENCE {
       acPMSBCSRDInUserDefinedFailures15SrdID          Unsigned32,
       acPMSBCSRDInUserDefinedFailures15Interval       Unsigned32,
       acPMSBCSRDInUserDefinedFailures15Val            Counter32
     }



     acPMSBCSRDInUserDefinedFailures15SrdID OBJECT-TYPE
       SYNTAX Unsigned32 (0..600)
       MAX-ACCESS not-accessible
       STATUS obsolete
       DESCRIPTION
           "SRD number.
0 is the first SRD."
       ::= {acPMSBCSRDInUserDefinedFailures15Entry 1}



     acPMSBCSRDInUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures15Entry 2}



     acPMSBCSRDInUserDefinedFailures15Val OBJECT-TYPE
       SYNTAX Counter32
       MAX-ACCESS read-only
       STATUS obsolete
       DESCRIPTION
           "Value of gauge or counter."
       ::= {acPMSBCSRDInUserDefinedFailures15Entry 3}



     -- ****************************************
     -- acPMSBCSRDOutUserDefinedFailures15 table declaration
     -- ****************************************
     acPMSBCSRDOutUserDefinedFailures15Table OBJECT-TYPE
       SYNTAX SEQUENCE OF AcPMSBCSRDOutUserDefinedFailures15Entry
       MAX-ACCESS not-accessible
       STATUS obsolete
       DESCRIPTION
           "Number of user defined Failures 15 for outgoing dialogs per SRD"
       ::= {acPMSBCUserDefinedFailures15 4}



     -- ****************************************
     -- acPMSBCSRDOutUserDefinedFailures15 table entry
     -- ****************************************
     acPMSBCSRDOutUserDefinedFailures15Entry OBJECT-TYPE
       SYNTAX AcPMSBCSRDOutUserDefinedFailures15Entry
       MAX-ACCESS not-accessible
       STATUS obsolete
       DESCRIPTION
           ""
       INDEX {acPMSBCSRDOutUserDefinedFailures15SrdID,acPMSBCSRDOutUserDefinedFailures15Interval}
       ::= {acPMSBCSRDOutUserDefinedFailures15Table 1}



     -- ****************************************
     -- acPMSBCSRDOutUserDefinedFailures15 TABLE
     -- ****************************************
     AcPMSBCSRDOutUserDefinedFailures15Entry ::= SEQUENCE {
       acPMSBCSRDOutUserDefinedFailures15SrdID         Unsigned32,
       acPMSBCSRDOutUserDefinedFailures15Interval      Unsigned32,
       acPMSBCSRDOutUserDefinedFailures15Val           Counter32
     }



     acPMSBCSRDOutUserDefinedFailures15SrdID OBJECT-TYPE
       SYNTAX Unsigned32 (0..600)
       MAX-ACCESS not-accessible
       STATUS obsolete
       DESCRIPTION
           "SRD number.
0 is the first SRD."
       ::= {acPMSBCSRDOutUserDefinedFailures15Entry 1}



     acPMSBCSRDOutUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures15Entry 2}



     acPMSBCSRDOutUserDefinedFailures15Val OBJECT-TYPE
       SYNTAX Counter32
       MAX-ACCESS read-only
       STATUS obsolete
       DESCRIPTION
           "Value of gauge or counter."
       ::= {acPMSBCSRDOutUserDefinedFailures15Entry 3}



     -- ****************************************
     -- acPMSBCIPGroupInUserDefinedFailures15 table declaration
     -- ****************************************
     acPMSBCIPGroupInUserDefinedFailures15Table OBJECT-TYPE
       SYNTAX SEQUENCE OF AcPMSBCIPGroupInUserDefinedFailures15Entry
       MAX-ACCESS not-accessible
       STATUS obsolete
       DESCRIPTION
           "Number of user defined Failures 15 for incoming dialogs per IP Group"
       ::= {acPMSBCUserDefinedFailures15 5}



     -- ****************************************
     -- acPMSBCIPGroupInUserDefinedFailures15 table entry
     -- ****************************************
     acPMSBCIPGroupInUserDefinedFailures15Entry OBJECT-TYPE
       SYNTAX AcPMSBCIPGroupInUserDefinedFailures15Entry
       MAX-ACCESS not-accessible
       STATUS obsolete
       DESCRIPTION
           ""
       INDEX {acPMSBCIPGroupInUserDefinedFailures15IPGroupID,acPMSBCIPGroupInUserDefinedFailures15Interval}
       ::= {acPMSBCIPGroupInUserDefinedFailures15Table 1}



     -- ****************************************
     -- acPMSBCIPGroupInUserDefinedFailures15 TABLE
     -- ****************************************
     AcPMSBCIPGroupInUserDefinedFailures15Entry ::= SEQUENCE {
       acPMSBCIPGroupInUserDefinedFailures15IPGroupID  Unsigned32,
       acPMSBCIPGroupInUserDefinedFailures15Interval   Unsigned32,
       acPMSBCIPGroupInUserDefinedFailures15Val        Counter32
     }



     acPMSBCIPGroupInUserDefinedFailures15IPGroupID OBJECT-TYPE
       SYNTAX Unsigned32 (0..5000)
       MAX-ACCESS not-accessible
       STATUS obsolete
       DESCRIPTION
           "IP Group number."
       ::= {acPMSBCIPGroupInUserDefinedFailures15Entry 1}



     acPMSBCIPGroupInUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures15Entry 2}



     acPMSBCIPGroupInUserDefinedFailures15Val OBJECT-TYPE
       SYNTAX Counter32
       MAX-ACCESS read-only
       STATUS obsolete
       DESCRIPTION
           "Value of gauge or counter."
       ::= {acPMSBCIPGroupInUserDefinedFailures15Entry 3}



     -- ****************************************
     -- acPMSBCIPGroupOutUserDefinedFailures15 table declaration
     -- ****************************************
     acPMSBCIPGroupOutUserDefinedFailures15Table OBJECT-TYPE
       SYNTAX SEQUENCE OF AcPMSBCIPGroupOutUserDefinedFailures15Entry
       MAX-ACCESS not-accessible
       STATUS obsolete
       DESCRIPTION
           "Number of user defined Failures 15 for outgoing dialogs per IP Group"
       ::= {acPMSBCUserDefinedFailures15 6}



     -- ****************************************
     -- acPMSBCIPGroupOutUserDefinedFailures15 table entry
     -- ****************************************
     acPMSBCIPGroupOutUserDefinedFailures15Entry OBJECT-TYPE
       SYNTAX AcPMSBCIPGroupOutUserDefinedFailures15Entry
       MAX-ACCESS not-accessible
       STATUS obsolete
       DESCRIPTION
           ""
       INDEX {acPMSBCIPGroupOutUserDefinedFailures15IPGroupID,acPMSBCIPGroupOutUserDefinedFailures15Interval}
       ::= {acPMSBCIPGroupOutUserDefinedFailures15Table 1}



     -- ****************************************
     -- acPMSBCIPGroupOutUserDefinedFailures15 TABLE
     -- ****************************************
     AcPMSBCIPGroupOutUserDefinedFailures15Entry ::= SEQUENCE {
       acPMSBCIPGroupOutUserDefinedFailures15IPGroupID Unsigned32,
       acPMSBCIPGroupOutUserDefinedFailures15Interval  Unsigned32,
       acPMSBCIPGroupOutUserDefinedFailures15Val       Counter32
     }



     acPMSBCIPGroupOutUserDefinedFailures15IPGroupID OBJECT-TYPE
       SYNTAX Unsigned32 (0..5000)
       MAX-ACCESS not-accessible
       STATUS obsolete
       DESCRIPTION
           "IP Group number."
       ::= {acPMSBCIPGroupOutUserDefinedFailures15Entry 1}



     acPMSBCIPGroupOutUserDefinedFailures15Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures15Entry 2}



     acPMSBCIPGroupOutUserDefinedFailures15Val OBJECT-TYPE
       SYNTAX Counter32
       MAX-ACCESS read-only
       STATUS obsolete
       DESCRIPTION
           "Value of gauge or counter."
       ::= {acPMSBCIPGroupOutUserDefinedFailures15Entry 3}



     acPMSBCUserDefinedFailures16 OBJECT IDENTIFIER ::= {acPMSBCUserDefinedFailuresPMs 16}


     -- ****************************************
     -- acPMSBCInUserDefinedFailures16 table declaration
     -- ****************************************
     acPMSBCInUserDefinedFailures16Table OBJECT-TYPE
       SYNTAX SEQUENCE OF AcPMSBCInUserDefinedFailures16Entry
       MAX-ACCESS not-accessible
       STATUS obsolete
       DESCRIPTION
           "Number of user defined failures 16 for incoming dialogs (System global)"
       ::= {acPMSBCUserDefinedFailures16 1}



     -- ****************************************
     -- acPMSBCInUserDefinedFailures16 table entry
     -- ****************************************
     acPMSBCInUserDefinedFailures16Entry OBJECT-TYPE
       SYNTAX AcPMSBCInUserDefinedFailures16Entry
       MAX-ACCESS not-accessible
       STATUS obsolete
       DESCRIPTION
           ""
       INDEX {acPMSBCInUserDefinedFailures16Interval}
       ::= {acPMSBCInUserDefinedFailures16Table 1}



     -- ****************************************
     -- acPMSBCInUserDefinedFailures16 TABLE
     -- ****************************************
     AcPMSBCInUserDefinedFailures16Entry ::= SEQUENCE {
       acPMSBCInUserDefinedFailures16Interval          Unsigned32,
       acPMSBCInUserDefinedFailures16Val               Counter32
     }



     acPMSBCInUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures16Entry 1}



     acPMSBCInUserDefinedFailures16Val OBJECT-TYPE
       SYNTAX Counter32
       MAX-ACCESS read-only
       STATUS obsolete
       DESCRIPTION
           "Value of gauge or counter."
       ::= {acPMSBCInUserDefinedFailures16Entry 2}



     -- ****************************************
     -- acPMSBCOutUserDefinedFailures16 table declaration
     -- ****************************************
     acPMSBCOutUserDefinedFailures16Table OBJECT-TYPE
       SYNTAX SEQUENCE OF AcPMSBCOutUserDefinedFailures16Entry
       MAX-ACCESS not-accessible
       STATUS obsolete
       DESCRIPTION
           "Number of user defined Failures 16 for outgoing dialogs (System global)"
       ::= {acPMSBCUserDefinedFailures16 2}



     -- ****************************************
     -- acPMSBCOutUserDefinedFailures16 table entry
     -- ****************************************
     acPMSBCOutUserDefinedFailures16Entry OBJECT-TYPE
       SYNTAX AcPMSBCOutUserDefinedFailures16Entry
       MAX-ACCESS not-accessible
       STATUS obsolete
       DESCRIPTION
           ""
       INDEX {acPMSBCOutUserDefinedFailures16Interval}
       ::= {acPMSBCOutUserDefinedFailures16Table 1}



     -- ****************************************
     -- acPMSBCOutUserDefinedFailures16 TABLE
     -- ****************************************
     AcPMSBCOutUserDefinedFailures16Entry ::= SEQUENCE {
       acPMSBCOutUserDefinedFailures16Interval         Unsigned32,
       acPMSBCOutUserDefinedFailures16Val              Counter32
     }



     acPMSBCOutUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures16Entry 1}



     acPMSBCOutUserDefinedFailures16Val OBJECT-TYPE
       SYNTAX Counter32
       MAX-ACCESS read-only
       STATUS obsolete
       DESCRIPTION
           "Value of gauge or counter."
       ::= {acPMSBCOutUserDefinedFailures16Entry 2}



     -- ****************************************
     -- acPMSBCSRDInUserDefinedFailures16 table declaration
     -- ****************************************
     acPMSBCSRDInUserDefinedFailures16Table OBJECT-TYPE
       SYNTAX SEQUENCE OF AcPMSBCSRDInUserDefinedFailures16Entry
       MAX-ACCESS not-accessible
       STATUS obsolete
       DESCRIPTION
           "Number of user defined Failures 16 for incoming dialogs per SRD"
       ::= {acPMSBCUserDefinedFailures16 3}



     -- ****************************************
     -- acPMSBCSRDInUserDefinedFailures16 table entry
     -- ****************************************
     acPMSBCSRDInUserDefinedFailures16Entry OBJECT-TYPE
       SYNTAX AcPMSBCSRDInUserDefinedFailures16Entry
       MAX-ACCESS not-accessible
       STATUS obsolete
       DESCRIPTION
           ""
       INDEX {acPMSBCSRDInUserDefinedFailures16SrdID,acPMSBCSRDInUserDefinedFailures16Interval}
       ::= {acPMSBCSRDInUserDefinedFailures16Table 1}



     -- ****************************************
     -- acPMSBCSRDInUserDefinedFailures16 TABLE
     -- ****************************************
     AcPMSBCSRDInUserDefinedFailures16Entry ::= SEQUENCE {
       acPMSBCSRDInUserDefinedFailures16SrdID          Unsigned32,
       acPMSBCSRDInUserDefinedFailures16Interval       Unsigned32,
       acPMSBCSRDInUserDefinedFailures16Val            Counter32
     }



     acPMSBCSRDInUserDefinedFailures16SrdID OBJECT-TYPE
       SYNTAX Unsigned32 (0..600)
       MAX-ACCESS not-accessible
       STATUS obsolete
       DESCRIPTION
           "SRD number.
0 is the first SRD."
       ::= {acPMSBCSRDInUserDefinedFailures16Entry 1}



     acPMSBCSRDInUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures16Entry 2}



     acPMSBCSRDInUserDefinedFailures16Val OBJECT-TYPE
       SYNTAX Counter32
       MAX-ACCESS read-only
       STATUS obsolete
       DESCRIPTION
           "Value of gauge or counter."
       ::= {acPMSBCSRDInUserDefinedFailures16Entry 3}



     -- ****************************************
     -- acPMSBCSRDOutUserDefinedFailures16 table declaration
     -- ****************************************
     acPMSBCSRDOutUserDefinedFailures16Table OBJECT-TYPE
       SYNTAX SEQUENCE OF AcPMSBCSRDOutUserDefinedFailures16Entry
       MAX-ACCESS not-accessible
       STATUS obsolete
       DESCRIPTION
           "Number of user defined Failures 16 for outgoing dialogs per SRD"
       ::= {acPMSBCUserDefinedFailures16 4}



     -- ****************************************
     -- acPMSBCSRDOutUserDefinedFailures16 table entry
     -- ****************************************
     acPMSBCSRDOutUserDefinedFailures16Entry OBJECT-TYPE
       SYNTAX AcPMSBCSRDOutUserDefinedFailures16Entry
       MAX-ACCESS not-accessible
       STATUS obsolete
       DESCRIPTION
           ""
       INDEX {acPMSBCSRDOutUserDefinedFailures16SrdID,acPMSBCSRDOutUserDefinedFailures16Interval}
       ::= {acPMSBCSRDOutUserDefinedFailures16Table 1}



     -- ****************************************
     -- acPMSBCSRDOutUserDefinedFailures16 TABLE
     -- ****************************************
     AcPMSBCSRDOutUserDefinedFailures16Entry ::= SEQUENCE {
       acPMSBCSRDOutUserDefinedFailures16SrdID         Unsigned32,
       acPMSBCSRDOutUserDefinedFailures16Interval      Unsigned32,
       acPMSBCSRDOutUserDefinedFailures16Val           Counter32
     }



     acPMSBCSRDOutUserDefinedFailures16SrdID OBJECT-TYPE
       SYNTAX Unsigned32 (0..600)
       MAX-ACCESS not-accessible
       STATUS obsolete
       DESCRIPTION
           "SRD number.
0 is the first SRD."
       ::= {acPMSBCSRDOutUserDefinedFailures16Entry 1}



     acPMSBCSRDOutUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures16Entry 2}



     acPMSBCSRDOutUserDefinedFailures16Val OBJECT-TYPE
       SYNTAX Counter32
       MAX-ACCESS read-only
       STATUS obsolete
       DESCRIPTION
           "Value of gauge or counter."
       ::= {acPMSBCSRDOutUserDefinedFailures16Entry 3}



     -- ****************************************
     -- acPMSBCIPGroupInUserDefinedFailures16 table declaration
     -- ****************************************
     acPMSBCIPGroupInUserDefinedFailures16Table OBJECT-TYPE
       SYNTAX SEQUENCE OF AcPMSBCIPGroupInUserDefinedFailures16Entry
       MAX-ACCESS not-accessible
       STATUS obsolete
       DESCRIPTION
           "Number of user defined Failures 16 for incoming dialogs per IP Group"
       ::= {acPMSBCUserDefinedFailures16 5}



     -- ****************************************
     -- acPMSBCIPGroupInUserDefinedFailures16 table entry
     -- ****************************************
     acPMSBCIPGroupInUserDefinedFailures16Entry OBJECT-TYPE
       SYNTAX AcPMSBCIPGroupInUserDefinedFailures16Entry
       MAX-ACCESS not-accessible
       STATUS obsolete
       DESCRIPTION
           ""
       INDEX {acPMSBCIPGroupInUserDefinedFailures16IPGroupID,acPMSBCIPGroupInUserDefinedFailures16Interval}
       ::= {acPMSBCIPGroupInUserDefinedFailures16Table 1}



     -- ****************************************
     -- acPMSBCIPGroupInUserDefinedFailures16 TABLE
     -- ****************************************
     AcPMSBCIPGroupInUserDefinedFailures16Entry ::= SEQUENCE {
       acPMSBCIPGroupInUserDefinedFailures16IPGroupID  Unsigned32,
       acPMSBCIPGroupInUserDefinedFailures16Interval   Unsigned32,
       acPMSBCIPGroupInUserDefinedFailures16Val        Counter32
     }



     acPMSBCIPGroupInUserDefinedFailures16IPGroupID OBJECT-TYPE
       SYNTAX Unsigned32 (0..5000)
       MAX-ACCESS not-accessible
       STATUS obsolete
       DESCRIPTION
           "IP Group number."
       ::= {acPMSBCIPGroupInUserDefinedFailures16Entry 1}



     acPMSBCIPGroupInUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures16Entry 2}



     acPMSBCIPGroupInUserDefinedFailures16Val OBJECT-TYPE
       SYNTAX Counter32
       MAX-ACCESS read-only
       STATUS obsolete
       DESCRIPTION
           "Value of gauge or counter."
       ::= {acPMSBCIPGroupInUserDefinedFailures16Entry 3}



     -- ****************************************
     -- acPMSBCIPGroupOutUserDefinedFailures16 table declaration
     -- ****************************************
     acPMSBCIPGroupOutUserDefinedFailures16Table OBJECT-TYPE
       SYNTAX SEQUENCE OF AcPMSBCIPGroupOutUserDefinedFailures16Entry
       MAX-ACCESS not-accessible
       STATUS obsolete
       DESCRIPTION
           "Number of user defined Failures 16 for outgoing dialogs per IP Group"
       ::= {acPMSBCUserDefinedFailures16 6}



     -- ****************************************
     -- acPMSBCIPGroupOutUserDefinedFailures16 table entry
     -- ****************************************
     acPMSBCIPGroupOutUserDefinedFailures16Entry OBJECT-TYPE
       SYNTAX AcPMSBCIPGroupOutUserDefinedFailures16Entry
       MAX-ACCESS not-accessible
       STATUS obsolete
       DESCRIPTION
           ""
       INDEX {acPMSBCIPGroupOutUserDefinedFailures16IPGroupID,acPMSBCIPGroupOutUserDefinedFailures16Interval}
       ::= {acPMSBCIPGroupOutUserDefinedFailures16Table 1}



     -- ****************************************
     -- acPMSBCIPGroupOutUserDefinedFailures16 TABLE
     -- ****************************************
     AcPMSBCIPGroupOutUserDefinedFailures16Entry ::= SEQUENCE {
       acPMSBCIPGroupOutUserDefinedFailures16IPGroupID Unsigned32,
       acPMSBCIPGroupOutUserDefinedFailures16Interval  Unsigned32,
       acPMSBCIPGroupOutUserDefinedFailures16Val       Counter32
     }



     acPMSBCIPGroupOutUserDefinedFailures16IPGroupID OBJECT-TYPE
       SYNTAX Unsigned32 (0..5000)
       MAX-ACCESS not-accessible
       STATUS obsolete
       DESCRIPTION
           "IP Group number."
       ::= {acPMSBCIPGroupOutUserDefinedFailures16Entry 1}



     acPMSBCIPGroupOutUserDefinedFailures16Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures16Entry 2}



     acPMSBCIPGroupOutUserDefinedFailures16Val OBJECT-TYPE
       SYNTAX Counter32
       MAX-ACCESS read-only
       STATUS obsolete
       DESCRIPTION
           "Value of gauge or counter."
       ::= {acPMSBCIPGroupOutUserDefinedFailures16Entry 3}



     acPMSBCUserDefinedFailures17 OBJECT IDENTIFIER ::= {acPMSBCUserDefinedFailuresPMs 17}


     -- ****************************************
     -- acPMSBCInUserDefinedFailures17 table declaration
     -- ****************************************
     acPMSBCInUserDefinedFailures17Table OBJECT-TYPE
       SYNTAX SEQUENCE OF AcPMSBCInUserDefinedFailures17Entry
       MAX-ACCESS not-accessible
       STATUS obsolete
       DESCRIPTION
           "Number of user defined failures 17 for incoming dialogs (System global)"
       ::= {acPMSBCUserDefinedFailures17 1}



     -- ****************************************
     -- acPMSBCInUserDefinedFailures17 table entry
     -- ****************************************
     acPMSBCInUserDefinedFailures17Entry OBJECT-TYPE
       SYNTAX AcPMSBCInUserDefinedFailures17Entry
       MAX-ACCESS not-accessible
       STATUS obsolete
       DESCRIPTION
           ""
       INDEX {acPMSBCInUserDefinedFailures17Interval}
       ::= {acPMSBCInUserDefinedFailures17Table 1}



     -- ****************************************
     -- acPMSBCInUserDefinedFailures17 TABLE
     -- ****************************************
     AcPMSBCInUserDefinedFailures17Entry ::= SEQUENCE {
       acPMSBCInUserDefinedFailures17Interval          Unsigned32,
       acPMSBCInUserDefinedFailures17Val               Counter32
     }



     acPMSBCInUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures17Entry 1}



     acPMSBCInUserDefinedFailures17Val OBJECT-TYPE
       SYNTAX Counter32
       MAX-ACCESS read-only
       STATUS obsolete
       DESCRIPTION
           "Value of gauge or counter."
       ::= {acPMSBCInUserDefinedFailures17Entry 2}



     -- ****************************************
     -- acPMSBCOutUserDefinedFailures17 table declaration
     -- ****************************************
     acPMSBCOutUserDefinedFailures17Table OBJECT-TYPE
       SYNTAX SEQUENCE OF AcPMSBCOutUserDefinedFailures17Entry
       MAX-ACCESS not-accessible
       STATUS obsolete
       DESCRIPTION
           "Number of user defined Failures 17 for outgoing dialogs (System global)"
       ::= {acPMSBCUserDefinedFailures17 2}



     -- ****************************************
     -- acPMSBCOutUserDefinedFailures17 table entry
     -- ****************************************
     acPMSBCOutUserDefinedFailures17Entry OBJECT-TYPE
       SYNTAX AcPMSBCOutUserDefinedFailures17Entry
       MAX-ACCESS not-accessible
       STATUS obsolete
       DESCRIPTION
           ""
       INDEX {acPMSBCOutUserDefinedFailures17Interval}
       ::= {acPMSBCOutUserDefinedFailures17Table 1}



     -- ****************************************
     -- acPMSBCOutUserDefinedFailures17 TABLE
     -- ****************************************
     AcPMSBCOutUserDefinedFailures17Entry ::= SEQUENCE {
       acPMSBCOutUserDefinedFailures17Interval         Unsigned32,
       acPMSBCOutUserDefinedFailures17Val              Counter32
     }



     acPMSBCOutUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures17Entry 1}



     acPMSBCOutUserDefinedFailures17Val OBJECT-TYPE
       SYNTAX Counter32
       MAX-ACCESS read-only
       STATUS obsolete
       DESCRIPTION
           "Value of gauge or counter."
       ::= {acPMSBCOutUserDefinedFailures17Entry 2}



     -- ****************************************
     -- acPMSBCSRDInUserDefinedFailures17 table declaration
     -- ****************************************
     acPMSBCSRDInUserDefinedFailures17Table OBJECT-TYPE
       SYNTAX SEQUENCE OF AcPMSBCSRDInUserDefinedFailures17Entry
       MAX-ACCESS not-accessible
       STATUS obsolete
       DESCRIPTION
           "Number of user defined Failures 17 for incoming dialogs per SRD"
       ::= {acPMSBCUserDefinedFailures17 3}



     -- ****************************************
     -- acPMSBCSRDInUserDefinedFailures17 table entry
     -- ****************************************
     acPMSBCSRDInUserDefinedFailures17Entry OBJECT-TYPE
       SYNTAX AcPMSBCSRDInUserDefinedFailures17Entry
       MAX-ACCESS not-accessible
       STATUS obsolete
       DESCRIPTION
           ""
       INDEX {acPMSBCSRDInUserDefinedFailures17SrdID,acPMSBCSRDInUserDefinedFailures17Interval}
       ::= {acPMSBCSRDInUserDefinedFailures17Table 1}



     -- ****************************************
     -- acPMSBCSRDInUserDefinedFailures17 TABLE
     -- ****************************************
     AcPMSBCSRDInUserDefinedFailures17Entry ::= SEQUENCE {
       acPMSBCSRDInUserDefinedFailures17SrdID          Unsigned32,
       acPMSBCSRDInUserDefinedFailures17Interval       Unsigned32,
       acPMSBCSRDInUserDefinedFailures17Val            Counter32
     }



     acPMSBCSRDInUserDefinedFailures17SrdID OBJECT-TYPE
       SYNTAX Unsigned32 (0..600)
       MAX-ACCESS not-accessible
       STATUS obsolete
       DESCRIPTION
           "SRD number.
0 is the first SRD."
       ::= {acPMSBCSRDInUserDefinedFailures17Entry 1}



     acPMSBCSRDInUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures17Entry 2}



     acPMSBCSRDInUserDefinedFailures17Val OBJECT-TYPE
       SYNTAX Counter32
       MAX-ACCESS read-only
       STATUS obsolete
       DESCRIPTION
           "Value of gauge or counter."
       ::= {acPMSBCSRDInUserDefinedFailures17Entry 3}



     -- ****************************************
     -- acPMSBCSRDOutUserDefinedFailures17 table declaration
     -- ****************************************
     acPMSBCSRDOutUserDefinedFailures17Table OBJECT-TYPE
       SYNTAX SEQUENCE OF AcPMSBCSRDOutUserDefinedFailures17Entry
       MAX-ACCESS not-accessible
       STATUS obsolete
       DESCRIPTION
           "Number of user defined Failures 17 for outgoing dialogs per SRD"
       ::= {acPMSBCUserDefinedFailures17 4}



     -- ****************************************
     -- acPMSBCSRDOutUserDefinedFailures17 table entry
     -- ****************************************
     acPMSBCSRDOutUserDefinedFailures17Entry OBJECT-TYPE
       SYNTAX AcPMSBCSRDOutUserDefinedFailures17Entry
       MAX-ACCESS not-accessible
       STATUS obsolete
       DESCRIPTION
           ""
       INDEX {acPMSBCSRDOutUserDefinedFailures17SrdID,acPMSBCSRDOutUserDefinedFailures17Interval}
       ::= {acPMSBCSRDOutUserDefinedFailures17Table 1}



     -- ****************************************
     -- acPMSBCSRDOutUserDefinedFailures17 TABLE
     -- ****************************************
     AcPMSBCSRDOutUserDefinedFailures17Entry ::= SEQUENCE {
       acPMSBCSRDOutUserDefinedFailures17SrdID         Unsigned32,
       acPMSBCSRDOutUserDefinedFailures17Interval      Unsigned32,
       acPMSBCSRDOutUserDefinedFailures17Val           Counter32
     }



     acPMSBCSRDOutUserDefinedFailures17SrdID OBJECT-TYPE
       SYNTAX Unsigned32 (0..600)
       MAX-ACCESS not-accessible
       STATUS obsolete
       DESCRIPTION
           "SRD number.
0 is the first SRD."
       ::= {acPMSBCSRDOutUserDefinedFailures17Entry 1}



     acPMSBCSRDOutUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures17Entry 2}



     acPMSBCSRDOutUserDefinedFailures17Val OBJECT-TYPE
       SYNTAX Counter32
       MAX-ACCESS read-only
       STATUS obsolete
       DESCRIPTION
           "Value of gauge or counter."
       ::= {acPMSBCSRDOutUserDefinedFailures17Entry 3}



     -- ****************************************
     -- acPMSBCIPGroupInUserDefinedFailures17 table declaration
     -- ****************************************
     acPMSBCIPGroupInUserDefinedFailures17Table OBJECT-TYPE
       SYNTAX SEQUENCE OF AcPMSBCIPGroupInUserDefinedFailures17Entry
       MAX-ACCESS not-accessible
       STATUS obsolete
       DESCRIPTION
           "Number of user defined Failures 17 for incoming dialogs per IP Group"
       ::= {acPMSBCUserDefinedFailures17 5}



     -- ****************************************
     -- acPMSBCIPGroupInUserDefinedFailures17 table entry
     -- ****************************************
     acPMSBCIPGroupInUserDefinedFailures17Entry OBJECT-TYPE
       SYNTAX AcPMSBCIPGroupInUserDefinedFailures17Entry
       MAX-ACCESS not-accessible
       STATUS obsolete
       DESCRIPTION
           ""
       INDEX {acPMSBCIPGroupInUserDefinedFailures17IPGroupID,acPMSBCIPGroupInUserDefinedFailures17Interval}
       ::= {acPMSBCIPGroupInUserDefinedFailures17Table 1}



     -- ****************************************
     -- acPMSBCIPGroupInUserDefinedFailures17 TABLE
     -- ****************************************
     AcPMSBCIPGroupInUserDefinedFailures17Entry ::= SEQUENCE {
       acPMSBCIPGroupInUserDefinedFailures17IPGroupID  Unsigned32,
       acPMSBCIPGroupInUserDefinedFailures17Interval   Unsigned32,
       acPMSBCIPGroupInUserDefinedFailures17Val        Counter32
     }



     acPMSBCIPGroupInUserDefinedFailures17IPGroupID OBJECT-TYPE
       SYNTAX Unsigned32 (0..5000)
       MAX-ACCESS not-accessible
       STATUS obsolete
       DESCRIPTION
           "IP Group number."
       ::= {acPMSBCIPGroupInUserDefinedFailures17Entry 1}



     acPMSBCIPGroupInUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures17Entry 2}



     acPMSBCIPGroupInUserDefinedFailures17Val OBJECT-TYPE
       SYNTAX Counter32
       MAX-ACCESS read-only
       STATUS obsolete
       DESCRIPTION
           "Value of gauge or counter."
       ::= {acPMSBCIPGroupInUserDefinedFailures17Entry 3}



     -- ****************************************
     -- acPMSBCIPGroupOutUserDefinedFailures17 table declaration
     -- ****************************************
     acPMSBCIPGroupOutUserDefinedFailures17Table OBJECT-TYPE
       SYNTAX SEQUENCE OF AcPMSBCIPGroupOutUserDefinedFailures17Entry
       MAX-ACCESS not-accessible
       STATUS obsolete
       DESCRIPTION
           "Number of user defined Failures 17 for outgoing dialogs per IP Group"
       ::= {acPMSBCUserDefinedFailures17 6}



     -- ****************************************
     -- acPMSBCIPGroupOutUserDefinedFailures17 table entry
     -- ****************************************
     acPMSBCIPGroupOutUserDefinedFailures17Entry OBJECT-TYPE
       SYNTAX AcPMSBCIPGroupOutUserDefinedFailures17Entry
       MAX-ACCESS not-accessible
       STATUS obsolete
       DESCRIPTION
           ""
       INDEX {acPMSBCIPGroupOutUserDefinedFailures17IPGroupID,acPMSBCIPGroupOutUserDefinedFailures17Interval}
       ::= {acPMSBCIPGroupOutUserDefinedFailures17Table 1}



     -- ****************************************
     -- acPMSBCIPGroupOutUserDefinedFailures17 TABLE
     -- ****************************************
     AcPMSBCIPGroupOutUserDefinedFailures17Entry ::= SEQUENCE {
       acPMSBCIPGroupOutUserDefinedFailures17IPGroupID Unsigned32,
       acPMSBCIPGroupOutUserDefinedFailures17Interval  Unsigned32,
       acPMSBCIPGroupOutUserDefinedFailures17Val       Counter32
     }



     acPMSBCIPGroupOutUserDefinedFailures17IPGroupID OBJECT-TYPE
       SYNTAX Unsigned32 (0..5000)
       MAX-ACCESS not-accessible
       STATUS obsolete
       DESCRIPTION
           "IP Group number."
       ::= {acPMSBCIPGroupOutUserDefinedFailures17Entry 1}



     acPMSBCIPGroupOutUserDefinedFailures17Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures17Entry 2}



     acPMSBCIPGroupOutUserDefinedFailures17Val OBJECT-TYPE
       SYNTAX Counter32
       MAX-ACCESS read-only
       STATUS obsolete
       DESCRIPTION
           "Value of gauge or counter."
       ::= {acPMSBCIPGroupOutUserDefinedFailures17Entry 3}



     acPMSBCUserDefinedFailures18 OBJECT IDENTIFIER ::= {acPMSBCUserDefinedFailuresPMs 18}


     -- ****************************************
     -- acPMSBCInUserDefinedFailures18 table declaration
     -- ****************************************
     acPMSBCInUserDefinedFailures18Table OBJECT-TYPE
       SYNTAX SEQUENCE OF AcPMSBCInUserDefinedFailures18Entry
       MAX-ACCESS not-accessible
       STATUS obsolete
       DESCRIPTION
           "Number of user defined failures 18 for incoming dialogs (System global)"
       ::= {acPMSBCUserDefinedFailures18 1}



     -- ****************************************
     -- acPMSBCInUserDefinedFailures18 table entry
     -- ****************************************
     acPMSBCInUserDefinedFailures18Entry OBJECT-TYPE
       SYNTAX AcPMSBCInUserDefinedFailures18Entry
       MAX-ACCESS not-accessible
       STATUS obsolete
       DESCRIPTION
           ""
       INDEX {acPMSBCInUserDefinedFailures18Interval}
       ::= {acPMSBCInUserDefinedFailures18Table 1}



     -- ****************************************
     -- acPMSBCInUserDefinedFailures18 TABLE
     -- ****************************************
     AcPMSBCInUserDefinedFailures18Entry ::= SEQUENCE {
       acPMSBCInUserDefinedFailures18Interval          Unsigned32,
       acPMSBCInUserDefinedFailures18Val               Counter32
     }



     acPMSBCInUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures18Entry 1}



     acPMSBCInUserDefinedFailures18Val OBJECT-TYPE
       SYNTAX Counter32
       MAX-ACCESS read-only
       STATUS obsolete
       DESCRIPTION
           "Value of gauge or counter."
       ::= {acPMSBCInUserDefinedFailures18Entry 2}



     -- ****************************************
     -- acPMSBCOutUserDefinedFailures18 table declaration
     -- ****************************************
     acPMSBCOutUserDefinedFailures18Table OBJECT-TYPE
       SYNTAX SEQUENCE OF AcPMSBCOutUserDefinedFailures18Entry
       MAX-ACCESS not-accessible
       STATUS obsolete
       DESCRIPTION
           "Number of user defined Failures 18 for outgoing dialogs (System global)"
       ::= {acPMSBCUserDefinedFailures18 2}



     -- ****************************************
     -- acPMSBCOutUserDefinedFailures18 table entry
     -- ****************************************
     acPMSBCOutUserDefinedFailures18Entry OBJECT-TYPE
       SYNTAX AcPMSBCOutUserDefinedFailures18Entry
       MAX-ACCESS not-accessible
       STATUS obsolete
       DESCRIPTION
           ""
       INDEX {acPMSBCOutUserDefinedFailures18Interval}
       ::= {acPMSBCOutUserDefinedFailures18Table 1}



     -- ****************************************
     -- acPMSBCOutUserDefinedFailures18 TABLE
     -- ****************************************
     AcPMSBCOutUserDefinedFailures18Entry ::= SEQUENCE {
       acPMSBCOutUserDefinedFailures18Interval         Unsigned32,
       acPMSBCOutUserDefinedFailures18Val              Counter32
     }



     acPMSBCOutUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures18Entry 1}



     acPMSBCOutUserDefinedFailures18Val OBJECT-TYPE
       SYNTAX Counter32
       MAX-ACCESS read-only
       STATUS obsolete
       DESCRIPTION
           "Value of gauge or counter."
       ::= {acPMSBCOutUserDefinedFailures18Entry 2}



     -- ****************************************
     -- acPMSBCSRDInUserDefinedFailures18 table declaration
     -- ****************************************
     acPMSBCSRDInUserDefinedFailures18Table OBJECT-TYPE
       SYNTAX SEQUENCE OF AcPMSBCSRDInUserDefinedFailures18Entry
       MAX-ACCESS not-accessible
       STATUS obsolete
       DESCRIPTION
           "Number of user defined Failures 18 for incoming dialogs per SRD"
       ::= {acPMSBCUserDefinedFailures18 3}



     -- ****************************************
     -- acPMSBCSRDInUserDefinedFailures18 table entry
     -- ****************************************
     acPMSBCSRDInUserDefinedFailures18Entry OBJECT-TYPE
       SYNTAX AcPMSBCSRDInUserDefinedFailures18Entry
       MAX-ACCESS not-accessible
       STATUS obsolete
       DESCRIPTION
           ""
       INDEX {acPMSBCSRDInUserDefinedFailures18SrdID,acPMSBCSRDInUserDefinedFailures18Interval}
       ::= {acPMSBCSRDInUserDefinedFailures18Table 1}



     -- ****************************************
     -- acPMSBCSRDInUserDefinedFailures18 TABLE
     -- ****************************************
     AcPMSBCSRDInUserDefinedFailures18Entry ::= SEQUENCE {
       acPMSBCSRDInUserDefinedFailures18SrdID          Unsigned32,
       acPMSBCSRDInUserDefinedFailures18Interval       Unsigned32,
       acPMSBCSRDInUserDefinedFailures18Val            Counter32
     }



     acPMSBCSRDInUserDefinedFailures18SrdID OBJECT-TYPE
       SYNTAX Unsigned32 (0..600)
       MAX-ACCESS not-accessible
       STATUS obsolete
       DESCRIPTION
           "SRD number.
0 is the first SRD."
       ::= {acPMSBCSRDInUserDefinedFailures18Entry 1}



     acPMSBCSRDInUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures18Entry 2}



     acPMSBCSRDInUserDefinedFailures18Val OBJECT-TYPE
       SYNTAX Counter32
       MAX-ACCESS read-only
       STATUS obsolete
       DESCRIPTION
           "Value of gauge or counter."
       ::= {acPMSBCSRDInUserDefinedFailures18Entry 3}



     -- ****************************************
     -- acPMSBCSRDOutUserDefinedFailures18 table declaration
     -- ****************************************
     acPMSBCSRDOutUserDefinedFailures18Table OBJECT-TYPE
       SYNTAX SEQUENCE OF AcPMSBCSRDOutUserDefinedFailures18Entry
       MAX-ACCESS not-accessible
       STATUS obsolete
       DESCRIPTION
           "Number of user defined Failures 18 for outgoing dialogs per SRD"
       ::= {acPMSBCUserDefinedFailures18 4}



     -- ****************************************
     -- acPMSBCSRDOutUserDefinedFailures18 table entry
     -- ****************************************
     acPMSBCSRDOutUserDefinedFailures18Entry OBJECT-TYPE
       SYNTAX AcPMSBCSRDOutUserDefinedFailures18Entry
       MAX-ACCESS not-accessible
       STATUS obsolete
       DESCRIPTION
           ""
       INDEX {acPMSBCSRDOutUserDefinedFailures18SrdID,acPMSBCSRDOutUserDefinedFailures18Interval}
       ::= {acPMSBCSRDOutUserDefinedFailures18Table 1}



     -- ****************************************
     -- acPMSBCSRDOutUserDefinedFailures18 TABLE
     -- ****************************************
     AcPMSBCSRDOutUserDefinedFailures18Entry ::= SEQUENCE {
       acPMSBCSRDOutUserDefinedFailures18SrdID         Unsigned32,
       acPMSBCSRDOutUserDefinedFailures18Interval      Unsigned32,
       acPMSBCSRDOutUserDefinedFailures18Val           Counter32
     }



     acPMSBCSRDOutUserDefinedFailures18SrdID OBJECT-TYPE
       SYNTAX Unsigned32 (0..600)
       MAX-ACCESS not-accessible
       STATUS obsolete
       DESCRIPTION
           "SRD number.
0 is the first SRD."
       ::= {acPMSBCSRDOutUserDefinedFailures18Entry 1}



     acPMSBCSRDOutUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures18Entry 2}



     acPMSBCSRDOutUserDefinedFailures18Val OBJECT-TYPE
       SYNTAX Counter32
       MAX-ACCESS read-only
       STATUS obsolete
       DESCRIPTION
           "Value of gauge or counter."
       ::= {acPMSBCSRDOutUserDefinedFailures18Entry 3}



     -- ****************************************
     -- acPMSBCIPGroupInUserDefinedFailures18 table declaration
     -- ****************************************
     acPMSBCIPGroupInUserDefinedFailures18Table OBJECT-TYPE
       SYNTAX SEQUENCE OF AcPMSBCIPGroupInUserDefinedFailures18Entry
       MAX-ACCESS not-accessible
       STATUS obsolete
       DESCRIPTION
           "Number of user defined Failures 18 for incoming dialogs per IP Group"
       ::= {acPMSBCUserDefinedFailures18 5}



     -- ****************************************
     -- acPMSBCIPGroupInUserDefinedFailures18 table entry
     -- ****************************************
     acPMSBCIPGroupInUserDefinedFailures18Entry OBJECT-TYPE
       SYNTAX AcPMSBCIPGroupInUserDefinedFailures18Entry
       MAX-ACCESS not-accessible
       STATUS obsolete
       DESCRIPTION
           ""
       INDEX {acPMSBCIPGroupInUserDefinedFailures18IPGroupID,acPMSBCIPGroupInUserDefinedFailures18Interval}
       ::= {acPMSBCIPGroupInUserDefinedFailures18Table 1}



     -- ****************************************
     -- acPMSBCIPGroupInUserDefinedFailures18 TABLE
     -- ****************************************
     AcPMSBCIPGroupInUserDefinedFailures18Entry ::= SEQUENCE {
       acPMSBCIPGroupInUserDefinedFailures18IPGroupID  Unsigned32,
       acPMSBCIPGroupInUserDefinedFailures18Interval   Unsigned32,
       acPMSBCIPGroupInUserDefinedFailures18Val        Counter32
     }



     acPMSBCIPGroupInUserDefinedFailures18IPGroupID OBJECT-TYPE
       SYNTAX Unsigned32 (0..5000)
       MAX-ACCESS not-accessible
       STATUS obsolete
       DESCRIPTION
           "IP Group number."
       ::= {acPMSBCIPGroupInUserDefinedFailures18Entry 1}



     acPMSBCIPGroupInUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures18Entry 2}



     acPMSBCIPGroupInUserDefinedFailures18Val OBJECT-TYPE
       SYNTAX Counter32
       MAX-ACCESS read-only
       STATUS obsolete
       DESCRIPTION
           "Value of gauge or counter."
       ::= {acPMSBCIPGroupInUserDefinedFailures18Entry 3}



     -- ****************************************
     -- acPMSBCIPGroupOutUserDefinedFailures18 table declaration
     -- ****************************************
     acPMSBCIPGroupOutUserDefinedFailures18Table OBJECT-TYPE
       SYNTAX SEQUENCE OF AcPMSBCIPGroupOutUserDefinedFailures18Entry
       MAX-ACCESS not-accessible
       STATUS obsolete
       DESCRIPTION
           "Number of user defined Failures 18 for outgoing dialogs per IP Group"
       ::= {acPMSBCUserDefinedFailures18 6}



     -- ****************************************
     -- acPMSBCIPGroupOutUserDefinedFailures18 table entry
     -- ****************************************
     acPMSBCIPGroupOutUserDefinedFailures18Entry OBJECT-TYPE
       SYNTAX AcPMSBCIPGroupOutUserDefinedFailures18Entry
       MAX-ACCESS not-accessible
       STATUS obsolete
       DESCRIPTION
           ""
       INDEX {acPMSBCIPGroupOutUserDefinedFailures18IPGroupID,acPMSBCIPGroupOutUserDefinedFailures18Interval}
       ::= {acPMSBCIPGroupOutUserDefinedFailures18Table 1}



     -- ****************************************
     -- acPMSBCIPGroupOutUserDefinedFailures18 TABLE
     -- ****************************************
     AcPMSBCIPGroupOutUserDefinedFailures18Entry ::= SEQUENCE {
       acPMSBCIPGroupOutUserDefinedFailures18IPGroupID Unsigned32,
       acPMSBCIPGroupOutUserDefinedFailures18Interval  Unsigned32,
       acPMSBCIPGroupOutUserDefinedFailures18Val       Counter32
     }



     acPMSBCIPGroupOutUserDefinedFailures18IPGroupID OBJECT-TYPE
       SYNTAX Unsigned32 (0..5000)
       MAX-ACCESS not-accessible
       STATUS obsolete
       DESCRIPTION
           "IP Group number."
       ::= {acPMSBCIPGroupOutUserDefinedFailures18Entry 1}



     acPMSBCIPGroupOutUserDefinedFailures18Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures18Entry 2}



     acPMSBCIPGroupOutUserDefinedFailures18Val OBJECT-TYPE
       SYNTAX Counter32
       MAX-ACCESS read-only
       STATUS obsolete
       DESCRIPTION
           "Value of gauge or counter."
       ::= {acPMSBCIPGroupOutUserDefinedFailures18Entry 3}



     acPMSBCUserDefinedFailures19 OBJECT IDENTIFIER ::= {acPMSBCUserDefinedFailuresPMs 19}


     -- ****************************************
     -- acPMSBCInUserDefinedFailures19 table declaration
     -- ****************************************
     acPMSBCInUserDefinedFailures19Table OBJECT-TYPE
       SYNTAX SEQUENCE OF AcPMSBCInUserDefinedFailures19Entry
       MAX-ACCESS not-accessible
       STATUS obsolete
       DESCRIPTION
           "Number of user defined failures 19 for incoming dialogs (System global)"
       ::= {acPMSBCUserDefinedFailures19 1}



     -- ****************************************
     -- acPMSBCInUserDefinedFailures19 table entry
     -- ****************************************
     acPMSBCInUserDefinedFailures19Entry OBJECT-TYPE
       SYNTAX AcPMSBCInUserDefinedFailures19Entry
       MAX-ACCESS not-accessible
       STATUS obsolete
       DESCRIPTION
           ""
       INDEX {acPMSBCInUserDefinedFailures19Interval}
       ::= {acPMSBCInUserDefinedFailures19Table 1}



     -- ****************************************
     -- acPMSBCInUserDefinedFailures19 TABLE
     -- ****************************************
     AcPMSBCInUserDefinedFailures19Entry ::= SEQUENCE {
       acPMSBCInUserDefinedFailures19Interval          Unsigned32,
       acPMSBCInUserDefinedFailures19Val               Counter32
     }



     acPMSBCInUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures19Entry 1}



     acPMSBCInUserDefinedFailures19Val OBJECT-TYPE
       SYNTAX Counter32
       MAX-ACCESS read-only
       STATUS obsolete
       DESCRIPTION
           "Value of gauge or counter."
       ::= {acPMSBCInUserDefinedFailures19Entry 2}



     -- ****************************************
     -- acPMSBCOutUserDefinedFailures19 table declaration
     -- ****************************************
     acPMSBCOutUserDefinedFailures19Table OBJECT-TYPE
       SYNTAX SEQUENCE OF AcPMSBCOutUserDefinedFailures19Entry
       MAX-ACCESS not-accessible
       STATUS obsolete
       DESCRIPTION
           "Number of user defined Failures 19 for outgoing dialogs (System global)"
       ::= {acPMSBCUserDefinedFailures19 2}



     -- ****************************************
     -- acPMSBCOutUserDefinedFailures19 table entry
     -- ****************************************
     acPMSBCOutUserDefinedFailures19Entry OBJECT-TYPE
       SYNTAX AcPMSBCOutUserDefinedFailures19Entry
       MAX-ACCESS not-accessible
       STATUS obsolete
       DESCRIPTION
           ""
       INDEX {acPMSBCOutUserDefinedFailures19Interval}
       ::= {acPMSBCOutUserDefinedFailures19Table 1}



     -- ****************************************
     -- acPMSBCOutUserDefinedFailures19 TABLE
     -- ****************************************
     AcPMSBCOutUserDefinedFailures19Entry ::= SEQUENCE {
       acPMSBCOutUserDefinedFailures19Interval         Unsigned32,
       acPMSBCOutUserDefinedFailures19Val              Counter32
     }



     acPMSBCOutUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures19Entry 1}



     acPMSBCOutUserDefinedFailures19Val OBJECT-TYPE
       SYNTAX Counter32
       MAX-ACCESS read-only
       STATUS obsolete
       DESCRIPTION
           "Value of gauge or counter."
       ::= {acPMSBCOutUserDefinedFailures19Entry 2}



     -- ****************************************
     -- acPMSBCSRDInUserDefinedFailures19 table declaration
     -- ****************************************
     acPMSBCSRDInUserDefinedFailures19Table OBJECT-TYPE
       SYNTAX SEQUENCE OF AcPMSBCSRDInUserDefinedFailures19Entry
       MAX-ACCESS not-accessible
       STATUS obsolete
       DESCRIPTION
           "Number of user defined Failures 19 for incoming dialogs per SRD"
       ::= {acPMSBCUserDefinedFailures19 3}



     -- ****************************************
     -- acPMSBCSRDInUserDefinedFailures19 table entry
     -- ****************************************
     acPMSBCSRDInUserDefinedFailures19Entry OBJECT-TYPE
       SYNTAX AcPMSBCSRDInUserDefinedFailures19Entry
       MAX-ACCESS not-accessible
       STATUS obsolete
       DESCRIPTION
           ""
       INDEX {acPMSBCSRDInUserDefinedFailures19SrdID,acPMSBCSRDInUserDefinedFailures19Interval}
       ::= {acPMSBCSRDInUserDefinedFailures19Table 1}



     -- ****************************************
     -- acPMSBCSRDInUserDefinedFailures19 TABLE
     -- ****************************************
     AcPMSBCSRDInUserDefinedFailures19Entry ::= SEQUENCE {
       acPMSBCSRDInUserDefinedFailures19SrdID          Unsigned32,
       acPMSBCSRDInUserDefinedFailures19Interval       Unsigned32,
       acPMSBCSRDInUserDefinedFailures19Val            Counter32
     }



     acPMSBCSRDInUserDefinedFailures19SrdID OBJECT-TYPE
       SYNTAX Unsigned32 (0..600)
       MAX-ACCESS not-accessible
       STATUS obsolete
       DESCRIPTION
           "SRD number.
0 is the first SRD."
       ::= {acPMSBCSRDInUserDefinedFailures19Entry 1}



     acPMSBCSRDInUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures19Entry 2}



     acPMSBCSRDInUserDefinedFailures19Val OBJECT-TYPE
       SYNTAX Counter32
       MAX-ACCESS read-only
       STATUS obsolete
       DESCRIPTION
           "Value of gauge or counter."
       ::= {acPMSBCSRDInUserDefinedFailures19Entry 3}



     -- ****************************************
     -- acPMSBCSRDOutUserDefinedFailures19 table declaration
     -- ****************************************
     acPMSBCSRDOutUserDefinedFailures19Table OBJECT-TYPE
       SYNTAX SEQUENCE OF AcPMSBCSRDOutUserDefinedFailures19Entry
       MAX-ACCESS not-accessible
       STATUS obsolete
       DESCRIPTION
           "Number of user defined Failures 19 for outgoing dialogs per SRD"
       ::= {acPMSBCUserDefinedFailures19 4}



     -- ****************************************
     -- acPMSBCSRDOutUserDefinedFailures19 table entry
     -- ****************************************
     acPMSBCSRDOutUserDefinedFailures19Entry OBJECT-TYPE
       SYNTAX AcPMSBCSRDOutUserDefinedFailures19Entry
       MAX-ACCESS not-accessible
       STATUS obsolete
       DESCRIPTION
           ""
       INDEX {acPMSBCSRDOutUserDefinedFailures19SrdID,acPMSBCSRDOutUserDefinedFailures19Interval}
       ::= {acPMSBCSRDOutUserDefinedFailures19Table 1}



     -- ****************************************
     -- acPMSBCSRDOutUserDefinedFailures19 TABLE
     -- ****************************************
     AcPMSBCSRDOutUserDefinedFailures19Entry ::= SEQUENCE {
       acPMSBCSRDOutUserDefinedFailures19SrdID         Unsigned32,
       acPMSBCSRDOutUserDefinedFailures19Interval      Unsigned32,
       acPMSBCSRDOutUserDefinedFailures19Val           Counter32
     }



     acPMSBCSRDOutUserDefinedFailures19SrdID OBJECT-TYPE
       SYNTAX Unsigned32 (0..600)
       MAX-ACCESS not-accessible
       STATUS obsolete
       DESCRIPTION
           "SRD number.
0 is the first SRD."
       ::= {acPMSBCSRDOutUserDefinedFailures19Entry 1}



     acPMSBCSRDOutUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures19Entry 2}



     acPMSBCSRDOutUserDefinedFailures19Val OBJECT-TYPE
       SYNTAX Counter32
       MAX-ACCESS read-only
       STATUS obsolete
       DESCRIPTION
           "Value of gauge or counter."
       ::= {acPMSBCSRDOutUserDefinedFailures19Entry 3}



     -- ****************************************
     -- acPMSBCIPGroupInUserDefinedFailures19 table declaration
     -- ****************************************
     acPMSBCIPGroupInUserDefinedFailures19Table OBJECT-TYPE
       SYNTAX SEQUENCE OF AcPMSBCIPGroupInUserDefinedFailures19Entry
       MAX-ACCESS not-accessible
       STATUS obsolete
       DESCRIPTION
           "Number of user defined Failures 19 for incoming dialogs per IP Group"
       ::= {acPMSBCUserDefinedFailures19 5}



     -- ****************************************
     -- acPMSBCIPGroupInUserDefinedFailures19 table entry
     -- ****************************************
     acPMSBCIPGroupInUserDefinedFailures19Entry OBJECT-TYPE
       SYNTAX AcPMSBCIPGroupInUserDefinedFailures19Entry
       MAX-ACCESS not-accessible
       STATUS obsolete
       DESCRIPTION
           ""
       INDEX {acPMSBCIPGroupInUserDefinedFailures19IPGroupID,acPMSBCIPGroupInUserDefinedFailures19Interval}
       ::= {acPMSBCIPGroupInUserDefinedFailures19Table 1}



     -- ****************************************
     -- acPMSBCIPGroupInUserDefinedFailures19 TABLE
     -- ****************************************
     AcPMSBCIPGroupInUserDefinedFailures19Entry ::= SEQUENCE {
       acPMSBCIPGroupInUserDefinedFailures19IPGroupID  Unsigned32,
       acPMSBCIPGroupInUserDefinedFailures19Interval   Unsigned32,
       acPMSBCIPGroupInUserDefinedFailures19Val        Counter32
     }



     acPMSBCIPGroupInUserDefinedFailures19IPGroupID OBJECT-TYPE
       SYNTAX Unsigned32 (0..5000)
       MAX-ACCESS not-accessible
       STATUS obsolete
       DESCRIPTION
           "IP Group number."
       ::= {acPMSBCIPGroupInUserDefinedFailures19Entry 1}



     acPMSBCIPGroupInUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures19Entry 2}



     acPMSBCIPGroupInUserDefinedFailures19Val OBJECT-TYPE
       SYNTAX Counter32
       MAX-ACCESS read-only
       STATUS obsolete
       DESCRIPTION
           "Value of gauge or counter."
       ::= {acPMSBCIPGroupInUserDefinedFailures19Entry 3}



     -- ****************************************
     -- acPMSBCIPGroupOutUserDefinedFailures19 table declaration
     -- ****************************************
     acPMSBCIPGroupOutUserDefinedFailures19Table OBJECT-TYPE
       SYNTAX SEQUENCE OF AcPMSBCIPGroupOutUserDefinedFailures19Entry
       MAX-ACCESS not-accessible
       STATUS obsolete
       DESCRIPTION
           "Number of user defined Failures 19 for outgoing dialogs per IP Group"
       ::= {acPMSBCUserDefinedFailures19 6}



     -- ****************************************
     -- acPMSBCIPGroupOutUserDefinedFailures19 table entry
     -- ****************************************
     acPMSBCIPGroupOutUserDefinedFailures19Entry OBJECT-TYPE
       SYNTAX AcPMSBCIPGroupOutUserDefinedFailures19Entry
       MAX-ACCESS not-accessible
       STATUS obsolete
       DESCRIPTION
           ""
       INDEX {acPMSBCIPGroupOutUserDefinedFailures19IPGroupID,acPMSBCIPGroupOutUserDefinedFailures19Interval}
       ::= {acPMSBCIPGroupOutUserDefinedFailures19Table 1}



     -- ****************************************
     -- acPMSBCIPGroupOutUserDefinedFailures19 TABLE
     -- ****************************************
     AcPMSBCIPGroupOutUserDefinedFailures19Entry ::= SEQUENCE {
       acPMSBCIPGroupOutUserDefinedFailures19IPGroupID Unsigned32,
       acPMSBCIPGroupOutUserDefinedFailures19Interval  Unsigned32,
       acPMSBCIPGroupOutUserDefinedFailures19Val       Counter32
     }



     acPMSBCIPGroupOutUserDefinedFailures19IPGroupID OBJECT-TYPE
       SYNTAX Unsigned32 (0..5000)
       MAX-ACCESS not-accessible
       STATUS obsolete
       DESCRIPTION
           "IP Group number."
       ::= {acPMSBCIPGroupOutUserDefinedFailures19Entry 1}



     acPMSBCIPGroupOutUserDefinedFailures19Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures19Entry 2}



     acPMSBCIPGroupOutUserDefinedFailures19Val OBJECT-TYPE
       SYNTAX Counter32
       MAX-ACCESS read-only
       STATUS obsolete
       DESCRIPTION
           "Value of gauge or counter."
       ::= {acPMSBCIPGroupOutUserDefinedFailures19Entry 3}



     acPMSBCUserDefinedFailures20 OBJECT IDENTIFIER ::= {acPMSBCUserDefinedFailuresPMs 20}


     -- ****************************************
     -- acPMSBCInUserDefinedFailures20 table declaration
     -- ****************************************
     acPMSBCInUserDefinedFailures20Table OBJECT-TYPE
       SYNTAX SEQUENCE OF AcPMSBCInUserDefinedFailures20Entry
       MAX-ACCESS not-accessible
       STATUS obsolete
       DESCRIPTION
           "Number of user defined failures 20 for incoming dialogs (System global)"
       ::= {acPMSBCUserDefinedFailures20 1}



     -- ****************************************
     -- acPMSBCInUserDefinedFailures20 table entry
     -- ****************************************
     acPMSBCInUserDefinedFailures20Entry OBJECT-TYPE
       SYNTAX AcPMSBCInUserDefinedFailures20Entry
       MAX-ACCESS not-accessible
       STATUS obsolete
       DESCRIPTION
           ""
       INDEX {acPMSBCInUserDefinedFailures20Interval}
       ::= {acPMSBCInUserDefinedFailures20Table 1}



     -- ****************************************
     -- acPMSBCInUserDefinedFailures20 TABLE
     -- ****************************************
     AcPMSBCInUserDefinedFailures20Entry ::= SEQUENCE {
       acPMSBCInUserDefinedFailures20Interval          Unsigned32,
       acPMSBCInUserDefinedFailures20Val               Counter32
     }



     acPMSBCInUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures20Entry 1}



     acPMSBCInUserDefinedFailures20Val OBJECT-TYPE
       SYNTAX Counter32
       MAX-ACCESS read-only
       STATUS obsolete
       DESCRIPTION
           "Value of gauge or counter."
       ::= {acPMSBCInUserDefinedFailures20Entry 2}



     -- ****************************************
     -- acPMSBCOutUserDefinedFailures20 table declaration
     -- ****************************************
     acPMSBCOutUserDefinedFailures20Table OBJECT-TYPE
       SYNTAX SEQUENCE OF AcPMSBCOutUserDefinedFailures20Entry
       MAX-ACCESS not-accessible
       STATUS obsolete
       DESCRIPTION
           "Number of user defined Failures 20 for outgoing dialogs (System global)"
       ::= {acPMSBCUserDefinedFailures20 2}



     -- ****************************************
     -- acPMSBCOutUserDefinedFailures20 table entry
     -- ****************************************
     acPMSBCOutUserDefinedFailures20Entry OBJECT-TYPE
       SYNTAX AcPMSBCOutUserDefinedFailures20Entry
       MAX-ACCESS not-accessible
       STATUS obsolete
       DESCRIPTION
           ""
       INDEX {acPMSBCOutUserDefinedFailures20Interval}
       ::= {acPMSBCOutUserDefinedFailures20Table 1}



     -- ****************************************
     -- acPMSBCOutUserDefinedFailures20 TABLE
     -- ****************************************
     AcPMSBCOutUserDefinedFailures20Entry ::= SEQUENCE {
       acPMSBCOutUserDefinedFailures20Interval         Unsigned32,
       acPMSBCOutUserDefinedFailures20Val              Counter32
     }



     acPMSBCOutUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures20Entry 1}



     acPMSBCOutUserDefinedFailures20Val OBJECT-TYPE
       SYNTAX Counter32
       MAX-ACCESS read-only
       STATUS obsolete
       DESCRIPTION
           "Value of gauge or counter."
       ::= {acPMSBCOutUserDefinedFailures20Entry 2}



     -- ****************************************
     -- acPMSBCSRDInUserDefinedFailures20 table declaration
     -- ****************************************
     acPMSBCSRDInUserDefinedFailures20Table OBJECT-TYPE
       SYNTAX SEQUENCE OF AcPMSBCSRDInUserDefinedFailures20Entry
       MAX-ACCESS not-accessible
       STATUS obsolete
       DESCRIPTION
           "Number of user defined Failures 20 for incoming dialogs per SRD"
       ::= {acPMSBCUserDefinedFailures20 3}



     -- ****************************************
     -- acPMSBCSRDInUserDefinedFailures20 table entry
     -- ****************************************
     acPMSBCSRDInUserDefinedFailures20Entry OBJECT-TYPE
       SYNTAX AcPMSBCSRDInUserDefinedFailures20Entry
       MAX-ACCESS not-accessible
       STATUS obsolete
       DESCRIPTION
           ""
       INDEX {acPMSBCSRDInUserDefinedFailures20SrdID,acPMSBCSRDInUserDefinedFailures20Interval}
       ::= {acPMSBCSRDInUserDefinedFailures20Table 1}



     -- ****************************************
     -- acPMSBCSRDInUserDefinedFailures20 TABLE
     -- ****************************************
     AcPMSBCSRDInUserDefinedFailures20Entry ::= SEQUENCE {
       acPMSBCSRDInUserDefinedFailures20SrdID          Unsigned32,
       acPMSBCSRDInUserDefinedFailures20Interval       Unsigned32,
       acPMSBCSRDInUserDefinedFailures20Val            Counter32
     }



     acPMSBCSRDInUserDefinedFailures20SrdID OBJECT-TYPE
       SYNTAX Unsigned32 (0..600)
       MAX-ACCESS not-accessible
       STATUS obsolete
       DESCRIPTION
           "SRD number.
0 is the first SRD."
       ::= {acPMSBCSRDInUserDefinedFailures20Entry 1}



     acPMSBCSRDInUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures20Entry 2}



     acPMSBCSRDInUserDefinedFailures20Val OBJECT-TYPE
       SYNTAX Counter32
       MAX-ACCESS read-only
       STATUS obsolete
       DESCRIPTION
           "Value of gauge or counter."
       ::= {acPMSBCSRDInUserDefinedFailures20Entry 3}



     -- ****************************************
     -- acPMSBCSRDOutUserDefinedFailures20 table declaration
     -- ****************************************
     acPMSBCSRDOutUserDefinedFailures20Table OBJECT-TYPE
       SYNTAX SEQUENCE OF AcPMSBCSRDOutUserDefinedFailures20Entry
       MAX-ACCESS not-accessible
       STATUS obsolete
       DESCRIPTION
           "Number of user defined Failures 20 for outgoing dialogs per SRD"
       ::= {acPMSBCUserDefinedFailures20 4}



     -- ****************************************
     -- acPMSBCSRDOutUserDefinedFailures20 table entry
     -- ****************************************
     acPMSBCSRDOutUserDefinedFailures20Entry OBJECT-TYPE
       SYNTAX AcPMSBCSRDOutUserDefinedFailures20Entry
       MAX-ACCESS not-accessible
       STATUS obsolete
       DESCRIPTION
           ""
       INDEX {acPMSBCSRDOutUserDefinedFailures20SrdID,acPMSBCSRDOutUserDefinedFailures20Interval}
       ::= {acPMSBCSRDOutUserDefinedFailures20Table 1}



     -- ****************************************
     -- acPMSBCSRDOutUserDefinedFailures20 TABLE
     -- ****************************************
     AcPMSBCSRDOutUserDefinedFailures20Entry ::= SEQUENCE {
       acPMSBCSRDOutUserDefinedFailures20SrdID         Unsigned32,
       acPMSBCSRDOutUserDefinedFailures20Interval      Unsigned32,
       acPMSBCSRDOutUserDefinedFailures20Val           Counter32
     }



     acPMSBCSRDOutUserDefinedFailures20SrdID OBJECT-TYPE
       SYNTAX Unsigned32 (0..600)
       MAX-ACCESS not-accessible
       STATUS obsolete
       DESCRIPTION
           "SRD number.
0 is the first SRD."
       ::= {acPMSBCSRDOutUserDefinedFailures20Entry 1}



     acPMSBCSRDOutUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures20Entry 2}



     acPMSBCSRDOutUserDefinedFailures20Val OBJECT-TYPE
       SYNTAX Counter32
       MAX-ACCESS read-only
       STATUS obsolete
       DESCRIPTION
           "Value of gauge or counter."
       ::= {acPMSBCSRDOutUserDefinedFailures20Entry 3}



     -- ****************************************
     -- acPMSBCIPGroupInUserDefinedFailures20 table declaration
     -- ****************************************
     acPMSBCIPGroupInUserDefinedFailures20Table OBJECT-TYPE
       SYNTAX SEQUENCE OF AcPMSBCIPGroupInUserDefinedFailures20Entry
       MAX-ACCESS not-accessible
       STATUS obsolete
       DESCRIPTION
           "Number of user defined Failures 20 for incoming dialogs per IP Group"
       ::= {acPMSBCUserDefinedFailures20 5}



     -- ****************************************
     -- acPMSBCIPGroupInUserDefinedFailures20 table entry
     -- ****************************************
     acPMSBCIPGroupInUserDefinedFailures20Entry OBJECT-TYPE
       SYNTAX AcPMSBCIPGroupInUserDefinedFailures20Entry
       MAX-ACCESS not-accessible
       STATUS obsolete
       DESCRIPTION
           ""
       INDEX {acPMSBCIPGroupInUserDefinedFailures20IPGroupID,acPMSBCIPGroupInUserDefinedFailures20Interval}
       ::= {acPMSBCIPGroupInUserDefinedFailures20Table 1}



     -- ****************************************
     -- acPMSBCIPGroupInUserDefinedFailures20 TABLE
     -- ****************************************
     AcPMSBCIPGroupInUserDefinedFailures20Entry ::= SEQUENCE {
       acPMSBCIPGroupInUserDefinedFailures20IPGroupID  Unsigned32,
       acPMSBCIPGroupInUserDefinedFailures20Interval   Unsigned32,
       acPMSBCIPGroupInUserDefinedFailures20Val        Counter32
     }



     acPMSBCIPGroupInUserDefinedFailures20IPGroupID OBJECT-TYPE
       SYNTAX Unsigned32 (0..5000)
       MAX-ACCESS not-accessible
       STATUS obsolete
       DESCRIPTION
           "IP Group number."
       ::= {acPMSBCIPGroupInUserDefinedFailures20Entry 1}



     acPMSBCIPGroupInUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures20Entry 2}



     acPMSBCIPGroupInUserDefinedFailures20Val OBJECT-TYPE
       SYNTAX Counter32
       MAX-ACCESS read-only
       STATUS obsolete
       DESCRIPTION
           "Value of gauge or counter."
       ::= {acPMSBCIPGroupInUserDefinedFailures20Entry 3}



     -- ****************************************
     -- acPMSBCIPGroupOutUserDefinedFailures20 table declaration
     -- ****************************************
     acPMSBCIPGroupOutUserDefinedFailures20Table OBJECT-TYPE
       SYNTAX SEQUENCE OF AcPMSBCIPGroupOutUserDefinedFailures20Entry
       MAX-ACCESS not-accessible
       STATUS obsolete
       DESCRIPTION
           "Number of user defined Failures 20 for outgoing dialogs per IP Group"
       ::= {acPMSBCUserDefinedFailures20 6}



     -- ****************************************
     -- acPMSBCIPGroupOutUserDefinedFailures20 table entry
     -- ****************************************
     acPMSBCIPGroupOutUserDefinedFailures20Entry OBJECT-TYPE
       SYNTAX AcPMSBCIPGroupOutUserDefinedFailures20Entry
       MAX-ACCESS not-accessible
       STATUS obsolete
       DESCRIPTION
           ""
       INDEX {acPMSBCIPGroupOutUserDefinedFailures20IPGroupID,acPMSBCIPGroupOutUserDefinedFailures20Interval}
       ::= {acPMSBCIPGroupOutUserDefinedFailures20Table 1}



     -- ****************************************
     -- acPMSBCIPGroupOutUserDefinedFailures20 TABLE
     -- ****************************************
     AcPMSBCIPGroupOutUserDefinedFailures20Entry ::= SEQUENCE {
       acPMSBCIPGroupOutUserDefinedFailures20IPGroupID Unsigned32,
       acPMSBCIPGroupOutUserDefinedFailures20Interval  Unsigned32,
       acPMSBCIPGroupOutUserDefinedFailures20Val       Counter32
     }



     acPMSBCIPGroupOutUserDefinedFailures20IPGroupID OBJECT-TYPE
       SYNTAX Unsigned32 (0..5000)
       MAX-ACCESS not-accessible
       STATUS obsolete
       DESCRIPTION
           "IP Group number."
       ::= {acPMSBCIPGroupOutUserDefinedFailures20Entry 1}



     acPMSBCIPGroupOutUserDefinedFailures20Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures20Entry 2}



     acPMSBCIPGroupOutUserDefinedFailures20Val OBJECT-TYPE
       SYNTAX Counter32
       MAX-ACCESS read-only
       STATUS obsolete
       DESCRIPTION
           "Value of gauge or counter."
       ::= {acPMSBCIPGroupOutUserDefinedFailures20Entry 3}



     acPMSBCUserDefinedFailures21 OBJECT IDENTIFIER ::= {acPMSBCUserDefinedFailuresPMs 21}


     -- ****************************************
     -- acPMSBCInUserDefinedFailures21 table declaration
     -- ****************************************
     acPMSBCInUserDefinedFailures21Table OBJECT-TYPE
       SYNTAX SEQUENCE OF AcPMSBCInUserDefinedFailures21Entry
       MAX-ACCESS not-accessible
       STATUS obsolete
       DESCRIPTION
           "Number of user defined failures 21 for incoming dialogs (System global)"
       ::= {acPMSBCUserDefinedFailures21 1}



     -- ****************************************
     -- acPMSBCInUserDefinedFailures21 table entry
     -- ****************************************
     acPMSBCInUserDefinedFailures21Entry OBJECT-TYPE
       SYNTAX AcPMSBCInUserDefinedFailures21Entry
       MAX-ACCESS not-accessible
       STATUS obsolete
       DESCRIPTION
           ""
       INDEX {acPMSBCInUserDefinedFailures21Interval}
       ::= {acPMSBCInUserDefinedFailures21Table 1}



     -- ****************************************
     -- acPMSBCInUserDefinedFailures21 TABLE
     -- ****************************************
     AcPMSBCInUserDefinedFailures21Entry ::= SEQUENCE {
       acPMSBCInUserDefinedFailures21Interval          Unsigned32,
       acPMSBCInUserDefinedFailures21Val               Counter32
     }



     acPMSBCInUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures21Entry 1}



     acPMSBCInUserDefinedFailures21Val OBJECT-TYPE
       SYNTAX Counter32
       MAX-ACCESS read-only
       STATUS obsolete
       DESCRIPTION
           "Value of gauge or counter."
       ::= {acPMSBCInUserDefinedFailures21Entry 2}



     -- ****************************************
     -- acPMSBCOutUserDefinedFailures21 table declaration
     -- ****************************************
     acPMSBCOutUserDefinedFailures21Table OBJECT-TYPE
       SYNTAX SEQUENCE OF AcPMSBCOutUserDefinedFailures21Entry
       MAX-ACCESS not-accessible
       STATUS obsolete
       DESCRIPTION
           "Number of user defined Failures 21 for outgoing dialogs (System global)"
       ::= {acPMSBCUserDefinedFailures21 2}



     -- ****************************************
     -- acPMSBCOutUserDefinedFailures21 table entry
     -- ****************************************
     acPMSBCOutUserDefinedFailures21Entry OBJECT-TYPE
       SYNTAX AcPMSBCOutUserDefinedFailures21Entry
       MAX-ACCESS not-accessible
       STATUS obsolete
       DESCRIPTION
           ""
       INDEX {acPMSBCOutUserDefinedFailures21Interval}
       ::= {acPMSBCOutUserDefinedFailures21Table 1}



     -- ****************************************
     -- acPMSBCOutUserDefinedFailures21 TABLE
     -- ****************************************
     AcPMSBCOutUserDefinedFailures21Entry ::= SEQUENCE {
       acPMSBCOutUserDefinedFailures21Interval         Unsigned32,
       acPMSBCOutUserDefinedFailures21Val              Counter32
     }



     acPMSBCOutUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures21Entry 1}



     acPMSBCOutUserDefinedFailures21Val OBJECT-TYPE
       SYNTAX Counter32
       MAX-ACCESS read-only
       STATUS obsolete
       DESCRIPTION
           "Value of gauge or counter."
       ::= {acPMSBCOutUserDefinedFailures21Entry 2}



     -- ****************************************
     -- acPMSBCSRDInUserDefinedFailures21 table declaration
     -- ****************************************
     acPMSBCSRDInUserDefinedFailures21Table OBJECT-TYPE
       SYNTAX SEQUENCE OF AcPMSBCSRDInUserDefinedFailures21Entry
       MAX-ACCESS not-accessible
       STATUS obsolete
       DESCRIPTION
           "Number of user defined Failures 21 for incoming dialogs per SRD"
       ::= {acPMSBCUserDefinedFailures21 3}



     -- ****************************************
     -- acPMSBCSRDInUserDefinedFailures21 table entry
     -- ****************************************
     acPMSBCSRDInUserDefinedFailures21Entry OBJECT-TYPE
       SYNTAX AcPMSBCSRDInUserDefinedFailures21Entry
       MAX-ACCESS not-accessible
       STATUS obsolete
       DESCRIPTION
           ""
       INDEX {acPMSBCSRDInUserDefinedFailures21SrdID,acPMSBCSRDInUserDefinedFailures21Interval}
       ::= {acPMSBCSRDInUserDefinedFailures21Table 1}



     -- ****************************************
     -- acPMSBCSRDInUserDefinedFailures21 TABLE
     -- ****************************************
     AcPMSBCSRDInUserDefinedFailures21Entry ::= SEQUENCE {
       acPMSBCSRDInUserDefinedFailures21SrdID          Unsigned32,
       acPMSBCSRDInUserDefinedFailures21Interval       Unsigned32,
       acPMSBCSRDInUserDefinedFailures21Val            Counter32
     }



     acPMSBCSRDInUserDefinedFailures21SrdID OBJECT-TYPE
       SYNTAX Unsigned32 (0..600)
       MAX-ACCESS not-accessible
       STATUS obsolete
       DESCRIPTION
           "SRD number.
0 is the first SRD."
       ::= {acPMSBCSRDInUserDefinedFailures21Entry 1}



     acPMSBCSRDInUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures21Entry 2}



     acPMSBCSRDInUserDefinedFailures21Val OBJECT-TYPE
       SYNTAX Counter32
       MAX-ACCESS read-only
       STATUS obsolete
       DESCRIPTION
           "Value of gauge or counter."
       ::= {acPMSBCSRDInUserDefinedFailures21Entry 3}



     -- ****************************************
     -- acPMSBCSRDOutUserDefinedFailures21 table declaration
     -- ****************************************
     acPMSBCSRDOutUserDefinedFailures21Table OBJECT-TYPE
       SYNTAX SEQUENCE OF AcPMSBCSRDOutUserDefinedFailures21Entry
       MAX-ACCESS not-accessible
       STATUS obsolete
       DESCRIPTION
           "Number of user defined Failures 21 for outgoing dialogs per SRD"
       ::= {acPMSBCUserDefinedFailures21 4}



     -- ****************************************
     -- acPMSBCSRDOutUserDefinedFailures21 table entry
     -- ****************************************
     acPMSBCSRDOutUserDefinedFailures21Entry OBJECT-TYPE
       SYNTAX AcPMSBCSRDOutUserDefinedFailures21Entry
       MAX-ACCESS not-accessible
       STATUS obsolete
       DESCRIPTION
           ""
       INDEX {acPMSBCSRDOutUserDefinedFailures21SrdID,acPMSBCSRDOutUserDefinedFailures21Interval}
       ::= {acPMSBCSRDOutUserDefinedFailures21Table 1}



     -- ****************************************
     -- acPMSBCSRDOutUserDefinedFailures21 TABLE
     -- ****************************************
     AcPMSBCSRDOutUserDefinedFailures21Entry ::= SEQUENCE {
       acPMSBCSRDOutUserDefinedFailures21SrdID         Unsigned32,
       acPMSBCSRDOutUserDefinedFailures21Interval      Unsigned32,
       acPMSBCSRDOutUserDefinedFailures21Val           Counter32
     }



     acPMSBCSRDOutUserDefinedFailures21SrdID OBJECT-TYPE
       SYNTAX Unsigned32 (0..600)
       MAX-ACCESS not-accessible
       STATUS obsolete
       DESCRIPTION
           "SRD number.
0 is the first SRD."
       ::= {acPMSBCSRDOutUserDefinedFailures21Entry 1}



     acPMSBCSRDOutUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures21Entry 2}



     acPMSBCSRDOutUserDefinedFailures21Val OBJECT-TYPE
       SYNTAX Counter32
       MAX-ACCESS read-only
       STATUS obsolete
       DESCRIPTION
           "Value of gauge or counter."
       ::= {acPMSBCSRDOutUserDefinedFailures21Entry 3}



     -- ****************************************
     -- acPMSBCIPGroupInUserDefinedFailures21 table declaration
     -- ****************************************
     acPMSBCIPGroupInUserDefinedFailures21Table OBJECT-TYPE
       SYNTAX SEQUENCE OF AcPMSBCIPGroupInUserDefinedFailures21Entry
       MAX-ACCESS not-accessible
       STATUS obsolete
       DESCRIPTION
           "Number of user defined Failures 21 for incoming dialogs per IP Group"
       ::= {acPMSBCUserDefinedFailures21 5}



     -- ****************************************
     -- acPMSBCIPGroupInUserDefinedFailures21 table entry
     -- ****************************************
     acPMSBCIPGroupInUserDefinedFailures21Entry OBJECT-TYPE
       SYNTAX AcPMSBCIPGroupInUserDefinedFailures21Entry
       MAX-ACCESS not-accessible
       STATUS obsolete
       DESCRIPTION
           ""
       INDEX {acPMSBCIPGroupInUserDefinedFailures21IPGroupID,acPMSBCIPGroupInUserDefinedFailures21Interval}
       ::= {acPMSBCIPGroupInUserDefinedFailures21Table 1}



     -- ****************************************
     -- acPMSBCIPGroupInUserDefinedFailures21 TABLE
     -- ****************************************
     AcPMSBCIPGroupInUserDefinedFailures21Entry ::= SEQUENCE {
       acPMSBCIPGroupInUserDefinedFailures21IPGroupID  Unsigned32,
       acPMSBCIPGroupInUserDefinedFailures21Interval   Unsigned32,
       acPMSBCIPGroupInUserDefinedFailures21Val        Counter32
     }



     acPMSBCIPGroupInUserDefinedFailures21IPGroupID OBJECT-TYPE
       SYNTAX Unsigned32 (0..5000)
       MAX-ACCESS not-accessible
       STATUS obsolete
       DESCRIPTION
           "IP Group number."
       ::= {acPMSBCIPGroupInUserDefinedFailures21Entry 1}



     acPMSBCIPGroupInUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures21Entry 2}



     acPMSBCIPGroupInUserDefinedFailures21Val OBJECT-TYPE
       SYNTAX Counter32
       MAX-ACCESS read-only
       STATUS obsolete
       DESCRIPTION
           "Value of gauge or counter."
       ::= {acPMSBCIPGroupInUserDefinedFailures21Entry 3}



     -- ****************************************
     -- acPMSBCIPGroupOutUserDefinedFailures21 table declaration
     -- ****************************************
     acPMSBCIPGroupOutUserDefinedFailures21Table OBJECT-TYPE
       SYNTAX SEQUENCE OF AcPMSBCIPGroupOutUserDefinedFailures21Entry
       MAX-ACCESS not-accessible
       STATUS obsolete
       DESCRIPTION
           "Number of user defined Failures 21 for outgoing dialogs per IP Group"
       ::= {acPMSBCUserDefinedFailures21 6}



     -- ****************************************
     -- acPMSBCIPGroupOutUserDefinedFailures21 table entry
     -- ****************************************
     acPMSBCIPGroupOutUserDefinedFailures21Entry OBJECT-TYPE
       SYNTAX AcPMSBCIPGroupOutUserDefinedFailures21Entry
       MAX-ACCESS not-accessible
       STATUS obsolete
       DESCRIPTION
           ""
       INDEX {acPMSBCIPGroupOutUserDefinedFailures21IPGroupID,acPMSBCIPGroupOutUserDefinedFailures21Interval}
       ::= {acPMSBCIPGroupOutUserDefinedFailures21Table 1}



     -- ****************************************
     -- acPMSBCIPGroupOutUserDefinedFailures21 TABLE
     -- ****************************************
     AcPMSBCIPGroupOutUserDefinedFailures21Entry ::= SEQUENCE {
       acPMSBCIPGroupOutUserDefinedFailures21IPGroupID Unsigned32,
       acPMSBCIPGroupOutUserDefinedFailures21Interval  Unsigned32,
       acPMSBCIPGroupOutUserDefinedFailures21Val       Counter32
     }



     acPMSBCIPGroupOutUserDefinedFailures21IPGroupID OBJECT-TYPE
       SYNTAX Unsigned32 (0..5000)
       MAX-ACCESS not-accessible
       STATUS obsolete
       DESCRIPTION
           "IP Group number."
       ::= {acPMSBCIPGroupOutUserDefinedFailures21Entry 1}



     acPMSBCIPGroupOutUserDefinedFailures21Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures21Entry 2}



     acPMSBCIPGroupOutUserDefinedFailures21Val OBJECT-TYPE
       SYNTAX Counter32
       MAX-ACCESS read-only
       STATUS obsolete
       DESCRIPTION
           "Value of gauge or counter."
       ::= {acPMSBCIPGroupOutUserDefinedFailures21Entry 3}



     acPMSBCUserDefinedFailures22 OBJECT IDENTIFIER ::= {acPMSBCUserDefinedFailuresPMs 22}


     -- ****************************************
     -- acPMSBCInUserDefinedFailures22 table declaration
     -- ****************************************
     acPMSBCInUserDefinedFailures22Table OBJECT-TYPE
       SYNTAX SEQUENCE OF AcPMSBCInUserDefinedFailures22Entry
       MAX-ACCESS not-accessible
       STATUS obsolete
       DESCRIPTION
           "Number of user defined failures 22 for incoming dialogs (System global)"
       ::= {acPMSBCUserDefinedFailures22 1}



     -- ****************************************
     -- acPMSBCInUserDefinedFailures22 table entry
     -- ****************************************
     acPMSBCInUserDefinedFailures22Entry OBJECT-TYPE
       SYNTAX AcPMSBCInUserDefinedFailures22Entry
       MAX-ACCESS not-accessible
       STATUS obsolete
       DESCRIPTION
           ""
       INDEX {acPMSBCInUserDefinedFailures22Interval}
       ::= {acPMSBCInUserDefinedFailures22Table 1}



     -- ****************************************
     -- acPMSBCInUserDefinedFailures22 TABLE
     -- ****************************************
     AcPMSBCInUserDefinedFailures22Entry ::= SEQUENCE {
       acPMSBCInUserDefinedFailures22Interval          Unsigned32,
       acPMSBCInUserDefinedFailures22Val               Counter32
     }



     acPMSBCInUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures22Entry 1}



     acPMSBCInUserDefinedFailures22Val OBJECT-TYPE
       SYNTAX Counter32
       MAX-ACCESS read-only
       STATUS obsolete
       DESCRIPTION
           "Value of gauge or counter."
       ::= {acPMSBCInUserDefinedFailures22Entry 2}



     -- ****************************************
     -- acPMSBCOutUserDefinedFailures22 table declaration
     -- ****************************************
     acPMSBCOutUserDefinedFailures22Table OBJECT-TYPE
       SYNTAX SEQUENCE OF AcPMSBCOutUserDefinedFailures22Entry
       MAX-ACCESS not-accessible
       STATUS obsolete
       DESCRIPTION
           "Number of user defined Failures 22 for outgoing dialogs (System global)"
       ::= {acPMSBCUserDefinedFailures22 2}



     -- ****************************************
     -- acPMSBCOutUserDefinedFailures22 table entry
     -- ****************************************
     acPMSBCOutUserDefinedFailures22Entry OBJECT-TYPE
       SYNTAX AcPMSBCOutUserDefinedFailures22Entry
       MAX-ACCESS not-accessible
       STATUS obsolete
       DESCRIPTION
           ""
       INDEX {acPMSBCOutUserDefinedFailures22Interval}
       ::= {acPMSBCOutUserDefinedFailures22Table 1}



     -- ****************************************
     -- acPMSBCOutUserDefinedFailures22 TABLE
     -- ****************************************
     AcPMSBCOutUserDefinedFailures22Entry ::= SEQUENCE {
       acPMSBCOutUserDefinedFailures22Interval         Unsigned32,
       acPMSBCOutUserDefinedFailures22Val              Counter32
     }



     acPMSBCOutUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures22Entry 1}



     acPMSBCOutUserDefinedFailures22Val OBJECT-TYPE
       SYNTAX Counter32
       MAX-ACCESS read-only
       STATUS obsolete
       DESCRIPTION
           "Value of gauge or counter."
       ::= {acPMSBCOutUserDefinedFailures22Entry 2}



     -- ****************************************
     -- acPMSBCSRDInUserDefinedFailures22 table declaration
     -- ****************************************
     acPMSBCSRDInUserDefinedFailures22Table OBJECT-TYPE
       SYNTAX SEQUENCE OF AcPMSBCSRDInUserDefinedFailures22Entry
       MAX-ACCESS not-accessible
       STATUS obsolete
       DESCRIPTION
           "Number of user defined Failures 22 for incoming dialogs per SRD"
       ::= {acPMSBCUserDefinedFailures22 3}



     -- ****************************************
     -- acPMSBCSRDInUserDefinedFailures22 table entry
     -- ****************************************
     acPMSBCSRDInUserDefinedFailures22Entry OBJECT-TYPE
       SYNTAX AcPMSBCSRDInUserDefinedFailures22Entry
       MAX-ACCESS not-accessible
       STATUS obsolete
       DESCRIPTION
           ""
       INDEX {acPMSBCSRDInUserDefinedFailures22SrdID,acPMSBCSRDInUserDefinedFailures22Interval}
       ::= {acPMSBCSRDInUserDefinedFailures22Table 1}



     -- ****************************************
     -- acPMSBCSRDInUserDefinedFailures22 TABLE
     -- ****************************************
     AcPMSBCSRDInUserDefinedFailures22Entry ::= SEQUENCE {
       acPMSBCSRDInUserDefinedFailures22SrdID          Unsigned32,
       acPMSBCSRDInUserDefinedFailures22Interval       Unsigned32,
       acPMSBCSRDInUserDefinedFailures22Val            Counter32
     }



     acPMSBCSRDInUserDefinedFailures22SrdID OBJECT-TYPE
       SYNTAX Unsigned32 (0..600)
       MAX-ACCESS not-accessible
       STATUS obsolete
       DESCRIPTION
           "SRD number.
0 is the first SRD."
       ::= {acPMSBCSRDInUserDefinedFailures22Entry 1}



     acPMSBCSRDInUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures22Entry 2}



     acPMSBCSRDInUserDefinedFailures22Val OBJECT-TYPE
       SYNTAX Counter32
       MAX-ACCESS read-only
       STATUS obsolete
       DESCRIPTION
           "Value of gauge or counter."
       ::= {acPMSBCSRDInUserDefinedFailures22Entry 3}



     -- ****************************************
     -- acPMSBCSRDOutUserDefinedFailures22 table declaration
     -- ****************************************
     acPMSBCSRDOutUserDefinedFailures22Table OBJECT-TYPE
       SYNTAX SEQUENCE OF AcPMSBCSRDOutUserDefinedFailures22Entry
       MAX-ACCESS not-accessible
       STATUS obsolete
       DESCRIPTION
           "Number of user defined Failures 22 for outgoing dialogs per SRD"
       ::= {acPMSBCUserDefinedFailures22 4}



     -- ****************************************
     -- acPMSBCSRDOutUserDefinedFailures22 table entry
     -- ****************************************
     acPMSBCSRDOutUserDefinedFailures22Entry OBJECT-TYPE
       SYNTAX AcPMSBCSRDOutUserDefinedFailures22Entry
       MAX-ACCESS not-accessible
       STATUS obsolete
       DESCRIPTION
           ""
       INDEX {acPMSBCSRDOutUserDefinedFailures22SrdID,acPMSBCSRDOutUserDefinedFailures22Interval}
       ::= {acPMSBCSRDOutUserDefinedFailures22Table 1}



     -- ****************************************
     -- acPMSBCSRDOutUserDefinedFailures22 TABLE
     -- ****************************************
     AcPMSBCSRDOutUserDefinedFailures22Entry ::= SEQUENCE {
       acPMSBCSRDOutUserDefinedFailures22SrdID         Unsigned32,
       acPMSBCSRDOutUserDefinedFailures22Interval      Unsigned32,
       acPMSBCSRDOutUserDefinedFailures22Val           Counter32
     }



     acPMSBCSRDOutUserDefinedFailures22SrdID OBJECT-TYPE
       SYNTAX Unsigned32 (0..600)
       MAX-ACCESS not-accessible
       STATUS obsolete
       DESCRIPTION
           "SRD number.
0 is the first SRD."
       ::= {acPMSBCSRDOutUserDefinedFailures22Entry 1}



     acPMSBCSRDOutUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures22Entry 2}



     acPMSBCSRDOutUserDefinedFailures22Val OBJECT-TYPE
       SYNTAX Counter32
       MAX-ACCESS read-only
       STATUS obsolete
       DESCRIPTION
           "Value of gauge or counter."
       ::= {acPMSBCSRDOutUserDefinedFailures22Entry 3}



     -- ****************************************
     -- acPMSBCIPGroupInUserDefinedFailures22 table declaration
     -- ****************************************
     acPMSBCIPGroupInUserDefinedFailures22Table OBJECT-TYPE
       SYNTAX SEQUENCE OF AcPMSBCIPGroupInUserDefinedFailures22Entry
       MAX-ACCESS not-accessible
       STATUS obsolete
       DESCRIPTION
           "Number of user defined Failures 22 for incoming dialogs per IP Group"
       ::= {acPMSBCUserDefinedFailures22 5}



     -- ****************************************
     -- acPMSBCIPGroupInUserDefinedFailures22 table entry
     -- ****************************************
     acPMSBCIPGroupInUserDefinedFailures22Entry OBJECT-TYPE
       SYNTAX AcPMSBCIPGroupInUserDefinedFailures22Entry
       MAX-ACCESS not-accessible
       STATUS obsolete
       DESCRIPTION
           ""
       INDEX {acPMSBCIPGroupInUserDefinedFailures22IPGroupID,acPMSBCIPGroupInUserDefinedFailures22Interval}
       ::= {acPMSBCIPGroupInUserDefinedFailures22Table 1}



     -- ****************************************
     -- acPMSBCIPGroupInUserDefinedFailures22 TABLE
     -- ****************************************
     AcPMSBCIPGroupInUserDefinedFailures22Entry ::= SEQUENCE {
       acPMSBCIPGroupInUserDefinedFailures22IPGroupID  Unsigned32,
       acPMSBCIPGroupInUserDefinedFailures22Interval   Unsigned32,
       acPMSBCIPGroupInUserDefinedFailures22Val        Counter32
     }



     acPMSBCIPGroupInUserDefinedFailures22IPGroupID OBJECT-TYPE
       SYNTAX Unsigned32 (0..5000)
       MAX-ACCESS not-accessible
       STATUS obsolete
       DESCRIPTION
           "IP Group number."
       ::= {acPMSBCIPGroupInUserDefinedFailures22Entry 1}



     acPMSBCIPGroupInUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures22Entry 2}



     acPMSBCIPGroupInUserDefinedFailures22Val OBJECT-TYPE
       SYNTAX Counter32
       MAX-ACCESS read-only
       STATUS obsolete
       DESCRIPTION
           "Value of gauge or counter."
       ::= {acPMSBCIPGroupInUserDefinedFailures22Entry 3}



     -- ****************************************
     -- acPMSBCIPGroupOutUserDefinedFailures22 table declaration
     -- ****************************************
     acPMSBCIPGroupOutUserDefinedFailures22Table OBJECT-TYPE
       SYNTAX SEQUENCE OF AcPMSBCIPGroupOutUserDefinedFailures22Entry
       MAX-ACCESS not-accessible
       STATUS obsolete
       DESCRIPTION
           "Number of user defined Failures 22 for outgoing dialogs per IP Group"
       ::= {acPMSBCUserDefinedFailures22 6}



     -- ****************************************
     -- acPMSBCIPGroupOutUserDefinedFailures22 table entry
     -- ****************************************
     acPMSBCIPGroupOutUserDefinedFailures22Entry OBJECT-TYPE
       SYNTAX AcPMSBCIPGroupOutUserDefinedFailures22Entry
       MAX-ACCESS not-accessible
       STATUS obsolete
       DESCRIPTION
           ""
       INDEX {acPMSBCIPGroupOutUserDefinedFailures22IPGroupID,acPMSBCIPGroupOutUserDefinedFailures22Interval}
       ::= {acPMSBCIPGroupOutUserDefinedFailures22Table 1}



     -- ****************************************
     -- acPMSBCIPGroupOutUserDefinedFailures22 TABLE
     -- ****************************************
     AcPMSBCIPGroupOutUserDefinedFailures22Entry ::= SEQUENCE {
       acPMSBCIPGroupOutUserDefinedFailures22IPGroupID Unsigned32,
       acPMSBCIPGroupOutUserDefinedFailures22Interval  Unsigned32,
       acPMSBCIPGroupOutUserDefinedFailures22Val       Counter32
     }



     acPMSBCIPGroupOutUserDefinedFailures22IPGroupID OBJECT-TYPE
       SYNTAX Unsigned32 (0..5000)
       MAX-ACCESS not-accessible
       STATUS obsolete
       DESCRIPTION
           "IP Group number."
       ::= {acPMSBCIPGroupOutUserDefinedFailures22Entry 1}



     acPMSBCIPGroupOutUserDefinedFailures22Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures22Entry 2}



     acPMSBCIPGroupOutUserDefinedFailures22Val OBJECT-TYPE
       SYNTAX Counter32
       MAX-ACCESS read-only
       STATUS obsolete
       DESCRIPTION
           "Value of gauge or counter."
       ::= {acPMSBCIPGroupOutUserDefinedFailures22Entry 3}



     acPMSBCUserDefinedFailures23 OBJECT IDENTIFIER ::= {acPMSBCUserDefinedFailuresPMs 23}


     -- ****************************************
     -- acPMSBCInUserDefinedFailures23 table declaration
     -- ****************************************
     acPMSBCInUserDefinedFailures23Table OBJECT-TYPE
       SYNTAX SEQUENCE OF AcPMSBCInUserDefinedFailures23Entry
       MAX-ACCESS not-accessible
       STATUS obsolete
       DESCRIPTION
           "Number of user defined failures 23 for incoming dialogs (System global)"
       ::= {acPMSBCUserDefinedFailures23 1}



     -- ****************************************
     -- acPMSBCInUserDefinedFailures23 table entry
     -- ****************************************
     acPMSBCInUserDefinedFailures23Entry OBJECT-TYPE
       SYNTAX AcPMSBCInUserDefinedFailures23Entry
       MAX-ACCESS not-accessible
       STATUS obsolete
       DESCRIPTION
           ""
       INDEX {acPMSBCInUserDefinedFailures23Interval}
       ::= {acPMSBCInUserDefinedFailures23Table 1}



     -- ****************************************
     -- acPMSBCInUserDefinedFailures23 TABLE
     -- ****************************************
     AcPMSBCInUserDefinedFailures23Entry ::= SEQUENCE {
       acPMSBCInUserDefinedFailures23Interval          Unsigned32,
       acPMSBCInUserDefinedFailures23Val               Counter32
     }



     acPMSBCInUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures23Entry 1}



     acPMSBCInUserDefinedFailures23Val OBJECT-TYPE
       SYNTAX Counter32
       MAX-ACCESS read-only
       STATUS obsolete
       DESCRIPTION
           "Value of gauge or counter."
       ::= {acPMSBCInUserDefinedFailures23Entry 2}



     -- ****************************************
     -- acPMSBCOutUserDefinedFailures23 table declaration
     -- ****************************************
     acPMSBCOutUserDefinedFailures23Table OBJECT-TYPE
       SYNTAX SEQUENCE OF AcPMSBCOutUserDefinedFailures23Entry
       MAX-ACCESS not-accessible
       STATUS obsolete
       DESCRIPTION
           "Number of user defined Failures 23 for outgoing dialogs (System global)"
       ::= {acPMSBCUserDefinedFailures23 2}



     -- ****************************************
     -- acPMSBCOutUserDefinedFailures23 table entry
     -- ****************************************
     acPMSBCOutUserDefinedFailures23Entry OBJECT-TYPE
       SYNTAX AcPMSBCOutUserDefinedFailures23Entry
       MAX-ACCESS not-accessible
       STATUS obsolete
       DESCRIPTION
           ""
       INDEX {acPMSBCOutUserDefinedFailures23Interval}
       ::= {acPMSBCOutUserDefinedFailures23Table 1}



     -- ****************************************
     -- acPMSBCOutUserDefinedFailures23 TABLE
     -- ****************************************
     AcPMSBCOutUserDefinedFailures23Entry ::= SEQUENCE {
       acPMSBCOutUserDefinedFailures23Interval         Unsigned32,
       acPMSBCOutUserDefinedFailures23Val              Counter32
     }



     acPMSBCOutUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures23Entry 1}



     acPMSBCOutUserDefinedFailures23Val OBJECT-TYPE
       SYNTAX Counter32
       MAX-ACCESS read-only
       STATUS obsolete
       DESCRIPTION
           "Value of gauge or counter."
       ::= {acPMSBCOutUserDefinedFailures23Entry 2}



     -- ****************************************
     -- acPMSBCSRDInUserDefinedFailures23 table declaration
     -- ****************************************
     acPMSBCSRDInUserDefinedFailures23Table OBJECT-TYPE
       SYNTAX SEQUENCE OF AcPMSBCSRDInUserDefinedFailures23Entry
       MAX-ACCESS not-accessible
       STATUS obsolete
       DESCRIPTION
           "Number of user defined Failures 23 for incoming dialogs per SRD"
       ::= {acPMSBCUserDefinedFailures23 3}



     -- ****************************************
     -- acPMSBCSRDInUserDefinedFailures23 table entry
     -- ****************************************
     acPMSBCSRDInUserDefinedFailures23Entry OBJECT-TYPE
       SYNTAX AcPMSBCSRDInUserDefinedFailures23Entry
       MAX-ACCESS not-accessible
       STATUS obsolete
       DESCRIPTION
           ""
       INDEX {acPMSBCSRDInUserDefinedFailures23SrdID,acPMSBCSRDInUserDefinedFailures23Interval}
       ::= {acPMSBCSRDInUserDefinedFailures23Table 1}



     -- ****************************************
     -- acPMSBCSRDInUserDefinedFailures23 TABLE
     -- ****************************************
     AcPMSBCSRDInUserDefinedFailures23Entry ::= SEQUENCE {
       acPMSBCSRDInUserDefinedFailures23SrdID          Unsigned32,
       acPMSBCSRDInUserDefinedFailures23Interval       Unsigned32,
       acPMSBCSRDInUserDefinedFailures23Val            Counter32
     }



     acPMSBCSRDInUserDefinedFailures23SrdID OBJECT-TYPE
       SYNTAX Unsigned32 (0..600)
       MAX-ACCESS not-accessible
       STATUS obsolete
       DESCRIPTION
           "SRD number.
0 is the first SRD."
       ::= {acPMSBCSRDInUserDefinedFailures23Entry 1}



     acPMSBCSRDInUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures23Entry 2}



     acPMSBCSRDInUserDefinedFailures23Val OBJECT-TYPE
       SYNTAX Counter32
       MAX-ACCESS read-only
       STATUS obsolete
       DESCRIPTION
           "Value of gauge or counter."
       ::= {acPMSBCSRDInUserDefinedFailures23Entry 3}



     -- ****************************************
     -- acPMSBCSRDOutUserDefinedFailures23 table declaration
     -- ****************************************
     acPMSBCSRDOutUserDefinedFailures23Table OBJECT-TYPE
       SYNTAX SEQUENCE OF AcPMSBCSRDOutUserDefinedFailures23Entry
       MAX-ACCESS not-accessible
       STATUS obsolete
       DESCRIPTION
           "Number of user defined Failures 23 for outgoing dialogs per SRD"
       ::= {acPMSBCUserDefinedFailures23 4}



     -- ****************************************
     -- acPMSBCSRDOutUserDefinedFailures23 table entry
     -- ****************************************
     acPMSBCSRDOutUserDefinedFailures23Entry OBJECT-TYPE
       SYNTAX AcPMSBCSRDOutUserDefinedFailures23Entry
       MAX-ACCESS not-accessible
       STATUS obsolete
       DESCRIPTION
           ""
       INDEX {acPMSBCSRDOutUserDefinedFailures23SrdID,acPMSBCSRDOutUserDefinedFailures23Interval}
       ::= {acPMSBCSRDOutUserDefinedFailures23Table 1}



     -- ****************************************
     -- acPMSBCSRDOutUserDefinedFailures23 TABLE
     -- ****************************************
     AcPMSBCSRDOutUserDefinedFailures23Entry ::= SEQUENCE {
       acPMSBCSRDOutUserDefinedFailures23SrdID         Unsigned32,
       acPMSBCSRDOutUserDefinedFailures23Interval      Unsigned32,
       acPMSBCSRDOutUserDefinedFailures23Val           Counter32
     }



     acPMSBCSRDOutUserDefinedFailures23SrdID OBJECT-TYPE
       SYNTAX Unsigned32 (0..600)
       MAX-ACCESS not-accessible
       STATUS obsolete
       DESCRIPTION
           "SRD number.
0 is the first SRD."
       ::= {acPMSBCSRDOutUserDefinedFailures23Entry 1}



     acPMSBCSRDOutUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures23Entry 2}



     acPMSBCSRDOutUserDefinedFailures23Val OBJECT-TYPE
       SYNTAX Counter32
       MAX-ACCESS read-only
       STATUS obsolete
       DESCRIPTION
           "Value of gauge or counter."
       ::= {acPMSBCSRDOutUserDefinedFailures23Entry 3}



     -- ****************************************
     -- acPMSBCIPGroupInUserDefinedFailures23 table declaration
     -- ****************************************
     acPMSBCIPGroupInUserDefinedFailures23Table OBJECT-TYPE
       SYNTAX SEQUENCE OF AcPMSBCIPGroupInUserDefinedFailures23Entry
       MAX-ACCESS not-accessible
       STATUS obsolete
       DESCRIPTION
           "Number of user defined Failures 23 for incoming dialogs per IP Group"
       ::= {acPMSBCUserDefinedFailures23 5}



     -- ****************************************
     -- acPMSBCIPGroupInUserDefinedFailures23 table entry
     -- ****************************************
     acPMSBCIPGroupInUserDefinedFailures23Entry OBJECT-TYPE
       SYNTAX AcPMSBCIPGroupInUserDefinedFailures23Entry
       MAX-ACCESS not-accessible
       STATUS obsolete
       DESCRIPTION
           ""
       INDEX {acPMSBCIPGroupInUserDefinedFailures23IPGroupID,acPMSBCIPGroupInUserDefinedFailures23Interval}
       ::= {acPMSBCIPGroupInUserDefinedFailures23Table 1}



     -- ****************************************
     -- acPMSBCIPGroupInUserDefinedFailures23 TABLE
     -- ****************************************
     AcPMSBCIPGroupInUserDefinedFailures23Entry ::= SEQUENCE {
       acPMSBCIPGroupInUserDefinedFailures23IPGroupID  Unsigned32,
       acPMSBCIPGroupInUserDefinedFailures23Interval   Unsigned32,
       acPMSBCIPGroupInUserDefinedFailures23Val        Counter32
     }



     acPMSBCIPGroupInUserDefinedFailures23IPGroupID OBJECT-TYPE
       SYNTAX Unsigned32 (0..5000)
       MAX-ACCESS not-accessible
       STATUS obsolete
       DESCRIPTION
           "IP Group number."
       ::= {acPMSBCIPGroupInUserDefinedFailures23Entry 1}



     acPMSBCIPGroupInUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures23Entry 2}



     acPMSBCIPGroupInUserDefinedFailures23Val OBJECT-TYPE
       SYNTAX Counter32
       MAX-ACCESS read-only
       STATUS obsolete
       DESCRIPTION
           "Value of gauge or counter."
       ::= {acPMSBCIPGroupInUserDefinedFailures23Entry 3}



     -- ****************************************
     -- acPMSBCIPGroupOutUserDefinedFailures23 table declaration
     -- ****************************************
     acPMSBCIPGroupOutUserDefinedFailures23Table OBJECT-TYPE
       SYNTAX SEQUENCE OF AcPMSBCIPGroupOutUserDefinedFailures23Entry
       MAX-ACCESS not-accessible
       STATUS obsolete
       DESCRIPTION
           "Number of user defined Failures 23 for outgoing dialogs per IP Group"
       ::= {acPMSBCUserDefinedFailures23 6}



     -- ****************************************
     -- acPMSBCIPGroupOutUserDefinedFailures23 table entry
     -- ****************************************
     acPMSBCIPGroupOutUserDefinedFailures23Entry OBJECT-TYPE
       SYNTAX AcPMSBCIPGroupOutUserDefinedFailures23Entry
       MAX-ACCESS not-accessible
       STATUS obsolete
       DESCRIPTION
           ""
       INDEX {acPMSBCIPGroupOutUserDefinedFailures23IPGroupID,acPMSBCIPGroupOutUserDefinedFailures23Interval}
       ::= {acPMSBCIPGroupOutUserDefinedFailures23Table 1}



     -- ****************************************
     -- acPMSBCIPGroupOutUserDefinedFailures23 TABLE
     -- ****************************************
     AcPMSBCIPGroupOutUserDefinedFailures23Entry ::= SEQUENCE {
       acPMSBCIPGroupOutUserDefinedFailures23IPGroupID Unsigned32,
       acPMSBCIPGroupOutUserDefinedFailures23Interval  Unsigned32,
       acPMSBCIPGroupOutUserDefinedFailures23Val       Counter32
     }



     acPMSBCIPGroupOutUserDefinedFailures23IPGroupID OBJECT-TYPE
       SYNTAX Unsigned32 (0..5000)
       MAX-ACCESS not-accessible
       STATUS obsolete
       DESCRIPTION
           "IP Group number."
       ::= {acPMSBCIPGroupOutUserDefinedFailures23Entry 1}



     acPMSBCIPGroupOutUserDefinedFailures23Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures23Entry 2}



     acPMSBCIPGroupOutUserDefinedFailures23Val OBJECT-TYPE
       SYNTAX Counter32
       MAX-ACCESS read-only
       STATUS obsolete
       DESCRIPTION
           "Value of gauge or counter."
       ::= {acPMSBCIPGroupOutUserDefinedFailures23Entry 3}



     acPMSBCUserDefinedFailures24 OBJECT IDENTIFIER ::= {acPMSBCUserDefinedFailuresPMs 24}


     -- ****************************************
     -- acPMSBCInUserDefinedFailures24 table declaration
     -- ****************************************
     acPMSBCInUserDefinedFailures24Table OBJECT-TYPE
       SYNTAX SEQUENCE OF AcPMSBCInUserDefinedFailures24Entry
       MAX-ACCESS not-accessible
       STATUS obsolete
       DESCRIPTION
           "Number of user defined failures 24 for incoming dialogs (System global)"
       ::= {acPMSBCUserDefinedFailures24 1}



     -- ****************************************
     -- acPMSBCInUserDefinedFailures24 table entry
     -- ****************************************
     acPMSBCInUserDefinedFailures24Entry OBJECT-TYPE
       SYNTAX AcPMSBCInUserDefinedFailures24Entry
       MAX-ACCESS not-accessible
       STATUS obsolete
       DESCRIPTION
           ""
       INDEX {acPMSBCInUserDefinedFailures24Interval}
       ::= {acPMSBCInUserDefinedFailures24Table 1}



     -- ****************************************
     -- acPMSBCInUserDefinedFailures24 TABLE
     -- ****************************************
     AcPMSBCInUserDefinedFailures24Entry ::= SEQUENCE {
       acPMSBCInUserDefinedFailures24Interval          Unsigned32,
       acPMSBCInUserDefinedFailures24Val               Counter32
     }



     acPMSBCInUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures24Entry 1}



     acPMSBCInUserDefinedFailures24Val OBJECT-TYPE
       SYNTAX Counter32
       MAX-ACCESS read-only
       STATUS obsolete
       DESCRIPTION
           "Value of gauge or counter."
       ::= {acPMSBCInUserDefinedFailures24Entry 2}



     -- ****************************************
     -- acPMSBCOutUserDefinedFailures24 table declaration
     -- ****************************************
     acPMSBCOutUserDefinedFailures24Table OBJECT-TYPE
       SYNTAX SEQUENCE OF AcPMSBCOutUserDefinedFailures24Entry
       MAX-ACCESS not-accessible
       STATUS obsolete
       DESCRIPTION
           "Number of user defined Failures 24 for outgoing dialogs (System global)"
       ::= {acPMSBCUserDefinedFailures24 2}



     -- ****************************************
     -- acPMSBCOutUserDefinedFailures24 table entry
     -- ****************************************
     acPMSBCOutUserDefinedFailures24Entry OBJECT-TYPE
       SYNTAX AcPMSBCOutUserDefinedFailures24Entry
       MAX-ACCESS not-accessible
       STATUS obsolete
       DESCRIPTION
           ""
       INDEX {acPMSBCOutUserDefinedFailures24Interval}
       ::= {acPMSBCOutUserDefinedFailures24Table 1}



     -- ****************************************
     -- acPMSBCOutUserDefinedFailures24 TABLE
     -- ****************************************
     AcPMSBCOutUserDefinedFailures24Entry ::= SEQUENCE {
       acPMSBCOutUserDefinedFailures24Interval         Unsigned32,
       acPMSBCOutUserDefinedFailures24Val              Counter32
     }



     acPMSBCOutUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures24Entry 1}



     acPMSBCOutUserDefinedFailures24Val OBJECT-TYPE
       SYNTAX Counter32
       MAX-ACCESS read-only
       STATUS obsolete
       DESCRIPTION
           "Value of gauge or counter."
       ::= {acPMSBCOutUserDefinedFailures24Entry 2}



     -- ****************************************
     -- acPMSBCSRDInUserDefinedFailures24 table declaration
     -- ****************************************
     acPMSBCSRDInUserDefinedFailures24Table OBJECT-TYPE
       SYNTAX SEQUENCE OF AcPMSBCSRDInUserDefinedFailures24Entry
       MAX-ACCESS not-accessible
       STATUS obsolete
       DESCRIPTION
           "Number of user defined Failures 24 for incoming dialogs per SRD"
       ::= {acPMSBCUserDefinedFailures24 3}



     -- ****************************************
     -- acPMSBCSRDInUserDefinedFailures24 table entry
     -- ****************************************
     acPMSBCSRDInUserDefinedFailures24Entry OBJECT-TYPE
       SYNTAX AcPMSBCSRDInUserDefinedFailures24Entry
       MAX-ACCESS not-accessible
       STATUS obsolete
       DESCRIPTION
           ""
       INDEX {acPMSBCSRDInUserDefinedFailures24SrdID,acPMSBCSRDInUserDefinedFailures24Interval}
       ::= {acPMSBCSRDInUserDefinedFailures24Table 1}



     -- ****************************************
     -- acPMSBCSRDInUserDefinedFailures24 TABLE
     -- ****************************************
     AcPMSBCSRDInUserDefinedFailures24Entry ::= SEQUENCE {
       acPMSBCSRDInUserDefinedFailures24SrdID          Unsigned32,
       acPMSBCSRDInUserDefinedFailures24Interval       Unsigned32,
       acPMSBCSRDInUserDefinedFailures24Val            Counter32
     }



     acPMSBCSRDInUserDefinedFailures24SrdID OBJECT-TYPE
       SYNTAX Unsigned32 (0..600)
       MAX-ACCESS not-accessible
       STATUS obsolete
       DESCRIPTION
           "SRD number.
0 is the first SRD."
       ::= {acPMSBCSRDInUserDefinedFailures24Entry 1}



     acPMSBCSRDInUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures24Entry 2}



     acPMSBCSRDInUserDefinedFailures24Val OBJECT-TYPE
       SYNTAX Counter32
       MAX-ACCESS read-only
       STATUS obsolete
       DESCRIPTION
           "Value of gauge or counter."
       ::= {acPMSBCSRDInUserDefinedFailures24Entry 3}



     -- ****************************************
     -- acPMSBCSRDOutUserDefinedFailures24 table declaration
     -- ****************************************
     acPMSBCSRDOutUserDefinedFailures24Table OBJECT-TYPE
       SYNTAX SEQUENCE OF AcPMSBCSRDOutUserDefinedFailures24Entry
       MAX-ACCESS not-accessible
       STATUS obsolete
       DESCRIPTION
           "Number of user defined Failures 24 for outgoing dialogs per SRD"
       ::= {acPMSBCUserDefinedFailures24 4}



     -- ****************************************
     -- acPMSBCSRDOutUserDefinedFailures24 table entry
     -- ****************************************
     acPMSBCSRDOutUserDefinedFailures24Entry OBJECT-TYPE
       SYNTAX AcPMSBCSRDOutUserDefinedFailures24Entry
       MAX-ACCESS not-accessible
       STATUS obsolete
       DESCRIPTION
           ""
       INDEX {acPMSBCSRDOutUserDefinedFailures24SrdID,acPMSBCSRDOutUserDefinedFailures24Interval}
       ::= {acPMSBCSRDOutUserDefinedFailures24Table 1}



     -- ****************************************
     -- acPMSBCSRDOutUserDefinedFailures24 TABLE
     -- ****************************************
     AcPMSBCSRDOutUserDefinedFailures24Entry ::= SEQUENCE {
       acPMSBCSRDOutUserDefinedFailures24SrdID         Unsigned32,
       acPMSBCSRDOutUserDefinedFailures24Interval      Unsigned32,
       acPMSBCSRDOutUserDefinedFailures24Val           Counter32
     }



     acPMSBCSRDOutUserDefinedFailures24SrdID OBJECT-TYPE
       SYNTAX Unsigned32 (0..600)
       MAX-ACCESS not-accessible
       STATUS obsolete
       DESCRIPTION
           "SRD number.
0 is the first SRD."
       ::= {acPMSBCSRDOutUserDefinedFailures24Entry 1}



     acPMSBCSRDOutUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures24Entry 2}



     acPMSBCSRDOutUserDefinedFailures24Val OBJECT-TYPE
       SYNTAX Counter32
       MAX-ACCESS read-only
       STATUS obsolete
       DESCRIPTION
           "Value of gauge or counter."
       ::= {acPMSBCSRDOutUserDefinedFailures24Entry 3}



     -- ****************************************
     -- acPMSBCIPGroupInUserDefinedFailures24 table declaration
     -- ****************************************
     acPMSBCIPGroupInUserDefinedFailures24Table OBJECT-TYPE
       SYNTAX SEQUENCE OF AcPMSBCIPGroupInUserDefinedFailures24Entry
       MAX-ACCESS not-accessible
       STATUS obsolete
       DESCRIPTION
           "Number of user defined Failures 24 for incoming dialogs per IP Group"
       ::= {acPMSBCUserDefinedFailures24 5}



     -- ****************************************
     -- acPMSBCIPGroupInUserDefinedFailures24 table entry
     -- ****************************************
     acPMSBCIPGroupInUserDefinedFailures24Entry OBJECT-TYPE
       SYNTAX AcPMSBCIPGroupInUserDefinedFailures24Entry
       MAX-ACCESS not-accessible
       STATUS obsolete
       DESCRIPTION
           ""
       INDEX {acPMSBCIPGroupInUserDefinedFailures24IPGroupID,acPMSBCIPGroupInUserDefinedFailures24Interval}
       ::= {acPMSBCIPGroupInUserDefinedFailures24Table 1}



     -- ****************************************
     -- acPMSBCIPGroupInUserDefinedFailures24 TABLE
     -- ****************************************
     AcPMSBCIPGroupInUserDefinedFailures24Entry ::= SEQUENCE {
       acPMSBCIPGroupInUserDefinedFailures24IPGroupID  Unsigned32,
       acPMSBCIPGroupInUserDefinedFailures24Interval   Unsigned32,
       acPMSBCIPGroupInUserDefinedFailures24Val        Counter32
     }



     acPMSBCIPGroupInUserDefinedFailures24IPGroupID OBJECT-TYPE
       SYNTAX Unsigned32 (0..5000)
       MAX-ACCESS not-accessible
       STATUS obsolete
       DESCRIPTION
           "IP Group number."
       ::= {acPMSBCIPGroupInUserDefinedFailures24Entry 1}



     acPMSBCIPGroupInUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures24Entry 2}



     acPMSBCIPGroupInUserDefinedFailures24Val OBJECT-TYPE
       SYNTAX Counter32
       MAX-ACCESS read-only
       STATUS obsolete
       DESCRIPTION
           "Value of gauge or counter."
       ::= {acPMSBCIPGroupInUserDefinedFailures24Entry 3}



     -- ****************************************
     -- acPMSBCIPGroupOutUserDefinedFailures24 table declaration
     -- ****************************************
     acPMSBCIPGroupOutUserDefinedFailures24Table OBJECT-TYPE
       SYNTAX SEQUENCE OF AcPMSBCIPGroupOutUserDefinedFailures24Entry
       MAX-ACCESS not-accessible
       STATUS obsolete
       DESCRIPTION
           "Number of user defined Failures 24 for outgoing dialogs per IP Group"
       ::= {acPMSBCUserDefinedFailures24 6}



     -- ****************************************
     -- acPMSBCIPGroupOutUserDefinedFailures24 table entry
     -- ****************************************
     acPMSBCIPGroupOutUserDefinedFailures24Entry OBJECT-TYPE
       SYNTAX AcPMSBCIPGroupOutUserDefinedFailures24Entry
       MAX-ACCESS not-accessible
       STATUS obsolete
       DESCRIPTION
           ""
       INDEX {acPMSBCIPGroupOutUserDefinedFailures24IPGroupID,acPMSBCIPGroupOutUserDefinedFailures24Interval}
       ::= {acPMSBCIPGroupOutUserDefinedFailures24Table 1}



     -- ****************************************
     -- acPMSBCIPGroupOutUserDefinedFailures24 TABLE
     -- ****************************************
     AcPMSBCIPGroupOutUserDefinedFailures24Entry ::= SEQUENCE {
       acPMSBCIPGroupOutUserDefinedFailures24IPGroupID Unsigned32,
       acPMSBCIPGroupOutUserDefinedFailures24Interval  Unsigned32,
       acPMSBCIPGroupOutUserDefinedFailures24Val       Counter32
     }



     acPMSBCIPGroupOutUserDefinedFailures24IPGroupID OBJECT-TYPE
       SYNTAX Unsigned32 (0..5000)
       MAX-ACCESS not-accessible
       STATUS obsolete
       DESCRIPTION
           "IP Group number."
       ::= {acPMSBCIPGroupOutUserDefinedFailures24Entry 1}



     acPMSBCIPGroupOutUserDefinedFailures24Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures24Entry 2}



     acPMSBCIPGroupOutUserDefinedFailures24Val OBJECT-TYPE
       SYNTAX Counter32
       MAX-ACCESS read-only
       STATUS obsolete
       DESCRIPTION
           "Value of gauge or counter."
       ::= {acPMSBCIPGroupOutUserDefinedFailures24Entry 3}



     acPMSBCUserDefinedFailures25 OBJECT IDENTIFIER ::= {acPMSBCUserDefinedFailuresPMs 25}


     -- ****************************************
     -- acPMSBCInUserDefinedFailures25 table declaration
     -- ****************************************
     acPMSBCInUserDefinedFailures25Table OBJECT-TYPE
       SYNTAX SEQUENCE OF AcPMSBCInUserDefinedFailures25Entry
       MAX-ACCESS not-accessible
       STATUS obsolete
       DESCRIPTION
           "Number of user defined failures 25 for incoming dialogs (System global)"
       ::= {acPMSBCUserDefinedFailures25 1}



     -- ****************************************
     -- acPMSBCInUserDefinedFailures25 table entry
     -- ****************************************
     acPMSBCInUserDefinedFailures25Entry OBJECT-TYPE
       SYNTAX AcPMSBCInUserDefinedFailures25Entry
       MAX-ACCESS not-accessible
       STATUS obsolete
       DESCRIPTION
           ""
       INDEX {acPMSBCInUserDefinedFailures25Interval}
       ::= {acPMSBCInUserDefinedFailures25Table 1}



     -- ****************************************
     -- acPMSBCInUserDefinedFailures25 TABLE
     -- ****************************************
     AcPMSBCInUserDefinedFailures25Entry ::= SEQUENCE {
       acPMSBCInUserDefinedFailures25Interval          Unsigned32,
       acPMSBCInUserDefinedFailures25Val               Counter32
     }



     acPMSBCInUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures25Entry 1}



     acPMSBCInUserDefinedFailures25Val OBJECT-TYPE
       SYNTAX Counter32
       MAX-ACCESS read-only
       STATUS obsolete
       DESCRIPTION
           "Value of gauge or counter."
       ::= {acPMSBCInUserDefinedFailures25Entry 2}



     -- ****************************************
     -- acPMSBCOutUserDefinedFailures25 table declaration
     -- ****************************************
     acPMSBCOutUserDefinedFailures25Table OBJECT-TYPE
       SYNTAX SEQUENCE OF AcPMSBCOutUserDefinedFailures25Entry
       MAX-ACCESS not-accessible
       STATUS obsolete
       DESCRIPTION
           "Number of user defined Failures 25 for outgoing dialogs (System global)"
       ::= {acPMSBCUserDefinedFailures25 2}



     -- ****************************************
     -- acPMSBCOutUserDefinedFailures25 table entry
     -- ****************************************
     acPMSBCOutUserDefinedFailures25Entry OBJECT-TYPE
       SYNTAX AcPMSBCOutUserDefinedFailures25Entry
       MAX-ACCESS not-accessible
       STATUS obsolete
       DESCRIPTION
           ""
       INDEX {acPMSBCOutUserDefinedFailures25Interval}
       ::= {acPMSBCOutUserDefinedFailures25Table 1}



     -- ****************************************
     -- acPMSBCOutUserDefinedFailures25 TABLE
     -- ****************************************
     AcPMSBCOutUserDefinedFailures25Entry ::= SEQUENCE {
       acPMSBCOutUserDefinedFailures25Interval         Unsigned32,
       acPMSBCOutUserDefinedFailures25Val              Counter32
     }



     acPMSBCOutUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures25Entry 1}



     acPMSBCOutUserDefinedFailures25Val OBJECT-TYPE
       SYNTAX Counter32
       MAX-ACCESS read-only
       STATUS obsolete
       DESCRIPTION
           "Value of gauge or counter."
       ::= {acPMSBCOutUserDefinedFailures25Entry 2}



     -- ****************************************
     -- acPMSBCSRDInUserDefinedFailures25 table declaration
     -- ****************************************
     acPMSBCSRDInUserDefinedFailures25Table OBJECT-TYPE
       SYNTAX SEQUENCE OF AcPMSBCSRDInUserDefinedFailures25Entry
       MAX-ACCESS not-accessible
       STATUS obsolete
       DESCRIPTION
           "Number of user defined Failures 25 for incoming dialogs per SRD"
       ::= {acPMSBCUserDefinedFailures25 3}



     -- ****************************************
     -- acPMSBCSRDInUserDefinedFailures25 table entry
     -- ****************************************
     acPMSBCSRDInUserDefinedFailures25Entry OBJECT-TYPE
       SYNTAX AcPMSBCSRDInUserDefinedFailures25Entry
       MAX-ACCESS not-accessible
       STATUS obsolete
       DESCRIPTION
           ""
       INDEX {acPMSBCSRDInUserDefinedFailures25SrdID,acPMSBCSRDInUserDefinedFailures25Interval}
       ::= {acPMSBCSRDInUserDefinedFailures25Table 1}



     -- ****************************************
     -- acPMSBCSRDInUserDefinedFailures25 TABLE
     -- ****************************************
     AcPMSBCSRDInUserDefinedFailures25Entry ::= SEQUENCE {
       acPMSBCSRDInUserDefinedFailures25SrdID          Unsigned32,
       acPMSBCSRDInUserDefinedFailures25Interval       Unsigned32,
       acPMSBCSRDInUserDefinedFailures25Val            Counter32
     }



     acPMSBCSRDInUserDefinedFailures25SrdID OBJECT-TYPE
       SYNTAX Unsigned32 (0..600)
       MAX-ACCESS not-accessible
       STATUS obsolete
       DESCRIPTION
           "SRD number.
0 is the first SRD."
       ::= {acPMSBCSRDInUserDefinedFailures25Entry 1}



     acPMSBCSRDInUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures25Entry 2}



     acPMSBCSRDInUserDefinedFailures25Val OBJECT-TYPE
       SYNTAX Counter32
       MAX-ACCESS read-only
       STATUS obsolete
       DESCRIPTION
           "Value of gauge or counter."
       ::= {acPMSBCSRDInUserDefinedFailures25Entry 3}



     -- ****************************************
     -- acPMSBCSRDOutUserDefinedFailures25 table declaration
     -- ****************************************
     acPMSBCSRDOutUserDefinedFailures25Table OBJECT-TYPE
       SYNTAX SEQUENCE OF AcPMSBCSRDOutUserDefinedFailures25Entry
       MAX-ACCESS not-accessible
       STATUS obsolete
       DESCRIPTION
           "Number of user defined Failures 25 for outgoing dialogs per SRD"
       ::= {acPMSBCUserDefinedFailures25 4}



     -- ****************************************
     -- acPMSBCSRDOutUserDefinedFailures25 table entry
     -- ****************************************
     acPMSBCSRDOutUserDefinedFailures25Entry OBJECT-TYPE
       SYNTAX AcPMSBCSRDOutUserDefinedFailures25Entry
       MAX-ACCESS not-accessible
       STATUS obsolete
       DESCRIPTION
           ""
       INDEX {acPMSBCSRDOutUserDefinedFailures25SrdID,acPMSBCSRDOutUserDefinedFailures25Interval}
       ::= {acPMSBCSRDOutUserDefinedFailures25Table 1}



     -- ****************************************
     -- acPMSBCSRDOutUserDefinedFailures25 TABLE
     -- ****************************************
     AcPMSBCSRDOutUserDefinedFailures25Entry ::= SEQUENCE {
       acPMSBCSRDOutUserDefinedFailures25SrdID         Unsigned32,
       acPMSBCSRDOutUserDefinedFailures25Interval      Unsigned32,
       acPMSBCSRDOutUserDefinedFailures25Val           Counter32
     }



     acPMSBCSRDOutUserDefinedFailures25SrdID OBJECT-TYPE
       SYNTAX Unsigned32 (0..600)
       MAX-ACCESS not-accessible
       STATUS obsolete
       DESCRIPTION
           "SRD number.
0 is the first SRD."
       ::= {acPMSBCSRDOutUserDefinedFailures25Entry 1}



     acPMSBCSRDOutUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures25Entry 2}



     acPMSBCSRDOutUserDefinedFailures25Val OBJECT-TYPE
       SYNTAX Counter32
       MAX-ACCESS read-only
       STATUS obsolete
       DESCRIPTION
           "Value of gauge or counter."
       ::= {acPMSBCSRDOutUserDefinedFailures25Entry 3}



     -- ****************************************
     -- acPMSBCIPGroupInUserDefinedFailures25 table declaration
     -- ****************************************
     acPMSBCIPGroupInUserDefinedFailures25Table OBJECT-TYPE
       SYNTAX SEQUENCE OF AcPMSBCIPGroupInUserDefinedFailures25Entry
       MAX-ACCESS not-accessible
       STATUS obsolete
       DESCRIPTION
           "Number of user defined Failures 25 for incoming dialogs per IP Group"
       ::= {acPMSBCUserDefinedFailures25 5}



     -- ****************************************
     -- acPMSBCIPGroupInUserDefinedFailures25 table entry
     -- ****************************************
     acPMSBCIPGroupInUserDefinedFailures25Entry OBJECT-TYPE
       SYNTAX AcPMSBCIPGroupInUserDefinedFailures25Entry
       MAX-ACCESS not-accessible
       STATUS obsolete
       DESCRIPTION
           ""
       INDEX {acPMSBCIPGroupInUserDefinedFailures25IPGroupID,acPMSBCIPGroupInUserDefinedFailures25Interval}
       ::= {acPMSBCIPGroupInUserDefinedFailures25Table 1}



     -- ****************************************
     -- acPMSBCIPGroupInUserDefinedFailures25 TABLE
     -- ****************************************
     AcPMSBCIPGroupInUserDefinedFailures25Entry ::= SEQUENCE {
       acPMSBCIPGroupInUserDefinedFailures25IPGroupID  Unsigned32,
       acPMSBCIPGroupInUserDefinedFailures25Interval   Unsigned32,
       acPMSBCIPGroupInUserDefinedFailures25Val        Counter32
     }



     acPMSBCIPGroupInUserDefinedFailures25IPGroupID OBJECT-TYPE
       SYNTAX Unsigned32 (0..5000)
       MAX-ACCESS not-accessible
       STATUS obsolete
       DESCRIPTION
           "IP Group number."
       ::= {acPMSBCIPGroupInUserDefinedFailures25Entry 1}



     acPMSBCIPGroupInUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures25Entry 2}



     acPMSBCIPGroupInUserDefinedFailures25Val OBJECT-TYPE
       SYNTAX Counter32
       MAX-ACCESS read-only
       STATUS obsolete
       DESCRIPTION
           "Value of gauge or counter."
       ::= {acPMSBCIPGroupInUserDefinedFailures25Entry 3}



     -- ****************************************
     -- acPMSBCIPGroupOutUserDefinedFailures25 table declaration
     -- ****************************************
     acPMSBCIPGroupOutUserDefinedFailures25Table OBJECT-TYPE
       SYNTAX SEQUENCE OF AcPMSBCIPGroupOutUserDefinedFailures25Entry
       MAX-ACCESS not-accessible
       STATUS obsolete
       DESCRIPTION
           "Number of user defined Failures 25 for outgoing dialogs per IP Group"
       ::= {acPMSBCUserDefinedFailures25 6}



     -- ****************************************
     -- acPMSBCIPGroupOutUserDefinedFailures25 table entry
     -- ****************************************
     acPMSBCIPGroupOutUserDefinedFailures25Entry OBJECT-TYPE
       SYNTAX AcPMSBCIPGroupOutUserDefinedFailures25Entry
       MAX-ACCESS not-accessible
       STATUS obsolete
       DESCRIPTION
           ""
       INDEX {acPMSBCIPGroupOutUserDefinedFailures25IPGroupID,acPMSBCIPGroupOutUserDefinedFailures25Interval}
       ::= {acPMSBCIPGroupOutUserDefinedFailures25Table 1}



     -- ****************************************
     -- acPMSBCIPGroupOutUserDefinedFailures25 TABLE
     -- ****************************************
     AcPMSBCIPGroupOutUserDefinedFailures25Entry ::= SEQUENCE {
       acPMSBCIPGroupOutUserDefinedFailures25IPGroupID Unsigned32,
       acPMSBCIPGroupOutUserDefinedFailures25Interval  Unsigned32,
       acPMSBCIPGroupOutUserDefinedFailures25Val       Counter32
     }



     acPMSBCIPGroupOutUserDefinedFailures25IPGroupID OBJECT-TYPE
       SYNTAX Unsigned32 (0..5000)
       MAX-ACCESS not-accessible
       STATUS obsolete
       DESCRIPTION
           "IP Group number."
       ::= {acPMSBCIPGroupOutUserDefinedFailures25Entry 1}



     acPMSBCIPGroupOutUserDefinedFailures25Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures25Entry 2}



     acPMSBCIPGroupOutUserDefinedFailures25Val OBJECT-TYPE
       SYNTAX Counter32
       MAX-ACCESS read-only
       STATUS obsolete
       DESCRIPTION
           "Value of gauge or counter."
       ::= {acPMSBCIPGroupOutUserDefinedFailures25Entry 3}



     acPMSBCUserDefinedFailures26 OBJECT IDENTIFIER ::= {acPMSBCUserDefinedFailuresPMs 26}


     -- ****************************************
     -- acPMSBCInUserDefinedFailures26 table declaration
     -- ****************************************
     acPMSBCInUserDefinedFailures26Table OBJECT-TYPE
       SYNTAX SEQUENCE OF AcPMSBCInUserDefinedFailures26Entry
       MAX-ACCESS not-accessible
       STATUS obsolete
       DESCRIPTION
           "Number of user defined failures 26 for incoming dialogs (System global)"
       ::= {acPMSBCUserDefinedFailures26 1}



     -- ****************************************
     -- acPMSBCInUserDefinedFailures26 table entry
     -- ****************************************
     acPMSBCInUserDefinedFailures26Entry OBJECT-TYPE
       SYNTAX AcPMSBCInUserDefinedFailures26Entry
       MAX-ACCESS not-accessible
       STATUS obsolete
       DESCRIPTION
           ""
       INDEX {acPMSBCInUserDefinedFailures26Interval}
       ::= {acPMSBCInUserDefinedFailures26Table 1}



     -- ****************************************
     -- acPMSBCInUserDefinedFailures26 TABLE
     -- ****************************************
     AcPMSBCInUserDefinedFailures26Entry ::= SEQUENCE {
       acPMSBCInUserDefinedFailures26Interval          Unsigned32,
       acPMSBCInUserDefinedFailures26Val               Counter32
     }



     acPMSBCInUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCInUserDefinedFailures26Entry 1}



     acPMSBCInUserDefinedFailures26Val OBJECT-TYPE
       SYNTAX Counter32
       MAX-ACCESS read-only
       STATUS obsolete
       DESCRIPTION
           "Value of gauge or counter."
       ::= {acPMSBCInUserDefinedFailures26Entry 2}



     -- ****************************************
     -- acPMSBCOutUserDefinedFailures26 table declaration
     -- ****************************************
     acPMSBCOutUserDefinedFailures26Table OBJECT-TYPE
       SYNTAX SEQUENCE OF AcPMSBCOutUserDefinedFailures26Entry
       MAX-ACCESS not-accessible
       STATUS obsolete
       DESCRIPTION
           "Number of user defined Failures 26 for outgoing dialogs (System global)"
       ::= {acPMSBCUserDefinedFailures26 2}



     -- ****************************************
     -- acPMSBCOutUserDefinedFailures26 table entry
     -- ****************************************
     acPMSBCOutUserDefinedFailures26Entry OBJECT-TYPE
       SYNTAX AcPMSBCOutUserDefinedFailures26Entry
       MAX-ACCESS not-accessible
       STATUS obsolete
       DESCRIPTION
           ""
       INDEX {acPMSBCOutUserDefinedFailures26Interval}
       ::= {acPMSBCOutUserDefinedFailures26Table 1}



     -- ****************************************
     -- acPMSBCOutUserDefinedFailures26 TABLE
     -- ****************************************
     AcPMSBCOutUserDefinedFailures26Entry ::= SEQUENCE {
       acPMSBCOutUserDefinedFailures26Interval         Unsigned32,
       acPMSBCOutUserDefinedFailures26Val              Counter32
     }



     acPMSBCOutUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCOutUserDefinedFailures26Entry 1}



     acPMSBCOutUserDefinedFailures26Val OBJECT-TYPE
       SYNTAX Counter32
       MAX-ACCESS read-only
       STATUS obsolete
       DESCRIPTION
           "Value of gauge or counter."
       ::= {acPMSBCOutUserDefinedFailures26Entry 2}



     -- ****************************************
     -- acPMSBCSRDInUserDefinedFailures26 table declaration
     -- ****************************************
     acPMSBCSRDInUserDefinedFailures26Table OBJECT-TYPE
       SYNTAX SEQUENCE OF AcPMSBCSRDInUserDefinedFailures26Entry
       MAX-ACCESS not-accessible
       STATUS obsolete
       DESCRIPTION
           "Number of user defined Failures 26 for incoming dialogs per SRD"
       ::= {acPMSBCUserDefinedFailures26 3}



     -- ****************************************
     -- acPMSBCSRDInUserDefinedFailures26 table entry
     -- ****************************************
     acPMSBCSRDInUserDefinedFailures26Entry OBJECT-TYPE
       SYNTAX AcPMSBCSRDInUserDefinedFailures26Entry
       MAX-ACCESS not-accessible
       STATUS obsolete
       DESCRIPTION
           ""
       INDEX {acPMSBCSRDInUserDefinedFailures26SrdID,acPMSBCSRDInUserDefinedFailures26Interval}
       ::= {acPMSBCSRDInUserDefinedFailures26Table 1}



     -- ****************************************
     -- acPMSBCSRDInUserDefinedFailures26 TABLE
     -- ****************************************
     AcPMSBCSRDInUserDefinedFailures26Entry ::= SEQUENCE {
       acPMSBCSRDInUserDefinedFailures26SrdID          Unsigned32,
       acPMSBCSRDInUserDefinedFailures26Interval       Unsigned32,
       acPMSBCSRDInUserDefinedFailures26Val            Counter32
     }



     acPMSBCSRDInUserDefinedFailures26SrdID OBJECT-TYPE
       SYNTAX Unsigned32 (0..600)
       MAX-ACCESS not-accessible
       STATUS obsolete
       DESCRIPTION
           "SRD number.
0 is the first SRD."
       ::= {acPMSBCSRDInUserDefinedFailures26Entry 1}



     acPMSBCSRDInUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDInUserDefinedFailures26Entry 2}



     acPMSBCSRDInUserDefinedFailures26Val OBJECT-TYPE
       SYNTAX Counter32
       MAX-ACCESS read-only
       STATUS obsolete
       DESCRIPTION
           "Value of gauge or counter."
       ::= {acPMSBCSRDInUserDefinedFailures26Entry 3}



     -- ****************************************
     -- acPMSBCSRDOutUserDefinedFailures26 table declaration
     -- ****************************************
     acPMSBCSRDOutUserDefinedFailures26Table OBJECT-TYPE
       SYNTAX SEQUENCE OF AcPMSBCSRDOutUserDefinedFailures26Entry
       MAX-ACCESS not-accessible
       STATUS obsolete
       DESCRIPTION
           "Number of user defined Failures 26 for outgoing dialogs per SRD"
       ::= {acPMSBCUserDefinedFailures26 4}



     -- ****************************************
     -- acPMSBCSRDOutUserDefinedFailures26 table entry
     -- ****************************************
     acPMSBCSRDOutUserDefinedFailures26Entry OBJECT-TYPE
       SYNTAX AcPMSBCSRDOutUserDefinedFailures26Entry
       MAX-ACCESS not-accessible
       STATUS obsolete
       DESCRIPTION
           ""
       INDEX {acPMSBCSRDOutUserDefinedFailures26SrdID,acPMSBCSRDOutUserDefinedFailures26Interval}
       ::= {acPMSBCSRDOutUserDefinedFailures26Table 1}



     -- ****************************************
     -- acPMSBCSRDOutUserDefinedFailures26 TABLE
     -- ****************************************
     AcPMSBCSRDOutUserDefinedFailures26Entry ::= SEQUENCE {
       acPMSBCSRDOutUserDefinedFailures26SrdID         Unsigned32,
       acPMSBCSRDOutUserDefinedFailures26Interval      Unsigned32,
       acPMSBCSRDOutUserDefinedFailures26Val           Counter32
     }



     acPMSBCSRDOutUserDefinedFailures26SrdID OBJECT-TYPE
       SYNTAX Unsigned32 (0..600)
       MAX-ACCESS not-accessible
       STATUS obsolete
       DESCRIPTION
           "SRD number.
0 is the first SRD."
       ::= {acPMSBCSRDOutUserDefinedFailures26Entry 1}



     acPMSBCSRDOutUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCSRDOutUserDefinedFailures26Entry 2}



     acPMSBCSRDOutUserDefinedFailures26Val OBJECT-TYPE
       SYNTAX Counter32
       MAX-ACCESS read-only
       STATUS obsolete
       DESCRIPTION
           "Value of gauge or counter."
       ::= {acPMSBCSRDOutUserDefinedFailures26Entry 3}



     -- ****************************************
     -- acPMSBCIPGroupInUserDefinedFailures26 table declaration
     -- ****************************************
     acPMSBCIPGroupInUserDefinedFailures26Table OBJECT-TYPE
       SYNTAX SEQUENCE OF AcPMSBCIPGroupInUserDefinedFailures26Entry
       MAX-ACCESS not-accessible
       STATUS obsolete
       DESCRIPTION
           "Number of user defined Failures 26 for incoming dialogs per IP Group"
       ::= {acPMSBCUserDefinedFailures26 5}



     -- ****************************************
     -- acPMSBCIPGroupInUserDefinedFailures26 table entry
     -- ****************************************
     acPMSBCIPGroupInUserDefinedFailures26Entry OBJECT-TYPE
       SYNTAX AcPMSBCIPGroupInUserDefinedFailures26Entry
       MAX-ACCESS not-accessible
       STATUS obsolete
       DESCRIPTION
           ""
       INDEX {acPMSBCIPGroupInUserDefinedFailures26IPGroupID,acPMSBCIPGroupInUserDefinedFailures26Interval}
       ::= {acPMSBCIPGroupInUserDefinedFailures26Table 1}



     -- ****************************************
     -- acPMSBCIPGroupInUserDefinedFailures26 TABLE
     -- ****************************************
     AcPMSBCIPGroupInUserDefinedFailures26Entry ::= SEQUENCE {
       acPMSBCIPGroupInUserDefinedFailures26IPGroupID  Unsigned32,
       acPMSBCIPGroupInUserDefinedFailures26Interval   Unsigned32,
       acPMSBCIPGroupInUserDefinedFailures26Val        Counter32
     }



     acPMSBCIPGroupInUserDefinedFailures26IPGroupID OBJECT-TYPE
       SYNTAX Unsigned32 (0..5000)
       MAX-ACCESS not-accessible
       STATUS obsolete
       DESCRIPTION
           "IP Group number."
       ::= {acPMSBCIPGroupInUserDefinedFailures26Entry 1}



     acPMSBCIPGroupInUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupInUserDefinedFailures26Entry 2}



     acPMSBCIPGroupInUserDefinedFailures26Val OBJECT-TYPE
       SYNTAX Counter32
       MAX-ACCESS read-only
       STATUS obsolete
       DESCRIPTION
           "Value of gauge or counter."
       ::= {acPMSBCIPGroupInUserDefinedFailures26Entry 3}



     -- ****************************************
     -- acPMSBCIPGroupOutUserDefinedFailures26 table declaration
     -- ****************************************
     acPMSBCIPGroupOutUserDefinedFailures26Table OBJECT-TYPE
       SYNTAX SEQUENCE OF AcPMSBCIPGroupOutUserDefinedFailures26Entry
       MAX-ACCESS not-accessible
       STATUS obsolete
       DESCRIPTION
           "Number of user defined Failures 26 for outgoing dialogs per IP Group"
       ::= {acPMSBCUserDefinedFailures26 6}



     -- ****************************************
     -- acPMSBCIPGroupOutUserDefinedFailures26 table entry
     -- ****************************************
     acPMSBCIPGroupOutUserDefinedFailures26Entry OBJECT-TYPE
       SYNTAX AcPMSBCIPGroupOutUserDefinedFailures26Entry
       MAX-ACCESS not-accessible
       STATUS obsolete
       DESCRIPTION
           ""
       INDEX {acPMSBCIPGroupOutUserDefinedFailures26IPGroupID,acPMSBCIPGroupOutUserDefinedFailures26Interval}
       ::= {acPMSBCIPGroupOutUserDefinedFailures26Table 1}



     -- ****************************************
     -- acPMSBCIPGroupOutUserDefinedFailures26 TABLE
     -- ****************************************
     AcPMSBCIPGroupOutUserDefinedFailures26Entry ::= SEQUENCE {
       acPMSBCIPGroupOutUserDefinedFailures26IPGroupID Unsigned32,
       acPMSBCIPGroupOutUserDefinedFailures26Interval  Unsigned32,
       acPMSBCIPGroupOutUserDefinedFailures26Val       Counter32
     }



     acPMSBCIPGroupOutUserDefinedFailures26IPGroupID OBJECT-TYPE
       SYNTAX Unsigned32 (0..5000)
       MAX-ACCESS not-accessible
       STATUS obsolete
       DESCRIPTION
           "IP Group number."
       ::= {acPMSBCIPGroupOutUserDefinedFailures26Entry 1}



     acPMSBCIPGroupOutUserDefinedFailures26Interval OBJECT-TYPE
       SYNTAX Unsigned32 (0..2)
       MAX-ACCESS not-accessible
       STATUS obsolete
       DESCRIPTION
           "Interval index.
0 - current period (incomplete monitoring - mid period).
1 - Last full period.
2 - One before last."
       ::= {acPMSBCIPGroupOutUserDefinedFailures26Entry 2}



     acPMSBCIPGroupOutUserDefinedFailures26Val OBJECT-TYPE
       SYNTAX Counter32
       MAX-ACCESS read-only
       STATUS obsolete
       DESCRIPTION
           "Value of gauge or counter."
       ::= {acPMSBCIPGroupOutUserDefinedFailures26Entry 3}





END
