ENGENIUS-MESH-MIB DEFINITIONS ::= BEGIN

IMPORTS
	MODULE-IDENTITY, OBJECT-TYPE, NOTIFICATION-TYPE, OBJECT-IDENTITY, 
	enterprises, IpAddress, Counter32, Gauge32, TimeTicks, Integer32,
	Counter64                                              
            	FROM SNMPv2-SMI
                                                   
	DisplayString, MacAddress, TruthValue, TimeStamp,
	TimeInterval, DateAndTime, RowStatus, TEXTUAL-CONVENTION
	FROM SNMPv2-TC

	MODULE-COMPLIANCE, OBJECT-GROUP
	FROM SNMPv2-CONF

	ifIndex
	    FROM RFC1213-MIB
        
      InetAddressType, InetAddress 
          FROM INET-ADDRESS-MIB;	    

engeniusmesh MODULE-IDENTITY
    LAST-UPDATED "200803071000Z"
    ORGANIZATION "Senao Networks, Inc."
    CONTACT-INFO
       "Senao Networks, Inc.
	No. 500, Fusing 3rd Road,
	Hwa-Ya Technology Park Kuei-Shan Hsiang,
	Taoyuan County 333,
	Taiwan.
	Tel: 886-3-328-9289
	Fax: 886-3-396-2222
	Email: sales@senao.com
	Website: http://www.engeniustech.com/corporate/"
    DESCRIPTION
        "MIB Definition used in the Engenius Mesh Product Line:
         iso(1).org(3).dod(6).internet(1).private(4).enterprises(1).
         engenius(14125).engeniusmesh(1)"
	REVISION        "200803071000Z"
    DESCRIPTION "added operating mode, added hardwarename"
	REVISION        "200803041000Z"
    DESCRIPTION "added multicast, ospfd, ebtables"
	REVISION        "200802281600Z"
    DESCRIPTION "added option in ipaddress.tbl, system mode, added prmt in pppoe"
	REVISION 	"200802261700Z"
    DESCRIPTION	"Updated Interface list"
	REVISION 	"200801211600Z"
    DESCRIPTION	"Added prmt in routedog, added mlrdrelay, added system mode options"
	REVISION 	"200711291500Z"
    DESCRIPTION	"Added vlan in tmipd"
	REVISION        "200711231700Z"
    DESCRIPTION "Added option in operational mode"
	REVISION 	"200710051000Z"
    DESCRIPTION	"Added static key configuration"
	REVISION 	"200710021030Z"
    DESCRIPTION	"Added LocalUser and UserGroup table"
	REVISION 	"200709261900Z"
	DESCRIPTION	"Added system memory status and reset snmp cmd"
	REVISION 	"200709201300Z"
	DESCRIPTION	"Added user group in firewall table"
	REVISION 	"200709131200Z"
	DESCRIPTION	"Added script to call when system mode changed"
	REVISION 	"200708291700Z"
	DESCRIPTION	"Added option in system mode"
	REVISION 	"200708211700Z"
	DESCRIPTION	"Added nms address table"
	REVISION        "200708031100Z"
	DESCRIPTION "Added option in wireless-security"
	REVISION        "200707181700Z"
	DESCRIPTION "Added tm75.opts"
	REVISION 	"200707111700Z"
	DESCRIPTION	"Edited input range in trafficshaping, routewatchdog, advtuning,dhcpd, added wireless seperation, interchange macaccess index 3 and 4"
	REVISION 	"200707101400Z"
	DESCRIPTION	"Edit logout_n_block command type to ipaddress, added active_mac_list and dhcp_client_list"
	REVISION        "200706201700Z"
	DESCRIPTION "Added type in macaccess table, and blockuser command"
	REVISION        "200706081600Z"
	DESCRIPTION "Added scalar parameters in captive and advancedTunning"
	REVISION        "200706011500Z"
        DESCRIPTION     "Added wme table and a scalar item in captive"
	REVISION        "200705081700Z"
        DESCRIPTION     "Added max row for tables"
	REVISION	"200704251600Z"
	DESCRIPTION	"Added SSHD"
	REVISION 	"200704101000Z"
    	DESCRIPTION	"Added option for system mode (clientrelay)"
	REVISION 	"200704021000Z"
	DESCRIPTION	"Added Tx Power and Current Tx Power in Wireless Table"
	REVISION 	"200702091700Z"
	DESCRIPTION	"Added Advanced Tunning and upload command"
	REVISION 	"200702081800Z"
	DESCRIPTION	"Added Linux Dog"
	REVISION 	"200702081000Z"
	DESCRIPTION	"Added Route Dog"
	REVISION 	"200701151000Z"
	DESCRIPTION	"Added Client Statistic Table"
	REVISION 	"200701111000Z"
	DESCRIPTION	"Added MLDR"
	REVISION 	"200701081000Z"
	DESCRIPTION	"Added item into trap table"
	REVISION 	"200612141000Z"
	DESCRIPTION	"Added autoip and interface list"
	REVISION    "200612011000Z"	
    	DESCRIPTION "Added client info, wireless table entry & traps entry"
	REVISION    "200611291000Z"	
    	DESCRIPTION "Added L2tpc"
	REVISION    "200611281000Z"	
    	DESCRIPTION "Added AP1_channel_list, edit ath0 and ath1 to Mesh and AP0, added DHCP_active, added IPSec"
	REVISION    "200611231000Z"	
    	DESCRIPTION "Added reboot and reset command"
	REVISION    "200611101000Z"
    	DESCRIPTION "Refer to configuration file v0.14, and remove flash and commands, and added signal level table"
	REVISION    "200611081000Z"
    	DESCRIPTION "Added wireless frequency channel for ath0 and ath1, and refer to configuration file v0.13"
	REVISION    "200611061000Z"
    	DESCRIPTION "Refer to configuration file v0.12"
	REVISION    "200611021000Z"
    	DESCRIPTION "Refer to configuration file v0.10"
	REVISION    "200610301000Z"
    	DESCRIPTION "Refer to configuration file v0.8"
	REVISION    "200610271000Z"
    	DESCRIPTION "Refer to configuration file v0.7"
    	REVISION    "200610181000Z"
    	DESCRIPTION "Minor changes, add Trap"
    	REVISION    "200610051000Z"
    	DESCRIPTION "Added Topology Table"
   	REVISION	"200610010000Z"
    	DESCRIPTION	"New Version"

      ::= { engenius 1 }

engenius				OBJECT IDENTIFIER ::= { enterprises 14125 }



nodeStatus			OBJECT IDENTIFIER ::= { engeniusmesh 1 }
nodeConfiguration		OBJECT IDENTIFIER ::= { engeniusmesh 2 }
nodeCommand        	OBJECT IDENTIFIER ::= { engeniusmesh 3 }

nodeStatusSystem		OBJECT IDENTIFIER ::= { nodeStatus 1 }
nodeStatusTrap		OBJECT IDENTIFIER ::= { nodeStatus 2 }

nodeConfigurationSystem		OBJECT IDENTIFIER ::= { nodeConfiguration 1 }
nodeConfigurationEthernet	OBJECT IDENTIFIER ::= { nodeConfiguration 2 }
nodeConfigurationWireless	OBJECT IDENTIFIER ::= { nodeConfiguration 3 }
nodeConfigurationVlan		OBJECT IDENTIFIER ::= { nodeConfiguration 4 }
nodeConfigurationBridge		OBJECT IDENTIFIER ::= { nodeConfiguration 5 }
nodeConfigurationIpaddress	OBJECT IDENTIFIER ::= { nodeConfiguration 6 }
nodeConfigurationNetwork	OBJECT IDENTIFIER ::= { nodeConfiguration 7 }
nodeConfigurationSyslog		OBJECT IDENTIFIER ::= { nodeConfiguration 8 }
nodeConfigurationOlsr		OBJECT IDENTIFIER ::= { nodeConfiguration 9 }
nodeConfigurationRoute		OBJECT IDENTIFIER ::= { nodeConfiguration 10 }
nodeConfigurationNtp		OBJECT IDENTIFIER ::= { nodeConfiguration 11 }
nodeConfigurationDhcpd		OBJECT IDENTIFIER ::= { nodeConfiguration 12 }
nodeConfigurationDns		OBJECT IDENTIFIER ::= { nodeConfiguration 13 }
nodeConfigurationTopology	OBJECT IDENTIFIER ::= { nodeConfiguration 14 }
nodeConfigurationFirewall	OBJECT IDENTIFIER ::= { nodeConfiguration 15 }
nodeConfigurationMacaccess	OBJECT IDENTIFIER ::= { nodeConfiguration 16 }
nodeConfigurationNat		OBJECT IDENTIFIER ::= { nodeConfiguration 17 }
nodeConfigurationOlsrGW 	OBJECT IDENTIFIER ::= { nodeConfiguration 18 }
nodeConfigurationShaping	OBJECT IDENTIFIER ::= { nodeConfiguration 19 }
nodeConfigurationPppoe		OBJECT IDENTIFIER ::= { nodeConfiguration 20 }
nodeConfigurationPptp		OBJECT IDENTIFIER ::= { nodeConfiguration 21 }
nodeConfigurationTmipd		OBJECT IDENTIFIER ::= { nodeConfiguration 22 }
nodeConfigurationCaptive 	OBJECT IDENTIFIER ::= { nodeConfiguration 23 }
nodeConfigurationRadiusClient	OBJECT IDENTIFIER ::= { nodeConfiguration 24 }
nodeConfigurationHttpd		OBJECT IDENTIFIER ::= { nodeConfiguration 25 }
nodeConfigurationSnmpd		OBJECT IDENTIFIER ::= { nodeConfiguration 26 }
nodeConfigurationTrap		OBJECT IDENTIFIER ::= { nodeConfiguration 27 }
nodeConfigurationDdns		OBJECT IDENTIFIER ::= { nodeConfiguration 28 }
nodeConfigurationZeroconfig	OBJECT IDENTIFIER ::= { nodeConfiguration 29 }
nodeConfigurationSignallevel	OBJECT IDENTIFIER ::= { nodeConfiguration 30 }
nodeConfigurationIpsec		OBJECT IDENTIFIER ::= { nodeConfiguration 31 }
nodeConfigurationL2tpc		OBJECT IDENTIFIER ::= { nodeConfiguration 32 }
nodeConfigurationAutoip		OBJECT IDENTIFIER ::= { nodeConfiguration 33 }
nodeConfigurationInterfaces	OBJECT IDENTIFIER ::= { nodeConfiguration 34 }
nodeConfigurationMlrd		OBJECT IDENTIFIER ::= { nodeConfiguration 35 }
nodeConfigurationRoutedog	OBJECT IDENTIFIER ::= { nodeConfiguration 36 }
nodeConfigurationLinuxdog	OBJECT IDENTIFIER ::= { nodeConfiguration 37 }
nodeConfigurationAdvTunning	OBJECT IDENTIFIER ::= { nodeConfiguration 38 }
nodeConfigurationSshd		OBJECT IDENTIFIER ::= { nodeConfiguration 39 }
nodeConfigutationWme		OBJECT IDENTIFIER ::= { nodeConfiguration 40 }
nodeConfigurationTm75		OBJECT IDENTIFIER ::= { nodeConfiguration 41 }
nodeConfigurationNmsAddress	OBJECT IDENTIFIER ::= { nodeConfiguration 42 }
nodeConfigurationUserDb		OBJECT IDENTIFIER ::= { nodeConfiguration 43 }
nodeConfigurationUserGroup	OBJECT IDENTIFIER ::= { nodeConfiguration 44 }
nodeConfigurationStatickey	OBJECT IDENTIFIER ::= { nodeConfiguration 45 }
nodeConfigurationDhcrelay	OBJECT IDENTIFIER ::= { nodeConfiguration 46 }
nodeConfigurationMulticast	OBJECT IDENTIFIER ::= { nodeConfiguration 47 }
nodeConfigurationOspfd		OBJECT IDENTIFIER ::= { nodeConfiguration 48 }
nodeConfigurationEbtables	OBJECT IDENTIFIER ::= { nodeConfiguration 49 }

nodeCommandReboot               	OBJECT IDENTIFIER ::= { nodeCommand 1 }
nodeCommandReset                	OBJECT IDENTIFIER ::= { nodeCommand 2 }
nodeCommandUpload				OBJECT IDENTIFIER ::= { nodeCommand 3 }
nodeCommandLogoutBlock 			OBJECT IDENTIFIER ::= { nodeCommand 4 }
nodeCommandRestartSnmp			OBJECT IDENTIFIER ::= { nodeCommand 5 }


-- ==========================
-- Defination Begins
-- ==========================

-- =======| nodeStatusSystem | =========

systemUptime OBJECT-TYPE
	SYNTAX DisplayString (SIZE (0..50))
   	MAX-ACCESS read-only
     	STATUS current
     	DESCRIPTION
	"This object represents the value of sysUpTime from 
	the time the station entered its current operational state."
     ::= { nodeStatusSystem 1 }

systemMemory OBJECT-TYPE
	SYNTAX Integer32
	MAX-ACCESS read-only
	STATUS current
	DESCRIPTION
	"This object represent the percentage of the system free memory."
	::= { nodeStatusSystem 2 }

systemDevicename OBJECT-TYPE
	SYNTAX DisplayString (SIZE (0..50))
	MAX-ACCESS read-only
	STATUS current
	DESCRIPTION
	"This object represents the name of the system device."
	::= { nodeStatusSystem 3 }

systemCheckingState OBJECT-TYPE
       SYNTAX DisplayString
       MAX-ACCESS read-only
       STATUS current
       DESCRIPTION
       "Check is dorado system"
       ::= { nodeStatusSystem 4 }

-- ========= | Traps Definition | =============

trapVariable OBJECT IDENTIFIER
    ::= { nodeStatusTrap 1 }

genericTrapVariable OBJECT-TYPE
    SYNTAX DisplayString
    MAX-ACCESS read-only
    STATUS current
    DESCRIPTION
	"This object is used to provide additional information on traps."
    ::= { trapVariable 1 }

genericTrapVarMACAddress OBJECT-TYPE
    SYNTAX MacAddress
    MAX-ACCESS read-only
    STATUS current
    DESCRIPTION
	"This object is used to store the MAC address of the device
	that has sent a trap."
    ::= { trapVariable 2 }

genericTrapVarHostIPAddress OBJECT-TYPE
    SYNTAX IpAddress
    MAX-ACCESS read-only
    STATUS current
    DESCRIPTION
	"This object is used to store the IP Address of the Host."
    ::= { trapVariable 3 }

genericTrapVarHostname OBJECT-TYPE
    SYNTAX DisplayString
    MAX-ACCESS read-only
    STATUS current
    DESCRIPTION
	"This object is used to store the hostname of the system."
    ::= { trapVariable 4 }

genericTrapVarInterface OBJECT-TYPE
    SYNTAX Integer32
    MAX-ACCESS read-only
    STATUS current
    DESCRIPTION
        "This object is used to store the interface number."
    ::= { trapVariable 5 }

genericTrapVarWirelessCard OBJECT-TYPE
    SYNTAX INTEGER
    {
        cardA(1),
        cardB(2)
    }
    MAX-ACCESS read-only
    STATUS current
    DESCRIPTION
        "This object is used to determine on which Wireless Card,
	Card A or Card B, a wireless TRAP has occured on."
    ::= { trapVariable 6 }

genericTrapVarEthernetPort OBJECT-TYPE
    SYNTAX INTEGER
    {
        ethPortA(1),
        ethPortB(2)
    }
    MAX-ACCESS read-only
    STATUS current
    DESCRIPTION
        "This object is used to determine on which ethernet port,
	port A or port B, a TRAP has occured on."
    ::= { trapVariable 7 }

genericTrapVarCount OBJECT-TYPE
    SYNTAX Integer32
    MAX-ACCESS read-only
    STATUS current
    DESCRIPTION
	"This object is used to store the number of occurance of certain events."
    ::= { trapVariable 8 }

adminTraps OBJECT-IDENTITY
    STATUS current
    DESCRIPTION
        "This is the administrator related trap group."
    ::= { nodeStatusTrap 2 }

adminTrapsAdminConf NOTIFICATION-TYPE
    OBJECTS { genericTrapVarHostIPAddress, genericTrapVariable}
    STATUS current
    DESCRIPTION
	"This traps is generated when the administrator configures any of the web configuration page.
Trap Severity Level: Informative."
    ::= { adminTraps 1 }

adminTrapsAdminCmd NOTIFICATION-TYPE
    OBJECTS { genericTrapVarHostIPAddress, genericTrapVariable}
    STATUS current
    DESCRIPTION
	"This traps is generated when the administrator initiate an command.
Trap Severity Level: Informative."
    ::= { adminTraps 2 }


userTraps OBJECT-IDENTITY
    STATUS current
    DESCRIPTION
        "This is the user related trap group."
    ::= { nodeStatusTrap 3 }

userTrapsUserLogin NOTIFICATION-TYPE
    OBJECTS { genericTrapVarHostIPAddress, genericTrapVariable}
    STATUS current
    DESCRIPTION
	"This traps is generated when a user login to the network.
Trap Severity Level: Informative."
    ::= { userTraps 1 }

userTrapsUserLogout NOTIFICATION-TYPE
    OBJECTS { genericTrapVarHostIPAddress, genericTrapVariable}
    STATUS current
    DESCRIPTION
        "This trap is generated when a user logout from the network.
Trap Severity Level: Informative."
    ::= { userTraps 2 }


systemTraps OBJECT-IDENTITY
    STATUS current
    DESCRIPTION
        "This is the system related trap/notification group."
    ::= { nodeStatusTrap 4 }

systemTrapsSystemReboot NOTIFICATION-TYPE
    OBJECTS { genericTrapVarHostIPAddress, genericTrapVariable}
    STATUS current
    DESCRIPTION
        "This trap is generated when the system is down to reboot.
Trap Severity Level: Major."
    ::= { systemTraps 1 }

systemTrapsSystemRestore NOTIFICATION-TYPE
    OBJECTS { genericTrapVarHostIPAddress, genericTrapVariable}
    STATUS current
    DESCRIPTION
        "This trap is generated the default configuration of the system is restored.
Trap Severity Level: Major."
    ::= { systemTraps 2 }

systemTrapsSystemUpgrade NOTIFICATION-TYPE
    OBJECTS { genericTrapVarHostIPAddress, genericTrapVariable}
    STATUS current
    DESCRIPTION
        "This trap is generated when the firmware of the system is upgraded.
Trap Severity Level: Major."
    ::= { systemTraps 3 }

systemTrapsSystemConf NOTIFICATION-TYPE
    OBJECTS { genericTrapVarHostIPAddress, genericTrapVariable}
    STATUS current
    DESCRIPTION
        "This trap is generated when the configuration of the system is upgraded.
Trap Severity Level: Major."
    ::= { systemTraps 4 }

systemTrapsSystemStatus NOTIFICATION-TYPE
    OBJECTS { genericTrapVarHostIPAddress, genericTrapVariable}
    STATUS current
    DESCRIPTION
        "This trap is generated when any changes occur to the system, like memory, firmware, etc.
Trap Severity Level: Minor."
    ::= { systemTraps 5 }



-- ======== | nodeConfigurationSystem | ==========

systemName OBJECT-TYPE
	SYNTAX DisplayString (SIZE (0..32))
	MAX-ACCESS read-write
	STATUS current
	DESCRIPTION
	"The name of the managed device"
	DEFVAL { "Nil" }
     ::= { nodeConfigurationSystem 1 }

systemLocation OBJECT-TYPE
	SYNTAX DisplayString (SIZE (0..32))
	MAX-ACCESS read-write
	STATUS current
	DESCRIPTION
	"The location name of the managed device"
	DEFVAL { "Unknown" }
     ::= { nodeConfigurationSystem 2 }

systemContactName OBJECT-TYPE
	SYNTAX DisplayString (SIZE (0..32))
	MAX-ACCESS read-write
	STATUS current
	DESCRIPTION
	"The name of the contact person who manages the device"
		DEFVAL { "Unknown" }	
     ::= { nodeConfigurationSystem 3 }

systemContactMail OBJECT-TYPE
	SYNTAX DisplayString (SIZE (0..32))
	MAX-ACCESS read-write
	STATUS current
	DESCRIPTION
	"The Email Address of the contact person who manages the device"
		DEFVAL { "Unknown" }	
     ::= { nodeConfigurationSystem 4 }

systemContactPhone OBJECT-TYPE
	SYNTAX DisplayString (SIZE (0..32))
	MAX-ACCESS read-write
	STATUS current
	DESCRIPTION
	"The contact number of the contact person who manages the device"
	DEFVAL { "Unknown" }
     ::= { nodeConfigurationSystem 5 }

systemDescription OBJECT-TYPE
	SYNTAX DisplayString (SIZE (0..32))
	MAX-ACCESS read-write
	STATUS current
	DESCRIPTION	
	"A short description regarding the managed device"
	DEFVAL { "Nil" }
     ::= { nodeConfigurationSystem 6 }

systemObjectid OBJECT-TYPE
	SYNTAX DisplayString (SIZE (0..32))
	MAX-ACCESS read-only
	STATUS current
	DESCRIPTION 
	"The object id of the system"
	DEFVAL { "Nil" }
	::= { nodeConfigurationSystem 7 }

systemOperatemode OBJECT-TYPE
	SYNTAX INTEGER
	{
		gateway(1),
		relay(2),
		clientrelay(3),
		layer2gw(4),
		layer2(5),
		bridge(6),
		router(7),
		dualradiogw(8),
		dualradiorelay(9),
		dualradiocrelay(10),
		mlrd(11),
		slavebridge(12),
		masterbridge(13),
		wdsbridge(14),
		repeater(15),
		client(16),
		clientrouter(17),
		wdsrouter(18)
	}
	MAX-ACCESS read-write
	STATUS current
	DESCRIPTION
	"Define the mode of the system/device"
	DEFVAL { gateway }
	::= { nodeConfigurationSystem 8 }

systemUpdateMode OBJECT-TYPE
   SYNTAX Integer32 (1..13)
   MAX-ACCESS read-write
   STATUS current
   DESCRIPTION 
       "SnmpSet to update the system firmware when mode is changed."
   ::= { nodeConfigurationSystem 9 } 



-- =========== | nodeConfigurationEthernet | ==============

ethernetInterfaceTable OBJECT-TYPE
    	SYNTAX SEQUENCE OF EthernetInterfaceTableEntry
    	MAX-ACCESS not-accessible
    	STATUS current
    	DESCRIPTION
	"This table contains the information of the ethernet interfaces." 
    ::= { nodeConfigurationEthernet 1 }

ethernetInterfaceTableEntry OBJECT-TYPE
    	SYNTAX EthernetInterfaceTableEntry 
   	MAX-ACCESS not-accessible
    	STATUS current
    	DESCRIPTION
	"Represent the entry in the Ethernet Interface table."
    INDEX { ethInterfaceTableIndex }
    ::= { ethernetInterfaceTable 1 }

EthernetInterfaceTableEntry::=
    SEQUENCE
    {
	ethInterfaceTableIndex	 	Integer32, 
	ethInterfaceTableName	 	OCTET STRING,
	ethInterfaceTableBase 	 	OCTET STRING,
	ethInterfaceTableMac	 	MacAddress,
	ethInterfaceTableBridge	 	OCTET STRING,
	ethInterfaceTableBridgeCost 	Integer32, 
	ethInterfaceTableBridgePrio 	Integer32,
        ethInterfaceTableComments 	DisplayString, 
	ethInterfaceTableActive 	INTEGER,
	ethInterfaceTableRowStatus	RowStatus 	
    }

ethInterfaceTableIndex OBJECT-TYPE
    SYNTAX Integer32 (0..2)
    MAX-ACCESS not-accessible
    STATUS current
    DESCRIPTION
	"Specify the index of the Ethernet interface table."
    ::= { ethernetInterfaceTableEntry 1 }

ethInterfaceTableName OBJECT-TYPE
    SYNTAX OCTET STRING (SIZE (0..32))
    MAX-ACCESS read-create
    STATUS current
    DESCRIPTION
	"The name of the ethernet interface."
	DEFVAL { "Nil" }
    ::= { ethernetInterfaceTableEntry 2 }

ethInterfaceTableBase OBJECT-TYPE
    SYNTAX OCTET STRING (SIZE (0..32))
    MAX-ACCESS read-create
    STATUS current
    DESCRIPTION
	"The base name of the ethernet interface."
	DEFVAL { "Nil" }
    ::= { ethernetInterfaceTableEntry 3 }

ethInterfaceTableMac OBJECT-TYPE
    SYNTAX MacAddress
    MAX-ACCESS read-create
    STATUS current
    DESCRIPTION
	"The hardware address of the interface."
	DEFVAL { "Nil" }
    ::= { ethernetInterfaceTableEntry 4 }

ethInterfaceTableBridge OBJECT-TYPE
    SYNTAX OCTET STRING (SIZE (0..32))
    MAX-ACCESS read-create
    STATUS current
    DESCRIPTION
	"The bridge interface that the current ethernet interface is attached to."
	DEFVAL { "Nil" }
    ::= { ethernetInterfaceTableEntry 5 }

ethInterfaceTableBridgeCost OBJECT-TYPE
    SYNTAX Integer32 (0..65536)
    MAX-ACCESS read-create
    STATUS current
    DESCRIPTION
	"The cost of the bridge interface that the current ethernet interface is attached to."
    DEFVAL { 0 }
    ::= { ethernetInterfaceTableEntry 6 }

ethInterfaceTableBridgePrio OBJECT-TYPE
    SYNTAX Integer32 (0..65536)
    MAX-ACCESS read-create
    STATUS current
    DESCRIPTION
	"The priority of the bridge interface that the current ethernet interface is attached to."
    DEFVAL { 0 }
    ::= { ethernetInterfaceTableEntry 7 }


ethInterfaceTableComments OBJECT-TYPE
    SYNTAX DisplayString (SIZE (0..32))
    MAX-ACCESS read-create
    STATUS current
    DESCRIPTION
	"An optional comment associated to entry of the ethernet interface table."
	DEFVAL { "Nil" }
    ::= { ethernetInterfaceTableEntry 8 }

ethInterfaceTableActive OBJECT-TYPE 
    SYNTAX INTEGER
    {
	enable(1),
	disable(2)
    }
    MAX-ACCESS read-create
    STATUS current
    DESCRIPTION
	"The status of the Ethernet interface table entry."
    DEFVAL { enable }
    ::= { ethernetInterfaceTableEntry 9 }

ethInterfaceTableRowStatus OBJECT-TYPE
   SYNTAX RowStatus
   MAX-ACCESS read-create
   STATUS current
   DESCRIPTION
        "The row status in the Ethernet interface table entry"
   ::= { ethernetInterfaceTableEntry 10 }


-- ============== | nodeConfigurationWireless | ==============

wirelessInterfaceTable OBJECT-TYPE
    	SYNTAX SEQUENCE OF WirelessInterfaceTableEntry
    	MAX-ACCESS not-accessible
    	STATUS current
    	DESCRIPTION
	"This table contains the information of the Wireless interfaces." 
    ::= { nodeConfigurationWireless 1 }

wirelessInterfaceTableEntry OBJECT-TYPE
    	SYNTAX WirelessInterfaceTableEntry 
   	MAX-ACCESS not-accessible
    	STATUS current
    	DESCRIPTION
	"Represent the entry in the Wireless interface table."
    INDEX { wlanInterfaceTableIndex }
    ::= { wirelessInterfaceTable 1 }

WirelessInterfaceTableEntry::=
    SEQUENCE
    {
	wlanInterfaceTableIndex	 		Integer32, 
	wlanInterfaceTableName	 		OCTET STRING,
	wlanInterfaceTableBase 	 		OCTET STRING,
	wlanInterfaceTableBridge		OCTET STRING,
	wlanInterfaceTableBridgeCost 		Integer32, 
	wlanInterfaceTableBridgePrio 		Integer32,
	wlanInterfaceTableMode			INTEGER,
	wlanInterfaceTableBand			INTEGER,
	wlanInterfaceTableEssid			DisplayString,
	wlanInterfaceTableFreq			Integer32,
	wlanInterfaceTableMac	 		MacAddress,
	wlanInterfaceTableSecurity		INTEGER,
	wlanInterfaceTableWpaType		INTEGER,
	wlanInterfaceTableDot1x			INTEGER,
	wlanInterfaceTableEncryptionKey	OCTET STRING,
	wlanInterfaceTableBroadcastSsid	INTEGER,
	wlanInterfaceTableBeaconInt		Integer32,
	wlanInterfaceTableRtsThreshold	Integer32,
	wlanInterfaceTableFragThreshold	Integer32,
	wlanInterfaceTableDtimInterval	Integer32,
	wlanInterfaceTableDatarate		Integer32,
	wlanInterfaceTableDiversity		INTEGER,
	wlanInterfaceTableTxAntenna		INTEGER,
	wlanInterfaceTableRxAntenna		INTEGER,
	wlanInterfaceTableCrntTxPower		Integer32,
	wlanInterfaceTableTxPower		Integer32,
	wlanInterfaceTableSeperation		INTEGER,
      wlanInterfaceTableComments 		DisplayString, 
	wlanInterfaceTableActive 		INTEGER,
	wlanInterfaceTableRowStatus		RowStatus 	
    }

wlanInterfaceTableIndex OBJECT-TYPE
    SYNTAX Integer32 (0..52)
    MAX-ACCESS not-accessible
    STATUS current
    DESCRIPTION
	"Specify the index of the Wireless interface table."
    ::= { wirelessInterfaceTableEntry 1 }

wlanInterfaceTableName OBJECT-TYPE
    SYNTAX OCTET STRING (SIZE (0..32))
    MAX-ACCESS read-create
    STATUS current
    DESCRIPTION
	"The name of the Wireless interface."
	DEFVAL { "Nil" }
    ::= { wirelessInterfaceTableEntry 2 }

wlanInterfaceTableBase OBJECT-TYPE
    SYNTAX OCTET STRING (SIZE (0..32))
    MAX-ACCESS read-create
    STATUS current
    DESCRIPTION
	"The base name of the Wireless interface."
	DEFVAL { "Nil" }
    ::= { wirelessInterfaceTableEntry 3 }

wlanInterfaceTableBridge OBJECT-TYPE
    SYNTAX OCTET STRING (SIZE (0..32))
    MAX-ACCESS read-create
    STATUS current
    DESCRIPTION
	"The bridge interface that the current wireless interface is attached to."
	DEFVAL { "Nil" }
    ::= { wirelessInterfaceTableEntry 4 }

wlanInterfaceTableBridgeCost OBJECT-TYPE
    SYNTAX Integer32 (0..65536)
    MAX-ACCESS read-create
    STATUS current
    DESCRIPTION
	"The cost of the bridge interface that the current wireless interface is attached to."
    DEFVAL { 100 }
    ::= { wirelessInterfaceTableEntry 5 }

wlanInterfaceTableBridgePrio OBJECT-TYPE
    SYNTAX Integer32 (0..65536)
    MAX-ACCESS read-create
    STATUS current
    DESCRIPTION
	"The priority of the bridge interface that the current wireless interface is attached to."
    DEFVAL { 100 }
    ::= { wirelessInterfaceTableEntry 6 }

wlanInterfaceTableMode OBJECT-TYPE
     SYNTAX INTEGER
    {
	ap(1),
	sta(2),
	adhoc(3),
	wds(4)
    }
    MAX-ACCESS read-create
    STATUS current
    DESCRIPTION
	"The operating mode of the wireless interface."
    ::= { wirelessInterfaceTableEntry 7 }

wlanInterfaceTableBand OBJECT-TYPE
	SYNTAX INTEGER
	{
		dot11a(1),
		dot11b(2),
		dot11g(3)
	}
	MAX-ACCESS read-create
    	STATUS current
    	DESCRIPTION
	"The Operating band of the wireless interface."
    ::= { wirelessInterfaceTableEntry 8 }


wlanInterfaceTableEssid OBJECT-TYPE
     SYNTAX DisplayString (SIZE (0..32))
    MAX-ACCESS read-create
    STATUS current
    DESCRIPTION
	"The Essid of the wireless interface table entry."
	DEFVAL { "Nil" }
    ::= { wirelessInterfaceTableEntry 9 }

wlanInterfaceTableFreq OBJECT-TYPE
    SYNTAX Integer32 (0..65536)
    MAX-ACCESS read-create
    STATUS current
    DESCRIPTION
	"The operating frequency of the wireless interface."
    ::= { wirelessInterfaceTableEntry 10 }

wlanInterfaceTableMac OBJECT-TYPE
    SYNTAX MacAddress
    MAX-ACCESS read-create
    STATUS current
    DESCRIPTION
	"The hardware address of the interface."
    ::= { wirelessInterfaceTableEntry 11 }

wlanInterfaceTableSecurity OBJECT-TYPE
     SYNTAX INTEGER
    {
	open(1),
	wep(2),
	wpa1(3),
	aes(4),
	wpa2(5),
	wpa1n2(6)
    }
    MAX-ACCESS read-create
    STATUS current
    DESCRIPTION
	"The security mode of the wireless interface entry."
    DEFVAL { open }
    ::= { wirelessInterfaceTableEntry 12 }

wlanInterfaceTableWpaType OBJECT-TYPE
     SYNTAX INTEGER
    {
	tkip(1),
	aes(2)
    }
    MAX-ACCESS read-create
    STATUS current
    DESCRIPTION
	"The WPA Type of the wireless interface using."
     DEFVAL { tkip }
    ::= { wirelessInterfaceTableEntry 13 }

wlanInterfaceTableDot1x OBJECT-TYPE
     SYNTAX INTEGER
    {
	true(1),
	false(2)
    }
    MAX-ACCESS read-create
    STATUS current
    DESCRIPTION
	"Enable the radius server as authenticator for the current wireless interface entry."
    DEFVAL { false }
    ::= { wirelessInterfaceTableEntry 14 }

wlanInterfaceTableEncryptionKey OBJECT-TYPE
    SYNTAX OCTET STRING (SIZE (0..64))
    MAX-ACCESS read-create
    STATUS current
    DESCRIPTION
	"The key used with WEP encryption."
	DEFVAL { "Nil" }
    ::= { wirelessInterfaceTableEntry 15 }

wlanInterfaceTableBroadcastSsid OBJECT-TYPE
	SYNTAX INTEGER
	{
		enable(1),
		disable(2)
    	}
   	MAX-ACCESS read-create
    	STATUS current
    	DESCRIPTION
	"Enable or disable broadcast ESSID."
    DEFVAL { enable }
    ::= { wirelessInterfaceTableEntry 16 }

wlanInterfaceTableBeaconInt OBJECT-TYPE
	SYNTAX Integer32 (20..1000)
	MAX-ACCESS read-create
    STATUS current
    DESCRIPTION
	"The beacon interval in mili seconds."
     DEFVAL { 100 }
    ::= { wirelessInterfaceTableEntry 17 }

wlanInterfaceTableRtsThreshold OBJECT-TYPE
	SYNTAX Integer32 (256..2346)
	MAX-ACCESS read-create
    STATUS current
    DESCRIPTION
	"The RTS Threshold."
     DEFVAL { 2346 }
    ::= { wirelessInterfaceTableEntry 18 }

wlanInterfaceTableFragThreshold OBJECT-TYPE
	SYNTAX Integer32 (1500..2346)
	MAX-ACCESS read-create
    STATUS current
    DESCRIPTION
	"The Fragment Threshold (Even Number only)."
     DEFVAL { 2346 }
    ::= { wirelessInterfaceTableEntry 19 }

wlanInterfaceTableDtimInterval OBJECT-TYPE
	SYNTAX Integer32 (1..256)
	MAX-ACCESS read-create
    STATUS current
    DESCRIPTION
	"The DTIM interval."
     DEFVAL { 1 }
    ::= { wirelessInterfaceTableEntry 20 }

wlanInterfaceTableDatarate OBJECT-TYPE
	SYNTAX Integer32 (0..54)
	MAX-ACCESS read-create
    STATUS current
    DESCRIPTION
	"The Data rate, available choice are auto(0), 1, 2, 5, 6, 9, 11, 12, 18, 24, 36, 48 and 54."
     DEFVAL { 0 }
    ::= { wirelessInterfaceTableEntry 21 }

wlanInterfaceTableDiversity OBJECT-TYPE
	SYNTAX INTEGER
	{
		enable(1),
		disable(2),
		carddefault(3)
    	}
   	MAX-ACCESS read-create
    	STATUS current
    	DESCRIPTION
	"Select to enable or disable the diversity of the antenna."
    DEFVAL { carddefault }
    ::= { wirelessInterfaceTableEntry 22 }

wlanInterfaceTableTxAntenna OBJECT-TYPE
	SYNTAX INTEGER
	{
		diversity(0),
		port1(1),
		port2(2),
		carddefault(3)
    	}
   	MAX-ACCESS read-create
    	STATUS current
    	DESCRIPTION
	"Select the type of the transmission antenna."
    DEFVAL { carddefault }
    ::= { wirelessInterfaceTableEntry 23 }


wlanInterfaceTableRxAntenna OBJECT-TYPE
	SYNTAX INTEGER
	{
		diversity(0),
		port1(1),
		port2(2),
		carddefault(3)
    	}
   	MAX-ACCESS read-create
    	STATUS current
    	DESCRIPTION
	"Select the type of the receiving antenna."
    DEFVAL { carddefault }
    ::= { wirelessInterfaceTableEntry 24 }


wlanInterfaceTableCrntTxPower OBJECT-TYPE
	SYNTAX Integer32 (0..9999)
	MAX-ACCESS read-create
	STATUS current
    	DESCRIPTION
		"The current Transmit Power level in dBm of the device wireless card."
	DEFVAL { 0 }
    ::= { wirelessInterfaceTableEntry 25 }

wlanInterfaceTableTxPower OBJECT-TYPE
	SYNTAX Integer32 (0..9999)
	MAX-ACCESS read-create
	STATUS current
    	DESCRIPTION
		"The Transmit Power level in dBm (0-27) of the wireless card, where 9999 indicates MAX value of the card."
    DEFVAL { 9999 }
    ::= { wirelessInterfaceTableEntry 26 }

wlanInterfaceTableSeperation OBJECT-TYPE
	SYNTAX INTEGER
    {
	enable(1),
	disable(2)
    }
    MAX-ACCESS read-create
    STATUS current
    DESCRIPTION
	"Enable or disable wireless seperation."
    DEFVAL { disable }
    ::= { wirelessInterfaceTableEntry 27 }


wlanInterfaceTableComments OBJECT-TYPE
    SYNTAX DisplayString (SIZE (0..32))
    MAX-ACCESS read-create
    STATUS current
    DESCRIPTION
	"An optional comment associated to entry of the wireless  interface table."
	DEFVAL { "Nil" }
    ::= { wirelessInterfaceTableEntry 28 }

wlanInterfaceTableActive OBJECT-TYPE 
    SYNTAX INTEGER
    {
	enable(1),
	disable(2)
    }
    MAX-ACCESS read-create
    STATUS current
    DESCRIPTION
	"The status of the Wireless interface table entry."
    DEFVAL { enable }
    ::= { wirelessInterfaceTableEntry 29 }

wlanInterfaceTableRowStatus OBJECT-TYPE
   SYNTAX RowStatus
   MAX-ACCESS read-create
   STATUS current
   DESCRIPTION
        "The row status in the Wireless interface table entry"
   ::= { wirelessInterfaceTableEntry 30 }


wirelessFrequencyMeshTable OBJECT-TYPE
    	SYNTAX SEQUENCE OF WirelessFrequencyMeshTableEntry
    	MAX-ACCESS not-accessible
    	STATUS current
    	DESCRIPTION
	"This table display the available frequency channel of the Wireless Mesh interface." 
    ::= { nodeConfigurationWireless 2 }

wirelessFrequencyMeshTableEntry OBJECT-TYPE
    	SYNTAX WirelessFrequencyMeshTableEntry 
   	MAX-ACCESS not-accessible
    	STATUS current
    	DESCRIPTION
	"Represent the entry in the Wireless Mesh frequency table."
    INDEX { wlanFrequencyMeshTableIndex }
    ::= { wirelessFrequencyMeshTable 1 }

WirelessFrequencyMeshTableEntry::=
    SEQUENCE
    {
	wlanFrequencyMeshTableIndex	 	Integer32, 
	wlanFrequencyMeshTableChannel 	Integer32,
	wlanFrequencyMeshTableFrequency 	OCTET STRING,
	wlanFrequencyMeshTableRowStatus	RowStatus 	
    }

wlanFrequencyMeshTableIndex OBJECT-TYPE
    SYNTAX Integer32 (0..100)
    MAX-ACCESS not-accessible
    STATUS current
    DESCRIPTION
	"Specify the index of the Wireless Mesh interface table."
    ::= { wirelessFrequencyMeshTableEntry 1 }

wlanFrequencyMeshTableChannel OBJECT-TYPE
    SYNTAX Integer32 (0..65535)
    MAX-ACCESS read-only
    STATUS current
    DESCRIPTION
	"The channel number of the frequency."
    ::= { wirelessFrequencyMeshTableEntry 2 }

wlanFrequencyMeshTableFrequency OBJECT-TYPE
    SYNTAX OCTET STRING
    MAX-ACCESS read-only
    STATUS current
    DESCRIPTION
	"The frequency level in Giga Hertz."
    ::= { wirelessFrequencyMeshTableEntry 3 }

wlanFrequencyMeshTableRowStatus OBJECT-TYPE
   SYNTAX RowStatus
   MAX-ACCESS read-only
   STATUS current
   DESCRIPTION
        "The row status in the Wireless Mesh frequency table entry"
   ::= { wirelessFrequencyMeshTableEntry 4 }

wirelessFrequencyAp0Table OBJECT-TYPE
    	SYNTAX SEQUENCE OF WirelessFrequencyAp0TableEntry
    	MAX-ACCESS not-accessible
    	STATUS current
    	DESCRIPTION
	"This table display the available frequency channel of the wireless access point radio 1 card." 
    ::= { nodeConfigurationWireless 3 }

wirelessFrequencyAp0TableEntry OBJECT-TYPE
    	SYNTAX WirelessFrequencyAp0TableEntry 
   	MAX-ACCESS not-accessible
    	STATUS current
    	DESCRIPTION
	"Represent the entry in the Wireless radio 1 frequency table."
    INDEX { wlanFrequencyAp0TableIndex }
    ::= { wirelessFrequencyAp0Table 1 }

WirelessFrequencyAp0TableEntry::=
    SEQUENCE
    {
	wlanFrequencyAp0TableIndex	 	Integer32, 
	wlanFrequencyAp0TableChannel 		Integer32,
	wlanFrequencyAp0TableFrequency 	OCTET STRING,
	wlanFrequencyAp0TableRowStatus	RowStatus 	
    }

wlanFrequencyAp0TableIndex OBJECT-TYPE
    SYNTAX Integer32 (0..100)
    MAX-ACCESS not-accessible
    STATUS current
    DESCRIPTION
	"Specify the index of the Wireless radio 1 interface table."
    ::= { wirelessFrequencyAp0TableEntry 1 }

wlanFrequencyAp0TableChannel OBJECT-TYPE
    SYNTAX Integer32 (0..65535)
    MAX-ACCESS read-only
    STATUS current
    DESCRIPTION
	"The channel number of the frequency."
    ::= { wirelessFrequencyAp0TableEntry 2 }

wlanFrequencyAp0TableFrequency OBJECT-TYPE
    SYNTAX OCTET STRING
    MAX-ACCESS read-only
    STATUS current
    DESCRIPTION
	"The frequency level in Giga Hertz."
    ::= { wirelessFrequencyAp0TableEntry 3 }

wlanFrequencyAp0TableRowStatus OBJECT-TYPE
   SYNTAX RowStatus
   MAX-ACCESS read-only
   STATUS current
   DESCRIPTION
        "The row status in the Wireless radio 1 frequency table entry"
   ::= { wirelessFrequencyAp0TableEntry 4 }

wirelessFrequencyAp1Table OBJECT-TYPE
    	SYNTAX SEQUENCE OF WirelessFrequencyAp1TableEntry
    	MAX-ACCESS not-accessible
    	STATUS current
    	DESCRIPTION
	"This table display the available frequency channel of the wireless access point radio 2 (if exist)." 
    ::= { nodeConfigurationWireless 4 }

wirelessFrequencyAp1TableEntry OBJECT-TYPE
    	SYNTAX WirelessFrequencyAp1TableEntry 
   	MAX-ACCESS not-accessible
    	STATUS current
    	DESCRIPTION
	"Represent the entry in the Wireless radio 2 frequency table."
    INDEX { wlanFrequencyAp1TableIndex }
    ::= { wirelessFrequencyAp1Table 1 }

WirelessFrequencyAp1TableEntry::=
    SEQUENCE
    {
	wlanFrequencyAp1TableIndex	 	Integer32, 
	wlanFrequencyAp1TableChannel 		Integer32,
	wlanFrequencyAp1TableFrequency 	OCTET STRING,
	wlanFrequencyAp1TableRowStatus	RowStatus 	
    }

wlanFrequencyAp1TableIndex OBJECT-TYPE
    SYNTAX Integer32 (0..100)
    MAX-ACCESS not-accessible
    STATUS current
    DESCRIPTION
	"Specify the index of the Wireless radio 2 interface table."
    ::= { wirelessFrequencyAp1TableEntry 1 }

wlanFrequencyAp1TableChannel OBJECT-TYPE
    SYNTAX Integer32 (0..65535)
    MAX-ACCESS read-only
    STATUS current
    DESCRIPTION
	"The channel number of the frequency."
    ::= { wirelessFrequencyAp1TableEntry 2 }

wlanFrequencyAp1TableFrequency OBJECT-TYPE
    SYNTAX OCTET STRING
    MAX-ACCESS read-only
    STATUS current
    DESCRIPTION
	"The frequency level in Giga Hertz."
    ::= { wirelessFrequencyAp1TableEntry 3 }

wlanFrequencyAp1TableRowStatus OBJECT-TYPE
   SYNTAX RowStatus
   MAX-ACCESS read-only
   STATUS current
   DESCRIPTION
        "The row status in the Wireless radio 2 frequency table entry"
   ::= { wirelessFrequencyAp1TableEntry 4 }


-- ============ | nodeConfigurationVlan | =================

vlanInterfaceTable OBJECT-TYPE
    	SYNTAX SEQUENCE OF VlanInterfaceTableEntry
    	MAX-ACCESS not-accessible
    	STATUS current
    	DESCRIPTION
	"This table contains the information of the VLAN interfaces." 
    ::= { nodeConfigurationVlan 1 }

vlanInterfaceTableEntry OBJECT-TYPE
    	SYNTAX VlanInterfaceTableEntry 
   	MAX-ACCESS not-accessible
    	STATUS current
    	DESCRIPTION
	"Represent the entry in the VLAN interface table."
    INDEX { vlanInterfaceTableIndex }
    ::= { vlanInterfaceTable 1 }

VlanInterfaceTableEntry::=
    SEQUENCE
    {
	vlanInterfaceTableIndex	 	Integer32, 
	vlanInterfaceTableName	 	OCTET STRING,
	vlanInterfaceTableBase 	 	OCTET STRING,
	vlanInterfaceTableMac	 	MacAddress,
	vlanInterfaceTableId		Integer32,
	vlanInterfaceTableBridge	OCTET STRING,
	vlanInterfaceTableBridgeCost 	Integer32, 
	vlanInterfaceTableBridgePrio 	Integer32,
        vlanInterfaceTableComments 	DisplayString, 
	vlanInterfaceTableActive 	INTEGER,
	vlanInterfaceTableRowStatus	RowStatus 	
    }

vlanInterfaceTableIndex OBJECT-TYPE
    SYNTAX Integer32 (0..32)
    MAX-ACCESS not-accessible
    STATUS current
    DESCRIPTION
	"Specify the index of the VLAN interface table."
    ::= { vlanInterfaceTableEntry 1 }

vlanInterfaceTableName OBJECT-TYPE
    SYNTAX OCTET STRING (SIZE (0..32))
    MAX-ACCESS read-create
    STATUS current
    DESCRIPTION
	"The name of the VLAN interface."
	DEFVAL { "Nil" }
    ::= { vlanInterfaceTableEntry 2 }

vlanInterfaceTableBase OBJECT-TYPE
    SYNTAX OCTET STRING (SIZE (0..32))
    MAX-ACCESS read-create
    STATUS current
    DESCRIPTION
	"The base name of the VLAN interface."	
	DEFVAL { "Nil" }
    ::= { vlanInterfaceTableEntry 3 }

vlanInterfaceTableMac OBJECT-TYPE
    SYNTAX MacAddress
    MAX-ACCESS read-create
    STATUS current
    DESCRIPTION
	"The hardware address of the interface."
    ::= { vlanInterfaceTableEntry 4 }

vlanInterfaceTableId OBJECT-TYPE 
    SYNTAX Integer32
    MAX-ACCESS read-create
    STATUS current
    DESCRIPTION
	"The VLAN ID for the table entry."
   ::= { vlanInterfaceTableEntry 5 }


vlanInterfaceTableBridge OBJECT-TYPE
    SYNTAX OCTET STRING (SIZE (0..32))
    MAX-ACCESS read-create
    STATUS current
    DESCRIPTION
	"The bridge interface that the current VLAN interface is attached to."
		DEFVAL { "Nil" }
    ::= { vlanInterfaceTableEntry 6 }

vlanInterfaceTableBridgeCost OBJECT-TYPE
    SYNTAX Integer32 (0..65536)
    MAX-ACCESS read-create
    STATUS current
    DESCRIPTION
	"The cost of the bridge interface that the current VLAN interface is attached to."
    DEFVAL { 100 }
    ::= { vlanInterfaceTableEntry 7 }

vlanInterfaceTableBridgePrio OBJECT-TYPE
    SYNTAX Integer32 (0..65536)
    MAX-ACCESS read-create
    STATUS current
    DESCRIPTION
	"The priority of the bridge interface that the current VLAN interface is attached to."
    DEFVAL { 100 }
    ::= { vlanInterfaceTableEntry 8 }

vlanInterfaceTableComments OBJECT-TYPE
    SYNTAX DisplayString (SIZE (0..32))
    MAX-ACCESS read-create
    STATUS current
    DESCRIPTION
	"An optional comment associated to entry of the VLAN interface table."
	DEFVAL { "Nil" }
    ::= { vlanInterfaceTableEntry 9 }

vlanInterfaceTableActive OBJECT-TYPE 
    SYNTAX INTEGER
    {
	enable(1),
	disable(2)
    }
    MAX-ACCESS read-create
    STATUS current
    DESCRIPTION
	"The status of the VLAN interface table entry."
    DEFVAL { enable }
    ::= { vlanInterfaceTableEntry 10 }

vlanInterfaceTableRowStatus OBJECT-TYPE
   SYNTAX RowStatus
   MAX-ACCESS read-create
   STATUS current
   DESCRIPTION
        "The row status in the VLAN interface table entry"
   ::= { vlanInterfaceTableEntry 11 }


-- ============== | nodeConfigurationBridge | ==================

bridgeInterfaceTable OBJECT-TYPE
    	SYNTAX SEQUENCE OF BridgeInterfaceTableEntry
    	MAX-ACCESS not-accessible
    	STATUS current
    	DESCRIPTION
	"This table contains the information of the bridge interfaces." 
    ::= { nodeConfigurationBridge 1 }

bridgeInterfaceTableEntry OBJECT-TYPE
    	SYNTAX BridgeInterfaceTableEntry 
   	MAX-ACCESS not-accessible
    	STATUS current
    	DESCRIPTION
	"Represent the entry in the Bridge Interface table."
    INDEX { bridgeInterfaceTableIndex }
    ::= { bridgeInterfaceTable 1 }

BridgeInterfaceTableEntry::=
    SEQUENCE
    {
	bridgeInterfaceTableIndex	 	Integer32, 
	bridgeInterfaceTableName	 	OCTET STRING,
	bridgeInterfaceTableMac	 	MacAddress,
	bridgeInterfaceTableAge	 	Integer32, 
	bridgeInterfaceTablePrio	 	Integer32,
	bridgeInterfaceTableFwdDelay 	Integer32, 
	bridgeInterfaceTableHelloInt	Integer32,
	bridgeInterfaceTableMaxAge	Integer32, 
	bridgeInterfaceTableStp	 	INTEGER,
      bridgeInterfaceTableComments 	DisplayString, 
	bridgeInterfaceTableActive 	INTEGER,
	bridgeInterfaceTableRowStatus	RowStatus 	
    }

bridgeInterfaceTableIndex OBJECT-TYPE
    SYNTAX Integer32 (0..16)
    MAX-ACCESS not-accessible
    STATUS current
    DESCRIPTION
	"Specify the index of the Bridge interface table."
    ::= { bridgeInterfaceTableEntry 1 }

bridgeInterfaceTableName OBJECT-TYPE
    SYNTAX OCTET STRING (SIZE (0..32))
    MAX-ACCESS read-create
    STATUS current
    DESCRIPTION
	"The name of the Bridge interface."
	DEFVAL { "Nil" }
    ::= { bridgeInterfaceTableEntry 2 }

bridgeInterfaceTableMac OBJECT-TYPE
    SYNTAX MacAddress
    MAX-ACCESS read-create
    STATUS current
    DESCRIPTION
	"The hardware address of the interface."
    ::= { bridgeInterfaceTableEntry 3 }

bridgeInterfaceTableAge OBJECT-TYPE
    SYNTAX Integer32 (0..65536)
    MAX-ACCESS read-create
    STATUS current
    DESCRIPTION
	"The bridge ageing time."
    DEFVAL { 300 }
    ::= { bridgeInterfaceTableEntry 4 }

bridgeInterfaceTablePrio OBJECT-TYPE
    SYNTAX Integer32 (0..65536)
    MAX-ACCESS read-create
    STATUS current
    DESCRIPTION
	"The priority of the bridge interface."
    DEFVAL { 32768 }
    ::= { bridgeInterfaceTableEntry 5 }

bridgeInterfaceTableFwdDelay OBJECT-TYPE
    SYNTAX Integer32 (0..65536)
    MAX-ACCESS read-create
    STATUS current
    DESCRIPTION
	"The bridge forwarding delay."
    DEFVAL { 15 }
    ::= { bridgeInterfaceTableEntry 6 }

bridgeInterfaceTableHelloInt OBJECT-TYPE
    SYNTAX Integer32 (0..65536)
    MAX-ACCESS read-create
    STATUS current
    DESCRIPTION
	"The Hello Interval of the bridge interface."
    DEFVAL { 2 }
    ::= { bridgeInterfaceTableEntry 7 }

bridgeInterfaceTableMaxAge OBJECT-TYPE
    SYNTAX Integer32 (0..65536)
    MAX-ACCESS read-create
    STATUS current
    DESCRIPTION
	"The bridge maximum message age."
    DEFVAL { 20 }
	::= { bridgeInterfaceTableEntry 8 }

bridgeInterfaceTableStp OBJECT-TYPE 
    SYNTAX INTEGER
    {
	on(1),
	off(2)
    }
    MAX-ACCESS read-create
    STATUS current
    DESCRIPTION
	"Turn on or off the Spanning Tree Protocol."
    DEFVAL { 2 }
	::= { bridgeInterfaceTableEntry 9 }


bridgeInterfaceTableComments OBJECT-TYPE
    SYNTAX DisplayString (SIZE (0..32))
    MAX-ACCESS read-create
    STATUS current
    DESCRIPTION
	"An optional comment associated to entry of the bridge interface table."
	DEFVAL { "Nil" }
    ::= { bridgeInterfaceTableEntry 10 }

bridgeInterfaceTableActive OBJECT-TYPE 
    SYNTAX INTEGER
    {
	enable(1),
	disable(2)
    }
    MAX-ACCESS read-create
    STATUS current
    DESCRIPTION
	"The status of the bridge interface table entry."
    DEFVAL { enable }
    ::= { bridgeInterfaceTableEntry 11 }

bridgeInterfaceTableRowStatus OBJECT-TYPE
   SYNTAX RowStatus
   MAX-ACCESS read-create
   STATUS current
   DESCRIPTION
        "The row status in the Bridge interface table entry."
   ::= { bridgeInterfaceTableEntry 12 }


-- =============== | nodeConfigurationIpaddress | ================

ipAddressesTable OBJECT-TYPE
    	SYNTAX SEQUENCE OF IpAddressesTableEntry
    	MAX-ACCESS not-accessible
    	STATUS current
    	DESCRIPTION
	"This table contains the information of the IP Addresses." 
    ::= { nodeConfigurationIpaddress 1 }

ipAddressesTableEntry OBJECT-TYPE
    	SYNTAX IpAddressesTableEntry 
   	MAX-ACCESS not-accessible
    	STATUS current
    	DESCRIPTION
	"Represent the entry in the IP Address Table."
    INDEX { ipAddressesTableIndex }
    ::= { ipAddressesTable 1 }

IpAddressesTableEntry::=
    SEQUENCE
    {
	ipAddressesTableIndex 	 	Integer32, 
	ipAddressesTableIface		OCTET STRING,
	ipAddressesTableType		INTEGER,
	ipAddressesTableIp		IpAddress,
	ipAddressesTableNetmask		IpAddress,
	ipAddressesTableBroadcast		IpAddress,
	ipAddressesTableGateway		IpAddress,
	ipAddressesTableRouted		INTEGER,
	ipAddressesTableComments 	DisplayString, 
	ipAddressesTableActive 	 	INTEGER,
	ipAddressesTableRowStatus	RowStatus 	
    }

ipAddressesTableIndex OBJECT-TYPE
    SYNTAX Integer32 (0..64)
    MAX-ACCESS not-accessible
    STATUS current
    DESCRIPTION
	"Specify the index of the IP Address table."
    ::= { ipAddressesTableEntry 1 }

ipAddressesTableIface OBJECT-TYPE
    SYNTAX OCTET STRING (SIZE (0..32))
    MAX-ACCESS read-create
    STATUS current
    DESCRIPTION
	"The name of the interface."
	DEFVAL { "Nil" }
    ::= { ipAddressesTableEntry 2 }

ipAddressesTableType OBJECT-TYPE 
    SYNTAX INTEGER
    {
	static(1),
	dhcp(2),
	pppoe(3),
	ipalias(4)
    }
    MAX-ACCESS read-create
    STATUS current
    DESCRIPTION
	"The type of IP Address: Static or DHCP."
    DEFVAL { dhcp }
    ::= { ipAddressesTableEntry 3 }

ipAddressesTableIp OBJECT-TYPE
    SYNTAX IpAddress
    MAX-ACCESS read-create
    STATUS current
    DESCRIPTION
	"The IP Address."
    ::= { ipAddressesTableEntry 4}

ipAddressesTableNetmask OBJECT-TYPE
    SYNTAX IpAddress
    MAX-ACCESS read-create
    STATUS current
    DESCRIPTION
	"The Netmask for IP Address."
    ::= { ipAddressesTableEntry 5 }

ipAddressesTableBroadcast OBJECT-TYPE
    SYNTAX IpAddress
    MAX-ACCESS read-create
    STATUS current
    DESCRIPTION
	"The Broadcast IP for the IP Address."
    ::= { ipAddressesTableEntry 6 }

ipAddressesTableGateway OBJECT-TYPE
    SYNTAX IpAddress
    MAX-ACCESS read-create
    STATUS current
    DESCRIPTION
	"The Gateway IP for the IP Address."
    ::= { ipAddressesTableEntry 7 }

ipAddressesTableRouted OBJECT-TYPE 
    SYNTAX INTEGER
    {
	routable(1),
	nat(2)
    }
    MAX-ACCESS read-create
    STATUS current
    DESCRIPTION 
	"The type of the IP Address table entry."
    DEFVAL { routable }
     ::= { ipAddressesTableEntry 8 }


ipAddressesTableComments OBJECT-TYPE
    SYNTAX DisplayString (SIZE (0..32))
    MAX-ACCESS read-create
    STATUS current
    DESCRIPTION
	"An optional comment associated to entry of the IP Address table."	
	DEFVAL { "Nil" }
    ::= { ipAddressesTableEntry 9 }

ipAddressesTableActive OBJECT-TYPE 
    SYNTAX INTEGER
    {
	enable(1),
	disable(2)
    }
    MAX-ACCESS read-create
    STATUS current
    DESCRIPTION 
	"The status of the IP Address table entry."
    DEFVAL { enable }
    ::= { ipAddressesTableEntry 10 }

ipAddressesTableRowStatus OBJECT-TYPE
   SYNTAX RowStatus
   MAX-ACCESS read-create
   STATUS current
   DESCRIPTION
        "The row status in the IP Address table entry."
   ::= { ipAddressesTableEntry 11 }


-- ================== | nodeConfigurationNetwork | ====================

networkPrimaryDns OBJECT-TYPE
	SYNTAX IpAddress
	MAX-ACCESS read-write
	STATUS current
	DESCRIPTION
	"The primary DNS Server IP address"
     ::= { nodeConfigurationNetwork 1 }

networkSecondaryDns OBJECT-TYPE
	SYNTAX IpAddress
	MAX-ACCESS read-write
	STATUS current
	DESCRIPTION
	"The secondary DNS Server IP address"
     ::= { nodeConfigurationNetwork 2 }

networkDomain OBJECT-TYPE
	SYNTAX OCTET STRING (SIZE(0..32))
	MAX-ACCESS read-write
	STATUS current
	DESCRIPTION
	"The DNS Server Domain name"
	DEFVAL { "Nil" }
     ::= { nodeConfigurationNetwork 3 }


-- ============= | nodeConfigurationSyslog | ======================

syslogActive OBJECT-TYPE 
    SYNTAX INTEGER
    {
	enable(1),
	disable(2)
    }
    MAX-ACCESS read-write
    STATUS current
    DESCRIPTION 
	"Enable/Disable the syslog service."
    DEFVAL { enable }
    ::= { nodeConfigurationSyslog 1 }

syslogKlog OBJECT-TYPE 
    SYNTAX INTEGER
    {
	enable(1),
	disable(2)
    }
    MAX-ACCESS read-write
    STATUS current
    DESCRIPTION 
	"Enable/Disable the Klog service."
    DEFVAL { disable }
    ::= { nodeConfigurationSyslog 2 }

syslogLevel OBJECT-TYPE 
    SYNTAX Integer32 (0..7)
    MAX-ACCESS read-write
    STATUS current
    DESCRIPTION 
	"Define the level of the syslog service."
	DEFVAL { 5 }
    ::= { nodeConfigurationSyslog 3 }

syslogRemoteActive OBJECT-TYPE 
    SYNTAX INTEGER
    {
	enable(1),
	disable(2)
    }
    MAX-ACCESS read-write
    STATUS current
    DESCRIPTION 
	"Enable/Disable the remote syslog server."
    DEFVAL { disable }
    ::= { nodeConfigurationSyslog 4 }

syslogRemoteAddress OBJECT-TYPE
    SYNTAX OCTET STRING (SIZE(0..512))
    MAX-ACCESS read-write
    STATUS current
    DESCRIPTION
	"The remote syslog server name/address"
	DEFVAL { "Nil" }
     ::= { nodeConfigurationSyslog 5 }


-- ==================== | nodeConfigurationOlsr | ======================

olsrActive OBJECT-TYPE
     SYNTAX INTEGER
    {
	enable(1),
	disable(2)
    }
    MAX-ACCESS read-write
    STATUS current
    DESCRIPTION 
	"Enable/Disable the OLSR service."
    DEFVAL { enable }
    ::= { nodeConfigurationOlsr 1 }

olsrTosValue OBJECT-TYPE
    SYNTAX Integer32 (0..16)
    MAX-ACCESS read-write
    STATUS current
    DESCRIPTION 
	"Display the value for the IP header of control traffic."
    DEFVAL { 16 }	
    ::= { nodeConfigurationOlsr 2 }

olsrWillingnessActive OBJECT-TYPE
    SYNTAX INTEGER
    {
	  enable(1),
	  disable(2)
    } 
    MAX-ACCESS read-write
    STATUS current
    DESCRIPTION 
	 "Display the option of automatic willingness calculation."
    DEFVAL { enable }	
    ::= { nodeConfigurationOlsr 3 }

olsrWillingness OBJECT-TYPE
    SYNTAX Integer32 (0..7)
    MAX-ACCESS read-write
    STATUS current
    DESCRIPTION 
	"Display the willingness value."
    DEFVAL { 4 }	
    ::= { nodeConfigurationOlsr 4 }

olsrHysteresisActive OBJECT-TYPE
    SYNTAX INTEGER
    {
	  enable(1),
	  disable(2)
    } 
    MAX-ACCESS read-write
    STATUS current
    DESCRIPTION 
	"Display the option of hysteresis."
    DEFVAL { disable }	
    ::= { nodeConfigurationOlsr 5 }

olsrHysteresisScaling OBJECT-TYPE
    SYNTAX OCTET STRING (SIZE(0..32))
    MAX-ACCESS read-write
    STATUS current
    DESCRIPTION 
	"Display the scale of hysteresis parameter (range: 0 to 1)."
    DEFVAL { "0.50" }	
    ::= { nodeConfigurationOlsr 6 }

olsrHysteresisThrHigh OBJECT-TYPE
    SYNTAX OCTET STRING (SIZE(0..32))
    MAX-ACCESS read-write
    STATUS current
    DESCRIPTION 
	"Display the value of high threshold (range: 0 to 1)."
    DEFVAL { "0.80" }	
    ::= { nodeConfigurationOlsr 7 }

olsrHysteresisThrLow OBJECT-TYPE
    SYNTAX OCTET STRING (SIZE(0..32))
    MAX-ACCESS read-write
    STATUS current
    DESCRIPTION 
	"Display the value of low threshold (range: 0 to 1)."
    DEFVAL { "0.30" }	
    ::= { nodeConfigurationOlsr 8 }

olsrLinkQualityType OBJECT-TYPE
    SYNTAX INTEGER
    {
	disable(0),
	useformpr(1),
	useformprandrouting(2)
    } 
    MAX-ACCESS read-write
    STATUS current
    DESCRIPTION 
	"Display the option of link quality type."
    DEFVAL { disable }	
    ::= { nodeConfigurationOlsr 9 }

olsrLinkQualitySize OBJECT-TYPE
    SYNTAX Integer32 (3..128)
    MAX-ACCESS read-write
    STATUS current
    DESCRIPTION 
	"Display the link quality window size."
    DEFVAL { 10 }	
    ::= { nodeConfigurationOlsr 10 }

olsrPollRate OBJECT-TYPE
    SYNTAX OCTET STRING (SIZE(0..32))
    MAX-ACCESS read-write
    STATUS current
    DESCRIPTION 
	"Display the polling rate in milliseconds."
    DEFVAL { "0.05" }	
    ::= { nodeConfigurationOlsr 11 }

olsrTcType OBJECT-TYPE
    SYNTAX INTEGER
    {
	sendonlymprselectors(0),
	sendonlymprselectorsandmprs(1),
	sendallneighbors(2)
    }
    MAX-ACCESS read-write
    STATUS current
    DESCRIPTION 
	"Display the option of TC type."
    DEFVAL { sendonlymprselectors }	
    ::= { nodeConfigurationOlsr 12 }

olsrMpr OBJECT-TYPE
    SYNTAX INTEGER (1..20)
    MAX-ACCESS read-write
    STATUS current
    DESCRIPTION 
	"Display the value of how many MPRs a node should try to select to reach every 2 hop neighbour."
    DEFVAL { 1 }	
    ::= { nodeConfigurationOlsr 13 }


olsrSharedKey OBJECT-TYPE
    SYNTAX DisplayString (SIZE(0..32))
    MAX-ACCESS read-write
    STATUS current
    DESCRIPTION
	"The shared key for OLSR"
	DEFVAL { "Nil" }
      ::= { nodeConfigurationOlsr 14 }

olsrInterfaceTable OBJECT-TYPE
    	SYNTAX SEQUENCE OF OlsrInterfaceTableEntry
    	MAX-ACCESS not-accessible
    	STATUS current
    	DESCRIPTION
	"This table contains the information of the OLSR interfaces." 
    ::= { nodeConfigurationOlsr 15 }

olsrInterfaceTableEntry OBJECT-TYPE
    	SYNTAX OlsrInterfaceTableEntry 
   	MAX-ACCESS not-accessible
    	STATUS current
    	DESCRIPTION
	"Represent the entry in the OLSR Interface table."
    INDEX { olsrInterfaceTableIndex }
    ::= { olsrInterfaceTable 1 }

OlsrInterfaceTableEntry::=
    SEQUENCE
    {
	olsrInterfaceTableIndex	 		Integer32, 
	olsrInterfaceTableIface	 		OCTET STRING,
	olsrInterfaceTableHelloInterval	OCTET STRING,
	olsrInterfaceTableHelloValidity	OCTET STRING,
	olsrInterfaceTableTcInterval		OCTET STRING,
	olsrInterfaceTableTcValidity		OCTET STRING,
	olsrInterfaceTableMidInterval		OCTET STRING,
	olsrInterfaceTableMidValidity		OCTET STRING,
	olsrInterfaceTableHnaInterval		OCTET STRING,
	olsrInterfaceTableHnaValidity		OCTET STRING,
      olsrInterfaceTableComments 		DisplayString, 
	olsrInterfaceTableActive 		INTEGER,
	olsrInterfaceTableRowStatus		RowStatus 	
    }

olsrInterfaceTableIndex OBJECT-TYPE
    SYNTAX Integer32 (0..10)
    MAX-ACCESS not-accessible
    STATUS current
    DESCRIPTION
	"Specify the index of the OLSR interface table."
    ::= { olsrInterfaceTableEntry 1 }

olsrInterfaceTableIface OBJECT-TYPE
    SYNTAX OCTET STRING (SIZE (0..32))
    MAX-ACCESS read-create
    STATUS current
    DESCRIPTION
	"The name of the OLSR  interface."
    ::= { olsrInterfaceTableEntry 2 }

olsrInterfaceTableHelloInterval OBJECT-TYPE
    SYNTAX OCTET STRING (SIZE (0..32))
    MAX-ACCESS read-create
    STATUS current
    DESCRIPTION
	"The hello interval of the OLSR  interface."
    DEFVAL { "2.0" }
    ::= { olsrInterfaceTableEntry 3 }

olsrInterfaceTableHelloValidity OBJECT-TYPE
    SYNTAX OCTET STRING (SIZE (0..32))
    MAX-ACCESS read-create
    STATUS current
    DESCRIPTION
	"The hello validity of the OLSR  interface."
    DEFVAL { "30.0" }
    ::= { olsrInterfaceTableEntry 4 }

olsrInterfaceTableTcInterval OBJECT-TYPE
    SYNTAX OCTET STRING (SIZE (0..32))
    MAX-ACCESS read-create
    STATUS current
    DESCRIPTION
	"The TC interval of the OLSR  interface."
    DEFVAL { "5.0" }
    ::= { olsrInterfaceTableEntry 5 }

olsrInterfaceTableTcValidity OBJECT-TYPE
    SYNTAX OCTET STRING (SIZE (0..32))
    MAX-ACCESS read-create
    STATUS current
    DESCRIPTION
	"The TC validity of the OLSR  interface."
    DEFVAL { "60.0" }
    ::= { olsrInterfaceTableEntry 6 }

olsrInterfaceTableMidInterval OBJECT-TYPE
    SYNTAX OCTET STRING (SIZE (0..32))
    MAX-ACCESS read-create
    STATUS current
    DESCRIPTION
	"The MID interval of the OLSR  interface."
    DEFVAL { "5.0" }
    ::= { olsrInterfaceTableEntry 7 }

olsrInterfaceTableMidValidity OBJECT-TYPE
    SYNTAX OCTET STRING (SIZE (0..32))
    MAX-ACCESS read-create
    STATUS current
    DESCRIPTION
	"The MID validity of the OLSR  interface."
    DEFVAL { "60.0" }
    ::= { olsrInterfaceTableEntry 8 }

olsrInterfaceTableHnaInterval OBJECT-TYPE
    SYNTAX OCTET STRING (SIZE (0..32))
    MAX-ACCESS read-create
    STATUS current
    DESCRIPTION
	"The HNA interval of the OLSR  interface."
    DEFVAL { "5.0" }
    ::= { olsrInterfaceTableEntry 9 }

olsrInterfaceTableHnaValidity OBJECT-TYPE
    SYNTAX OCTET STRING (SIZE (0..32))
    MAX-ACCESS read-create
    STATUS current
    DESCRIPTION
	"The HNA validity of the OLSR  interface."
    DEFVAL { "60.0" }
    ::= { olsrInterfaceTableEntry 10 }


olsrInterfaceTableComments OBJECT-TYPE
    SYNTAX DisplayString (SIZE (0..32))
    MAX-ACCESS read-create
    STATUS current
    DESCRIPTION
	"An optional description regarding the entry of the Olsr Interface table."
    DEFVAL { "none" }
    ::= { olsrInterfaceTableEntry 11 }

olsrInterfaceTableActive OBJECT-TYPE 
    SYNTAX INTEGER
    {
	enable(1),
	disable(2)
    }
    MAX-ACCESS read-create
    STATUS current
    DESCRIPTION 
	"The status of the OLSR Interface table entry."
    DEFVAL { enable }
    ::= { olsrInterfaceTableEntry 12 }

olsrInterfaceTableRowStatus OBJECT-TYPE
   SYNTAX RowStatus
   MAX-ACCESS read-create
   STATUS current
   DESCRIPTION
        "The row status in the OLSR Interface table entry."
   ::= { olsrInterfaceTableEntry 13 }

-- =================== | nodeConfigurationOlsrGW | ================
olsrGatewayTable OBJECT-TYPE
    	SYNTAX SEQUENCE OF OlsrGatewayTableEntry
    	MAX-ACCESS not-accessible
    	STATUS current
    	DESCRIPTION
	"This table contains the OLSR local network gateway." 
    ::= { nodeConfigurationOlsrGW 1 }

olsrGatewayTableEntry OBJECT-TYPE
    	SYNTAX OlsrGatewayTableEntry 
   	MAX-ACCESS not-accessible
    	STATUS current
    	DESCRIPTION
	"Represent the entry in the OLSR Gateway table."
    INDEX { olsrGatewayTableIndex }
    ::= { olsrGatewayTable 1 }

OlsrGatewayTableEntry::=
    SEQUENCE
    {
	olsrGatewayTableIndex	 	Integer32, 
	olsrGatewayTableSubnet	 	IpAddress,
	olsrGatewayTableNetmask		IpAddress,
      olsrGatewayTableComments 	DisplayString, 
	olsrGatewayTableActive 		INTEGER,
	olsrGatewayTableRowStatus	RowStatus 	
    }

olsrGatewayTableIndex OBJECT-TYPE
    SYNTAX Integer32 (0..10)
    MAX-ACCESS not-accessible
    STATUS current
    DESCRIPTION
	"Specify the index of the OLSR gateway table."
    ::= { olsrGatewayTableEntry 1 }

olsrGatewayTableSubnet OBJECT-TYPE
    SYNTAX IpAddress
    MAX-ACCESS read-create
    STATUS current
    DESCRIPTION
	"The Subnet Address of the OLSR gateway entry."
    ::= { olsrGatewayTableEntry 2 }

olsrGatewayTableNetmask OBJECT-TYPE
    SYNTAX IpAddress
    MAX-ACCESS read-create
    STATUS current
    DESCRIPTION
	"The netmask for the subnet above."
    ::= { olsrGatewayTableEntry 3 }

olsrGatewayTableComments OBJECT-TYPE
    SYNTAX DisplayString (SIZE (0..32))
    MAX-ACCESS read-create
    STATUS current
    DESCRIPTION
	"An optional description regarding the entry of the Olsr Gateway table."
    DEFVAL { "none" }
    ::= { olsrGatewayTableEntry 4 }

olsrGatewayTableActive OBJECT-TYPE 
    SYNTAX INTEGER
    {
	enable(1),
	disable(2)
    }
    MAX-ACCESS read-create
    STATUS current
    DESCRIPTION 
	"The status of the OLSR Gateway table entry."
    DEFVAL { enable }
    ::= { olsrGatewayTableEntry 5 }

olsrGatewayTableRowStatus OBJECT-TYPE
   SYNTAX RowStatus
   MAX-ACCESS read-create
   STATUS current
   DESCRIPTION
        "The row status in the OLSR Gateway table entry."
   ::= { olsrGatewayTableEntry 6 }


-- =================== | nodeConfigurationRoute | ==================

routeTable OBJECT-TYPE
    	SYNTAX SEQUENCE OF RouteTableEntry
    	MAX-ACCESS not-accessible
    	STATUS current
    	DESCRIPTION
	"This table contains the information of the Route settings." 
    ::= { nodeConfigurationRoute 1 }

routeTableEntry OBJECT-TYPE
    	SYNTAX RouteTableEntry 
   	MAX-ACCESS not-accessible
    	STATUS current
    	DESCRIPTION
	"Represent the entry in the Route table."
    INDEX { routeTableIndex }
    ::= { routeTable 1 }

RouteTableEntry::=
    SEQUENCE
    {
	routeTableIndex	 	Integer32, 
	routeTableSubnet	IpAddress,
	routeTableNetmask	IpAddress,
	routeTableGateway	IpAddress,
	routeTableDevice		OCTET STRING,
	routeTableDirect		INTEGER,
        	routeTableComments 	DisplayString, 
	routeTableActive 	INTEGER,
	routeTableRowStatus	RowStatus 	
    }

routeTableIndex OBJECT-TYPE
    SYNTAX Integer32 (0..128)
    MAX-ACCESS not-accessible
    STATUS current
    DESCRIPTION
	"Specify the index of the routing table."
    ::= { routeTableEntry 1 }

routeTableSubnet OBJECT-TYPE
    SYNTAX IpAddress
    MAX-ACCESS read-create
    STATUS current
    DESCRIPTION
	"The destination Subnet of the routing rule."
    ::= { routeTableEntry 2 }

routeTableNetmask OBJECT-TYPE
    SYNTAX IpAddress
    MAX-ACCESS read-create
    STATUS current
    DESCRIPTION
	"The Netmask for the destination subnet of the routing rule."
    ::= { routeTableEntry 3 }

routeTableGateway OBJECT-TYPE
    SYNTAX IpAddress
    MAX-ACCESS read-create
    STATUS current
    DESCRIPTION
	"The next hop gateway IP Address."
    ::= { routeTableEntry 4 }

routeTableDevice OBJECT-TYPE
    SYNTAX OCTET STRING (SIZE(0..32))
    MAX-ACCESS read-create
    STATUS current
    DESCRIPTION
	"The Device Interface Name."
    ::= { routeTableEntry 5 }

routeTableDirect OBJECT-TYPE
      SYNTAX INTEGER
      {
	direct(1),
	indirect(2)
      }
    MAX-ACCESS read-create
    STATUS current
    DESCRIPTION
	"The type of routing: direct or indirect."
    DEFVAL { direct }
    ::= { routeTableEntry 6 }

routeTableComments OBJECT-TYPE
    SYNTAX DisplayString (SIZE (0..32))
    MAX-ACCESS read-create
    STATUS current
    DESCRIPTION
	"An optional description regarding the entry of the Routing table."
	DEFVAL { "Nil" }
    ::= { routeTableEntry 7 }

routeTableActive OBJECT-TYPE 
    SYNTAX INTEGER
    {
	enable(1),
	disable(2)
    }
    MAX-ACCESS read-create
    STATUS current
    DESCRIPTION 
	"The status of the Routing table entry."
    DEFVAL { enable }
    ::= { routeTableEntry 8 }

routeTableRowStatus OBJECT-TYPE
   SYNTAX RowStatus
   MAX-ACCESS read-create
   STATUS current
   DESCRIPTION
        "The row status in the Routing table entry."
   ::= { routeTableEntry 9 }


-- =================== | nodeConfigurationNtp | =====================

ntpActive  OBJECT-TYPE
       SYNTAX INTEGER
       {
	enable(1),
	disable(2)
       }
       MAX-ACCESS read-write
       STATUS current
       DESCRIPTION
	"Enable/Disable the NTP service of the device."
       DEFVAL { enable }
       ::= { nodeConfigurationNtp 1 }

ntpTimezone OBJECT-TYPE
      SYNTAX DisplayString
      MAX-ACCESS read-write
      STATUS current
      DESCRIPTION
	"NTP Timezone."
	DEFVAL { "337" }	
       ::= { nodeConfigurationNtp 2 }

ntpTable OBJECT-TYPE
    	SYNTAX SEQUENCE OF NtpTableEntry
    	MAX-ACCESS not-accessible
    	STATUS current
    	DESCRIPTION
	"This is the Network Time Protocol servers table." 
    ::= { nodeConfigurationNtp 3 }

ntpTableEntry OBJECT-TYPE
    	SYNTAX NtpTableEntry 
   	MAX-ACCESS not-accessible
    	STATUS current
    	DESCRIPTION
	"Represent the entry in the NTP table."
    INDEX { ntpTableIndex }
    ::= { ntpTable 1 }

NtpTableEntry::=
    SEQUENCE
    {
	ntpTableIndex	 	Integer32, 
	ntpTableServer		OCTET STRING,
	ntpTableMinPoll		Integer32,
	ntpTableMaxPoll		Integer32,
        ntpTableComments 	DisplayString, 
	ntpTableActive 		INTEGER,
	ntpTableRowStatus	RowStatus 	
    }

ntpTableIndex OBJECT-TYPE
    SYNTAX Integer32 (0..8)
    MAX-ACCESS not-accessible
    STATUS current
    DESCRIPTION
	"Specify the index of the NTP table."
    ::= { ntpTableEntry 1 }

ntpTableServer OBJECT-TYPE
    SYNTAX OCTET STRING (SIZE(0..32))
    MAX-ACCESS read-create
    STATUS current
    DESCRIPTION
	"The name of the NTP Server."
	DEFVAL { "Nil" }
    ::= { ntpTableEntry 2 }

ntpTableMinPoll OBJECT-TYPE
    SYNTAX Integer32 (0..10)
    MAX-ACCESS read-create
    STATUS current
    DESCRIPTION
	"The minimum poll time in seconds."
    ::= { ntpTableEntry 3 }

ntpTableMaxPoll OBJECT-TYPE
    SYNTAX  Integer32 (0..100)
    MAX-ACCESS read-create
    STATUS current
    DESCRIPTION
	"The maximum poll time in seconds."
    ::= { ntpTableEntry 4 }

ntpTableComments OBJECT-TYPE
    SYNTAX DisplayString (SIZE (0..32))
    MAX-ACCESS read-create
    STATUS current
    DESCRIPTION
	"An optional description regarding the entry of the NTP table."
	DEFVAL { "Nil" }
    ::= { ntpTableEntry 5 }

ntpTableActive OBJECT-TYPE 
    SYNTAX INTEGER
    {
	enable(1),
	disable(2)
    }
    MAX-ACCESS read-create
    STATUS current
    DESCRIPTION 
	"The status of the NTP table entry."
    DEFVAL { enable }
    ::= { ntpTableEntry 6 }

ntpTableRowStatus OBJECT-TYPE
   SYNTAX RowStatus
   MAX-ACCESS read-create
   STATUS current
   DESCRIPTION
        "The row status in the NTP table entry."
   ::= { ntpTableEntry 7 }

	
-- =================== | nodeConfigurationDhcpd | ======================

dhcpdTable OBJECT-TYPE
    	SYNTAX SEQUENCE OF DhcpdTableEntry
    	MAX-ACCESS not-accessible
    	STATUS current
    	DESCRIPTION
	"This is the DHCP server table." 
    ::= { nodeConfigurationDhcpd 1 }

dhcpdTableEntry OBJECT-TYPE
    	SYNTAX DhcpdTableEntry 
   	MAX-ACCESS not-accessible
    	STATUS current
    	DESCRIPTION
	"Represent the entry in the DHCP server table."
    INDEX { dhcpdTableIndex }
    ::= { dhcpdTable 1 }

DhcpdTableEntry::=
    SEQUENCE
    {
	dhcpdTableIndex	 	Integer32, 
	dhcpdTableIface		OCTET STRING,
	dhcpdTableSubnet	IpAddress,
	dhcpdTableNetstart	IpAddress,
	dhcpdTableNetend	IpAddress,
	dhcpdTableNetmask	IpAddress,
	dhcpdTableMaxLease	Integer32,
	dhcpdTableLease		Integer32,
	dhcpdTableDomain	OCTET STRING,
	dhcpdTableDns		IpAddress,
	dhcpdTableRouter	IpAddress,
      dhcpdTableComments 	DisplayString, 
	dhcpdTableActive 	INTEGER,
	dhcpdTableRowStatus	RowStatus 	
    }

dhcpdTableIndex OBJECT-TYPE
    SYNTAX Integer32 (0..16)
    MAX-ACCESS not-accessible
    STATUS current
    DESCRIPTION
	"Specify the index of the DHCP server table."
    ::= { dhcpdTableEntry 1 }

dhcpdTableIface OBJECT-TYPE
    SYNTAX OCTET STRING (SIZE(0..32))
    MAX-ACCESS read-create
    STATUS current
    DESCRIPTION
	"Specify the interface name of the DHCP server table entry."
	DEFVAL { "Nil" }
    ::= { dhcpdTableEntry 2 }

dhcpdTableSubnet OBJECT-TYPE
    SYNTAX IpAddress
    MAX-ACCESS read-create
    STATUS current
    DESCRIPTION
	"Specify the Subnet Address for the DHCP server table entry."
    ::= { dhcpdTableEntry 3 }

dhcpdTableNetstart OBJECT-TYPE
    SYNTAX IpAddress
    MAX-ACCESS read-create
    STATUS current
    DESCRIPTION
	"Specify the Starting IP Address for the DHCP server table entry."
    ::= { dhcpdTableEntry 4 }

dhcpdTableNetend OBJECT-TYPE
    SYNTAX IpAddress
    MAX-ACCESS read-create
    STATUS current
    DESCRIPTION
	"Specify the Ending IP Address for the DHCP server table entry."
    ::= { dhcpdTableEntry 5 }

dhcpdTableNetmask OBJECT-TYPE
    SYNTAX IpAddress 
    MAX-ACCESS read-create
    STATUS current
    DESCRIPTION
	"Specify the Netmask for the subnet Address for the DHCP server table entry."
    ::= { dhcpdTableEntry 6 }

dhcpdTableMaxLease OBJECT-TYPE
    SYNTAX Integer32 (600..864000)
    MAX-ACCESS read-create
    STATUS current
    DESCRIPTION
	"Specify the maximum lease time for the DHCP server table entry."
    ::= { dhcpdTableEntry 7 }

dhcpdTableLease OBJECT-TYPE
    SYNTAX Integer32 (600..864000)
    MAX-ACCESS read-create
    STATUS current
    DESCRIPTION
	"Specify the default lease time for the DHCP server table entry."
    ::= { dhcpdTableEntry 8 }

dhcpdTableDomain OBJECT-TYPE
    SYNTAX OCTET STRING (SIZE(0..32))
    MAX-ACCESS read-create
    STATUS current
    DESCRIPTION
	"The domain name of the DHCP server table's entry."
	DEFVAL { "Nil" }
    ::= { dhcpdTableEntry 9 }

dhcpdTableDns OBJECT-TYPE
    SYNTAX IpAddress
    MAX-ACCESS read-create
    STATUS current
    DESCRIPTION
	"Specify the DNS IP Address for the DHCP server table entry."
    ::= { dhcpdTableEntry 10 }

dhcpdTableRouter OBJECT-TYPE
    SYNTAX IpAddress
    MAX-ACCESS read-create
    STATUS current
    DESCRIPTION
	"Specify the Router IP Address for the DHCP server table entry."
    ::= { dhcpdTableEntry 11 }

dhcpdTableComments OBJECT-TYPE
    SYNTAX DisplayString (SIZE (0..32))
    MAX-ACCESS read-create
    STATUS current
    DESCRIPTION
	"An optional description regarding the entry of the DHCP server table."
	DEFVAL { "Nil" }
    ::= { dhcpdTableEntry 12 }

dhcpdTableActive OBJECT-TYPE 
    SYNTAX INTEGER
    {
	enable(1),
	disable(2)
    }
    MAX-ACCESS read-create
    STATUS current
    DESCRIPTION 
	"The status of the DHCP server table entry."
    DEFVAL { enable }
    ::= { dhcpdTableEntry 13 }

dhcpdTableRowStatus OBJECT-TYPE
   SYNTAX RowStatus
   MAX-ACCESS read-create
   STATUS current
   DESCRIPTION
        "The row status in the DHCP server table entry."
   ::= { dhcpdTableEntry 14 }

dhcpdActive OBJECT-TYPE
  SYNTAX INTEGER
  {
	enable(1),
	disable(2)
  }
  MAX-ACCESS read-write
  STATUS current
  DESCRIPTION
   	"Enable/Disable the DHCPD Service of the device."
  DEFVAL {enable }
   ::= { nodeConfigurationDhcpd 2 }

dhcpClientExecute OBJECT-TYPE
	SYNTAX Integer32 (1..2)
	MAX-ACCESS read-only
	STATUS current
	DESCRIPTION
	"A command to execute the DHCP Client list"
	::= { nodeConfigurationDhcpd 3 }

dhcpClientTable OBJECT-TYPE
    	SYNTAX SEQUENCE OF DhcpClientTableEntry
    	MAX-ACCESS not-accessible
    	STATUS current
    	DESCRIPTION
	"This is the read-only DHCP client table." 
    ::= { nodeConfigurationDhcpd 4 }

dhcpClientTableEntry OBJECT-TYPE
    	SYNTAX DhcpClientTableEntry 
   	MAX-ACCESS not-accessible
    	STATUS current
    	DESCRIPTION
	"Represent the entry in the DHCP client table."
    INDEX { dhcpClientTableIndex }
    ::= { dhcpClientTable 1 }

DhcpClientTableEntry ::=
    SEQUENCE
    {
	dhcpClientTableIndex	 	Integer32, 
	dhcpClientTableIp			IpAddress,
	dhcpClientTableMac		MacAddress,
	dhcpClientTableHostname		DisplayString
    }

dhcpClientTableIndex OBJECT-TYPE
    SYNTAX Integer32 (0..254)
    MAX-ACCESS not-accessible
    STATUS current
    DESCRIPTION
	"Specify the index of the DHCP client table."
    ::= { dhcpClientTableEntry 1 }

dhcpClientTableIp OBJECT-TYPE
    SYNTAX IpAddress
    MAX-ACCESS read-only
    STATUS current
    DESCRIPTION
	"Specify the IP address of the client in the DHCP server."
    ::= { dhcpClientTableEntry 2 }

dhcpClientTableMac OBJECT-TYPE
    SYNTAX MacAddress
    MAX-ACCESS read-only
    STATUS current
    DESCRIPTION
	"Specify the MAC address of the client in the DHCP server."
    ::= { dhcpClientTableEntry 3 }

dhcpClientTableHostname OBJECT-TYPE
    SYNTAX DisplayString
    MAX-ACCESS read-only
    STATUS current
    DESCRIPTION
	"Specify the Host name of the client in the DHCP server."
    ::= { dhcpClientTableEntry 4 }


-- ================= | nodeConfigurationDns | ===================

dnsActive OBJECT-TYPE
  SYNTAX INTEGER
  {
	enable(1),
	disable(2)
  }
  MAX-ACCESS read-write
  STATUS current
  DESCRIPTION
   	"Enable/Disable the DNS Service of the device."
  DEFVAL {enable }
   ::= { nodeConfigurationDns 1 }

dnsDomainNeeded  OBJECT-TYPE
        SYNTAX INTEGER
         {
	enable(1),
	disable(2)
           }
          MAX-ACCESS read-only
          STATUS current
          DESCRIPTION
        	"Enable/Disable the strict domain checking of the DNS Service."
	DEFVAL { disable }
   ::= { nodeConfigurationDns 2 }

dnsBogusPriv  OBJECT-TYPE
        SYNTAX INTEGER
         {
	enable(1),
	disable(2)
           }
          MAX-ACCESS read-only
          STATUS current
          DESCRIPTION
        	"Enable/Disable the feature."
	DEFVAL { disable }
   ::= { nodeConfigurationDns 3 }

dnsFilterWin2k  OBJECT-TYPE
        SYNTAX INTEGER
         {
	enable(1),
	disable(2)
           }
          MAX-ACCESS read-only
          STATUS current
          DESCRIPTION
        	"Enable/Disable the filter for Windows 2k."
	DEFVAL { enable }
   ::= { nodeConfigurationDns 4 }

dnsStrictOrder  OBJECT-TYPE
        SYNTAX INTEGER
         {
	enable(1),
	disable(2)
           }
          MAX-ACCESS read-only
          STATUS current
          DESCRIPTION
        	"Enable/Disable the strict DNS lookup order feature ."
	DEFVAL { enable }
   ::= { nodeConfigurationDns 5 }

dnsTable OBJECT-TYPE
    	SYNTAX SEQUENCE OF DnsTableEntry
    	MAX-ACCESS not-accessible
    	STATUS current
    	DESCRIPTION
	"This table contains the information of the DNS." 
    ::= { nodeConfigurationDns 6 }

dnsTableEntry OBJECT-TYPE
    	SYNTAX DnsTableEntry 
   	MAX-ACCESS not-accessible
    	STATUS current
    	DESCRIPTION
	"Represent the entry in the DNS table."
    INDEX { dnsTableIndex }
    ::= { dnsTable 1 }

DnsTableEntry::=
    SEQUENCE
    {
	dnsTableIndex	 	Integer32, 
	dnsTableDns		OCTET STRING,
	dnsTableIpaddress	IpAddress,
      dnsTableComments 	DisplayString, 
	dnsTableActive 	 	INTEGER,
	dnsTableRowStatus	RowStatus 	
    }

dnsTableIndex OBJECT-TYPE
    SYNTAX Integer32 (0..128)
    MAX-ACCESS not-accessible
    STATUS current
    DESCRIPTION
	"Specify the index of the DNS service table."
    ::= { dnsTableEntry 1 }

dnsTableDns OBJECT-TYPE
      SYNTAX OCTET STRING (SIZE (0..32))
      MAX-ACCESS read-create
      STATUS current
      DESCRIPTION
	"Specify the Hostname/Domain name of the DNS Service table entry."
	DEFVAL { "Nil" }
     ::= { dnsTableEntry 2 }

dnsTableIpaddress OBJECT-TYPE
      SYNTAX IpAddress
      MAX-ACCESS read-create
      STATUS current
      DESCRIPTION
	"Specify the reply IP Address of the table entry."
     ::= { dnsTableEntry 3 }

dnsTableComments OBJECT-TYPE
    SYNTAX DisplayString (SIZE (0..32))
    MAX-ACCESS read-create
    STATUS current
    DESCRIPTION
	"An optional comment associated to entry of the DNS service table."
	DEFVAL { "Nil" }
    ::= { dnsTableEntry 4 }

dnsTableActive OBJECT-TYPE 
    SYNTAX INTEGER
    {
	enable(1),
	disable(2)
    }
    MAX-ACCESS read-create
    STATUS current
    DESCRIPTION
	"The status of the DNS table entry."
    DEFVAL { enable }
    ::= { dnsTableEntry 5 }

dnsTableRowStatus OBJECT-TYPE
   SYNTAX RowStatus
   MAX-ACCESS read-create
   STATUS current
   DESCRIPTION
        "The row status in the DNS table entry"
   ::= { dnsTableEntry 6 }


-- =================== nodeConfigurationTopology ========

topologyTable OBJECT-TYPE
    	SYNTAX SEQUENCE OF TopologyTableEntry
    	MAX-ACCESS not-accessible
    	STATUS current
    	DESCRIPTION
	"This table contains the list of topology of the node, displaying the relationship between this node and other." 
    ::= { nodeConfigurationTopology 1 }

topologyTableEntry OBJECT-TYPE
    	SYNTAX TopologyTableEntry 
   	MAX-ACCESS not-accessible
    	STATUS current
    	DESCRIPTION
	"Represent the entry in the Topology table."
    INDEX { topologyTableIndex }
    ::= { topologyTable 1 }

TopologyTableEntry::=
    SEQUENCE
    {
	topologyTableIndex		Integer32, 
	topologyTableSource		OCTET STRING,
	topologyTableDestination	OCTET STRING,
      	topologyTableLabel		OCTET STRING, 
	topologyTableStyle		OCTET STRING	
    }

topologyTableIndex OBJECT-TYPE
    SYNTAX Integer32 (0..4096)
    MAX-ACCESS not-accessible
    STATUS current
    DESCRIPTION
	"Specify the index of the node Topology table."
    ::= { topologyTableEntry 1 }

topologyTableSource OBJECT-TYPE
    SYNTAX OCTET STRING (SIZE(7..17))
    MAX-ACCESS read-only
    STATUS current
    DESCRIPTION
	"The source node's IP Address"
    ::= { topologyTableEntry 2 } 

topologyTableDestination OBJECT-TYPE
    SYNTAX OCTET STRING (SIZE(7..17))
    MAX-ACCESS read-only
    STATUS current
    DESCRIPTION
	"The destination node's IP Address"
    ::= { topologyTableEntry 3 } 

topologyTableLabel OBJECT-TYPE
    SYNTAX OCTET STRING (SIZE(0..32))
    MAX-ACCESS read-only
    STATUS current
    DESCRIPTION
	"The label of the link between the source node and destination node."
    ::= { topologyTableEntry 4 } 

topologyTableStyle OBJECT-TYPE
    SYNTAX OCTET STRING (SIZE(0..32))
    MAX-ACCESS read-only
    STATUS current
    DESCRIPTION
	"The style of the link between the source node and destination node."
    ::= { topologyTableEntry 5 } 


-- =================== nodeConfigurationFirewall ===============

firewallActive OBJECT-TYPE
    SYNTAX INTEGER	
    {
	enable(1),
	disable(2)
    }
    MAX-ACCESS read-write
    STATUS current
    DESCRIPTION
        "Enable/Disable the Firewall feature of the node."
    DEFVAL { disable }	
   ::= { nodeConfigurationFirewall 1 }

firewallTable OBJECT-TYPE
    	SYNTAX SEQUENCE OF FirewallTableEntry
    	MAX-ACCESS not-accessible
    	STATUS current
    	DESCRIPTION
	"This table contains rules of the firewall of the system." 
    ::= { nodeConfigurationFirewall 2 }

firewallTableEntry OBJECT-TYPE
    	SYNTAX FirewallTableEntry 
   	MAX-ACCESS not-accessible
    	STATUS current
    	DESCRIPTION
	"Represent the entry in the Firewall table."
    INDEX { firewallTableIndex }
    ::= { firewallTable 1 }

FirewallTableEntry::=
    SEQUENCE
    {
	firewallTableIndex		Integer32, 
	firewallTableTarget		INTEGER,
	firewallTableSrcIface		OCTET STRING,
	firewallTableDstIface		OCTET STRING,
	firewallTableSrcIp		IpAddress,
	firewallTableSrcMask		IpAddress,
	firewallTableDstIp		IpAddress,
	firewallTableDstMask		IpAddress,
	firewallTableProtocol		Integer32,
	firewallTableStartPort		Integer32,
	firewallTableEndPort		Integer32,
	firewallTableUserGroup		Integer32,
	firewallTableComment		DisplayString,
	firewallTableActive 		INTEGER,
	firewallTableRowStatus		RowStatus 
    }

firewallTableIndex OBJECT-TYPE
    SYNTAX Integer32 (0..1024)
    MAX-ACCESS not-accessible
    STATUS current
    DESCRIPTION
	"Specify the index of the firewall table."
    ::= { firewallTableEntry 1 }

firewallTableTarget OBJECT-TYPE
    SYNTAX INTEGER
    {
	allow(1),
	deny(2)
    }
    MAX-ACCESS read-create
    STATUS current
    DESCRIPTION
        "Allow or deny the Target."
    DEFVAL { allow }	
   ::= { firewallTableEntry 2 } 

firewallTableSrcIface OBJECT-TYPE
    SYNTAX OCTET STRING (SIZE(0..32))
    MAX-ACCESS read-create
    STATUS current
    DESCRIPTION
	"The source interface name"
	DEFVAL { "Nil" }
    ::= { firewallTableEntry 3 }

firewallTableDstIface OBJECT-TYPE
    SYNTAX OCTET STRING (SIZE(0..32))
    MAX-ACCESS read-create
    STATUS current
    DESCRIPTION
	"The destination interface name"
	DEFVAL { "Nil" }
    ::= { firewallTableEntry 4 }

firewallTableSrcIp OBJECT-TYPE
    SYNTAX IpAddress
    MAX-ACCESS read-create
    STATUS current
    DESCRIPTION
	"The source IP Address"
    ::= { firewallTableEntry 5 }

firewallTableSrcMask OBJECT-TYPE
    SYNTAX IpAddress
    MAX-ACCESS read-create
    STATUS current
    DESCRIPTION
	"The net mask for the source IP Address"
    ::= { firewallTableEntry 6 }

firewallTableDstIp OBJECT-TYPE
    SYNTAX IpAddress
    MAX-ACCESS read-create
    STATUS current
    DESCRIPTION
	"The destination IP Address"
    ::= { firewallTableEntry 7 }

firewallTableDstMask OBJECT-TYPE
    SYNTAX IpAddress
    MAX-ACCESS read-create
    STATUS current
    DESCRIPTION
	"The net mask for the destination IP Address"
    ::= { firewallTableEntry 8 }

firewallTableProtocol OBJECT-TYPE 
     SYNTAX Integer32 (0..255)
     MAX-ACCESS read-create
     STATUS current
     DESCRIPTION
	"The protocol in number"
     DEFVAL { 0 }
     ::= { firewallTableEntry 9 }

firewallTableStartPort OBJECT-TYPE 
     SYNTAX Integer32 (-1..65535)
     MAX-ACCESS read-create
     STATUS current
     DESCRIPTION
	"The start port number"
     DEFVAL { -1 }
     ::= { firewallTableEntry 10 }

firewallTableEndPort OBJECT-TYPE 
     SYNTAX Integer32 (-1..65535)
     MAX-ACCESS read-create
     STATUS current
     DESCRIPTION
	"The end port number"
     DEFVAL { -1 }
     ::= { firewallTableEntry 11 }

firewallTableUserGroup OBJECT-TYPE 
     SYNTAX Integer32 (-1..999999)
     MAX-ACCESS read-create
     STATUS current
     DESCRIPTION
	"User group associated with this rule"
     DEFVAL { -1 }
     ::= { firewallTableEntry 12 }


firewallTableComment OBJECT-TYPE
      SYNTAX DisplayString (SIZE(0..32))
      MAX-ACCESS read-create
      STATUS current
      DESCRIPTION
 	"The name for the specified rules"
	DEFVAL { "Nil" }
      ::= { firewallTableEntry 13 }

firewallTableActive OBJECT-TYPE 
    SYNTAX INTEGER
    {
	enable(1),
	disable(2)
    }
    MAX-ACCESS read-create
    STATUS current
    DESCRIPTION
	"The status of the firewall table entry."
    DEFVAL { enable }
    ::= { firewallTableEntry 14 }

firewallTableRowStatus OBJECT-TYPE
   SYNTAX RowStatus
   MAX-ACCESS read-create
   STATUS current
   DESCRIPTION
        "The row status in the firewall table entry"
   ::= { firewallTableEntry 15 }


-- =================== nodeConfigurationMacaccess ===============

macaccessActive OBJECT-TYPE
    SYNTAX INTEGER	
    {
	enable(1),
	disable(2)
    }
    MAX-ACCESS read-write
    STATUS current
    DESCRIPTION
        "Enable/Disable the MAC ACCESS feature of the node."
    DEFVAL { disable }	
   ::= { nodeConfigurationMacaccess 1 }

macaccessType OBJECT-TYPE
    SYNTAX INTEGER	
    {
	allow(1),
	deny(2)
    }
    MAX-ACCESS read-write
    STATUS current
    DESCRIPTION
        "Choose the default type of the access, either Allow or Deny."
    DEFVAL { allow }	
   ::= { nodeConfigurationMacaccess 2 }

macaccessTable OBJECT-TYPE
    	SYNTAX SEQUENCE OF MacaccessTableEntry
    	MAX-ACCESS not-accessible
    	STATUS current
    	DESCRIPTION
	"This table display the Mac Access Table." 
    ::= { nodeConfigurationMacaccess 4 }

macaccessTableEntry OBJECT-TYPE
    	SYNTAX MacaccessTableEntry 
   	MAX-ACCESS not-accessible
    	STATUS current
    	DESCRIPTION
	"Represent the entry in the Mac Access table."
    INDEX { macaccessTableIndex }
    ::= { macaccessTable 1 }

MacaccessTableEntry::=
    SEQUENCE
    {
	macaccessTableIndex		Integer32, 
	macaccessTableMac			MacAddress,
	macaccessTableType		INTEGER,
	macaccessTableComment		DisplayString,
	macaccessTableActive		INTEGER,
	macaccessTableRowStatus		RowStatus 
    }

macaccessTableIndex OBJECT-TYPE
    SYNTAX Integer32 (0..1024)
    MAX-ACCESS not-accessible
    STATUS current
    DESCRIPTION
	"Specify the index of the MAC Access table."
    ::= { macaccessTableEntry 1 }

macaccessTableMac OBJECT-TYPE
    SYNTAX MacAddress
    MAX-ACCESS read-create
    STATUS current
    DESCRIPTION
	"The MAC address to be filtered."
    ::= { macaccessTableEntry 2 }

macaccessTableType OBJECT-TYPE 
    SYNTAX INTEGER
    {
	allow(1),
	deny(2)
    }
    MAX-ACCESS read-create
    STATUS current
    DESCRIPTION
	"The type of the access for the MAC access table entry."
    DEFVAL { deny }
    ::= { macaccessTableEntry 3 }

macaccessTableComment OBJECT-TYPE
    SYNTAX DisplayString (SIZE (0..32))
    MAX-ACCESS read-create
    STATUS current
    DESCRIPTION
	"An optional comment associated to entry of the MAC Access table."
	DEFVAL { "Nil" }
    ::= { macaccessTableEntry 4 }

macaccessTableActive OBJECT-TYPE 
    SYNTAX INTEGER
    {
	enable(1),
	disable(2)
    }
    MAX-ACCESS read-create
    STATUS current
    DESCRIPTION
	"The status of the MAC access table entry."
    DEFVAL { enable }
    ::= { macaccessTableEntry 5 }

macaccessTableRowStatus OBJECT-TYPE
   SYNTAX RowStatus
   MAX-ACCESS read-create
   STATUS current
   DESCRIPTION
        "The row status in the MAC Access table entry"
   ::= { macaccessTableEntry 6 }

macActiveListExecute OBJECT-TYPE
	SYNTAX Integer32 (1..2)
	MAX-ACCESS read-only
	STATUS current
	DESCRIPTION
	"A command to execute the Active MAC list"
	::= { nodeConfigurationMacaccess 3 }

macActiveTable OBJECT-TYPE
    	SYNTAX SEQUENCE OF MacActiveTableEntry
    	MAX-ACCESS not-accessible
    	STATUS current
    	DESCRIPTION
	"This is the read-only Active MAC table." 
    ::= { nodeConfigurationMacaccess 5 }

macActiveTableEntry OBJECT-TYPE
    	SYNTAX MacActiveTableEntry 
   	MAX-ACCESS not-accessible
    	STATUS current
    	DESCRIPTION
	"Represent the entry in the Active MAC table."
    INDEX { macActiveTableIndex }
    ::= { macActiveTable 1 }

MacActiveTableEntry ::=
    SEQUENCE
    {
	macActiveTableIndex	 	Integer32, 
	macActiveTableMac			MacAddress,
	macActiveTableIp			IpAddress 
    }

macActiveTableIndex OBJECT-TYPE
    SYNTAX Integer32 (0..1024)
    MAX-ACCESS not-accessible
    STATUS current
    DESCRIPTION
	"Specify the index of the Active MAC table."
    ::= { macActiveTableEntry 1 }

macActiveTableMac OBJECT-TYPE
    SYNTAX MacAddress
    MAX-ACCESS read-only
    STATUS current
    DESCRIPTION
	"Specify the MAC address of the active user Active MAC table."
    ::= { macActiveTableEntry 2 }

macActiveTableIp OBJECT-TYPE
    SYNTAX IpAddress
    MAX-ACCESS read-only
    STATUS current
    DESCRIPTION
	"Specify the MAC address of the active user Active MAC table."
    ::= { macActiveTableEntry 3 }

-- =================== nodeConfigurationNat ===============

natActive OBJECT-TYPE
    SYNTAX INTEGER	
    {
	enable(1),
	disable(2)
    }
    MAX-ACCESS read-write
    STATUS current
    DESCRIPTION
        "Enable/Disable the NAT Table of the node."
    DEFVAL { disable }	
   ::= { nodeConfigurationNat 1 }

natTable OBJECT-TYPE
    	SYNTAX SEQUENCE OF NatTableEntry
    	MAX-ACCESS not-accessible
    	STATUS current
    	DESCRIPTION
	"This table display the NAT Table." 
    ::= { nodeConfigurationNat 2 }

natTableEntry OBJECT-TYPE
    	SYNTAX NatTableEntry 
   	MAX-ACCESS not-accessible
    	STATUS current
    	DESCRIPTION
	"Represent the entry in the NAT table."
    INDEX { natTableIndex }
    ::= { natTable 1 }

NatTableEntry::=
    SEQUENCE
    {
	natTableIndex		Integer32, 
	natTableProtocol	INTEGER,
	natTablePort		Integer32,
	natTableIp		IpAddress,
	natTableComment		DisplayString,
	natTableActive		INTEGER,
	natTableRowStatus	RowStatus 
    }

natTableIndex OBJECT-TYPE
    SYNTAX Integer32 (0..256)
    MAX-ACCESS not-accessible
    STATUS current
    DESCRIPTION
	"Specify the index of the NAT table."
    ::= { natTableEntry 1 }

natTableProtocol OBJECT-TYPE
    SYNTAX INTEGER
    {
	tcp(1),
	udp(2),
	both(3)
    }
    MAX-ACCESS read-create
    STATUS current
    DESCRIPTION
	"Define the type of protocol of the NAT Table entry"
    DEFVAL { tcp }
    ::= { natTableEntry 2 }

natTablePort OBJECT-TYPE
    SYNTAX Integer32 (1..65535)
    MAX-ACCESS read-create
    STATUS current
    DESCRIPTION
	"Define the port number of the NAT Table entry"
    ::= { natTableEntry 3 }

natTableIp OBJECT-TYPE
    SYNTAX IpAddress
    MAX-ACCESS read-create
    STATUS current
    DESCRIPTION
	"Define the IP Address of the NAT Table entry"
    ::= { natTableEntry 4 }

natTableComment OBJECT-TYPE
    SYNTAX DisplayString (SIZE (0..32))
    MAX-ACCESS read-create
    STATUS current
    DESCRIPTION
	"An optional comment associated to entry of the NAT table."
	DEFVAL { "Nil" }
    ::= { natTableEntry 5 }

natTableActive OBJECT-TYPE 
    SYNTAX INTEGER
    {
	enable(1),
	disable(2)
    }
    MAX-ACCESS read-create
    STATUS current
    DESCRIPTION
	"The status of the NAT table entry."
    DEFVAL { enable }
    ::= { natTableEntry 6 }

natTableRowStatus OBJECT-TYPE
   SYNTAX RowStatus
   MAX-ACCESS read-create
   STATUS current
   DESCRIPTION
        "The row status in the NAT table entry"
   ::= { natTableEntry 7 }


-- =================== nodeConfigurationShaping ==========

shapingActive OBJECT-TYPE
	SYNTAX INTEGER
	{
		enable(1),
		disable(2)
	}
	MAX-ACCESS read-write
	STATUS current
	DESCRIPTION
	"Enable/disable the traffic shaping service of the device"
	DEFVAL { disable }
	::= { nodeConfigurationShaping 1 }

shapingWanRateup OBJECT-TYPE
    SYNTAX Integer32 (5..100)
    MAX-ACCESS read-write
    STATUS current
    DESCRIPTION 
	"WAN port uplink speed in Mbps."
    DEFVAL { 100 }	
    ::= { nodeConfigurationShaping 2 }

shapingWanRatedown OBJECT-TYPE
    SYNTAX Integer32 (5..100)
    MAX-ACCESS read-write
    STATUS current
    DESCRIPTION 
	"WAN port downlink speed in Mbps."
    DEFVAL { 100 }	
    ::= { nodeConfigurationShaping 3 }

shapingMeshRateup OBJECT-TYPE
    SYNTAX Integer32 (0..65535)
    MAX-ACCESS read-write
    STATUS current
    DESCRIPTION 
	"Mesh port uplink speed in Mbps."
    DEFVAL { 100 }	
    ::= { nodeConfigurationShaping 4 }

shapingMeshRatedown OBJECT-TYPE
    SYNTAX Integer32 (0..65535)
    MAX-ACCESS read-write
    STATUS current
    DESCRIPTION 
	"Mesh port downlink speed in Mbps."
    DEFVAL { 100 }	
    ::= { nodeConfigurationShaping 5 }

shapingVlanRateup OBJECT-TYPE
    SYNTAX Integer32 (0..65535)
    MAX-ACCESS read-write
    STATUS current
    DESCRIPTION 
	"VLAN port uplink speed in Mbps."
    DEFVAL { 100 }	
    ::= { nodeConfigurationShaping 6 }

shapingVlanRatedown OBJECT-TYPE
    SYNTAX Integer32 (0..65535)
    MAX-ACCESS read-write
    STATUS current
    DESCRIPTION 
	"VLAN port downlink speed in Mbps."
    DEFVAL { 100 }	
    ::= { nodeConfigurationShaping 7 }

shapingDefaultup OBJECT-TYPE
    SYNTAX Integer32 (32..65535)
    MAX-ACCESS read-write
    STATUS current
    DESCRIPTION 
	"User default uplink speed in kbps."
    DEFVAL { 256 }	
    ::= { nodeConfigurationShaping 8 }

shapingDefaultdown OBJECT-TYPE
    SYNTAX Integer32 (32..65535)
    MAX-ACCESS read-write
    STATUS current
    DESCRIPTION 
	"User default downlink speed in kbps."
    DEFVAL { 256 }	
    ::= { nodeConfigurationShaping 9 }

shapingTable OBJECT-TYPE
    	SYNTAX SEQUENCE OF ShapingTableEntry
    	MAX-ACCESS not-accessible
    	STATUS current
    	DESCRIPTION
	"This table display the traffic shaping table." 
    ::= { nodeConfigurationShaping 10 }

shapingTableEntry OBJECT-TYPE
    	SYNTAX ShapingTableEntry 
   	MAX-ACCESS not-accessible
    	STATUS current
    	DESCRIPTION
	"Represent the entry in the traffic shaping table."
    INDEX { shapingTableIndex }
    ::= { shapingTable 1 }

ShapingTableEntry::=
    SEQUENCE
    {
	shapingTableIndex		Integer32, 
	shapingTableProtocol	INTEGER,
	shapingTablePort		Integer32,
	shapingTableMinsize	Integer32,
	shapingTableMaxsize	Integer32,
	shapingTablePriority	INTEGER,
	shapingTableComment	DisplayString,
	shapingTableActive	INTEGER,
	shapingTableRowStatus	RowStatus 
    }

shapingTableIndex OBJECT-TYPE
    SYNTAX Integer32 (0..1024)
    MAX-ACCESS not-accessible
    STATUS current
    DESCRIPTION
	"Specify the index of the traffic shaping table."
    ::= { shapingTableEntry 1 }

shapingTableProtocol OBJECT-TYPE
    SYNTAX INTEGER
    {
	tcp(1),
	udp(2),
	both(3)
    }
    MAX-ACCESS read-create
    STATUS current
    DESCRIPTION
	"Define the type of protocol of the traffic shaping Table entry"
    DEFVAL { tcp }
    ::= { shapingTableEntry 2 }

shapingTablePort OBJECT-TYPE
    SYNTAX Integer32 (1..65535)
    MAX-ACCESS read-create
    STATUS current
    DESCRIPTION
	"Define the port number of the traffic shaping Table entry"
    ::= { shapingTableEntry 3 }

shapingTableMinsize OBJECT-TYPE
    SYNTAX Integer32 (1..65535)
    MAX-ACCESS read-create
    STATUS current
    DESCRIPTION
	"Define the minimum packet size of the traffic shaping Table entry"
    ::= { shapingTableEntry 4 }

shapingTableMaxsize OBJECT-TYPE
    SYNTAX Integer32 (1..65535)
    MAX-ACCESS read-create
    STATUS current
    DESCRIPTION
	"Define the maximum packet size of the traffic shaping Table entry"
    ::= { shapingTableEntry 5 }

shapingTablePriority OBJECT-TYPE
    SYNTAX INTEGER
    {
	background(1),
	video(2),
	voice(3),
	besteffort(4)
    }
    MAX-ACCESS read-create
    STATUS current
    DESCRIPTION
	"Define the type of priority of the traffic shaping Table entry"
    DEFVAL { background }
    ::= { shapingTableEntry 6 }

shapingTableComment OBJECT-TYPE
    SYNTAX DisplayString (SIZE (0..32))
    MAX-ACCESS read-create
    STATUS current
    DESCRIPTION
	"An optional comment associated to entry of the traffiic shaping table."
	DEFVAL { "Nil" }
    ::= { shapingTableEntry 7 }

shapingTableActive OBJECT-TYPE 
    SYNTAX INTEGER
    {
	enable(1),
	disable(2)
    }
    MAX-ACCESS read-create
    STATUS current
    DESCRIPTION
	"The status of the traffic shaping table entry."
    DEFVAL { enable }
    ::= { shapingTableEntry 8 }

shapingTableRowStatus OBJECT-TYPE
   SYNTAX RowStatus
   MAX-ACCESS read-create
   STATUS current
   DESCRIPTION
        "The row status in the traffic shaping table entry"
   ::= { shapingTableEntry 9 }


-- =================== nodeConfigurationPppoe ============

pppoeActive OBJECT-TYPE
	SYNTAX INTEGER
	{
		enable(1),
		disable(2)
	}
	MAX-ACCESS read-write
	STATUS current
	DESCRIPTION
	"Enable/disable the PPPoE service of the system"
	DEFVAL { disable }
	::= { nodeConfigurationPppoe 1 }

pppoeUsername OBJECT-TYPE
	SYNTAX DisplayString (SIZE (0..32))
	MAX-ACCESS read-write
	STATUS current
	DESCRIPTION
	"The username of the PPPoE service"
	DEFVAL { "Nil" }
     ::= { nodeConfigurationPppoe 2 }

pppoePassword OBJECT-TYPE
	SYNTAX DisplayString (SIZE (0..32))
	MAX-ACCESS read-write
	STATUS current
	DESCRIPTION
	"The password correspond to the username of the PPPoE service"
	DEFVAL { "Nil" }
     ::= { nodeConfigurationPppoe 3 }

pppoeAuthType OBJECT-TYPE
	SYNTAX INTEGER
	{
		pap(1),
		chap(2)
	}
	MAX-ACCESS read-write
	STATUS current
	DESCRIPTION
	"The type of authentication"
	DEFVAL { pap }
	::= { nodeConfigurationPppoe 4 }

pppoeUseChap OBJECT-TYPE
	SYNTAX INTEGER
	{
		enable(1),
		disable(2)
	}
	MAX-ACCESS read-write
	STATUS current
	DESCRIPTION
	"Enable/disable server side authentication"
	DEFVAL { disable }
	::= { nodeConfigurationPppoe 5 }

pppoeChapUsername OBJECT-TYPE
	SYNTAX DisplayString (SIZE (0..32))
	MAX-ACCESS read-write
	STATUS current
	DESCRIPTION
	"The username at the server side"
	DEFVAL { "Nil" }
     ::= { nodeConfigurationPppoe 6 }

pppoeChapPassword OBJECT-TYPE
	SYNTAX DisplayString (SIZE (0..32))
	MAX-ACCESS read-write
	STATUS current
	DESCRIPTION
	"The password correspond to the username at the server side"
	DEFVAL { "Nil" }
     ::= { nodeConfigurationPppoe 7 }



-- =================== nodeConfigurationPptp =============

pptpActive OBJECT-TYPE
	SYNTAX INTEGER
	{
		enable(1),
		disable(2)
	}
	MAX-ACCESS read-write
	STATUS current
	DESCRIPTION
	"Enable/disable the PPTP server service of the system"
	DEFVAL { enable }
	::= { nodeConfigurationPptp 1 }



pptpTable OBJECT-TYPE
    	SYNTAX SEQUENCE OF PptpTableEntry
    	MAX-ACCESS not-accessible
    	STATUS current
    	DESCRIPTION
	"This table display the PPTP server Table." 
    ::= { nodeConfigurationPptp 2 }

pptpTableEntry OBJECT-TYPE
    	SYNTAX PptpTableEntry 
   	MAX-ACCESS not-accessible
    	STATUS current
    	DESCRIPTION
	"Represent the entry in the PPTP server table."
    INDEX { pptpTableIndex }
    ::= { pptpTable 1 }

PptpTableEntry::=
    SEQUENCE
    {
	pptpTableIndex		Integer32, 
	pptpTableUsername		DisplayString,
	pptpTablePassword		DisplayString,
	pptpTableIp			IpAddress,
	pptpTableComment		DisplayString,
	pptpTableActive		INTEGER,
	pptpTableRowStatus	RowStatus 
    }

pptpTableIndex OBJECT-TYPE
    SYNTAX Integer32 (0..10)
    MAX-ACCESS not-accessible
    STATUS current
    DESCRIPTION
	"Specify the index of the PPTP server table."
    ::= { pptpTableEntry 1 }

pptpTableUsername OBJECT-TYPE
    SYNTAX DisplayString (SIZE (1..32))
    MAX-ACCESS read-create
    STATUS current
    DESCRIPTION
	"The username of the PPTP server user."
	DEFVAL { "Nil" }
    ::= { pptpTableEntry 2 }

pptpTablePassword OBJECT-TYPE
    SYNTAX DisplayString (SIZE (1..32))
    MAX-ACCESS read-create
    STATUS current
    DESCRIPTION
	"The password for the username of the PPTP server user."
	DEFVAL { "Nil" }
    ::= { pptpTableEntry 3 }

pptpTableIp OBJECT-TYPE
    SYNTAX IpAddress
    MAX-ACCESS read-create
    STATUS current
    DESCRIPTION
	"Define the IP Address of the PPTP server Table entry"
    ::= { pptpTableEntry 4 }

pptpTableComment OBJECT-TYPE
    SYNTAX DisplayString (SIZE (0..32))
    MAX-ACCESS read-create
    STATUS current
    DESCRIPTION
	"An optional comment associated to entry of the PPTP Server users table."
	DEFVAL { "Nil" }	
    ::= { pptpTableEntry 5 }

pptpTableActive OBJECT-TYPE 
    SYNTAX INTEGER
    {
	enable(1),
	disable(2)
    }
    MAX-ACCESS read-create
    STATUS current
    DESCRIPTION
	"The status of the PPTP Server users table entry."
    DEFVAL { enable }
    ::= { pptpTableEntry 6 }

pptpTableRowStatus OBJECT-TYPE
   SYNTAX RowStatus
   MAX-ACCESS read-create
   STATUS current
   DESCRIPTION
        "The row status in the PPTP Server users table entry"
   ::= { pptpTableEntry 7 }

pptpServerip OBJECT-TYPE
	SYNTAX IpAddress
	MAX-ACCESS read-write
	STATUS current
	DESCRIPTION
	"Define the PPTP Server IP Address"
	::= { nodeConfigurationPptp 3 }

pptpStartip OBJECT-TYPE
	SYNTAX IpAddress
	MAX-ACCESS read-write
	STATUS current
	DESCRIPTION
	"Define the PPTP Client Start Address"
	::= { nodeConfigurationPptp 4 }

pptpEndip OBJECT-TYPE
	SYNTAX IpAddress
	MAX-ACCESS read-write
	STATUS current
	DESCRIPTION
	"Define the PPTP Client End Address"
	::= { nodeConfigurationPptp 5 }

-- =================== nodeConfigurationTmipd ============

tmipdActive OBJECT-TYPE
	SYNTAX INTEGER
	{
		enable(1),
		disable(2)
	}
	MAX-ACCESS read-write
	STATUS current
	DESCRIPTION
	"Enable/disable the transparent mobile IP Agent service"
	DEFVAL { disable }
	::= { nodeConfigurationTmipd 1 }

tmipdNetname OBJECT-TYPE
	SYNTAX OCTET STRING (SIZE (1..32))
	MAX-ACCESS read-write
	STATUS current
	DESCRIPTION
	"The Mobile IP network name"
	DEFVAL { "Nil" }
     ::= { nodeConfigurationTmipd 2 }

tmipdMlrdip OBJECT-TYPE
    SYNTAX IpAddress
    MAX-ACCESS read-write 
    STATUS current
    DESCRIPTION
	"The IP Address of the Mobile Location Register server."
    ::= { nodeConfigurationTmipd 3 }

tmipdVlan OBJECT-TYPE
	SYNTAX OCTET STRING (SIZE (1..32))
	MAX-ACCESS read-write
	STATUS current
	DESCRIPTION
	"The Mobile IP network name"
	DEFVAL { "vlan0" }
     ::= { nodeConfigurationTmipd 4 }


-- =================== nodeConfigurationCaptive ==========

captiveActive OBJECT-TYPE
	SYNTAX INTEGER
	{
		enable(1),
		disable(2)
	}
	MAX-ACCESS read-write
	STATUS current
	DESCRIPTION
	"Enable/disable the webbased authentication"
	DEFVAL { disable }
	::= { nodeConfigurationCaptive 1 }

captiveRedirect OBJECT-TYPE
	SYNTAX DisplayString (SIZE (1..512))
	MAX-ACCESS read-write
	STATUS current
	DESCRIPTION
	"Redirect users to this URL on success authentication"
	DEFVAL { "Nil" }
     ::= { nodeConfigurationCaptive 2 }

captivePop3push OBJECT-TYPE
	SYNTAX INTEGER
	{
		enable(1),
		disable(2)
	}
	MAX-ACCESS read-write
	STATUS current
	DESCRIPTION
	"Push email to not authenticated users"
	DEFVAL { enable }
	::= { nodeConfigurationCaptive 3 }

captiveExternalActive OBJECT-TYPE
	SYNTAX INTEGER
	{
		enable(1),
		disable(2)
	}
	MAX-ACCESS read-write
	STATUS current
	DESCRIPTION
	"Enable/disable external login server"
	DEFVAL { disable }
	::= { nodeConfigurationCaptive 4 }

captiveExternalServer OBJECT-TYPE
	SYNTAX DisplayString (SIZE (1..512))
	MAX-ACCESS read-write
	STATUS current
	DESCRIPTION
	"External login server URL"
	DEFVAL { "Nil" }	
     ::= { nodeConfigurationCaptive 5 }

captiveDefaultIdleTimeout OBJECT-TYPE
    SYNTAX Integer32 (1..65535)
    MAX-ACCESS read-write
    STATUS current
    DESCRIPTION 
	"Default Idle Timeout."
    DEFVAL { 300 }	
    ::= { nodeConfigurationCaptive 6 }

captiveDefaultSessionTimeout OBJECT-TYPE
    SYNTAX Integer32 (1..65535)
    MAX-ACCESS read-write
    STATUS current
    DESCRIPTION 
	"Default Session Timeout."
    DEFVAL { 65000 }	
    ::= { nodeConfigurationCaptive 7 }

captiveHttpActive OBJECT-TYPE
	SYNTAX INTEGER
	{
		enable(1),
		disable(2)
	}
	MAX-ACCESS read-write
	STATUS current
	DESCRIPTION
	"Enable/disable login with HTTP"
	DEFVAL { enable }
	::= { nodeConfigurationCaptive 8 }

captiveHttpPort OBJECT-TYPE
    SYNTAX Integer32 (1000..65535)
    MAX-ACCESS read-write
    STATUS current
    DESCRIPTION 
	"Port used in captive login."
    DEFVAL { 3000 }	
    ::= { nodeConfigurationCaptive 9 }

captiveHttpsActive OBJECT-TYPE
	SYNTAX INTEGER
	{
		enable(1),
		disable(2)
	}
	MAX-ACCESS read-write
	STATUS current
	DESCRIPTION
	"Enable/disable login with HTTPS"
	DEFVAL { enable }
	::= { nodeConfigurationCaptive 10 }

captiveHttpsPort OBJECT-TYPE
    SYNTAX Integer32 (1000..65535)
    MAX-ACCESS read-write
    STATUS current
    DESCRIPTION 
	"Port used in captive login."
    DEFVAL { 3001 }	
    ::= { nodeConfigurationCaptive 11 }

captiveWebspaceActive OBJECT-TYPE
	SYNTAX INTEGER
	{
		enable(1),
		disable(2)
	}
	MAX-ACCESS read-write
	STATUS current
	DESCRIPTION
	"Enable/disable login with HTTPS"
	DEFVAL { enable }
	::= { nodeConfigurationCaptive 12 }

captiveWebspacePort OBJECT-TYPE
    SYNTAX Integer32 (1000..65535)
    MAX-ACCESS read-write
    STATUS current
    DESCRIPTION 
	"Port used in captive login."
    DEFVAL { 3002 }	
    ::= { nodeConfigurationCaptive 13 }

captiveDefaultLanguage OBJECT-TYPE
	SYNTAX DisplayString (SIZE (1..32))
	MAX-ACCESS read-write
	STATUS current
	DESCRIPTION
	"The name of the managed device"
	DEFVAL { "english" }
     ::= { nodeConfigurationCaptive 14 }

captiveMultipleUsername	OBJECT-TYPE
	SYNTAX INTEGER
	{
		enable(1),
		disable(2)
	}
	MAX-ACCESS read-write
	STATUS current
	DESCRIPTION
	"Enable/disable multiple login with same username"
	DEFVAL { disable }
	::= { nodeConfigurationCaptive 15 }

captive1xLogin	OBJECT-TYPE
	SYNTAX INTEGER
	{
		enable(1),
		disable(2)
	}
	MAX-ACCESS read-write
	STATUS current
	DESCRIPTION
		"Enable/disable to use 1x login when available"
	DEFVAL { enable }
	::= { nodeConfigurationCaptive 16 }


-- =================== nodeConfigurationRadiusClient =========

radiusclientActive OBJECT-TYPE
	SYNTAX INTEGER
	{
		enable(1),
		disable(2)
	}
	MAX-ACCESS read-write
	STATUS current
	DESCRIPTION
	"Enable/disable RADIUS client service"
	DEFVAL { enable }
	::= { nodeConfigurationRadiusClient 1 }

radiusclientNasid OBJECT-TYPE
	SYNTAX DisplayString (SIZE (1..32))
	MAX-ACCESS read-write
	STATUS current
	DESCRIPTION
	"RADIUS attribute"
	DEFVAL { "Nil" }
     ::= { nodeConfigurationRadiusClient 2 }

radiusclientCalledstationid OBJECT-TYPE
	SYNTAX DisplayString (SIZE (1..32))
	MAX-ACCESS read-write
	STATUS current
	DESCRIPTION
	"RADIUS attribute"
	DEFVAL { "Nil" }
     ::= { nodeConfigurationRadiusClient 3 }

radiusclientNasport OBJECT-TYPE
    SYNTAX Integer32 (1..65535)
    MAX-ACCESS read-write
    STATUS current
    DESCRIPTION 
	"RADIUS attribute."
    DEFVAL { 1 }	
    ::= { nodeConfigurationRadiusClient 4 }

radiusclientNasporttype OBJECT-TYPE
    SYNTAX Integer32 (1..65535)
    MAX-ACCESS read-write
    STATUS current
    DESCRIPTION 
	"RADIUS attribute."
    DEFVAL { 19 }	
    ::= { nodeConfigurationRadiusClient 5 }

radiusclientInterimupdate OBJECT-TYPE
    SYNTAX Integer32 (1..65535)
    MAX-ACCESS read-write
    STATUS current
    DESCRIPTION 
	"Interim update interval."
	DEFVAL { 300 }
    ::= { nodeConfigurationRadiusClient 6 }

radiusclientTable OBJECT-TYPE
    	SYNTAX SEQUENCE OF RadiusclientTableEntry
    	MAX-ACCESS not-accessible
    	STATUS current
    	DESCRIPTION
	"This table display the Servers entry of the RADIUS client." 
    ::= { nodeConfigurationRadiusClient 7 }

radiusclientTableEntry OBJECT-TYPE
    	SYNTAX RadiusclientTableEntry 
   	MAX-ACCESS not-accessible
    	STATUS current
    	DESCRIPTION
	"Represent the entry in the RADIUS client table."
    INDEX { radiusclientTableIndex }
    ::= { radiusclientTable 1 }

RadiusclientTableEntry::=
    SEQUENCE
    {
	radiusclientTableIndex 			Integer32, 
	radiusclientTableServername		DisplayString,
	radiusclientTableServertype		INTEGER,
	radiusclientTableServerport		Integer32,
	radiusclientTableServersecret		DisplayString,
	radiusclientTableComment		DisplayString,
	radiusclientTableActive			INTEGER,
	radiusclientTableRowStatus		RowStatus 
    }

radiusclientTableIndex OBJECT-TYPE
    SYNTAX Integer32 (0..8)
    MAX-ACCESS not-accessible
    STATUS current
    DESCRIPTION
	"Specify the index of the RADIUS client table."
    ::= { radiusclientTableEntry 1 }

radiusclientTableServername OBJECT-TYPE
    SYNTAX DisplayString (SIZE (1..32))
    MAX-ACCESS read-create
    STATUS current
    DESCRIPTION
	"The server name of the RADIUS client."
	DEFVAL { "Nil" }
    ::= { radiusclientTableEntry 2 }

radiusclientTableServertype OBJECT-TYPE 
    SYNTAX INTEGER
    {
	authenticate(1),
	accounting(2)
    }
    MAX-ACCESS read-create
    STATUS current
    DESCRIPTION
	"The server type: authenticate or accounting."
    ::= { radiusclientTableEntry 3 }

radiusclientTableServerport OBJECT-TYPE 
    SYNTAX Integer32 (1..65535)
    MAX-ACCESS read-create
    STATUS current
    DESCRIPTION
	"The server port of the RADIUS client."
    ::= { radiusclientTableEntry 4 }

radiusclientTableServersecret OBJECT-TYPE
	SYNTAX DisplayString (SIZE (0..32))
	MAX-ACCESS read-create
	STATUS current
	DESCRIPTION
	   "Share secret of the radius client."
	DEFVAL { "Nil" }
	::= { radiusclientTableEntry 5 }

radiusclientTableComment OBJECT-TYPE
    SYNTAX DisplayString (SIZE (0..32))
    MAX-ACCESS read-create
    STATUS current
    DESCRIPTION
	"An optional comment associated to entry of the RADIUS client table."
	DEFVAL { "Nil" }
    ::= { radiusclientTableEntry 6 }

radiusclientTableActive OBJECT-TYPE 
    SYNTAX INTEGER
    {
	enable(1),
	disable(2)
    }
    MAX-ACCESS read-create
    STATUS current
    DESCRIPTION
	"The status of the RADIUS client table entry."
    DEFVAL { enable }
    ::= { radiusclientTableEntry 7 }

radiusclientTableRowStatus OBJECT-TYPE
   SYNTAX RowStatus
   MAX-ACCESS read-create
   STATUS current
   DESCRIPTION
        "The row status in the RADIUS client table entry"
   ::= { radiusclientTableEntry 8 }



-- =================== nodeConfigurationHttpd ===============

httpdActive OBJECT-TYPE
	SYNTAX INTEGER
	{
		enable(1),
		disable(2)
	}
	MAX-ACCESS read-write
	STATUS current
	DESCRIPTION
	"Enable/disable the webbased management"
	DEFVAL { enable }
	::= { nodeConfigurationHttpd 1 }

httpdPort OBJECT-TYPE
    SYNTAX Integer32 (1..65535)
    MAX-ACCESS read-write
    STATUS current
    DESCRIPTION 
	"The HTTPD port number."
    DEFVAL { 443 }	
    ::= { nodeConfigurationHttpd 2 }

httpdUsername OBJECT-TYPE
	SYNTAX DisplayString (SIZE (1..32))
	MAX-ACCESS read-write
	STATUS current
	DESCRIPTION
	"The admin username"
	DEFVAL { "admin" }
     ::= { nodeConfigurationHttpd 3 }

httpdPassword OBJECT-TYPE
	SYNTAX DisplayString (SIZE (1..32))
	MAX-ACCESS read-write
	STATUS current
	DESCRIPTION
	"The admin password"
	DEFVAL { "admin" }
     ::= { nodeConfigurationHttpd 4 }

httpdAccessctrl OBJECT-TYPE
	SYNTAX INTEGER
	{
		enable(1),
		disable(2)
	}
	MAX-ACCESS read-write
	STATUS current
	DESCRIPTION
	"Enable/disable the Access Control"
	DEFVAL { enable }
	::= { nodeConfigurationHttpd 5 }

httpdTable OBJECT-TYPE
    	SYNTAX SEQUENCE OF HttpdTableEntry
    	MAX-ACCESS not-accessible
    	STATUS current
    	DESCRIPTION
	"This table display the access control of the HTTPD Table." 
    ::= { nodeConfigurationHttpd 6 }

httpdTableEntry OBJECT-TYPE
    	SYNTAX HttpdTableEntry 
   	MAX-ACCESS not-accessible
    	STATUS current
    	DESCRIPTION
	"Represent the entry in the HTTPD table."
    INDEX { httpdTableIndex }
    ::= { httpdTable 1 }

HttpdTableEntry::=
    SEQUENCE
    {
	httpdTableIndex		Integer32, 
	httpdTableDevice		OCTET STRING,
	httpdTableSubnet		IpAddress,
	httpdTableNetmask		IpAddress,
	httpdTableDevnet		INTEGER,
	httpdTableComment		DisplayString,
	httpdTableActive		INTEGER,
	httpdTableRowStatus	RowStatus 
    }

httpdTableIndex OBJECT-TYPE
    SYNTAX Integer32 (0..64)
    MAX-ACCESS not-accessible
    STATUS current
    DESCRIPTION
	"Specify the index of the HTTPD table."
    ::= { httpdTableEntry 1 }

httpdTableDevice OBJECT-TYPE
    SYNTAX OCTET STRING (SIZE (1..32))
    MAX-ACCESS read-create
    STATUS current
    DESCRIPTION
	"Allow access from device."
	DEFVAL { "Nil" }
    ::= { httpdTableEntry 2 }

httpdTableSubnet OBJECT-TYPE
    SYNTAX IpAddress
    MAX-ACCESS read-create
    STATUS current
    DESCRIPTION
	"Allow access from network"
    ::= { httpdTableEntry 3 }

httpdTableNetmask OBJECT-TYPE
    SYNTAX IpAddress
    MAX-ACCESS read-create
    STATUS current
    DESCRIPTION
	"Netmask for the subnet"
    ::= { httpdTableEntry 4 }

httpdTableDevnet OBJECT-TYPE
    SYNTAX INTEGER
    {
	device(1),
	network(2)
    }
    MAX-ACCESS read-create
    STATUS current
    DESCRIPTION
	"Define the type HTTPD Table entry: Use device or network"
    DEFVAL { device }
    ::= { httpdTableEntry 5 }

httpdTableComment OBJECT-TYPE
    SYNTAX DisplayString (SIZE (0..32))
    MAX-ACCESS read-create
    STATUS current
    DESCRIPTION
	"An optional comment associated to entry of the HTTPD table."
	DEFVAL { "Nil" }
    ::= { httpdTableEntry 6 }

httpdTableActive OBJECT-TYPE 
    SYNTAX INTEGER
    {
	enable(1),
	disable(2)
    }
    MAX-ACCESS read-create
    STATUS current
    DESCRIPTION
	"The status of the HTTPD table entry."
    DEFVAL { enable }
    ::= { httpdTableEntry 7 }

httpdTableRowStatus OBJECT-TYPE
   SYNTAX RowStatus
   MAX-ACCESS read-create
   STATUS current
   DESCRIPTION
        "The row status in the HTTPD table entry"
   ::= { httpdTableEntry 8 }

httpdCertPassword OBJECT-TYPE
	SYNTAX DisplayString (SIZE (1..32))
	MAX-ACCESS read-write
	STATUS current
	DESCRIPTION
	"The certificate password"
	DEFVAL { "httpconf" }
     ::= { nodeConfigurationHttpd 7 }



-- =================== nodeConfigurationSnmpd ==============

snmpdActive OBJECT-TYPE
	SYNTAX INTEGER
	{
		enable(1),
		disable(2)
	}
	MAX-ACCESS read-write
	STATUS current
	DESCRIPTION
	"Enable/disable the SNMPD management"
	DEFVAL { enable }
	::= { nodeConfigurationSnmpd 1 }

snmpdVersion OBJECT-TYPE
	SYNTAX INTEGER
	{
		v1o2c(1),
		v3(2),
		all(3)
	}
	MAX-ACCESS read-write
	STATUS current
	DESCRIPTION
	"The SNMP Version"
	DEFVAL { v1o2c }
	::= { nodeConfigurationSnmpd 2 }

snmpdPort OBJECT-TYPE
    SYNTAX Integer32 (1..65535)
    MAX-ACCESS read-write
    STATUS current
    DESCRIPTION 
	"SNMPD Port."
    DEFVAL { 161 }	
    ::= { nodeConfigurationSnmpd 3 }

snmpdReadcommunity OBJECT-TYPE
	SYNTAX DisplayString (SIZE (4..32))
	MAX-ACCESS read-write
	STATUS current
	DESCRIPTION
	"The read-only Community for SNMP v1 or v2c user"
	DEFVAL { "public" }
     ::= { nodeConfigurationSnmpd 4 }

snmpdWritecommunity OBJECT-TYPE
	SYNTAX DisplayString (SIZE (4..32))
	MAX-ACCESS read-write
	STATUS current
	DESCRIPTION
	"The read-write Community for SNMP v1 or v2c user"
	DEFVAL { "private" }
     ::= { nodeConfigurationSnmpd 5 }

snmpdReadusername OBJECT-TYPE
	SYNTAX DisplayString (SIZE (8..50))
	MAX-ACCESS read-write
	STATUS current
	DESCRIPTION
	"The read-only Username for SNMP v3 user"
	DEFVAL { "snmpv3rouser" }
     ::= { nodeConfigurationSnmpd 6 }

snmpdWriteusername OBJECT-TYPE
	SYNTAX DisplayString (SIZE (8..50))
	MAX-ACCESS read-write
	STATUS current
	DESCRIPTION
	"The read-write Username for SNMP v3 user"
	DEFVAL { "snmpv3rwuser" }
     ::= { nodeConfigurationSnmpd 7 }


snmpdPassword OBJECT-TYPE
	SYNTAX DisplayString (SIZE (8..50))
	MAX-ACCESS read-write
	STATUS current
	DESCRIPTION
	"The authentication password for SNMP v3 user"
	DEFVAL { "snmpv3password" }
     ::= { nodeConfigurationSnmpd 8 }

snmpdPassphrase OBJECT-TYPE
	SYNTAX DisplayString (SIZE (8..50))
	MAX-ACCESS read-write
	STATUS current
	DESCRIPTION
	"The private passphrase for SNMP v3 user"
	DEFVAL { "snmpv3passphrase" }
     ::= { nodeConfigurationSnmpd 9 }

snmpdAccessctrl OBJECT-TYPE
	SYNTAX INTEGER
	{
		enable(1),
		disable(2)
	}
	MAX-ACCESS read-write
	STATUS current
	DESCRIPTION
	"Enable/disable the SNMPD access control"
	DEFVAL { enable }
	::= { nodeConfigurationSnmpd 10 }

snmpdTable OBJECT-TYPE
    	SYNTAX SEQUENCE OF SnmpdTableEntry
    	MAX-ACCESS not-accessible
    	STATUS current
    	DESCRIPTION
	"This table display the access control of the SNMPD Table." 
    ::= { nodeConfigurationSnmpd 11 }

snmpdTableEntry OBJECT-TYPE
    	SYNTAX SnmpdTableEntry 
   	MAX-ACCESS not-accessible
    	STATUS current
    	DESCRIPTION
	"Represent the entry in the SNMPD table."
    INDEX { snmpdTableIndex }
    ::= { snmpdTable 1 }

SnmpdTableEntry::=
    SEQUENCE
    {
	snmpdTableIndex			Integer32, 
	snmpdTableDevice		OCTET STRING,	
	snmpdTableSubnet		IpAddress,
	snmpdTableNetmask		IpAddress,
	snmpdTableDevnet		INTEGER,
	snmpdTableComment		DisplayString,
	snmpdTableActive		INTEGER,
	snmpdTableRowStatus		RowStatus 
    }

snmpdTableIndex OBJECT-TYPE
    SYNTAX Integer32 (0..64)
    MAX-ACCESS not-accessible
    STATUS current
    DESCRIPTION
	"Specify the index of the SNMPD table."
    ::= { snmpdTableEntry 1 }

snmpdTableDevice OBJECT-TYPE
    SYNTAX OCTET STRING (SIZE (1..32))
    MAX-ACCESS read-create
    STATUS current
    DESCRIPTION
	"Allow access from device."
	DEFVAL { "Nil" }
    ::= { snmpdTableEntry 2 }

snmpdTableSubnet OBJECT-TYPE
    SYNTAX IpAddress
    MAX-ACCESS read-create
    STATUS current
    DESCRIPTION
	"Allow access from network"
    ::= { snmpdTableEntry 3 }

snmpdTableNetmask OBJECT-TYPE
    SYNTAX IpAddress
    MAX-ACCESS read-create
    STATUS current
    DESCRIPTION
	"Netmask for the subnet"
    ::= { snmpdTableEntry 4 }

snmpdTableDevnet OBJECT-TYPE
    SYNTAX INTEGER
    {
	device(1),
	network(2)
    }
    MAX-ACCESS read-create
    STATUS current
    DESCRIPTION
	"Define the type SNMPD Table entry: Use device or network"
    DEFVAL { device }
    ::= { snmpdTableEntry 5 }

snmpdTableComment OBJECT-TYPE
    SYNTAX DisplayString (SIZE (0..32))
    MAX-ACCESS read-create
    STATUS current
    DESCRIPTION
	"An optional comment associated to entry of the SNMPD table."
	DEFVAL { "Nil" }
    ::= { snmpdTableEntry 6 }

snmpdTableActive OBJECT-TYPE 
    SYNTAX INTEGER
    {
	enable(1),
	disable(2)
    }
    MAX-ACCESS read-create
    STATUS current
    DESCRIPTION
	"The status of the SNMPD table entry."
    DEFVAL { enable }
    ::= { snmpdTableEntry 7 }

snmpdTableRowStatus OBJECT-TYPE
   SYNTAX RowStatus
   MAX-ACCESS read-create
   STATUS current
   DESCRIPTION
        "The row status in the SNMPD table entry"
   ::= { snmpdTableEntry 8 }


-- =================== nodeConfigurationTrap ==============

trapActive OBJECT-TYPE
	SYNTAX INTEGER
	{
		enable(1),
		disable(2)
	}
	MAX-ACCESS read-write
	STATUS current
	DESCRIPTION
	"Enable/disable Trap management of the device"
	DEFVAL { disable }
	::= { nodeConfigurationTrap 1 }

trapConfiguration OBJECT-TYPE
	SYNTAX INTEGER
	{
		enable(1),
		disable(2)
	}
	MAX-ACCESS read-write
	STATUS current
	DESCRIPTION
	"Enable/disable the trap on Configuration"
	DEFVAL { enable }
	::= { nodeConfigurationTrap 2 }

trapSecurity OBJECT-TYPE
	SYNTAX INTEGER
	{
		enable(1),
		disable(2)
	}
	MAX-ACCESS read-write
	STATUS current
	DESCRIPTION
	"Enable/disable the trap on Security"
	DEFVAL { enable }
	::= { nodeConfigurationTrap 3 }

trapWireless OBJECT-TYPE
	SYNTAX INTEGER
	{
		enable(1),
		disable(2)
	}
	MAX-ACCESS read-write
	STATUS current
	DESCRIPTION
	"Enable/disable the trap on Wireless"
	DEFVAL { enable }
	::= { nodeConfigurationTrap 4 }

trapOperational OBJECT-TYPE
	SYNTAX INTEGER
	{
		enable(1),
		disable(2)
	}
	MAX-ACCESS read-write
	STATUS current
	DESCRIPTION
	"Enable/disable the trap on operational"
	DEFVAL { enable }
	::= { nodeConfigurationTrap 5 }

trapFlash OBJECT-TYPE
	SYNTAX INTEGER
	{
		enable(1),
		disable(2)
	}
	MAX-ACCESS read-write
	STATUS current
	DESCRIPTION
	"Enable/disable the trap on flash"
	DEFVAL { enable }
	::= { nodeConfigurationTrap 6 }

trapTftp OBJECT-TYPE
	SYNTAX INTEGER
	{
		enable(1),
		disable(2)
	}
	MAX-ACCESS read-write
	STATUS current
	DESCRIPTION
	"Enable/disable the trap on TFTP"
	DEFVAL { enable }
	::= { nodeConfigurationTrap 7 }

trapImage OBJECT-TYPE
	SYNTAX INTEGER
	{
		enable(1),
		disable(2)
	}
	MAX-ACCESS read-write
	STATUS current
	DESCRIPTION
	"Enable/disable the trap on Image"
	DEFVAL { enable }
	::= { nodeConfigurationTrap 8 }


trapAuthentication OBJECT-TYPE
	SYNTAX INTEGER
	{
		enable(1),
		disable(2)
	}
	MAX-ACCESS read-write
	STATUS current
	DESCRIPTION
	"Enable/disable the trap on authentication failure"
	DEFVAL { enable }
	::= { nodeConfigurationTrap 9 }

trapTable OBJECT-TYPE
    	SYNTAX SEQUENCE OF TrapTableEntry
    	MAX-ACCESS not-accessible
    	STATUS current
    	DESCRIPTION
	"This table display the SNMP Trap Host Table." 
    ::= { nodeConfigurationTrap 10 }

trapTableEntry OBJECT-TYPE
    	SYNTAX TrapTableEntry 
   	MAX-ACCESS not-accessible
    	STATUS current
    	DESCRIPTION
	"Represent the entry in the SNMP Trap Host table."
    INDEX { trapTableIndex }
    ::= { trapTable 1 }

TrapTableEntry::=
    SEQUENCE
    {
	trapTableIndex		Integer32, 
	trapTableIp			IpAddress,
	trapTableCommunity	DisplayString,
	trapTableUsername		DisplayString,
	trapTableAuthpasswd	DisplayString,
	trapTablePrivpasswd	DisplayString,
	trapTableVersion		INTEGER,
	trapTableComment		DisplayString,
	trapTableActive		INTEGER,
	trapTableRowStatus	RowStatus 
    }

trapTableIndex OBJECT-TYPE
    SYNTAX Integer32 (0..8)
    MAX-ACCESS not-accessible
    STATUS current
    DESCRIPTION
	"Specify the index of the SNMP Trap Host Table."
    ::= { trapTableEntry 1 }

trapTableIp OBJECT-TYPE
    SYNTAX IpAddress
    MAX-ACCESS read-create
    STATUS current
    DESCRIPTION
	"The destination IP Address of the SNMP Trap Host Table entry"
    ::= { trapTableEntry 2 }

trapTableCommunity OBJECT-TYPE
    SYNTAX DisplayString (SIZE (0|4..32))
    MAX-ACCESS read-create
    STATUS current
    DESCRIPTION
	"The community of the remote SNMP Host."
	DEFVAL { "Nil" }
    ::= { trapTableEntry 3 }

trapTableUsername OBJECT-TYPE
    SYNTAX DisplayString (SIZE (0|8..50))
    MAX-ACCESS read-create
    STATUS current
    DESCRIPTION
	"The username of the SNMP v3 trap manager."
	DEFVAL { "Nil" }
    ::= { trapTableEntry 4 }

trapTableAuthpasswd OBJECT-TYPE
    SYNTAX DisplayString (SIZE (0|8..50))
    MAX-ACCESS read-create
    STATUS current
    DESCRIPTION
	"The authentication password of the SNMP v3 trap manager."
	DEFVAL { "Nil" }
    ::= { trapTableEntry 5 }

trapTablePrivpasswd OBJECT-TYPE
    SYNTAX DisplayString (SIZE (0|8..50))
    MAX-ACCESS read-create
    STATUS current
    DESCRIPTION
	"The privacy password of the SNMP v3 trap manager."
	DEFVAL { "Nil" }
    ::= { trapTableEntry 6 }

trapTableVersion OBJECT-TYPE 
    SYNTAX INTEGER
    {
	version2c(1),
	version3(2)
    }
    MAX-ACCESS read-create
    STATUS current
    DESCRIPTION
	"The SNMP version used by the remote trap manager."
    DEFVAL { version2c }
    ::= { trapTableEntry 7 }

trapTableComment OBJECT-TYPE
    SYNTAX DisplayString (SIZE (0..32))
    MAX-ACCESS read-create
    STATUS current
    DESCRIPTION
	"An optional comment associated to entry of the SNMP Trap Host table."
	DEFVAL { "Nil" }
    ::= { trapTableEntry 8 }

trapTableActive OBJECT-TYPE 
    SYNTAX INTEGER
    {
	enable(1),
	disable(2)
    }
    MAX-ACCESS read-create
    STATUS current
    DESCRIPTION
	"The status of the SNMP Trap Host table entry."
    DEFVAL { enable }
    ::= { trapTableEntry 9 }

trapTableRowStatus OBJECT-TYPE
   SYNTAX RowStatus
   MAX-ACCESS read-create
   STATUS current
   DESCRIPTION
        "The row status in the SNMP Trap Host table entry"
   ::= { trapTableEntry 10 }

-- =================== nodeConfigurationDdns =============

ddnsActive OBJECT-TYPE
	SYNTAX INTEGER
	{
		enable(1),
		disable(2)
	}
	MAX-ACCESS read-write
	STATUS current
	DESCRIPTION
	"Enable/disable Dynamic DNS service of the device"
	DEFVAL { enable }
	::= { nodeConfigurationDdns 1 }

ddnsServer OBJECT-TYPE
	SYNTAX INTEGER
	{
		dyndns(1),
		easydns(2),
		no-ip(3),
		zoneedit(4),
		tzo(5)
	}
	MAX-ACCESS read-write
	STATUS current
	DESCRIPTION
	"Select the Dynamic DNS provider"
	DEFVAL { dyndns }
	::= { nodeConfigurationDdns 2 }

ddnsHostname OBJECT-TYPE
	SYNTAX DisplayString (SIZE (1..512))
	MAX-ACCESS read-write
	STATUS current
	DESCRIPTION
	"The hostname associated with the service provider"
		DEFVAL { "Nil" }
     ::= { nodeConfigurationDdns 3 }

ddnsUsername OBJECT-TYPE
	SYNTAX DisplayString (SIZE (1..32))
	MAX-ACCESS read-write
	STATUS current
	DESCRIPTION
	"The username"
	DEFVAL { "Nil" }
     ::= { nodeConfigurationDdns 4 }

ddnsPassword OBJECT-TYPE
	SYNTAX DisplayString (SIZE (1..32))
	MAX-ACCESS read-write
	STATUS current
	DESCRIPTION
	"The password"
	DEFVAL { "Nil" }
     ::= { nodeConfigurationDdns 5 }



-- ===================| nodeConfigurationZeroconfig |=====================

zeroconfigActive OBJECT-TYPE
	SYNTAX INTEGER
	{
		enable(1),
		disable(2)
	}
	MAX-ACCESS read-write
	STATUS current
	DESCRIPTION
	"Enable/disable Zero Config service of the device"
	DEFVAL { disable }
	::= { nodeConfigurationZeroconfig 1 }

zeroconfigProxyActive OBJECT-TYPE
	SYNTAX INTEGER
	{
		enable(1),
		disable(2)
	}
	MAX-ACCESS read-write
	STATUS current
	DESCRIPTION
	"Handle Client proxy"
	DEFVAL { enable }
	::= { nodeConfigurationZeroconfig 2 }

zeroconfigProxyport OBJECT-TYPE
	SYNTAX Integer32 (1000..65535)
	MAX-ACCESS read-write
	STATUS current
	DESCRIPTION
	"Port used in proxy login"
	DEFVAL { 8080 }
	::= { nodeConfigurationZeroconfig 3 }

zeroconfigStaticipActive OBJECT-TYPE
	SYNTAX INTEGER
	{
		enable(1),
		disable(2)
	}
	MAX-ACCESS read-write
	STATUS current
	DESCRIPTION
	"Handle static ip client"
	DEFVAL { enable }
	::= { nodeConfigurationZeroconfig 4 }

-- ==================| nodeConfigurationSignallevel |==================

signallevelExecute OBJECT-TYPE
	SYNTAX Integer32 (1..2)
	MAX-ACCESS read-only
	STATUS current
	DESCRIPTION
	"A command to execute the RSSI update"
	::= { nodeConfigurationSignallevel 1 }

signallevelTable OBJECT-TYPE
    	SYNTAX SEQUENCE OF SignallevelTableEntry
    	MAX-ACCESS not-accessible
    	STATUS current
    	DESCRIPTION
	"This table contains the list of signal level between the node and its neighbour nodes." 
    ::= { nodeConfigurationSignallevel 2 }

signallevelTableEntry OBJECT-TYPE
    	SYNTAX SignallevelTableEntry
   	MAX-ACCESS not-accessible
    	STATUS current
    	DESCRIPTION
	"Represent the entry in the Signal Level table."
    INDEX { signallevelTableIndex }
    ::= { signallevelTable 1 }

SignallevelTableEntry::=
    SEQUENCE
    {
	signallevelTableIndex		Integer32, 
	signallevelTableSource		OCTET STRING,
	signallevelTableDestination	OCTET STRING,
	signallevelTableRssi		OCTET STRING	
    }

signallevelTableIndex OBJECT-TYPE
    SYNTAX Integer32 (0..32)
    MAX-ACCESS not-accessible
    STATUS current
    DESCRIPTION
	"Specify the index of the node Signal Level table."
    ::= { signallevelTableEntry 1 }

signallevelTableSource OBJECT-TYPE
    SYNTAX OCTET STRING
    MAX-ACCESS read-only
    STATUS current
    DESCRIPTION
	"The source node's IP Address"
    ::= { signallevelTableEntry 2 } 

signallevelTableDestination OBJECT-TYPE
    SYNTAX OCTET STRING
    MAX-ACCESS read-only
    STATUS current
    DESCRIPTION
	"The destination node's IP Address"
    ::= { signallevelTableEntry 3 } 

signallevelTableRssi OBJECT-TYPE
    SYNTAX OCTET STRING
    MAX-ACCESS read-only
    STATUS current
    DESCRIPTION
	"The singal level between the source node and destination node in RSSI."
    ::= { signallevelTableEntry 4 } 





clientInfoTable OBJECT-TYPE
    	SYNTAX SEQUENCE OF ClientInfoTableEntry
    	MAX-ACCESS not-accessible
    	STATUS current
    	DESCRIPTION
	"This table contains the list of clients info of the nodes." 
    ::= { nodeConfigurationSignallevel 3 }

clientInfoTableEntry OBJECT-TYPE
    	SYNTAX ClientInfoTableEntry
   	MAX-ACCESS not-accessible
    	STATUS current
    	DESCRIPTION
	"Represent the entry in the Client Info table."
    INDEX { clientInfoTableIndex }
    ::= { clientInfoTable 1 }

ClientInfoTableEntry::=
    SEQUENCE
    {
	clientInfoTableIndex		Integer32, 
	clientInfoTableEssid		OCTET STRING,
	clientInfoTableMac		OCTET STRING,
	clientInfoTableChannel		OCTET STRING,
	clientInfoTableRate		OCTET STRING,	
	clientInfoTableRssi		OCTET STRING,
	clientInfoTableIdletime		OCTET STRING	
    }

clientInfoTableIndex OBJECT-TYPE
    SYNTAX Integer32 (0..4096)
    MAX-ACCESS not-accessible
    STATUS current
    DESCRIPTION
	"Specify the index of the node Client Info table."
    ::= { clientInfoTableEntry 1 }

clientInfoTableEssid OBJECT-TYPE
    SYNTAX OCTET STRING
    MAX-ACCESS read-only
    STATUS current
    DESCRIPTION
	"The ESSID of the AP"
    ::= { clientInfoTableEntry 2 } 

clientInfoTableMac OBJECT-TYPE
    SYNTAX OCTET STRING
    MAX-ACCESS read-only
    STATUS current
    DESCRIPTION
	"The MAC Address of the client"
    ::= { clientInfoTableEntry 3 } 

clientInfoTableChannel OBJECT-TYPE
    SYNTAX OCTET STRING
    MAX-ACCESS read-only
    STATUS current
    DESCRIPTION
	"The channel of the Client"
    ::= { clientInfoTableEntry 4 } 

clientInfoTableRate OBJECT-TYPE
    SYNTAX OCTET STRING
    MAX-ACCESS read-only
    STATUS current
    DESCRIPTION
	"The speed rate of the client in kbps"
    ::= { clientInfoTableEntry 5 } 


clientInfoTableRssi OBJECT-TYPE
    SYNTAX OCTET STRING
    MAX-ACCESS read-only
    STATUS current
    DESCRIPTION
	"The singal level between the client and node in RSSI."
    ::= { clientInfoTableEntry 6 } 

clientInfoTableIdletime OBJECT-TYPE
    SYNTAX OCTET STRING
    MAX-ACCESS read-only
    STATUS current
    DESCRIPTION
	"The idle timeout in second of the client."
	::= { clientInfoTableEntry 7 } 
	

clientStatTable OBJECT-TYPE
    	SYNTAX SEQUENCE OF ClientStatTableEntry
    	MAX-ACCESS not-accessible
    	STATUS current
    	DESCRIPTION
	"This table contains the details of the clients' statistic." 
    ::= { nodeConfigurationSignallevel 4 }

clientStatTableEntry OBJECT-TYPE
    	SYNTAX ClientStatTableEntry
   	MAX-ACCESS not-accessible
    	STATUS current
    	DESCRIPTION
	"Represent the entry in the Client Stat table."
    INDEX { clientStatTableIndex }
    ::= { clientStatTable 1 }

ClientStatTableEntry::=
    SEQUENCE
    {
	clientStatTableIndex		Integer32, 
	clientStatTableIp			IpAddress,
	clientStatTableMac		MacAddress,
	clientStatTableTx			OCTET STRING,
	clientStatTableRx			OCTET STRING,	
	clientStatTableTxPkt		OCTET STRING,
	clientStatTableRxPkt		OCTET STRING,
	clientStatTableOnlinetime	OCTET STRING	
    }

clientStatTableIndex OBJECT-TYPE
    SYNTAX Integer32 (0..512)
    MAX-ACCESS not-accessible
    STATUS current
    DESCRIPTION
	"Specify the index of the node Client Statistic table."
    ::= { clientStatTableEntry 1 }

clientStatTableIp OBJECT-TYPE
    SYNTAX IpAddress
    MAX-ACCESS read-only
    STATUS current
    DESCRIPTION
	"The IP Address of the clinet"
    ::= { clientStatTableEntry 2 } 

clientStatTableMac OBJECT-TYPE
    SYNTAX MacAddress
    MAX-ACCESS read-only
    STATUS current
    DESCRIPTION
	"The MAC Address of the client"
    ::= { clientStatTableEntry 3 } 

clientStatTableTx OBJECT-TYPE
    SYNTAX OCTET STRING
    MAX-ACCESS read-only
    STATUS current
    DESCRIPTION
	"The trasmit of the client in bytes count"
    ::= { clientStatTableEntry 4 } 

clientStatTableRx OBJECT-TYPE
    SYNTAX OCTET STRING
    MAX-ACCESS read-only
    STATUS current
    DESCRIPTION
	"The receive of the client in bytes count"
    ::= { clientStatTableEntry 5 } 

clientStatTableTxPkt OBJECT-TYPE
    SYNTAX OCTET STRING
    MAX-ACCESS read-only
    STATUS current
    DESCRIPTION
	"The transmit of the client in packets count.."
    ::= { clientStatTableEntry 6 } 

clientStatTableRxPkt OBJECT-TYPE
    SYNTAX OCTET STRING
    MAX-ACCESS read-only
    STATUS current
    DESCRIPTION
	"The receive of the client in packets count.."
	::= { clientStatTableEntry 7 } 

clientStatTableOnlinetime OBJECT-TYPE
    SYNTAX OCTET STRING
    MAX-ACCESS read-only
    STATUS current
    DESCRIPTION
	"The Online time of the client in 'HH:MM:SS'."
	::= { clientStatTableEntry 8 } 



-- ============| nodeConfigurationIpsec | ==============

ipsecActive OBJECT-TYPE
	SYNTAX INTEGER
	{
		enable(1),
		disable(2)
	}
	MAX-ACCESS read-write
	STATUS current
	DESCRIPTION
	"Enable the IP Sec service of the device"
	DEFVAL { enable }
	::= { nodeConfigurationIpsec 1 }

ipsecType OBJECT-TYPE
	SYNTAX INTEGER
	{
		x509(1),
		rsa(2),
		psk(3)
	}
	MAX-ACCESS read-write
	STATUS current
	DESCRIPTION
	"Select the type of the IP Sec "
	DEFVAL { x509 }
	::= { nodeConfigurationIpsec 2 }

ipsecLocalId OBJECT-TYPE
    SYNTAX OCTET STRING (SIZE (0..64))
    MAX-ACCESS read-write
    STATUS current
    DESCRIPTION 
	"Define the local identity."
	DEFVAL { "Nil" }
    ::= { nodeConfigurationIpsec 3 }

ipsecRemoteId OBJECT-TYPE
    SYNTAX OCTET STRING (SIZE (0..64))
    MAX-ACCESS read-write
    STATUS current
    DESCRIPTION 
	"Define the remote identity."
	DEFVAL { "Nil" }
    ::= { nodeConfigurationIpsec 4 }

ipsecRemoteIp OBJECT-TYPE
    SYNTAX IpAddress
    MAX-ACCESS read-write
    STATUS current
    DESCRIPTION 
	"Define the remote IP Address."
    ::= { nodeConfigurationIpsec 5 }

ipsecRemoteSubnet OBJECT-TYPE
    SYNTAX IpAddress
    MAX-ACCESS read-write
    STATUS current
    DESCRIPTION 
	"Define the remote Subnet."
    ::= { nodeConfigurationIpsec 6 }

ipsecRemoteNetmask OBJECT-TYPE
    SYNTAX IpAddress
    MAX-ACCESS read-write
    STATUS current
    DESCRIPTION 
	"Define the remote netmask for the subnet."
    ::= { nodeConfigurationIpsec 7 }

ipsecLocalCertpass OBJECT-TYPE
    SYNTAX OCTET STRING (SIZE (0..128))
    MAX-ACCESS read-write
    STATUS current
    DESCRIPTION 
	"Define the x.509 certificate pem passphrase."
	DEFVAL { "Nil" }
    ::= { nodeConfigurationIpsec 8 }

ipsecLocalRsa OBJECT-TYPE
    SYNTAX OCTET STRING (SIZE (0..1024))
    MAX-ACCESS read-write
    STATUS current
    DESCRIPTION 
	"Define the RSA Key."
	DEFVAL { "Nil" }
    ::= { nodeConfigurationIpsec 9 }

ipsecRemoteRsa OBJECT-TYPE
    SYNTAX OCTET STRING (SIZE (0..1024))
    MAX-ACCESS read-write
    STATUS current
    DESCRIPTION 
	"Define the remote RSA Key."
	DEFVAL { "Nil" }
    ::= { nodeConfigurationIpsec 10	}

ipsecPsk OBJECT-TYPE
    SYNTAX OCTET STRING (SIZE (0..1024))
    MAX-ACCESS read-write
    STATUS current
    DESCRIPTION 
	"Define the PSK Key."
	DEFVAL { "Nil" }
    ::= { nodeConfigurationIpsec 11	}

-- ============| nodeConfigurationL2tpc |===============

l2tpcActive OBJECT-TYPE
	SYNTAX INTEGER
	{
		enable(1),
		disable(2)
	}
	MAX-ACCESS read-write
	STATUS current
	DESCRIPTION
	"Enable the L2TP Client feature of the device"
	DEFVAL { enable }
	::= { nodeConfigurationL2tpc 1 }

l2tpcLns OBJECT-TYPE
    SYNTAX OCTET STRING (SIZE (0..128))
    MAX-ACCESS read-write
    STATUS current
    DESCRIPTION 
	"Define the L2TP LNS address (Type: DNS String)"
		DEFVAL { "Nil" }
    ::= { nodeConfigurationL2tpc 2 }

l2tpcUsername OBJECT-TYPE
	SYNTAX DisplayString (SIZE (0..128))
	MAX-ACCESS read-write
	STATUS current
	DESCRIPTION
	"The username of the L2TP Client"
	DEFVAL { "Nil" }
     ::= { nodeConfigurationL2tpc 3 }

l2tpcSecret OBJECT-TYPE
	SYNTAX DisplayString (SIZE (0..128))
	MAX-ACCESS read-write
	STATUS current
	DESCRIPTION
	"The secret key of the L2TP Client"
	DEFVAL { "Nil" }
     ::= { nodeConfigurationL2tpc 4 }

-- ============| nodeConfigurationAutoip	| ====================	

autoipActive OBJECT-TYPE
	SYNTAX INTEGER
	{
		enable(1),
		disable(2)
	}
	MAX-ACCESS read-write
	STATUS current
	DESCRIPTION
	"Enable the auto IP service of the device"
	DEFVAL { enable }
	::= { nodeConfigurationAutoip 1 }

autoipMeship OBJECT-TYPE
	SYNTAX Integer32 (0..255)
	MAX-ACCESS read-write
	STATUS current
	DESCRIPTION
	"The prefix of the mesh IP Address."
	DEFVAL { 10 }
	::= { nodeConfigurationAutoip 2 }

autoipVlanip OBJECT-TYPE
	SYNTAX Integer32 (0..255)
	MAX-ACCESS read-write
	STATUS current
	DESCRIPTION
	"The prefix of the vlan IP Address"
	DEFVAL { 172 }
	::= { nodeConfigurationAutoip 3 }

-- ============| nodeConfigurationInterfaces | ===============

interfacesTable OBJECT-TYPE
    	SYNTAX SEQUENCE OF InterfacesTableEntry
    	MAX-ACCESS not-accessible
    	STATUS current
    	DESCRIPTION
	"This table contains the list of interfaces name of the system." 
    ::= { nodeConfigurationInterfaces 1 }

interfacesTableEntry OBJECT-TYPE
    	SYNTAX InterfacesTableEntry
   	MAX-ACCESS not-accessible
    	STATUS current
    	DESCRIPTION
	"Represent the entry in the Interfaces table."
    INDEX { interfacesTableIndex }
    ::= { interfacesTable 1 }

InterfacesTableEntry::=
    SEQUENCE
    {
	interfacesTableIndex		Integer32, 
	interfacesTableDev		OCTET STRING,
	interfacesTableLabel		OCTET STRING
    }

interfacesTableIndex OBJECT-TYPE
    SYNTAX Integer32 (0..64)
    MAX-ACCESS not-accessible
    STATUS current
    DESCRIPTION
	"Specify the index of the interfaces table."
    ::= { interfacesTableEntry 1 }

interfacesTableDev OBJECT-TYPE
    SYNTAX OCTET STRING
    MAX-ACCESS read-only
    STATUS current
    DESCRIPTION
	"The name of the interfaces "
    ::= { interfacesTableEntry 2 } 

interfacesTableLabel OBJECT-TYPE
    SYNTAX OCTET STRING
    MAX-ACCESS read-only
    STATUS current
    DESCRIPTION
	"The label of the interfaces "
    ::= { interfacesTableEntry 3 } 


-- ============| nodeConfigurationMlrd | =============

mlrdActive OBJECT-TYPE
	SYNTAX INTEGER
	{
		enable(1),
		disable(2)
	}
	MAX-ACCESS read-write
	STATUS current
	DESCRIPTION
	"Enable the MLRD service of the device"
	DEFVAL { enable }
	::= { nodeConfigurationMlrd 1 }

mlrdNetname	OBJECT-TYPE
	SYNTAX OCTET STRING (SIZE(0..32))
	MAX-ACCESS read-write
	STATUS current
	DESCRIPTION
	"The Mobile IP Network name"
	DEFVAL { "Nil" }
     ::= { nodeConfigurationMlrd 2 }

mlrdBackupActive OBJECT-TYPE
	SYNTAX INTEGER
	{
		enable(1),
		disable(2)
	}
	MAX-ACCESS read-write
	STATUS current
	DESCRIPTION
	"Enable the MLRD backup server"
	DEFVAL { disable }
	::= { nodeConfigurationMlrd 3 }

mlrdRole OBJECT-TYPE
	SYNTAX INTEGER
	{
		primary(1),
		backup(2)
	}
	MAX-ACCESS read-write
	STATUS current
	DESCRIPTION
	"The role of the server"
		DEFVAL { primary }
	::= { nodeConfigurationMlrd 4 }

mlrdPeer	OBJECT-TYPE
	SYNTAX OCTET STRING (SIZE(0..128))
	MAX-ACCESS read-write
	STATUS current
	DESCRIPTION
	"Primary/Secondary Server address depends on current role "
	DEFVAL { "Nil" }
     ::= { nodeConfigurationMlrd 5 }

mlrdBackupInterval OBJECT-TYPE 
    SYNTAX Integer32 (2..9999)
    MAX-ACCESS read-write
    STATUS current
    DESCRIPTION 
	"The backup interval, in minute."
	DEFVAL { 5 }
    ::= { nodeConfigurationMlrd 6 }

mlrdStaticActive OBJECT-TYPE
	SYNTAX INTEGER
	{
		enable(1),
		disable(2)
	}
	MAX-ACCESS read-write
	STATUS current
	DESCRIPTION
	"Enable or disable the static entry"
	DEFVAL { disable }
	::= { nodeConfigurationMlrd 7 }

mlrdTable OBJECT-TYPE
    	SYNTAX SEQUENCE OF MlrdTableEntry
    	MAX-ACCESS not-accessible
    	STATUS current
    	DESCRIPTION
	"The MLRD Static entry table." 
    ::= { nodeConfigurationMlrd 8 }

mlrdTableEntry OBJECT-TYPE
    	SYNTAX MlrdTableEntry 
   	MAX-ACCESS not-accessible
    	STATUS current
    	DESCRIPTION
	"Represent the entry in the MLRD static entry table."
    INDEX { mlrdTableIndex }
    ::= { mlrdTable 1 }

MlrdTableEntry::=
    SEQUENCE
    {
	mlrdTableIndex		Integer32, 
	mlrdTableMac		MacAddress,
	mlrdTableIp			IpAddress,
	mlrdTableParent		IpAddress,
	mlrdTableDefaultRoute	IpAddress,
	mlrdTableComment		DisplayString,
	mlrdTableActive		INTEGER,
	mlrdTableRowStatus	RowStatus 
    }

mlrdTableIndex OBJECT-TYPE
    SYNTAX Integer32 (0..8)
    MAX-ACCESS not-accessible
    STATUS current
    DESCRIPTION
	"Specify the index of the MLRD static entry Table."
    ::= { mlrdTableEntry 1 }

mlrdTableMac OBJECT-TYPE
    SYNTAX MacAddress
    MAX-ACCESS read-create
    STATUS current
    DESCRIPTION
	"The static station Mac Address."
    ::= { mlrdTableEntry 2 }

mlrdTableIp OBJECT-TYPE
    SYNTAX IpAddress
    MAX-ACCESS read-create
    STATUS current
    DESCRIPTION
	"The station assigned IP Address."
    ::= { mlrdTableEntry 3 }

mlrdTableParent OBJECT-TYPE
    SYNTAX IpAddress
    MAX-ACCESS read-create
    STATUS current
    DESCRIPTION
	"The station assigned parent."
    ::= { mlrdTableEntry 4 }

mlrdTableDefaultRoute OBJECT-TYPE
    SYNTAX IpAddress
    MAX-ACCESS read-create
    STATUS current
    DESCRIPTION
	"The station's default route."
    ::= { mlrdTableEntry 5 }

mlrdTableComment OBJECT-TYPE
    SYNTAX DisplayString (SIZE (0..32))
    MAX-ACCESS read-create
    STATUS current
    DESCRIPTION
	"An optional comment associated to entry of the MLRD static entry table."
	DEFVAL { "Nil" }
    ::= { mlrdTableEntry 6 }

mlrdTableActive OBJECT-TYPE 
    SYNTAX INTEGER
    {
	enable(1),
	disable(2)
    }
    MAX-ACCESS read-create
    STATUS current
    DESCRIPTION
	"The status of the MLRD static table entry."
    DEFVAL { enable }
    ::= { mlrdTableEntry 7 }

mlrdTableRowStatus OBJECT-TYPE
   SYNTAX RowStatus
   MAX-ACCESS read-create
   STATUS current
   DESCRIPTION
        "The row status in the MLRD static entry table row"
   ::= { mlrdTableEntry 8 }


-- ============| nodeConfigurationRoutedog | =============

routedogActive OBJECT-TYPE
	SYNTAX INTEGER
	{
		enable(1),
		disable(2)
	}
	MAX-ACCESS read-write
	STATUS current
	DESCRIPTION
	"Enable the route watch dog service of the device"
	DEFVAL { enable }
	::= { nodeConfigurationRoutedog 1 }

routedogSsid OBJECT-TYPE
	SYNTAX DisplayString (SIZE (0..32))
	MAX-ACCESS read-write
	STATUS current
	DESCRIPTION
	"The SSID used when no default routes"
	DEFVAL { "ServiceDown" }
     ::= { nodeConfigurationRoutedog 2 }
	
routedogInterval OBJECT-TYPE
	SYNTAX Integer32 (10..60)
	MAX-ACCESS read-write
	STATUS current
	DESCRIPTION
	"Checking interval"
	DEFVAL { 30 }
	::= { nodeConfigurationRoutedog 3 }

routedogReboot OBJECT-TYPE
	SYNTAX INTEGER
	{
		enable(1),
		disable(2)
	}
	MAX-ACCESS read-write
	STATUS current
	DESCRIPTION
	"Enable the system to reboot when interval count is reached"
	DEFVAL { disable }
	::= { nodeConfigurationRoutedog 4 }

routedogIntervaCount OBJECT-TYPE
	SYNTAX Integer32 (1..255)
	MAX-ACCESS read-write
	STATUS current
	DESCRIPTION
	"Number of interval before perform system reboot"
	DEFVAL { 10 }
	::= { nodeConfigurationRoutedog 5 }

-- ============| nodeConfigurationLinuxdog | =============

linuxdogActive OBJECT-TYPE
	SYNTAX INTEGER
	{
		enable(1),
		disable(2)
	}
	MAX-ACCESS read-write
	STATUS current
	DESCRIPTION
	"Enable the Linux Kernel watch dog service of the device"
	DEFVAL { enable }
	::= { nodeConfigurationLinuxdog 1 }


linuxdogInterval OBJECT-TYPE
	SYNTAX Integer32 (10..60)
	MAX-ACCESS read-write
	STATUS current
	DESCRIPTION
	"Checking interval"
	DEFVAL { 60 }
	::= { nodeConfigurationLinuxdog 2 }


-- ============| nodeConfigurationAdvTunning | =========

advTunningConntrackMax OBJECT-TYPE
	SYNTAX Integer32 (4096..212368)
	MAX-ACCESS read-write
	STATUS current
	DESCRIPTION
	"Max Connection Tracking"
	DEFVAL { 212368 }
	::= { nodeConfigurationAdvTunning 1 }

advTunningConntrackGenericTimeout OBJECT-TYPE
	SYNTAX Integer32 (50..1200)
	MAX-ACCESS read-write
	STATUS current
	DESCRIPTION
	"Connection Tracking generic timeout"
	DEFVAL { 600 }
	::= { nodeConfigurationAdvTunning 2 }

advTunningConntrackIcmpTimeout OBJECT-TYPE
	SYNTAX Integer32 (10..60)
	MAX-ACCESS read-write
	STATUS current
	DESCRIPTION
	"Connection Tracking icmp timeout"
	DEFVAL { 30 }
	::= { nodeConfigurationAdvTunning 3 }

advTunningConntrackTcpcloseTimeout OBJECT-TYPE
	SYNTAX Integer32 (5..30)
	MAX-ACCESS read-write
	STATUS current
	DESCRIPTION
	"Connection Tracking TCP close timeout"
	DEFVAL { 10 }
	::= { nodeConfigurationAdvTunning 4 }

advTunningConntrackTcpclosewaitTimeout OBJECT-TYPE
	SYNTAX Integer32 (10..120)
	MAX-ACCESS read-write
	STATUS current
	DESCRIPTION
	"Connection Tracking TCP close wait timeout"
	DEFVAL { 60 }
	::= { nodeConfigurationAdvTunning 5 }

advTunningConntrackTcpestablishTimeout OBJECT-TYPE
	SYNTAX Integer32 (600..864000)
	MAX-ACCESS read-write
	STATUS current
	DESCRIPTION
	"Connection Tracking TCP established timeout"
	DEFVAL { 3600 }
	::= { nodeConfigurationAdvTunning 6 }

advTunningConntrackTcpfinwaitTimeout OBJECT-TYPE
	SYNTAX Integer32 (10..3600)
	MAX-ACCESS read-write
	STATUS current
	DESCRIPTION
	"Connection Tracking TCP finished wait timeout"
	DEFVAL { 120 }
	::= { nodeConfigurationAdvTunning 7 }

advTunningConntrackTcplastackTimeout OBJECT-TYPE
	SYNTAX Integer32 (10..60)
	MAX-ACCESS read-write
	STATUS current
	DESCRIPTION
	"Connection Tracking TCP last ack timeout"
	DEFVAL { 30 }
	::= { nodeConfigurationAdvTunning 8 }

advTunningConntrackTcpsynrecvTimeout OBJECT-TYPE
	SYNTAX Integer32 (10..120)
	MAX-ACCESS read-write
	STATUS current
	DESCRIPTION
	"Connection Tracking TCP syn receive timeout"
	DEFVAL { 60 }
	::= { nodeConfigurationAdvTunning 9 }

advTunningConntrackTcpsynsentTimeout OBJECT-TYPE
	SYNTAX Integer32 (10..240)
	MAX-ACCESS read-write
	STATUS current
	DESCRIPTION
	"Connection Tracking TCP syn sent timeout"
	DEFVAL { 120 }
	::= { nodeConfigurationAdvTunning 10 }

advTunningConntrackTcptimewaitTimeout OBJECT-TYPE
	SYNTAX Integer32 (10..240)
	MAX-ACCESS read-write
	STATUS current
	DESCRIPTION
	"Connection Tracking TCP time wait timeout"
	DEFVAL { 120 }
	::= { nodeConfigurationAdvTunning 11 }

advTunningConntrackUdpTimeout OBJECT-TYPE
	SYNTAX Integer32 (10..60)
	MAX-ACCESS read-write
	STATUS current
	DESCRIPTION
	"Connection Tracking UDP timeout"
	DEFVAL { 30 }
	::= { nodeConfigurationAdvTunning 12 }

advTunningConntrackUdpstreamTimeout OBJECT-TYPE
	SYNTAX Integer32 (10..360)
	MAX-ACCESS read-write
	STATUS current
	DESCRIPTION
	"Connection Tracking UDP stream timeout"
	DEFVAL { 180 }
	::= { nodeConfigurationAdvTunning 13 }

advTunningWirelessRadio0Distance OBJECT-TYPE
	SYNTAX Integer32 (100..10000)
	MAX-ACCESS read-write
	STATUS current
	DESCRIPTION
	"Estimate operating distance (meter) 0 - card default"
	DEFVAL { 400 }
	::= { nodeConfigurationAdvTunning 14 }

advTunningWirelessRadio1Distance OBJECT-TYPE
	SYNTAX Integer32 (100..10000)
	MAX-ACCESS read-write
	STATUS current
	DESCRIPTION
	"Estimate operating distance (meter) 0 - card default"
	DEFVAL { 400 }
	::= { nodeConfigurationAdvTunning 15 }

advTunningWirelessRadio2Distance OBJECT-TYPE
	SYNTAX Integer32 (100..10000)
	MAX-ACCESS read-write
	STATUS current
	DESCRIPTION
	"Estimate operating distance (meter) 0 - card default"
	DEFVAL { 400 }
	::= { nodeConfigurationAdvTunning 16 }

advTunningWirelessRadio3Distance OBJECT-TYPE
	SYNTAX Integer32 (100..10000)
	MAX-ACCESS read-write
	STATUS current
	DESCRIPTION
	"Estimate operating distance (meter) 0 - card default"
	DEFVAL { 400 }
	::= { nodeConfigurationAdvTunning 17 }

advTunningWirelessRegionDomain OBJECT-TYPE
	SYNTAX Integer32 (1..9999)
	MAX-ACCESS read-only
	STATUS current
	DESCRIPTION
	"The wireless regulatory domain"
	DEFVAL { 10 }
	::= { nodeConfigurationAdvTunning 18 }

advTunningWirelessCountry OBJECT-TYPE
	SYNTAX Integer32 (1..9999)
	MAX-ACCESS read-write
	STATUS current
	DESCRIPTION
	"Wireless Country settings"
	DEFVAL { 840 }
	::= { nodeConfigurationAdvTunning 19 }

advTunningWirelessOutdoor OBJECT-TYPE
       SYNTAX INTEGER
	{
		enable(1),
		disable(2)
	}
	MAX-ACCESS read-write
	STATUS current
	DESCRIPTION
		"Operating in Outdoor"
	DEFVAL { enable }
	::= { nodeConfigurationAdvTunning 20 }

advTunningWirelessXChannel OBJECT-TYPE
       SYNTAX INTEGER
	{
		enable(1),
		disable(2)
	}
	MAX-ACCESS read-write
	STATUS current
	DESCRIPTION
		"Enable extended channel mode"
	DEFVAL { disable }
	::= { nodeConfigurationAdvTunning 21 }


-- ============| nodeConfigurationSshd |================

sshdActive OBJECT-TYPE
       	SYNTAX INTEGER
	{
		enable(1),
		disable(2)
	}
	MAX-ACCESS read-write
	STATUS current
	DESCRIPTION
	"Enable the SSH  service of the device"
	DEFVAL { enable }
	::= { nodeConfigurationSshd 1 }

sshdPort OBJECT-TYPE
   SYNTAX Integer32 (1..65535)
   MAX-ACCESS read-write
   STATUS current
   DESCRIPTION 
       "The port number of the device use for SSH purpose."
   DEFVAL { 22 }
   ::= { nodeConfigurationSshd 2 }

-- ============| nodeConfigutationWme | ====================


wmeTable OBJECT-TYPE
    	SYNTAX SEQUENCE OF WmeTableEntry
    	MAX-ACCESS not-accessible
    	STATUS current
    	DESCRIPTION
	"The Wireless Multimedia Extension table." 
    ::= { nodeConfigutationWme 1 }

wmeTableEntry OBJECT-TYPE
    	SYNTAX WmeTableEntry 
   	MAX-ACCESS not-accessible
    	STATUS current
    	DESCRIPTION
	"Represent the entry in the WME table."
    INDEX { wmeTableIndex }
    ::= { wmeTable 1 }

WmeTableEntry::=
    SEQUENCE
    {
	wmeTableIndex		Integer32, 
	wmeTableName		OCTET STRING,
	wmeTableCwminBe		Integer32,
	wmeTableCwminBk		Integer32,
	wmeTableCwminVi		Integer32,
	wmeTableCwminVo		Integer32,
	wmeTableBssCwminBe		Integer32,
	wmeTableBssCwminBk		Integer32,
	wmeTableBssCwminVi		Integer32,
	wmeTableBssCwminVo		Integer32,
	wmeTableCwmaxBe		Integer32,
	wmeTableCwmaxBk		Integer32,
	wmeTableCwmaxVi		Integer32,
	wmeTableCwmaxVo		Integer32,
	wmeTableBssCwmaxBe		Integer32,
	wmeTableBssCwmaxBk		Integer32,
	wmeTableBssCwmaxVi		Integer32,
	wmeTableBssCwmaxVo		Integer32,
	wmeTableAifsnBe		Integer32,
	wmeTableAifsnBk		Integer32,
	wmeTableAifsnVi		Integer32,
	wmeTableAifsnVo		Integer32,
	wmeTableBssAifsnBe		Integer32,
	wmeTableBssAifsnBk		Integer32,
	wmeTableBssAifsnVi		Integer32,
	wmeTableBssAifsnVo		Integer32,
	wmeTableTxoplimitBe		Integer32,
	wmeTableTxoplimitBk		Integer32,
	wmeTableTxoplimitVi		Integer32,
	wmeTableTxoplimitVo		Integer32,
	wmeTableBssTxoplimitBe		Integer32,
	wmeTableBssTxoplimitBk		Integer32,
	wmeTableBssTxoplimitVi		Integer32,
	wmeTableBssTxoplimitVo		Integer32,
	wmeTableAcmBe		INTEGER,
	wmeTableAcmBk		INTEGER,
	wmeTableAcmVi		INTEGER,
	wmeTableAcmVo		INTEGER,
	wmeTableNoackpolicyBe		INTEGER,
	wmeTableNoackpolicyBk		INTEGER,
	wmeTableNoackpolicyVi		INTEGER,
	wmeTableNoackpolicyVo		INTEGER,
	wmeTableComment		DisplayString,
	wmeTableActive		INTEGER,
	wmeTableRowStatus		RowStatus 
    }

wmeTableIndex OBJECT-TYPE
    SYNTAX Integer32 (0..16)
    MAX-ACCESS not-accessible
    STATUS current
    DESCRIPTION
	"Specify the index of the WME Table."
    ::= { wmeTableEntry 1 }

wmeTableName OBJECT-TYPE
    SYNTAX OCTET STRING (SIZE (0..32))
    MAX-ACCESS read-create
    STATUS current
    DESCRIPTION
	"The interface name."
	DEFVAL { "Nil" }
    ::= { wmeTableEntry 2 }

wmeTableCwminBe OBJECT-TYPE
	SYNTAX Integer32 (0..255)
	MAX-ACCESS read-create
	STATUS current
	DESCRIPTION
	   "CWMIN parameter for Best effort class"
	DEFVAL { 4 }
	::= { wmeTableEntry 3 }	

wmeTableCwminBk OBJECT-TYPE
	SYNTAX Integer32 (0..255)
	MAX-ACCESS read-create
	STATUS current
	DESCRIPTION
	   "CWMIN parameter for background class"
	DEFVAL { 4 }
	::= { wmeTableEntry 4 }	

wmeTableCwminVi OBJECT-TYPE
	SYNTAX Integer32 (0..255)
	MAX-ACCESS read-create
	STATUS current
	DESCRIPTION
	   "CWMIN parameter for Video class"
	DEFVAL { 3 }
	::= { wmeTableEntry 5 }	

wmeTableCwminVo OBJECT-TYPE
	SYNTAX Integer32 (0..255)
	MAX-ACCESS read-create
	STATUS current
	DESCRIPTION
	   "CWMIN parameter for Voice class"
	DEFVAL { 2 }
	::= { wmeTableEntry 6 }	

wmeTableBssCwminBe OBJECT-TYPE
	SYNTAX Integer32 (0..255)
	MAX-ACCESS read-create
	STATUS current
	DESCRIPTION
	   "BSS_CWMIN parameter for Best effort class"
	DEFVAL { 4 }
	::= { wmeTableEntry 7 }	

wmeTableBssCwminBk OBJECT-TYPE
	SYNTAX Integer32 (0..255)
	MAX-ACCESS read-create
	STATUS current
	DESCRIPTION
	   "BSS_CWMIN parameter for background class"
	DEFVAL { 4 }
	::= { wmeTableEntry 8 }	

wmeTableBssCwminVi OBJECT-TYPE
	SYNTAX Integer32 (0..255)
	MAX-ACCESS read-create
	STATUS current
	DESCRIPTION
	   "BSS_CWMIN parameter for Video class"
	DEFVAL { 3 }
	::= { wmeTableEntry 9 }	

wmeTableBssCwminVo OBJECT-TYPE
	SYNTAX Integer32 (0..255)
	MAX-ACCESS read-create
	STATUS current
	DESCRIPTION
	   "BSS_CWMIN parameter for Voice class"
	DEFVAL { 2 }
	::= { wmeTableEntry 10 }	


wmeTableCwmaxBe OBJECT-TYPE
	SYNTAX Integer32 (0..255)
	MAX-ACCESS read-create
	STATUS current
	DESCRIPTION
	   "CWMAX parameter for Best effort class"
	DEFVAL { 6 }
	::= { wmeTableEntry 11 }	

wmeTableCwmaxBk OBJECT-TYPE
	SYNTAX Integer32 (0..255)
	MAX-ACCESS read-create
	STATUS current
	DESCRIPTION
	   "CWMAX parameter for background class"
	DEFVAL { 10 }
	::= { wmeTableEntry 12 }	

wmeTableCwmaxVi OBJECT-TYPE
	SYNTAX Integer32 (0..255)
	MAX-ACCESS read-create
	STATUS current
	DESCRIPTION
	   "CWMAX parameter for Video class"
	DEFVAL { 4 }
	::= { wmeTableEntry 13 }	

wmeTableCwmaxVo OBJECT-TYPE
	SYNTAX Integer32 (0..255)
	MAX-ACCESS read-create
	STATUS current
	DESCRIPTION
	   "CWMAX parameter for Voice class"
	DEFVAL { 3 }
	::= { wmeTableEntry 14 }	

wmeTableBssCwmaxBe OBJECT-TYPE
	SYNTAX Integer32 (0..255)
	MAX-ACCESS read-create
	STATUS current
	DESCRIPTION
	   "BSS_CWMAX parameter for Best effort class"
	DEFVAL { 10 }
	::= { wmeTableEntry 15 }	

wmeTableBssCwmaxBk OBJECT-TYPE
	SYNTAX Integer32 (0..255)
	MAX-ACCESS read-create
	STATUS current
	DESCRIPTION
	   "BSS_CWMAX parameter for background class"
	DEFVAL { 10 }
	::= { wmeTableEntry 16 }	

wmeTableBssCwmaxVi OBJECT-TYPE
	SYNTAX Integer32 (0..255)
	MAX-ACCESS read-create
	STATUS current
	DESCRIPTION
	   "BSS_CWMAX parameter for Video class"
	DEFVAL { 4 }
	::= { wmeTableEntry 17 }	

wmeTableBssCwmaxVo OBJECT-TYPE
	SYNTAX Integer32 (0..255)
	MAX-ACCESS read-create
	STATUS current
	DESCRIPTION
	   "BSS_CWMAX parameter for Voice class"
	DEFVAL { 3 }
	::= { wmeTableEntry 18 }	




wmeTableAifsnBe OBJECT-TYPE
	SYNTAX Integer32 (0..255)
	MAX-ACCESS read-create
	STATUS current
	DESCRIPTION
	   "AIFSN parameter for Best effort class"
	DEFVAL { 3 }
	::= { wmeTableEntry 19 }	

wmeTableAifsnBk OBJECT-TYPE
	SYNTAX Integer32 (0..255)
	MAX-ACCESS read-create
	STATUS current
	DESCRIPTION
	   "AIFSN parameter for background class"
	DEFVAL { 7 }
	::= { wmeTableEntry 20 }	

wmeTableAifsnVi OBJECT-TYPE
	SYNTAX Integer32 (0..255)
	MAX-ACCESS read-create
	STATUS current
	DESCRIPTION
	   "AIFSN parameter for Video class"
	DEFVAL { 1 }
	::= { wmeTableEntry 21 }	

wmeTableAifsnVo OBJECT-TYPE
	SYNTAX Integer32 (0..255)
	MAX-ACCESS read-create
	STATUS current
	DESCRIPTION
	   "AIFSN parameter for Voice class"
	DEFVAL { 1 }
	::= { wmeTableEntry 22 }	


wmeTableBssAifsnBe OBJECT-TYPE
	SYNTAX Integer32 (0..255)
	MAX-ACCESS read-create
	STATUS current
	DESCRIPTION
	   "BSS_AIFSN parameter for Best effort class"
	DEFVAL { 3 }
	::= { wmeTableEntry 23 }	

wmeTableBssAifsnBk OBJECT-TYPE
	SYNTAX Integer32 (0..255)
	MAX-ACCESS read-create
	STATUS current
	DESCRIPTION
	   "BSS_AIFSN parameter for background class"
	DEFVAL { 7 }
	::= { wmeTableEntry 24 }	

wmeTableBssAifsnVi OBJECT-TYPE
	SYNTAX Integer32 (0..255)
	MAX-ACCESS read-create
	STATUS current
	DESCRIPTION
	   "BSS_AIFSN parameter for Video class"
	DEFVAL { 2 }
	::= { wmeTableEntry 25 }	

wmeTableBssAifsnVo OBJECT-TYPE
	SYNTAX Integer32 (0..255)
	MAX-ACCESS read-create
	STATUS current
	DESCRIPTION
	   "BSS_AIFSN parameter for Voice class"
	DEFVAL { 2 }
	::= { wmeTableEntry 26 }	



wmeTableTxoplimitBe OBJECT-TYPE
	SYNTAX Integer32 (0..65535)
	MAX-ACCESS read-create
	STATUS current
	DESCRIPTION
	   "TXOPLIMIT parameter for Best effort class (in miliseconds)"
	DEFVAL { 0 }
	::= { wmeTableEntry 27 }	

wmeTableTxoplimitBk OBJECT-TYPE
	SYNTAX Integer32 (0..65535)
	MAX-ACCESS read-create
	STATUS current
	DESCRIPTION
	   "TXOPLIMIT parameter for Background class (in miliseconds)"
	DEFVAL { 0 }
	::= { wmeTableEntry 28 }	

wmeTableTxoplimitVi OBJECT-TYPE
	SYNTAX Integer32 (0..65535)
	MAX-ACCESS read-create
	STATUS current
	DESCRIPTION
	   "TXOPLIMIT parameter for Video class (in miliseconds)"
	DEFVAL { 3008 }
	::= { wmeTableEntry 29 }	

wmeTableTxoplimitVo OBJECT-TYPE
	SYNTAX Integer32 (0..65535)
	MAX-ACCESS read-create
	STATUS current
	DESCRIPTION
	   "TXOPLIMIT parameter for Voice class (in miliseconds)"
	DEFVAL { 1504 }
	::= { wmeTableEntry 30 }	


wmeTableBssTxoplimitBe OBJECT-TYPE
	SYNTAX Integer32 (0..65535)
	MAX-ACCESS read-create
	STATUS current
	DESCRIPTION
	   "BSS_TXOPLIMIT parameter for Best effort class (in miliseconds)"
	DEFVAL { 0 }
	::= { wmeTableEntry 31 }	

wmeTableBssTxoplimitBk OBJECT-TYPE
	SYNTAX Integer32 (0..65535)
	MAX-ACCESS read-create
	STATUS current
	DESCRIPTION
	   "BSS_TXOPLIMIT parameter for Background class (in miliseconds)"
	DEFVAL { 0 }
	::= { wmeTableEntry 32 }	

wmeTableBssTxoplimitVi OBJECT-TYPE
	SYNTAX Integer32 (0..65535)
	MAX-ACCESS read-create
	STATUS current
	DESCRIPTION
	   "BSS_TXOPLIMIT parameter for Video class (in miliseconds)"
	DEFVAL { 3008 }
	::= { wmeTableEntry 33 }	

wmeTableBssTxoplimitVo OBJECT-TYPE
	SYNTAX Integer32 (0..65535)
	MAX-ACCESS read-create
	STATUS current
	DESCRIPTION
	   "BSS_TXOPLIMIT parameter for Voice class (in miliseconds)"
	DEFVAL { 1504 }
	::= { wmeTableEntry 34 }


wmeTableAcmBe OBJECT-TYPE 
    SYNTAX INTEGER
    {
	enable(1),
	disable(2)
    }
    MAX-ACCESS read-create
    STATUS current
    DESCRIPTION
	"Enable / Disable Admission Control for Best effort class."
    DEFVAL { disable }
    ::= { wmeTableEntry 35 }

wmeTableAcmBk OBJECT-TYPE 
    SYNTAX INTEGER
    {
	enable(1),
	disable(2)
    }
    MAX-ACCESS read-create
    STATUS current
    DESCRIPTION
	"Enable / Disable Admission Control for Background class."
    DEFVAL { disable }
    ::= { wmeTableEntry 36 }

wmeTableAcmVi OBJECT-TYPE 
    SYNTAX INTEGER
    {
	enable(1),
	disable(2)
    }
    MAX-ACCESS read-create
    STATUS current
    DESCRIPTION
	"Enable / Disable Admission Control for Video class."
    DEFVAL { disable }
    ::= { wmeTableEntry 37 }

wmeTableAcmVo OBJECT-TYPE 
    SYNTAX INTEGER
    {
	enable(1),
	disable(2)
    }
    MAX-ACCESS read-create
    STATUS current
    DESCRIPTION
	"Enable / Disable Admission Control for Voice class."
    DEFVAL { disable }
    ::= { wmeTableEntry 38 }


wmeTableNoackpolicyBe OBJECT-TYPE 
    SYNTAX INTEGER
    {
	enable(1),
	disable(2)
    }
    MAX-ACCESS read-create
    STATUS current
    DESCRIPTION
	"Enable / Disable support for No-ack for Best effort class."
    DEFVAL { disable }
    ::= { wmeTableEntry 39 }

wmeTableNoackpolicyBk OBJECT-TYPE 
    SYNTAX INTEGER
    {
	enable(1),
	disable(2)
    }
    MAX-ACCESS read-create
    STATUS current
    DESCRIPTION
	"Enable / Disable support for No-ack for Background class."
    DEFVAL { disable }
    ::= { wmeTableEntry 40 }

wmeTableNoackpolicyVi OBJECT-TYPE 
    SYNTAX INTEGER
    {
	enable(1),
	disable(2)
    }
    MAX-ACCESS read-create
    STATUS current
    DESCRIPTION
	"Enable / Disable support for No-ack for Video class."
    DEFVAL { disable }
    ::= { wmeTableEntry 41 }

wmeTableNoackpolicyVo OBJECT-TYPE 
    SYNTAX INTEGER
    {
	enable(1),
	disable(2)
    }
    MAX-ACCESS read-create
    STATUS current
    DESCRIPTION
	"Enable / Disable support for No-ack for Voice class."
    DEFVAL { disable }
    ::= { wmeTableEntry 42 }

wmeTableComment OBJECT-TYPE
    SYNTAX DisplayString (SIZE (0..32))
    MAX-ACCESS read-create
    STATUS current
    DESCRIPTION
	"An optional comment associated to the WME table."
	DEFVAL { "Nil" }
    ::= { wmeTableEntry 43 }

wmeTableActive OBJECT-TYPE 
    SYNTAX INTEGER
    {
	enable(1),
	disable(2)
    }
    MAX-ACCESS read-create
    STATUS current
    DESCRIPTION
	"The status of the WME table entry."
    DEFVAL { enable }
    ::= { wmeTableEntry 44 }

wmeTableRowStatus OBJECT-TYPE
   SYNTAX RowStatus
   MAX-ACCESS read-create
   STATUS current
   DESCRIPTION
        "The row status in the WME table row"
   ::= { wmeTableEntry 45 }


-- ============| nodeConfigurationTm75 | ==============

tm75Active OBJECT-TYPE
	SYNTAX INTEGER
	{
		enable(1),
		disable(2)
	}
	MAX-ACCESS read-write
	STATUS current
	DESCRIPTION
	"Enable the TM75 temperature sensor"
	DEFVAL { enable }
	::= { nodeConfigurationTm75 1 }

tm75Resolution OBJECT-TYPE
	SYNTAX INTEGER
	{
		pt5c(0),
		pt25c(1),
		pt125c(2),
		pt0625c(3)
	}
	MAX-ACCESS read-write
	STATUS current
	DESCRIPTION
	"Select the temperature conversion resolution"
	DEFVAL { pt5c }
	::= { nodeConfigurationTm75 2 }

tm75Temperature OBJECT-TYPE
	SYNTAX OCTET STRING (SIZE(0..512))
    	MAX-ACCESS read-only
    	STATUS current
    	DESCRIPTION
		"Current Temperature, with 4 digits floating point (-55..128)"
	DEFVAL { "X" }
     ::= { nodeConfigurationTm75 3 }


-- ============| nodeConfigurationNmsAddress |=============


nmsAddressTable OBJECT-TYPE
    	SYNTAX SEQUENCE OF NmsAddressTableEntry
    	MAX-ACCESS not-accessible
    	STATUS current
    	DESCRIPTION
	"This is the list of NMS servers that will be updated by the AP periodically." 
    ::= { nodeConfigurationNmsAddress 1 }

nmsAddressTableEntry OBJECT-TYPE
    	SYNTAX NmsAddressTableEntry 
   	MAX-ACCESS not-accessible
    	STATUS current
    	DESCRIPTION
	"Represent the entry in the NMS Address table."
    INDEX { nmsAddressTableIndex }
    ::= { nmsAddressTable 1 }

NmsAddressTableEntry::=
    SEQUENCE
    {
	nmsAddressTableIndex 	 	Integer32, 
	nmsAddressTableAddress		DisplayString,
	nmsAddressTablePort		Integer32,
	nmsAddressTableInterval		Integer32,
      nmsAddressTableComment 		DisplayString, 
	nmsAddressTableActive 		INTEGER,
	nmsAddressTableRowStatus	RowStatus 	
    }

nmsAddressTableIndex OBJECT-TYPE
    SYNTAX Integer32 (0..128)
    MAX-ACCESS not-accessible
    STATUS current
    DESCRIPTION
	"Specify the index of the NMS Address table."
    ::= { nmsAddressTableEntry 1 }

nmsAddressTableAddress OBJECT-TYPE
    SYNTAX DisplayString (SIZE(0..255))
    MAX-ACCESS read-create
    STATUS current
    DESCRIPTION
	"The DNS/IP Address of the NMS server."
	DEFVAL { "Nil" }
    ::= { nmsAddressTableEntry 2 }

nmsAddressTablePort OBJECT-TYPE
    SYNTAX Integer32 (1..65535)
    MAX-ACCESS read-create
    STATUS current
    DESCRIPTION
	"The NMS server port."
	DEFVAL { 80 }
    ::= { nmsAddressTableEntry 3 }

nmsAddressTableInterval OBJECT-TYPE
    SYNTAX  Integer32 (60..300000)
    MAX-ACCESS read-create
    STATUS current
    DESCRIPTION
	"The AP update interval of that particular NMS server."
    ::= { nmsAddressTableEntry 4 }

nmsAddressTableComment OBJECT-TYPE
    SYNTAX DisplayString (SIZE (0..32))
    MAX-ACCESS read-create
    STATUS current
    DESCRIPTION
	"An optional description regarding the entry of the NMS Address table."
	DEFVAL { "Nil" }
    ::= { nmsAddressTableEntry 5 }

nmsAddressTableActive OBJECT-TYPE 
    SYNTAX INTEGER
    {
	enable(1),
	disable(2)
    }
    MAX-ACCESS read-create
    STATUS current
    DESCRIPTION 
	"The status of the NMS Address table entry."
    DEFVAL { enable }
    ::= { nmsAddressTableEntry 6 }

nmsAddressTableRowStatus OBJECT-TYPE
   SYNTAX RowStatus
   MAX-ACCESS read-create
   STATUS current
   DESCRIPTION
        "The row status in the NMS Address table entry."
   ::= { nmsAddressTableEntry 7 }


-- ============| nodeConfigurationUserDb |=====================

userDbUsername OBJECT-TYPE
	SYNTAX DisplayString (SIZE (1..32))
	MAX-ACCESS read-write
	STATUS current
	DESCRIPTION
	"The username of the user entry."
     ::= { nodeConfigurationUserDb 1 }

userDbPassword OBJECT-TYPE
	SYNTAX DisplayString (SIZE (1..32))
	MAX-ACCESS read-write
	STATUS current
	DESCRIPTION
	"The login password for the username in the User database."
     ::= { nodeConfigurationUserDb 2 }

userDbGroupid OBJECT-TYPE
	SYNTAX DisplayString (SIZE (0..32))
	MAX-ACCESS read-write
	STATUS current
	DESCRIPTION
	"The User Group id assign for the user in the database."
     ::= { nodeConfigurationUserDb 3 }

userDbAddCmd OBJECT-TYPE
	SYNTAX Integer32 (1..2)
	MAX-ACCESS read-write
	STATUS current
	DESCRIPTION
	"SnmpSet this item to add the entry to the group, with the parameters stored in the temp folder"
	::= { nodeConfigurationUserDb 4 }

userDbEditCmd OBJECT-TYPE
	SYNTAX Integer32 (1..2)
	MAX-ACCESS read-write
	STATUS current
	DESCRIPTION
	"SnmpSet this item to edit the entry in the group, with the parameters stored in the temp folder"
	::= { nodeConfigurationUserDb 5 }

userDbDelCmd OBJECT-TYPE
	SYNTAX Integer32 (0..999999)
	MAX-ACCESS read-write
	STATUS current
	DESCRIPTION
	"SnmpSet the id to delete the entry from the table"
	::= { nodeConfigurationUserDb 6 }

userDbTable OBJECT-TYPE
    	SYNTAX SEQUENCE OF UserDbTableEntry
    	MAX-ACCESS not-accessible
    	STATUS current
    	DESCRIPTION
	"This table contains the local user database." 
    ::= { nodeConfigurationUserDb 7 }

userDbTableEntry OBJECT-TYPE
    	SYNTAX UserDbTableEntry
   	MAX-ACCESS not-accessible
    	STATUS current
    	DESCRIPTION
	"Represent the entry in the local user database table."
    INDEX { userDbTableIndex }
    ::= { userDbTable 1 }

UserDbTableEntry::=
    SEQUENCE
    {
	userDbTableIndex 		 	Integer32, 
	userDbTableName	 		DisplayString,
	userDbTablePassword	 	DisplayString,
	userDbTableGid	 		Integer32,
	userDbTableStatus			INTEGER
    }

userDbTableIndex OBJECT-TYPE
    SYNTAX Integer32 (0..128)
    MAX-ACCESS not-accessible
    STATUS current
    DESCRIPTION
	"Specify the index of the user group table."
    ::= { userDbTableEntry 1 }
 

userDbTableName OBJECT-TYPE
    SYNTAX DisplayString (SIZE (1..32))
    MAX-ACCESS read-only
    STATUS current
    DESCRIPTION
	"The name of the user"
    ::= { userDbTableEntry 2 } 

userDbTablePassword OBJECT-TYPE
    SYNTAX DisplayString (SIZE (1..32))
    MAX-ACCESS read-only
    STATUS current
    DESCRIPTION
	"The login password for the username"
    ::= { userDbTableEntry 3 } 

userDbTableGid OBJECT-TYPE
    SYNTAX Integer32(-1..999999)
    MAX-ACCESS read-only
    STATUS current
    DESCRIPTION
	"The group id used for the username"
    ::= { userDbTableEntry 4 } 

userDbTableStatus OBJECT-TYPE
    SYNTAX INTEGER
	{
		enable(1),
		loggedin(2),
		idle(3),
		expired(4)
	}
    MAX-ACCESS read-only
    STATUS current
    DESCRIPTION
	"The default download bandwidth of the entry"
    ::= { userDbTableEntry 5 } 


-- ============| nodeConfigurationUserGroup |==================

userGroupId OBJECT-TYPE
	SYNTAX DisplayString (SIZE (0..32))
	MAX-ACCESS read-write
	STATUS current
	DESCRIPTION
	"The ID number of the User Group."
     ::= { nodeConfigurationUserGroup 1 }

userGroupName OBJECT-TYPE
	SYNTAX DisplayString (SIZE (0..32))
	MAX-ACCESS read-write
	STATUS current
	DESCRIPTION
	"The Name of the User Group."
     ::= { nodeConfigurationUserGroup 2 }

userGroupLanguage OBJECT-TYPE
	SYNTAX DisplayString (SIZE (0..32))
	MAX-ACCESS read-write
	STATUS current
	DESCRIPTION
	"The default language of the User Group."
     ::= { nodeConfigurationUserGroup 3 }

userGroupUpload OBJECT-TYPE
	SYNTAX DisplayString (SIZE (0..32))
	MAX-ACCESS read-write
	STATUS current
	DESCRIPTION
	"The upload bandwidth of the User Group."
     ::= { nodeConfigurationUserGroup 4 }

userGroupDownload OBJECT-TYPE
	SYNTAX DisplayString (SIZE (0..32))
	MAX-ACCESS read-write
	STATUS current
	DESCRIPTION
	"The download bandwidth of the User Group."
     ::= { nodeConfigurationUserGroup 5 }

userGroupIdleTimeout OBJECT-TYPE
	SYNTAX DisplayString (SIZE (0..32))
	MAX-ACCESS read-write
	STATUS current
	DESCRIPTION
	"The default idle timeout of the User Group."
     ::= { nodeConfigurationUserGroup 6 }

userGroupSessionTimeout OBJECT-TYPE
	SYNTAX DisplayString (SIZE (0..32))
	MAX-ACCESS read-write
	STATUS current
	DESCRIPTION
	"The default session timeout of the User Group."
     ::= { nodeConfigurationUserGroup 7 }

userGroupUrl OBJECT-TYPE
	SYNTAX DisplayString (SIZE (0..512))
	MAX-ACCESS read-write
	STATUS current
	DESCRIPTION
	"The default URL to direct to for the user in this User Group."
     ::= { nodeConfigurationUserGroup 8 }

userGroupComment OBJECT-TYPE
	SYNTAX DisplayString (SIZE (0..32))
	MAX-ACCESS read-write
	STATUS current
	DESCRIPTION
	"The optional comment for the User Group."
     ::= { nodeConfigurationUserGroup 9 }

userGroupAddCmd OBJECT-TYPE
	SYNTAX Integer32 (1..2)
	MAX-ACCESS read-write
	STATUS current
	DESCRIPTION
	"SnmpSet this item to add the entry to the group, with the parameters stored in the temp folder"
	::= { nodeConfigurationUserGroup 10 }

userGroupEditCmd OBJECT-TYPE
	SYNTAX Integer32 (1..2)
	MAX-ACCESS read-write
	STATUS current
	DESCRIPTION
	"SnmpSet this item to edit the entry in the group, with the parameters stored in the temp folder"
	::= { nodeConfigurationUserGroup 11 }

userGroupDelCmd OBJECT-TYPE
	SYNTAX Integer32 (0..999999)
	MAX-ACCESS read-write
	STATUS current
	DESCRIPTION
	"SnmpSet the id to delete the entry from the group"
	::= { nodeConfigurationUserGroup 12 }

userGroupTable OBJECT-TYPE
    	SYNTAX SEQUENCE OF UserGroupTableEntry
    	MAX-ACCESS not-accessible
    	STATUS current
    	DESCRIPTION
	"This table contains the local user group." 
    ::= { nodeConfigurationUserGroup 13 }

userGroupTableEntry OBJECT-TYPE
    	SYNTAX UserGroupTableEntry
   	MAX-ACCESS not-accessible
    	STATUS current
    	DESCRIPTION
	"Represent the entry in the user group table."
    INDEX { userGroupTableIndex }
    ::= { userGroupTable 1 }

UserGroupTableEntry::=
    SEQUENCE
    {
	userGroupTableIndex	 	Integer32, 
	userGroupTableGid	 		Integer32,
	userGroupTableName	 	DisplayString,
	userGroupTableLanguage	 	DisplayString,
	userGroupTableUpload	 	Integer32,
	userGroupTableDownload		Integer32, 
	userGroupTableIdleTimeout	Integer32,
      userGroupTableSessTimeout	Integer32, 
	userGroupTableUrl			DisplayString,
	userGroupTableComment		DisplayString	
    }

userGroupTableIndex OBJECT-TYPE
    SYNTAX Integer32 (0..16)
    MAX-ACCESS not-accessible
    STATUS current
    DESCRIPTION
	"Specify the index of the user group table."
    ::= { userGroupTableEntry 1 }

userGroupTableGid OBJECT-TYPE
    SYNTAX Integer32(0..999999)
    MAX-ACCESS read-only
    STATUS current
    DESCRIPTION
	"The group id of the entry"
    ::= { userGroupTableEntry 2 } 

userGroupTableName OBJECT-TYPE
    SYNTAX DisplayString (SIZE (0..32))
    MAX-ACCESS read-only
    STATUS current
    DESCRIPTION
	"The group name of the entry"
    ::= { userGroupTableEntry 3 } 

userGroupTableLanguage OBJECT-TYPE
    SYNTAX DisplayString (SIZE (0..32))
    MAX-ACCESS read-only
    STATUS current
    DESCRIPTION
	"The group's default language of the entry"
    ::= { userGroupTableEntry 4 } 

userGroupTableUpload OBJECT-TYPE
    SYNTAX Integer32(32..300000)
    MAX-ACCESS read-only
    STATUS current
    DESCRIPTION
	"The default upload bandwidth of the entry"
    ::= { userGroupTableEntry 5 } 

userGroupTableDownload OBJECT-TYPE
    SYNTAX Integer32(32..300000)
    MAX-ACCESS read-only
    STATUS current
    DESCRIPTION
	"The default download bandwidth of the entry"
    ::= { userGroupTableEntry 6 } 

userGroupTableIdleTimeout OBJECT-TYPE
    SYNTAX Integer32(0..300000)
    MAX-ACCESS read-only
    STATUS current
    DESCRIPTION
	"The default idle timeout of the entry"
    ::= { userGroupTableEntry 7 } 

userGroupTableSessTimeout OBJECT-TYPE
    SYNTAX Integer32(0..300000)
    MAX-ACCESS read-only
    STATUS current
    DESCRIPTION
	"The default session timeout of the entry"
    ::= { userGroupTableEntry 8 } 

userGroupTableUrl OBJECT-TYPE
    SYNTAX DisplayString (SIZE (0..512))
    MAX-ACCESS read-only
    STATUS current
    DESCRIPTION
	"The redirect URL for the entry"
    ::= { userGroupTableEntry 9 } 

userGroupTableComment OBJECT-TYPE
    SYNTAX DisplayString (SIZE (0..32))
    MAX-ACCESS read-only
    STATUS current
    DESCRIPTION
	"The group's optional comment"
    ::= { userGroupTableEntry 10 } 


-- ============| nodeConfigurationStatickey |============================

statickeyWifi0Key0 OBJECT-TYPE
    SYNTAX OCTET STRING (SIZE(0..64))
    MAX-ACCESS read-write
    STATUS current
    DESCRIPTION
	"Static Key 0 for Wifi0"
    ::= { nodeConfigurationStatickey 1 }

statickeyWifi0Key1 OBJECT-TYPE
    SYNTAX OCTET STRING (SIZE(0..64))
    MAX-ACCESS read-write
    STATUS current
    DESCRIPTION
	"Static Key 1 for Wifi0"
    ::= { nodeConfigurationStatickey 2 }

statickeyWifi0Key2 OBJECT-TYPE
    SYNTAX OCTET STRING (SIZE(0..64))
    MAX-ACCESS read-write
    STATUS current
    DESCRIPTION
	"Static Key 2 for Wifi0"
    ::= { nodeConfigurationStatickey 3 }

statickeyWifi0Key3 OBJECT-TYPE
    SYNTAX OCTET STRING (SIZE(0..64))
    MAX-ACCESS read-write
    STATUS current
    DESCRIPTION
	"Static Key 3 for Wifi0"
    ::= { nodeConfigurationStatickey 4 }

statickeyWifi1Key0 OBJECT-TYPE
    SYNTAX OCTET STRING (SIZE(0..64))
    MAX-ACCESS read-write
    STATUS current
    DESCRIPTION
	"Static Key 0 for Wifi1"
    ::= { nodeConfigurationStatickey 5 }

statickeyWifi1Key1 OBJECT-TYPE
    SYNTAX OCTET STRING (SIZE(0..64))
    MAX-ACCESS read-write
    STATUS current
    DESCRIPTION
	"Static Key 1 for Wifi1"
    ::= { nodeConfigurationStatickey 6 }

statickeyWifi1Key2 OBJECT-TYPE
    SYNTAX OCTET STRING (SIZE(0..64))
    MAX-ACCESS read-write
    STATUS current
    DESCRIPTION
	"Static Key 2 for Wifi1"
    ::= { nodeConfigurationStatickey 7 }

statickeyWifi1Key3 OBJECT-TYPE
    SYNTAX OCTET STRING (SIZE(0..64))
    MAX-ACCESS read-write
    STATUS current
    DESCRIPTION
	"Static Key 3 for Wifi1"
    ::= { nodeConfigurationStatickey 8 }


-- ============| nodeConfigurationDhcrelay | =============

dhcrelayActive  OBJECT-TYPE
       SYNTAX INTEGER
       {
	enable(1),
	disable(2)
       }
       MAX-ACCESS read-write
       STATUS current
       DESCRIPTION
	"Enable/Disable the DHCP Relay."
       DEFVAL { disable }
       ::= { nodeConfigurationDhcrelay 1 }

dhcrelayPort OBJECT-TYPE
      SYNTAX Integer32 (1..65535)
      MAX-ACCESS read-write
      STATUS current
      DESCRIPTION
	"DHCP Relay Port."
	DEFVAL { 67 }	
       ::= { nodeConfigurationDhcrelay 2 }

dhcrelayHopcount OBJECT-TYPE
      SYNTAX Integer32 (1..255)
      MAX-ACCESS read-write
      STATUS current
      DESCRIPTION
	"Maximum hop count before the packet is dropped."
	DEFVAL { 10 }	
       ::= { nodeConfigurationDhcrelay 3 }

dhcrelayPktsize OBJECT-TYPE
      SYNTAX Integer32 (600..1400)
      MAX-ACCESS read-write
      STATUS current
      DESCRIPTION
	"Maximum Packet size for the DHCP discover."
	DEFVAL { 1400 }	
       ::= { nodeConfigurationDhcrelay 4 }


dhcrelayTable OBJECT-TYPE
    	SYNTAX SEQUENCE OF DhcrelayTableEntry
    	MAX-ACCESS not-accessible
    	STATUS current
    	DESCRIPTION
	"This is the DHCP Relay table." 
    ::= { nodeConfigurationDhcrelay 5 }

dhcrelayTableEntry OBJECT-TYPE
    	SYNTAX DhcrelayTableEntry 
   	MAX-ACCESS not-accessible
    	STATUS current
    	DESCRIPTION
	"Represent the entry in the DHCP Relay table."
    INDEX { dhcrelayTableIndex }
    ::= { dhcrelayTable 1 }

DhcrelayTableEntry::=
    SEQUENCE
    {
	dhcrelayTableIndex	 	Integer32, 
	dhcrelayTableType			INTEGER,
	dhcrelayTableExtra		DisplayString,
      dhcrelayTableComments 		DisplayString, 
	dhcrelayTableActive 		INTEGER,
	dhcrelayTableRowStatus		RowStatus 	
    }

dhcrelayTableIndex OBJECT-TYPE
    SYNTAX Integer32 (0..32)
    MAX-ACCESS not-accessible
    STATUS current
    DESCRIPTION
	"Specify the index of the DHCP Relay table."
    ::= { dhcrelayTableEntry 1 }

dhcrelayTableType OBJECT-TYPE 
    SYNTAX INTEGER
    {
	server(1),
	interface(2)
    }
    MAX-ACCESS read-create
    STATUS current
    DESCRIPTION 
	"The type of this DHCP Relay table entry."
    DEFVAL { interface }
    ::= { dhcrelayTableEntry 2 }

dhcrelayTableExtra OBJECT-TYPE
    SYNTAX DisplayString (SIZE (1..32))
    MAX-ACCESS read-create
    STATUS current
    DESCRIPTION
	"Extra information for the type, eg for server(1)-ip address, or interface(2)-interface name."
	DEFVAL { "Nil" }
    ::= { dhcrelayTableEntry 3 }

dhcrelayTableComments OBJECT-TYPE
    SYNTAX DisplayString (SIZE (1..32))
    MAX-ACCESS read-create
    STATUS current
    DESCRIPTION
	"An optional description regarding the entry of the DHCP Relay table."
	DEFVAL { "Nil" }
    ::= { dhcrelayTableEntry 4 }

dhcrelayTableActive OBJECT-TYPE 
    SYNTAX INTEGER
    {
	enable(1),
	disable(2)
    }
    MAX-ACCESS read-create
    STATUS current
    DESCRIPTION 
	"The status of the DHCP Relay table entry."
    DEFVAL { enable }
    ::= { dhcrelayTableEntry 5 }

dhcrelayTableRowStatus OBJECT-TYPE
   SYNTAX RowStatus
   MAX-ACCESS read-create
   STATUS current
   DESCRIPTION
        "The row status in the DHCP Relay table entry."
   ::= { dhcrelayTableEntry 6 }


-- ============| nodeConfigurationMulticast |==================

multicastActive  OBJECT-TYPE
   SYNTAX INTEGER
   {
	enable(1),
	disable(2)
   }
   MAX-ACCESS read-write
   STATUS current
   DESCRIPTION
	"Enable/Disable the Multicast."
       DEFVAL { enable }
   ::= { nodeConfigurationMulticast 1 }

-- ============| nodeConfigurationOspfd |==================

ospfdActive  OBJECT-TYPE
   SYNTAX INTEGER
   {
	enable(1),
	disable(2)
   }
   MAX-ACCESS read-write
   STATUS current
   DESCRIPTION
	"Enable/Disable the OSPF."
       DEFVAL { disable }
   ::= { nodeConfigurationOspfd 1 }

-- ============| nodeConfigurationEbtables |==================

ebtablesActive  OBJECT-TYPE
   SYNTAX INTEGER
   {
	enable(1),
	disable(2)
   }
   MAX-ACCESS read-write
   STATUS current
   DESCRIPTION
	"Enable/Disable the ebtables."
       DEFVAL { disable }
   ::= { nodeConfigurationEbtables 1 }

ebTable OBJECT-TYPE
    	SYNTAX SEQUENCE OF EbTableEntry
    	MAX-ACCESS not-accessible
    	STATUS current
    	DESCRIPTION
	"This is the Ebtable rules." 
    ::= { nodeConfigurationEbtables 2 }

ebTableEntry OBJECT-TYPE
    	SYNTAX EbTableEntry 
   	MAX-ACCESS not-accessible
    	STATUS current
    	DESCRIPTION
	"Represent the entry in the ebtables."
    INDEX { ebTableIndex }
    ::= { ebTable 1 }

EbTableEntry::=
    SEQUENCE
    {
	ebTableIndex	 	Integer32, 
	ebTableTarget		INTEGER,
	ebTableSrcIface		OCTET STRING,
      ebTableDstIface 		OCTET STRING, 
	ebTableMatchMac 		INTEGER,
	ebTableSrcMac		MacAddress,
	ebTableDstMac		MacAddress,
      ebTableProtocol 		INTEGER, 
	ebTableSrcIp 		IpAddress,
	ebTableSrcMask		IpAddress,
	ebTableDstIp		IpAddress,
      ebTableDstMask 		IpAddress, 
	ebTableIpProt 		INTEGER,
	ebTableSrcPortStart	Integer32,
	ebTableSrcPortEnd		Integer32,
	ebTableDstPortStart	Integer32,
	ebTableDstPortEnd		Integer32,
	ebTableVlanid		Integer32,
      ebTableComments 		DisplayString, 
	ebTableActive 		INTEGER,
	ebTableRowStatus		RowStatus 	
    }

ebTableIndex OBJECT-TYPE
    SYNTAX Integer32 (0..64)
    MAX-ACCESS not-accessible
    STATUS current
    DESCRIPTION
	"Specify the index of the ebtables."
    ::= { ebTableEntry 1 }

ebTableTarget OBJECT-TYPE 
    SYNTAX INTEGER
    {
	allow(1),
	deny(2)
    }
    MAX-ACCESS read-create
    STATUS current
    DESCRIPTION 
	"Select the type of this rule: allow or deny ."
    DEFVAL { allow }
    ::= { ebTableEntry 2 }

ebTableSrcIface OBJECT-TYPE
    SYNTAX OCTET STRING (SIZE (1..32))
    MAX-ACCESS read-create
    STATUS current
    DESCRIPTION
	"Source Interface"
	DEFVAL { "Nil" }
    ::= { ebTableEntry 3 }

ebTableDstIface OBJECT-TYPE
    SYNTAX OCTET STRING (SIZE (1..32))
    MAX-ACCESS read-create
    STATUS current
    DESCRIPTION
	"Destination Interface"
	DEFVAL { "Nil" }
    ::= { ebTableEntry 4 }

ebTableMatchMac OBJECT-TYPE 
    SYNTAX INTEGER
    {
	enable(1),
	disable(2)
    }
    MAX-ACCESS read-create
    STATUS current
    DESCRIPTION 
	"Enable or disable the MAC matching."
    DEFVAL { enable }
    ::= { ebTableEntry 5 }

ebTableSrcMac OBJECT-TYPE
    SYNTAX MacAddress
    MAX-ACCESS read-create
    STATUS current
    DESCRIPTION
	"Source MAC Address"
    ::= { ebTableEntry 6 }

ebTableDstMac OBJECT-TYPE
    SYNTAX MacAddress
    MAX-ACCESS read-create
    STATUS current
    DESCRIPTION
	"Destination MAC Address"
    ::= { ebTableEntry 7 }

ebTableProtocol OBJECT-TYPE 
    SYNTAX INTEGER
    {
	ipv4(1),
	arp(2),
	e802dot1q(3),
	ppp(4)
    }
    MAX-ACCESS read-create
    STATUS current
    DESCRIPTION 
	"The protocol type."
    DEFVAL { ipv4 }
    ::= { ebTableEntry 8 }

ebTableSrcIp OBJECT-TYPE
    SYNTAX IpAddress
    MAX-ACCESS read-create
    STATUS current
    DESCRIPTION
	"Source IP Address"
    ::= { ebTableEntry 9 }

ebTableSrcMask OBJECT-TYPE
    SYNTAX IpAddress
    MAX-ACCESS read-create
    STATUS current
    DESCRIPTION
	"Source netmask"
    ::= { ebTableEntry 10 }

ebTableDstIp OBJECT-TYPE
    SYNTAX IpAddress
    MAX-ACCESS read-create
    STATUS current
    DESCRIPTION
	"Destination IP Address"
    ::= { ebTableEntry 11 }

ebTableDstMask OBJECT-TYPE
    SYNTAX IpAddress
    MAX-ACCESS read-create
    STATUS current
    DESCRIPTION
	"Destination netmask"
    ::= { ebTableEntry 12 }

ebTableIpProt OBJECT-TYPE 
    SYNTAX INTEGER
    {
	icmp(1),
	tcp(6),
	udp(17)
    }
    MAX-ACCESS read-create
    STATUS current
    DESCRIPTION 
	"The protocol type."
    DEFVAL { icmp }
    ::= { ebTableEntry 13 }

ebTableSrcPortStart OBJECT-TYPE
    SYNTAX Integer32 (-1..65536)
    MAX-ACCESS read-create
    STATUS current
    DESCRIPTION
	"Start of Source port"
    DEFVAL { -1 }
    ::= { ebTableEntry 14 }

ebTableSrcPortEnd OBJECT-TYPE
    SYNTAX Integer32 (-1..65536)
    MAX-ACCESS read-create
    STATUS current
    DESCRIPTION
	"End of Source port"
    DEFVAL { -1 }
    ::= { ebTableEntry 15 }

ebTableDstPortStart OBJECT-TYPE
    SYNTAX Integer32 (-1..65536)
    MAX-ACCESS read-create
    STATUS current
    DESCRIPTION
	"Start of Destination port"
    DEFVAL { -1 }
    ::= { ebTableEntry 16 }

ebTableDstPortEnd OBJECT-TYPE
    SYNTAX Integer32 (-1..65536)
    MAX-ACCESS read-create
    STATUS current
    DESCRIPTION
	"End of Destination port"
    DEFVAL { -1 }
    ::= { ebTableEntry 17 }

ebTableVlanid OBJECT-TYPE
    SYNTAX Integer32 (0..4096)
    MAX-ACCESS read-create
    STATUS current
    DESCRIPTION
	"VLAN ID"
    DEFVAL { 0 }
    ::= { ebTableEntry 18 }

ebTableComments OBJECT-TYPE
    SYNTAX DisplayString (SIZE (1..32))
    MAX-ACCESS read-create
    STATUS current
    DESCRIPTION
	"Optional comment"
    ::= { ebTableEntry 19 }

ebTableActive OBJECT-TYPE 
    SYNTAX INTEGER
    {
	enable(1),
	disable(2)
    }
    MAX-ACCESS read-create
    STATUS current
    DESCRIPTION 
	"The status of the ebtables entry."
    DEFVAL { enable }
    ::= { ebTableEntry 20 }

ebTableRowStatus OBJECT-TYPE
   SYNTAX RowStatus
   MAX-ACCESS read-create
   STATUS current
   DESCRIPTION
        "The row status in the ebtable entry."
   ::= { ebTableEntry 21 }


-- ============| nodeCommandReboot |==================

rebootTime OBJECT-TYPE
   SYNTAX Integer32 (1..300)
   MAX-ACCESS read-write
   STATUS current
   DESCRIPTION 
       "Set a value of timeout (1~300, in seconds) and reboot the device."
   DEFVAL { 1 }
   ::= { nodeCommandReboot 1 }


-- =============| nodeCommandReset | ===================

resetToDefault OBJECT-TYPE
   SYNTAX Integer32
   MAX-ACCESS read-write
   STATUS current
   DESCRIPTION 
       "SnmpSet this command to reset the device back to factory default value."
   DEFVAL { 0 }
   ::= { nodeCommandReset 1 } 

-- =============| nodeCommandUpload | ===================

uploadDownloadFilename OBJECT-TYPE
   SYNTAX DisplayString
   MAX-ACCESS read-write
   STATUS current
   DESCRIPTION 
       "The name of the file that wished to be upload/download through TFTP"
   ::= { nodeCommandUpload 1 } 

uploadDownloadFiletype OBJECT-TYPE
   SYNTAX INTEGER
	{
		config(1),
		firmware(2),
		ipx509local(3),
		ipx509remote(4),
		iprsa(5)
	}
   MAX-ACCESS read-write
   STATUS current
   DESCRIPTION 
       "The type of the file"
   ::= { nodeCommandUpload 2 } 


uploadDownloadIpaddress OBJECT-TYPE
   SYNTAX IpAddress
   MAX-ACCESS read-write
   STATUS current
   DESCRIPTION 
       "The TFTP IP Address"
   ::= { nodeCommandUpload 3 } 

uploadDownloadPassword OBJECT-TYPE
   SYNTAX DisplayString (SIZE(0..64))
   MAX-ACCESS read-write
   STATUS current
   DESCRIPTION 
       "The password used for extract the certificate file"
   ::= { nodeCommandUpload 4 } 

uploadDownloadOperationtype OBJECT-TYPE
   SYNTAX INTEGER
	{
		download(1),
		upload(2),
		uploadandreboot(3)
	}
   MAX-ACCESS read-write
   STATUS current
   DESCRIPTION 
       "The type of TFTP operation to be done"
   ::= { nodeCommandUpload 5 } 

uploadDownloadExecutetftp OBJECT-TYPE
   SYNTAX INTEGER
	{
		execute(1)
	}
   MAX-ACCESS read-write
   STATUS current
   DESCRIPTION 
       "Execute the TFTP operation by setting this command to value 1"
   ::= { nodeCommandUpload 6 } 

-- =============| nodeCommandLogoutBlock | ===================

logoutAndBlockAction OBJECT-TYPE
   SYNTAX IpAddress
   MAX-ACCESS read-write
   STATUS current
   DESCRIPTION 
       "SnmpSet to logout and block the user with the IP address."
   ::= { nodeCommandLogoutBlock 1 } 

-- =============| nodeCommandRestartSnmp | ===================

restartSnmpService OBJECT-TYPE
   SYNTAX Integer32
   MAX-ACCESS read-write
   STATUS current
   DESCRIPTION 
       "SnmpSet to restart the SNMP Service."
   ::= { nodeCommandRestartSnmp 1 } 


END
