ASTARO-MIB DEFINITIONS ::= BEGIN

--
-- Astaro Notification Definition
--
-- .1.3.6.1.4.1.9789
-- .iso.org.dod.internet.private.enterprises.astaro
--      .1500  (.notification)
--           .0  (DEBUG)
--           .1  (INFO)
--           .2  (WARN)
--           .3  (CRIT)
--                .0 - .999   (<notificationID>)
--

IMPORTS
    MODULE-IDENTITY, OBJECT-TYPE, NOTIFICATION-TYPE,
    enterprises 
             FROM SNMPv2-SMI ;



-- 
-- top level
--

astaro MODULE-IDENTITY
    LAST-UPDATED "201110060000Z"
    ORGANIZATION "Astaro GmbH & Co. KG - a Sophos company"
    CONTACT-INFO 
                 "Astaro GmbH & Co. KG - a Sophos company
                 Amalienbadstr. 41/Bau 52
                 76227 Karlsruhe

                 Telefon: +49-800-2782761 (Germany Only)
                 Telefon: +49-721-25516-0 (Outside Germany)
                 Fax: +49 721 25516 200
                 Email: emea@astaro.com
                 www.astaro.com"
    DESCRIPTION  
                 "The MIB module for Notification Events

                 Copyright (C) 2009 by Astaro AG"
    REVISION     "200812170000Z"
    DESCRIPTION  
                 "Initial version"
::= { enterprises 9789 }

notification OBJECT IDENTIFIER ::= { astaro 1500 }


--
-- Notification severiry
--

debug OBJECT IDENTIFIER ::= { notification 0 }
info  OBJECT IDENTIFIER ::= { notification 1 }
warn  OBJECT IDENTIFIER ::= { notification 2 }
crit  OBJECT IDENTIFIER ::= { notification 3 }


-- 
-- Notifications
--
CRIT-025 NOTIFICATION-TYPE
    STATUS current
    DESCRIPTION
          "License usage: EXCEEDING 100% OF USER COUNT on Sophos UTM"
::= { crit 25 }

CRIT-026 NOTIFICATION-TYPE
    STATUS current
    DESCRIPTION
          "License usage: EXCEEDING 110% OF USER COUNT on Sophos UTM"
::= { crit 26 }

CRIT-027 NOTIFICATION-TYPE
    STATUS current
    DESCRIPTION
          "License usage: No valid HA license"
::= { crit 27 }

CRIT-028 NOTIFICATION-TYPE
    STATUS current
    DESCRIPTION
          "License usage: No valid Cluster license"
::= { crit 28 }

CRIT-054 NOTIFICATION-TYPE
    STATUS current
    DESCRIPTION
          "UPS power critical, system shutting down"
::= { crit 54 }

CRIT-060 NOTIFICATION-TYPE
    STATUS current
    DESCRIPTION
          "Raid degraded: harddisk replacement needed"
::= { crit 60 }

CRIT-065 NOTIFICATION-TYPE
    STATUS current
    DESCRIPTION
          "IPv6 Renumbering failed"
::= { info 65 }

CRIT-080 NOTIFICATION-TYPE
    STATUS current
    DESCRIPTION
          "HA System: There is no slave node, please check your HA System"
::= { crit 80 }

CRIT-081 NOTIFICATION-TYPE
    STATUS current
    DESCRIPTION
          "HA System: Your installed system versions differ, please check your HA System"
::= { crit 81 }

CRIT-082 NOTIFICATION-TYPE
    STATUS current
    DESCRIPTION
          "HA System: Some interfaces are unplugged, please check your HA System"
::= { crit 82 }

CRIT-090 NOTIFICATION-TYPE
    STATUS current
    DESCRIPTION
          "Cluster: One or more nodes are dead, please check your Cluster"
::= { crit 90 }

CRIT-091 NOTIFICATION-TYPE
    STATUS current
    DESCRIPTION
          "Cluster: Your installed system versions differ, please check your Cluster"
::= { crit 91 }

CRIT-092 NOTIFICATION-TYPE
    STATUS current
    DESCRIPTION
          "Cluster: Some interfaces are unplugged, please check your Cluster"
::= { crit 92 }

CRIT-310 NOTIFICATION-TYPE
    STATUS current
    DESCRIPTION
          "Up2Date prefetch failed"
::= { crit 310 }

CRIT-311 NOTIFICATION-TYPE
    STATUS current
    DESCRIPTION
          "Firmware Up2Date installation failed"
::= { crit 311 }

CRIT-712 NOTIFICATION-TYPE
    STATUS current
    DESCRIPTION
          "System shut down due to full log file partition"
::= { crit 712 }

CRIT-850 NOTIFICATION-TYPE
    STATUS current
    DESCRIPTION
          "Intrusion Prevention Alert"
::= { crit 850 }

CRIT-852 NOTIFICATION-TYPE
    STATUS current
    DESCRIPTION
          "Intrusion Prevention Alert (Packet dropped)"
::= { crit 852 }

CRIT-861 NOTIFICATION-TYPE
    STATUS current
    DESCRIPTION
          "Advanced Threat Protection Alert"
::= { crit 861 }

INFO-000 NOTIFICATION-TYPE
    STATUS current
    DESCRIPTION
          "System was restarted"
::= { info 0 }

INFO-005 NOTIFICATION-TYPE
    STATUS current
    DESCRIPTION
          "Successful WebAdmin login"
::= { info 5 }

INFO-006 NOTIFICATION-TYPE
    STATUS current
    DESCRIPTION
          "Successful SSH login"
::= { info 6 }

INFO-007 NOTIFICATION-TYPE
    STATUS current
    DESCRIPTION
          "Successful console login"
::= { info 5 }

INFO-010 NOTIFICATION-TYPE
    STATUS current
    DESCRIPTION
          "Configuration Auto Backup"
::= { info 10 }

INFO-011 NOTIFICATION-TYPE
    STATUS current
    DESCRIPTION
          "Configuration Backup File"
::= { info 11 }

INFO-020 NOTIFICATION-TYPE
    STATUS current
    DESCRIPTION
          "License expiry: a feature will expire"
::= { info 20 }

INFO-021 NOTIFICATION-TYPE
    STATUS current
    DESCRIPTION
          "License expiry: a feature expires today"
::= { info 21 }

INFO-022 NOTIFICATION-TYPE
    STATUS current
    DESCRIPTION
          "License expiry: a feature expired"
::= { info 22 }

INFO-040 NOTIFICATION-TYPE
    STATUS current
    DESCRIPTION
          "Remote Configuration Manager - System Information"
::= { info 40 }

INFO-050 NOTIFICATION-TYPE
    STATUS current
    DESCRIPTION
          "UPS device connected"
::= { info 50 }

INFO-051 NOTIFICATION-TYPE
    STATUS current
    DESCRIPTION
          "UPS device disconnected"
::= { info 51 }

INFO-053 NOTIFICATION-TYPE
    STATUS current
    DESCRIPTION
          "UPS power restored"
::= { info 53 }

INFO-062 NOTIFICATION-TYPE
    STATUS current
    DESCRIPTION
          "Raid rebuild process started"
::= { info 62 }

INFO-063 NOTIFICATION-TYPE
    STATUS current
    DESCRIPTION
          "Raid rebuild process finished"
::= { info 63 }

INFO-065 NOTIFICATION-TYPE
    STATUS current
    DESCRIPTION
          "IPv6 Renumbering successful"
::= { info 65 }

INFO-080 NOTIFICATION-TYPE
    STATUS current
    DESCRIPTION
          "HA node is now Master"
::= { info 80 }

INFO-081 NOTIFICATION-TYPE
    STATUS current
    DESCRIPTION
          "HA node is now Slave"
::= { info 81 }

INFO-083 NOTIFICATION-TYPE
    STATUS current
    DESCRIPTION
          "HA System is active and fully functional"
::= { info 83 }

INFO-090 NOTIFICATION-TYPE
    STATUS current
    DESCRIPTION
          "Cluster node is now Master"
::= { info 90 }

INFO-091 NOTIFICATION-TYPE
    STATUS current
    DESCRIPTION
          "Cluster node is now Slave"
::= { info 91 }

INFO-092 NOTIFICATION-TYPE
    STATUS current
    DESCRIPTION
          "Cluster node is now Worker"
::= { info 92 }

INFO-093 NOTIFICATION-TYPE
    STATUS current
    DESCRIPTION
          "Cluster is active and fully functional"
::= { info 93 }

INFO-094 NOTIFICATION-TYPE
    STATUS current
    DESCRIPTION
          "Upgrade: download successful"
::= { info 94 }

INFO-095 NOTIFICATION-TYPE
    STATUS current
    DESCRIPTION
          "RED Unlock code"
::= { info 95 }

INFO-105 NOTIFICATION-TYPE
    STATUS current
    DESCRIPTION
          "User Authenticator not running - restarted"
::= { info 105 }

INFO-106 NOTIFICATION-TYPE
    STATUS current
    DESCRIPTION
          "Cron Task Scheduler not running - restarted"
::= { info 106 }

INFO-107 NOTIFICATION-TYPE
    STATUS current
    DESCRIPTION
          "WebAdmin webserver not running - restarted"
::= { info 107 }

INFO-108 NOTIFICATION-TYPE
    STATUS current
    DESCRIPTION
          "Ssh server not running - restarted"
::= { info 108 }

INFO-109 NOTIFICATION-TYPE
    STATUS current
    DESCRIPTION
          "Dhcp client not running - restarted"
::= { info 109 }

INFO-110 NOTIFICATION-TYPE
    STATUS current
    DESCRIPTION
          "Configuration daemon not running - restarted"
::= { info 110 }

INFO-111 NOTIFICATION-TYPE
    STATUS current
    DESCRIPTION
          "Syslog server not running - restarted"
::= { info 111 }

INFO-112 NOTIFICATION-TYPE
    STATUS current
    DESCRIPTION
          "Middleware not running - restarted"
::= { info 112 }

INFO-114 NOTIFICATION-TYPE
    STATUS current
    DESCRIPTION
          "Ulogd not running - restarted"
::= { info 114 }

INFO-115 NOTIFICATION-TYPE
    STATUS current
    DESCRIPTION
          "Snort not running - restarted"
::= { info 115 }

INFO-116 NOTIFICATION-TYPE
    STATUS current
    DESCRIPTION
          "Snmpd daemon not running - restarted"
::= { info 116 }

INFO-117 NOTIFICATION-TYPE
    STATUS current
    DESCRIPTION
          "Pop3 proxy not running - restarted"
::= { info 117 }

INFO-118 NOTIFICATION-TYPE
    STATUS current
    DESCRIPTION
          "Ftp proxy not running - restarted"
::= { info 118 }

INFO-119 NOTIFICATION-TYPE
    STATUS current
    DESCRIPTION
          "Named not running - restarted"
::= { info 119 }

INFO-120 NOTIFICATION-TYPE
    STATUS current
    DESCRIPTION
          "Sockd not running - restarted"
::= { info 120 }

INFO-121 NOTIFICATION-TYPE
    STATUS current
    DESCRIPTION
          "Identd not running - restarted"
::= { info 121 }

INFO-122 NOTIFICATION-TYPE
    STATUS current
    DESCRIPTION
          "Dhcpd not running - restarted"
::= { info 122 }

INFO-123 NOTIFICATION-TYPE
    STATUS current
    DESCRIPTION
          "IRQd not running - restarted"
::= { info 123 }

INFO-124 NOTIFICATION-TYPE
    STATUS current
    DESCRIPTION
          "Ufod not running - restarted"
::= { info 124 }

INFO-125 NOTIFICATION-TYPE
    STATUS current
    DESCRIPTION
          "Smtpd not running - restarted"
::= { info 125 }

INFO-126 NOTIFICATION-TYPE
    STATUS current
    DESCRIPTION
          "Dyndns not running - restarted"
::= { info 126 }

INFO-127 NOTIFICATION-TYPE
    STATUS current
    DESCRIPTION
          "Spam filter not running - restarted"
::= { info 127 }

INFO-128 NOTIFICATION-TYPE
    STATUS current
    DESCRIPTION
          "Pptpd not running - restarted"
::= { info 128 }

INFO-129 NOTIFICATION-TYPE
    STATUS current
    DESCRIPTION
          "IPv6 Watchdog not running - restarted"
::= { info 129 }

INFO-130 NOTIFICATION-TYPE
    STATUS current
    DESCRIPTION
          "Winbindd not running - restarted"
::= { info 130 }

INFO-131 NOTIFICATION-TYPE
    STATUS current
    DESCRIPTION
          "Xinetd not running - restarted"
::= { info 131 }

INFO-132 NOTIFICATION-TYPE
    STATUS current
    DESCRIPTION
          "ACC core daemon not running - restarted"
::= { info 132 }

INFO-133 NOTIFICATION-TYPE
    STATUS current
    DESCRIPTION
          "ACC up2date cache not running - restarted"
::= { info 133 }

INFO-134 NOTIFICATION-TYPE
    STATUS current
    DESCRIPTION
          "IPsec starter not running - restarted"
::= { info 134 }

INFO-135 NOTIFICATION-TYPE
    STATUS current
    DESCRIPTION
          "IPsec pluto not running - restarted"
::= { info 135 }

INFO-136 NOTIFICATION-TYPE
    STATUS current
    DESCRIPTION
          "ACC device agent not running - restarted"
::= { info 136 }

INFO-138 NOTIFICATION-TYPE
    STATUS current
    DESCRIPTION
          "Smtp scan daemon not running - restarted"
::= { info 138 }

INFO-139 NOTIFICATION-TYPE
    STATUS current
    DESCRIPTION
          "Content Filter Framework not running - restarted"
::= { info 139 }

INFO-140 NOTIFICATION-TYPE
    STATUS current
    DESCRIPTION
          "Notification Daemon not running - restarted"
::= { info 140 }

INFO-141 NOTIFICATION-TYPE
    STATUS current
    DESCRIPTION
          "Http proxy not running - restarted"
::= { info 141 }

INFO-142 NOTIFICATION-TYPE
    STATUS current
    DESCRIPTION
          "OSPF daemon (ospfd) not running - restarted"
::= { info 142 }

INFO-143 NOTIFICATION-TYPE
    STATUS current
    DESCRIPTION
          "Dynamic routing daemon (quagga) not running - restarted"
::= { info 143 }

INFO-144 NOTIFICATION-TYPE
    STATUS current
    DESCRIPTION
          "HAL (Hardware Abstraction Layer) system daemon not running - restarted"
::= { info 144 }

INFO-145 NOTIFICATION-TYPE
    STATUS current
    DESCRIPTION
          "Udev (system device manager) daemon not running - restarted"
::= { info 145 }

INFO-146 NOTIFICATION-TYPE
    STATUS current
    DESCRIPTION
          "Dbus (application device bus) system daemon not running - restarted"
::= { info 146 }

INFO-147 NOTIFICATION-TYPE
    STATUS current
    DESCRIPTION
          "NTP (network time synchronization) daemon not running - restarted"
::= { info 147 }

INFO-148 NOTIFICATION-TYPE
    STATUS current
    DESCRIPTION
          "L2TP-over-IPsec daemon not running - restarted"
::= { info 148 }

INFO-149 NOTIFICATION-TYPE
    STATUS current
    DESCRIPTION
          "Application Control daemon not running - restarted"
::= { info 149 }

INFO-150 NOTIFICATION-TYPE
    STATUS current
    DESCRIPTION
          "Root partition is filling up - please check"
::= { info 150 }

INFO-152 NOTIFICATION-TYPE
    STATUS current
    DESCRIPTION
          "Network Monitor not running - restarted"
::= { info 152 }

INFO-153 NOTIFICATION-TYPE
    STATUS current
    DESCRIPTION
          "Log Disk is filling up - please check"
::= { info 153 }

INFO-154 NOTIFICATION-TYPE
    STATUS current
    DESCRIPTION
          "Data Disk is filling up - please check"
::= { info 154 }

INFO-163 NOTIFICATION-TYPE
    STATUS current
    DESCRIPTION
          "Log Disk is short of inodes - please check"
::= { info 163 }

INFO-164 NOTIFICATION-TYPE
    STATUS current
    DESCRIPTION
          "Data Disk is short of inodes - please check"
::= { info 164 }

INFO-170 NOTIFICATION-TYPE
    STATUS current
    DESCRIPTION
          "HA confd sync daemon not running - restarted"
::= { info 170 }

INFO-171 NOTIFICATION-TYPE
    STATUS current
    DESCRIPTION
          "HA up2date proxy not running - restarted"
::= { info 171 }

INFO-172 NOTIFICATION-TYPE
    STATUS current
    DESCRIPTION
          "HA conntrack daemon not running - restarted"
::= { info 172 }

INFO-173 NOTIFICATION-TYPE
    STATUS current
    DESCRIPTION
          "HA csync2 daemon not running - restarted"
::= { info 173 }

INFO-175 NOTIFICATION-TYPE
    STATUS current
    DESCRIPTION
          "IPv6 Teredo Tunnel Broker client not running - restarted"
::= { info 175 }

INFO-176 NOTIFICATION-TYPE
    STATUS current
    DESCRIPTION
          "IPv6 gogo6 Tunnel Broker client not running - restarted"
::= { info 176 }

INFO-177 NOTIFICATION-TYPE
    STATUS current
    DESCRIPTION
          "IPv6 Routing Advertisement daemon not running - restarted"
::= { info 177 }

INFO-178 NOTIFICATION-TYPE
    STATUS current
    DESCRIPTION
          "IPv6 Hurricane Tunnel Broker client not running - restarted"
::= { info 178 }

INFO-179 NOTIFICATION-TYPE
    STATUS current
    DESCRIPTION
          "DNS resolver not running - restarted"
::= { info 179 }

INFO-180 NOTIFICATION-TYPE
    STATUS current
    DESCRIPTION
          "Client Authentication daemon not running - restarted"
::= { info 180 }

INFO-181 NOTIFICATION-TYPE
    STATUS current
    DESCRIPTION
          "Service Monitor not running - restarted"
::= { info 181 }

INFO-182 NOTIFICATION-TYPE
    STATUS current
    DESCRIPTION
          "Job queue manager (atd) not running - restarted"
::= { info 182 }

INFO-183 NOTIFICATION-TYPE
    STATUS current
    DESCRIPTION
          "BGP daemon (bgpd) not running - restarted"
::= { info 183 }

INFO-184 NOTIFICATION-TYPE
    STATUS current
    DESCRIPTION
          "RED server not running - restarted"
::= { info 184 }

INFO-185 NOTIFICATION-TYPE
    STATUS current
    DESCRIPTION
          "RED client not running - restarted"
::= { info 185 }

INFO-186 NOTIFICATION-TYPE
    STATUS current
    DESCRIPTION
          "Confd request queuer not running - restarted"
::= { info 186 }

INFO-187 NOTIFICATION-TYPE
    STATUS current
    DESCRIPTION
          "Confd queue runner not running - restarted"
::= { info 187 }

INFO-188 NOTIFICATION-TYPE
    STATUS current
    DESCRIPTION
          "urid not running - restarted"
::= { info 188 }

INFO-189 NOTIFICATION-TYPE
    STATUS current
    DESCRIPTION
          "Web Application Firewall not running - restarted"
::= { info 189 }

INFO-190 NOTIFICATION-TYPE
    STATUS current
    DESCRIPTION
          "Support access daemon not running - restarted"
::= { info 190 }

INFO-191 NOTIFICATION-TYPE
    STATUS current
    DESCRIPTION
          "RPM database restored"
::= { info 191 }

INFO-192 NOTIFICATION-TYPE
    STATUS current
    DESCRIPTION
          "RRD cache daemon not running - restarted"
::= { info 192 }

INFO-301 NOTIFICATION-TYPE
    STATUS current
    DESCRIPTION
          "New Firmware Up2Date is ready for installation"
::= { info 301 }

INFO-302 NOTIFICATION-TYPE
    STATUS current
    DESCRIPTION
          "New Firmware Up2Date installed"
::= { info 302 }

INFO-306 NOTIFICATION-TYPE
    STATUS current
    DESCRIPTION
          "New Pattern Up2Dates installed"
::= { info 306 }

INFO-310 NOTIFICATION-TYPE
    STATUS current
    DESCRIPTION
          "Up2Date prefetch is working again"
::= { info 310 }

INFO-320 NOTIFICATION-TYPE
    STATUS current
    DESCRIPTION
          "Database Conversion Started"
::= { info 320 }

INFO-321 NOTIFICATION-TYPE
    STATUS current
    DESCRIPTION
          "Database Conversion Adjourned"
::= { info 321 }

INFO-322 NOTIFICATION-TYPE
    STATUS current
    DESCRIPTION
          "Database Conversion Finished"
::= { info 322 }

INFO-601 NOTIFICATION-TYPE
    STATUS current
    DESCRIPTION
          "Your Hotspot password"
::= { info 601 }

INFO-700 NOTIFICATION-TYPE
    STATUS current
    DESCRIPTION
          "Daily log file archive"
::= { info 700 }

INFO-710 NOTIFICATION-TYPE
    STATUS current
    DESCRIPTION
          "Log file partition is filling up"
::= { info 710 }

INFO-720 NOTIFICATION-TYPE
    STATUS current
    DESCRIPTION
          "Daily Executive Report"
::= { info 720 }

INFO-721 NOTIFICATION-TYPE
    STATUS current
    DESCRIPTION
          "Weekly Executive Report"
::= { info 721 }

INFO-722 NOTIFICATION-TYPE
    STATUS current
    DESCRIPTION
          "Monthly Executive Report"
::= { info 722 }

INFO-723 NOTIFICATION-TYPE
    STATUS current
    DESCRIPTION
          "Daily Executive Report"
::= { info 723 }

INFO-724 NOTIFICATION-TYPE
    STATUS current
    DESCRIPTION
          "Weekly Executive Report"
::= { info 724 }

INFO-725 NOTIFICATION-TYPE
    STATUS current
    DESCRIPTION
          "Monthly Executive Report"
::= { info 725 }

INFO-726 NOTIFICATION-TYPE
    STATUS current
    DESCRIPTION
          "VPN connection using Site-to-Site is up again"
::= { info 726 }

INFO-727 NOTIFICATION-TYPE
    STATUS current
    DESCRIPTION
          "RED connection is up again"
::= { info 727 }

INFO-728 NOTIFICATION-TYPE
    STATUS current
    DESCRIPTION
          "Access Point is online again"
::= { info 728 }

INFO-729 NOTIFICATION-TYPE
    STATUS current
    DESCRIPTION
          "Mesh Access Point is online again"
::= { info 729 }

INFO-850 NOTIFICATION-TYPE
    STATUS current
    DESCRIPTION
          "Intrusion Prevention Alert"
::= { info 850 }

INFO-852 NOTIFICATION-TYPE
    STATUS current
    DESCRIPTION
          "Intrusion Prevention Alert (Packet dropped)"
::= { info 852 }

WARN-005 NOTIFICATION-TYPE
    STATUS current
    DESCRIPTION
          "Failed WebAdmin login"
::= { warn 5 }

WARN-006 NOTIFICATION-TYPE
    STATUS current
    DESCRIPTION
          "Failed SSH login"
::= { warn 6 }

WARN-007 NOTIFICATION-TYPE
    STATUS current
    DESCRIPTION
          "Failed console login"
::= { warn 7 }

WARN-025 NOTIFICATION-TYPE
    STATUS current
    DESCRIPTION
          "License usage: EXCEEDING 90% OF USER COUNT on Sophos UTM"
::= { warn 25 }

WARN-030 NOTIFICATION-TYPE
    STATUS current
    DESCRIPTION
          "Primary internet uplink is down, switching to backup line"
::= { warn 30 }

WARN-031 NOTIFICATION-TYPE
    STATUS current
    DESCRIPTION
          "Primary internet uplink is back online, switching to main line"
::= { warn 31 }

WARN-032 NOTIFICATION-TYPE
    STATUS current
    DESCRIPTION
          "Internet uplink is down"
::= { warn 32 }

WARN-033 NOTIFICATION-TYPE
    STATUS current
    DESCRIPTION
          "Internet uplink is up again"
::= { warn 33 }

WARN-040 NOTIFICATION-TYPE
    STATUS current
    DESCRIPTION
          "Sophos UTM weak Certificate check - found weak certificates"
::= { warn 40 }

WARN-052 NOTIFICATION-TYPE
    STATUS current
    DESCRIPTION
          "UPS on battery power"
::= { warn 52 }

WARN-061 NOTIFICATION-TYPE
    STATUS current
    DESCRIPTION
          "Raid degraded: defective harddisk inserted"
::= { warn 61 }

WARN-070 NOTIFICATION-TYPE
    STATUS current
    DESCRIPTION
          "Too many failed logins"
::= { warn 70 }

WARN-080 NOTIFICATION-TYPE
    STATUS current
    DESCRIPTION
          "HA selfcheck"
::= { warn 80 }

WARN-090 NOTIFICATION-TYPE
    STATUS current
    DESCRIPTION
          "Cluster selfcheck"
::= { warn 90 }

WARN-094 NOTIFICATION-TYPE
    STATUS current
    DESCRIPTION
          "Upgrade failed"
::= { warn 94 }

WARN-129 NOTIFICATION-TYPE
    STATUS current
    DESCRIPTION
          "Spam Filter cannot query database servers"
::= { warn 129 }

WARN-136 NOTIFICATION-TYPE
    STATUS current
    DESCRIPTION
          "ACC server not reachable"
::= { warn 136 }

WARN-160 NOTIFICATION-TYPE
    STATUS current
    DESCRIPTION
          "Root partition is short of inodes - please check"
::= { warn 160 }

WARN-161 NOTIFICATION-TYPE
    STATUS current
    DESCRIPTION
          "RPM Database is corrupted"
::= { warn 161 }

WARN-162 NOTIFICATION-TYPE
    STATUS current
    DESCRIPTION
          "Corrupted RPM database rebuild failed"
::= { warn 162 }

WARN-201 NOTIFICATION-TYPE
    STATUS current
    DESCRIPTION
          "A RED device has been deauthorized automatically"
::= { warn 201 }

WARN-501 NOTIFICATION-TYPE
    STATUS current
    DESCRIPTION
          "Endpoint Virus Detected"
::= { warn 501 }

WARN-531 NOTIFICATION-TYPE
    STATUS current
    DESCRIPTION
          "Directory Services synchronization"
::= { warn 531 }

WARN-711 NOTIFICATION-TYPE
    STATUS current
    DESCRIPTION
          "Log files have been deleted"
::= { warn 711 }

WARN-715 NOTIFICATION-TYPE
    STATUS current
    DESCRIPTION
          "Remote log file storage failed"
::= { warn 715 }

WARN-726 NOTIFICATION-TYPE
    STATUS current
    DESCRIPTION
          "VPN connection using Site-to-Site is down"
::= { warn 726 }

WARN-727 NOTIFICATION-TYPE
    STATUS current
    DESCRIPTION
          "RED connection is down"
::= { warn 727 }

WARN-728 NOTIFICATION-TYPE
    STATUS current
    DESCRIPTION
          "Access Point is offline"
::= { warn 728 }

WARN-729 NOTIFICATION-TYPE
    STATUS current
    DESCRIPTION
          "Mesh Access Point is offline"
::= { warn 729 }

WARN-850 NOTIFICATION-TYPE
    STATUS current
    DESCRIPTION
          "Intrusion Prevention Alert"
::= { warn 850 }

WARN-852 NOTIFICATION-TYPE
    STATUS current
    DESCRIPTION
          "Intrusion Prevention Alert (Packet dropped)"
::= { warn 852 }

WARN-856 NOTIFICATION-TYPE
    STATUS current
    DESCRIPTION
          "Portscan detected"
::= { warn 856 }



END
