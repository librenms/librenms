TIMETRA-SERV-MIB DEFINITIONS ::= BEGIN

IMPORTS
    MODULE-IDENTITY, OBJECT-TYPE,
    NOTIFICATION-TYPE, Gauge32,
    Integer32, Unsigned32, IpAddress,
    TimeTicks, Counter64, Counter32             FROM SNMPv2-SMI

    MODULE-COMPLIANCE, OBJECT-GROUP,
    NOTIFICATION-GROUP                          FROM SNMPv2-CONF

    TEXTUAL-CONVENTION, DisplayString,
    RowStatus, MacAddress, TimeStamp,
    TruthValue, RowPointer, DateAndTime         FROM SNMPv2-TC

    InterfaceIndex, InterfaceIndexOrZero        FROM IF-MIB

    InetAddressPrefixLength,
    InetAddressType, InetAddress,
    InetAddressIPv4, InetAddressIPv6,
    InetAutonomousSystemNumber                  FROM INET-ADDRESS-MIB

    ServiceAdminStatus, ServiceOperStatus,
    TmnxPortID, TmnxEncapVal,
    TmnxServId, TmnxCustId, TNamedItem,
    TmnxExtServId,
    TLNamedItem, TLNamedItemOrEmpty,
    TmnxVRtrID, TmnxVRtrIDOrZero, QTag, QTagOrZero,
    SdpBindId, TNamedItemOrEmpty,
    TPortSchedulerPIR,
    TmnxActionType,
    TCIRRate, TPIRRate,
    TmnxEnabledDisabled,
    TPolicyStatementNameOrEmpty,
    TmnxVPNRouteDistinguisher,
    TmnxManagedRouteStatus,
    TmnxAdminState,
    TmnxSubIdentStringOrEmpty, 
    TmnxSubProfileStringOrEmpty,
    TmnxSlaProfileStringOrEmpty, 
    TmnxAppProfileStringOrEmpty,
    TmnxAncpStringOrZero,
    TmnxSubMgtIntDestIdOrEmpty,
    TmnxDefSubIdSource,
    TIngressQueueId,
    TBurstPercentOrDefault,
    TmnxBgpAutonomousSystem,
    BgpPeeringStatus, SvcISID, TmnxTlsGroupId,
    TmnxSpokeSdpId, TmnxSpokeSdpIdOrZero, TmnxLdpFECType,
    TmnxPwGlobalId, TmnxPwGlobalIdOrZero,
    TmnxMsPwPeSignaling, TmnxPwPathHopId,
    TmnxSvcOperGrpCreationOrigin,
    TmnxAccessLoopEncapDataLink, 
    TmnxAccessLoopEncaps1,
    TmnxAccessLoopEncaps2,    
    TmnxOperGrpHoldUpTime,TmnxOperGrpHoldDownTime,
    TmnxAiiType, 
    TDirectionIngEgr, TWeight,
    TQosOverrideType,
    THsmdaWrrWeightOverride,
    TPIRRateOverride,
    TCIRRateOverride,
    TBurstSizeBytesOverride, TPortSchedulerAggRateLimitPIR,
    TBurstSizeBytesOvr,
    TSiteOperStatus, TmnxSpbFdbLocale, TmnxSpbFdbState,
    TmnxSpbFid, TmnxSpbFidOrZero, TmnxSpbBridgePriority,
    TItemDescription, TPolicyID,  THPolVirtualScheCIRRate,
    THPolVirtualSchePIRRate, TItemScope,
    TQosIngressPolicyID, TNetworkPolicyID, TQosQGrpInstanceIDorZero,
    TmnxBfdIntfSessOperState,
    TLDisplayString, TBurstLimit,
    TResolveStatus,
    LAGInterfaceNumberOrZero,
    TmnxRouteTargetOrigin, TmnxRouteDistType,
    TmnxCreateOrigin, TmnxISID, TmnxISIDNoZero,
    TmnxProxyEntryType,
    TmnxSvcEvi, TmnxSvcEviOrZero,
    TmnxEvpnMultiHomingState,
    TmnxSubShcvAction, TmnxSubShcvInterval, 
    TmnxSubShcvRetryTimeout, TmnxSubShcvRetryCount,
    TmnxSubShcvSrcIpOrigin
       ,TmnxRadiusFramedRouteMetric,
       TmnxRadiusFramedRoutePreference,
       TmnxRadiusFramedRouteTag
    , TQosQueuePIRRateOverride, TQosQueueCIRRateOverride
    , TmnxRipListenerStatus
    , TmnxSubTerminationType
    ,TmnxTunnelTypeExt 

                                                FROM TIMETRA-TC-MIB

    timetraSRMIBModules, tmnxSRObjs,
    tmnxSRNotifyPrefix, tmnxSRConfs             FROM TIMETRA-GLOBAL-MIB

    tmnxCardSlotNum, tmnxMDASlotNum             FROM TIMETRA-CHASSIS-MIB

    tVirtualSchedulerName,
    tSchedulerPolicyName,
    tQosIngQGroupName                           FROM TIMETRA-QOS-MIB

    TIPFilterID,
    TDHCPFilterID,
    TEntryId, TFilterID                         FROM TIMETRA-FILTER-MIB;


timetraServicesMIBModule   MODULE-IDENTITY
        LAST-UPDATED "201501010000Z"
        ORGANIZATION "Nokia"
        CONTACT-INFO
            "Nokia SROS Support
             Web: http://www.nokia.com"
    DESCRIPTION
        "This document is the SNMP MIB module to manage and provision
        the various services of the Nokia SROS system.

        Copyright 2003-2015 Nokia. All rights reserved. 
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
--  Revision History
--
    REVISION        "201501200000Z"
    DESCRIPTION     "Rev 13.0               01 Jan 2015 00:00
                     13.0 release of the TIMETRA-SERV-MIB."
                     
    REVISION        "201401010000Z"
    DESCRIPTION     "Rev 12.0               01 Jan 2014 00:00
                     12.0 release of the TIMETRA-SERV-MIB."

    REVISION        "201102010000Z"
    DESCRIPTION     "Rev 9.0                01 Feb 2011 00:00
                     9.0 release of the TIMETRA-SERV-MIB."

    REVISION        "200902280000Z"
    DESCRIPTION     "Rev 7.0                28 Feb 2009 00:00
                     7.0 release of the TIMETRA-SERV-MIB."

    REVISION        "200807010000Z"
    DESCRIPTION     "Rev 6.1                01 Jul 2008 00:00
                     6.1 release of the TIMETRA-SERV-MIB."

    REVISION        "200801010000Z"
    DESCRIPTION     "Rev 6.0                01 Jan 2008 00:00
                     6.0 release of the TIMETRA-SERV-MIB."

    REVISION        "200701010000Z"
    DESCRIPTION     "Rev 5.0                01 Jan 2007 00:00
                     5.0 release of the TIMETRA-SERV-MIB."

    REVISION        "200602280000Z"
    DESCRIPTION     "Rev 4.0                28 Feb 2006 00:00
                     4.0 release of the TIMETRA-SERV-MIB."

    REVISION        "200508310000Z"
    DESCRIPTION     "Rev 3.0                31 Aug 2005 00:00
                     3.0 release of the TIMETRA-SERV-MIB."

    REVISION        "200501240000Z"
    DESCRIPTION     "Rev 2.1                24 Jan 2005 00:00
                     2.1 release of the TIMETRA-SERV-MIB."

    REVISION        "200401150000Z"
    DESCRIPTION     "Rev 2.0                15 Jan 2004 00:00
                     2.0 release of the TIMETRA-SERV-MIB."

    REVISION        "200308150000Z"
    DESCRIPTION     "Rev 1.2                15 Aug 2003 00:00
                     1.2 release of the TIMETRA-SERV-MIB."

    REVISION        "200301200000Z"
    DESCRIPTION     "Rev 1.0                20 Jan 2003 00:00
                     1.0 Release of the TIMETRA-SERV-MIB."

    REVISION        "200008140000Z"
    DESCRIPTION     "Rev 0.1                14 Aug 2000 00:00
                     Initial version of the TIMETRA-SERV-MIB."

    ::= { timetraSRMIBModules 4 }

-- --------------------------------------------------------------------
--      TIMETRA-SERV-MIB organisation
-- --------------------------------------------------------------------
tmnxServObjs            OBJECT IDENTIFIER ::= { tmnxSRObjs 4 }
    tmnxCustObjs            OBJECT IDENTIFIER ::= { tmnxServObjs 1 }
    tmnxSvcObjs             OBJECT IDENTIFIER ::= { tmnxServObjs 2 }
    tmnxTstpNotifyObjs      OBJECT IDENTIFIER ::= { tmnxServObjs 5 }
    tmnxSvcNotifyObjs       OBJECT IDENTIFIER ::= { tmnxServObjs 6 }
    tmnxSvcTimeObjs         OBJECT IDENTIFIER ::= { tmnxServObjs 7 }

tmnxServConformance     OBJECT IDENTIFIER ::= { tmnxSRConfs 4 }
    tmnxCustConformance     OBJECT IDENTIFIER ::= { tmnxServConformance 1 }
    tmnxSvcConformance      OBJECT IDENTIFIER ::= { tmnxServConformance 2 }
    tmnxTstpConformance     OBJECT IDENTIFIER ::= { tmnxServConformance 5 }

tmnxServNotifications   OBJECT IDENTIFIER ::= { tmnxSRNotifyPrefix 4 }
    custTrapsPrefix         OBJECT IDENTIFIER ::= { tmnxServNotifications 1 }
        custTraps               OBJECT IDENTIFIER ::= { custTrapsPrefix 0 }
    svcTrapsPrefix          OBJECT IDENTIFIER ::= { tmnxServNotifications 2 }
        svcTraps                OBJECT IDENTIFIER ::= { svcTrapsPrefix 0 }
    tstpTrapsPrefix         OBJECT IDENTIFIER ::= { tmnxServNotifications 5 }
        tstpTraps               OBJECT IDENTIFIER ::= { tstpTrapsPrefix 0 }

tmnxSvcDCObjs             OBJECT IDENTIFIER ::= { tmnxSvcObjs 200 }

-- --------------------------------------------------------------------
--      TIMETRA-SERV-MIB Textual Conventions
-- --------------------------------------------------------------------
ArpHostInfoOrigin ::= TEXTUAL-CONVENTION
    STATUS          current
    DESCRIPTION     "Indicates the originator of the provided information."
    SYNTAX          INTEGER {
                        none            (0),
                        radius          (2),
                        default         (5) 
                    }

ServObjName ::= TEXTUAL-CONVENTION
    STATUS          current
    DESCRIPTION     "ASCII string used to name various service
                     objects."
    SYNTAX          DisplayString (SIZE (0..32))

ServObjDesc ::= TEXTUAL-CONVENTION
    STATUS          current
    DESCRIPTION     "ASCII string used to describe various service
                     objects."
    SYNTAX          DisplayString (SIZE (0..80))

ServObjLongDesc ::= TEXTUAL-CONVENTION
    STATUS          current
    DESCRIPTION     "Long ASCII string used to describe various service
                     objects."
    SYNTAX          DisplayString (SIZE (0..160))

ServType ::= TEXTUAL-CONVENTION
    STATUS          current
    DESCRIPTION     "This textual convention is used to specify the
                     type of a given service."
    SYNTAX          INTEGER {
                        unknown (0), -- Unknown service type
                        epipe   (1), -- Ethernet pipe
                        tls     (3), -- Virtual private LAN service (VPLS)
                        vprn    (4), -- Virtual private routed network
                        ies     (5), -- Internet enhanced service
                        mirror  (6), -- Mirror service
                        apipe   (7), -- ATM pipe service
                        fpipe   (8), -- FR pipe service
                        ipipe   (9), -- IP interworking pipe service
                        cpipe   (10),-- Circuit Emulation pipe service
                        intTls  (11), -- Internal VPLS service
                        rvpls   (15) -- IES interface associated with RVPLS
                    }

VpnId ::= TEXTUAL-CONVENTION
    STATUS          current
    DESCRIPTION     "A number used to identify a VPN. In general
                     each service corresponds to a single VPN, but
                     under some circumstances a VPN may be composed
                     of multiple services."
    SYNTAX          Unsigned32 (0|1..2147483647)

SdpId ::= TEXTUAL-CONVENTION
    STATUS          current
    DESCRIPTION     "A 16-bit number used to identify a Service
                     Distribution Point. This ID must be unique only
                     within the ESR where it is defined. The value 0
                     is used as the null ID."
    SYNTAX          Unsigned32 (0|1..17407)

SdpTemplateId ::= TEXTUAL-CONVENTION
    STATUS          current
    DESCRIPTION     "A number used to uniquely identify a template 
                     for the creation of a Service Destination Point.
                     The value 0 is used as the null ID."
    SYNTAX          Unsigned32 (0|1..2147483647)

PWTemplateId ::= TEXTUAL-CONVENTION
    STATUS          current
    DESCRIPTION     "A number used to uniquely identify an pseudowire (PW)
                     template for the creation of a Service Destination
                     Point. The value 0 is used as the null ID."
    SYNTAX          Unsigned32 (0|1..2147483647)

PWTemplateIdNoZero ::= TEXTUAL-CONVENTION
    STATUS          current
    DESCRIPTION     "A number used to uniquely identify an pseudowire (PW)
                     template for the creation of a Service Destination
                     Point. The value 0 is used as the null ID."
    SYNTAX          Unsigned32 (1..2147483647)

TlsBpduTranslation ::= TEXTUAL-CONVENTION
    STATUS          current
    DESCRIPTION     "This textual convention is used to specify whether
                     received L2 Protocol Tunnel pdu's are translated
                     before being sent out on a port or sap."
    SYNTAX          INTEGER {
                        auto     (1),
                        disabled (2),
                        pvst     (3),
                        stp      (4),
                        pvst-rw  (5),
                        auto-rw  (6)
                    }

TlsLimitMacMoveLevel ::= TEXTUAL-CONVENTION
    STATUS          current
    DESCRIPTION     "This textual convention is used to specify the hierarchy
                     in which spoke-SDPs are blocked when a MAC-move limit is
                     exceeded. When a MAC is moving among multiple SAPs or
                     spoke-SDPs, the SAP bind or spoke-SDP bind with the
                     lower level is blocked first. (tertiary is the lowest)"
    SYNTAX          INTEGER {
                        primary   (1),
                        secondary (2),
                        tertiary  (3)
                    }

TlsLimitMacMove  ::= TEXTUAL-CONVENTION
    STATUS          current
    DESCRIPTION     "This textual convention is used to specify the behavior
                     when the re-learn rate specified by svcTlsMacMoveMaxRate
                     is exceeded.

                     A value of 'blockable' specifies that the agent will
                     monitor the MAC relearn rate on a SAP or SDP Bind and
                     it will block it when the re-learn rate specified by
                     svcTlsMacMoveMaxRate is exceeded. A value of 'nonBlockable'
                     specifies that the  SAP or SDP Bind will not be blocked,
                     and another blockable SAP or SDP Bind will be blocked
                     instead."
    SYNTAX          INTEGER {
                        blockable    (1),
                        nonBlockable (2)
                    }

SdpBindVcType  ::= TEXTUAL-CONVENTION
    STATUS          current
    DESCRIPTION     "This textual convention is used to specify the type of
                     virtual circuit (VC) associated with the SDP binding.
                     The value 'vpls' is no longer supported."
    SYNTAX          INTEGER {
                        undef      (1),
                        ether      (2),
                        --vpls     (3) obsolete
                        vlan       (4),
                        mirror     (5),
                        atmSdu     (6),
                        atmCell    (7),
                        atmVcc     (8),
                        atmVpc     (9),
                        frDlci     (10),
                        ipipe      (11),
                        satopE1    (12),
                        satopT1    (13),
                        satopE3    (14),
                        satopT3    (15),
                        cesopsn    (16),
                        cesopsnCas (17)
                    }

StpExceptionCondition ::= TEXTUAL-CONVENTION
    STATUS          current
    DESCRIPTION     "This textual convention is used to specify an
                     STP exception condition encountered on an
                     interface
                     - none : no exception condition found.
                     - oneWayCommuniation : The neighbor RSTP peer on this link
                                            is not able to detect our presence.
                     - downstreamLoopDetected : A loop is detected on this
                       link."
    SYNTAX          INTEGER {
                        none                   (1),
                        oneWayCommuniation     (2),
                        downstreamLoopDetected (3)
                    }

LspIdList ::= TEXTUAL-CONVENTION
    STATUS          current
    DESCRIPTION     "Each group of four octets in this string specify
                     a 32-bit LSP ID, which corresponds to the
                     vRtrMplsLspIndex of the given MPLS LSP. The LSP
                     IDs are stored in network byte order; i.e. octet
                     N corresponds to the most significant 8 bits of
                     the LSP ID, and octet N+3 correspond to the least
                     significant 8 bits. The list is terminated by the
                     null LSP ID. The LSP IDs in this list are not
                     required to be sorted in any specific order. The
                     list is large enough to hold up to 16 LSP IDs,
                     plus the null terminator."
    SYNTAX          OCTET STRING (SIZE (0..68))

BridgeId ::= TEXTUAL-CONVENTION
    STATUS          current
    DESCRIPTION     "The Bridge-Identifier used by the Spanning Tree
                     Protocol to uniquely identify a bridge. The first
                     two octets represent the bridge priority (in big
                     endian format) while the remaining six octets
                     represent the main MAC address of the bridge."
    SYNTAX          OCTET STRING (SIZE (8))

TSapIngQueueId ::= TEXTUAL-CONVENTION
    STATUS          current
    DESCRIPTION     "The value used to uniquely identify a SAP ingress queue.
                     The actual valid values are those defined in the given
                     SAP ingress QoS policy."
    SYNTAX          Unsigned32 (1..32)

TSapEgrQueueId ::= TEXTUAL-CONVENTION
    STATUS          current
    DESCRIPTION     "The value used to uniquely identify a SAP egress queue.
                     The actual valid values are those defined in the given
                     SAP egress QoS policy."
    SYNTAX          Unsigned32 (1..8)

TStpPortState ::= TEXTUAL-CONVENTION
    STATUS          current
    DESCRIPTION     "The value used to specify the port state as defined
                     by application of the Spanning Tree Protocol. This
                     state controls what action a port takes on reception
                     of a frame."
    SYNTAX          INTEGER {
                        disabled   (1),
                        blocking   (2),
                        listening  (3),
                        learning   (4),
                        forwarding (5),
                        broken     (6),
                        discarding (7)
                    }

StpPortRole ::= TEXTUAL-CONVENTION
    STATUS          current
    DESCRIPTION     "the stp portrole defined by the Rapid Spanning Tree
                     Protocol."

    SYNTAX          INTEGER {
                        master     (0),
                        root       (1),
                        designated (2),
                        alternate  (3),
                        backup     (4),
                        disabled   (5)
                    }

StpProtocol ::= TEXTUAL-CONVENTION
    STATUS          current
    DESCRIPTION     "indicates all possible version of the stp protocol."
    SYNTAX          INTEGER {
                        notApplicable (0),
                        stp           (1),
                        rstp          (2),
                        mstp          (3)
                    }

MfibLocation ::= TEXTUAL-CONVENTION
    STATUS          current
    DESCRIPTION     "MfibLocation represents the type of local 'interface':
                     -'sap'  : sap interface
                     -'sdp'  : mesh-sdp or spoke-sdp interface
                     -'vxlan': evpn vxlan
                     -'evpnMpls : evpn mpls
                     "
    SYNTAX          INTEGER {
                        sap   (1),
                        sdp   (2),
                        vxlan (3),
                        evpnMpls (4)
                    }

MfibGrpSrcFwdOrBlk ::= TEXTUAL-CONVENTION
    STATUS          current
    DESCRIPTION     "MfibGrpSrcFwdOrBlk describes whether traffic for the
                     related source-group is to be forwarded or blocked."
    SYNTAX          INTEGER {
                        forward (1),
                        block   (2)
                    }

MvplsPruneState ::= TEXTUAL-CONVENTION
    STATUS          current
    DESCRIPTION     "Managed VPLS (mVPLS): state of a SAP or spoke-SDP in a
                     user VPLS (uVPLS).
                     - notApplicable :
                       the SAP or spoke SDP of a uVPLS is not managed by a SAP
                       or spoke SDP of a mVPLS.
                     - notPruned:
                       the SAP or spoke SDP of a uVPLS is managed by a mVPLS,
                       but the link is not pruned.
                     -pruned
                       the SAP or spoke SDP of a uVPLS is managed by a mVPLS,
                       but the link is pruned as a result of an STP decision
                       taken in the STP instance running in the mVPLS."
    SYNTAX          INTEGER {
                        notApplicable (1),
                        notPruned     (2),
                        pruned        (3)
                    }

TQosQueueAttribute ::= TEXTUAL-CONVENTION
    STATUS          current
    DESCRIPTION     "Indicates attributes of a QoS queue"
    SYNTAX          BITS {
                        cbs          (0),
                        cir          (1),
                        cirAdaptRule (2),
                        mbs          (3),
                        pir          (4),
                        pirAdaptRule (5),
                        hiPrioOnly   (6),
                        avgOverhead  (7), --egress only
                        weight       (8),
                        cirWeight    (9),
                        pirPercent   (10),
                        cirPercent   (11),
                        mgmtpol    (12),
                        pirWeight   (13),
                        cirLevel     (14)
                    }

TVirtSchedAttribute ::= TEXTUAL-CONVENTION
    STATUS          current
    DESCRIPTION     "Indicates attributes of a virtual scheduler"
    SYNTAX          BITS {
                        cir       (0),
                        pir       (1),
                        summedCir (2),
                        weight    (3),
                        cirWeight (4)
                    }

MstiInstanceId ::= TEXTUAL-CONVENTION
    STATUS          current
    DESCRIPTION     "indicates all possible multiple spanning tree instances,
                     not including the CIST."
    SYNTAX          Unsigned32 (1..4094)

MstiInstanceIdOrZero ::= TEXTUAL-CONVENTION
    STATUS          current
    DESCRIPTION     "indicates all possible multiple spanning tree instances,
                     including the CIST (for which case the value '0' is 
                     reserved)."
    SYNTAX          Unsigned32 (0..4094)

DhcpLseStateInfoOrigin ::= TEXTUAL-CONVENTION
    STATUS          current
    DESCRIPTION     "Indicates the originator of the provided information."
    SYNTAX          INTEGER {
                        none            (0),
                        dhcp            (1),
                        radius          (2),
                        retailerRadius  (3),
                        retailerDhcp    (4),
                        default         (5), 
                        localUserDb     (6),
                        gtp             (7), -- GPRS Tunneling Protocol, WLAN GW
                        localPool       (8),
                        wpp             (9),
                        diameterGx     (10),
                        dtc            (11),
                        diameterNasreq (12)
                    }

IAIDType ::= TEXTUAL-CONVENTION
    STATUS          current
    DESCRIPTION     "Indicates the type of the addresses that are associated
                     with the Identity Association ID (IAID)"
    SYNTAX          INTEGER {
                        undefined     (0),
                        temporary     (1), -- IAID for temporary addresses,
                                           -- as defined in RFC 3041
                        non-temporary (2), -- IAID for non-temporary addresses
                        prefix        (3)  -- IAID for prefixes
                    }

TdmOptionsSigPkts ::= TEXTUAL-CONVENTION
    STATUS          current
    DESCRIPTION     "Encodes support for the cpipe circuit emulation (CE)
                     application signaling packets:
                     - 'noSigPkts' :
                       for a cpipe that does not use signalling packets.
                     - 'dataPkts' :
                       for a cpipe carrying TDM data packets and expecting CE
                       application signalling packets in a separate cpipe.
                     - 'sigPkts' :
                       for a cpipe carrying CE application signalling packets
                       with the data packets in a separate cpipe.
                     - 'dataAndSigPkts' :
                       for a cpipe carrying TDM data and CE application
                       signalling on the same cpipe."

    SYNTAX          INTEGER {
                        noSigPkts      (0),
                        dataPkts       (1),
                        sigPkts        (2),
                        dataAndSigPkts (3)
                    }

TdmOptionsCasTrunkFraming ::= TEXTUAL-CONVENTION
    STATUS          current
    DESCRIPTION     "Encodes the CEM SAPs CAS trunk framing type:
                     - 'noCas' :
                       for all CEM SAPs except 'nxDS0WithCas'.
                     - 'e1Trunk' :
                       for a 'nxDS0WithCas' SAP with E1 trunk.
                     - 't1EsfTrunk' :
                       for a 'nxDS0WithCas' SAP with T1 ESF trunk.
                     - 't1SfTrunk' :
                       for a 'nxDS0WithCas' SAP with T1 SF trunk."
    SYNTAX          INTEGER {
                        noCas      (0),
                        e1Trunk    (1),
                        t1EsfTrunk (2),
                        t1SfTrunk  (3)
                    }

CemSapReportAlarm ::= TEXTUAL-CONVENTION
    STATUS      current
    DESCRIPTION
        "The CemSapReportAlarm data type indicates the type of CEM SAP alarm:
         strayPkts     - receiving stray packets.
         malformedPkts - detecting malformed packets.
         pktLoss       - experiencing packet loss.
         bfrOverrun    - experiencing jitter buffer overrun.
         bfrUnderrun   - experiencing jitter buffer underrun.
         rmtPktLoss    - remote packet loss indication.
         rmtFault      - remote TDM fault indication.
         rmtRdi        - remote RDI indication."
    SYNTAX          BITS {
                        notUsed       (0),
                        strayPkts     (1),
                        malformedPkts (2),
                        pktLoss       (3),
                        bfrOverrun    (4),
                        bfrUnderrun   (5),
                        rmtPktLoss    (6),
                        rmtFault      (7),
                        rmtRdi        (8)
                    }
 
CemSapEcid ::= TEXTUAL-CONVENTION
    STATUS          current
    DESCRIPTION     "The Emulated Circuit Identifier (ECID) is a 20 bit
                     unsigned binary field containing an identifier for the
                     circuit being emulated.  ECIDs have local significance
                     only and are associated with a specific MAC address.
                     Therefore the SAP can have a different ECID for each
                     direction."
    SYNTAX          Unsigned32 (0..1048575)
                     
SdpBFHundredthsOfPercent ::= TEXTUAL-CONVENTION
    STATUS      current
    DESCRIPTION
        "The percentage of total SDP bandwidth reserved for SDP bindings 
         with two decimal places accuracy."
    SYNTAX      Integer32 (1..10000)

SdpBindBandwidth ::= TEXTUAL-CONVENTION
    STATUS       current
    DESCRIPTION
        "The required SDP binding bandwidth, in kbps."
    SYNTAX       Unsigned32 (0..100000000)


L2ptProtocols ::= TEXTUAL-CONVENTION
    STATUS      current
    DESCRIPTION
        "The L2ptProtocols indicates which L2 protocols should have their tunnels
         terminated when 'L2ptTermination' is enabled.
         stp           - spanning tree protocols stp/mstp/pvst/rstp
         cdp           - cisco discovery protocol
         vtp           - virtual trunk protocol
         dtp           - dynamic trunking protocol     
         pagp          - port aggregation protocol
         udld          - unidirectional link detection"

    SYNTAX          BITS {
                        stp       (0),
                        cdp       (1),
                        vtp       (2),
                        dtp       (3),
                        pagp      (4),
                        udld      (5)
                    }

ConfigStatus ::= TEXTUAL-CONVENTION
    STATUS      current
    DESCRIPTION
        "The ConfigStatus indicates the status of the configuration for
         the purpose of notifications."
    SYNTAX          INTEGER {
                        created  (1),
                        modified (2),
                        deleted  (3)
                    }

ServAccessLocation ::= TEXTUAL-CONVENTION
    STATUS          current
    DESCRIPTION     
            "ServAccessLocation represents the type of local 'access point':
                     -'sap'  : sap 
                     -'spoke': spoke-sdp ."
    SYNTAX          INTEGER {
                        sap (1),
                        spoke (2)
                    }

ServShcvOperState ::= TEXTUAL-CONVENTION
    STATUS          current
    DESCRIPTION     
            "ServShcvOperState represents the operational state 
              of the subscriber host connectivity verification."
    SYNTAX          INTEGER {
                        disabled  (1),
                        undefined (2),
                        down      (3),
                        up        (4)
                    }

TMrpPolicyDefaultAction ::= TEXTUAL-CONVENTION
    STATUS       current
    DESCRIPTION
        "action to take on the traffic when no mrp-policy filter entry matches.

         when set to block(1), no MMRP attributes will be advertised unless 
         there is a specific mrp-policy entry which causes them to be advertised
         on this SAP/SDP.

         when set to allow(2), all MMRP attributes will be advertised unless 
         there is a specific mrp-policy entry which causes them to be blocked
         on this SAP/SDP.
        "
    SYNTAX INTEGER { block(1), allow(2) }

TMrpPolicyAction ::= TEXTUAL-CONVENTION
    STATUS       current
    DESCRIPTION
        "action to take on the traffic when the mrp-policy filter entry matches.

         when set to block(1) the matching MMRP attributes will not be 
         advertised on this SAP/SDP. 

         when set to allow(2) the matching MMRP attributes will be 
         advertised on this SAP/SDP. 

         when set to end-station(3) an end-station emulation is present on this 
         SAP/SDP for the MMRP attributes related with matching ISIDs. 

         When set to none(0) the mrp-policy entry will be considered incomplete
         and hence rendered inactive.
        "
    SYNTAX INTEGER { none(0), block(1), allow(2), end-station(3) }
    
TmnxSiteId ::= TEXTUAL-CONVENTION
    STATUS          current
    DESCRIPTION
        "A number used to identify a site. This ID must be unique within the
        service-domain."
    SYNTAX       Integer32 (1..65535)

TmnxSiteIdOrEmpty ::= TEXTUAL-CONVENTION
    STATUS          current
    DESCRIPTION
        "A number used to identify a site. This ID must be unique within the
        service-domain.

        The value of -1 is used as 'undefined'."
    SYNTAX       Integer32 (-1|1..65535)

-- --------------------------------------------------------------------
-- Objects in the TIMETRA-SERV-MIB
-- --------------------------------------------------------------------
-- --------------------------------------------------------------------
-- Customer related objects
-- --------------------------------------------------------------------
custNumEntries OBJECT-TYPE
    SYNTAX          Integer32
    MAX-ACCESS      read-only
    STATUS          current
    DESCRIPTION     "The value of the object custNumEntries indicates the
                     current number of customer records configured in this
                     device."
    ::= { tmnxCustObjs 1 }

custNextFreeId OBJECT-TYPE
    SYNTAX          TmnxCustId
    MAX-ACCESS      read-only
    STATUS          current
    DESCRIPTION     "The value of the object custNextFreeId indicates the next
                     available value for custId, the index for the
                     custInfoTable."
    ::= { tmnxCustObjs 2 }

-- ------------------------------------
-- Customer Table
-- ------------------------------------
custInfoTable OBJECT-TYPE
    SYNTAX          SEQUENCE OF CustInfoEntry
    MAX-ACCESS      not-accessible
    STATUS          current
    DESCRIPTION     "A table that contains customer information. There
                     is an entry in this table corresponding to the
                     default customer. This entry cannot be edited or
                     deleted, and it is used as the default customer
                     for newly created services."
    ::= { tmnxCustObjs 3 }

custInfoEntry OBJECT-TYPE
    SYNTAX          CustInfoEntry
    MAX-ACCESS      not-accessible
    STATUS          current
    DESCRIPTION     "Information about a specific customer."
    INDEX           { custId }
    ::= { custInfoTable 1 }

CustInfoEntry ::=
    SEQUENCE {
        custId              TmnxCustId,
        custRowStatus       RowStatus,
        custDescription     ServObjDesc,
        custContact         ServObjDesc,
        custPhone           ServObjDesc,
        custLastMgmtChange  TimeStamp,
        custCreationOrigin  TmnxCreateOrigin
    }

custId OBJECT-TYPE
    SYNTAX          TmnxCustId
    MAX-ACCESS      read-only
    STATUS          current
    DESCRIPTION     "Customer identifier. This ID must be unique
                     within a service domain."
    ::= { custInfoEntry 1 }

custRowStatus OBJECT-TYPE
    SYNTAX          RowStatus
    MAX-ACCESS      read-create
    STATUS          current
    DESCRIPTION     "The value of the object  custRowStatus specifies the
                     status of this row."
    ::= { custInfoEntry 2 }

custDescription OBJECT-TYPE
    SYNTAX          ServObjDesc
    MAX-ACCESS      read-create
    STATUS          current
    DESCRIPTION     "The value of the object custDescription specifies
                     optional, generic information about this customer
                     in a displayable format."
    DEFVAL          { "" }
    ::= { custInfoEntry 3 }

custContact OBJECT-TYPE
    SYNTAX          ServObjDesc
    MAX-ACCESS      read-create
    STATUS          current
    DESCRIPTION     "The value of the object custContact specifies the name of
                     the primary contact person for this customer."
    DEFVAL          { "" }
    ::= { custInfoEntry 4 }

custPhone OBJECT-TYPE
    SYNTAX          ServObjDesc
    MAX-ACCESS      read-create
    STATUS          current
    DESCRIPTION     "The value of the object custPhone specifies the
                     phone/pager number used to reach the primary contact
                     person."
    DEFVAL          { "" }
    ::= { custInfoEntry 5 }

custLastMgmtChange OBJECT-TYPE
    SYNTAX          TimeStamp
    MAX-ACCESS      read-only
    STATUS          current
    DESCRIPTION     "The value of the object custLastMgmtChange indicates the
                     value of the object sysUpTime at the time of the
                     most recent management-initiated change to
                     this customer."
    ::= { custInfoEntry 6 }

custCreationOrigin OBJECT-TYPE
    SYNTAX          TmnxCreateOrigin
    MAX-ACCESS      read-only
    STATUS          current
    DESCRIPTION     "The value of the object custCreationOrigin indicates the
                     mechanism used to create this customer."
    ::= { custInfoEntry 7 }

-- ------------------------------------
-- Customer Multi-Service Site Table
-- ------------------------------------
custMultiServiceSiteTable OBJECT-TYPE
    SYNTAX          SEQUENCE OF CustMultiServiceSiteEntry
    MAX-ACCESS      not-accessible
    STATUS          current
    DESCRIPTION     ""
    ::= { tmnxCustObjs 4 }

custMultiServiceSiteEntry OBJECT-TYPE
    SYNTAX          CustMultiServiceSiteEntry
    MAX-ACCESS      not-accessible
    STATUS          current
    DESCRIPTION     "Information about a specific customer's
                     multi-service site."
    INDEX           { custId, IMPLIED custMultSvcSiteName }
    ::= { custMultiServiceSiteTable 1 }

CustMultiServiceSiteEntry ::=
    SEQUENCE {
        custMultSvcSiteName                     TNamedItem,
        custMultSvcSiteRowStatus                RowStatus,
        custMultSvcSiteDescription              ServObjDesc,
        custMultSvcSiteScope                    INTEGER,
        custMultSvcSiteAssignment               Unsigned32,
        custMultSvcSiteIngressSchedulerPolicy   ServObjName,
        custMultSvcSiteEgressSchedulerPolicy    ServObjName,
        custMultSvcSiteLastMgmtChange           TimeStamp,
        custMultSvcSiteTodSuite                 TNamedItemOrEmpty,
        custMultSvcSiteCurrentIngrSchedPlcy     ServObjName,
        custMultSvcSiteCurrentEgrSchedPlcy      ServObjName,
        custMultSvcSiteEgressAggRateLimit       TPortSchedulerAggRateLimitPIR,
        custMultSvcSiteIntendedIngrSchedPlcy    ServObjName,
        custMultSvcSiteIntendedEgrSchedPlcy     ServObjName,
        custMultSvcSiteFrameBasedAccnt          TruthValue,
        custMultSvcSiteSubscriberMss            TruthValue,
        custMultSvcSiteIngPolcrCtrlPolcy        TNamedItemOrEmpty,
        custMultSvcSiteEgrPolcrCtrlPolcy        TNamedItemOrEmpty,
        custMultSvcSiteEgressAggRateLUB         TruthValue,
        custMultSvcSiteEgrAggRateLimit          Unsigned32
    }

custMultSvcSiteName OBJECT-TYPE
    SYNTAX          TNamedItem
    MAX-ACCESS      read-only
    STATUS          current
    DESCRIPTION     "The value of object custMultSvcSiteName specifies
                     the customer's Multi-Service Site name."
    ::= { custMultiServiceSiteEntry 1 }

custMultSvcSiteRowStatus OBJECT-TYPE
    SYNTAX          RowStatus
    MAX-ACCESS      read-create
    STATUS          current
    DESCRIPTION     "The value of the object  custMultSvcSiteRowStatus
                     specifies the status of this row."
    ::= { custMultiServiceSiteEntry 2 }

custMultSvcSiteDescription OBJECT-TYPE
    SYNTAX          ServObjDesc
    MAX-ACCESS      read-create
    STATUS          current
    DESCRIPTION     "The value of the object custMultSvcSiteDescription
                     specifies option, generic information about this
                     customer's Multi-Service Site."
    DEFVAL          { "" }
    ::= { custMultiServiceSiteEntry 3 }

custMultSvcSiteScope OBJECT-TYPE
    SYNTAX          INTEGER {
                        port (1),
                        card (2)
                    }
    MAX-ACCESS      read-create
    STATUS          current
    DESCRIPTION     "The value of the object custMultSvcSiteScope specifies
                     the scope of the ingress and egress QoS scheduler policies
                     assigned to this Multi-Service Site. When the value is
                    'port' all the SAPs that are members of this
                     Multi-Service Site must be defined on the same port.
                     Similarly for the case of'card'."
    DEFVAL          { port }
    ::= { custMultiServiceSiteEntry 4 }

custMultSvcSiteAssignment OBJECT-TYPE
    SYNTAX          Unsigned32
    MAX-ACCESS      read-create
    STATUS          current
    DESCRIPTION     "The value of the object custMultSvcSiteAssignment
                     specifies the port ID, MDA, or card number, where
                     the SAPs that are members of this Multi-
                     Service Site are defined."
    DEFVAL          { 0 }
    ::= { custMultiServiceSiteEntry 5 }

custMultSvcSiteIngressSchedulerPolicy OBJECT-TYPE
    SYNTAX          ServObjName
    MAX-ACCESS      read-create
    STATUS          current
    DESCRIPTION     "The value of the object
                     custMultSvcSiteIngressSchedulerPolicy specifies the
                     ingress QoS scheduler policy assigned to this
                     Multi-Service Site."
    DEFVAL          { "" }
    ::= { custMultiServiceSiteEntry 6 }

custMultSvcSiteEgressSchedulerPolicy OBJECT-TYPE
    SYNTAX          ServObjName
    MAX-ACCESS      read-create
    STATUS          current
    DESCRIPTION     "The value of the object
                     custMultSvcSiteEgressSchedulerPolicy specifies the egress
                     QoS scheduler policy assigned to this Multi-Service Site."
    DEFVAL          { "" }
    ::= { custMultiServiceSiteEntry 7 }

custMultSvcSiteLastMgmtChange OBJECT-TYPE
    SYNTAX          TimeStamp
    MAX-ACCESS      read-only
    STATUS          current
    DESCRIPTION     "The value of the object custMultSvcSiteLastMgmtChange
                     indicates the value of sysUpTime at the time of the
                     most recent management-initiated change to
                     this multi-service site."
    ::= { custMultiServiceSiteEntry 8 }

custMultSvcSiteTodSuite OBJECT-TYPE
    SYNTAX          TNamedItemOrEmpty
    MAX-ACCESS      read-create
    STATUS          current
    DESCRIPTION     "The value of the object custMultSvcSiteTodSuite specifies
                     the Time of Day (ToD) suite to be applied on this
                     multi-service site. An empty string indicates that no ToD
                     suite is applied on this multi-service Site.
                     A set request will only be allowed, if the indicated suite
                     is defined is TIMETRA-SCHEDULER-MIB::tmnxTodSuiteTable.
                     Using a suite the values of
                     custMultSvcSiteIngressSchedulerPolicy and
                     custMultSvcSiteEgressSchedulerPolicy can be time based
                     manipulated."
    DEFVAL          { ''H }
    ::= { custMultiServiceSiteEntry 9 }

custMultSvcSiteCurrentIngrSchedPlcy OBJECT-TYPE
    SYNTAX          ServObjName
    MAX-ACCESS      read-only
    STATUS          current
    DESCRIPTION     "The value of the object
                     custMultSvcSiteCurrentIngrSchedPlcy indicates the Ingress
                     QoS scheduler on this multi-service Site, or zero if none
                     is currently active.
                     The active policy may deviate from
                     custMultSvcSiteIngressSchedulerPolicy
                     in case it is overruled by a ToD-suite policy defined on
                     this multi-service site."
    ::= { custMultiServiceSiteEntry 10 }

custMultSvcSiteCurrentEgrSchedPlcy OBJECT-TYPE
    SYNTAX          ServObjName
    MAX-ACCESS      read-only
    STATUS          current
    DESCRIPTION     "The value of the object custMultSvcSiteCurrentEgrSchedPlcy
                     indicates the Egress QoS scheduler on this SAP, or zero if
                     none is currently active.
                     The active policy may deviate from the
                     sapEgressQosSchedulerPolicy in case it is overruled by a
                     ToD-suite policy defined on this multi-service site."
    ::= { custMultiServiceSiteEntry 11 }

custMultSvcSiteEgressAggRateLimit       OBJECT-TYPE
    SYNTAX          TPortSchedulerAggRateLimitPIR
    UNITS           "kbps"
    MAX-ACCESS      read-create
    STATUS          obsolete
    DESCRIPTION     "The value of the object custMultSvcSiteEgressAggRateLimit
                     specifies the maximum total rate of all egress queues for
                     this multi-service site. The value '-1' means that there
                     is no limit.

                     This objects is obsoleted in 13.0 release and replaced by
                     custMultSvcSiteEgrAggRateLimit."
    DEFVAL          { -1 }
    ::= { custMultiServiceSiteEntry 12 }

custMultSvcSiteIntendedIngrSchedPlcy OBJECT-TYPE
    SYNTAX          ServObjName
    MAX-ACCESS      read-only
    STATUS          current
    DESCRIPTION     "The value of the object custMultSvcSiteIntendedIngrSchedPlcy
                     indicates  indicates the Ingress QoS scheduler on this
                     multi-service Site that should be applied.
                     If it deviates from custMultSvcSiteCurrentIngrSchedPlcy,
                     this  means that there was a problem when trying to
                     activate this filter. It can only deviate when using
                     tod-suites for the SAP. When the tod-suites decides that
                     a new filter must be applied, it will try to do this.
                     If it fails, the current and intended field are
                     not equal."
    ::= { custMultiServiceSiteEntry 13 }

custMultSvcSiteIntendedEgrSchedPlcy OBJECT-TYPE
    SYNTAX          ServObjName
    MAX-ACCESS      read-only
    STATUS          current
    DESCRIPTION     "The value of the object custMultSvcSiteIntendedEgrSchedPlcy
                     indicates  indicates the Egress QoS scheduler on this
                     multi-service Site that should be applied.
                     If it deviates from custMultSvcSiteCurrentEgrSchedPlcy,
                     this  means that there was a problem when trying to
                     activate this filter. It can only deviate when using
                     tod-suites for the SAP. When the tod-suites decides that
                     a new filter must be applied, it will try to do this.
                     If it fails, the current and intended field are
                     not equal."
    ::= { custMultiServiceSiteEntry 14 }

custMultSvcSiteFrameBasedAccnt OBJECT-TYPE
    SYNTAX       TruthValue
    MAX-ACCESS   read-create
    STATUS       current
    DESCRIPTION
        "The value of custMultSvcSiteFrameBasedAccnt specifies whether
         to use frame-based accounting when evaluating 
         custMultSvcSiteEgrAggRateLimit for the egress queues for
         this multi-service site.

         If the value is 'false', the default packet-based accounting
         method will be used."
    DEFVAL { false }
    ::= { custMultiServiceSiteEntry 15 }

custMultSvcSiteSubscriberMss  OBJECT-TYPE
    SYNTAX       TruthValue
    MAX-ACCESS   read-create
    STATUS       current
    DESCRIPTION
        "The value of custMultSvcSiteSubscriberMss specifies whether
         this multi-service site will be used as the default multi-service site for
         subscribers linked to the port specified in custMultSvcSiteAssignment when
         the use-subscriber-mss flag is set on the subscriber's subscriber-profile.
    
         This field can only be set when the value of custMultSvcSiteScope is set
         to 'port(1)'."
    DEFVAL { false }
::= { custMultiServiceSiteEntry 16 }

custMultSvcSiteIngPolcrCtrlPolcy  OBJECT-TYPE
    SYNTAX       TNamedItemOrEmpty
    MAX-ACCESS   read-create
    STATUS       current
    DESCRIPTION
        "The value of the object custMultSvcSiteIngPolcrCtrlPolcy specifies the
         ingress QoS policer control policy assigned to this Multi-Service Site."
    DEFVAL { "" }
::= { custMultiServiceSiteEntry 17 }

custMultSvcSiteEgrPolcrCtrlPolcy  OBJECT-TYPE
    SYNTAX       TNamedItemOrEmpty
    MAX-ACCESS   read-create
    STATUS       current
    DESCRIPTION
        "The value of the object custMultSvcSiteEgrPolcrCtrlPolcy specifies the
         egress QoS policer control policy assigned to this Multi-Service Site."
    DEFVAL { "" }
::= { custMultiServiceSiteEntry 18 }

custMultSvcSiteEgressAggRateLUB   OBJECT-TYPE
    SYNTAX      TruthValue
    MAX-ACCESS  read-create
    STATUS      current
    DESCRIPTION 
        "The value of custMultSvcSiteEgressAggRateLUB specifies whether to limit
         the unused bandwidth and allow a tighter control in allocation of 
         bandwidth by HQos.

         When the value of custMultSvcSiteEgressAggRateLUB is set to 'true',
         HQos algorithm distributes any unused aggregate bandwidth between
         queues operating below their fair share rates. This allows a simplified
         aggregate rate protection while allocating bandwidth by HQos scheduling
         algorithm."
    DEFVAL { false }
    ::= { custMultiServiceSiteEntry 19 }



custMultSvcSiteEgrAggRateLimit      OBJECT-TYPE
    SYNTAX          Unsigned32 (1..3200000000 | 4294967295)
    UNITS           "kbps"
    MAX-ACCESS      read-create
    STATUS          current
    DESCRIPTION
        "The value of the object custMultSvcSiteEgrAggRateLimit specifies the
         maximum total rate of all egress queues for this multi-service site.
         The value of 4294967295 (0xFFFFFFFF) means that there is no limit."
    DEFVAL { 4294967295 }
    ::= { custMultiServiceSiteEntry 22 }

-- ----------------------------------------------------
-- Customer Multi-Service Site Ingress Statistics Table
-- ----------------------------------------------------
custMultiSvcSiteIngStatsTable OBJECT-TYPE
    SYNTAX          SEQUENCE OF CustMultiSvcSiteIngQosSchedStatsEntry
    MAX-ACCESS      not-accessible
    STATUS          current
    DESCRIPTION     "A table that contains ingress QoS scheduler
                     statistics for the customer multi service site."
    ::= { tmnxCustObjs 5 }

custMultiSvcSiteIngStatsEntry OBJECT-TYPE
    SYNTAX          CustMultiSvcSiteIngQosSchedStatsEntry
    MAX-ACCESS      not-accessible
    STATUS          current
    DESCRIPTION     "Ingress statistics about a specific customer
                     multi service site ingress scheduler."
    INDEX           { custId, custMultSvcSiteName, IMPLIED custIngQosSchedName}
    ::= { custMultiSvcSiteIngStatsTable 1 }

CustMultiSvcSiteIngQosSchedStatsEntry ::=
    SEQUENCE {
        custIngQosSchedName                     TNamedItem,
        custIngQosSchedStatsForwardedPackets    Counter64,
        custIngQosSchedStatsForwardedOctets     Counter64
    }

custIngQosSchedName OBJECT-TYPE
    SYNTAX          TNamedItem
    MAX-ACCESS      not-accessible
    STATUS          current
    DESCRIPTION     "The index of the ingress QoS scheduler of
                     this customer multi service site."
    ::= { custMultiSvcSiteIngStatsEntry 1 }

custIngQosSchedStatsForwardedPackets OBJECT-TYPE
    SYNTAX          Counter64
    MAX-ACCESS      read-only
    STATUS          current
    DESCRIPTION     "The value of the object
                     custIngQosSchedStatsForwardedPackets indicates the number
                     of forwarded packets, as determined by the customer
                     multi service site ingress scheduler policy."
    ::= { custMultiSvcSiteIngStatsEntry 2 }

custIngQosSchedStatsForwardedOctets OBJECT-TYPE
    SYNTAX          Counter64
    MAX-ACCESS      read-only
    STATUS          current
    DESCRIPTION     "The value of the object
                     custIngQosSchedStatsForwardedOctets indicates the number
                     of forwarded octets, as determined by the customer
                     multi service site ingress scheduler policy."
    ::= { custMultiSvcSiteIngStatsEntry 3 }

-- -----------------------------------------------------
-- Customer Multi-Service Site Egress Statistics Table
-- -----------------------------------------------------
custMultiSvcSiteEgrStatsTable OBJECT-TYPE
    SYNTAX          SEQUENCE OF CustMultiSvcSiteEgrQosSchedStatsEntry
    MAX-ACCESS      not-accessible
    STATUS          current
    DESCRIPTION     "A table that contains egress QoS scheduler
                     statistics for the customer multi service site."
    ::= { tmnxCustObjs 6 }

custMultiSvcSiteEgrStatsEntry OBJECT-TYPE
    SYNTAX          CustMultiSvcSiteEgrQosSchedStatsEntry
    MAX-ACCESS      not-accessible
    STATUS          current
    DESCRIPTION     "Egress statistics about a specific customer
                     multi service site egress scheduler."
    INDEX           { custId, custMultSvcSiteName, IMPLIED custEgrQosSchedName}
    ::= { custMultiSvcSiteEgrStatsTable 1 }

CustMultiSvcSiteEgrQosSchedStatsEntry ::=
    SEQUENCE {
        custEgrQosSchedName                     TNamedItem,
        custEgrQosSchedStatsForwardedPackets    Counter64,
        custEgrQosSchedStatsForwardedOctets     Counter64
    }

custEgrQosSchedName OBJECT-TYPE
    SYNTAX          TNamedItem
    MAX-ACCESS      not-accessible
    STATUS          current
    DESCRIPTION     "The index of the egress QoS scheduler of
                     this customer multi service site."
    ::= { custMultiSvcSiteEgrStatsEntry 1 }

custEgrQosSchedStatsForwardedPackets OBJECT-TYPE
    SYNTAX          Counter64
    MAX-ACCESS      read-only
    STATUS          current
    DESCRIPTION     "The value of the object
                     custEgrQosSchedStatsForwardedPackets indicates number of
                     forwarded packets, as determined by the customer
                     multi service site egress scheduler policy."
    ::= { custMultiSvcSiteEgrStatsEntry 2 }

custEgrQosSchedStatsForwardedOctets OBJECT-TYPE
    SYNTAX          Counter64
    MAX-ACCESS      read-only
    STATUS          current
    DESCRIPTION     "The value of the object
                     custEgrQosSchedStatsForwardedOctets indicates the number
                     of forwarded octets, as determined by the customer
                     multi service site egress scheduler policy."
    ::= { custMultiSvcSiteEgrStatsEntry 3 }

-- ----------------------------------------------------
-- Customer Multi-Service Site Ingress Statistics Table
-- with specific portId
-- ----------------------------------------------------
custIngQosPortIdSchedStatsTable OBJECT-TYPE
    SYNTAX          SEQUENCE OF CustIngQosPortIdSchedStatsEntry
    MAX-ACCESS      not-accessible
    STATUS          current
    DESCRIPTION
        "The custIngQosPortIdSchedStatsTable contains ingress QoS scheduler
         statistics for the customer multi service site."
    ::= { tmnxCustObjs 7 }

custIngQosPortIdSchedStatsEntry OBJECT-TYPE
    SYNTAX          CustIngQosPortIdSchedStatsEntry
    MAX-ACCESS      not-accessible
    STATUS          current
    DESCRIPTION
        "Each entry represents the ingress statistics about a specific customer
         multi service site ingress scheduler. Entries are created when
         a scheduler policy is applied to an MSS."
    INDEX           { custId, custMultSvcSiteName,
                      custIngQosPortIdSchedName, custIngQosAssignmentPortId }
    ::= { custIngQosPortIdSchedStatsTable 1 }

CustIngQosPortIdSchedStatsEntry ::=
    SEQUENCE {
        custIngQosPortIdSchedName                     TNamedItem,
        custIngQosAssignmentPortId                    TmnxPortID,
        custIngQosPortSchedFwdPkts                    Counter64,
        custIngQosPortSchedFwdOctets                  Counter64
    }

custIngQosPortIdSchedName OBJECT-TYPE
    SYNTAX          TNamedItem
    MAX-ACCESS      not-accessible
    STATUS          current
    DESCRIPTION
        "The value of custIngQosPortIdSchedName is used as an index
         of the ingress QoS scheduler of this customer multi service site."
    ::= { custIngQosPortIdSchedStatsEntry 1 }

custIngQosAssignmentPortId OBJECT-TYPE
    SYNTAX          TmnxPortID
    MAX-ACCESS      not-accessible
    STATUS          current
    DESCRIPTION
        "The value of custIngQosAssignmentPortId is used as an index
         of the ingress QoS scheduler/arbiter of this customer multi service 
         site. When an MSS assignment is an aps/ccag/lag in 'link' mode, each
         member-port of the aps/ccag/lag has its own scheduler/arbiter. This 
         object refers to the TmnxPortID of these member-ports."
    ::= {custIngQosPortIdSchedStatsEntry 2}

custIngQosPortSchedFwdPkts OBJECT-TYPE
    SYNTAX          Counter64
    MAX-ACCESS      read-only
    STATUS          current
    DESCRIPTION
        "The value of custIngQosPortSchedFwdPkts indicates the
         number of forwarded packets, as determined by the customer
         multi service site ingress scheduler policy."
    ::= { custIngQosPortIdSchedStatsEntry 3 }

custIngQosPortSchedFwdOctets OBJECT-TYPE
    SYNTAX          Counter64
    MAX-ACCESS      read-only
    STATUS          current
    DESCRIPTION
        "The value of custIngQosPortSchedFwdOctets indicates the
         number of forwarded octets, as determined by the customer
         multi service site ingress scheduler policy."
    ::= { custIngQosPortIdSchedStatsEntry 4 }

-- --------------------------------------------------------
-- Customer Multi-Service Site Egress Statistics Table
-- with specific portId
-- --------------------------------------------------------
custEgrQosPortIdSchedStatsTable OBJECT-TYPE
    SYNTAX          SEQUENCE OF CustEgrQosPortIdSchedStatsEntry
    MAX-ACCESS      not-accessible
    STATUS          current
    DESCRIPTION
        "The custEgrQosPortIdSchedStatsTable contains egress QoS scheduler
         statistics for the customer multi service site."
    ::= { tmnxCustObjs 8 }

custEgrQosPortIdSchedStatsEntry OBJECT-TYPE
    SYNTAX          CustEgrQosPortIdSchedStatsEntry
    MAX-ACCESS      not-accessible
    STATUS          current
    DESCRIPTION
        "Each row entry represents the egress statistics for a customer
         multi-service-site egress scheduler. Entries are created when
         a scheduler policy is applied to an MSS."
    INDEX           { custId, custMultSvcSiteName,
                      custEgrQosPortIdSchedName, custEgrQosAssignmentPortId }
    ::= { custEgrQosPortIdSchedStatsTable 1 }

CustEgrQosPortIdSchedStatsEntry ::=
    SEQUENCE {
        custEgrQosPortIdSchedName       TNamedItem,
        custEgrQosAssignmentPortId      TmnxPortID,
        custEgrQosPortSchedFwdPkts      Counter64,
        custEgrQosPortSchedFwdOctets    Counter64
    }

custEgrQosPortIdSchedName OBJECT-TYPE
    SYNTAX          TNamedItem
    MAX-ACCESS      not-accessible
    STATUS          current
    DESCRIPTION
        "The value of custEgrQosPortIdSchedName is used as an index
         of the egress QoS scheduler of this customer multi service site."
    ::= { custEgrQosPortIdSchedStatsEntry 1}

custEgrQosAssignmentPortId OBJECT-TYPE
    SYNTAX          TmnxPortID
    MAX-ACCESS      not-accessible
    STATUS          current
    DESCRIPTION
        "The value of custEgrQosAssignmentPortId is used as an index
         of the egress QoS scheduler/arbiter of this customer multi service 
         site. When an MSS assignment is an aps/ccag/lag in 'link' mode, each
         member-port of the aps/ccag/lag has its own scheduler/arbiter. This 
         object refers to the TmnxPortID of these member-ports."
    ::= { custEgrQosPortIdSchedStatsEntry 2}

custEgrQosPortSchedFwdPkts OBJECT-TYPE
    SYNTAX          Counter64
    MAX-ACCESS      read-only
    STATUS          current
    DESCRIPTION
        "The value of custEgrQosPortSchedFwdPkts indicates the
         number of forwarded packets, as determined by the customer
         multi service site egress scheduler policy."
    ::= { custEgrQosPortIdSchedStatsEntry 3 }

custEgrQosPortSchedFwdOctets OBJECT-TYPE
    SYNTAX          Counter64
    MAX-ACCESS      read-only
    STATUS          current
    DESCRIPTION
        "The value of custEgrQosPortSchedFwdOctets indicates the
         number of forwarded octets, as determined by the customer
         multi service site egress scheduler policy."
    ::= { custEgrQosPortIdSchedStatsEntry 4 }

-- --------------------------------------------------------
-- Customer Multi-Service Site Ingress QoS Scheduler Table
-- --------------------------------------------------------
custMssIngQosSchedInfoTable OBJECT-TYPE
    SYNTAX          SEQUENCE OF CustMssIngQosSchedInfoEntry
    MAX-ACCESS      not-accessible
    STATUS          current
    DESCRIPTION     "A table that contains ingress QoS scheduler
                     statistics for the customer multi service site."
    ::= { tmnxCustObjs 9 }

custMssIngQosSchedInfoEntry OBJECT-TYPE
    SYNTAX          CustMssIngQosSchedInfoEntry
    MAX-ACCESS      not-accessible
    STATUS          current
    DESCRIPTION     "Ingress statistics about a specific customer
                     multi service site ingress scheduler."
    INDEX           { custId,
                      custMultSvcSiteName,
                      IMPLIED custMssIngQosSName }
    ::= { custMssIngQosSchedInfoTable 1 }

CustMssIngQosSchedInfoEntry ::=
    SEQUENCE {
        custMssIngQosSName              TNamedItem,
        custMssIngQosSRowStatus         RowStatus,
        custMssIngQosSLastMgmtChange    TimeStamp,
        custMssIngQosSOverrideFlags     TVirtSchedAttribute,
        custMssIngQosSPIR               THPolVirtualSchePIRRate,
        custMssIngQosSCIR               THPolVirtualScheCIRRate,
        custMssIngQosSSummedCIR         TruthValue,
        custMssIngQosSPIRHi             Unsigned32,
        custMssIngQosSPIRLo             Unsigned32,
        custMssIngQosSCIRHi             Unsigned32,
        custMssIngQosSCIRLo             Unsigned32,
        custMssIngQosSParentWeight      TWeight,
        custMssIngQosSParentCIRWeight   TWeight
    }

custMssIngQosSName OBJECT-TYPE
    SYNTAX          TNamedItem
    MAX-ACCESS      not-accessible
    STATUS          current
    DESCRIPTION     "The value of custMssIngQosSName indicates the name of
                     the virtual scheduler whose parameters are to be
                     overridden."
    ::= { custMssIngQosSchedInfoEntry 1 }

custMssIngQosSRowStatus OBJECT-TYPE
    SYNTAX          RowStatus
    MAX-ACCESS      read-create
    STATUS          current
    DESCRIPTION     "The value of custMssIngQosSRowStatus controls the
                     creation and deletion of rows in this table."
    ::= { custMssIngQosSchedInfoEntry 2 }

custMssIngQosSLastMgmtChange OBJECT-TYPE
    SYNTAX          TimeStamp
    MAX-ACCESS      read-only
    STATUS          current
    DESCRIPTION     "The value of custMssIngQosSLastMgmtChange indicates the
                     value of sysUpTime at the time of the last management
                     change of any writable object of this row."
    ::= { custMssIngQosSchedInfoEntry 3 }

custMssIngQosSOverrideFlags OBJECT-TYPE
    SYNTAX          TVirtSchedAttribute
    MAX-ACCESS      read-create
    STATUS          current
    DESCRIPTION     "The value of custMssIngQosSOverrideFlags specifies the
                     set of attributes whose values have been overridden
                     via management on this virtual scheduler. Clearing a
                     given flag will return the corresponding overridden
                     attribute to the value defined on the SAP's ingress
                     scheduler policy."
    ::= { custMssIngQosSchedInfoEntry 4 }

custMssIngQosSPIR OBJECT-TYPE
    SYNTAX          THPolVirtualSchePIRRate
    UNITS           "kilo bits per second"
    MAX-ACCESS      read-create
    STATUS          obsolete
    DESCRIPTION     "The value of custMssIngQosSPIR specifies the desired
                     PIR value for this virtual scheduler.

                     This object is obsoleted in 11.0 Release. It is replaced by 
                     custMssIngQosSPIRHi and custMssIngQosSPIRLo."
    DEFVAL { -1 }
    ::= { custMssIngQosSchedInfoEntry 5 }

custMssIngQosSCIR OBJECT-TYPE
    SYNTAX          THPolVirtualScheCIRRate
    UNITS           "kilo bits per second"
    MAX-ACCESS      read-create
    STATUS          obsolete
    DESCRIPTION     "The value of custMssIngQosSCIR specifies the desired
                     CIR value for this virtual scheduler.

                     This object is obsoleted in 11.0 Release. It is replaced by 
                     custMssIngQosSCIRHi and custMssIngQosSCIRLo."
    DEFVAL { 0 }
    ::= { custMssIngQosSchedInfoEntry 6 }

custMssIngQosSSummedCIR OBJECT-TYPE
    SYNTAX          TruthValue
    MAX-ACCESS      read-create
    STATUS          current
    DESCRIPTION     "The value of custMssIngQosSSummedCIR specifies if the CIR
                     should be used as the summed CIR values of the children
                     schedulers or queues. If set to 'true', the applicable
                     scheduler CIR (custMssIngQosSCIR) loses its meaning."
    DEFVAL { true }
    ::= { custMssIngQosSchedInfoEntry 7 }

custMssIngQosSPIRHi OBJECT-TYPE
    SYNTAX          Unsigned32 (0 | 4294967295)
    UNITS           "kbps"
    MAX-ACCESS      read-create
    STATUS          current
    DESCRIPTION     "The value of custMssIngQosSPIRHi indicates upper 32 bits of
                     the pir-rate allowed for this virtual scheduler.    

                     This value should always be set along with
                     custMssIngQosSPIRLo, otherwise an 'inconsistentValue' error
                     is returned.

                     When the value of custMssIngQosSPIRHi along with the value
                     of custMssIngQosSPIRLo is set to 4294967295 (0xFFFFFFFF),
                     rate for this virtual scheduler indicates maximum rate."
    DEFVAL { 4294967295 }
    ::= { custMssIngQosSchedInfoEntry 8 }

custMssIngQosSPIRLo OBJECT-TYPE
    SYNTAX       Unsigned32 (1..3200000000 | 4294967295)
    UNITS        "kbps"
    MAX-ACCESS   read-create
    STATUS       current
    DESCRIPTION     "The value of custMssIngQosSPIRLo indicates lower 32 bits of
                     the pir-rate allowed for this virtual scheduler.    

                     This value should always be set along with
                     custMssIngQosSPIRHi, otherwise an 'inconsistentValue' error
                     is returned.

                     When the value of custMssIngQosSPIRHi along with the value
                     of custMssIngQosSPIRLo is set to 4294967295 (0xFFFFFFFF),
                     rate for this virtual scheduler indicates maximum rate."
    DEFVAL { 4294967295 }
    ::= { custMssIngQosSchedInfoEntry 9 }

custMssIngQosSCIRHi OBJECT-TYPE
    SYNTAX       Unsigned32 (0 | 4294967295)
    UNITS        "kbps"
    MAX-ACCESS   read-create
    STATUS       current
    DESCRIPTION     "The value of custMssIngQosSCIRHi indicates upper 32 bits of
                     the cir-rate allowed for this virtual scheduler.    

                     This value should always be set along with
                     custMssIngQosSCIRLo, otherwise an 'inconsistentValue' error
                     is returned.

                     When the value of custMssIngQosSCIRHi along with the value
                     of custMssIngQosSCIRLo is set to 4294967295 (0xFFFFFFFF),
                     rate for this virtual scheduler indicates maximum rate."
    DEFVAL { 4294967295 }
    ::= { custMssIngQosSchedInfoEntry 10 }

custMssIngQosSCIRLo OBJECT-TYPE
    SYNTAX       Unsigned32 (0..3200000000 | 4294967295)
    UNITS        "kbps"
    MAX-ACCESS   read-create
    STATUS       current
    DESCRIPTION     "The value of custMssIngQosSCIRLo indicates lower 32 bits of
                     the cir-rate allowed for this virtual scheduler.    

                     This value should always be set along with
                     custMssIngQosSCIRHi, otherwise an 'inconsistentValue' error
                     is returned.

                     When the value of custMssIngQosSCIRHi along with the value
                     of custMssIngQosSCIRLo is set to 4294967295 (0xFFFFFFFF),
                     rate for this virtual scheduler indicates maximum rate."
    DEFVAL { 4294967295 }
    ::= { custMssIngQosSchedInfoEntry 11 }

custMssIngQosSParentWeight          OBJECT-TYPE
    SYNTAX       TWeight
    MAX-ACCESS   read-create
    STATUS       current
    DESCRIPTION
        "The value of custMssIngQosSParentWeight specifies the weight that needs
         to be used by this virtual scheduler to which this queue would be
         feeding."
    DEFVAL { 1 }
    ::= { custMssIngQosSchedInfoEntry 12 }


custMssIngQosSParentCIRWeight       OBJECT-TYPE
    SYNTAX       TWeight
    MAX-ACCESS   read-create
    STATUS       current
    DESCRIPTION
        "The value of custMssIngQosSParentCIRWeight specifies the weight that
         needs to be used until the committed rate by this virtual scheduler to
         which this queue would be feeding."
    DEFVAL { 1 }
    ::= { custMssIngQosSchedInfoEntry 13 }

-- --------------------------------------------------------
-- Customer Multi-Service Site Egrress QoS Scheduler Table
-- --------------------------------------------------------
custMssEgrQosSchedInfoTable OBJECT-TYPE
    SYNTAX          SEQUENCE OF CustMssEgrQosSchedInfoEntry
    MAX-ACCESS      not-accessible
    STATUS          current
    DESCRIPTION     "A table that contains egress QoS scheduler
                     statistics for the customer multi service site."
    ::= { tmnxCustObjs 10 }

custMssEgrQosSchedInfoEntry OBJECT-TYPE
    SYNTAX          CustMssEgrQosSchedInfoEntry
    MAX-ACCESS      not-accessible
    STATUS          current
    DESCRIPTION     "Egrress statistics about a specific customer
                     multi service site egress scheduler."
    INDEX           { custId,
                      custMultSvcSiteName,
                      IMPLIED custMssEgrQosSName }
    ::= { custMssEgrQosSchedInfoTable 1 }

CustMssEgrQosSchedInfoEntry ::=
    SEQUENCE {
        custMssEgrQosSName              TNamedItem,
        custMssEgrQosSRowStatus         RowStatus,
        custMssEgrQosSLastMgmtChange    TimeStamp,
        custMssEgrQosSOverrideFlags     TVirtSchedAttribute,
        custMssEgrQosSPIR               THPolVirtualSchePIRRate,
        custMssEgrQosSCIR               THPolVirtualScheCIRRate,
        custMssEgrQosSSummedCIR         TruthValue,
        custMssEgrQosSPIRHi             Unsigned32,
        custMssEgrQosSPIRLo             Unsigned32,
        custMssEgrQosSCIRHi             Unsigned32,
        custMssEgrQosSCIRLo             Unsigned32,
        custMssEgrQosSParentWeight      TWeight,
        custMssEgrQosSParentCIRWeight   TWeight
    }

custMssEgrQosSName OBJECT-TYPE
    SYNTAX          TNamedItem
    MAX-ACCESS      not-accessible
    STATUS          current
    DESCRIPTION     "The value of custMssEgrQosSName indicates the name of
                     the virtual scheduler whose parameters are to be
                     overridden."
    ::= { custMssEgrQosSchedInfoEntry 1 }

custMssEgrQosSRowStatus OBJECT-TYPE
    SYNTAX          RowStatus
    MAX-ACCESS      read-create
    STATUS          current
    DESCRIPTION     "The value of custMssEgrQosSRowStatus controls the
                     creation and deletion of rows in this table."
    ::= { custMssEgrQosSchedInfoEntry 2 }

custMssEgrQosSLastMgmtChange OBJECT-TYPE
    SYNTAX          TimeStamp
    MAX-ACCESS      read-only
    STATUS          current
    DESCRIPTION     "The value of custMssEgrQosSLastMgmtChange indicates the
                     value of sysUpTime at the time of the last management
                     change of any writable object of this row."
    ::= { custMssEgrQosSchedInfoEntry 3 }

custMssEgrQosSOverrideFlags OBJECT-TYPE
    SYNTAX          TVirtSchedAttribute
    MAX-ACCESS      read-create
    STATUS          current
    DESCRIPTION     "The value of custMssEgrQosSOverrideFlags specifies the
                     set of attributes whose values have been overridden
                     via management on this virtual scheduler. Clearing a
                     given flag will return the corresponding overridden
                     attribute to the value defined on the SAP's ingress
                     scheduler policy."
    ::= { custMssEgrQosSchedInfoEntry 4 }

custMssEgrQosSPIR OBJECT-TYPE
    SYNTAX          THPolVirtualSchePIRRate
    UNITS           "kilo bits per second"
    MAX-ACCESS      read-create
    STATUS          obsolete
    DESCRIPTION     "The value of custMssEgrQosSPIR specifies the desired
                     PIR value for this virtual scheduler.
  
                     This object is obsoleted in 11.0 Release. It is replaced by 
                     custMssEgrQosSPIRHi and custMssEgrQosSPIRLo."
    DEFVAL { -1 }
    ::= { custMssEgrQosSchedInfoEntry 5 }

custMssEgrQosSCIR OBJECT-TYPE
    SYNTAX          THPolVirtualScheCIRRate
    UNITS           "kilo bits per second"
    MAX-ACCESS      read-create
    STATUS          obsolete
    DESCRIPTION     "The value of custMssEgrQosSCIR specifies the desired
                     CIR value for this virtual scheduler.

                     This object is obsoleted in 11.0 Release. It is replaced by 
                     custMssEgrQosSCIRHi and custMssEgrQosSCIRLo."
    DEFVAL { 0 }
    ::= { custMssEgrQosSchedInfoEntry 6 }

custMssEgrQosSSummedCIR OBJECT-TYPE
    SYNTAX          TruthValue
    MAX-ACCESS      read-create
    STATUS          current
    DESCRIPTION     "The value of custMssEgrQosSSummedCIR specifies if the CIR
                     should be used as the summed CIR values of the children
                     schedulers or queues. If set to 'true', the applicable
                     scheduler CIR (custMssEgrQosSCIR) loses its meaning."
    DEFVAL { true }
    ::= { custMssEgrQosSchedInfoEntry 7 }

custMssEgrQosSPIRHi OBJECT-TYPE
    SYNTAX          Unsigned32 (0 | 4294967295)
    UNITS           "kbps"
    MAX-ACCESS      read-create
    STATUS          current
    DESCRIPTION     "The value of custMssEgrQosSPIRHi indicates upper 32 bits of
                     the pir-rate allowed for this virtual scheduler.    

                     This value should always be set along with
                     custMssEgrQosSPIRLo, otherwise an 'inconsistentValue' error
                     is returned.

                     When the value of custMssEgrQosSPIRHi along with the value
                     of custMssEgrQosSPIRLo is set to 4294967295 (0xFFFFFFFF),
                     rate for this virtual scheduler indicates maximum rate."
    DEFVAL { 4294967295 }
    ::= { custMssEgrQosSchedInfoEntry 8 }

custMssEgrQosSPIRLo OBJECT-TYPE
    SYNTAX       Unsigned32 (1..3200000000 | 4294967295)
    UNITS        "kbps"
    MAX-ACCESS   read-create
    STATUS       current
    DESCRIPTION     "The value of custMssEgrQosSPIRLo indicates lower 32 bits of
                     the pir-rate allowed for this virtual scheduler.    

                     This value should always be set along with
                     custMssEgrQosSPIRHi, otherwise an 'inconsistentValue' error
                     is returned.

                     When the value of custMssEgrQosSPIRHi along with the value
                     of custMssEgrQosSPIRLo is set to 4294967295 (0xFFFFFFFF),
                     rate for this virtual scheduler indicates maximum rate."
    DEFVAL { 4294967295 }
    ::= { custMssEgrQosSchedInfoEntry 9 }

custMssEgrQosSCIRHi OBJECT-TYPE
    SYNTAX       Unsigned32 (0 | 4294967295)
    UNITS        "kbps"
    MAX-ACCESS   read-create
    STATUS       current
    DESCRIPTION     "The value of custMssEgrQosSCIRHi indicates upper 32 bits of
                     the cir-rate allowed for this virtual scheduler.    

                     This value should always be set along with
                     custMssEgrQosSCIRLo, otherwise an 'inconsistentValue' error
                     is returned.

                     When the value of custMssEgrQosSCIRHi along with the value
                     of custMssEgrQosSCIRLo is set to 4294967295 (0xFFFFFFFF),
                     rate for this virtual scheduler indicates maximum rate."
    DEFVAL { 4294967295 }
    ::= { custMssEgrQosSchedInfoEntry 10 }

custMssEgrQosSCIRLo OBJECT-TYPE
    SYNTAX       Unsigned32 (0..3200000000 | 4294967295)
    UNITS        "kbps"
    MAX-ACCESS   read-create
    STATUS       current
    DESCRIPTION     "The value of custMssEgrQosSCIRLo indicates lower 32 bits of
                     the cir-rate allowed for this virtual scheduler.    

                     This value should always be set along with
                     custMssEgrQosSCIRHi, otherwise an 'inconsistentValue' error
                     is returned.

                     When the value of custMssEgrQosSCIRHi along with the value
                     of custMssEgrQosSCIRLo is set to 4294967295 (0xFFFFFFFF),
                     rate for this virtual scheduler indicates maximum rate."
    DEFVAL { 4294967295 }
    ::= { custMssEgrQosSchedInfoEntry 11 }

custMssEgrQosSParentWeight          OBJECT-TYPE
    SYNTAX       TWeight
    MAX-ACCESS   read-create
    STATUS       current
    DESCRIPTION
        "The value of custMssEgrQosSParentWeight specifies the weight that needs
         to be used by this virtual scheduler to which this queue would be
         feeding."
    DEFVAL { 1 }
    ::= { custMssEgrQosSchedInfoEntry 12 }


custMssEgrQosSParentCIRWeight       OBJECT-TYPE
    SYNTAX       TWeight
    MAX-ACCESS   read-create
    STATUS       current
    DESCRIPTION
        "The value of custMssEgrQosSParentCIRWeight specifies the weight that
         needs to be used until the committed rate by this virtual scheduler to
         which this queue would be feeding."
    DEFVAL { 1 }
    ::= { custMssEgrQosSchedInfoEntry 13 }

-- --------------------------------------------------------
-- Customer Multi-Service Site Ingress Per-Policy 
-- Statistics Table
-- --------------------------------------------------------
custMultiSvcSiteIngSchedPlcyStatsTable OBJECT-TYPE
    SYNTAX          SEQUENCE OF CustMultiSvcSiteIngSchedPlcyStatsEntry
    MAX-ACCESS      not-accessible
    STATUS          current
    DESCRIPTION     "A table that contains ingress QoS scheduler
                     statistics for the customer multi service site, organized
                     by scheduler policy."
    ::= { tmnxCustObjs 11 }

custMultiSvcSiteIngSchedPlcyStatsEntry OBJECT-TYPE
    SYNTAX          CustMultiSvcSiteIngSchedPlcyStatsEntry
    MAX-ACCESS      not-accessible
    STATUS          current
    DESCRIPTION     "Ingress statistics about a specific customer
                     multi service site egress scheduler. Entries are created 
                     when a scheduler policy of a MSS is replaced with another 
                     one due to Time-Of-Day policies."
    INDEX           { custId, custMultSvcSiteName, 
                      tSchedulerPolicyName, IMPLIED tVirtualSchedulerName}
    ::= { custMultiSvcSiteIngSchedPlcyStatsTable 1 }

CustMultiSvcSiteIngSchedPlcyStatsEntry ::=
    SEQUENCE {
        custIngSchedPlcyStatsFwdPkt    Counter64,
        custIngSchedPlcyStatsFwdOct     Counter64
    }

custIngSchedPlcyStatsFwdPkt OBJECT-TYPE
    SYNTAX          Counter64
    MAX-ACCESS      read-only
    STATUS          current
    DESCRIPTION     "The value of the object
                     custIngSchedPlcyStatsFwdPkt indicates 
                     the number of forwarded packets, as determined by the 
                     customer multi service site ingress scheduler policy."
    ::= { custMultiSvcSiteIngSchedPlcyStatsEntry 1 }

custIngSchedPlcyStatsFwdOct OBJECT-TYPE
    SYNTAX          Counter64
    MAX-ACCESS      read-only
    STATUS          current
    DESCRIPTION     "The value of the object
                     custIngSchedPlcyStatsFwdOct indicates 
                     the number of forwarded octets, as determined by the 
                     customer multi service site ingress scheduler policy."
    ::= { custMultiSvcSiteIngSchedPlcyStatsEntry 2 }

-- --------------------------------------------------------
-- Customer Multi-Service Site Egress Per-Policy  
-- Statistics Table
-- --------------------------------------------------------
custMultiSvcSiteEgrSchedPlcyStatsTable OBJECT-TYPE
    SYNTAX          SEQUENCE OF CustMultiSvcSiteEgrSchedPlcyStatsEntry
    MAX-ACCESS      not-accessible
    STATUS          current
    DESCRIPTION     "A table that contains egress QoS scheduler
                     statistics for the customer multi service site, organized
                     by scheduler policy."
    ::= { tmnxCustObjs 12 }

custMultiSvcSiteEgrSchedPlcyStatsEntry OBJECT-TYPE
    SYNTAX          CustMultiSvcSiteEgrSchedPlcyStatsEntry
    MAX-ACCESS      not-accessible
    STATUS          current
    DESCRIPTION     "Egress statistics about a specific customer
                     multi service site egress scheduler. Entries are created 
                     when a scheduler policy of a MSS is replaced with another 
                     one due to Time-Of-Day policies."
    INDEX           { custId, custMultSvcSiteName, 
                      tSchedulerPolicyName, IMPLIED tVirtualSchedulerName}
    ::= { custMultiSvcSiteEgrSchedPlcyStatsTable 1 }

CustMultiSvcSiteEgrSchedPlcyStatsEntry ::=
    SEQUENCE {
        custEgrSchedPlcyStatsFwdPkt    Counter64,
        custEgrSchedPlcyStatsFwdOct    Counter64
    }

custEgrSchedPlcyStatsFwdPkt OBJECT-TYPE
    SYNTAX          Counter64
    MAX-ACCESS      read-only
    STATUS          current
    DESCRIPTION     "The value of the object
                     custEgrSchedPlcyStatsFwdPkt indicates 
                     the number of forwarded packets, as determined by 
                     the customer multi service site egress scheduler policy."
    ::= { custMultiSvcSiteEgrSchedPlcyStatsEntry 1 }

custEgrSchedPlcyStatsFwdOct OBJECT-TYPE
    SYNTAX          Counter64
    MAX-ACCESS      read-only
    STATUS          current
    DESCRIPTION     "The value of the object
                     custEgrSchedPlcyStatsFwdOct indicates 
                     the number of forwarded octets, as determined by 
                     the customer multi service site egress scheduler policy."
    ::= { custMultiSvcSiteEgrSchedPlcyStatsEntry 2 }

-- --------------------------------------------------------
-- Customer Multi-Service Site Ingress Per-Policy Statistics 
-- Table with specific portId
-- --------------------------------------------------------
custMultiSvcSiteIngSchedPlcyPortStatsTable OBJECT-TYPE
    SYNTAX          SEQUENCE OF CustMultiSvcSiteIngSchedPlcyPortStatsEntry
    MAX-ACCESS      not-accessible
    STATUS          current
    DESCRIPTION
        "The custMultiSvcSiteIngSchedPlcyPortStatsTable contains 
         ingress QoS scheduler statistics for the customer multi service site,
         organized by scheduler policy."
    ::= { tmnxCustObjs 13 }

custMultiSvcSiteIngSchedPlcyPortStatsEntry OBJECT-TYPE
    SYNTAX          CustMultiSvcSiteIngSchedPlcyPortStatsEntry
    MAX-ACCESS      not-accessible
    STATUS          current
    DESCRIPTION
        "Each entry represents the ingress statistics about a specific customer
         multi service site ingress scheduler. Entries are created when
         a scheduler policy of a MSS is replaced with another one due
         to Time-Of-Day policies."
    INDEX           { custId, custMultSvcSiteName, tSchedulerPolicyName, 
                      tVirtualSchedulerName, 
                      custIngSchedPlcyPortStatsPort }
    ::= { custMultiSvcSiteIngSchedPlcyPortStatsTable 1 }

CustMultiSvcSiteIngSchedPlcyPortStatsEntry ::=
    SEQUENCE {
        custIngSchedPlcyPortStatsPort           TmnxPortID,
        custIngSchedPlcyPortStatsFwdPkt         Counter64,
        custIngSchedPlcyPortStatsFwdOct         Counter64
    }

custIngSchedPlcyPortStatsPort OBJECT-TYPE
    SYNTAX          TmnxPortID
    MAX-ACCESS      not-accessible
    STATUS          current
    DESCRIPTION
        "The value of custIngSchedPlcyPortStatsPort is used as 
         an index of the ingress QoS scheduler of this customer multi service 
         site.
         When an MSS assignment is an aps/ccag/lag in 'link' mode, each
         member-port of the aps/ccag/lag has its own scheduler. This object
         refers to the TmnxPortID of these member-ports."
    ::= { custMultiSvcSiteIngSchedPlcyPortStatsEntry 1}

custIngSchedPlcyPortStatsFwdPkt OBJECT-TYPE
    SYNTAX          Counter64
    MAX-ACCESS      read-only
    STATUS          current
    DESCRIPTION
        "The value of custIngSchedPlcyPortStatsFwdPkt indicates the
         number of forwarded packets, as determined by the customer
         multi service site ingress scheduler policy."
    ::= { custMultiSvcSiteIngSchedPlcyPortStatsEntry 2 }

custIngSchedPlcyPortStatsFwdOct OBJECT-TYPE
    SYNTAX          Counter64
    MAX-ACCESS      read-only
    STATUS          current
    DESCRIPTION
        "The value of custIngSchedPlcyPortStatsFwdOct indicates the
         number of forwarded octets, as determined by the customer
         multi service site ingress scheduler policy."
    ::= { custMultiSvcSiteIngSchedPlcyPortStatsEntry 3 }


-- --------------------------------------------------------
-- Customer Multi-Service Site Egress Per-Policy Statistics 
-- Table with specific portId
-- --------------------------------------------------------
custMultiSvcSiteEgrSchedPlcyPortStatsTable OBJECT-TYPE
    SYNTAX          SEQUENCE OF CustMultiSvcSiteEgrSchedPlcyPortStatsEntry
    MAX-ACCESS      not-accessible
    STATUS          current
    DESCRIPTION
        "The custMultiSvcSiteEgrSchedPlcyPortStatsTable contains 
         egress QoS scheduler statistics for the customer multi service site,
         organized by scheduler policy."
    ::= { tmnxCustObjs 14 }

custMultiSvcSiteEgrSchedPlcyPortStatsEntry OBJECT-TYPE
    SYNTAX          CustMultiSvcSiteEgrSchedPlcyPortStatsEntry
    MAX-ACCESS      not-accessible
    STATUS          current
    DESCRIPTION
        "Each entry represents the egress statistics about a specific customer
         multi service site egress scheduler. Entries are created when
         a scheduler policy of a MSS is replaced with another one due
         to Time-Of-Day policies."
    INDEX           { custId, custMultSvcSiteName, tSchedulerPolicyName,
                      tVirtualSchedulerName, 
                      custEgrSchedPlcyPortStatsPort }
    ::= { custMultiSvcSiteEgrSchedPlcyPortStatsTable 1 }

CustMultiSvcSiteEgrSchedPlcyPortStatsEntry ::=
    SEQUENCE {
        custEgrSchedPlcyPortStatsPort      TmnxPortID,
        custEgrSchedPlcyPortStatsFwdPkt    Counter64,
        custEgrSchedPlcyPortStatsFwdOct    Counter64
    }

custEgrSchedPlcyPortStatsPort OBJECT-TYPE
    SYNTAX          TmnxPortID
    MAX-ACCESS      not-accessible
    STATUS          current
    DESCRIPTION
        "The value of custEgrSchedPlcyPortStatsPort is used as 
         an index of the egress QoS scheduler of this customer multi service 
         site.
         When an MSS assignment is an aps/ccag/lag in 'link' mode, each
         member-port of the aps/ccag/lag has its own scheduler. This object
         refers to the TmnxPortID of these member-ports."
    ::= { custMultiSvcSiteEgrSchedPlcyPortStatsEntry 1}

custEgrSchedPlcyPortStatsFwdPkt OBJECT-TYPE
    SYNTAX          Counter64
    MAX-ACCESS      read-only
    STATUS          current
    DESCRIPTION
        "The value of custEgrSchedPlcyPortStatsFwdPkt indicates the
         number of forwarded packets, as determined by the customer
         multi service site egress scheduler policy."
    ::= { custMultiSvcSiteEgrSchedPlcyPortStatsEntry 2 }

custEgrSchedPlcyPortStatsFwdOct OBJECT-TYPE
    SYNTAX          Counter64
    MAX-ACCESS      read-only
    STATUS          current
    DESCRIPTION
        "The value of custEgrSchedPlcyPortStatsFwdOct indicates the
         number of forwarded octets, as determined by the customer
         multi service site egress scheduler policy."
    ::= { custMultiSvcSiteEgrSchedPlcyPortStatsEntry 3 }

-- --------------------------------------------------------
-- Customer Multi-Service Site Ingress Per-Policy Statistics 
-- Table with specific arbiter
-- --------------------------------------------------------
custMssIngQosArbitStatsTable OBJECT-TYPE
    SYNTAX          SEQUENCE OF CustMssIngQosArbitStatsEntry
    MAX-ACCESS      not-accessible
    STATUS          current
    DESCRIPTION
        "The custMssIngQosArbitStatsTable contains 
         ingress QoS arbiter statistics for the customer multi service site,
         organized by arbiter."
    ::= { tmnxCustObjs 15 }

custMssIngQosArbitStatsEntry OBJECT-TYPE
    SYNTAX          CustMssIngQosArbitStatsEntry
    MAX-ACCESS      not-accessible
    STATUS          current
    DESCRIPTION
        "Each entry represents the ingress statistics about a specific customer
         multi service site ingress arbiter." 
    INDEX           { custId, custMultSvcSiteName, custMssIngQosArbitName }
    ::= { custMssIngQosArbitStatsTable 1 }

CustMssIngQosArbitStatsEntry ::=
    SEQUENCE {
        custMssIngQosArbitName                 TNamedItem,
        custMssIngQosArbitStatsFwdPkts         Counter64,
        custMssIngQosArbitStatsFwdPktsLo       Counter32,
        custMssIngQosArbitStatsFwdPktsHi       Counter32,
        custMssIngQosArbitStatsFwdOcts         Counter64,
        custMssIngQosArbitStatsFwdOctsLo       Counter32,
        custMssIngQosArbitStatsFwdOctsHi       Counter32
    }

custMssIngQosArbitName OBJECT-TYPE
    SYNTAX          TNamedItem
    MAX-ACCESS      not-accessible
    STATUS          current
    DESCRIPTION
        "The value of custMssIngQosArbitName is used as an index of the ingress
         QoS arbiter of this customer multi service site."
    ::= { custMssIngQosArbitStatsEntry 1 }

custMssIngQosArbitStatsFwdPkts OBJECT-TYPE
    SYNTAX          Counter64
    MAX-ACCESS      read-only
    STATUS          current
    DESCRIPTION
        "The value of custMssIngQosArbitStatsFwdPkts indicates the number of 
         forwarded packets, as determined by the customer multi service site
         ingress arbiter policy."
    ::= { custMssIngQosArbitStatsEntry 2 }

custMssIngQosArbitStatsFwdPktsLo OBJECT-TYPE
    SYNTAX          Counter32
    MAX-ACCESS      read-only
    STATUS          current
    DESCRIPTION
        "The value of custMssIngQosArbitStatsFwdPktsLo indicates the lower 32
         bits of custMssIngQosArbitStatsFwdPkts."
    ::= { custMssIngQosArbitStatsEntry 3 }

custMssIngQosArbitStatsFwdPktsHi OBJECT-TYPE
    SYNTAX          Counter32
    MAX-ACCESS      read-only
    STATUS          current
    DESCRIPTION
        "The value of custMssIngQosArbitStatsFwdPktsHi indicates the higher 32
         bits of custMssIngQosArbitStatsFwdPkts."
    ::= { custMssIngQosArbitStatsEntry 4 }

custMssIngQosArbitStatsFwdOcts OBJECT-TYPE
    SYNTAX          Counter64
    MAX-ACCESS      read-only
    STATUS          current
    DESCRIPTION
        "The value of custMssIngQosArbitStatsFwdOcts indicates the number of 
         forwarded octets, as determined by the customer multi service site 
         ingress arbiter policy."
    ::= { custMssIngQosArbitStatsEntry 5 }

custMssIngQosArbitStatsFwdOctsLo OBJECT-TYPE
    SYNTAX          Counter32
    MAX-ACCESS      read-only
    STATUS          current
    DESCRIPTION
        "The value of custMssIngQosArbitStatsFwdOctsLo indicates the lower 32
         bits of custMssIngQosArbitStatsFwdOcts."
    ::= { custMssIngQosArbitStatsEntry 6 }

custMssIngQosArbitStatsFwdOctsHi OBJECT-TYPE
    SYNTAX          Counter32
    MAX-ACCESS      read-only
    STATUS          current
    DESCRIPTION
        "The value of custMssIngQosArbitStatsFwdOctsHi indicates the higher 32
         bits of custMssIngQosArbitStatsFwdOcts."
    ::= { custMssIngQosArbitStatsEntry 7 }

-- --------------------------------------------------------
-- Customer Multi-Service Site Egress Per-Policy Statistics 
-- Table with specific arbiter
-- --------------------------------------------------------
custMssEgrQosArbitStatsTable OBJECT-TYPE
    SYNTAX          SEQUENCE OF CustMssEgrQosArbitStatsEntry
    MAX-ACCESS      not-accessible
    STATUS          current
    DESCRIPTION
        "The custMssEgrQosArbitStatsTable contains 
         egress QoS arbiter statistics for the customer multi service site,
         organized by arbiter."
    ::= { tmnxCustObjs 16 }

custMssEgrQosArbitStatsEntry OBJECT-TYPE
    SYNTAX          CustMssEgrQosArbitStatsEntry
    MAX-ACCESS      not-accessible
    STATUS          current
    DESCRIPTION
        "Each entry represents the egress statistics about a specific customer
         multi service site egress arbiter." 
    INDEX           { custId, custMultSvcSiteName, custMssEgrQosArbitName }
    ::= { custMssEgrQosArbitStatsTable 1 }

CustMssEgrQosArbitStatsEntry ::=
    SEQUENCE {
        custMssEgrQosArbitName                 TNamedItem,
        custMssEgrQosArbitStatsFwdPkts         Counter64,
        custMssEgrQosArbitStatsFwdPktsLo       Counter32,
        custMssEgrQosArbitStatsFwdPktsHi       Counter32,
        custMssEgrQosArbitStatsFwdOcts         Counter64,
        custMssEgrQosArbitStatsFwdOctsLo       Counter32,
        custMssEgrQosArbitStatsFwdOctsHi       Counter32
    }

custMssEgrQosArbitName OBJECT-TYPE
    SYNTAX          TNamedItem
    MAX-ACCESS      not-accessible
    STATUS          current
    DESCRIPTION
        "The value of custMssEgrQosArbitName is used as 
         an index of the egress QoS arbiter of this customer multi service 
         site."
    ::= { custMssEgrQosArbitStatsEntry 1 }

custMssEgrQosArbitStatsFwdPkts OBJECT-TYPE
    SYNTAX          Counter64
    MAX-ACCESS      read-only
    STATUS          current
    DESCRIPTION
        "The value of custMssEgrQosArbitStatsFwdPkts indicates the number of 
         forwarded packets, as determined by the customer multi service site
         egress arbiter policy."
    ::= { custMssEgrQosArbitStatsEntry 2 }

custMssEgrQosArbitStatsFwdPktsLo OBJECT-TYPE
    SYNTAX          Counter32
    MAX-ACCESS      read-only
    STATUS          current
    DESCRIPTION
        "The value of custMssEgrQosArbitStatsFwdPktsLo indicates the lower 32
         bits of custMssEgrQosArbitStatsFwdPkts."
    ::= { custMssEgrQosArbitStatsEntry 3 }

custMssEgrQosArbitStatsFwdPktsHi OBJECT-TYPE
    SYNTAX          Counter32
    MAX-ACCESS      read-only
    STATUS          current
    DESCRIPTION
        "The value of custMssEgrQosArbitStatsFwdPktsHi indicates the higher 32
         bits of custMssEgrQosArbitStatsFwdPkts."
    ::= { custMssEgrQosArbitStatsEntry 4 }

custMssEgrQosArbitStatsFwdOcts OBJECT-TYPE
    SYNTAX          Counter64
    MAX-ACCESS      read-only
    STATUS          current
    DESCRIPTION
        "The value of custMssEgrQosArbitStatsFwdOcts indicates the number of 
         forwarded octets, as determined by the customer multi service site 
         egress arbiter policy."
    ::= { custMssEgrQosArbitStatsEntry 5 }

custMssEgrQosArbitStatsFwdOctsLo OBJECT-TYPE
    SYNTAX          Counter32
    MAX-ACCESS      read-only
    STATUS          current
    DESCRIPTION
        "The value of custMssEgrQosArbitStatsFwdOctsLo indicates the lower 32
         bits of custMssEgrQosArbitStatsFwdOcts."
    ::= { custMssEgrQosArbitStatsEntry 6 }

custMssEgrQosArbitStatsFwdOctsHi OBJECT-TYPE
    SYNTAX          Counter32
    MAX-ACCESS      read-only
    STATUS          current
    DESCRIPTION
        "The value of custMssEgrQosArbitStatsFwdOctsHi indicates the higher 32
         bits of custMssEgrQosArbitStatsFwdOcts."
    ::= { custMssEgrQosArbitStatsEntry 7 }

-- ---------------------------------------------------------
-- Customer Multi-Service Site Ingress Per-Policy Statistics 
-- Table with specific portId
-- ---------------------------------------------------------
custIngQosPortIdArbitStatsTable OBJECT-TYPE
    SYNTAX          SEQUENCE OF CustIngQosPortIdArbitStatsEntry
    MAX-ACCESS      not-accessible
    STATUS          current
    DESCRIPTION
        "The custIngQosPortIdArbitStatsTable contains ingress QoS arbiter
         statistics for the customer multi service site."
    ::= { tmnxCustObjs 17 }

custIngQosPortIdArbitStatsEntry OBJECT-TYPE
    SYNTAX          CustIngQosPortIdArbitStatsEntry
    MAX-ACCESS      not-accessible
    STATUS          current
    DESCRIPTION
        "Each entry represents the ingress statistics about a specific customer
         multi service site ingress arbiter."
    INDEX           { custId, custMultSvcSiteName,
                      custIngQosPortIdArbitName, custIngQosAssignmentPortId }
    ::= { custIngQosPortIdArbitStatsTable 1 }

CustIngQosPortIdArbitStatsEntry ::=
    SEQUENCE {
        custIngQosPortIdArbitName                     TNamedItem,
        custIngQosPortIdArbitFwdPkts                  Counter64,
        custIngQosPortIdArbitFwdPktsLo                Counter32,
        custIngQosPortIdArbitFwdPktsHi                Counter32,
        custIngQosPortIdArbitFwdOcts                  Counter64,
        custIngQosPortIdArbitFwdOctsLo                Counter32,
        custIngQosPortIdArbitFwdOctsHi                Counter32
    }

custIngQosPortIdArbitName OBJECT-TYPE
    SYNTAX          TNamedItem
    MAX-ACCESS      not-accessible
    STATUS          current
    DESCRIPTION
        "The value of custIngQosPortIdArbitName is used as an index
         of the ingress QoS arbiter of this customer multi service site."
    ::= { custIngQosPortIdArbitStatsEntry 1 }

custIngQosPortIdArbitFwdPkts OBJECT-TYPE
    SYNTAX          Counter64
    MAX-ACCESS      read-only
    STATUS          current
    DESCRIPTION
        "The value of custIngQosPortIdArbitFwdPkts indicates the
         number of forwarded packets, as determined by the customer
         multi service site ingress arbiter policy."
    ::= { custIngQosPortIdArbitStatsEntry 2 }

custIngQosPortIdArbitFwdPktsLo OBJECT-TYPE
    SYNTAX          Counter32
    MAX-ACCESS      read-only
    STATUS          current
    DESCRIPTION
        "The value of custIngQosPortIdArbitFwdPktsLo indicates the lower 32
         bits of custIngQosPortIdArbitFwdPkts."
    ::= { custIngQosPortIdArbitStatsEntry 3 }

custIngQosPortIdArbitFwdPktsHi OBJECT-TYPE
    SYNTAX          Counter32
    MAX-ACCESS      read-only
    STATUS          current
    DESCRIPTION
        "The value of custIngQosPortIdArbitFwdPktsHi indicates the higher 32
         bits of custIngQosPortIdArbitFwdPkts."
    ::= { custIngQosPortIdArbitStatsEntry 4 }

custIngQosPortIdArbitFwdOcts OBJECT-TYPE
    SYNTAX          Counter64
    MAX-ACCESS      read-only
    STATUS          current
    DESCRIPTION
        "The value of custIngQosPortIdArbitFwdOcts indicates the
         number of forwarded octets, as determined by the customer
         multi service site ingress arbiter policy."
    ::= { custIngQosPortIdArbitStatsEntry 5 }

custIngQosPortIdArbitFwdOctsLo OBJECT-TYPE
    SYNTAX          Counter32
    MAX-ACCESS      read-only
    STATUS          current
    DESCRIPTION
        "The value of custIngQosPortIdArbitFwdOctsLo indicates the lower 32
         bits of custIngQosPortIdArbitFwdOcts."
    ::= { custIngQosPortIdArbitStatsEntry 6 }

custIngQosPortIdArbitFwdOctsHi OBJECT-TYPE
    SYNTAX          Counter32
    MAX-ACCESS      read-only
    STATUS          current
    DESCRIPTION
        "The value of custIngQosPortIdArbitFwdOctsHi indicates the higher 32
         bits of custIngQosPortIdArbitFwdOcts."
    ::= { custIngQosPortIdArbitStatsEntry 7 }

-- --------------------------------------------------------
-- Customer Multi-Service Site Egress Per-Policy Statistics 
-- Table with specific portId
-- --------------------------------------------------------
custEgrQosPortIdArbitStatsTable OBJECT-TYPE
    SYNTAX          SEQUENCE OF CustEgrQosPortIdArbitStatsEntry
    MAX-ACCESS      not-accessible
    STATUS          current
    DESCRIPTION
        "The custEgrQosPortIdArbitStatsTable contains egress QoS arbiter
         statistics for the customer multi service site."
    ::= { tmnxCustObjs 18 }

custEgrQosPortIdArbitStatsEntry OBJECT-TYPE
    SYNTAX          CustEgrQosPortIdArbitStatsEntry
    MAX-ACCESS      not-accessible
    STATUS          current
    DESCRIPTION
        "Each row entry represents the egress statistics for a customer
         multi-service-site egress arbiter."
    INDEX           { custId, custMultSvcSiteName,
                      custEgrQosPortIdArbitName, custEgrQosAssignmentPortId }
    ::= { custEgrQosPortIdArbitStatsTable 1 }

CustEgrQosPortIdArbitStatsEntry ::=
    SEQUENCE {
        custEgrQosPortIdArbitName                     TNamedItem,
        custEgrQosPortIdArbitFwdPkts                  Counter64,
        custEgrQosPortIdArbitFwdPktsLo                Counter32,
        custEgrQosPortIdArbitFwdPktsHi                Counter32,
        custEgrQosPortIdArbitFwdOcts                  Counter64,
        custEgrQosPortIdArbitFwdOctsLo                Counter32,
        custEgrQosPortIdArbitFwdOctsHi                Counter32
    }

custEgrQosPortIdArbitName OBJECT-TYPE
    SYNTAX          TNamedItem
    MAX-ACCESS      not-accessible
    STATUS          current
    DESCRIPTION
        "The value of custEgrQosPortIdArbitName is used as an index
         of the egress QoS arbiter of this customer multi service site."
    ::= { custEgrQosPortIdArbitStatsEntry 1}

custEgrQosPortIdArbitFwdPkts OBJECT-TYPE
    SYNTAX          Counter64
    MAX-ACCESS      read-only
    STATUS          current
    DESCRIPTION
        "The value of custEgrQosPortIdArbitFwdPkts indicates the
         number of forwarded packets, as determined by the customer
         multi service site egress arbiter policy."
    ::= { custEgrQosPortIdArbitStatsEntry 2 }

custEgrQosPortIdArbitFwdPktsLo OBJECT-TYPE
    SYNTAX          Counter32
    MAX-ACCESS      read-only
    STATUS          current
    DESCRIPTION
        "The value of custEgrQosPortIdArbitFwdPktsLo indicates the lower 32
         bits of custEgrQosPortIdArbitFwdPkts."
    ::= { custEgrQosPortIdArbitStatsEntry 3 }

custEgrQosPortIdArbitFwdPktsHi OBJECT-TYPE
    SYNTAX          Counter32
    MAX-ACCESS      read-only
    STATUS          current
    DESCRIPTION
        "The value of custEgrQosPortIdArbitFwdPktsHi indicates the higher 32
         bits of custEgrQosPortIdArbitFwdPkts."
    ::= { custEgrQosPortIdArbitStatsEntry 4 }

custEgrQosPortIdArbitFwdOcts OBJECT-TYPE
    SYNTAX          Counter64
    MAX-ACCESS      read-only
    STATUS          current
    DESCRIPTION
        "The value of custEgrQosPortIdArbitFwdOcts indicates the
         number of forwarded octets, as determined by the customer
         multi service site egress arbiter policy."
    ::= { custEgrQosPortIdArbitStatsEntry 5 }

custEgrQosPortIdArbitFwdOctsLo OBJECT-TYPE
    SYNTAX          Counter32
    MAX-ACCESS      read-only
    STATUS          current
    DESCRIPTION
        "The value of custEgrQosPortIdArbitFwdOctsLo indicates the lower 32
         bits of custEgrQosPortIdArbitFwdOcts."
    ::= { custEgrQosPortIdArbitStatsEntry 6 }

custEgrQosPortIdArbitFwdOctsHi OBJECT-TYPE
    SYNTAX          Counter32
    MAX-ACCESS      read-only
    STATUS          current
    DESCRIPTION
        "The value of custEgrQosPortIdArbitFwdOctsHi indicates the higher 32
         bits of custEgrQosPortIdArbitFwdOcts."
    ::= { custEgrQosPortIdArbitStatsEntry 7 }

-- ------------------------------------
-- Customer traps
-- ------------------------------------
custCreated NOTIFICATION-TYPE
    OBJECTS {
        custId
    }
    STATUS          obsolete
    DESCRIPTION     "The trap custCreated is sent when a new row is created
                     in the custInfoTable. The object is obsoleted and replaced 
                     with tmnxConfigModify notification."
    ::= { custTraps 1 }

custDeleted NOTIFICATION-TYPE
    OBJECTS {
        custId
    }
    STATUS          obsolete
    DESCRIPTION     "The trap custDeleted is sent when an existing row is
                     deleted from the custInfoTable. The object is obsoleted and 
                     replaced with tmnxConfigModify notification."
    ::= { custTraps 2 }

custMultSvcSiteCreated NOTIFICATION-TYPE
    OBJECTS {
        custId,
        custMultSvcSiteName
    }
    STATUS          obsolete
    DESCRIPTION     "The trap custMultSvcSiteCreated is sent when a new row is
                     created in the custMultiServiceSiteTable.  The object is 
                     obsoleted and replaced with tmnxConfigModify notification."
    ::= { custTraps 3 }

custMultSvcSiteDeleted NOTIFICATION-TYPE
    OBJECTS {
        custId,
        custMultSvcSiteName
    }
    STATUS          obsolete
    DESCRIPTION     "The trap custMultSvcSiteDeleted is sent when an existing
                     row is deleted from the custMultiServiceSiteTable. The 
                     object is obsoleted and replaced with tmnxConfigModify 
                     notification."
    ::= { custTraps 4 }

-- --------------------------------------------------------------------
-- Service related objects
-- --------------------------------------------------------------------
-- ------------------------------
-- tmnxSvcObjs group
-- ------------------------------
svcNumEntries OBJECT-TYPE
    SYNTAX          Integer32
    MAX-ACCESS      read-only
    STATUS          current
    DESCRIPTION     "The current number of services configured on this node."
    ::= { tmnxSvcObjs 1 }

-- --------------------------------
-- Base Service Table
-- --------------------------------
svcBaseInfoTable OBJECT-TYPE
    SYNTAX          SEQUENCE OF SvcBaseInfoEntry
    MAX-ACCESS      not-accessible
    STATUS          current
    DESCRIPTION     "A table that contains basic service information."
    ::= { tmnxSvcObjs 2 }

svcBaseInfoEntry OBJECT-TYPE
    SYNTAX          SvcBaseInfoEntry
    MAX-ACCESS      not-accessible
    STATUS          current
    DESCRIPTION     "Basic information about a specific service."
    INDEX           { svcId }
    ::= { svcBaseInfoTable 1 }

SvcBaseInfoEntry ::=
    SEQUENCE {
        svcId                 TmnxServId,
        svcRowStatus          RowStatus,
        svcType               ServType,
        svcCustId             TmnxCustId,
        svcIpRouting          TmnxEnabledDisabled,
        svcDescription        ServObjDesc,
        svcMtu                INTEGER,
        svcAdminStatus        ServiceAdminStatus,
        svcOperStatus         ServiceOperStatus,
        svcNumSaps            Integer32,
        svcNumSdps            Integer32,
        svcLastMgmtChange     TimeStamp,
        svcDefMeshVcId        Unsigned32,
        svcVpnId              VpnId,
        svcVRouterId          TmnxVRtrIDOrZero,
        svcAutoBind           INTEGER,
        svcLastStatusChange   TimeStamp,
        svcVllType            INTEGER,
        svcMgmtVpls           TruthValue,
        svcRadiusDiscovery    TruthValue,
        svcRadiusUserNameType INTEGER,
        svcRadiusUserName     DisplayString,
        svcVcSwitching        TruthValue,
        svcRadiusPEDiscPolicy TNamedItemOrEmpty,
        svcRadiusDiscoveryShutdown ServiceAdminStatus,
        svcVplsType           INTEGER,
        svcNumMcStandbySaps   Integer32,
        svcName               TLNamedItemOrEmpty,
        svcInterASMvpn        TruthValue,
        svcHashLabel          TruthValue,
        svcTmplUsed           TNamedItemOrEmpty,
        svcCtrlSvcId          TmnxServId,
        svcCreationOrigin     TmnxCreateOrigin,
        svcNumMHStandbySaps   Integer32,
        svcVsdDomainName      TNamedItemOrEmpty,
        svcIsTestSvc          TruthValue,
        svcTlsModeEtree       TruthValue,
        svcNumEvpnMHStandbySaps  Integer32
    }

svcId OBJECT-TYPE
    SYNTAX          TmnxServId
    MAX-ACCESS      read-only
    STATUS          current
    DESCRIPTION     "The value of the object svcId specifies the
                     Service identifier. This value should be unique within the
                     service domain."
    ::= { svcBaseInfoEntry 1 }

svcRowStatus OBJECT-TYPE
    SYNTAX          RowStatus
    MAX-ACCESS      read-create
    STATUS          current
    DESCRIPTION     "This value of the object  svcRowStatus specifies the
                     status of this row.

                     To delete an entry from this table, the corresponding
                     service must be administratively down, have no SAP's
                     defined on it, and have no SDP bindings.

                     For svcType 'vprn', the service can be associated
                     with a routing instance by specifying svcVRouterId
                     during the creation of the service.

                     The value of the object svcVplsType specifies the VPLS
                     service type. The value of this object must be specified
                     when the row is created and cannot be changed while the
                     svcRowStatus is 'active'."

    ::= { svcBaseInfoEntry 2 }

svcType OBJECT-TYPE
    SYNTAX          ServType
    MAX-ACCESS      read-create
    STATUS          current
    DESCRIPTION     "The value of the object svcType specifies the service
                     type: e.g. epipe, tls, etc. The value of this object
                     must be specified when the row is created and cannot be
                     changed while the row status is 'active'."
    ::= { svcBaseInfoEntry 3 }

svcCustId OBJECT-TYPE
    SYNTAX          TmnxCustId
    MAX-ACCESS      read-create
    STATUS          current
    DESCRIPTION     "The value of the object svcCustId specifies the ID of the
                     customer who owns this service.
                     The value of this object must be specified when the row is
                     created and cannot be changed while the row status is
                     'active'."
    ::= { svcBaseInfoEntry 4 }

svcIpRouting OBJECT-TYPE
    SYNTAX          TmnxEnabledDisabled 
    MAX-ACCESS      read-create
    STATUS          current
    DESCRIPTION     "The value of the object svcIpRouting specifies, for a
                     'tls' service, whether IP routing is enabled.
                     For 'epipe', 'apipe', 'fpipe', 'ipipe'
                     and 'cpipe' services, this object cannot be set and has
                     the value 'disabled', whereas for 'vprn' and 'ies'
                     services the value is 'enabled' and cannot be set either.
                     For 'tls' services the value of this object must be
                     specified when the row is created and cannot be changed
                     while the row status is 'active'."
    ::= { svcBaseInfoEntry 5 }

svcDescription OBJECT-TYPE
    SYNTAX          ServObjDesc
    MAX-ACCESS      read-create
    STATUS          current
    DESCRIPTION     "The value of the object svcDescription specifiers an
                     optional, generic information about this service."
    DEFVAL          { "" }
    ::= { svcBaseInfoEntry 6 }

svcMtu OBJECT-TYPE
    SYNTAX          INTEGER (0..9212)
    MAX-ACCESS      read-create
    STATUS          current
    DESCRIPTION     "The value of the object svcMtu specifies the largest frame
                     size (in octets) that this service can handle.

                     Setting svcMtu to a value of zero (0), causes the agent
                     to recalculate the default MTU size.

                     The default value of this object depends on the service
                     type:
                     1514 octets for epipe and tls, 1508 for apipe
                     and fpipe, and 1500 octets for vprn, ipipe and ies, 1514
                     octets for cpipe."
    ::= { svcBaseInfoEntry 7 }

svcAdminStatus OBJECT-TYPE
    SYNTAX          ServiceAdminStatus
    MAX-ACCESS      read-create
    STATUS          current
    DESCRIPTION     "The value of the object svcAdminStatus specifies the
                     desired state of this service."
    DEFVAL          { down }
    ::= { svcBaseInfoEntry 8 }

svcOperStatus OBJECT-TYPE
    SYNTAX          ServiceOperStatus
    MAX-ACCESS      read-only
    STATUS          current
    DESCRIPTION     "The value of the object svcOperStatus indicates the
                     operating state of this service. The requirements for a
                     service to be operationally up depend on the service type:

                     epipe, apipe, fpipe, ipipe and cpipe services are
                     'up' when the service is administratively up and either
                     both SAP's or a SAP and a spoke SDP Bind are operationally
                     up.

                     tls services are 'up' when the service is
                     administratively up and either at least one SAP or
                     spoke SDP Bind or one mesh SDP Bind is operationally up.

                     tls service that has vxlan configuration is 'up' when the
                     service is administratively up.

                     ies services are 'up' when the service is
                     administratively up and at least one interface is
                     operationally up.
                     
                     vprn services are 'up' when the service is
                     administratively up however routing functionality is
                     available only when TIMETRA-VRTR-MIB::vRtrOperState is
                     'up'."
    ::= { svcBaseInfoEntry 9 }

svcNumSaps OBJECT-TYPE
    SYNTAX          Integer32
    MAX-ACCESS      read-only
    STATUS          current
    DESCRIPTION     "The value of the object svcNumSaps indicates the number of
                     SAPs defined on this service."
    ::= { svcBaseInfoEntry 10 }

svcNumSdps OBJECT-TYPE
    SYNTAX          Integer32
    MAX-ACCESS      read-only
    STATUS          current
    DESCRIPTION     "The value of the object svcNumSdps indicates the number of
                     SDPs bound to this service."
    ::= { svcBaseInfoEntry 11 }

svcLastMgmtChange OBJECT-TYPE
    SYNTAX          TimeStamp
    MAX-ACCESS      read-only
    STATUS          current
    DESCRIPTION     "The value of of the object svcLastMgmtChange indicates
                     the value of sysUpTime at the time of the most recent
                     management-initiated change to this service."
    ::= { svcBaseInfoEntry 12 }

svcDefMeshVcId OBJECT-TYPE
    SYNTAX          Unsigned32
    MAX-ACCESS      read-create
    STATUS          current
    DESCRIPTION     "The value of the object svcDefMeshVcId specifies, only in
                     services that accept mesh SDP bindings, the VC ID portion
                     of the sdpBindId index of each mesh SDP binding defined in
                     the service. The default value of this object is equal to
                     the service ID."
    ::= { svcBaseInfoEntry 13 }

svcVpnId OBJECT-TYPE
    SYNTAX          VpnId
    MAX-ACCESS      read-create
    STATUS          current
    DESCRIPTION     "The value of the object  svcVpnId specifies the VPN ID
                     assigned to this service.  The value of this object can
                     be specified only when the row is created. If the value is
                     not specified, it defaults to the service ID."
    DEFVAL          { 0 }
    ::= { svcBaseInfoEntry 14 }

svcVRouterId OBJECT-TYPE
    SYNTAX          TmnxVRtrIDOrZero
    MAX-ACCESS      read-create
    STATUS          current
    DESCRIPTION     "The value of the object svcVRouterId specifies, for a IES
                     or VPRN service the associated virtual router instance
                     where its interfaces are defined.

                     This object has a special significance for the VPRN
                     service as it can be used to associate the service to a
                     specific virtual router instance.

                     If no routing instance is specified or a value of zero (0)
                     is specified, the agent will assign the vRtrID index value
                     that would have been returned by the vRtrNextVRtrID object
                     in the TIMETRA-VRTR-MIB. The agent supports an SNMP SET
                     operation to the svcVRouterId object only during
                     row creation."
    DEFVAL { 0 }
    ::= { svcBaseInfoEntry 15 }

svcAutoBind OBJECT-TYPE
    SYNTAX          INTEGER {
                        none     (1),
                        gre      (2),
                        ldp      (3),
                        rsvp-te  (4),
                        mpls     (5),
                        mpls-gre (6)
                    }
    MAX-ACCESS      read-create
    STATUS          obsolete
    DESCRIPTION     "The value of the object svcAutoBind specifies, for a VPRN
                     service, the type of lookup to be used by the routing
                     instance if no SDP to the destination exists.
                     
                     The svcAutoBind object has been obsoleted and replaced with
                     objects in
                     svcTlsBgpEvpnAutoBindTnlTable or
                     svcVprnBgpAutoBindTable."
    DEFVAL          { none }
    ::= { svcBaseInfoEntry 16 }

svcLastStatusChange OBJECT-TYPE
    SYNTAX          TimeStamp
    MAX-ACCESS      read-only
    STATUS          current
    DESCRIPTION     "The value of the object svcLastStatusChange indicates the
                     value of sysUpTime at the time of the most recent
                     operating status change to his service."
    ::= { svcBaseInfoEntry 17 }

svcVllType OBJECT-TYPE
    SYNTAX          INTEGER {
                        undef     (1),
                        atmSdu    (6),
                        atmCell   (7),
                        atmVcc    (8),
                        atmVpc    (9),
                        frDlci    (10),
                        satopE1   (12),
                        satopT1   (13),
                        satopE3   (14),
                        satopT3   (15),
                        cesopsn   (16),
                        cesopsnCas(17)
                    }
    MAX-ACCESS      read-create
    STATUS          current
    DESCRIPTION     "The value of the object svcVllType specifies, for a apipe,
                     fpipe or cpipe service, the type of pseudo-wire to be
                     signalled for the service.  The default for this object
                     depends on the service type:
                     'atmSdu' for apipes, 'frDlci' for fpipes, satopE1 for
                     cpipes, and 'undef' for all other service types."
    ::= { svcBaseInfoEntry 18 }

svcMgmtVpls OBJECT-TYPE
    SYNTAX          TruthValue
    MAX-ACCESS      read-create
    STATUS          current
    DESCRIPTION    "The value of the object svcMgmtVpls specifies, only if
                    svcType = 'tls' whether or not the service is a management
                    vpls.
                    If set to false the service is acting as a regular VPLS
                    service. If set to true, the service is  acting  as  a
                    management  VPLS  service. This implies that RSTP will
                    always be enabled, and that the  conclusions of this RSTP
                    can be associated to different (regular) VPLSs.
                    The value of this object cannot be changed after creation."
    DEFVAL          { false }
    ::= { svcBaseInfoEntry 19 }

svcRadiusDiscovery OBJECT-TYPE
    SYNTAX           TruthValue
    MAX-ACCESS       read-create
    STATUS           current
    DESCRIPTION
        "The value of the object svcRadiusDiscovery specifies whether RADIUS
         auto-discovery is enabled on this service."
    DEFVAL          { false }
    ::= { svcBaseInfoEntry 20 }


svcRadiusUserNameType OBJECT-TYPE
    SYNTAX           INTEGER {
                     none                 (0),
                     vpn-id               (1),
                     router-distinguisher (2)
                     }
    MAX-ACCESS       read-create
    STATUS           obsolete
    DESCRIPTION
        "The value of the object svcRadiusUserNameType specifies whether RADIUS
         user name is vpn-id or router-distinguisher.  By default, the 
         value of this object is 'none'.  
         
         svcRadiusUserNameType and svcRadiusUserName, which indicates the 
         RADIUS username, must be set together in the same SNMP request 
         PDU if svcRadiusUserNameType is vpn-id or router-distinguisher or
         else the set request will fail with an inconsistentValue error."
    DEFVAL          { none }
    ::= { svcBaseInfoEntry 21 }

svcRadiusUserName OBJECT-TYPE
    SYNTAX           DisplayString (SIZE (0..64))
    MAX-ACCESS       read-create
    STATUS           obsolete
    DESCRIPTION
        "The value of the object svcRadiusUserName specifies the  RADIUS
         user name.  svcRadiusUserNameType specifies the type of the 
         username and has to be set along with svcRadiusUserName when 
         svcRadiusUserName can either be a vpn-id or a router-distinguisher."    
    DEFVAL          { "" }
    ::= { svcBaseInfoEntry 22 }

svcVcSwitching OBJECT-TYPE
    SYNTAX           TruthValue
    MAX-ACCESS       read-create
    STATUS           current
    DESCRIPTION
        "The value of the object svcVcSwitching specifies if the PW 
         switching signalling is used for the Spokes configured under the 
         service.  
         This object can only be specified when the row is created."
    DEFVAL     { false }
    ::= { svcBaseInfoEntry 23 }

svcRadiusPEDiscPolicy OBJECT-TYPE
    SYNTAX           TNamedItemOrEmpty
    MAX-ACCESS       read-create
    STATUS           obsolete
    DESCRIPTION
        "The value of the object svcRadiusPEDiscPolicy specifies the 
         RADIUS PE Discovery Policy name. "    
    DEFVAL     { "" }
    ::= { svcBaseInfoEntry 24 }
    
svcRadiusDiscoveryShutdown OBJECT-TYPE
    SYNTAX     ServiceAdminStatus
    MAX-ACCESS read-create
    STATUS     obsolete
    DESCRIPTION
      "The value of svcRadiusDiscoveryShutdown specifies the desired 
       administrative state for the RADIUS auto-discovery server. When 
       the server is 'down' the operational state of the server is
       disabled.  

       By default, state of the RADIUS auto-discovery server is 'down'."
    DEFVAL { down }
    ::= { svcBaseInfoEntry 25 }   

svcVplsType OBJECT-TYPE
    SYNTAX          INTEGER {
                        none  (1),
                        bVpls (2),
                        iVpls (3),
                        rVpls(10)
                    }
    MAX-ACCESS      read-create
    STATUS          current
    DESCRIPTION     "Backbone VPLS ('bVpls') refers to the B-Component instance
                     of the Provider Backbone Bridging (PBB/IEEE 802.1ah)
                     feature. It represents the Multi-point tunneling component
                     that multiplexes multiple Customer VPNs (ISIDs) together.
                     It is similar to a regular VPLS instance that operates
                     on the Backbone MAC addresses.

                     ISID VPLS ('iVpls') or I-VPLS refers to the I-Component
                     instance of the Provider Backbone Bridging (PBB/IEEE
                     802.1ah) feature. It identifies the specific VPN entity
                     associated to a customer Multipoint (ELAN) service. It is
                     similar to a regular VPLS instance that operates on the
                     Customer MAC addresses.
                     The value of the object svcVplsType specifies the VPLS
                     service type. The value of this object must be specified
                     when the row is created and cannot be changed while the
                     svcRowStatus is 'active'."
    DEFVAL     { none }
    ::= { svcBaseInfoEntry 26 }

svcNumMcStandbySaps OBJECT-TYPE
    SYNTAX          Integer32
    MAX-ACCESS      read-only
    STATUS          current
    DESCRIPTION     "The value of the object svcNumMcStandbySaps indicates the
                     number of SAPs defined on this service on a port which is
                     in multi-chassis standby mode."
    ::= { svcBaseInfoEntry 27 }

svcName OBJECT-TYPE
    SYNTAX          TLNamedItemOrEmpty
    MAX-ACCESS      read-create
    STATUS          current
    DESCRIPTION     "The value of the svcName specifies the name of the service.
                     This value should be unique within the service domain."
    DEFVAL { ''H }
    ::= { svcBaseInfoEntry 29 }   
    
svcInterASMvpn OBJECT-TYPE
    SYNTAX          TruthValue
    MAX-ACCESS      read-create
    STATUS          current
    DESCRIPTION   
        "The value of the object svcInterASMvpn specifies if the 
         configured VPRN service is used for inter-AS MVPN or not.

         If the value of the object is set to 'true', the VPRN 
         service is used for inter-AS MVPN only. If the value of
         the object is set to 'false', the VPRN service is not used
         for inter-AS MVPN." 
    DEFVAL          { false }
    ::= { svcBaseInfoEntry 30 }

svcHashLabel        OBJECT-TYPE
    SYNTAX          TruthValue
    MAX-ACCESS      read-create
    STATUS          current
    DESCRIPTION     "The value of svcHashLabel specifies whether the use of 
                     hash-label is enabled or not on this service."
    DEFVAL          { false }
    ::= { svcBaseInfoEntry 31 } 
 
svcTmplUsed OBJECT-TYPE
    SYNTAX          TNamedItemOrEmpty
    MAX-ACCESS      read-only
    STATUS          current
    DESCRIPTION     "The value of the svcTmplUsed indicates the name of the
                     service-template used to create this service.
                     
                     A value of empty string indicates that this service was
                     not created using a service-template."
    ::= { svcBaseInfoEntry 32 }   
    
svcCtrlSvcId OBJECT-TYPE
    SYNTAX          TmnxServId
    MAX-ACCESS      read-only
    STATUS          current
    DESCRIPTION     "The value of the object svcCtrlSvcId indicates the
                     Service identifier of the service controlling this service.

                     A value of '0' indicates that this service is not
                     controlled by another service."
    ::= { svcBaseInfoEntry 33 }

svcCreationOrigin   OBJECT-TYPE
    SYNTAX          TmnxCreateOrigin
    MAX-ACCESS      read-only
    STATUS          current
    DESCRIPTION     "The value of svcCreationOrigin indicates the protocol or
                     mechanism which created this service."
    ::= { svcBaseInfoEntry 34 }
svcNumMHStandbySaps OBJECT-TYPE
    SYNTAX          Integer32
    MAX-ACCESS      read-only
    STATUS          current
    DESCRIPTION     "The value of the object svcNumMHStandbySaps indicates the
                     number of SAPs defined on this service which are multi-home
                     standby SAPs."
    ::= { svcBaseInfoEntry 37 }

svcVsdDomainName OBJECT-TYPE
    SYNTAX          TNamedItemOrEmpty
    MAX-ACCESS      read-only
    STATUS          current
    DESCRIPTION     "The value of the object svcVsdDomainName indicates
                     the VSD Domain that is associated with this service."
    ::= { svcBaseInfoEntry 39 }

svcIsTestSvc OBJECT-TYPE
    SYNTAX          TruthValue
    MAX-ACCESS      read-create
    STATUS          current
    DESCRIPTION     "The value of the object svcIsTestSvc specifies whether
                     this service is a test service.
                     
                     An 'inconsistentValue' error is returned if this object
                     is changed to a different value after service is already
                     created."
    DEFVAL { false}
    ::= { svcBaseInfoEntry 40 }

svcTlsModeEtree OBJECT-TYPE
    SYNTAX          TruthValue
    MAX-ACCESS      read-create
    STATUS          current
    DESCRIPTION     "The value of the object svcTlsModeEtree specifies whether
                     e-tree mode is enabled on this service.

                     An 'inconsistentValue' error is returned if this object
                     is changed to a different value after service is already
                     created."
    DEFVAL { false }
    ::= { svcBaseInfoEntry 41 }

svcNumEvpnMHStandbySaps OBJECT-TYPE
    SYNTAX          Integer32
    MAX-ACCESS      read-only
    STATUS          current
    DESCRIPTION     "The value of the object svcNumEvpnMHStandbySaps
                     indicates the number of SAPs defined on this service
                     which are evpn multi-homed standby SAPs."
    ::= { svcBaseInfoEntry 42 }

-- ------------------------------------
-- TLS Service Table
-- ------------------------------------
svcTlsInfoTable OBJECT-TYPE
    SYNTAX          SEQUENCE OF SvcTlsInfoEntry
    MAX-ACCESS      not-accessible
    STATUS          current
    DESCRIPTION     "A table that contains TLS service information."
    ::= { tmnxSvcObjs 3 }

svcTlsInfoEntry OBJECT-TYPE
    SYNTAX          SvcTlsInfoEntry
    MAX-ACCESS      not-accessible
    STATUS          current
    DESCRIPTION     "TLS specific information about a service."
    INDEX           { svcId }
    ::= { svcTlsInfoTable 1 }

SvcTlsInfoEntry ::=
    SEQUENCE {
        svcTlsMacLearning                   TmnxEnabledDisabled,
        svcTlsDiscardUnknownDest            TmnxEnabledDisabled,
        svcTlsFdbTableSize                  Integer32,
        svcTlsFdbNumEntries                 Integer32,
        svcTlsFdbNumStaticEntries           Integer32,
        svcTlsFdbLocalAgeTime               Integer32,
        svcTlsFdbRemoteAgeTime              Integer32,
        svcTlsStpAdminStatus                TmnxEnabledDisabled,
        svcTlsStpPriority                   Integer32,
        svcTlsStpBridgeAddress              MacAddress,
        svcTlsStpTimeSinceTopologyChange    TimeTicks,
        svcTlsStpTopologyChanges            Integer32,
        svcTlsStpDesignatedRoot             BridgeId,
        svcTlsStpRootCost                   Integer32,
        svcTlsStpRootPort                   Integer32,
        svcTlsStpMaxAge                     Integer32,
        svcTlsStpHelloTime                  Integer32,
        svcTlsStpHoldTime                   Integer32,
        svcTlsStpForwardDelay               Integer32,
        svcTlsStpBridgeMaxAge               Integer32,
        svcTlsStpBridgeHelloTime            Integer32,
        svcTlsStpBridgeForwardDelay         Integer32,
        svcTlsStpOperStatus                 INTEGER,
        svcTlsStpVirtualRootBridgeStatus    INTEGER,
        svcTlsMacAgeing                     TmnxEnabledDisabled,
        svcTlsStpTopologyChangeActive       TruthValue,
        svcTlsFdbTableFullHighWatermark     Integer32,
        svcTlsFdbTableFullLowWatermark      Integer32,
        svcTlsVpnId                         VpnId,
        svcTlsCustId                        TmnxCustId,
        svcTlsStpVersion                    INTEGER,
        svcTlsStpHoldCount                  Integer32,
        svcTlsStpPrimaryBridge              BridgeId,
        svcTlsStpBridgeInstanceId           Integer32,
        svcTlsStpVcpOperProtocol            StpProtocol,
        svcTlsMacMoveMaxRate                Unsigned32,
        svcTlsMacMoveRetryTimeout           Unsigned32,
        svcTlsMacMoveAdminStatus            TmnxEnabledDisabled,
        svcTlsMacRelearnOnly                TruthValue,
        svcTlsMfibTableSize                 Integer32,
        svcTlsMfibTableFullHighWatermark    Integer32,
        svcTlsMfibTableFullLowWatermark     Integer32,
        svcTlsMacFlushOnFail                TmnxEnabledDisabled,
        svcTlsStpRegionName                 DisplayString,
        svcTlsStpRegionRevision             Integer32,
        svcTlsStpBridgeMaxHops              Integer32,
        svcTlsStpCistRegionalRoot           BridgeId,
        svcTlsStpCistIntRootCost            Integer32,
        svcTlsStpCistRemainingHopCount      Integer32,
        svcTlsStpCistRegionalRootPort       Integer32,
        svcTlsFdbNumLearnedEntries          Integer32,
        svcTlsFdbNumOamEntries              Integer32,
        svcTlsFdbNumDhcpEntries             Integer32,
        svcTlsFdbNumHostEntries             Integer32,
        svcTlsShcvAction                    TmnxSubShcvAction,                
        svcTlsShcvSrcIp                     IpAddress,
        svcTlsShcvSrcMac                    MacAddress,
        svcTlsShcvInterval                  TmnxSubShcvInterval,
        svcTlsPriPortsCumulativeFactor      Unsigned32,
        svcTlsSecPortsCumulativeFactor      Unsigned32,
        svcTlsL2ptTermEnabled               TruthValue,
        svcTlsPropagateMacFlush             TruthValue,
        svcTlsMrpAdminStatus                TmnxEnabledDisabled,
        svcTlsMrpMaxAttributes              Unsigned32,
        svcTlsMrpAttributeCount             Unsigned32,
        svcTlsMrpFailedRegisterCount        Unsigned32,
        svcTlsMcPathMgmtPlcyName            TNamedItem,
        svcTlsMrpFloodTime                  Unsigned32,
        svcTlsMrpAttrTblHighWatermark       Integer32,
        svcTlsMrpAttrTblLowWatermark        Integer32,
        svcTlsMacMoveNumRetries             Unsigned32,
        svcTlsMacSubNetLen                  Integer32,
        svcTlsSendFlushOnBVplsFail          TruthValue,
        svcTlsPropMacFlushFromBVpls         TruthValue,
        svcTlsMacNotifInterval              Unsigned32, 
        svcTlsMacNotifCount                 Unsigned32,
        svcTlsMacNotifAdminState            TmnxEnabledDisabled,
        svcTlsPerSvcHashing                 TmnxEnabledDisabled,
        svcTlsAllowIpIfBinding              TruthValue,
        svcTlsShcvRetryTimeout              TmnxSubShcvRetryTimeout,
        svcTlsShcvRetryCount                TmnxSubShcvRetryCount,
        svcTlsTempFloodTime                 Integer32,
        svcTlsTempFloodActive               TruthValue,
        svcTlsTempFloodChangeCount          Integer32,
        svcTlsShcvPolicyIpv4             TNamedItemOrEmpty
     }

svcTlsMacLearning OBJECT-TYPE
    SYNTAX          TmnxEnabledDisabled
    MAX-ACCESS      read-write
    STATUS          current
    DESCRIPTION     "The value of the object svcTlsMacLearning specifies
                     whether the MAC learning process is enabled in this TLS."
    DEFVAL          { enabled }
    ::= { svcTlsInfoEntry 1 }

svcTlsDiscardUnknownDest OBJECT-TYPE
    SYNTAX          TmnxEnabledDisabled
    MAX-ACCESS      read-write
    STATUS          current
    DESCRIPTION     "The value of the object svcTlsDiscardUnknownDest
                     specifies whether frames received with an unknown
                     destination MAC are discarded in this TLS."
    DEFVAL          { disabled }
    ::= { svcTlsInfoEntry 2 }

svcTlsFdbTableSize OBJECT-TYPE
    SYNTAX          Integer32 (1..511999)
    MAX-ACCESS      read-write
    STATUS          current
    DESCRIPTION     "The value of the object svcTlsFdbTableSize specifies the
                     maximum number of learned and static entries allowed in
                     the FDB of this service. 

                     The maximum value of svcTlsFdbTableSize is '511999', when
                     the the value of TIMETRA-CHASSIS-MIB::tmnxChassisOperMode
                     is 'd'.

                     The maximum value of svcTlsFdbTableSize is '196607', when
                     the the value of TIMETRA-CHASSIS-MIB::tmnxChassisOperMode
                     is 'c'.

                     In other cases, the maximum value of svcTlsFdbTableSize is
                     '131071'."
    DEFVAL          { 250 }
    ::= { svcTlsInfoEntry 3 }

svcTlsFdbNumEntries OBJECT-TYPE
    SYNTAX          Integer32
    MAX-ACCESS      read-only
    STATUS          current
    DESCRIPTION     "The value of the object svcTlsFdbNumEntries indicates the
                     current number of entries in the FDB of this service."
    ::= { svcTlsInfoEntry 4 }

svcTlsFdbNumStaticEntries OBJECT-TYPE
    SYNTAX          Integer32
    MAX-ACCESS      read-only
    STATUS          current
    DESCRIPTION     "The value of the object svcTlsFdbNumStaticEntries
                     indicates the current number of static entries in the FDB
                     of this service."
    ::= { svcTlsInfoEntry 5 }

svcTlsFdbLocalAgeTime OBJECT-TYPE
    SYNTAX          Integer32 (60..86400)
    MAX-ACCESS      read-write
    STATUS          current
    DESCRIPTION     "The value of the object svcTlsFdbLocalAgeTime specifies
                     the number of seconds used to age out TLS FDB entries
                     learned on local SAPs."
    DEFVAL          { 300 }
    ::= { svcTlsInfoEntry 6 }

svcTlsFdbRemoteAgeTime OBJECT-TYPE
    SYNTAX          Integer32 (60..86400)
    MAX-ACCESS      read-write
    STATUS          current
    DESCRIPTION     "The value of the object svcTlsFdbRemoteAgeTime specifies
                     the number of seconds used to age out TLS FDB entries
                     learned on an SDP. These entries correspond to MAC
                     addresses learned on remote SAPs."
    DEFVAL          { 900 }
    ::= { svcTlsInfoEntry 7 }

svcTlsStpAdminStatus OBJECT-TYPE
    SYNTAX          TmnxEnabledDisabled
    MAX-ACCESS      read-write
    STATUS          current
    DESCRIPTION     "The value of the object svcTlsStpAdminStatus specifies the
                     administrative state of the Spanning Tree Protocol
                     instance associated with this service."
    DEFVAL          { disabled }
    ::= { svcTlsInfoEntry 8 }

svcTlsStpPriority OBJECT-TYPE
    SYNTAX          Integer32 (0..65535)
    MAX-ACCESS      read-write
    STATUS          current
    DESCRIPTION     "The value of the object  svcTlsStpPriority specifies
                     the priority of the Spanning Tree Protocol instance
                     associated with this service.
                     It is used as the highest 4 bits of the Bridge ID
                     included in the Configuration BPDU's generated by
                     this bridge.
                     The svcTlsStpPriority can only take-on values which
                     multiples of 4096 (4k). If a value is specified which
                     is not a multiple of 4K, then this value will be
                     replaced by the closest multiple of 4K which is lower
                     then the value entered."
    DEFVAL          { 32768 }
    ::= { svcTlsInfoEntry 9 }

svcTlsStpBridgeAddress OBJECT-TYPE
    SYNTAX          MacAddress
    MAX-ACCESS      read-only
    STATUS          current
    DESCRIPTION     "The value of the  object svcTlsStpBridgeAddress indicates
                     the MAC address used to identify this bridge in the
                     network. It is used as the last six octets of the
                     Bridge ID included in the Configuration BPDU's generated
                     by this bridge. The most significant 38 bits of the bridge
                     address are taken from the base MAC address of the
                     device, while the least significant 10 bits are
                     based on the corresponding TLS instance ID."
    ::= { svcTlsInfoEntry 10 }

svcTlsStpTimeSinceTopologyChange OBJECT-TYPE
    SYNTAX          TimeTicks
    MAX-ACCESS      read-only
    STATUS          current
    DESCRIPTION     "The value of the object svcTlsStpTimeSinceTopologyChange
                     indicates the time (in hundredths of a second) since the
                     last time a topology change was detected by the Spanning
                     Tree Protocol instance associated with this service."
    ::= { svcTlsInfoEntry 11 }

svcTlsStpTopologyChanges OBJECT-TYPE
    SYNTAX          Integer32
    MAX-ACCESS      read-only
    STATUS          current
    DESCRIPTION     "The value of the object svcTlsStpTopologyChanges indicates
                     the total number of topology changes detected by the
                     Spanning Tree Protocol instance associated with this
                     service since the management entity was last reset or
                     initialized."
    ::= { svcTlsInfoEntry 12 }

svcTlsStpDesignatedRoot OBJECT-TYPE
    SYNTAX          BridgeId
    MAX-ACCESS      read-only
    STATUS          current
    DESCRIPTION     "The value of the object svcTlsStpDesignatedRoot indicates
                     the bridge identifier of the root of the spanning tree as
                     determined by the Spanning Tree Protocol instance
                     associated with this service. This value is used as the
                     Root Identifier parameter in all Configuration BPDUs
                     originated by this node."
    ::= { svcTlsInfoEntry 13 }

svcTlsStpRootCost OBJECT-TYPE
    SYNTAX          Integer32
    MAX-ACCESS      read-only
    STATUS          current
    DESCRIPTION     "The value of the object svcTlsStpRootCost indicates the
                     cost of the path to the root bridge as seen from this
                     bridge."
    ::= { svcTlsInfoEntry 14 }

svcTlsStpRootPort OBJECT-TYPE
    SYNTAX          Integer32
    MAX-ACCESS      read-only
    STATUS          current
    DESCRIPTION     "The value of the object svcTlsStpRootPort indicates the
                     port number of the port which offers the lowest cost path
                     from this bridge to the root bridge."
    ::= { svcTlsInfoEntry 15 }

svcTlsStpMaxAge OBJECT-TYPE
    SYNTAX          Integer32
    MAX-ACCESS      read-only
    STATUS          current
    DESCRIPTION     "The value of the object svcTlsStpMaxAge indicates the
                     maximum age of Spanning Tree Protocol information learned
                     from the network on any port before it is discarded. This
                     is the actual value that this bridge is currently using."
    ::= { svcTlsInfoEntry 16 }

svcTlsStpHelloTime OBJECT-TYPE
    SYNTAX          Integer32
    MAX-ACCESS      read-only
    STATUS          current
    DESCRIPTION     "The value of the object svcTlsStpHelloTime indicates the
                     amount of time between the transmission of Configuration
                     BPDUs. This is the actual value that this bridge is
                     currently using."
    ::= { svcTlsInfoEntry 17 }

svcTlsStpHoldTime OBJECT-TYPE
    SYNTAX          Integer32
    MAX-ACCESS      read-only
    STATUS          obsolete
    DESCRIPTION     "The value of the object svcTlsStpHoldTime indicates the
                     interval length during which no more than two
                     Configuration BPDUs shall be transmitted by this bridge.
                     This object is no longer used. It is replaced by the
                     object svcTlsStpHoldCount.
                     This object was made obsolete in the 3.0 release."
    ::= { svcTlsInfoEntry 18 }

svcTlsStpForwardDelay OBJECT-TYPE
    SYNTAX          Integer32
    MAX-ACCESS      read-only
    STATUS          current
    DESCRIPTION     "The value of the object svcTlsStpForwardDelay indicates
                     how fast a port changes its state when moving towards the
                     Forwarding state. The value determines how long the port
                     stays in each of the Listening and Learning states, which
                     precede the Forwarding state. This value is also used to
                     age all dynamic entries in the Forwarding Database when a
                     topology change has been detected and is underway. This is
                     the actual value that this bridge is currently using."
    ::= { svcTlsInfoEntry 19 }

svcTlsStpBridgeMaxAge OBJECT-TYPE
    SYNTAX          Integer32 (6..40)
    MAX-ACCESS      read-write
    STATUS          current
    DESCRIPTION     "The value of the object svcTlsStpBridgeMaxAge specifies
                     the value that all bridges should use for 'MaxAge' when this
                     bridge is acting as the root bridge."
    ::= { svcTlsInfoEntry 20 }

svcTlsStpBridgeHelloTime OBJECT-TYPE
    SYNTAX          Integer32 (1..10)
    MAX-ACCESS      read-write
    STATUS          current
    DESCRIPTION     "The value of the object svcTlsStpBridgeHelloTime specifies
                     the value that all bridges should use for 'HelloTime' when
                     this bridge is acting as the root bridge."
    ::= { svcTlsInfoEntry 21 }

svcTlsStpBridgeForwardDelay OBJECT-TYPE
    SYNTAX          Integer32 (4..30)
    MAX-ACCESS      read-write
    STATUS          current
    DESCRIPTION     "The value of the object svcTlsStpBridgeForwardDelay
                     specifies the value that all bridges should use for
                     'ForwardDelay' when this bridge is acting as the root
                     bridge."
    ::= { svcTlsInfoEntry 22 }

svcTlsStpOperStatus OBJECT-TYPE
    SYNTAX          INTEGER {
                        up   (1),
                        down (2)
                    }
    MAX-ACCESS      read-only
    STATUS          current
    DESCRIPTION     "The value of the object  svcTlsStpOperStatus indicates the
                     operating status of the Spanning Tree Protocol instance
                     associated with this service."
    ::= { svcTlsInfoEntry 30 }

svcTlsStpVirtualRootBridgeStatus OBJECT-TYPE
    SYNTAX          INTEGER {
                        up   (1),
                        down (2)
                    }
    MAX-ACCESS      read-only
    STATUS          current
    DESCRIPTION     "The value of the object  svcTlsStpVirtualRootBridgeStatus
                     indicates the operating status of the  Virtual Root Bridge
                     of the Spanning Tree Protocol instance associated with
                     this service. The status of the Virtual Root Bridge is
                    'up' when there is connectivity to the core: i.e. one or
                     more SDP's in this service are operationally up."
    ::= { svcTlsInfoEntry 31 }

svcTlsMacAgeing OBJECT-TYPE
    SYNTAX          TmnxEnabledDisabled
    MAX-ACCESS      read-write
    STATUS          current
    DESCRIPTION     "The value of the object svcTlsMacAgeing specifies whether
                     the MAC aging process is enabled in this TLS."
    DEFVAL          { enabled }
    ::= { svcTlsInfoEntry 32 }

svcTlsStpTopologyChangeActive OBJECT-TYPE
    SYNTAX          TruthValue
    MAX-ACCESS      read-only
    STATUS          current
    DESCRIPTION     "The value of the object svcTlsStpTopologyChangeActive
                     indicates, when set to 'true', that a topology change is
                     currently in progress."
    ::= { svcTlsInfoEntry 33 }

svcTlsFdbTableFullHighWatermark OBJECT-TYPE
    SYNTAX          Integer32 (0..100)
    MAX-ACCESS      read-write
    STATUS          current
    DESCRIPTION     "The value of the object svcTlsFdbTableFullHighWatermark
                     specifies the utilization of the FDB table of this TLS
                     service at which a table full alarm will be raised
                     by the agent."
    DEFVAL          { 95 }
    ::= { svcTlsInfoEntry 34 }

svcTlsFdbTableFullLowWatermark OBJECT-TYPE
    SYNTAX          Integer32 (0..100)
    MAX-ACCESS      read-write
    STATUS          current
    DESCRIPTION     "The value of the object svcTlsFdbTableFullLowWatermark
                     specifies the utilization of the FDB table of this TLS
                     service at which a table full alarm will be cleared
                     by the agent."
    DEFVAL          { 90 }
    ::= { svcTlsInfoEntry 35 }

svcTlsVpnId OBJECT-TYPE
    SYNTAX          VpnId
    MAX-ACCESS      read-only
    STATUS          current
    DESCRIPTION     "The value of the object svcTlsVpnId indicates the VPN ID
                     of the associated TLS service."
    ::= { svcTlsInfoEntry 36 }

svcTlsCustId OBJECT-TYPE
    SYNTAX          TmnxCustId
    MAX-ACCESS      read-only
    STATUS          current
    DESCRIPTION     "The vakue of the object svcTlsCustId indicates the
                     Customer ID of the associated TLS service."
    ::= { svcTlsInfoEntry 37 }

svcTlsStpVersion OBJECT-TYPE
    SYNTAX          INTEGER {
                        rstp         (2),
                        compDot1w    (3),
                        dot1w        (4),
                        mstp         (5),
                        pmstp        (6)
                    }
    MAX-ACCESS      read-write
    STATUS          current
    DESCRIPTION     "The value of the object svcTlsStpVersion specifies the
                     version of Spanning Tree Protocol the bridge is currently
                     running.

                     The value 'rstp' corresponds to  the Rapid Spanning
                     Tree Protocol specified in IEEE 802.1D/D4-2003.

                     The value 'compDot1w' corresponds to the mode where the
                     Rapid Spanning Tree is backward compatible with IEEE
                     802.1w.

                     The value 'dot1w' corresponds to  the Rapid Spanning
                     Tree Protocol fully conformant to IEEE 802.1w.

                     The value 'mstp' corresponds to the Multiple Spanning
                     Tree Protocol specified in IEEE 802.1Q-REV/D3.0-04/2005.
                     
                     The value 'pmstp' corresponds to Provider MSTP protocol
                     compliant with IEEE-802.1ad-2005.

                     New values may be defined as future versions of the
                     protocol become available."
    DEFVAL          { rstp }
    ::= { svcTlsInfoEntry 38 }

svcTlsStpHoldCount OBJECT-TYPE
    SYNTAX          Integer32 (1..20)
    MAX-ACCESS      read-write
    STATUS          current
    DESCRIPTION     "The value of the object svcTlsStpHoldCount specifies the
                     maximum number of BPDUs that are transmitted in any
                     'HelloTime' interval.
                     The value used by the bridge to limit the maximum
                     transmission rate of BPDUs."
    REFERENCE
                    "IEEE 802.1w clause 17.16.6"
    DEFVAL          { 6 }
    ::= { svcTlsInfoEntry 39 }

svcTlsStpPrimaryBridge OBJECT-TYPE
    SYNTAX          BridgeId
    MAX-ACCESS      read-only
    STATUS          current
    DESCRIPTION     "The value of the object svcTlsStpPrimaryBridge indicates
                     the BridgeId of the bridge that acts as the primary bridge,
                     being the gateway from the core mesh towards the root
                     bridge."
    ::= { svcTlsInfoEntry 40 }

svcTlsStpBridgeInstanceId OBJECT-TYPE
    SYNTAX          Integer32 (0 ..4095)
    MAX-ACCESS      read-only
    STATUS          current
    DESCRIPTION     "The value of the object svcTlsStpBridgeInstanceId
                     indicates a 12 bit value chosen by the the system. It is
                     part of the STP bridge Id, which consists of 8 octets:
                     - 4 highest bits of octet 1:
                         the bridge priority (ref svcTlsStpPriority)
                     - 12 bits (4 lowest bits of octet 1 + 8 bits of octet 2):
                         bridge instance Id (this object!).
                     - 6 octets: bridge MAC addess
                         ref svcTlsStpBridgeAddress
                     The value is set to 0 if svcTlsStpOperStatus is not 'up'."
    ::= { svcTlsInfoEntry 41 }

svcTlsStpVcpOperProtocol OBJECT-TYPE
    SYNTAX          StpProtocol
    MAX-ACCESS      read-only
    STATUS          current
    DESCRIPTION     "The value of the object svcTlsStpVcpOperProtocol indicates
                     whether stp, rstp or mstp is running on this VCP.
                     If the protocol is not enabled on this VCP, the value
                     notApplicable is returned."
    ::= { svcTlsInfoEntry 42 }

svcTlsMacMoveMaxRate OBJECT-TYPE
    SYNTAX          Unsigned32 (1..10)
    MAX-ACCESS      read-write
    STATUS          current
    DESCRIPTION     "The value of the object svcTlsMacMoveMaxRate specifies the
                     maximum rate at which MAC's can be re-learned in this TLS
                     service, before the SAP where the moving MAC was last seen
                     is automatically disabled in order to protect the system
                     against undetected loops or duplicate MAC's.
                     The rate is computed as the maximum number of re-learns
                     allowed in a 5 second interval: e.g. the default rate
                     of 2 re-learns per second corresponds to 10 re-learns
                     in a 5 second period."
    DEFVAL          { 2 }
    ::= { svcTlsInfoEntry 43 }

svcTlsMacMoveRetryTimeout OBJECT-TYPE
    SYNTAX          Unsigned32 (0..600)
    MAX-ACCESS      read-write
    STATUS          current
    DESCRIPTION     "The value of the object  svcTlsMacMoveRetryTimeout
                     specifies the time in seconds to wait before a SAP that
                     has been disabled after exceeding the maximum re-learn
                     rate is re-enabled.

                     A value of zero indicates that the SAP will not be
                     automatically re-enabled after being disabled. If after
                     the SAP is re-enabled it is disabled again, the effective
                     retry timeout is doubled in order to avoid thrashing.
                     
                     An inconsistentValue error is returned if the value of this
                     object is set to less than fie times the value of 
                     svcTlsSecPortsCumulativeFactor."
    DEFVAL { 10 }
    ::= { svcTlsInfoEntry 44 }

svcTlsMacMoveAdminStatus OBJECT-TYPE
    SYNTAX          TmnxEnabledDisabled
    MAX-ACCESS      read-write
    STATUS          current
    DESCRIPTION     "The value of the object svcTlsMacMoveAdminStatus
                     specifies the administrative state of the
                     MAC movement feature associated with this service."
    DEFVAL          { disabled }
    ::= { svcTlsInfoEntry 45 }

svcTlsMacRelearnOnly OBJECT-TYPE
    SYNTAX          TruthValue
    MAX-ACCESS      read-only
    STATUS          current
    DESCRIPTION     "The value of the object svcTlsMacRelearnOnly indicates
                     when set to 'true' that either the FDB table of this TLS
                     service is full, or that the maximum system-wide number of
                     MAC's supported by the agent has been reached, and thus
                     MAC learning is temporary disabled, and only MAC re-learns
                     can take place."
    ::= { svcTlsInfoEntry 46 }

svcTlsMfibTableSize OBJECT-TYPE
    SYNTAX          Integer32 (0..40959)
    MAX-ACCESS      read-write
    STATUS          current
    DESCRIPTION     "The value of the object  svcTlsMfibTableSize specifies the
                     maximum number of entries allowed in the MFIB table of
                     this service. If the value is 0, then there is no limit.

                     Allowable maximum value for this object will depend on the 
                     platform and the chassis-mode."
    DEFVAL          { 0 }
    ::= { svcTlsInfoEntry 47 }

svcTlsMfibTableFullHighWatermark OBJECT-TYPE
    SYNTAX          Integer32 (0..100)
    MAX-ACCESS      read-write
    STATUS          current
    DESCRIPTION     "The value of the object svcTlsMfibTableFullHighWatermark
                     specifies the utilization of the MFIB table of this TLS
                     service at which a table full alarm will be raised by the
                     agent."
    DEFVAL          { 95 }
    ::= { svcTlsInfoEntry 48 }

svcTlsMfibTableFullLowWatermark OBJECT-TYPE
    SYNTAX          Integer32 (0..100)
    MAX-ACCESS      read-write
    STATUS          current
    DESCRIPTION     "The value of the object svcTlsMfibTableFullLowWatermark
                     specifies utilization of the MFIB table of this TLS
                     service at which a table full alarm will be cleared by the
                     agent."
    DEFVAL          { 90 }
    ::= { svcTlsInfoEntry 49 }

svcTlsMacFlushOnFail OBJECT-TYPE
    SYNTAX          TmnxEnabledDisabled
    MAX-ACCESS      read-write
    STATUS          current
    DESCRIPTION     "The value of the object svcTlsMacFlushOnFail specifies
                     whether a special mac-flush is sent when a
                     port or sap becomes operational down."
    DEFVAL          { disabled }
    ::= { svcTlsInfoEntry 50 }

svcTlsStpRegionName OBJECT-TYPE
    SYNTAX          DisplayString (SIZE (0..32))
    MAX-ACCESS      read-write
    STATUS          current
    DESCRIPTION     "The value of the object svcTlsStpRegionName specifies
                     the MSTP region name. Together with region revision and
                     VLAN-to-instance assignment it defines the MSTP region."
    DEFVAL          { "" }
    ::= { svcTlsInfoEntry 51 }

svcTlsStpRegionRevision OBJECT-TYPE
    SYNTAX          Integer32 (0..65535)
    MAX-ACCESS      read-write
    STATUS          current
    DESCRIPTION     "The value of the object svcTlsStpRegionRevision specifies
                     the MSTP region revision number. Together with region
                     name and VLAN-to-instance assignment it defines the MSTP
                     region."
    DEFVAL          { 0 }
    ::= { svcTlsInfoEntry 52 }

svcTlsStpBridgeMaxHops OBJECT-TYPE
    SYNTAX          Integer32 (1..40)
    MAX-ACCESS      read-write
    STATUS          current
    DESCRIPTION     "The value of the object svcTlsStpBridgeMaxHops specifies
                     the maximum number of hops (known as 'MaxHops' in 802.1Q)."
    DEFVAL          { 20 }
    ::= { svcTlsInfoEntry 53 }

svcTlsStpCistRegionalRoot OBJECT-TYPE
    SYNTAX          BridgeId
    MAX-ACCESS      read-only
    STATUS          current
    DESCRIPTION     "The value of the object svcTlsStpCistRegionalRoot
                     indicates the bridge identifier of the regional root of
                     the CIST spanning tree as determined by the Spanning Tree
                     Protocol instance associated with this service. This value
                     is used as the CIST Regional Root Identifier parameter in
                     all MSTP BPDUs originated by this node."
    ::= { svcTlsInfoEntry 54 }

svcTlsStpCistIntRootCost OBJECT-TYPE
    SYNTAX          Integer32
    MAX-ACCESS      read-only
    STATUS          current
    DESCRIPTION     "The value of the object svcTlsStpCistIntRootCost indicates
                     the cost of the path to the CIST regional root bridge
                     as seen from this bridge."
    ::= { svcTlsInfoEntry 55 }

svcTlsStpCistRemainingHopCount OBJECT-TYPE
    SYNTAX          Integer32
    MAX-ACCESS      read-only
    STATUS          current
    DESCRIPTION     "The value of the object svcTlsStpCistRemainingHopCount
                     specifies the remaining number of hops."
    ::= { svcTlsInfoEntry 56 }

svcTlsStpCistRegionalRootPort OBJECT-TYPE
    SYNTAX          Integer32
    MAX-ACCESS      read-only
    STATUS          current
    DESCRIPTION     "The value of the object svcTlsStpCistRegionalRootPort
                     indicates the port number of the port which offers the
                     lowest cost path from this bridge to the regional root
                     bridge."
    ::= { svcTlsInfoEntry 57 }

svcTlsFdbNumLearnedEntries OBJECT-TYPE
    SYNTAX          Integer32
    MAX-ACCESS      read-only
    STATUS          current
    DESCRIPTION     "The value of the object svcTlsFdbNumLearnedEntries
                     indicates the current number of learned entries in the FDB
                     of this service."
    ::= { svcTlsInfoEntry 58 }

svcTlsFdbNumOamEntries OBJECT-TYPE
    SYNTAX          Integer32
    MAX-ACCESS      read-only
    STATUS          current
    DESCRIPTION     "The value of the object svcTlsFdbNumOamEntries
                     indicates the current number of OAM entries in the FDB
                     of this service."
    ::= { svcTlsInfoEntry 59 }

svcTlsFdbNumDhcpEntries OBJECT-TYPE
    SYNTAX          Integer32
    MAX-ACCESS      read-only
    STATUS          current
    DESCRIPTION     "The value of the object svcTlsFdbNumDhcpEntries
                     indicates the current number of dhcp-learned entries in the
                     FDB of this service."
    ::= { svcTlsInfoEntry 60 }

svcTlsFdbNumHostEntries OBJECT-TYPE
    SYNTAX          Integer32
    MAX-ACCESS      read-only
    STATUS          current
    DESCRIPTION     "The value of the object svcTlsFdbNumHostEntries
                     indicates the current number of host-learned entries in the
                     FDB of this service."
    ::= { svcTlsInfoEntry 61 }

svcTlsShcvAction OBJECT-TYPE
    SYNTAX          TmnxSubShcvAction
    MAX-ACCESS      read-write
    STATUS          current
    DESCRIPTION     "The value of the object svcTlsShcvAction
                     indicates whether any action should be triggered when
                     the connectivity check fails."
    DEFVAL          { alarm }
    ::= { svcTlsInfoEntry 62 }


svcTlsShcvSrcIp OBJECT-TYPE
    SYNTAX          IpAddress
    MAX-ACCESS      read-write
    STATUS          current
    DESCRIPTION     "The value of the object svcTlsShcvSrcIp
                     specifies the source IP address used when doing the
                     connectivity check. The value 0.0.0.0 indicates that
                     no host IP address is specified."
    ::= { svcTlsInfoEntry 63 }

svcTlsShcvSrcMac OBJECT-TYPE
    SYNTAX          MacAddress
    MAX-ACCESS      read-write
    STATUS          current
    DESCRIPTION     "The value of the object svcTlsShcvSrcMac
                     specifies the MAC address used when doing the connectivity
                     check. The value 0:0:0:0:0:0 indicates that no host MAC
                     address is specified."
    ::= { svcTlsInfoEntry 64 }

svcTlsShcvInterval OBJECT-TYPE
    SYNTAX          TmnxSubShcvInterval
    UNITS           "minutes"
    MAX-ACCESS      read-write
    STATUS          current
    DESCRIPTION     "The value of the object svcTlsShcvInterval specifies
                     the interval in minutes between connectivity checks.
                     Zero means no connectivity checking."
    DEFVAL          { 0 }
    ::= { svcTlsInfoEntry 65 }

svcTlsPriPortsCumulativeFactor OBJECT-TYPE
    SYNTAX          Unsigned32 (3..10)
    MAX-ACCESS      read-write
    STATUS          current
    DESCRIPTION     "The value of the object svcTlsPriPortsCumulativeFactor
                     specifies a factor for the primary ports defining how
                     many MAC-relearn periods should be used to measure the
                     MAC-relearn rate, svcTlsMacMoveMaxRate. This rate must
                     be exceeded during consecutive periods before the
                     corresponding ports (SAP and/or spoke-SDP) are blocked by
                     the MAC-move feature.

                     An inconsistentValue error is returned if an attempt is
                     made to set the value of svcTlsPriPortsCumulativeFactor to
                     a value lower than or equal to
                     svcTlsSecPortsCumulativeFactor."
    DEFVAL          { 3 }
    ::= { svcTlsInfoEntry 66 }

svcTlsSecPortsCumulativeFactor OBJECT-TYPE
    SYNTAX          Unsigned32 (2..9)
    MAX-ACCESS      read-write
    STATUS          current
    DESCRIPTION     "The value of the object svcTlsSecPortsCumulativeFactor
                     specifies a factor for the secondary ports defining how
                     many MAC-relearn periods should be used to measure the
                     MAC-relearn rate, svcTlsMacMoveMaxRate. This rate must
                     be exceeded during consecutive periods before the
                     corresponding ports (SAP and/or spoke-SDP) are blocked by
                     the MAC-move feature.

                     An inconsistentValue error is returned if an attempt is
                     made to set the value of svcTlsSecPortsCumulativeFactor to
                     a value greater than or equal to
                     svcTlsPriPortsCumulativeFactor."
    DEFVAL          { 2 }
    ::= { svcTlsInfoEntry 67 }

svcTlsL2ptTermEnabled OBJECT-TYPE
    SYNTAX          TruthValue
    MAX-ACCESS      read-only
    STATUS          current
    DESCRIPTION     "The value of the object svcTlsL2ptTermEnabled 
                     indicates if 'L2PT-termination' and/or 'Bpdu-translation' 
                     is in use in this service by at least one SAP or 
                     spoke SDP Bind. If the value is 'true', it means that
                     at least one of 'L2PT-termination' or 'Bpdu-translation'
                     is enabled.

                     When enabled it is not possible to enable
                     stp on this service." 
    ::= { svcTlsInfoEntry 68 }

svcTlsPropagateMacFlush OBJECT-TYPE
    SYNTAX          TruthValue
    MAX-ACCESS      read-write
    STATUS          current
    DESCRIPTION     "The value of svcTlsPropagateMacFlush specifies whether
                     'MAC flush' messages received from the given LDP are
                     propagated to all spoke-SDPs and mesh-SDPs within the
                     context of this VPLS service. The propagation will follow
                     the 'split-horizon' principle and any data-path blocking in
                     order to avoid the looping of these messages.

                     The value of 'true' enables the propagation."
    DEFVAL         { false }
    ::= { svcTlsInfoEntry 69 }

svcTlsMrpAdminStatus OBJECT-TYPE
    SYNTAX          TmnxEnabledDisabled
    MAX-ACCESS      read-write
    STATUS          current
    DESCRIPTION     "The value of the object svcTlsMrpAdminStatus specifies
                     whether the Multiple Registration Protocol (MRP) is
                     enabled in this TLS."
    DEFVAL          { disabled }
    ::= { svcTlsInfoEntry 70 }

svcTlsMrpMaxAttributes OBJECT-TYPE
    SYNTAX          Unsigned32 (1..8192)
    MAX-ACCESS      read-write
    STATUS          current
    DESCRIPTION     "The value of the object svcTlsMrpMaxAttributes indicates
                     maximum number of MMRP attributes supported in this TLS.

                     In most cases the default value is 2048 MRP attributes.
                     For some platform and chassis types, especially single slot
                     chassises, the default value will be lower due to resource
                     constraints.

                     The default value is set to 8192 when
                     svcTlsExtMmrpEndStationOnly is set to 'true'.

                     An inconsistentValue error is returned if an attempt is
                     made to set this object to a value the platform cannot
                     support."
    ::= { svcTlsInfoEntry 71 }

svcTlsMrpAttributeCount OBJECT-TYPE
    SYNTAX          Unsigned32
    MAX-ACCESS      read-only
    STATUS          current
    DESCRIPTION     "The value of the object svcTlsMrpAttributeCount indicates
                     the number of MMRP attributes currently associated to the
                     TLS by either being registered or declared.
                     
                     Note that an 'iVpls' service (with svcVplsType set to
                     'iVpls') holds a declaration in the 'bVpls' service (with
                     svcVplsType set to 'bVpls') regardless of the state of the
                     'iVpls' service, although that declaration will not be
                     propagated in the 'bVpls' service unless the svcOperStatus
                     of 'iVpls' service is 'up'."
    ::= { svcTlsInfoEntry 72 }

svcTlsMrpFailedRegisterCount OBJECT-TYPE
    SYNTAX          Unsigned32
    MAX-ACCESS      read-only
    STATUS          current
    DESCRIPTION     "The value of the object svcTlsMrpFailedRegisterCount
                     indicates number of failed MRP attribute registrations in
                     this TLS."
    ::= { svcTlsInfoEntry 73 }

svcTlsMcPathMgmtPlcyName OBJECT-TYPE
    SYNTAX          TNamedItem
    MAX-ACCESS      read-write
    STATUS          current
    DESCRIPTION     "The value of svcTlsMcPathMgmtPlcyName specifies the 
                     multicast policy name configured on this service."
    DEFVAL          { "default" }
    ::= { svcTlsInfoEntry 74 }

svcTlsMrpFloodTime OBJECT-TYPE
    SYNTAX          Unsigned32 (0|3..600)
    UNITS           "seconds"
    MAX-ACCESS      read-write
    STATUS          current
    DESCRIPTION     "The value of the object svcTlsMrpFloodTime specifies
                     the amount of time in seconds after a status change in the
                     TLS during which traffic is flooded.  Once that time
                     expires, traffic will be delivered according to the MRP
                     registrations which exist in the TLS.

                     The value of 0 indicates that no flooding will occur on
                     state changes in the TLS."
    DEFVAL          { 0 }
    ::= { svcTlsInfoEntry 75 }

svcTlsMrpAttrTblHighWatermark OBJECT-TYPE
    SYNTAX          Integer32 (0..100)
    MAX-ACCESS      read-write
    STATUS          current
    DESCRIPTION     "The value of the object svcTlsMrpAttrTblHighWatermark
                     specifies the utilization of the MRP attribute table of
                     this TLS service at which a table full alarm will be raised
                     by the agent."
    DEFVAL          { 95 }
    ::= { svcTlsInfoEntry 76 }

svcTlsMrpAttrTblLowWatermark OBJECT-TYPE
    SYNTAX          Integer32 (0..100)
    MAX-ACCESS      read-write
    STATUS          current
    DESCRIPTION     "The value of the object svcTlsMrpAttrTblLowWatermark
                     specifies utilization of the MRP attribute table of this
                     TLS service at which a table full alarm will be cleared by
                     the agent."
    DEFVAL          { 90 }
    ::= { svcTlsInfoEntry 77 }

svcTlsMacMoveNumRetries OBJECT-TYPE
    SYNTAX          Unsigned32 (0..255)
    MAX-ACCESS      read-write
    STATUS          current
    DESCRIPTION     "The value of the object  svcTlsMacMoveNumRetries
                     specifies the number of times retries are performed for
                     reenabling the SAP/SDP.

                     A value of zero indicates unlimited number of retries."
                     
    DEFVAL { 3 }
    ::= { svcTlsInfoEntry 78 }

svcTlsMacSubNetLen OBJECT-TYPE
    SYNTAX          Integer32 (24..48)
    MAX-ACCESS      read-write
    STATUS          current
    DESCRIPTION     "The value of the object svcTlsMacSubNetLen specifies
                     the number of bits to be considered when performing
                     MAC-Learning or MAC-Switching."
    DEFVAL { 48 }
    ::= { svcTlsInfoEntry 79 }


svcTlsSendFlushOnBVplsFail OBJECT-TYPE
    SYNTAX          TruthValue
    MAX-ACCESS      read-write
    STATUS          current
    DESCRIPTION     "The value of the object svcTlsSendFlushOnBVplsFail
                     specifies whether a special 'MAC flush' is sent in the
                     local 'iVpls' following a failure of SAP/Endpoint/SDP in
                     the 'bVpls'."
    DEFVAL { false }
    ::= { svcTlsInfoEntry 80 }

svcTlsPropMacFlushFromBVpls OBJECT-TYPE
    SYNTAX          TruthValue
    MAX-ACCESS      read-write
    STATUS          current
    DESCRIPTION     "The value of the object svcTlsPropMacFlushFromBVpls
                     specifies whether to propagate any 'MAC flush' from 'bVpls'
                     into the local 'iVpls'."
    DEFVAL { false }
    ::= { svcTlsInfoEntry 81 }

svcTlsMacNotifInterval OBJECT-TYPE
    SYNTAX          Unsigned32 (0..100)
    UNITS           "deci-seconds"
    MAX-ACCESS      read-write
    STATUS          current
    DESCRIPTION     "The value of svcTlsMacNotifInterval specifies time-interval
                     between subsequent MAC notification messages.  The default 
                     value for this object indicates that the value is inherited 
                     from svcMacNotifInterval."
    REFERENCE       "ITU-T Y.1731 specification"
    DEFVAL { 0 }
    ::= { svcTlsInfoEntry 82 }

svcTlsMacNotifCount OBJECT-TYPE
    SYNTAX          Unsigned32 (0..10)
    MAX-ACCESS      read-write
    STATUS          current
    DESCRIPTION     "The value of svcTlsMacNotifCount specifies number of
                     MAC notification messages to be sent. The default value 
                     for this object indicates that the value is inherited from 
                     svcMacNotifCount."
    REFERENCE       "ITU-T Y.1731 specification"
    DEFVAL { 0 }
    ::= { svcTlsInfoEntry 83 }

svcTlsMacNotifAdminState OBJECT-TYPE
    SYNTAX          TmnxEnabledDisabled
    MAX-ACCESS      read-write
    STATUS          current
    DESCRIPTION     "The value of svcTlsMacNotifAdminState specifies whether
                     MAC notification messages should be sent."
    DEFVAL { disabled }
    ::= { svcTlsInfoEntry 84 }

svcTlsPerSvcHashing  OBJECT-TYPE
    SYNTAX          TmnxEnabledDisabled
    MAX-ACCESS      read-write
    STATUS          current
    DESCRIPTION     "The value of svcTlsPerSvcHashing specifies service-level
                     hashing for Ethernet services."
    DEFVAL { disabled }
    ::= { svcTlsInfoEntry 85 }

svcTlsAllowIpIfBinding  OBJECT-TYPE
    SYNTAX          TruthValue
    MAX-ACCESS      read-write
    STATUS          current
    DESCRIPTION     "The value of the object svcTlsAllowIpIfBinding indicates,
                     whether to allow IP interface binding on this service."
    DEFVAL { false }
    ::= { svcTlsInfoEntry 86 }

svcTlsShcvRetryTimeout OBJECT-TYPE
    SYNTAX          TmnxSubShcvRetryTimeout
    UNITS           "seconds"
    MAX-ACCESS      read-write
    STATUS          current
    DESCRIPTION     "The value of the object svcTlsShcvRetryTimeout specifies
                     the timeout in seconds before a connectivity check
                     retransmission."
    DEFVAL          { 10 }
    ::= { svcTlsInfoEntry 87 }

svcTlsShcvRetryCount OBJECT-TYPE
    SYNTAX          TmnxSubShcvRetryCount
    MAX-ACCESS      read-write
    STATUS          current
    DESCRIPTION     "The value of the object svcTlsShcvRetryCount specifies
                     the number of connectivity check retransmissions.
                     
                     Setting the value to n specifies that, for any given host,
                     at most (n+1) probes are done each interval, 
                     and (n+1) missed replies are considered as a connectivity 
                     failure."
    DEFVAL          { 2 }
    ::= { svcTlsInfoEntry 88 }

svcTlsTempFloodTime OBJECT-TYPE
    SYNTAX          Integer32 (-1|3..600)
    UNITS           "seconds"
    MAX-ACCESS      read-write
    STATUS          current
    DESCRIPTION     "The value of the object svcTlsTempFloodTime specifies
                     duration of time traffic will be flooded on a TLS status
                     change in this TLS.

                     Value of '-1' disables this flooding behavior."
    DEFVAL          { -1 }
    ::= { svcTlsInfoEntry 89 }

svcTlsTempFloodActive OBJECT-TYPE
    SYNTAX          TruthValue
    MAX-ACCESS      read-only
    STATUS          current
    DESCRIPTION     "The value of the object svcTlsTempFloodActive indicates
                     whether temporary flooding is currently active in this TLS."
    ::= { svcTlsInfoEntry 90 }

svcTlsTempFloodChangeCount OBJECT-TYPE
    SYNTAX          Integer32 
    MAX-ACCESS      read-only
    STATUS          current
    DESCRIPTION     "The value of the object svcTlsTempFloodChangeCount
                     specifies the number of times temporary flooding status
                     changed from inactive to active in this TLS.
                     
                     The value of this object resets to zero when temporary
                     flooding is disabled."
    ::= { svcTlsInfoEntry 91 }

svcTlsShcvPolicyIpv4 OBJECT-TYPE
    SYNTAX      TNamedItemOrEmpty
    MAX-ACCESS  read-write
    STATUS      current
    DESCRIPTION
        "The value of svcTlsShcvPolicyIpv4 specifies the Subscriber Host Connectivity Verification (SHCV)
         policy for IPv4 only.

         A non empty value must correspond to a conceptual row in the TIMETRA-SUBSCRIBER-MGMT-MIB::tmnxSubShcvPlcyTable.
         
         A non empty value is only allowed while the value of svcTlsShcvInterval is equal to zero."
    DEFVAL { "" }
    ::= { svcTlsInfoEntry 92 }


-- ------------------------------------
-- TLS FDB Table
-- ------------------------------------
tlsFdbInfoTable OBJECT-TYPE
    SYNTAX          SEQUENCE OF TlsFdbInfoEntry
    MAX-ACCESS      not-accessible
    STATUS          current
    DESCRIPTION     "A table that contains TLS FDB information."
    ::= { tmnxSvcObjs 4 }

tlsFdbInfoEntry OBJECT-TYPE
    SYNTAX          TlsFdbInfoEntry
    MAX-ACCESS      not-accessible
    STATUS          current
    DESCRIPTION     "Information about a specific TLS FDB."
    INDEX           { svcId, tlsFdbMacAddr }
    ::= { tlsFdbInfoTable 1 }

TlsFdbInfoEntry ::=
    SEQUENCE {
        tlsFdbMacAddr           MacAddress,
        tlsFdbRowStatus         RowStatus,
        tlsFdbType              INTEGER,
        tlsFdbLocale            INTEGER,
        tlsFdbPortId            TmnxPortID,
        tlsFdbEncapValue        TmnxEncapVal,
        tlsFdbSdpId             SdpId,
        tlsFdbVcId              Unsigned32,
        tlsFdbVpnId             VpnId,
        tlsFdbCustId            TmnxCustId,
        tlsFdbLastStateChange   TimeStamp,
        tlsFdbProtected         TruthValue,
        tlsFdbBackboneDstMac    MacAddress,
        tlsFdbNumIVplsMac       Unsigned32,
        tlsFdbEndPointName      TNamedItemOrEmpty,
        tlsFdbEPMacOperSdpId    SdpId,
        tlsFdbEPMacOperVcId     Unsigned32,
        tlsFdbPbbNumEpipes      Unsigned32,
        tlsFdbVTEPAddrType      InetAddressType,
        tlsFdbVTEPAddr          InetAddress,
        tlsFdbVNI               Unsigned32,
        tlsFdbEvpnMplsTEPAddrType InetAddressType,
        tlsFdbEvpnMplsTEPAddr     InetAddress,
        tlsFdbEvpnMplsLabel       Unsigned32,
        tlsFdbEvpnMplsEthSegId    OCTET STRING
    }

tlsFdbMacAddr OBJECT-TYPE
    SYNTAX          MacAddress
    MAX-ACCESS      read-only
    STATUS          current
    DESCRIPTION     "The value of the object tlsFdbMacAddr specifies the
                     48-bit IEEE 802.3 MAC address."
    ::= { tlsFdbInfoEntry 1 }

tlsFdbRowStatus OBJECT-TYPE
    SYNTAX          RowStatus
    MAX-ACCESS      read-create
    STATUS          current
    DESCRIPTION     "The value of the object tlsFdbRowStatus specifies the
                     status of this row. The only values supported during a set
                     operation are 'createAndGo' and 'destroy'."
    ::= { tlsFdbInfoEntry 2 }

tlsFdbType OBJECT-TYPE
    SYNTAX          INTEGER {
                        static  (1),
                        learned (2),
                        oam     (3),
                        dhcp    (4),
                        host    (5),
                        intf    (6),
                        spb     (7),
                        condStatic (8),
                        bgpEvpn (9),
                        bgpEvpnStatic (10)
                    }
    MAX-ACCESS      read-create
    STATUS          current
    DESCRIPTION     " The value of the object tlsFdbType specifies:
                     - 'static':  Static TLS FDB entries created via management
                     - 'learned': dynamic entries created via the learning
                                  process
                     - 'oam':     entries created via the OAM process
                     - 'dhcp':    learned  addresses can be temporarily frozen
                                  by the DHCP snooping application for the
                                  duration of a DHCP lease
                     - 'host':    entry added by the system for a static
                                  configured subscriber host
                     - 'intf':    entry added by routed vpls
                     - 'spb' :    entry added by shortest-path bridging
                     - 'condStatic' : entry added via management using tlsCondStaticMacTable
                     - 'bgpEvpn' : entry added via BGP EVPN
                     - 'bgpEvpnStatic' : static entry added via BGP EVPN
                     "
    ::= { tlsFdbInfoEntry 3 }

tlsFdbLocale OBJECT-TYPE
    SYNTAX          INTEGER {
                        sap      (1),
                        sdp      (2),
                        cpm      (3),
                        endpoint (4),
                        vxlan (5),
                        evpnMpls (6)
                    }
    MAX-ACCESS      read-create
    STATUS          current
    DESCRIPTION     "The value of the object tlsFdbLocale specifies for TLS
                     FDB entries defined on a local SAP the value 'sap',
                     remote entries defined on an SDP have the value 'sdp',
                     entries associated with the Control Processor have the
                     value 'cpm' and entries associated with the explicit
                     endpoint have the value 'endpoint'.

                     FDB entries defined on VXLAN (virtual extensible LAN)
                     have the value of 'vxlan'.

                     The value of this object must be specified when
                     the row is created and cannot be changed while
                     the row status is 'active'."
    ::= { tlsFdbInfoEntry 4 }

tlsFdbPortId OBJECT-TYPE
    SYNTAX          TmnxPortID
    MAX-ACCESS      read-create
    STATUS          current
    DESCRIPTION     "When the value of tlsFdbLocale is 'sap', this
                     object, along with tlsFdbEncapValue, specifies
                     the SAP associated with the MAC address defined
                     by tlsFdbMacAddr. This object is otherwise
                     insignificant and should contain a value of 0."
    ::= { tlsFdbInfoEntry 5 }

tlsFdbEncapValue OBJECT-TYPE
    SYNTAX          TmnxEncapVal
    MAX-ACCESS      read-create
    STATUS          current
    DESCRIPTION     "The value of the object tlsFdbEncapValue specifies, when
                     the value of tlsFdbLocale is 'sap', along with
                     tlsFdbPortId, SAP associated with the MAC address defined
                     by tlsFdbMacAddr. This object is otherwise insignificant
                     and should contain a value of 0."
    ::= { tlsFdbInfoEntry 6 }

tlsFdbSdpId OBJECT-TYPE
    SYNTAX          SdpId
    MAX-ACCESS      read-create
    STATUS          current
    DESCRIPTION     "The value of the object tlsFdbSdpId specifies, when the
                     value of tlsFdbLocale is 'sdp', along with tlsFdbVcId,the
                     SDP Binding associated with the MAC address
                     defined by tlsFdbMacAddr. This object is other-
                     wise insignificant and should contain a value of 0."
    ::= { tlsFdbInfoEntry 7 }

tlsFdbVcId OBJECT-TYPE
    SYNTAX          Unsigned32
    MAX-ACCESS      read-create
    STATUS          current
    DESCRIPTION     "The value of the object tlsFdbVcId specifies, when the
                     value of tlsFdbLocale is 'sdp', along with tlsFdbSdpId,
                     the SDP Binding associated with the MAC address defined by
                     tlsFdbMacAddr. This object is other-wise insignificant and
                     should contain a value of 0."
    ::= { tlsFdbInfoEntry 8 }

tlsFdbVpnId OBJECT-TYPE
    SYNTAX          VpnId
    MAX-ACCESS      read-only
    STATUS          current
    DESCRIPTION     "The value of the object tlsFdbVpnId indicates the VPN ID
                     of the associated TLS."
    ::= { tlsFdbInfoEntry 9 }

tlsFdbCustId OBJECT-TYPE
    SYNTAX          TmnxCustId
    MAX-ACCESS      read-only
    STATUS          current
    DESCRIPTION     "The value of the object tlsFdbCustId indicates the
                     Customer ID of the associated TLS."
    ::= { tlsFdbInfoEntry 10 }

tlsFdbLastStateChange OBJECT-TYPE
    SYNTAX          TimeStamp
    MAX-ACCESS      read-only
    STATUS          current
    DESCRIPTION
        "The value of the object tlsFdbLastStateChange indicates
         the value of sysUpTime at the time of the most recent
         state change of this entry. A state change is defined as a
         change in the value of: tlsFdbRowStatus, tlsFdbType,
         tlsFdbLocale, tlsFdbPortId, tlsFdbEncapValue,
         tlsFdbSdpId, tlsFdbVcId, tlsFdbVTEPAddr or tlsFdbVNI."
    ::= { tlsFdbInfoEntry 11 }

tlsFdbProtected OBJECT-TYPE
    SYNTAX          TruthValue
    MAX-ACCESS      read-only
    STATUS          current
    DESCRIPTION     "The value of the object tlsFdbProtected indicates
                     whether or not this MAC is protected. When the value
                     of this object is 'true' the agent will protect
                     the MAC from being learned or re-learned on a SAP
                     that has restricted learning enabled."
    ::= { tlsFdbInfoEntry 12 }

tlsFdbBackboneDstMac OBJECT-TYPE
    SYNTAX          MacAddress
    MAX-ACCESS      read-only
    STATUS          current
    DESCRIPTION     "The value of the object tlsFdbBackboneDstMac indicates the
                     Backbone VPLS service MAC address used as destination MAC 
                     address in the Provider Backbone Bridging frames for this
                     tlsFdbMacAddr.
        
                     This object is insignificant for services with svcVplsType
                     not set to 'iVpls' and should contain a value of
                     0:0:0:0:0:0."
    ::= { tlsFdbInfoEntry 13 }

tlsFdbNumIVplsMac OBJECT-TYPE
    SYNTAX          Unsigned32
    MAX-ACCESS      read-only
    STATUS          current
    DESCRIPTION     "The value of the object tlsFdbNumIVplsMac indicates the
                     number of ISID VPLS service MAC addressess which are using
                     this Backbone MAC address defined by tlsFdbMacAddr.
        
                     This object is insignificant for services with svcVplsType
                     not set to 'bVpls' and should contain a value of 0."
    ::= { tlsFdbInfoEntry 14 }

tlsFdbEndPointName         OBJECT-TYPE
    SYNTAX      TNamedItemOrEmpty
    MAX-ACCESS  read-create
    STATUS      current
    DESCRIPTION
        "The value of tlsFdbEndPointName specifies the name of the service
        endpoint associated with the MAC Address."
    DEFVAL     { "" }
    ::= { tlsFdbInfoEntry 15 }

tlsFdbEPMacOperSdpId OBJECT-TYPE
    SYNTAX          SdpId
    MAX-ACCESS      read-only
    STATUS          current
    DESCRIPTION
        "The value of the object tlsFdbEPMacOperSdpId along with
        tlsFdbEPMacOperVcId indicates the SDP binding associated with this
        static MAC address for this endpoint.

        This object is valid when tlsFdbLocale is 'endpoint', otherwise 
        it should contain a value of 0."
    ::= { tlsFdbInfoEntry 16 }

tlsFdbEPMacOperVcId OBJECT-TYPE
    SYNTAX          Unsigned32
    MAX-ACCESS      read-only
    STATUS          current
    DESCRIPTION
        "The value of the object tlsFdbEPMacOperVcId along with
        tlsFdbEPMacOperSdpId indicates the SDP binding associated with this
        static MAC address for this endpoint.

        This object is valid when tlsFdbLocale is 'endpoint', otherwise 
        it should contain a value of 0."
    ::= { tlsFdbInfoEntry 17 }

tlsFdbPbbNumEpipes OBJECT-TYPE
    SYNTAX          Unsigned32
    MAX-ACCESS      read-only
    STATUS          current
    DESCRIPTION
        "The value of the object tlsFdbPbbNumEpipes indicates number of E-Pipes
        that resolve to this MAC Address.

        This object is valid for service with svcVplsType set to 'bVpls',
        otherwise it should contain a value of 0."
    ::= { tlsFdbInfoEntry 18 }

tlsFdbVTEPAddrType OBJECT-TYPE
    SYNTAX          InetAddressType
    MAX-ACCESS      read-only
    STATUS          current
    DESCRIPTION
        "The value of the object tlsFdbVTEPAddrType indicates type
         of the address associated with tlsFdbVTEPAddr."
    ::= { tlsFdbInfoEntry 19 }

tlsFdbVTEPAddr OBJECT-TYPE
    SYNTAX          InetAddress (SIZE(0|4|16))
    MAX-ACCESS      read-only
    STATUS          current
    DESCRIPTION
        "The value of the object tlsFdbVTEPAddr indicates VXLAN 
         (virtual extensible LAN) Tunnel Endpoint address of ethernet VPN
         (EVPN) destination."
    ::= { tlsFdbInfoEntry 20 }

tlsFdbVNI OBJECT-TYPE
    SYNTAX          Unsigned32
    MAX-ACCESS      read-only
    STATUS          current
    DESCRIPTION
        "The value of the object tlsFdbVNI indicates VXLAN 
         (virtual extensible LAN) Network Identifier (VNI) of the end-point of
         ethernet VPN (EVPN) destination."
   ::= { tlsFdbInfoEntry 21 }

tlsFdbEvpnMplsTEPAddrType OBJECT-TYPE
    SYNTAX          InetAddressType
    MAX-ACCESS      read-only
    STATUS          current
    DESCRIPTION
        "The value of the object tlsFdbEvpnMplsTEPAddrType indicates type
         of the address associated with tlsFdbEvpnMplsTEPAddr."
    ::= { tlsFdbInfoEntry 22 }

tlsFdbEvpnMplsTEPAddr OBJECT-TYPE
    SYNTAX          InetAddress (SIZE(0|4|16))
    MAX-ACCESS      read-only
    STATUS          current
    DESCRIPTION
        "The value of the object tlsFdbEvpnMplsTEPAddr indicates EVPN MPLS
         Tunnel Endpoint address of ethernet VPN (EVPN) destination."
    ::= { tlsFdbInfoEntry 23 }

tlsFdbEvpnMplsLabel OBJECT-TYPE
    SYNTAX          Unsigned32
    MAX-ACCESS      read-only
    STATUS          current
    DESCRIPTION
        "The value of the object tlsFdbEvpnMplsLabel indicates EVPN MPLS label
         of the end-point of ethernet VPN (EVPN) destination."
   ::= { tlsFdbInfoEntry 24 }

tlsFdbEvpnMplsEthSegId OBJECT-TYPE
    SYNTAX      OCTET STRING (SIZE(10))
    MAX-ACCESS  read-only
    STATUS      current
    DESCRIPTION
        "The value of tlsFdbEvpnMplsEthSegId indicates the ethernet segment
         identifier value associated with EVPN MPLS ethernet segment
         destination."
    ::= { tlsFdbInfoEntry 25 }


-- ------------------------------------
-- IES Interface Table
-- ------------------------------------
iesIfTable OBJECT-TYPE
    SYNTAX          SEQUENCE OF IesIfEntry
    MAX-ACCESS      not-accessible
    STATUS          current
    DESCRIPTION     "A table that contains IES interface information."
    ::= { tmnxSvcObjs 5 }

iesIfEntry OBJECT-TYPE
    SYNTAX          IesIfEntry
    MAX-ACCESS      not-accessible
    STATUS          current
    DESCRIPTION     "Information about a specific IES interface."
    INDEX           { svcId, iesIfIndex }
    ::= { iesIfTable 1 }

IesIfEntry ::=
    SEQUENCE {
        iesIfIndex                       InterfaceIndex,
        iesIfRowStatus                   RowStatus,
        iesIfName                        TNamedItem,
        iesIfDescription                 ServObjLongDesc,
        iesIfAdminStatus                 ServiceAdminStatus,
        iesIfOperStatus                  ServiceOperStatus,
        iesIfLastMgmtChange              TimeStamp,
        iesIfVpnId                       VpnId,
        iesIfCustId                      TmnxCustId,
        iesIfLoopback                    TruthValue,
        iesIfLastStatusChange            TimeStamp,
        iesIfType                        INTEGER,
        iesIfParentIf                    InterfaceIndexOrZero,
        iesIfShcvSource                  TmnxSubShcvSrcIpOrigin,
        iesIfShcvAction                  TmnxSubShcvAction,
        iesIfShcvInterval                TmnxSubShcvInterval,
        iesIfFwdServId                   TmnxServId,
        iesIfFwdSubIf                    InterfaceIndexOrZero,
        iesIfPrivateRetailSubnets        TruthValue,
        iesIfDelegatedPrefixLen          Unsigned32,
        iesIfLns                         TruthValue,
        iesIfVplsName                    TLNamedItemOrEmpty,
        iesIfVplsStatus                  ServiceOperStatus,
        iesIfVplsFailedReason            DisplayString,
        iesIfShcvRetryTimeout            TmnxSubShcvRetryTimeout,
        iesIfShcvRetryCount              TmnxSubShcvRetryCount,
        iesIfSapEgressQosId              TPolicyID,
        iesIfDefaultPrimaryDnsIPv4Addr   InetAddressIPv4,
        iesIfDefaultSecondaryDnsIPv4Addr InetAddressIPv4,
        iesIfDefaultPrimaryDnsIPv6Addr   InetAddressIPv6,
        iesIfDefaultSecondaryDnsIPv6Addr InetAddressIPv6,
        iesIfIPv6ConfigAllowed           TruthValue,
        iesIfSrrpRoutingEnabled          TruthValue,
        iesIfSrrpRoutingHoldTime         Unsigned32,
        iesIfMonitorOperGrp              TNamedItemOrEmpty,
        iesIfAllowUnmatchingSubnets      TruthValue,
        iesIfGroupInterfaceType          INTEGER,
        iesIfShcvFamily                  INTEGER,
        iesIfIPv6IpoeBridgedModeEnabled  TruthValue,
        iesIfIPv6AllowUnmatchingPfxs     TruthValue,
        iesIfMcastNetDomainEgrIfCon      INTEGER,
        iesIfIPv6AllowMultiWanAddr       TruthValue,
        iesIfIPv6Dhcp6OverrideSlaac      TruthValue,
        iesIfCreationOrigin              TmnxCreateOrigin,
        iesIfIPv6Dhcp6PDManagedRoute     TruthValue,
        iesIfVplsEvpnTunnel              TruthValue,
        iesIfExportHostRoutes            TruthValue,
        iesIfSuppressAaSub               TmnxEnabledDisabled,
        iesIfShcvPolicy                  TNamedItemOrEmpty,
        iesIfShcvPolicyIpv4              TNamedItemOrEmpty,
        iesIfShcvPolicyIpv6              TNamedItemOrEmpty,
        iesIfIpv6Dhcp6UserIdent          INTEGER,
        iesIfIPv6Dhcp6PDManagedRouteNH   INTEGER
    }
iesIfIndex OBJECT-TYPE
    SYNTAX          InterfaceIndex
    MAX-ACCESS      read-only
    STATUS          current
    DESCRIPTION     "The secondary index of the row in the vRtrIfTable
                     corresponding to this IES interface. The primary
                     index is 1; i.e. all IES interfaces are defined in
                     the Base virtual router context."
    ::= { iesIfEntry 1 }

iesIfRowStatus OBJECT-TYPE
    SYNTAX          RowStatus
    MAX-ACCESS      read-create
    STATUS          current
    DESCRIPTION     "The value of the object iesIfRowStatus specifies the
                     status of this row.
                     The only values supported during a set operation are
                     'createAndGo' and 'destroy'."
    ::= { iesIfEntry 2 }

iesIfName OBJECT-TYPE
    SYNTAX          TNamedItem
    MAX-ACCESS      read-create
    STATUS          current
    DESCRIPTION     "The value of the object iesIfName specifies the name used
                     to refer to this IES interface. This  name must be unique
                     within the Base virtual router context.
                     This object must be specified when the row is created, and
                     cannot be changed while the rowstatus is 'active'."
    ::= { iesIfEntry 3 }

iesIfDescription OBJECT-TYPE
    SYNTAX          ServObjLongDesc
    MAX-ACCESS      read-create
    STATUS          current
    DESCRIPTION     "The value of the object iesIfDescription specifies
                     generic information about this IES interface."
    DEFVAL          { "" }
    ::= { iesIfEntry 4 }

iesIfAdminStatus OBJECT-TYPE
    SYNTAX          ServiceAdminStatus
    MAX-ACCESS      read-create
    STATUS          current
    DESCRIPTION     "The value of the object iesIfAdminStatus specifies the
                     desired state of this IES interface."
    DEFVAL          { up }
    ::= { iesIfEntry 5 }

iesIfOperStatus OBJECT-TYPE
    SYNTAX          ServiceOperStatus
    MAX-ACCESS      read-only
    STATUS          current
    DESCRIPTION     "The value of the object iesIfOperStatus indicates the
                     operating state of this IES interface."
    ::= { iesIfEntry 6 }

iesIfLastMgmtChange OBJECT-TYPE
    SYNTAX          TimeStamp
    MAX-ACCESS      read-only
    STATUS          current
    DESCRIPTION     "The value of the object iesIfLastMgmtChange indicates the
                     value of sysUpTime at the time of the most recent
                     management-initiated change to this IES interface."
    ::= { iesIfEntry 7 }

iesIfVpnId OBJECT-TYPE
    SYNTAX          VpnId
    MAX-ACCESS      read-only
    STATUS          obsolete
    DESCRIPTION     "The value of the object iesIfVpnId indicates the VPN ID of
                     the associated IES service."
    ::= { iesIfEntry 8 }

iesIfCustId OBJECT-TYPE
    SYNTAX          TmnxCustId
    MAX-ACCESS      read-only
    STATUS          current
    DESCRIPTION     "The value of the object iesIfCustId indicates the Customer
                     ID of the associated IES service."
    ::= { iesIfEntry 9 }

iesIfLoopback OBJECT-TYPE
    SYNTAX          TruthValue
    MAX-ACCESS      read-create
    STATUS          current
    DESCRIPTION     "When the value of iesIfLoopback is set to 'true',
                     loopback is enabled on the  IES interface represented
                     by this row entry.  When the value is 'false',
                     loopback is disabled."
    ::= { iesIfEntry 10 }

iesIfLastStatusChange OBJECT-TYPE
    SYNTAX          TimeStamp
    MAX-ACCESS      read-only
    STATUS          current
    DESCRIPTION     "The value of the object iesIfLastStatusChange indicates
                     the value of sysUpTime at the time of the most recent
                     operating status change to his interface."
    ::= { iesIfEntry 11 }

iesIfType  OBJECT-TYPE
    SYNTAX          INTEGER {
                        service    (1),
                        subscriber (2),
                        group      (3),
                        redundant  (4),
                        cem        (5),
                        ipsec      (6),
                        ipMirror   (7),
                        video      (8),
                        reserved9  (9),
                        aarp       (10),
                        aa         (11)
                    }
    MAX-ACCESS      read-create
    STATUS          current
    DESCRIPTION     "The value of iesIfType specifies the type
                     of this IES interface. This object can only be set at
                     row creation time.
                     'service'     - This is a normal IES interface.
                     'subscriber'  - This is a subscriber interface, 
                                     under which multiple group interfaces 
                                     can be configured.
                     'group'       - This is a group interface, belonging 
                                     to a parent subscriber interface.
                     'redundant'   - This is a redundant interface, used 
                                     for dual homing.
                     'cem'         - This is a CEM interface, used for 
                                     IP/UDP encapsulated CEM IES interface.
                     'ipsec'       - This is an IPsec interface, used for 
                                     IPsec tunneling.
                     'ipMirror'    - This is an IP interface, used for 
                                     IP Mirroring.
                     'video'       - This is a video IP interface.
                     'aarp'        - This is an AARP (Assymmetry Removal)
                                     interface.
                     'aa'          - This is an AA (Application Assurance)
                                     interface."
    DEFVAL          { service }
    ::= { iesIfEntry 12 }

iesIfParentIf   OBJECT-TYPE
    SYNTAX          InterfaceIndexOrZero
    MAX-ACCESS      read-create
    STATUS          current
    DESCRIPTION     "The value of iesIfParentIf specifies the ifIndex of
                     this interface's parent. This value can only be set at
                     row creation time, and is only valid when
                     iesIfType is 'group'. The interface pointed to by
                     iesIfParentIf must be of type 'subscriber'."
    DEFVAL          { 0 }
    ::= { iesIfEntry 13 }

iesIfShcvSource    OBJECT-TYPE
    SYNTAX          TmnxSubShcvSrcIpOrigin 
    MAX-ACCESS      read-create
    STATUS          current
    DESCRIPTION     "The value of iesIfShcvSource specifies the source used
                     for subscriber host connectivity checking"
    DEFVAL          { interface }
    ::= { iesIfEntry 14 }

iesIfShcvAction    OBJECT-TYPE
    SYNTAX          TmnxSubShcvAction
    MAX-ACCESS      read-create
    STATUS          current
    DESCRIPTION     "The value of iesIfShcvAction specifies the action to be
                     taken for hosts on this interface whose host connectivity
                     checking fails"
    DEFVAL          { alarm }
    ::= { iesIfEntry 15 }

iesIfShcvInterval   OBJECT-TYPE
    SYNTAX          TmnxSubShcvInterval
    UNITS           "minutes"
    MAX-ACCESS      read-create
    STATUS          current
    DESCRIPTION     "The value of the object iesIfShcvInterval specifies
                     the interval in minutes between connectivity checks.
                     Zero means no in host-connection-verify."
    DEFVAL          { 0 }
    ::= { iesIfEntry 16 }

iesIfFwdServId       OBJECT-TYPE
    SYNTAX           TmnxServId
    MAX-ACCESS       read-create
    STATUS           current
    DESCRIPTION      "The value of iesIfFwdServId specifies the forwarding 
                      service ID for a subscriber interface in a retailer 
                      context. This value can only be set at row creation time
                      along with iesIfFwdSubIf, and it is only valid when 
                      iesIfType is 'subscriber'. The iesIfFwdServId MUST 
                      correspond to a service of type 'vprn'."
    DEFVAL           { 0 }
    ::= { iesIfEntry 17 }

iesIfFwdSubIf        OBJECT-TYPE
    SYNTAX           InterfaceIndexOrZero
    MAX-ACCESS       read-create
    STATUS           current
    DESCRIPTION      "The value of iesIfFwdSubIf specifies the forwarding 
                      subscriber interface for a subscriber interface in a 
                      retailer context. This value can only be set at row 
                      creation time along with iesIfFwdServId, and it is only 
                      valid when iesIfType is 'subscriber'. The interface 
                      pointed to by iesIfFwdSubIf MUST be of type 'subscriber' 
                      in the the service context defined by iesIfFwdServId."
    DEFVAL           { 0 }
    ::= { iesIfEntry 18 }

iesIfPrivateRetailSubnets  OBJECT-TYPE
    SYNTAX           TruthValue
    MAX-ACCESS       read-create
    STATUS           current
    DESCRIPTION      "The value of iesIfPrivateRetailSubnets specifies 
                      whether or not overlapping Ip address may exist between
                      different retailers referring to this interface." 
    ::= { iesIfEntry 19 }

iesIfDelegatedPrefixLen  OBJECT-TYPE
    SYNTAX      Unsigned32 (0|48..64)
    MAX-ACCESS  read-create
    STATUS      current
    DESCRIPTION
        "The value of iesIfDelegatedPrefixLen specifies the number of bits that
         can be allocated to a Delegated Prefix for IPv6.
         
         A value of zero (0) indicates a variable Delegated Prefix length."
    DEFVAL { 64 }
    ::= { iesIfEntry 20 }

iesIfLns             OBJECT-TYPE
    SYNTAX           TruthValue
    MAX-ACCESS       read-create
    STATUS           current
    DESCRIPTION      "The value of iesIfLns specifies whether this interface
                      can be used to terminate LNS (L2TP Network Server) PPP
                      sessions. The value of this object can only be set to
                      'true' at row creation time, and is only valid when
                      iesIfType is 'group'.
                      
                      This object is supported for backwards compatibility only;
                      the recommended way to create LNS group interfaces is by means
                      of the iesIfGroupInterfaceType object."
    DEFVAL           { false }
    ::= { iesIfEntry 21 }

iesIfVplsName OBJECT-TYPE
    SYNTAX          TLNamedItemOrEmpty
    MAX-ACCESS      read-create
    STATUS          current
    DESCRIPTION     "The value of the object iesIfVplsName specifies the name
                     of the VPLS service associated this interface."
    DEFVAL { ''H }
    ::= { iesIfEntry 22 }

iesIfVplsStatus OBJECT-TYPE
    SYNTAX          ServiceOperStatus
    MAX-ACCESS      read-only
    STATUS          current
    DESCRIPTION     "The value of the object iesIfVplsStatus indicates the
                     operational status of the VPLS service on this interface."
    ::= { iesIfEntry 23 }


iesIfVplsFailedReason OBJECT-TYPE
    SYNTAX           DisplayString 
    MAX-ACCESS       read-only
    STATUS           current
    DESCRIPTION
        "The value of the object iesIfVplsFailedReason specifies the reason
         when the value of iesIfVplsStatus is 'down'." 
    ::= { iesIfEntry 24 }

iesIfShcvRetryTimeout OBJECT-TYPE
    SYNTAX          TmnxSubShcvRetryTimeout
    UNITS           "seconds"
    MAX-ACCESS      read-create
    STATUS          current
    DESCRIPTION     "The value of the object iesIfShcvRetryTimeout specifies
                     the timeout in seconds before a connectivity check
                     retransmission."
    DEFVAL          { 10 }
    ::= { iesIfEntry 25 }

iesIfShcvRetryCount OBJECT-TYPE
    SYNTAX          TmnxSubShcvRetryCount
    MAX-ACCESS      read-create
    STATUS          current
    DESCRIPTION     "The value of the object iesIfShcvRetryCount specifies
                     the number of connectivity check retransmissions.
                     
                     Setting the value to n specifies that, for any given host,
                     at most (n+1) probes are done each interval, 
                     and (n+1) missed replies are considered as a connectivity 
                     failure."
    DEFVAL          { 2 }
    ::= { iesIfEntry 26 }

iesIfSapEgressQosId OBJECT-TYPE
    SYNTAX          TPolicyID
    MAX-ACCESS      read-create
    STATUS          current
    DESCRIPTION     "The value of the object iesIfSapEgressQosId specifies
                     the QoS policy ID which is used to reclassify IP packets
                     on the egress side of the SAPs associated with the 
                     VPLS service on this interface. 
                     
                     When set to the default value, this object specifies that 
                     the IP packets will not be reclassified on the egress SAPs
                     of the VPLS service attached to the IP interface."
    DEFVAL           { 0 }                 
    ::= { iesIfEntry 27 }
    
iesIfDefaultPrimaryDnsIPv4Addr OBJECT-TYPE
    SYNTAX          InetAddressIPv4
    MAX-ACCESS      read-create
    STATUS          current
    DESCRIPTION     "The value of the object iesIfDefaultPrimaryDnsIPv4Addr
                     specifies the IPv4 address of the default primary DNS 
                     server for the subscribers using this interface.
                     
                     Subscribers that cannot obtain an IPv4 DNS server addres
                     by other means, can use this for DNS name resolution. 
                     
                     The object iesIfDefaultPrimaryDnsIPv4Addr can only be set 
                     to a nonzero value if the value of iesIfType is 
                     'subscriber'."
    DEFVAL           { '00000000'H }
    ::= { iesIfEntry 28 }
    
iesIfDefaultSecondaryDnsIPv4Addr OBJECT-TYPE
    SYNTAX          InetAddressIPv4
    MAX-ACCESS      read-create
    STATUS          current
    DESCRIPTION     "The value of the object iesIfDefaultSecondaryDnsIPv4Addr 
                     specifies the IPv4 address of the default secondary DNS 
                     server for the subscribers using this interface.
                     
                     Subscribers that cannot obtain an IPv4 DNS server addres
                     by other means, can use this for DNS name resolution. 
                     
                     The object iesIfDefaultSecondaryDnsIPv4Addr can only be set 
                     to a nonzero value if the value of iesIfType is 
                     'subscriber'."
    DEFVAL           { '00000000'H }
    ::= { iesIfEntry 29 }
    
iesIfDefaultPrimaryDnsIPv6Addr OBJECT-TYPE
    SYNTAX          InetAddressIPv6
    MAX-ACCESS      read-create
    STATUS          current
    DESCRIPTION     "The value of the object iesIfDefaultPrimaryDnsIPv6Addr 
                     specifies the IPv6 address of the default primary 
                     DNS server for the subscribers using this interface.
                     
                     Subscribers that cannot obtain an IPv6 DNS server addres
                     by other means, can use this for DNS name resolution. 
                     
                     The object iesIfDefaultPrimaryDnsIPv6Addr can only be set 
                     to a nonzero value if the value of iesIfType is 
                     'subscriber'."
    DEFVAL           { '00000000000000000000000000000000'H }
    ::= { iesIfEntry 30 }
    
iesIfDefaultSecondaryDnsIPv6Addr OBJECT-TYPE
    SYNTAX          InetAddressIPv6
    MAX-ACCESS      read-create
    STATUS          current
    DESCRIPTION     "The value of the object iesIfDefaultSecondaryDnsIPv6Addr 
                     specifies the IPv6 address of the default primary 
                     DNS server for the subscribers using this interface.
                     
                     Subscribers that cannot obtain an IPv6 DNS server addres
                     by other means, can use this for DNS name resolution. 
                     
                     The object iesIfDefaultSecondaryDnsIPv6Addr can only be set 
                     to a nonzero value if the value of iesIfType is 
                     'subscriber'."
    DEFVAL           { '00000000000000000000000000000000'H }
    ::= { iesIfEntry 31 }

iesIfIPv6ConfigAllowed  OBJECT-TYPE
    SYNTAX          TruthValue
    MAX-ACCESS      read-create
    STATUS          current
    DESCRIPTION     "The value of iesIfIPv6ConfigAllowed specifies whether IPv6
                     can be configured on this interface. When the value is
                     'true', IPv6 can be configured on this interface. When it
                     is 'false', IPv6 cannot be configured.

                     The object iesIfIPv6ConfigAllowed can only be set if the 
                     value of iesIfType is 'subscriber' or 'group'."
    DEFVAL           { false }
    ::= { iesIfEntry 32 }

iesIfSrrpRoutingEnabled OBJECT-TYPE
    SYNTAX          TruthValue
    MAX-ACCESS      read-create
    STATUS          current
    DESCRIPTION     "The value of iesIfSrrpRoutingEnabled specifies
                     whether SRRP state monitoring for subscriber-management
                     routes and managed routes on this group interface is 
                     enabled or not.
                     
                     A value 'true' means monitoring is enabled, a value 'false'
                     means monitoring is disabled."
    DEFVAL           { false }                 
    ::= { iesIfEntry 33 }
    
iesIfSrrpRoutingHoldTime OBJECT-TYPE
    SYNTAX          Unsigned32 (0..50)
    MAX-ACCESS      read-create
    STATUS          current
    DESCRIPTION     "The value of iesIfSrrpRoutingHoldTime specifies
                     the delay before updating the route state after the last
                     SRRP transition."
    DEFVAL           { 0 }                 
    ::= { iesIfEntry 34 }
        
iesIfMonitorOperGrp OBJECT-TYPE
    SYNTAX          TNamedItemOrEmpty
    MAX-ACCESS      read-create
    STATUS          current
    DESCRIPTION     "The value of the iesIfMonitorOperGrp specifies the
                     Operational-Group identifier which will affect the state
                     of this interface."
    DEFVAL { "" }
    ::= { iesIfEntry 35 }

iesIfAllowUnmatchingSubnets  OBJECT-TYPE
    SYNTAX           TruthValue
    MAX-ACCESS       read-create
    STATUS           current
    DESCRIPTION      "The value of iesIfAllowUnmatchingSubnets specifies 
                      if subscriber hosts with a subnet that does not match
                      any of the subnets configured on this interface, are
                      allowed.
                      
                      This object is only relevant if the value of the object
                      iesIfType in this conceptual row is equal to 'subscriber';
                      otherwise, 'false' is the only allowed value.
                      
                      The value of iesIfAllowUnmatchingSubnets can only be set
                      to 'true' if the number of subnets (vRtrIpAddrTable) 
                      configured on this interface is between one and 255.
                      
                      The value of iesIfAllowUnmatchingSubnets can only be set
                      to 'true' while in the corresponding conceptual row in the
                      TIMETRA-VTR-MIB::vRtrIfTable the values of 
                      vRtrIfUnnumbered and vRtrIfUnnumberedIf are set to their
                      default values." 
    DEFVAL           { false }                 
    ::= { iesIfEntry 36 }

iesIfGroupInterfaceType  OBJECT-TYPE
    SYNTAX          INTEGER {
                        none                             (0),
                        plain                            (1),
                        lns                              (2),
                        softGre                          (3)
                    }
    MAX-ACCESS      read-create
    STATUS          current
    DESCRIPTION     "The value of iesIfGroupInterfaceType specifies
                     the type of group interface, if the value of iesIfType is
                     equal to 'group'.
                     
                     If the value of iesIfType is not equal to 'group',
                     the value of this object can only be set to 'none'. 
                     
                     The value of this object can only be set at row creation
                     time.
                     
                     If this row is created with a value of iesIfType equal 
                     to 'group', the default value of this object 
                     is equal to 'plain'.
                     
                     'none'        - This is not a group interface.
                     'plain'       - This is a plain group interface.
                     'lns'         - This is an LNS group interface, used to 
                                     terminate LNS (L2TP Network Server) PPP
                                     sessions.
                     'softGre'     - This is a Soft GRE group interface, used
                                     to terminate Soft-GRE type DHCP sessions."
    DEFVAL          { none }
    ::= { iesIfEntry 37 }

iesIfShcvFamily OBJECT-TYPE
    SYNTAX          INTEGER {
                        both (0),
                        ipv4 (1),
                        ipv6 (2)
                    }
    MAX-ACCESS      read-create
    STATUS          current
    DESCRIPTION     "The value of the object iesIfShcvFamily specifies
                     for which host IP family the connectivity is checked.

                     If the value of iesIfType is not equal to 'group',
                     the value of this object can only be set to 'ipv4'."
    DEFVAL          { ipv4 }
    ::= { iesIfEntry 38 }

iesIfIPv6IpoeBridgedModeEnabled OBJECT-TYPE
    SYNTAX          TruthValue
    MAX-ACCESS      read-create
    STATUS          current
    DESCRIPTION     "The value of iesIfIPv6IpoeBridgedModeEnabled specifies
                     whether IPv6 IPoE Bridged Mode is enabled or not.

                     If the value of iesIfType is not equal to 'group',
                     the value of this object cannot be set to 'true'."
    DEFVAL          { false }
    ::= { iesIfEntry 39 }

iesIfIPv6AllowUnmatchingPfxs  OBJECT-TYPE
    SYNTAX           TruthValue
    MAX-ACCESS       read-create
    STATUS           current
    DESCRIPTION      "The value of iesIfIPv6AllowUnmatchingPfxs specifies 
                      if subscriber hosts with a prefix that does not match
                      any of the prefixes configured on this interface, are
                      allowed.
                      
                      This object is only relevant if the value of the object
                      iesIfType in this conceptual row is equal to 'subscriber';
                      otherwise, 'false' is the only allowed value.
                      
                      The value of iesIfIPv6AllowUnmatchingPfxs can only be set
                      to 'true' if the number of prefixes (vRtrIpAddrTable) 
                      configured on this interface is between one and 254." 
    DEFVAL           { false }                 
    ::= { iesIfEntry 40 }

iesIfMcastNetDomainEgrIfCon OBJECT-TYPE
    SYNTAX      INTEGER {
                    notApplicable (1),
                    notAvailable  (2),
                    consistent    (3),
                    inconsistent  (4)
                }
    MAX-ACCESS  read-only
    STATUS      current
    DESCRIPTION
        " The value of iesIfMcastNetDomainEgrIfCon indicates whether the spoke
          sdp leaves the router interface in the multicast network domain 
          indicated by vRtrIfMcastNetworkDomainName.

          A value of 'notApplicable' indicates that this interface is not a 
          spoke sdp interface.

          A value of 'notAvailable' indicates that the outgoing interface is 
          unknown for this spoke spd interface.

          A value of 'consistent' indicates that the current spoke sdp egress 
          interface is in the multicast network domain indicated by 
          vRtrIfMcastNetworkDomainName.

          A value of 'inconsistent' indicates that the current spoke sdp egress 
          interface is not in the multicast network domain indicated by 
          vRtrIfMcastNetworkDomainName."
    ::= { iesIfEntry 41 }

iesIfIPv6AllowMultiWanAddr  OBJECT-TYPE
    SYNTAX           TruthValue
    MAX-ACCESS       read-create
    STATUS           current
    DESCRIPTION      "The value of iesIfIPv6AllowMultiWanAddr specifies
                      if multiple wan addresses from multiple sources are
                      allowed, or if the second addresses are rejected."
    DEFVAL           { false }
    ::= { iesIfEntry 42 }

iesIfIPv6Dhcp6OverrideSlaac  OBJECT-TYPE
    SYNTAX           TruthValue
    MAX-ACCESS       read-create
    STATUS           current
    DESCRIPTION      "The value of iesIfIPv6Dhcp6OverrideSlaac specifies
                      if the wan address received from SLAAC will be
                      removed when a (second) wan address is received
                      from DHCP6, or if the host will keep both."
    DEFVAL           { false }
    ::= { iesIfEntry 43 }

iesIfCreationOrigin  OBJECT-TYPE
    SYNTAX          TmnxCreateOrigin
    MAX-ACCESS      read-only
    STATUS          current
    DESCRIPTION     "The value of iesIfCreationOrigin indicates the mechanism
                     used to create this entry."
    DEFVAL { manual }
    ::= { iesIfEntry 44 }

iesIfIPv6Dhcp6PDManagedRoute  OBJECT-TYPE
    SYNTAX           TruthValue
    MAX-ACCESS       read-create
    STATUS           current
    DESCRIPTION      "The value of iesIfIPv6Dhcp6PDManagedRoute specifies
                      whether DHCP6 delegated prefixes will be installed
                      as managed routes."
    DEFVAL           { false }
    ::= { iesIfEntry 45 }

iesIfVplsEvpnTunnel OBJECT-TYPE
    SYNTAX           TruthValue
    MAX-ACCESS       read-create
    STATUS           current
    DESCRIPTION       
        "The value of iesIfVplsEvpnTunnel specifies whether this routed VPLS
         interface is to be used as a EVPN tunnel.
                      
         An 'inconsistentValue' error is returned if this object
         is set to 'true' when iesIfVplsName is set to default value."
    DEFVAL           { false }
    ::= { iesIfEntry 46 }

iesIfExportHostRoutes OBJECT-TYPE
    SYNTAX           TruthValue
    MAX-ACCESS       read-create
    STATUS           current
    DESCRIPTION       
        "The value of iesIfExportHostRoutes specifies whether to export host
         routes to the forwarding service."
    DEFVAL           { false }
    ::= { iesIfEntry 47 }

iesIfSuppressAaSub OBJECT-TYPE
    SYNTAX      TmnxEnabledDisabled
    MAX-ACCESS  read-create
    STATUS      current
    DESCRIPTION
        "The value of iesIfSuppressAaSub specifies whether or not to
         suppess Application-Assurance for Enhanced Subscriber Management (ESM)
         subscribers who are associated with this IES instance and have
         TIMETRA-BSX-NG-MIB::tmnxBsxAppProfSubSuppressible in 
         tmnxBsxAppProfEntry set to 'enabled (1)'."
    DEFVAL  { disabled }
    ::= { iesIfEntry 48 }

iesIfShcvPolicy OBJECT-TYPE
    SYNTAX      TNamedItemOrEmpty
    MAX-ACCESS  read-create
    STATUS      current
    DESCRIPTION
        "The value of iesIfShcvPolicy specifies the Subscriber Host Connectivity Verification (SHCV)
         policy.

         A non empty value must correspond to a conceptual row in the TIMETRA-SUBSCRIBER-MGMT-MIB::tmnxSubShcvPlcyTable.
         
         A non empty value is only allowed while the value of iesIfShcvInterval is equal to zero,
         and the values of iesIfShcvPolicyIpv4 and iesIfShcvPolicyIpv6 are both empty."
    DEFVAL { "" }
    ::= { iesIfEntry 49 }

iesIfShcvPolicyIpv4 OBJECT-TYPE
    SYNTAX      TNamedItemOrEmpty
    MAX-ACCESS  read-create
    STATUS      current
    DESCRIPTION
        "The value of iesIfShcvPolicyIpv4 specifies the Subscriber Host Connectivity Verification (SHCV)
         policy for IPv4 only.

         A non empty value must correspond to a conceptual row in the TIMETRA-SUBSCRIBER-MGMT-MIB::tmnxSubShcvPlcyTable.
         
         A non empty value is only allowed while the value of iesIfShcvInterval is equal to zero,
         and while the value of iesIfShcvPolicy is empty."
    DEFVAL { "" }
    ::= { iesIfEntry 50 }

iesIfShcvPolicyIpv6 OBJECT-TYPE
    SYNTAX      TNamedItemOrEmpty
    MAX-ACCESS  read-create
    STATUS      current
    DESCRIPTION
        "The value of iesIfShcvPolicyIpv6 specifies the Subscriber Host Connectivity Verification (SHCV)
         policy for IPv6 only.

         A non empty value must correspond to a conceptual row in the TIMETRA-SUBSCRIBER-MGMT-MIB::tmnxSubShcvPlcyTable.
         
         A non empty value is only allowed while the value of iesIfShcvInterval is equal to zero,
         and while the value of iesIfShcvPolicy is empty."
    DEFVAL { "" }
    ::= { iesIfEntry 51 }

iesIfIpv6Dhcp6UserIdent  OBJECT-TYPE
    SYNTAX          INTEGER {
                        mac            (1),
                        macInterfaceId (2)
                    }
    MAX-ACCESS      read-create
    STATUS          current
    DESCRIPTION     
        "The value of iesIfIpv6Dhcp6UserIdent specifies how subscriber hosts
         are identified.
                     
         A value of 'mac' identifies each subscriber by it's unique mac-address,
         while 'macInterfaceId' identifies the subscriber by mac-address +
         interface-id."
    DEFVAL          { mac }
    ::= { iesIfEntry 52 }

iesIfIPv6Dhcp6PDManagedRouteNH  OBJECT-TYPE
    SYNTAX          INTEGER {
                        ipv4    (1),
                        ipv6    (2)
                    }
    MAX-ACCESS      read-create
    STATUS          current
    DESCRIPTION     "The value of iesIfIPv6Dhcp6PDManagedRouteNH specifies the
                     type of nexthop for the pd-managed-route."
    DEFVAL          { ipv6 }
    ::= { iesIfEntry 53 }

-- ------------------------------------
-- TLS Split-Horizon Group Table
-- ------------------------------------
tlsShgInfoTable OBJECT-TYPE
    SYNTAX          SEQUENCE OF TlsShgInfoEntry
    MAX-ACCESS      not-accessible
    STATUS          current
    DESCRIPTION     "A table that contains TLS service split-horizon group
                     information. A maximum of 30 split-horizon groups can
                     be created in a given TLS service. Maximum is set to 15
                     for a TLS service with svcVplsType set to 'bVpls', or 
                     'iVpls'."
    ::= { tmnxSvcObjs 6 }

tlsShgInfoEntry OBJECT-TYPE
    SYNTAX          TlsShgInfoEntry
    MAX-ACCESS      not-accessible
    STATUS          current
    DESCRIPTION     "Split-horizon group information about a TLS service."
    INDEX           { svcId, IMPLIED tlsShgName }
    ::= { tlsShgInfoTable 1 }

TlsShgInfoEntry ::=
    SEQUENCE {
        tlsShgName                  TNamedItem,
        tlsShgRowStatus             RowStatus,
        tlsShgCustId                TmnxCustId,
        tlsShgInstanceId            Unsigned32,
        tlsShgDescription           ServObjDesc,
        tlsShgLastMgmtChange        TimeStamp,
        tlsShgResidential           TruthValue,
        tlsShgRestProtSrcMac        TruthValue,
        tlsShgRestUnprotDstMac      TruthValue,
        tlsShgRestProtSrcMacAction  INTEGER,
        tlsShgCreationOrigin        TmnxCreateOrigin,
        tlsShgSiteName              TNamedItemOrEmpty,
        tlsShgAutoLearnMacProtect   TruthValue
    }

tlsShgName OBJECT-TYPE
    SYNTAX          TNamedItem
    MAX-ACCESS      not-accessible
    STATUS          current
    DESCRIPTION     "The value of the object tlsShgName specifies the name of
                     the split-horizon group. The name must be unique within
                     a TLS, however the same name can appear in different
                     TLS services, in which case they denote different
                     split-horizon groups."
    ::= { tlsShgInfoEntry 1 }

tlsShgRowStatus OBJECT-TYPE
    SYNTAX          RowStatus
    MAX-ACCESS      read-create
    STATUS          current
    DESCRIPTION     "The value of the object  tlsShgRowStatus specifies the
                     status of this row.
                     The only values supported during a set operation are
                     'createAndGo' and 'destroy'. To delete an entry
                     from this table, there should be no TLS SAP's or
                     TLS spoke SDP Bindings refering to it."
    ::= { tlsShgInfoEntry 2 }

tlsShgCustId OBJECT-TYPE
    SYNTAX          TmnxCustId
    MAX-ACCESS      read-only
    STATUS          current
    DESCRIPTION     "The value of the object tlsShgCustId indicates the
                     Customer ID of the associated TLS service."
    ::= { tlsShgInfoEntry 3 }

tlsShgInstanceId OBJECT-TYPE
    SYNTAX          Unsigned32
    MAX-ACCESS      read-only
    STATUS          current
    DESCRIPTION     "The value of the object tlsShgInstanceId indicates the
                     instance identifier for the split horizon group."
    ::= { tlsShgInfoEntry 4 }

tlsShgDescription OBJECT-TYPE
    SYNTAX          ServObjDesc
    MAX-ACCESS      read-create
    STATUS          current
    DESCRIPTION     "The value of the object tlsShgDescription specifies
                     generic information about this split-horizon group."
    DEFVAL { "" }
    ::= { tlsShgInfoEntry 5 }

tlsShgLastMgmtChange OBJECT-TYPE
    SYNTAX          TimeStamp
    MAX-ACCESS      read-only
    STATUS          current
    DESCRIPTION     "The value of the object tlsShgLastMgmtChange indicates the
                     value of sysUpTime at the time of the most recent
                     management-initiated change to this split-horizon group."
    ::= { tlsShgInfoEntry 6 }

tlsShgResidential OBJECT-TYPE
    SYNTAX          TruthValue
    MAX-ACCESS      read-create
    STATUS          current
    DESCRIPTION     "The value of the object tlsShgResidential  specifies
                     whether  or not the split-horizon-group is residential.In
                     a Residential Split Horizon Group (RSHG) there is no
                     downstream broadcast, and all saps in the group will share
                     the default ingress queue. The value can be specified
                     during  row-creation, cannot be changed later on."
    DEFVAL { false }
    ::= { tlsShgInfoEntry 7 }

tlsShgRestProtSrcMac OBJECT-TYPE
    SYNTAX          TruthValue
    MAX-ACCESS      read-create
    STATUS          current
    DESCRIPTION     "The value of the object tlsShgRestProtSrcMac indicates
                     how the agent will handle relearn requests for protected
                     MAC addresses received on SAP's belonging to this SHG.
                     When the value of this object is 'true' requests to 
                     relearn a protected MAC address will be ignored.
                     In addition, if the value of tlsShgRestProtSrcMacAction
                     is 'disable', then the SAP where the protected source
                     MAC was seen will be brought operationally down."
    DEFVAL          { false }
    ::= { tlsShgInfoEntry 8 }

tlsShgRestUnprotDstMac OBJECT-TYPE
    SYNTAX          TruthValue
    MAX-ACCESS      read-create
    STATUS          current
    DESCRIPTION     "The value of the object tlsShgRestUnprotDstMac indicates
                     how the system will forward packets destined to an
                     unprotected MAC address. When the value of this object is
                     'true' packets destined to an unprotected MAC address
                     will be dropped."
    DEFVAL          { false }
    ::= { tlsShgInfoEntry 9 }
    
tlsShgRestProtSrcMacAction OBJECT-TYPE
    SYNTAX          INTEGER {
                        disable      (1),
                        alarm-only   (2),
                        discardFrame (3)
                    }
    MAX-ACCESS      read-create
    STATUS          current
    DESCRIPTION     "The value of the object tlsShgRestProtSrcMacAction
                     indicates the action to take whenever a relearn request
                     for a protected MAC is received on a restricted SAP
                     belonging to this SHG.

                     When the value of this object is 'disable' the SAP
                     will be placed in the operational down state, with the
                     operating flag 'recProtSrcMac' set.
                     
                     When the value of this object is 'alarm-only', the SAP
                     will be left up and only a notification,
                     sapReceivedProtSrcMac,  will be generated.

                     When the value of this object is 'discardFrame', the
                     SAP will start discarding the frame in addition to 
                     generating sapReceivedProtSrcMac notification."
    DEFVAL          { disable }    
    ::= { tlsShgInfoEntry 10 }

tlsShgCreationOrigin  OBJECT-TYPE
    SYNTAX          TmnxCreateOrigin
    MAX-ACCESS      read-only
    STATUS          current
    DESCRIPTION     "The value of tlsShgCreationOrigin indicates the protocol or 
                     mechanism which created this SHG."
    ::= { tlsShgInfoEntry 11 }

tlsShgSiteName OBJECT-TYPE
    SYNTAX          TNamedItemOrEmpty
    MAX-ACCESS      read-only
    STATUS          current
    DESCRIPTION     "The value of tlsShgSiteName indicates the site-name
                     associated with this SHG."
    ::= { tlsShgInfoEntry 12 }

tlsShgAutoLearnMacProtect   OBJECT-TYPE
    SYNTAX      TruthValue
    MAX-ACCESS  read-create
    STATUS      current
    DESCRIPTION
        "The value of tlsShgAutoLearnMacProtect specifies whether
         to enable automatic population of the MAC protect list with
         source MAC addresses learned on the associated with this SHG."
    DEFVAL { false }
    ::= { tlsShgInfoEntry 13 }

-- ------------------------------------
-- APIPE Service Table
-- ------------------------------------
svcApipeInfoTable OBJECT-TYPE
    SYNTAX          SEQUENCE OF SvcApipeInfoEntry
    MAX-ACCESS      not-accessible
    STATUS          current
    DESCRIPTION     "A table that contains APIPE service information."
    ::= { tmnxSvcObjs 7 }

svcApipeInfoEntry OBJECT-TYPE
    SYNTAX          SvcApipeInfoEntry
    MAX-ACCESS      not-accessible
    STATUS          current
    DESCRIPTION     "APIPE specific information about a service."
    INDEX           { svcId }
    ::= { svcApipeInfoTable 1 }

SvcApipeInfoEntry ::=
    SEQUENCE {
        svcApipeInterworking            INTEGER,
        svcApipeSignaledVllTypeOverride INTEGER
    }

svcApipeInterworking OBJECT-TYPE
    SYNTAX          INTEGER {
                        none              (1),
                        frf-5             (2),
                        frf-8-2-translate (3)
                    }
    MAX-ACCESS      read-write
    STATUS          current
    DESCRIPTION     "The value of the object svcApipeInterworking specifies the
                     interworking function that should be applied for packets
                     that ingress/egress SAPs that are part of a APIPE
                     service."
    DEFVAL          { none }
    ::= { svcApipeInfoEntry 1 }

svcApipeSignaledVllTypeOverride OBJECT-TYPE
    SYNTAX          INTEGER {
                      none(0),
                      atmVcc(8)
                    }
    MAX-ACCESS      read-write
    STATUS          current
    DESCRIPTION     "The value of object svcApipeSignaledVllTypeOverride
                     specifies the type of pseudo-wire (PW) signaling configured
                     to override the PW signaling specified by object svcVllType
                     for the APIPE VLL service.

                     Value 'none(0)' specifies that there is no configured
                     override of the PW signaling for the APIPE VLL service.

                     Value 'atmVcc(8)' specifies that the configured PW
                     signaling for override is of type '0x0009 N:1 VCC cell'
                     within an APIPE VLL service. Value 'atmVcc(8)' is allowed
                     only if all of the following conditions have been met:

                     1) An ATM SAP associated with the APIPE VLL service has an
                        assigned connection profile, found in
                        TIMETRA-CONN-PROF-MIB::tmnxConnProfTable.
                     2) svcVllType is equal to 'atmCell(7)'.
                     3) svcVcSwitching is equal to 'false'.

                     Otherwise, an 'inconsistentValue' error is returned.
                     If the above 3 conditions are satisfied,
                     svcApipeSignaledVllTypeOverride is set to 'atmVcc(8)'
                     and the ATM service is operational, the override is
                     triggered."
    DEFVAL          { none }
    ::= { svcApipeInfoEntry 2 }

-- ------------------------------------
-- TLS MFIB Information Table
-- ------------------------------------
tlsMFibInfoTable OBJECT-TYPE
    SYNTAX          SEQUENCE OF TlsMFibInfoEntry
    MAX-ACCESS      not-accessible
    STATUS          obsolete
    DESCRIPTION     "tlsMFibInfoTable contains the IPv4 Multicast FIB for
                     this Tls.
                     
                     This table was made obsolete in the 6.0 release.
                     It is replaced by tlsMFibTable."
    ::= { tmnxSvcObjs 8 }

tlsMFibInfoEntry OBJECT-TYPE
    SYNTAX          TlsMFibInfoEntry
    MAX-ACCESS      not-accessible
    STATUS          obsolete
    DESCRIPTION     "An  entry in the tlsMFibInfoTable. Each entry indicates
                     whether  traffic from a certain source to a certain
                     multicast destination (group) needs to be forwarded or
                     blocked on the indicated SAP/SDP."
    INDEX           { svcId,
                      tlsMFibInfoGrpAddr,
                      tlsMFibInfoSrcAddr,
                      tlsMFibInfoLocale,
                      tlsMFibInfoPortId,
                      tlsMFibInfoEncapValue,
                      tlsMFibInfoSdpId,
                      tlsMFibInfoVcId }

    ::= { tlsMFibInfoTable 1 }

TlsMFibInfoEntry ::=
    SEQUENCE {
        tlsMFibInfoGrpAddr      IpAddress,
        tlsMFibInfoSrcAddr      IpAddress,
        tlsMFibInfoLocale       MfibLocation,
        tlsMFibInfoPortId       TmnxPortID,
        tlsMFibInfoEncapValue   TmnxEncapVal,
        tlsMFibInfoSdpId        SdpId,
        tlsMFibInfoVcId         Unsigned32,
        tlsMFibInfoFwdOrBlk     MfibGrpSrcFwdOrBlk,
        tlsMFibInfoSvcId        TmnxServId
    }

tlsMFibInfoGrpAddr OBJECT-TYPE
    SYNTAX          IpAddress
    MAX-ACCESS      not-accessible
    STATUS          obsolete
    DESCRIPTION     "The value of the object tlsMFibInfoGrpAddr indicates the
                     IPv4 multicast destination address for which this table
                     entry contains information."
    ::= { tlsMFibInfoEntry 1 }

tlsMFibInfoSrcAddr OBJECT-TYPE
    SYNTAX          IpAddress
    MAX-ACCESS      not-accessible
    STATUS          obsolete
    DESCRIPTION     "tlsMFibInfoSrcAddr indicates the IPv4 unicast source
                     address for which this table entry contains information."
    ::= { tlsMFibInfoEntry 2 }

tlsMFibInfoLocale OBJECT-TYPE
    SYNTAX          MfibLocation
    MAX-ACCESS      not-accessible
    STATUS          obsolete
    DESCRIPTION     "tlsMFibInfoLocale indicates if the information in
                     this entry pertains to a 'sap' or to an 'sdp'."
    ::= { tlsMFibInfoEntry 3 }

tlsMFibInfoPortId OBJECT-TYPE
    SYNTAX          TmnxPortID
    MAX-ACCESS      not-accessible
    STATUS          obsolete
    DESCRIPTION     "When the value of tlsMFibInfoLocale is 'sap', the object
                     tlsMFibInfoPortId along with the object
                     tlsMFibInfoEncapValue, indicates the SAP for which this
                     entry contains information. This object is otherwise
                     insignificant and contains the value 0."
    ::= { tlsMFibInfoEntry 4 }

tlsMFibInfoEncapValue OBJECT-TYPE
    SYNTAX          TmnxEncapVal
    MAX-ACCESS      not-accessible
    STATUS          obsolete
    DESCRIPTION     "When the value of tlsMFibInfoLocale is 'sap', the object
                     tlsMFibInfoEncapValue, along with the object
                     tlsMFibInfoPortId, indicates the SAP for which this entry
                     contains information. This object is otherwise
                     insignificant and contains the value 0."
    ::= { tlsMFibInfoEntry 5 }

tlsMFibInfoSdpId OBJECT-TYPE
    SYNTAX          SdpId
    MAX-ACCESS      not-accessible
    STATUS          obsolete
    DESCRIPTION     "When the value of tlsMFibInfoLocale is 'sdp', the object
                     tlsMFibInfoSdpId, along with tlsMFibInfoVcId, indicates
                     the SDP Binding for which this entry contains information.
                     This object is otherwise insignificant and contains the
                     value 0."
    ::= { tlsMFibInfoEntry 6 }

tlsMFibInfoVcId OBJECT-TYPE
    SYNTAX          Unsigned32
    MAX-ACCESS      not-accessible
    STATUS          obsolete
    DESCRIPTION     "When the value of tlsMFibInfoLocale is 'sdp', the object
                     tlsMFibInfoVcId, along with tlsMFibInfoSdpId, indicates
                     the SDP Binding for which this entry contains information.
                     This object is otherwise insignificant and contains the
                     value 0."
    ::= { tlsMFibInfoEntry 7 }

tlsMFibInfoFwdOrBlk OBJECT-TYPE
    SYNTAX          MfibGrpSrcFwdOrBlk
    MAX-ACCESS      read-only
    STATUS          obsolete
    DESCRIPTION     "tlsMFibInfoFwdOrBlk indicates if traffic for the
                     indicated (S,G) pair will be blocked or forwarded on the
                     indicated SAP or SDP."
    ::= { tlsMFibInfoEntry 8 }

tlsMFibInfoSvcId OBJECT-TYPE
    SYNTAX          TmnxServId
    MAX-ACCESS      read-only
    STATUS          obsolete
    DESCRIPTION     "tlsMFibInfoSvcId indicates the TLS service to which
                     the indicated SAP or SDP belongs."
    ::= { tlsMFibInfoEntry 9 }

-- ----------------------------------------
-- TLS MFIB Group Source Statistics Table
-- ----------------------------------------
tlsMFibGrpSrcStatsTable OBJECT-TYPE
    SYNTAX          SEQUENCE OF TlsMFibGrpSrcStatsEntry
    MAX-ACCESS      not-accessible
    STATUS          obsolete
    DESCRIPTION     "tlsMFibGrpSrcStatsTable contains statistics for the
                     entries in the IPv4 Multicast FIB for this Tls. These
                     statistics are collected by the forwarding engine.
                     
                     This table was made obsolete in the 6.0 release.
                     It is replaced by tlsMFibStatsTable."
    ::= { tmnxSvcObjs 9 }

tlsMFibGrpSrcStatsEntry OBJECT-TYPE
    SYNTAX          TlsMFibGrpSrcStatsEntry
    MAX-ACCESS      not-accessible
    STATUS          obsolete
    DESCRIPTION     "An entry in the tlsMFibGrpSrcStatsTable."
    INDEX           { svcId,
                      tlsMFibGrpSrcStatsGrpAddr,
                      tlsMFibGrpSrcStatsSrcAddr }
    ::= { tlsMFibGrpSrcStatsTable 1 }

TlsMFibGrpSrcStatsEntry ::=
    SEQUENCE {
        tlsMFibGrpSrcStatsGrpAddr          IpAddress,
        tlsMFibGrpSrcStatsSrcAddr          IpAddress,
        tlsMFibGrpSrcStatsForwardedPkts    Counter64,
        tlsMFibGrpSrcStatsForwardedOctets  Counter64
    }

tlsMFibGrpSrcStatsGrpAddr OBJECT-TYPE
    SYNTAX          IpAddress
    MAX-ACCESS      not-accessible
    STATUS          obsolete
    DESCRIPTION     "tlsMFibGrpSrcStatsGrpAddr indicates the IPv4 multicast
                     destination address for which this table entry contains
                     information."
    ::= { tlsMFibGrpSrcStatsEntry 1 }

tlsMFibGrpSrcStatsSrcAddr OBJECT-TYPE
    SYNTAX          IpAddress
    MAX-ACCESS      not-accessible
    STATUS          obsolete
    DESCRIPTION     "tlsMFibGrpSrcStatsSrcAddr indicates the IPv4 unicast
                     source address for which this table entry contains
                     information."
    ::= { tlsMFibGrpSrcStatsEntry 2 }

tlsMFibGrpSrcStatsForwardedPkts OBJECT-TYPE
    SYNTAX          Counter64
    MAX-ACCESS      read-only
    STATUS          obsolete
    DESCRIPTION     "tlsMFibGrpSrcStatsForwardedPkts indicates the number of
                     IPv4 multicast packets that were forwarded to the SAPs
                     and SDPs listed in the tlsMFibInfoTable."
    ::= { tlsMFibGrpSrcStatsEntry 3 }

tlsMFibGrpSrcStatsForwardedOctets OBJECT-TYPE
    SYNTAX          Counter64
    MAX-ACCESS      read-only
    STATUS          obsolete
    DESCRIPTION     "tlsMFibGrpSrcStatsForwardedOctets indicates the number
                     of octets that were forwarded to the SAPs and SDPs
                     listed in the tlsMFibInfoTable."
    ::= { tlsMFibGrpSrcStatsEntry 4 }

-- --------------------------------
-- Redundant Group Table
-- --------------------------------
tlsRdntGrpTable OBJECT-TYPE
    SYNTAX          SEQUENCE OF TlsRdntGrpEntry
    MAX-ACCESS      not-accessible
    STATUS          current
    DESCRIPTION     "A table that contains TLS service Redundant Group
                     information.  There is no limit on the number of
                     Redundant Groups that can be created globally or
                     within a service."
    ::= {tmnxSvcObjs 10}

tlsRdntGrpEntry OBJECT-TYPE
    SYNTAX          TlsRdntGrpEntry
    MAX-ACCESS      not-accessible
    STATUS          current
    DESCRIPTION     "Redundant Group information"
    INDEX           { svcId, IMPLIED tlsRdntGrpName }
    ::= { tlsRdntGrpTable 1 }

TlsRdntGrpEntry ::=
    SEQUENCE {
        tlsRdntGrpName           TNamedItem,
        tlsRdntGrpRowStatus      RowStatus,
        tlsRdntGrpDescription    ServObjDesc,
        tlsRdntGrpLastMgmtChange TimeStamp
    }

tlsRdntGrpName OBJECT-TYPE
    SYNTAX          TNamedItem
    MAX-ACCESS      not-accessible
    STATUS          current
    DESCRIPTION     "The value of the object tlsRdntGrpName specifies the
                     name of the redundant group.
                     The name must be unique within a TLS, however the same
                     name can appear in different TLS services, in which
                     case they denote different redundant groups."
    ::= { tlsRdntGrpEntry 1 }

tlsRdntGrpRowStatus OBJECT-TYPE
    SYNTAX          RowStatus
    MAX-ACCESS      read-create
    STATUS          current
    DESCRIPTION     "The value of the object tlsRdntGrpRowStatus specifies
                     the status of this row. The only values supported are
                     'active', 'createAndGo' and 'destroy'."
    ::= { tlsRdntGrpEntry 2 }

tlsRdntGrpDescription OBJECT-TYPE
    SYNTAX          ServObjDesc
    MAX-ACCESS      read-create
    STATUS          current
    DESCRIPTION     "The value of the object tlsRdntGrpDescription specifies
                     generic information about this redundant group."
    DEFVAL          { ''H }
    ::= { tlsRdntGrpEntry 3 }

tlsRdntGrpLastMgmtChange OBJECT-TYPE
    SYNTAX          TimeStamp
    MAX-ACCESS      read-only
    STATUS          current
    DESCRIPTION     "The value of the object tlsRdntGrpLastMgmtChange
                     indicates the sysUpTime at the time of the most
                     recent management-initiated change to this redundant
                     group."
    ::= { tlsRdntGrpEntry 4 }

-- ---------------------------------
-- Redundant Group Member Table
-- ---------------------------------
tlsRdntGrpMemberTable OBJECT-TYPE
    SYNTAX          SEQUENCE OF TlsRdntGrpMemberEntry
    MAX-ACCESS      not-accessible
    STATUS          current
    DESCRIPTION     "A table that holds information about the members of
                     TLS redundant groups."
    ::= { tmnxSvcObjs 11 }

tlsRdntGrpMemberEntry OBJECT-TYPE
    SYNTAX          TlsRdntGrpMemberEntry
    MAX-ACCESS      not-accessible
    STATUS          current
    DESCRIPTION     "Redundant Group Member information."
    INDEX           { tlsRdntGrpName,
                      tlsRdntGrpMemberRemoteNodeAddrTp,
                      tlsRdntGrpMemberRemoteNodeAddr,
                      tlsRdntGrpMemberIsSap,
                      tlsRdntGrpMemberPort,
                      tlsRdntGrpMemberEncap
                    }
    ::= { tlsRdntGrpMemberTable 1 }

TlsRdntGrpMemberEntry ::=
    SEQUENCE {
        tlsRdntGrpMemberRemoteNodeAddrTp InetAddressType,
        tlsRdntGrpMemberRemoteNodeAddr   InetAddress,
        tlsRdntGrpMemberIsSap            TruthValue,
        tlsRdntGrpMemberPort             TmnxPortID,
        tlsRdntGrpMemberEncap            TmnxEncapVal,
        tlsRdntGrpMemberRowStatus        RowStatus,
        tlsRdntGrpMemberLastMgmtChange   TimeStamp
    }

tlsRdntGrpMemberRemoteNodeAddrTp OBJECT-TYPE
    SYNTAX          InetAddressType
    MAX-ACCESS      not-accessible
    STATUS          current
    DESCRIPTION     "The value of the object tlsRdntGrpMemberRemoteNodeAddrTp
                     specifies the addresstype of the remote ldp peer."
    ::= { tlsRdntGrpMemberEntry 1}

tlsRdntGrpMemberRemoteNodeAddr OBJECT-TYPE
    SYNTAX          InetAddress
    MAX-ACCESS      not-accessible
    STATUS          current
    DESCRIPTION     "The value of the object tlsRdntGrpMemberRemoteNodeAddr
                     specifies the ip address of the remote ldp peer."
    ::= { tlsRdntGrpMemberEntry 2}

tlsRdntGrpMemberIsSap OBJECT-TYPE
    SYNTAX          TruthValue
    MAX-ACCESS      not-accessible
    STATUS          current
    DESCRIPTION     "The value of the object tlsRdntGrpMemberIsSap
                     specifies whether the Port ID and Encap describe a sap
                     or a port (in which case Encap has no meaning)."
    ::= { tlsRdntGrpMemberEntry 3}

tlsRdntGrpMemberPort OBJECT-TYPE
    SYNTAX          TmnxPortID
    MAX-ACCESS      not-accessible
    STATUS          current
    DESCRIPTION     "When the value of tlsRdntGrpMemberIsSap is 'sap',
                     the value of the object  tlsRdntGrpMemberPort, along
                     with tlsRdntGrpMemberEncap, specifies
                     a SAP, otherwise a port (in which case
                     tlsRdntGrpMemberEncap is insignificant)."
    ::= { tlsRdntGrpMemberEntry 4}

tlsRdntGrpMemberEncap OBJECT-TYPE
    SYNTAX          TmnxEncapVal
    MAX-ACCESS      not-accessible
    STATUS          current
    DESCRIPTION     "When the value of tlsRdntGrpMemberIsSap is 'sap',
                     the value of the object  tlsRdntGrpMemberEncap, along
                     with tlsRdntGrpMemberPort, specifies a SAP. This object
                     is otherwise insignificant and  should contain a
                     value of 0."
    ::= { tlsRdntGrpMemberEntry 5}

tlsRdntGrpMemberRowStatus OBJECT-TYPE
    SYNTAX          RowStatus
    MAX-ACCESS      read-create
    STATUS          current
    DESCRIPTION     "The value of the object tlsRdntGrpMemberRowStatus
                     specifies the status of this row. The
                     only values supported are 'active', 'createAndGo'
                     and 'destroy'."
    ::= { tlsRdntGrpMemberEntry 6 }

tlsRdntGrpMemberLastMgmtChange OBJECT-TYPE
    SYNTAX          TimeStamp
    MAX-ACCESS      read-only
    STATUS          current
    DESCRIPTION     "The value of the object tlsRdntGrpMemberLastMgmtChange
                     indicates the time of the most recent management-initiated
                     change to this redundant group member."
    ::= { tlsRdntGrpMemberEntry 7}


-- -----------------------------------------
-- TLS MSTI Table
-- -----------------------------------------
tlsMstiTable OBJECT-TYPE
    SYNTAX          SEQUENCE OF TlsMstiEntry
    MAX-ACCESS      not-accessible
    STATUS          current
    DESCRIPTION     "A table that contains Multiple Spanning Tree Instance
                     (MSTI) information. Each management VPLS running MSTP can
                     have upto 15 MSTI, not including the CIST."
    ::= { tmnxSvcObjs 12 }

tlsMstiEntry OBJECT-TYPE
    SYNTAX          TlsMstiEntry
    MAX-ACCESS      not-accessible
    STATUS          current
    DESCRIPTION     "Information about a specific MSTI."
    INDEX           { svcId, tlsMstiInstanceId}
    ::= { tlsMstiTable 1 }

TlsMstiEntry ::=
    SEQUENCE {
        tlsMstiInstanceId        MstiInstanceId,
        tlsMstiRowStatus         RowStatus,
        tlsMstiPriority          Integer32,
        tlsMstiLastMgmtChange    TimeStamp,
        tlsMstiRegionalRoot      BridgeId,
        tlsMstiIntRootCost       Integer32,
        tlsMstiRemainingHopCount Integer32,
        tlsMstiRegionalRootPort  Integer32
    }

tlsMstiInstanceId OBJECT-TYPE
    SYNTAX          MstiInstanceId
    MAX-ACCESS      not-accessible
    STATUS          current
    DESCRIPTION     "The value of the object tlsMstiInstanceId specifies the
                     Multiple Spanning Tree Instance."
    ::= { tlsMstiEntry 1 }


tlsMstiRowStatus OBJECT-TYPE
    SYNTAX          RowStatus
    MAX-ACCESS      read-create
    STATUS          current
    DESCRIPTION     "The value of the object tlsMstiRowStatus specifies the
                     status of this row.
                     The only values supported during a set operation are
                     'active', 'createAndGo' and 'destroy'."
    ::= { tlsMstiEntry 2 }

tlsMstiPriority OBJECT-TYPE
    SYNTAX          Integer32 (0..65535)
    MAX-ACCESS      read-create
    STATUS          current
    DESCRIPTION     "The value of the object tlsMstiPriority specifies the
                     priority of this spcecific Multiple Spanning Tree
                     Instance for this service.
                     It is used as the highest 4 bits of the Bridge ID
                     included in the MSTP BPDU's generated by
                     this bridge.
                     The tlsMstiPriority can only take-on values which
                     multiples of 4096 (4k). If a value is specified which
                     is not a multiple of 4K, then this value will be
                     replaced by the closest multiple of 4K which is lower
                     then the value entered."
    DEFVAL          { 32768 }
    ::= { tlsMstiEntry 3 }

tlsMstiLastMgmtChange OBJECT-TYPE
    SYNTAX          TimeStamp
    MAX-ACCESS      read-only
    STATUS          current
    DESCRIPTION     "The value of the object tlsMstiLastMgmtChange indicates
                     the value of sysUpTime at the time of the most recent
                     management-initiated change to this MSTI."
    ::= { tlsMstiEntry 4 }

tlsMstiRegionalRoot OBJECT-TYPE
    SYNTAX          BridgeId
    MAX-ACCESS      read-only
    STATUS          current
    DESCRIPTION     "The value of the object tlsMstiRegionalRoot
                     indicates the bridge identifier of the regional root of
                     the MSTI spanning tree as determined by the Spanning Tree
                     Protocol instance associated with this service. This value
                     is used as the CIST Regional Root Identifier parameter in
                     all MSTP BPDUs originated by this node."
    ::= { tlsMstiEntry 5 }

tlsMstiIntRootCost OBJECT-TYPE
    SYNTAX          Integer32
    MAX-ACCESS      read-only
    STATUS          current
    DESCRIPTION     "The value of the object tlsMstiIntRootCost indicates the
                     cost of the path to the regional root bridge as seen from
                     this bridge."
    ::= { tlsMstiEntry 6 }

tlsMstiRemainingHopCount OBJECT-TYPE
    SYNTAX          Integer32
    MAX-ACCESS      read-only
    STATUS          current
    DESCRIPTION     "The value of the object tlsMstiRemainingHopCount
                     specifies the remaining number of hops."
    ::= { tlsMstiEntry 7 }

tlsMstiRegionalRootPort OBJECT-TYPE
    SYNTAX          Integer32
    MAX-ACCESS      read-only
    STATUS          current
    DESCRIPTION     "The value of the object tlsMstiRegionalRootPort indicates
                     the port number of the port which offers the lowest cost
                     path from this bridge to the regional root bridge."
    ::= { tlsMstiEntry 8 }

-- -----------------------------------------
-- TLS MSTI Managed VLAN List Table
-- -----------------------------------------
tlsMstiManagedVlanListTable OBJECT-TYPE
    SYNTAX          SEQUENCE OF TlsMstiManagedVlanListEntry
    MAX-ACCESS      not-accessible
    STATUS          current
    DESCRIPTION     "This table is used only for a management VPLS when MSTP
                     is running. It indicates for each multiple spanning tree
                     instance the ranges of associated VLANs that will be
                     affected when a certain SAP changes state."
    ::= { tmnxSvcObjs 13 }

tlsMstiManagedVlanListEntry OBJECT-TYPE
    SYNTAX          TlsMstiManagedVlanListEntry
    MAX-ACCESS      not-accessible
    STATUS          current
    DESCRIPTION     "Each row specifies a range of VLANS associated
                     with a SAP of a MVPLS. Ranges may contains overlapping
                     sections only for Mvpls SAPs that belong to the same
                     service."
    INDEX           { svcId,
                      tlsMstiInstanceId,
                      tlsMstiMvplsMinVlanTag,
                      tlsMstiMvplsMaxVlanTag }
    ::= { tlsMstiManagedVlanListTable 1 }

TlsMstiManagedVlanListEntry ::=
    SEQUENCE {
        tlsMstiMvplsMinVlanTag  QTag, -- integer(1 .. 4094)
        tlsMstiMvplsMaxVlanTag  QTag,
        tlsMstiMvplsRowStatus   RowStatus
    }

tlsMstiMvplsMinVlanTag OBJECT-TYPE
    SYNTAX          QTag
    MAX-ACCESS      not-accessible
    STATUS          current
    DESCRIPTION     "The value of tlsMstiMvplsMinVlanTag specifies
                     the left bound (i.e. min. value) of a range of VLANs
                     that are associated with the Mvpls SAP.
                     tlsMstiMvplsMinVlanTag must be smaller than (or equal
                     to) tlsMstiMvplsMaxVlanTag."
    ::= { tlsMstiManagedVlanListEntry 1 }

tlsMstiMvplsMaxVlanTag OBJECT-TYPE
    SYNTAX          QTag
    MAX-ACCESS      not-accessible
    STATUS          current
    DESCRIPTION     "The value of tlsMstiMvplsMaxVlanTag specifies the
                     right bound (i.e. max. value) of a range of VLANs that
                     are associated with the Mvpls SAP."
    ::= { tlsMstiManagedVlanListEntry 2 }

tlsMstiMvplsRowStatus OBJECT-TYPE
    SYNTAX           RowStatus
    MAX-ACCESS       read-create
    STATUS           current
    DESCRIPTION      "The value of tlsMstiMvplsRowStatus specifies
                      the status of this row. The only values supported
                      during a set operation are 'active', 'createAndGo' and
                      'destroy'."
    ::= { tlsMstiManagedVlanListEntry 3 }

-- -----------------------------------------
-- TLS Egress Multicast Group Table
-- -----------------------------------------
tlsEgressMulticastGroupTable OBJECT-TYPE
    SYNTAX          SEQUENCE OF TlsEgressMulticastGroupEntry
    MAX-ACCESS      not-accessible
    STATUS          current
    DESCRIPTION     "This table is used to manage VPLS Egress Multicast
                     Groups. These groups are used to group together VPLS
                     SAP's in order to improve the efficiency of the egress
                     multicast replication process."
    ::= { tmnxSvcObjs 14 }

tlsEgressMulticastGroupEntry OBJECT-TYPE
    SYNTAX          TlsEgressMulticastGroupEntry
    MAX-ACCESS      not-accessible
    STATUS          current
    DESCRIPTION     "An entry containing management information applicable
                     to a particular VPLS Egress Multicast Group."
    INDEX           { IMPLIED tlsEgrMcGrpName }
    ::= { tlsEgressMulticastGroupTable 1 }

TlsEgressMulticastGroupEntry ::=
    SEQUENCE {
        tlsEgrMcGrpName                 TNamedItem,
        tlsEgrMcGrpRowStatus            RowStatus,
        tlsEgrMcGrpLastMgmtChange       TimeStamp,
        tlsEgrMcGrpDescription          ServObjDesc,
        tlsEgrMcGrpChainLimit           Unsigned32,
        tlsEgrMcGrpEncapType            INTEGER,
        tlsEgrMcGrpDot1qEtherType       Unsigned32,
        tlsEgrMcGrpMacFilterId          TFilterID,
        tlsEgrMcGrpIpFilterId           TFilterID,
        tlsEgrMcGrpIpv6FilterId         TFilterID,
        tlsEgrMcGrpQinqEtherType        Unsigned32,
        tlsEgrMcGrpQinqFixedTagPosition INTEGER,
        tlsEgrMcGrpAdminQinqFixedTagVal Unsigned32,
        tlsEgrMcGrpOperQinqFixedTagVal  Unsigned32
    }

tlsEgrMcGrpName OBJECT-TYPE
    SYNTAX          TNamedItem
    MAX-ACCESS      not-accessible
    STATUS          current
    DESCRIPTION     "The value of tlsEgrMcGrpName indicates the name of
                     the Egress Multicast Group."
    ::= { tlsEgressMulticastGroupEntry 1 }

tlsEgrMcGrpRowStatus OBJECT-TYPE
    SYNTAX          RowStatus
    MAX-ACCESS      read-create
    STATUS          current
    DESCRIPTION     "The value of tlsEgrMcGrpRowStatus controls the creation
                     and deletion of rows in this table."
    ::= { tlsEgressMulticastGroupEntry 2 }

tlsEgrMcGrpLastMgmtChange OBJECT-TYPE
    SYNTAX          TimeStamp
    MAX-ACCESS      read-only
    STATUS          current
    DESCRIPTION     "The value of tlsEgrMcGrpLastMgmtChange indicates the
                     value of sysUpTime at the time of the last management
                     change of any writable object of this row."
    ::= { tlsEgressMulticastGroupEntry 3 }

tlsEgrMcGrpDescription OBJECT-TYPE
    SYNTAX          ServObjDesc
    MAX-ACCESS      read-create
    STATUS          current
    DESCRIPTION     "Generic information about this Egress Multicast Group."
    DEFVAL          { "" }
    ::= { tlsEgressMulticastGroupEntry 4 }

tlsEgrMcGrpChainLimit OBJECT-TYPE
    SYNTAX          Unsigned32 (1..30)
    MAX-ACCESS      read-create
    STATUS          current
    DESCRIPTION     "The value of tlsEgrMcGrpChainLimit specifies the maximum
                     number of SAP's that can be placed together in a single
                     chain on this Egress Multicast Group."
    DEFVAL          { 16 }
    ::= { tlsEgressMulticastGroupEntry 5 }

tlsEgrMcGrpEncapType OBJECT-TYPE
    SYNTAX          INTEGER {
                        unknown   (0),
                        nullEncap (1),
                        qEncap    (2),
                        qinqEncap (10)
                    }
    MAX-ACCESS      read-create
    STATUS          current
    DESCRIPTION     "The value of tlsEgrMcGrpEncapType specifies the common
                     service encapsulation type used by all the SAP's on this
                     Egress Multicast Group."
    DEFVAL          { nullEncap }
    ::= { tlsEgressMulticastGroupEntry 6 }

tlsEgrMcGrpDot1qEtherType OBJECT-TYPE
    SYNTAX          Unsigned32 ('600'H..'ffff'H)
    MAX-ACCESS      read-create
    STATUS          current
    DESCRIPTION     "The value of tlsEgrMcGrpDot1qEtherType specifies the
                     common ethertype value used by all the 802.1Q SAP's on
                     this Egress Multicast Group."
    DEFVAL          { '8100'H }
    ::= { tlsEgressMulticastGroupEntry 7 }

tlsEgrMcGrpMacFilterId OBJECT-TYPE
    SYNTAX          TFilterID
    MAX-ACCESS      read-create
    STATUS          current
    DESCRIPTION     "The value of tlsEgrMcGrpMacFilterId specifies the common
                     egress MAC filter ID used by all the SAP's on this
                     Egress Multicast Group."
    DEFVAL          { 0 }
    ::= { tlsEgressMulticastGroupEntry 8 }

tlsEgrMcGrpIpFilterId OBJECT-TYPE
    SYNTAX          TFilterID
    MAX-ACCESS      read-create
    STATUS          current
    DESCRIPTION     "The value of tlsEgrMcGrpIpFilterId specifies the common
                     egress IP filter ID used by all the SAP's on this
                     Egress Multicast Group."
    DEFVAL          { 0 }
    ::= { tlsEgressMulticastGroupEntry 9 }

tlsEgrMcGrpIpv6FilterId OBJECT-TYPE
    SYNTAX          TFilterID
    MAX-ACCESS      read-create
    STATUS          current
    DESCRIPTION     "The value of tlsEgrMcGrpIpv6FilterId specifies the common
                     egress IPv6 filter ID used by all the SAP's on this
                     Egress Multicast Group."
    DEFVAL          { 0 }
    ::= { tlsEgressMulticastGroupEntry 10 }

tlsEgrMcGrpQinqEtherType OBJECT-TYPE
    SYNTAX          Unsigned32 ('600'H..'ffff'H)
    MAX-ACCESS      read-create
    STATUS          current
    DESCRIPTION     "The value of tlsEgrMcGrpQinqEtherType specifies the
                     common ethertype value used by all the 'QinQ' SAP's in
                     this Egress Multicast Group."
    DEFVAL          { '8100'H }
    ::= { tlsEgressMulticastGroupEntry 11 }

tlsEgrMcGrpQinqFixedTagPosition OBJECT-TYPE
    SYNTAX          INTEGER {
                        topTag    (2),   -- top (outter) tag is fixed
                        bottomTag (3)    -- bottom (inner) tag is fixed
                    }
    MAX-ACCESS      read-create
    STATUS          current
    DESCRIPTION     "The value of tlsEgrMcGrpQinqFixedTagPosition specifies
                     the common position of the fixed 802.1Q tag of all the
                     'QinQ' SAP's in this Egress Multicast Group. This object
                     has no meaning when the value of tlsEgrMcGrpEncapType
                     is not 'qinqEncap'."
    DEFVAL          { bottomTag }
    ::= { tlsEgressMulticastGroupEntry 12 }

tlsEgrMcGrpAdminQinqFixedTagVal OBJECT-TYPE
    SYNTAX          Unsigned32 (0|1..4094)
    MAX-ACCESS      read-create
    STATUS          current
    DESCRIPTION     "The value of tlsEgrMcGrpAdminQinqFixedTagVal 
                     specifies the provisioned common value of the fixed 
                     802.1Q tag of all the 'QinQ' SAP's in this Egress 
                     Multicast Group.

                     The value 0 is used to indicate that the actual value 
                     of the fixed tag will be defined implicitly by the 
                     corresponding tag of the first SAP added to this Egress
                     Multicast Group."
    DEFVAL          { 0 }
    ::= { tlsEgressMulticastGroupEntry 13 } 

tlsEgrMcGrpOperQinqFixedTagVal OBJECT-TYPE
    SYNTAX          Unsigned32
    MAX-ACCESS      read-only
    STATUS          current
    DESCRIPTION     "The value of tlsEgrMcGrpOperQinqFixedTagVal 
                     specifies the operating common value of the fixed 
                     802.1Q tag of all the 'QinQ' SAP's in this Egress 
                     Multicast Group."
    ::= { tlsEgressMulticastGroupEntry 14 }

-- ----------------------------------------------------------------------------
-- DHCP Lease State Table
--
-- This table is replaced with the svcDhcpLeaseTable
--
-- ----------------------------------------------------------------------------
svcDhcpLeaseStateTable OBJECT-TYPE
    SYNTAX          SEQUENCE OF SvcDhcpLeaseStateEntry
    MAX-ACCESS      not-accessible
    STATUS          obsolete
    DESCRIPTION     "A table that contains DHCP lease states."
    ::= { tmnxSvcObjs 16 }

svcDhcpLeaseStateEntry OBJECT-TYPE
    SYNTAX          SvcDhcpLeaseStateEntry
    MAX-ACCESS      not-accessible
    STATUS          obsolete
    DESCRIPTION     "Information about a specific DHCP lease state."
    INDEX           { svcId,
                      svcDhcpLseStateCiAddrType,
                      svcDhcpLseStateCiAddr }
    ::= { svcDhcpLeaseStateTable 1 }

SvcDhcpLeaseStateEntry ::=
    SEQUENCE {
        svcDhcpLseStateCiAddrType           InetAddressType,
        svcDhcpLseStateCiAddr               InetAddress,
        svcDhcpLseStateLocale               INTEGER,
        svcDhcpLseStatePortId               TmnxPortID,
        svcDhcpLseStateEncapValue           TmnxEncapVal,
        svcDhcpLseStateSdpId                SdpId,
        svcDhcpLseStateVcId                 Unsigned32,
        svcDhcpLseStateChAddr               MacAddress,
        svcDhcpLseStateRemainLseTime        Unsigned32,
        svcDhcpLseStateOption82             OCTET STRING,
        svcDhcpLseStatePersistKey           Unsigned32,
        svcDhcpLseStateSubscrIdent          DisplayString,
        svcDhcpLseStateSubProfString        DisplayString,
        svcDhcpLseStateSlaProfString        DisplayString,
        svcDhcpLseStateShcvOperState        INTEGER,
        svcDhcpLseStateShcvChecks           Unsigned32,
        svcDhcpLseStateShcvReplies          Unsigned32,
        svcDhcpLseStateShcvReplyTime        TimeStamp,
        svcDhcpLseStateClientId             OCTET STRING,
        svcDhcpLseStateIAID                 Unsigned32,
        svcDhcpLseStateIAIDType             IAIDType,
        svcDhcpLseStateCiAddrMaskLen        Unsigned32,
        svcDhcpLseStateRetailerSvcId        TmnxServId,
        svcDhcpLseStateRetailerIf           InterfaceIndexOrZero,
        svcDhcpLseStateAncpString           DisplayString,
        svcDhcpLseStateFramedIpNetMaskTp    InetAddressType,
        svcDhcpLseStateFramedIpNetMask      InetAddress,
        svcDhcpLseStateBCastIpAddrType      InetAddressType,
        svcDhcpLseStateBCastIpAddr          InetAddress,
        svcDhcpLseStateDefaultRouterTp      InetAddressType,
        svcDhcpLseStateDefaultRouter        InetAddress,
        svcDhcpLseStatePrimaryDnsType       InetAddressType,
        svcDhcpLseStatePrimaryDns           InetAddress,
        svcDhcpLseStateSecondaryDnsType     InetAddressType,
        svcDhcpLseStateSecondaryDns         InetAddress,
        svcDhcpLseStateSessionTimeout       Unsigned32,
        svcDhcpLseStateServerLeaseStart     DateAndTime,
        svcDhcpLseStateServerLastRenew      DateAndTime,
        svcDhcpLseStateServerLeaseEnd       DateAndTime,
        svcDhcpLseStateDhcpServerAddrType   InetAddressType,
        svcDhcpLseStateDhcpServerAddr       InetAddress,
        svcDhcpLseStateOriginSubscrId       DhcpLseStateInfoOrigin,
        svcDhcpLseStateOriginStrings        DhcpLseStateInfoOrigin,
        svcDhcpLseStateOriginLeaseInfo      DhcpLseStateInfoOrigin,
        svcDhcpLseStateDhcpClientAddrType   InetAddressType,
        svcDhcpLseStateDhcpClientAddr       InetAddress,
        svcDhcpLseStateLeaseSplitActive     TruthValue,
        svcDhcpLseStateInterDestId          DisplayString,
        svcDhcpLseStatePrimaryNbnsType      InetAddressType,
        svcDhcpLseStatePrimaryNbns          InetAddress,
        svcDhcpLseStateSecondaryNbnsType    InetAddressType,
        svcDhcpLseStateSecondaryNbns        InetAddress,
        svcDhcpLseStateAppProfString        DisplayString,
        svcDhcpLseStateNextHopMacAddr       MacAddress,
        svcDhcpLseStateCategoryMapName      TNamedItemOrEmpty,
        svcDhcpLseStateNakNextRenew         TruthValue,
        svcDhcpLseStateRadiusClassAttr      OCTET STRING,
        svcDhcpLseStateRadiusUserName       DisplayString
    }

svcDhcpLseStateCiAddrType OBJECT-TYPE
    SYNTAX          InetAddressType
    MAX-ACCESS      not-accessible
    STATUS          obsolete
    DESCRIPTION     "The value of svcDhcpLseStateCiAddrType indicates the
                     address type of svcDhcpLseStateCiAddr."
    ::= { svcDhcpLeaseStateEntry 1 }

svcDhcpLseStateCiAddr OBJECT-TYPE
    SYNTAX          InetAddress (SIZE(4|16))
    MAX-ACCESS      not-accessible
    STATUS          obsolete
    DESCRIPTION     "The value of svcDhcpLseStateCiAddr indicates the IP
                     address of the DHCP lease state."
    ::= { svcDhcpLeaseStateEntry 2 }

svcDhcpLseStateLocale OBJECT-TYPE
    SYNTAX          INTEGER {
                        sap (1),
                        sdp (2)
                    }
    MAX-ACCESS      read-only
    STATUS          obsolete
    DESCRIPTION     "The value of svcDhcpLseStateLocale specifies if the DHCP
                     lease state is learned via a SAP or SDP."
    ::= { svcDhcpLeaseStateEntry 3 }

svcDhcpLseStatePortId OBJECT-TYPE
    SYNTAX          TmnxPortID
    MAX-ACCESS      read-only
    STATUS          obsolete
    DESCRIPTION     "When the value of svcDhcpLseStateLocale is 'sap', the
                     object svcDhcpLseStatePortId along with the object
                     svcDhcpLseStateEncapValue, indicates the SAP for which
                     this entry contains information. This object is otherwise
                     insignificant and contains the value 0."
    ::= { svcDhcpLeaseStateEntry 4 }

svcDhcpLseStateEncapValue OBJECT-TYPE
    SYNTAX          TmnxEncapVal
    MAX-ACCESS      read-only
    STATUS          obsolete
    DESCRIPTION     "When the value of svcDhcpLseStateLocale is 'sap', the
                     object svcDhcpLseStatePortId along with the object
                     svcDhcpLseStateEncapValue, indicates the SAP for which
                     this entry contains information. This object is otherwise
                     insignificant and contains the value 0."
    ::= { svcDhcpLeaseStateEntry 5 }

svcDhcpLseStateSdpId OBJECT-TYPE
    SYNTAX          SdpId
    MAX-ACCESS      read-only
    STATUS          obsolete
    DESCRIPTION     "When the value of svcDhcpLseStateLocale is 'sdp', the
                     object svcDhcpLseStateSdpId, along with the object
                     svcDhcpLseStateVcId, indicates the SDP Binding for which
                     this entry contains information. This object is otherwise
                     insignificant and contains the value 0."
    ::= { svcDhcpLeaseStateEntry 6 }

svcDhcpLseStateVcId OBJECT-TYPE
    SYNTAX          Unsigned32
    MAX-ACCESS      read-only
    STATUS          obsolete
    DESCRIPTION     "When the value of svcDhcpLseStateLocale is 'sdp', the
                     object svcDhcpLseStateSdpId, along with the object
                     svcDhcpLseStateVcId, indicates the SDP Binding for which
                     this entry contains information. This object is otherwise
                     insignificant and contains the value 0."
    ::= { svcDhcpLeaseStateEntry 7 }

svcDhcpLseStateChAddr OBJECT-TYPE
    SYNTAX          MacAddress
    MAX-ACCESS      read-only
    STATUS          obsolete
    DESCRIPTION     "The value of svcDhcpLseStateChAddr indicates the MAC
                     address of the DHCP lease state."
    ::= { svcDhcpLeaseStateEntry 8 }

svcDhcpLseStateRemainLseTime OBJECT-TYPE
    SYNTAX          Unsigned32
    UNITS           "seconds"
    MAX-ACCESS      read-only
    STATUS          obsolete
    DESCRIPTION     "The value of svcDhcpLseStateRemainLseTime indicates the
                     remaining lease time of the DHCP lease state."
    ::= { svcDhcpLeaseStateEntry 9 }

svcDhcpLseStateOption82 OBJECT-TYPE
    SYNTAX          OCTET STRING
    MAX-ACCESS      read-only
    STATUS          obsolete
    DESCRIPTION     "The value of svcDhcpLseStateOption82 indicates the content
                     of option 82 for this DHCP lease state."
    ::= { svcDhcpLeaseStateEntry 10 }

svcDhcpLseStatePersistKey OBJECT-TYPE
    SYNTAX          Unsigned32
    MAX-ACCESS      read-only
    STATUS          obsolete
    DESCRIPTION     "The value of svcDhcpLseStatePersistKey indicates a key
                     value that can be used to track this lease state in the
                     persistence file."
    ::= { svcDhcpLeaseStateEntry 11 }

svcDhcpLseStateSubscrIdent OBJECT-TYPE
    SYNTAX          DisplayString
    MAX-ACCESS      read-only
    STATUS          obsolete
    DESCRIPTION     "The value of svcDhcpLseStateSubscrIdent indicates the
                     id of the parent subscriber of this DHCP lease state.
                     
                     The value of svcDhcpLseStateOriginSubscrId indicates
                     whether this subscriber identification was received from
                     the DHCP or from the Radius server."
    ::= { svcDhcpLeaseStateEntry 12 }

svcDhcpLseStateSubProfString OBJECT-TYPE
    SYNTAX          DisplayString
    MAX-ACCESS      read-only
    STATUS          obsolete
    DESCRIPTION     "The value of svcDhcpLseStateSubProfString indicates the
                     subscriber profile string applicable for this DHCP lease
                     state.
                     
                     The value of svcDhcpLseStateOriginStrings indicates
                     whether this subscriber profile string was received from
                     the DHCP or from the Radius server."
    ::= { svcDhcpLeaseStateEntry 13 }

svcDhcpLseStateSlaProfString OBJECT-TYPE
    SYNTAX          DisplayString
    MAX-ACCESS      read-only
    STATUS          obsolete
    DESCRIPTION     "The value of svcDhcpLseStateSlaProfString indicates the
                     SLA profile string applicable for this DHCP lease state.
                     
                     The value of svcDhcpLseStateOriginStrings indicates
                     whether this SLA profile string was received from
                     the DHCP or from the Radius server."
    ::= { svcDhcpLeaseStateEntry 14 }

svcDhcpLseStateShcvOperState OBJECT-TYPE
    SYNTAX          INTEGER{
                        disabled  (1),
                        undefined (2),
                        down      (3),
                        up        (4)
                    }
    MAX-ACCESS      read-only
    STATUS          obsolete
    DESCRIPTION     "The value of svcDhcpLseStateShcvOperState indicates the
                     state of the subscriber host connectivity check for
                     this DHCP lease state."
    ::= { svcDhcpLeaseStateEntry 15 }

svcDhcpLseStateShcvChecks OBJECT-TYPE
    SYNTAX          Unsigned32
    MAX-ACCESS      read-only
    STATUS          obsolete
    DESCRIPTION     "The value of svcDhcpLseStateShcvChecks indicates the
                     number of host connectivity check requests for
                     this DHCP lease state."
    ::= { svcDhcpLeaseStateEntry 16 }

svcDhcpLseStateShcvReplies OBJECT-TYPE
    SYNTAX          Unsigned32
    MAX-ACCESS      read-only
    STATUS          obsolete
    DESCRIPTION     "The value of svcDhcpLseStateShcvReplies indicates the
                     number of host connectivity replies for
                     this DHCP lease state."
    ::= { svcDhcpLeaseStateEntry 17 }

svcDhcpLseStateShcvReplyTime OBJECT-TYPE
    SYNTAX          TimeStamp
    MAX-ACCESS      read-only
    STATUS          obsolete
    DESCRIPTION     "The value of svcDhcpLseStateShcvReplyTime indicates the
                     time of the last successful host connectivity check for
                     this DHCP lease state."
    ::= { svcDhcpLeaseStateEntry 18 }

svcDhcpLseStateClientId OBJECT-TYPE
    SYNTAX          OCTET STRING
    MAX-ACCESS      read-only
    STATUS          obsolete
    DESCRIPTION     "The value of svcDhcpLseStateClientId indicates the 
                     DHCPv6 clients unique identifier (DUID) as generated
                     by the client." 
    ::= { svcDhcpLeaseStateEntry 19 }

svcDhcpLseStateIAID OBJECT-TYPE
    SYNTAX          Unsigned32
    MAX-ACCESS      read-only
    STATUS          obsolete
    DESCRIPTION     "The value of svcDhcpLseStateIAID indicates the
                     Identity Association ID (IAID)
                     the address or prefix defined by
                     svcDhcpLseStateCiAddr/svcDhcpLseStateCiAddrMaskLen
                     has been assigned to.
                     
                     This object is only meaningful for DHCPv6 leases."
    REFERENCE
                    "RFC 3315 section 10"
    ::= { svcDhcpLeaseStateEntry 20 }

svcDhcpLseStateIAIDType OBJECT-TYPE
    SYNTAX          IAIDType
    MAX-ACCESS      read-only
    STATUS          obsolete
    DESCRIPTION     "The value of svcDhcpLseStateIAIDType indicates the
                     type of svcDhcpLseStateIAID.

                     This object is only meaningful for DHCPv6 leases."
    REFERENCE
                    "RFC 3315"
    ::= { svcDhcpLeaseStateEntry 21 }

svcDhcpLseStateCiAddrMaskLen OBJECT-TYPE
    SYNTAX          Unsigned32 (0..128)
    MAX-ACCESS      read-only
    STATUS          obsolete
    DESCRIPTION     "The value of svcDhcpLseStateCiAddrMaskLen indicates the 
                     prefix length of the svcDhcpLseStateCiAddr for a DHCPv6
                     lease."
    ::= { svcDhcpLeaseStateEntry 22 }

svcDhcpLseStateRetailerSvcId OBJECT-TYPE  
    SYNTAX          TmnxServId
    MAX-ACCESS      read-only
    STATUS          obsolete
    DESCRIPTION     "The value of svcDhcpLseStateRetailerSvcId indicates the
                     service ID of the retailer VPRN service to which this 
                     DHCP lease belongs. When this object is non zero, the
                     DHCP lease belongs to a retailer VPRN."
    ::= { svcDhcpLeaseStateEntry 23 }

svcDhcpLseStateRetailerIf OBJECT-TYPE
     SYNTAX         InterfaceIndexOrZero
     MAX-ACCESS      read-only
     STATUS          obsolete
     DESCRIPTION     "The value of svcDhcpLseStateRetailerIf indicates the
                      interface index of the retailer VPRN interface to 
                      which this DHCP lease belongs. When this object is 
                      non zero, the DHCP lease belongs to a retailer VPRN."
     ::= { svcDhcpLeaseStateEntry 24 }

svcDhcpLseStateAncpString OBJECT-TYPE
    SYNTAX          DisplayString (SIZE (1..63))
    MAX-ACCESS      read-only
    STATUS          obsolete
    DESCRIPTION     "The object svcDhcpLseStateAncpString indicates the
                     value of the ancp-string received from either the DHCP
                     or the Radius server as indicated by the value of 
                     svcDhcpLseStateOriginStrings."
    ::= { svcDhcpLeaseStateEntry 25 }

svcDhcpLseStateFramedIpNetMaskTp OBJECT-TYPE
    SYNTAX          InetAddressType
    MAX-ACCESS      read-only
    STATUS          obsolete
    DESCRIPTION     "The value of svcDhcpLseStateFramedIpNetMaskTp indicates the
                     address type of svcDhcpLseStateFramedIpNetMask."
    ::= { svcDhcpLeaseStateEntry 26 }

svcDhcpLseStateFramedIpNetMask OBJECT-TYPE
    SYNTAX          InetAddress
    MAX-ACCESS      read-only
    STATUS          obsolete
    DESCRIPTION     "The value of svcDhcpLseStateFramedIpNetMask indicates the
                     framed IP netmask received from either the DHCP or the
                     Radius server as indicated by the value of
                     svcDhcpLseStateOriginLeaseInfo.
                     
                     The value of this object is ''H when not applicable."
    ::= { svcDhcpLeaseStateEntry 27 }

svcDhcpLseStateBCastIpAddrType OBJECT-TYPE
    SYNTAX          InetAddressType
    MAX-ACCESS      read-only
    STATUS          obsolete
    DESCRIPTION     "The value of svcDhcpLseStateBCastIpAddrType indicates the
                     address type of svcDhcpLseStateBCastIpAddr."
    ::= { svcDhcpLeaseStateEntry 28 }

svcDhcpLseStateBCastIpAddr OBJECT-TYPE
    SYNTAX          InetAddress
    MAX-ACCESS      read-only
    STATUS          obsolete
    DESCRIPTION     "The value of svcDhcpLseStateBCastIpAddr indicates the
                     broadcast IP address received from either the DHCP or the
                     Radius server as indicated by the value of
                     svcDhcpLseStateOriginLeaseInfo.
                     
                     The value of this object is ''H when not applicable."
    ::= { svcDhcpLeaseStateEntry 29 }

svcDhcpLseStateDefaultRouterTp OBJECT-TYPE
    SYNTAX          InetAddressType
    MAX-ACCESS      read-only
    STATUS          obsolete
    DESCRIPTION     "The value of svcDhcpLseStateDefaultRouterTp indicates the
                     address type of svcDhcpLseStateDefaultRouter."
    ::= { svcDhcpLeaseStateEntry 30 }

svcDhcpLseStateDefaultRouter OBJECT-TYPE
    SYNTAX          InetAddress
    MAX-ACCESS      read-only
    STATUS          obsolete
    DESCRIPTION     "The value of svcDhcpLseStateDefaultRouter indicates the
                     default router received from either the DHCP or the
                     Radius server as indicated by the value of
                     svcDhcpLseStateOriginLeaseInfo.
                     
                     The value of this object is ''H when not applicable."
    ::= { svcDhcpLeaseStateEntry 31 }

svcDhcpLseStatePrimaryDnsType OBJECT-TYPE
    SYNTAX          InetAddressType
    MAX-ACCESS      read-only
    STATUS          obsolete
    DESCRIPTION     "The value of svcDhcpLseStatePrimaryDnsType indicates the
                     address type of svcDhcpLseStatePrimaryDns."
    ::= { svcDhcpLeaseStateEntry 32 }

svcDhcpLseStatePrimaryDns OBJECT-TYPE
    SYNTAX          InetAddress
    MAX-ACCESS      read-only
    STATUS          obsolete
    DESCRIPTION     "The value of svcDhcpLseStatePrimaryDns indicates the
                     primary DNS server received from either the DHCP or the
                     Radius server as indicated by the value of
                     svcDhcpLseStateOriginLeaseInfo.
                     
                     The value of this object is ''H when not applicable."
    ::= { svcDhcpLeaseStateEntry 33 }

svcDhcpLseStateSecondaryDnsType OBJECT-TYPE
    SYNTAX          InetAddressType
    MAX-ACCESS      read-only
    STATUS          obsolete
    DESCRIPTION     "The value of svcDhcpLseStateSecondaryDnsType indicates the
                     address type of svcDhcpLseStateSecondaryDns."
    ::= { svcDhcpLeaseStateEntry 34 }

svcDhcpLseStateSecondaryDns OBJECT-TYPE
    SYNTAX          InetAddress
    MAX-ACCESS      read-only
    STATUS          obsolete
    DESCRIPTION     "The value of svcDhcpLseStateSecondaryDns indicates the
                     secondary DNS server received from either the DHCP or the
                     Radius server as indicated by the value of
                     svcDhcpLseStateOriginLeaseInfo.
                     
                     The value of this object is ''H when not applicable."
    ::= { svcDhcpLeaseStateEntry 35 }

svcDhcpLseStateSessionTimeout OBJECT-TYPE
    SYNTAX          Unsigned32 (0..65535)
    UNITS           "seconds"
    MAX-ACCESS      read-only
    STATUS          obsolete
    DESCRIPTION     "The value of svcDhcpLseStateSessionTimeout indicates the
                     session timeout received from either the DHCP or the
                     Radius server as indicated by the value of
                     svcDhcpLseStateOriginLeaseInfo."
    ::= { svcDhcpLeaseStateEntry 36 }

svcDhcpLseStateServerLeaseStart OBJECT-TYPE
    SYNTAX          DateAndTime
    MAX-ACCESS      read-only
    STATUS          obsolete
    DESCRIPTION     "The value of svcDhcpLseStateServerLeaseStart indicates
                     when this lease was created."
    ::= { svcDhcpLeaseStateEntry 37 }

svcDhcpLseStateServerLastRenew OBJECT-TYPE
    SYNTAX          DateAndTime
    MAX-ACCESS      read-only
    STATUS          obsolete
    DESCRIPTION     "The value of svcDhcpLseStateServerLastRenew indicates
                     when we last received a renewal from either the DHCP or the
                     Radius server."
    ::= { svcDhcpLeaseStateEntry 38 }

svcDhcpLseStateServerLeaseEnd OBJECT-TYPE
    SYNTAX          DateAndTime
    MAX-ACCESS      read-only
    STATUS          obsolete
    DESCRIPTION     "The value of svcDhcpLseStateServerLeaseEnd indicates
                     when the server will consider the lease as being
                     expired."
    ::= { svcDhcpLeaseStateEntry 39 }

svcDhcpLseStateDhcpServerAddrType OBJECT-TYPE
    SYNTAX          InetAddressType
    MAX-ACCESS      read-only
    STATUS          obsolete
    DESCRIPTION     "The value of svcDhcpLseStateDhcpServerAddrType indicates
                     the address type of svcDhcpLseStateDhcpServerAddr."
    ::= { svcDhcpLeaseStateEntry 40 }

svcDhcpLseStateDhcpServerAddr OBJECT-TYPE
    SYNTAX          InetAddress
    MAX-ACCESS      read-only
    STATUS          obsolete
    DESCRIPTION     "The value of svcDhcpLseStateDhcpServerAddr indicates the
                     IP address of the DHCP server received from either the
                     DHCP or the Radius server as indicated by the value of
                     svcDhcpLseStateOriginLeaseInfo.
                     
                     The value of this object is ''H when not applicable."
    ::= { svcDhcpLeaseStateEntry 41 }

svcDhcpLseStateOriginSubscrId OBJECT-TYPE
    SYNTAX          DhcpLseStateInfoOrigin
    MAX-ACCESS      read-only
    STATUS          obsolete
    DESCRIPTION     "The value of svcDhcpLseStateOriginSubscrId indicates
                     which source provided the subscriber-id."
    ::= { svcDhcpLeaseStateEntry 42 }

svcDhcpLseStateOriginStrings OBJECT-TYPE
    SYNTAX          DhcpLseStateInfoOrigin
    MAX-ACCESS      read-only
    STATUS          obsolete
    DESCRIPTION     "The value of svcDhcpLseStateOriginStrings indicates
                     which server provided the Sub-profile, SLA profile,
                     Ancp string and Intermediate Destination Id."
    ::= { svcDhcpLeaseStateEntry 43 }

svcDhcpLseStateOriginLeaseInfo OBJECT-TYPE
    SYNTAX          DhcpLseStateInfoOrigin
    MAX-ACCESS      read-only
    STATUS          obsolete
    DESCRIPTION     "The value of svcDhcpLseStateOriginLeaseInfo indicates
                     which server provided the lease state information."
    ::= { svcDhcpLeaseStateEntry 44 }

svcDhcpLseStateDhcpClientAddrType OBJECT-TYPE
    SYNTAX          InetAddressType
    MAX-ACCESS      read-only
    STATUS          obsolete
    DESCRIPTION     "The value of svcDhcpLseStateDhcpClientAddrType indicates
                     the address type of svcDhcpLseStateDhcpClientAddr."
    ::= { svcDhcpLeaseStateEntry 45 }

svcDhcpLseStateDhcpClientAddr OBJECT-TYPE
    SYNTAX          InetAddress
    MAX-ACCESS      read-only
    STATUS          obsolete
    DESCRIPTION     "The value of svcDhcpLseStateDhcpClientAddr indicates the
                     IP address of the DHCP Client that owns the lease info.

                     In some cases this address can be different from the
                     address specified in svcDhcpLseStateCiAddr, e.g. in case of
                     DHCPv6 prefix delegation."
    ::= { svcDhcpLeaseStateEntry 46 }

svcDhcpLseStateLeaseSplitActive OBJECT-TYPE
    SYNTAX          TruthValue
    MAX-ACCESS      read-only
    STATUS          obsolete
    DESCRIPTION     "The value of svcDhcpLseStateLeaseSplitActive indicates
                     whether or not the current lease time resulted from a
                     lease split.
                     If svcDhcpLseStateLeaseSplitActive is 'true',
                     the lease time passed to the client is determined by the
                     value of the object sapTlsDhcpProxyLeaseTime for VPLS SAPs,
                     or by the value of the object vRtrIfDHCPProxyLeaseTime
                     for Layer 3 interfaces."
    ::= { svcDhcpLeaseStateEntry 47 }

svcDhcpLseStateInterDestId OBJECT-TYPE
    SYNTAX          DisplayString (SIZE (0..32))
    MAX-ACCESS      read-only
    STATUS          obsolete
    DESCRIPTION     "The object svcDhcpLseStateInterDestId indicates the
                     intermediate destination identifier received from either
                     the DHCP or the Radius server or the local user database
                     as indicated by the value of svcDhcpLseStateOriginStrings."
    ::= { svcDhcpLeaseStateEntry 48 }

svcDhcpLseStatePrimaryNbnsType OBJECT-TYPE
    SYNTAX          InetAddressType
    MAX-ACCESS      read-only
    STATUS          obsolete
    DESCRIPTION     "The value of svcDhcpLseStatePrimaryNbnsType indicates the
                     address type of svcDhcpLseStatePrimaryNbns."
    ::= { svcDhcpLeaseStateEntry 49 }

svcDhcpLseStatePrimaryNbns OBJECT-TYPE
    SYNTAX          InetAddress
    MAX-ACCESS      read-only
    STATUS          obsolete
    DESCRIPTION     "The value of svcDhcpLseStatePrimaryNbns indicates the
                     primary NBNS server received from either the DHCP or the
                     Radius server as indicated by the value of
                     svcDhcpLseStateOriginLeaseInfo.

                     The value of this object is ''H when not applicable."
    ::= { svcDhcpLeaseStateEntry 50 }

svcDhcpLseStateSecondaryNbnsType OBJECT-TYPE
    SYNTAX          InetAddressType
    MAX-ACCESS      read-only
    STATUS          obsolete
    DESCRIPTION     "The value of svcDhcpLseStateSecondaryNbnsType indicates
                     the address type of svcDhcpLseStateSecondaryNbns."
    ::= { svcDhcpLeaseStateEntry 51 }

svcDhcpLseStateSecondaryNbns OBJECT-TYPE
    SYNTAX          InetAddress
    MAX-ACCESS      read-only
    STATUS          obsolete
    DESCRIPTION     "The value of svcDhcpLseStateSecondaryNbns indicates the
                     secondary NBNS server received from either the DHCP or the
                     Radius server as indicated by the value of
                     svcDhcpLseStateOriginLeaseInfo.

                     The value of this object is ''H when not applicable."
    ::= { svcDhcpLeaseStateEntry 52 }

svcDhcpLseStateAppProfString OBJECT-TYPE
    SYNTAX          DisplayString
    MAX-ACCESS      read-only
    STATUS          obsolete
    DESCRIPTION     "The value of svcDhcpLseStateAppProfString indicates the
                     application profile string applicable for this DHCP lease
                     state.
                     
                     The value of svcDhcpLseStateOriginStrings indicates
                     whether this application profile string was received from
                     DHCP or from the Radius server."
    ::= { svcDhcpLeaseStateEntry 53 }

svcDhcpLseStateNextHopMacAddr OBJECT-TYPE
    SYNTAX          MacAddress
    MAX-ACCESS      read-only
    STATUS          obsolete
    DESCRIPTION     "The value of svcDhcpLseStateNextHopMacAddr indicates the
                     MAC address of the next hop of this DHCP lease state.
                     
                     Normally, the next hop MAC address equals the value of
                     svcDhcpLseStateChAddr. If the value of the object
                     TIMETRA-VRTR-MIB::vRtrIfDHCPLayer2Header is set to 'true',
                     a routing device can be present between this node and
                     the DHCP client. In that case, the value of the next hop
                     MAC address contains the MAC address of this routing
                     device."
    ::= { svcDhcpLeaseStateEntry 54 }

svcDhcpLseStateCategoryMapName OBJECT-TYPE
    SYNTAX          TNamedItemOrEmpty
    MAX-ACCESS      read-only
    STATUS          obsolete
    DESCRIPTION     "The object svcDhcpLseStateCategoryMapName indicates the
                     value of the category map name received from either the
                     DHCP or the Radius server as indicated by the value of 
                     svcDhcpLseStateOriginStrings."
    ::= { svcDhcpLeaseStateEntry 55 }

svcDhcpLseStateNakNextRenew OBJECT-TYPE
    SYNTAX          TruthValue
    MAX-ACCESS      read-only
    STATUS          obsolete
    DESCRIPTION     "The value of svcDhcpLseStateNakNextRenew indicates
                     that the system will reply with a DHCP-NAK when the client
                     sends the next DHCP-REQUEST, whereafter the lease-state
                     will be deleted. 

                     This state is entered upon reception of a 
                     FORCE-NAK COA (Change Of Authority) request from RADIUS
                     for this lease state, which at the same time also
                     triggered the system to send a FORCE-RENEW DHCP message
                     to the client."
    ::= { svcDhcpLeaseStateEntry 56 }

svcDhcpLseStateRadiusClassAttr OBJECT-TYPE
    SYNTAX          OCTET STRING (SIZE (0..64))
    MAX-ACCESS      read-only
    STATUS          obsolete
    DESCRIPTION     "The value of svcDhcpLseStateRadiusClassAttr indicates the
                     Class attribute returned by the RADIUS server in an
                     Access-Accept message.
         
                     If no RADIUS authentication is performed for this lease
                     state, or RADIUS did not return this attribute, the value
                     of this object is empty."
    ::= { svcDhcpLeaseStateEntry 57 }

svcDhcpLseStateRadiusUserName OBJECT-TYPE
    SYNTAX          DisplayString (SIZE (0..128))
    MAX-ACCESS      read-only
    STATUS          obsolete
    DESCRIPTION     "The value of svcDhcpLseStateRadiusUserName indicates the
                     User-Name attribute returned by the RADIUS server in an
                     Access-Accept message.

                     If RADIUS did not return this attribute, the value of this
                     object is equal to the User-Name attribute sent in the
                     original Access-Request message.
         
                     If no RADIUS authentication is performed for this session,
                     the value of this object is empty."
    ::= { svcDhcpLeaseStateEntry 58 }

-- ----------------------------------------------------------------------------
-- DHCP Lease State Table version 2
--
-- The MAC address is part of the key to allow multiple lease states having the
-- same IP address.
--
-- ----------------------------------------------------------------------------
svcDhcpLeaseTable OBJECT-TYPE
    SYNTAX          SEQUENCE OF SvcDhcpLeaseEntry
    MAX-ACCESS      not-accessible
    STATUS          current
    DESCRIPTION     "A table that contains DHCP lease states."
    ::= { tmnxSvcObjs 90 }

svcDhcpLeaseEntry OBJECT-TYPE
    SYNTAX          SvcDhcpLeaseEntry
    MAX-ACCESS      not-accessible
    STATUS          current
    DESCRIPTION     "Information about a specific DHCP lease state."
    INDEX           { svcId,
                      svcDhcpLeaseCiAddrType,
                      svcDhcpLeaseCiAddr,
                      svcDhcpLeaseNextHopMacAddr }
    ::= { svcDhcpLeaseTable 1 }

SvcDhcpLeaseEntry ::=
    SEQUENCE {
        svcDhcpLeaseCiAddrType           InetAddressType,
        svcDhcpLeaseCiAddr               InetAddress,
        svcDhcpLeaseNextHopMacAddr       MacAddress,
        svcDhcpLeaseChAddr               MacAddress,
        svcDhcpLeaseLocale               INTEGER,
        svcDhcpLeasePortId               TmnxPortID,
        svcDhcpLeaseEncapValue           TmnxEncapVal,
        svcDhcpLeaseSdpId                SdpId,
        svcDhcpLeaseVcId                 Unsigned32,
        svcDhcpLeaseRemainLseTime        Unsigned32,
        svcDhcpLeaseOption82             OCTET STRING,
        svcDhcpLeasePersistKey           Unsigned32,
        svcDhcpLeaseSubscrIdent          DisplayString,
        svcDhcpLeaseSubProfString        DisplayString,
        svcDhcpLeaseSlaProfString        DisplayString,
        svcDhcpLeaseShcvOperState        ServShcvOperState,
        svcDhcpLeaseShcvChecks           Unsigned32,
        svcDhcpLeaseShcvReplies          Unsigned32,
        svcDhcpLeaseShcvReplyTime        TimeStamp,
        svcDhcpLeaseClientId             OCTET STRING,
        svcDhcpLeaseIAID                 Unsigned32,
        svcDhcpLeaseIAIDType             IAIDType,
        svcDhcpLeaseCiAddrMaskLen        Unsigned32,
        svcDhcpLeaseRetailerSvcId        TmnxServId,
        svcDhcpLeaseRetailerIf           InterfaceIndexOrZero,
        svcDhcpLeaseAncpString           TmnxAncpStringOrZero,
        svcDhcpLeaseFramedIpNetMaskTp    InetAddressType,
        svcDhcpLeaseFramedIpNetMask      InetAddress,
        svcDhcpLeaseBCastIpAddrType      InetAddressType,
        svcDhcpLeaseBCastIpAddr          InetAddress,
        svcDhcpLeaseDefaultRouterTp      InetAddressType,
        svcDhcpLeaseDefaultRouter        InetAddress,
        svcDhcpLeasePrimaryDnsType       InetAddressType,
        svcDhcpLeasePrimaryDns           InetAddress,
        svcDhcpLeaseSecondaryDnsType     InetAddressType,
        svcDhcpLeaseSecondaryDns         InetAddress,
        svcDhcpLeaseSessionTimeout       Unsigned32,
        svcDhcpLeaseServerLeaseStart     DateAndTime,
        svcDhcpLeaseServerLastRenew      DateAndTime,
        svcDhcpLeaseServerLeaseEnd       DateAndTime,
        svcDhcpLeaseDhcpServerAddrType   InetAddressType,
        svcDhcpLeaseDhcpServerAddr       InetAddress,
        svcDhcpLeaseOriginSubscrId       DhcpLseStateInfoOrigin,
        svcDhcpLeaseOriginStrings        DhcpLseStateInfoOrigin,
        svcDhcpLeaseOriginLeaseInfo      DhcpLseStateInfoOrigin,
        svcDhcpLeaseDhcpClientAddrType   InetAddressType,
        svcDhcpLeaseDhcpClientAddr       InetAddress,
        svcDhcpLeaseLeaseSplitActive     TruthValue,
        svcDhcpLeaseInterDestId          DisplayString,
        svcDhcpLeasePrimaryNbnsType      InetAddressType,
        svcDhcpLeasePrimaryNbns          InetAddress,
        svcDhcpLeaseSecondaryNbnsType    InetAddressType,
        svcDhcpLeaseSecondaryNbns        InetAddress,
        svcDhcpLeaseAppProfString        DisplayString,
        svcDhcpLeaseCategoryMapName      TNamedItemOrEmpty,
        svcDhcpLeaseNakNextRenew         TruthValue,
        svcDhcpLeaseRadiusClassAttr      OCTET STRING,
        svcDhcpLeaseRadiusUserName       DisplayString,
        svcDhcpLeasePoolName             TNamedItem,
        svcDhcpLeaseServerId             OCTET STRING,
        svcDhcpLeaseInterfaceId          OCTET STRING,
        svcDhcpLeaseRemoteId             OCTET STRING,
        svcDhcpLeaseOption60             OCTET STRING,
        svcDhcpLeaseRadCalledStationId   OCTET STRING,
        svcDhcpLeaseLeaseTime            Unsigned32,
        svcDhcpLeaseSessTimeout          Unsigned32,
        svcDhcpLeaseUptime               Unsigned32,
        svcDhcpLeaseRemainingSessTime    Unsigned32,
        svcDhcpLeaseMngdRtStatus         TmnxManagedRouteStatus,
        svcDhcpLeaseTerminationType      TmnxSubTerminationType,
        svcDhcpLeaseIpoeSessionHost      TruthValue,   
        svcDhcpLeasePppSession           TruthValue
    }

svcDhcpLeaseCiAddrType OBJECT-TYPE
    SYNTAX          InetAddressType
    MAX-ACCESS      not-accessible
    STATUS          current
    DESCRIPTION     "The value of svcDhcpLeaseCiAddrType indicates the
                     address type of svcDhcpLeaseCiAddr."
    ::= { svcDhcpLeaseEntry 1 }

svcDhcpLeaseCiAddr OBJECT-TYPE
    SYNTAX          InetAddress (SIZE(4|16))
    MAX-ACCESS      not-accessible
    STATUS          current
    DESCRIPTION     "The value of svcDhcpLeaseCiAddr indicates the IP
                     address of the DHCP lease state."
    ::= { svcDhcpLeaseEntry 2 }

svcDhcpLeaseNextHopMacAddr OBJECT-TYPE
    SYNTAX          MacAddress
    MAX-ACCESS      not-accessible
    STATUS          current
    DESCRIPTION     "The value of svcDhcpLeaseNextHopMacAddr indicates the
                     MAC address of the next hop of this DHCP lease state.
                     
                     Normally, the next hop MAC address equals the value of
                     svcDhcpLeaseChAddr. If the value of the object
                     TIMETRA-VRTR-MIB::vRtrIfDHCPLayer2Header is set to 'true',
                     a routing device can be present between this node and
                     the DHCP client. In that case, the value of the next hop
                     MAC address contains the MAC address of this routing
                     device."
    ::= { svcDhcpLeaseEntry 3 }

svcDhcpLeaseChAddr OBJECT-TYPE
    SYNTAX          MacAddress
    MAX-ACCESS      read-only
    STATUS          current
    DESCRIPTION     "The value of svcDhcpLeaseChAddr indicates the MAC
                     address of the DHCP lease state."
    ::= { svcDhcpLeaseEntry 4 }

svcDhcpLeaseLocale OBJECT-TYPE
    SYNTAX          INTEGER {
                        sap (1),
                        sdp (2)
                    }
    MAX-ACCESS      read-only
    STATUS          current
    DESCRIPTION     "The value of svcDhcpLeaseLocale specifies if the DHCP
                     lease state is learned via a SAP or SDP."
    ::= { svcDhcpLeaseEntry 5 }

svcDhcpLeasePortId OBJECT-TYPE
    SYNTAX          TmnxPortID
    MAX-ACCESS      read-only
    STATUS          current
    DESCRIPTION     "When the value of svcDhcpLeaseLocale is 'sap', the
                     object svcDhcpLeasePortId along with the object
                     svcDhcpLeaseEncapValue, indicates the SAP for which
                     this entry contains information. This object is otherwise
                     insignificant and contains the value 0."
    ::= { svcDhcpLeaseEntry 6 }

svcDhcpLeaseEncapValue OBJECT-TYPE
    SYNTAX          TmnxEncapVal
    MAX-ACCESS      read-only
    STATUS          current
    DESCRIPTION     "When the value of svcDhcpLeaseLocale is 'sap', the
                     object svcDhcpLeasePortId along with the object
                     svcDhcpLeaseEncapValue, indicates the SAP for which
                     this entry contains information. This object is otherwise
                     insignificant and contains the value 0."
    ::= { svcDhcpLeaseEntry 7 }

svcDhcpLeaseSdpId OBJECT-TYPE
    SYNTAX          SdpId
    MAX-ACCESS      read-only
    STATUS          current
    DESCRIPTION     "When the value of svcDhcpLeaseLocale is 'sdp', the
                     object svcDhcpLeaseSdpId, along with the object
                     svcDhcpLeaseVcId, indicates the SDP Binding for which
                     this entry contains information. This object is otherwise
                     insignificant and contains the value 0."
    ::= { svcDhcpLeaseEntry 8 }

svcDhcpLeaseVcId OBJECT-TYPE
    SYNTAX          Unsigned32
    MAX-ACCESS      read-only
    STATUS          current
    DESCRIPTION     "When the value of svcDhcpLeaseLocale is 'sdp', the
                     object svcDhcpLeaseSdpId, along with the object
                     svcDhcpLeaseVcId, indicates the SDP Binding for which
                     this entry contains information. This object is otherwise
                     insignificant and contains the value 0."
    ::= { svcDhcpLeaseEntry 9 }

svcDhcpLeaseRemainLseTime OBJECT-TYPE
    SYNTAX          Unsigned32
    UNITS           "seconds"
    MAX-ACCESS      read-only
    STATUS          current
    DESCRIPTION     "The value of svcDhcpLeaseRemainLseTime indicates the
                     remaining lease time of the DHCP lease state."
    ::= { svcDhcpLeaseEntry 10 }

svcDhcpLeaseOption82 OBJECT-TYPE
    SYNTAX          OCTET STRING
    MAX-ACCESS      read-only
    STATUS          current
    DESCRIPTION     "The value of svcDhcpLeaseOption82 indicates the content
                     of option 82 for this DHCP lease state."
    ::= { svcDhcpLeaseEntry 11 }

svcDhcpLeasePersistKey OBJECT-TYPE
    SYNTAX          Unsigned32
    MAX-ACCESS      read-only
    STATUS          current
    DESCRIPTION     "The value of svcDhcpLeasePersistKey indicates a key
                     value that can be used to track this lease state in the
                     persistence file."
    ::= { svcDhcpLeaseEntry 12 }

svcDhcpLeaseSubscrIdent OBJECT-TYPE
    SYNTAX          DisplayString
    MAX-ACCESS      read-only
    STATUS          current
    DESCRIPTION     "The value of svcDhcpLeaseSubscrIdent indicates the
                     id of the parent subscriber of this DHCP lease state."
    ::= { svcDhcpLeaseEntry 13 }

svcDhcpLeaseSubProfString OBJECT-TYPE
    SYNTAX          DisplayString
    MAX-ACCESS      read-only
    STATUS          current
    DESCRIPTION     "The value of svcDhcpLeaseSubProfString indicates the
                     subscriber profile string applicable for this DHCP lease
                     state."
    ::= { svcDhcpLeaseEntry 14 }

svcDhcpLeaseSlaProfString OBJECT-TYPE
    SYNTAX          DisplayString
    MAX-ACCESS      read-only
    STATUS          current
    DESCRIPTION     "The value of svcDhcpLeaseSlaProfString indicates the
                     SLA profile string applicable for this DHCP lease state."
    ::= { svcDhcpLeaseEntry 15 }

svcDhcpLeaseShcvOperState OBJECT-TYPE
    SYNTAX          ServShcvOperState
    MAX-ACCESS      read-only
    STATUS          current
    DESCRIPTION     "The value of svcDhcpLeaseShcvOperState indicates the
                     state of the subscriber host connectivity check for
                     this DHCP lease state."
    ::= { svcDhcpLeaseEntry 16 }

svcDhcpLeaseShcvChecks OBJECT-TYPE
    SYNTAX          Unsigned32
    MAX-ACCESS      read-only
    STATUS          current
    DESCRIPTION     "The value of svcDhcpLeaseShcvChecks indicates the
                     number of host connectivity check requests for
                     this DHCP lease state."
    ::= { svcDhcpLeaseEntry 17 }

svcDhcpLeaseShcvReplies OBJECT-TYPE
    SYNTAX          Unsigned32
    MAX-ACCESS      read-only
    STATUS          current
    DESCRIPTION     "The value of svcDhcpLeaseShcvReplies indicates the
                     number of host connectivity replies for
                     this DHCP lease state."
    ::= { svcDhcpLeaseEntry 18 }

svcDhcpLeaseShcvReplyTime OBJECT-TYPE
    SYNTAX          TimeStamp
    MAX-ACCESS      read-only
    STATUS          current
    DESCRIPTION     "The value of svcDhcpLeaseShcvReplyTime indicates the
                     time of the last successful host connectivity check for
                     this DHCP lease state."
    ::= { svcDhcpLeaseEntry 19 }

svcDhcpLeaseClientId OBJECT-TYPE
    SYNTAX          OCTET STRING (SIZE (0..255))
    MAX-ACCESS      read-only
    STATUS          current
    DESCRIPTION     "The value of svcDhcpLeaseClientId indicates the 
                     DHCPv6 clients unique identifier (DUID) as generated
                     by the client." 
    ::= { svcDhcpLeaseEntry 20 }

svcDhcpLeaseIAID OBJECT-TYPE
    SYNTAX          Unsigned32
    MAX-ACCESS      read-only
    STATUS          current
    DESCRIPTION     "The value of svcDhcpLeaseIAID indicates the
                     Identity Association ID (IAID)
                     the address or prefix defined by
                     svcDhcpLeaseCiAddr/svcDhcpLeaseCiAddrMaskLen
                     has been assigned to.
                     
                     This object is only meaningful for DHCPv6 leases."
    REFERENCE
                    "RFC 3315 section 10"
    ::= { svcDhcpLeaseEntry 21 }

svcDhcpLeaseIAIDType OBJECT-TYPE
    SYNTAX          IAIDType
    MAX-ACCESS      read-only
    STATUS          current
    DESCRIPTION     "The value of svcDhcpLeaseIAIDType indicates the
                     type of svcDhcpLeaseIAID.

                     This object is only meaningful for DHCPv6 leases."
    REFERENCE
                    "RFC 3315"
    ::= { svcDhcpLeaseEntry 22 }

svcDhcpLeaseCiAddrMaskLen OBJECT-TYPE
    SYNTAX          Unsigned32 (0..128)
    MAX-ACCESS      read-only
    STATUS          current
    DESCRIPTION     "The value of svcDhcpLeaseCiAddrMaskLen indicates the 
                     prefix length of the svcDhcpLeaseCiAddr for a DHCPv6
                     lease."
    ::= { svcDhcpLeaseEntry 23 }

svcDhcpLeaseRetailerSvcId OBJECT-TYPE  
    SYNTAX          TmnxServId
    MAX-ACCESS      read-only
    STATUS          current
    DESCRIPTION     "The value of svcDhcpLeaseRetailerSvcId indicates the
                     service ID of the retailer VPRN service to which this 
                     DHCP lease belongs. When this object is non zero, the
                     DHCP lease belongs to a retailer VPRN."
    ::= { svcDhcpLeaseEntry 24 }

svcDhcpLeaseRetailerIf OBJECT-TYPE
     SYNTAX         InterfaceIndexOrZero
     MAX-ACCESS      read-only
     STATUS          current
     DESCRIPTION     "The value of svcDhcpLeaseRetailerIf indicates the
                      interface index of the retailer VPRN interface to 
                      which this DHCP lease belongs. When this object is 
                      non zero, the DHCP lease belongs to a retailer VPRN."
     ::= { svcDhcpLeaseEntry 25 }

svcDhcpLeaseAncpString OBJECT-TYPE
    SYNTAX          TmnxAncpStringOrZero
    MAX-ACCESS      read-only
    STATUS          current
    DESCRIPTION     "The object svcDhcpLeaseAncpString indicates the
                     value of the received ancp-string."
    ::= { svcDhcpLeaseEntry 26 }

svcDhcpLeaseFramedIpNetMaskTp OBJECT-TYPE
    SYNTAX          InetAddressType
    MAX-ACCESS      read-only
    STATUS          current
    DESCRIPTION     "The value of svcDhcpLeaseFramedIpNetMaskTp indicates the
                     address type of svcDhcpLeaseFramedIpNetMask."
    ::= { svcDhcpLeaseEntry 27 }

svcDhcpLeaseFramedIpNetMask OBJECT-TYPE
    SYNTAX          InetAddress
    MAX-ACCESS      read-only
    STATUS          current
    DESCRIPTION     "The value of svcDhcpLeaseFramedIpNetMask indicates the
                     framed IP netmask received from either the DHCP or the
                     Radius server as indicated by the value of
                     svcDhcpLeaseOriginLeaseInfo.
                     
                     The value of this object is ''H when not applicable."
    ::= { svcDhcpLeaseEntry 28 }

svcDhcpLeaseBCastIpAddrType OBJECT-TYPE
    SYNTAX          InetAddressType
    MAX-ACCESS      read-only
    STATUS          current
    DESCRIPTION     "The value of svcDhcpLeaseBCastIpAddrType indicates the
                     address type of svcDhcpLeaseBCastIpAddr."
    ::= { svcDhcpLeaseEntry 29 }

svcDhcpLeaseBCastIpAddr OBJECT-TYPE
    SYNTAX          InetAddress
    MAX-ACCESS      read-only
    STATUS          current
    DESCRIPTION     "The value of svcDhcpLeaseBCastIpAddr indicates the
                     broadcast IP address received from either the DHCP or the
                     Radius server as indicated by the value of
                     svcDhcpLeaseOriginLeaseInfo.
                     
                     The value of this object is ''H when not applicable."
    ::= { svcDhcpLeaseEntry 30 }

svcDhcpLeaseDefaultRouterTp OBJECT-TYPE
    SYNTAX          InetAddressType
    MAX-ACCESS      read-only
    STATUS          current
    DESCRIPTION     "The value of svcDhcpLeaseDefaultRouterTp indicates the
                     address type of svcDhcpLeaseDefaultRouter."
    ::= { svcDhcpLeaseEntry 31 }

svcDhcpLeaseDefaultRouter OBJECT-TYPE
    SYNTAX          InetAddress
    MAX-ACCESS      read-only
    STATUS          current
    DESCRIPTION     "The value of svcDhcpLeaseDefaultRouter indicates the
                     default router received from either the DHCP or the
                     Radius server as indicated by the value of
                     svcDhcpLeaseOriginLeaseInfo.
                     
                     The value of this object is ''H when not applicable."
    ::= { svcDhcpLeaseEntry 32 }

svcDhcpLeasePrimaryDnsType OBJECT-TYPE
    SYNTAX          InetAddressType
    MAX-ACCESS      read-only
    STATUS          current
    DESCRIPTION     "The value of svcDhcpLeasePrimaryDnsType indicates the
                     address type of svcDhcpLeasePrimaryDns."
    ::= { svcDhcpLeaseEntry 33 }

svcDhcpLeasePrimaryDns OBJECT-TYPE
    SYNTAX          InetAddress
    MAX-ACCESS      read-only
    STATUS          current
    DESCRIPTION     "The value of svcDhcpLeasePrimaryDns indicates the
                     primary DNS server received from the server indicated
                     by the value of svcDhcpLeaseOriginLeaseInfo.
                     
                     The value of this object is ''H when not applicable."
    ::= { svcDhcpLeaseEntry 34 }

svcDhcpLeaseSecondaryDnsType OBJECT-TYPE
    SYNTAX          InetAddressType
    MAX-ACCESS      read-only
    STATUS          current
    DESCRIPTION     "The value of svcDhcpLeaseSecondaryDnsType indicates the
                     address type of svcDhcpLeaseSecondaryDns."
    ::= { svcDhcpLeaseEntry 35 }

svcDhcpLeaseSecondaryDns OBJECT-TYPE
    SYNTAX          InetAddress
    MAX-ACCESS      read-only
    STATUS          current
    DESCRIPTION     "The value of svcDhcpLeaseSecondaryDns indicates the
                     secondary DNS server received from the server indicated
                     by the value of svcDhcpLeaseOriginLeaseInfo.
                     
                     The value of this object is ''H when not applicable."
    ::= { svcDhcpLeaseEntry 36 }

svcDhcpLeaseSessionTimeout OBJECT-TYPE
    SYNTAX          Unsigned32 (0..65535)
    UNITS           "seconds"
    MAX-ACCESS      read-only
    STATUS          obsolete
    DESCRIPTION     "The value of svcDhcpLeaseSessionTimeout indicates the
                     session timeout received from either the DHCP or the
                     Radius server as indicated by the value of
                     svcDhcpLeaseOriginLeaseInfo.

                     This object is replaced by svcDhcpLeaseLeaseTime
                     since release 11.0."
    ::= { svcDhcpLeaseEntry 37 }

svcDhcpLeaseServerLeaseStart OBJECT-TYPE
    SYNTAX          DateAndTime
    MAX-ACCESS      read-only
    STATUS          current
    DESCRIPTION     "The value of svcDhcpLeaseServerLeaseStart indicates
                     when this lease was created."
    ::= { svcDhcpLeaseEntry 38 }

svcDhcpLeaseServerLastRenew OBJECT-TYPE
    SYNTAX          DateAndTime
    MAX-ACCESS      read-only
    STATUS          current
    DESCRIPTION     "The value of svcDhcpLeaseServerLastRenew indicates
                     when we last received a renewal from either the DHCP or the
                     Radius server."
    ::= { svcDhcpLeaseEntry 39 }

svcDhcpLeaseServerLeaseEnd OBJECT-TYPE
    SYNTAX          DateAndTime
    MAX-ACCESS      read-only
    STATUS          current
    DESCRIPTION     "The value of svcDhcpLeaseServerLeaseEnd indicates
                     when the server will consider the lease as being
                     expired."
    ::= { svcDhcpLeaseEntry 40 }

svcDhcpLeaseDhcpServerAddrType OBJECT-TYPE
    SYNTAX          InetAddressType
    MAX-ACCESS      read-only
    STATUS          current
    DESCRIPTION     "The value of svcDhcpLeaseDhcpServerAddrType indicates
                     the address type of svcDhcpLeaseDhcpServerAddr."
    ::= { svcDhcpLeaseEntry 41 }

svcDhcpLeaseDhcpServerAddr OBJECT-TYPE
    SYNTAX          InetAddress
    MAX-ACCESS      read-only
    STATUS          current
    DESCRIPTION     "The value of svcDhcpLeaseDhcpServerAddr indicates the
                     IP address of the DHCP server received from either the
                     DHCP or the Radius server as indicated by the value of
                     svcDhcpLeaseOriginLeaseInfo.
                     
                     The value of this object is ''H when not applicable."
    ::= { svcDhcpLeaseEntry 42 }

svcDhcpLeaseOriginSubscrId OBJECT-TYPE
    SYNTAX          DhcpLseStateInfoOrigin
    MAX-ACCESS      read-only
    STATUS          obsolete
    DESCRIPTION     "The value of svcDhcpLeaseOriginSubscrId indicates
                     which source provided the subscriber-id."
    ::= { svcDhcpLeaseEntry 43 }

svcDhcpLeaseOriginStrings OBJECT-TYPE
    SYNTAX          DhcpLseStateInfoOrigin
    MAX-ACCESS      read-only
    STATUS          obsolete
    DESCRIPTION     "The value of svcDhcpLeaseOriginStrings indicates
                     which server provided the Sub-profile, SLA profile,
                     Ancp string and Intermediate Destination Id."
    ::= { svcDhcpLeaseEntry 44 }

svcDhcpLeaseOriginLeaseInfo OBJECT-TYPE
    SYNTAX          DhcpLseStateInfoOrigin
    MAX-ACCESS      read-only
    STATUS          current
    DESCRIPTION     "The value of svcDhcpLeaseOriginLeaseInfo indicates
                     which server provided the lease state information."
    ::= { svcDhcpLeaseEntry 45 }

svcDhcpLeaseDhcpClientAddrType OBJECT-TYPE
    SYNTAX          InetAddressType
    MAX-ACCESS      read-only
    STATUS          current
    DESCRIPTION     "The value of svcDhcpLeaseDhcpClientAddrType indicates
                     the address type of svcDhcpLeaseDhcpClientAddr."
    ::= { svcDhcpLeaseEntry 46 }

svcDhcpLeaseDhcpClientAddr OBJECT-TYPE
    SYNTAX          InetAddress
    MAX-ACCESS      read-only
    STATUS          current
    DESCRIPTION     "The value of svcDhcpLeaseDhcpClientAddr indicates the
                     IP address of the DHCP Client that owns the lease info.

                     In some cases this address can be different from the
                     address specified in svcDhcpLeaseCiAddr, e.g. in case of
                     DHCPv6 prefix delegation."
    ::= { svcDhcpLeaseEntry 47 }

svcDhcpLeaseLeaseSplitActive OBJECT-TYPE
    SYNTAX          TruthValue
    MAX-ACCESS      read-only
    STATUS          current
    DESCRIPTION     "The value of svcDhcpLeaseLeaseSplitActive indicates
                     whether or not the current lease time resulted from a
                     lease split.
                     If svcDhcpLeaseLeaseSplitActive is 'true',
                     the lease time passed to the client is determined by the
                     value of the object sapTlsDhcpProxyLeaseTime for VPLS SAPs,
                     or by the value of the object vRtrIfDHCPProxyLeaseTime
                     for Layer 3 interfaces."
    ::= { svcDhcpLeaseEntry 48 }

svcDhcpLeaseInterDestId OBJECT-TYPE
    SYNTAX          DisplayString (SIZE (0..32))
    MAX-ACCESS      read-only
    STATUS          current
    DESCRIPTION     "The object svcDhcpLeaseInterDestId indicates the
                     intermediate destination identifier received from either
                     the DHCP or the Radius server or the local user database."
    ::= { svcDhcpLeaseEntry 49 }

svcDhcpLeasePrimaryNbnsType OBJECT-TYPE
    SYNTAX          InetAddressType
    MAX-ACCESS      read-only
    STATUS          current
    DESCRIPTION     "The value of svcDhcpLeasePrimaryNbnsType indicates the
                     address type of svcDhcpLeasePrimaryNbns."
    ::= { svcDhcpLeaseEntry 50 }

svcDhcpLeasePrimaryNbns OBJECT-TYPE
    SYNTAX          InetAddress
    MAX-ACCESS      read-only
    STATUS          current
    DESCRIPTION     "The value of svcDhcpLeasePrimaryNbns indicates the
                     primary NBNS server received from either the DHCP or the
                     Radius server as indicated by the value of
                     svcDhcpLeaseOriginLeaseInfo.

                     The value of this object is ''H when not applicable."
    ::= { svcDhcpLeaseEntry 51 }

svcDhcpLeaseSecondaryNbnsType OBJECT-TYPE
    SYNTAX          InetAddressType
    MAX-ACCESS      read-only
    STATUS          current
    DESCRIPTION     "The value of svcDhcpLeaseSecondaryNbnsType indicates
                     the address type of svcDhcpLeaseSecondaryNbns."
    ::= { svcDhcpLeaseEntry 52 }

svcDhcpLeaseSecondaryNbns OBJECT-TYPE
    SYNTAX          InetAddress
    MAX-ACCESS      read-only
    STATUS          current
    DESCRIPTION     "The value of svcDhcpLeaseSecondaryNbns indicates the
                     secondary NBNS server received from either the DHCP or the
                     Radius server as indicated by the value of
                     svcDhcpLeaseOriginLeaseInfo.

                     The value of this object is ''H when not applicable."
    ::= { svcDhcpLeaseEntry 53 }

svcDhcpLeaseAppProfString OBJECT-TYPE
    SYNTAX          DisplayString
    MAX-ACCESS      read-only
    STATUS          current
    DESCRIPTION     "The value of svcDhcpLeaseAppProfString indicates the
                     application profile string applicable for this DHCP lease
                     state."
    ::= { svcDhcpLeaseEntry 54 }

svcDhcpLeaseCategoryMapName OBJECT-TYPE
    SYNTAX          TNamedItemOrEmpty
    MAX-ACCESS      read-only
    STATUS          current
    DESCRIPTION     "The object svcDhcpLeaseCategoryMapName indicates the
                     value of the category map name received from either the
                     DHCP or the Radius server."
    ::= { svcDhcpLeaseEntry 55 }

svcDhcpLeaseNakNextRenew OBJECT-TYPE
    SYNTAX          TruthValue
    MAX-ACCESS      read-only
    STATUS          current
    DESCRIPTION     "The value of svcDhcpLeaseNakNextRenew indicates
                     that the system will reply with a DHCP-NAK when the client
                     sends the next DHCP-REQUEST, whereafter the lease-state
                     will be deleted. 

                     This state is entered upon reception of a 
                     FORCE-NAK COA (Change Of Authority) request from RADIUS
                     for this lease state, which at the same time also
                     triggered the system to send a FORCE-RENEW DHCP message
                     to the client."
    ::= { svcDhcpLeaseEntry 56 }

svcDhcpLeaseRadiusClassAttr OBJECT-TYPE
    SYNTAX          OCTET STRING (SIZE (0..253))
    MAX-ACCESS      read-only
    STATUS          current
    DESCRIPTION     "The value of svcDhcpLeaseRadiusClassAttr indicates the
                     Class attribute returned by the RADIUS server in an
                     Access-Accept message.
         
                     If no RADIUS authentication is performed for this lease
                     state, or RADIUS did not return this attribute, the value
                     of this object is empty."
    ::= { svcDhcpLeaseEntry 57 }

svcDhcpLeaseRadiusUserName OBJECT-TYPE
    SYNTAX          DisplayString (SIZE (0..253))
    MAX-ACCESS      read-only
    STATUS          current
    DESCRIPTION     "The value of svcDhcpLeaseRadiusUserName indicates the
                     User-Name attribute returned by the RADIUS server in an
                     Access-Accept message.

                     If RADIUS did not return this attribute, the value of this
                     object is equal to the User-Name attribute sent in the
                     original Access-Request message.
         
                     If no RADIUS authentication is performed for this session,
                     the value of this object is empty."
    ::= { svcDhcpLeaseEntry 58 }

svcDhcpLeasePoolName OBJECT-TYPE
    SYNTAX          TNamedItem
    MAX-ACCESS      read-only
    STATUS          current
    DESCRIPTION     "The value of svcDhcpLeasePoolName indicates the
                     pool name included in the Relay-forward Message.
                     
                     This object is only meaningful for DHCPv6 leases."
    ::= { svcDhcpLeaseEntry 59 }

svcDhcpLeaseServerId OBJECT-TYPE
    SYNTAX          OCTET STRING (SIZE (0..255))
    MAX-ACCESS      read-only
    STATUS          current
    DESCRIPTION     "The value of svcDhcpLeaseServerId indicates the 
                     DHCPv6 servers unique identifier (DUID) as generated
                     by the server.

                     This object is only meaningful for DHCPv6 leases."
    REFERENCE
                    "RFC 3315"
    ::= { svcDhcpLeaseEntry 60 }

svcDhcpLeaseInterfaceId OBJECT-TYPE
    SYNTAX          OCTET STRING (SIZE (0..255))
    MAX-ACCESS      read-only
    STATUS          current
    DESCRIPTION     "The value of svcDhcpLeaseInterfaceId indicates the
                     content of the Interface-id option used for
                     authentication.

                     This object is only meaningful for DHCPv6 leases."
    REFERENCE
                    "RFC 3315"
    ::= { svcDhcpLeaseEntry 61 }

svcDhcpLeaseRemoteId OBJECT-TYPE
    SYNTAX          OCTET STRING (SIZE (0..255))
    MAX-ACCESS      read-only
    STATUS          current
    DESCRIPTION     "The value of svcDhcpLeaseRemoteId indicates the
                     content of the Remote-id option used for
                     authentication.

                     This object is only meaningful for DHCPv6 leases."
    REFERENCE
                    "RFC 4649"
    ::= { svcDhcpLeaseEntry 62 }

svcDhcpLeaseOption60 OBJECT-TYPE
    SYNTAX          OCTET STRING (SIZE (0..255))
    MAX-ACCESS      read-only
    STATUS          current
    DESCRIPTION     "The value of svcDhcpLeaseOption60 indicates the content
                     of option 60 for this DHCP lease state.

                     This object is only meaningful for DHCPv4 leases."
    REFERENCE 
                    "RFC 2132"
    ::= { svcDhcpLeaseEntry 63 }

svcDhcpLeaseRadCalledStationId OBJECT-TYPE
    SYNTAX          OCTET STRING (SIZE (0..64))
    MAX-ACCESS      read-only
    STATUS          current
    DESCRIPTION     "The value of svcDhcpLeaseRadCalledStationId indicates the
                     content of the Called-Station-Id RADIUS attribute used for
                     authentication."
    REFERENCE        "RFC 2865 RADIUS,
                      section 5.31.  Calling-Station-Id"
    ::= { svcDhcpLeaseEntry 64 }

svcDhcpLeaseLeaseTime OBJECT-TYPE
    SYNTAX          Unsigned32
    UNITS           "seconds"
    MAX-ACCESS      read-only
    STATUS          current
    DESCRIPTION     "The value of svcDhcpLeaseLeaseTime indicates the
                     lease time received from either the DHCP or the
                     Radius server or the local user database."
    ::= { svcDhcpLeaseEntry 65 }

svcDhcpLeaseSessTimeout OBJECT-TYPE
    SYNTAX          Unsigned32
    UNITS           "seconds"
    MAX-ACCESS      read-only
    STATUS          current
    DESCRIPTION     "The value of svcDhcpLeaseSessTimeout indicates the
                     session timeout received from either the DHCP or the
                     Radius server or the local user database."
    ::= { svcDhcpLeaseEntry 66 }

svcDhcpLeaseUptime OBJECT-TYPE
    SYNTAX          Unsigned32
    UNITS           "seconds"
    MAX-ACCESS      read-only
    STATUS          current
    DESCRIPTION     "The value of svcDhcpLeaseUptime indicates the host uptime."
    ::= { svcDhcpLeaseEntry 67 }

svcDhcpLeaseRemainingSessTime OBJECT-TYPE
    SYNTAX          Unsigned32
    UNITS           "seconds"
    MAX-ACCESS      read-only
    STATUS          current
    DESCRIPTION     "The value of svcDhcpLeaseRemainingSessTime indicates the
                     time before the host is disconnected."
    ::= { svcDhcpLeaseEntry 68 }

svcDhcpLeaseMngdRtStatus OBJECT-TYPE
    SYNTAX          TmnxManagedRouteStatus
    MAX-ACCESS      read-only
    STATUS          current
    DESCRIPTION     "The value of svcDhcpLeaseMngdRtStatus indicates the status
                     of the managed route associated with this lease.

                     This object is only meaningful for DHCPv6 PD leases."
    ::= { svcDhcpLeaseEntry 69 }

svcDhcpLeaseTerminationType OBJECT-TYPE
    SYNTAX      TmnxSubTerminationType
    MAX-ACCESS  read-only
    STATUS      current
    DESCRIPTION
        "The value of svcDhcpLeaseTerminationType indicates the termination type
         of this lease."
    ::= { svcDhcpLeaseEntry 70 }

svcDhcpLeaseIpoeSessionHost OBJECT-TYPE
    SYNTAX      TruthValue
    MAX-ACCESS  read-only
    STATUS      current
    DESCRIPTION
        "The value of svcDhcpLeaseIpoeSessionHost indicates whether or not
         this DHCP lease belongs to an IPoE session.
         
         If the value is 'true', the DHCP lease state belongs to an
         IPoE session."
    ::= { svcDhcpLeaseEntry 71 }

svcDhcpLeasePppSession OBJECT-TYPE
    SYNTAX      TruthValue
    MAX-ACCESS  read-only
    STATUS      current
    DESCRIPTION
        "The value of svcDhcpLeasePppSession indicates whether or not
         this DHCP lease state belongs to an PPP session.
         
         If the value is 'true', the DHCP lease state belongs to an
         PPP session."
    ::= { svcDhcpLeaseEntry 72 }

-- -----------------------------------------
-- TLS Protected MAC Address Table
-- -----------------------------------------
tlsProtectedMacTable OBJECT-TYPE
    SYNTAX          SEQUENCE OF TlsProtectedMacEntry
    MAX-ACCESS      not-accessible
    STATUS          current
    DESCRIPTION     "This table is used to manage protected MAC addresses
                     within a VPLS's FDB."
    ::= { tmnxSvcObjs 17 }

tlsProtectedMacEntry OBJECT-TYPE
    SYNTAX          TlsProtectedMacEntry
    MAX-ACCESS      not-accessible
    STATUS          current
    DESCRIPTION     "An entry containing management information applicable
                     to a particular protected MAC address."
    INDEX           { svcId, tlsProtMacAddress }
    ::= { tlsProtectedMacTable 1 }

TlsProtectedMacEntry ::=
    SEQUENCE {
        tlsProtMacAddress           MacAddress,
        tlsProtMacRowStatus         RowStatus,
        tlsProtMacLastMgmtChange    TimeStamp
    }

tlsProtMacAddress OBJECT-TYPE
    SYNTAX          MacAddress
    MAX-ACCESS      not-accessible
    STATUS          current
    DESCRIPTION     "The value of tlsProtMacAddress indicates the address
                     of the protected MAC."
    ::= { tlsProtectedMacEntry 1 }

tlsProtMacRowStatus OBJECT-TYPE
    SYNTAX          RowStatus
    MAX-ACCESS      read-create
    STATUS          current
    DESCRIPTION     "The value of tlsProtMacRowStatus controls the creation
                     and deletion of rows in this table."
    ::= { tlsProtectedMacEntry 2 }

tlsProtMacLastMgmtChange OBJECT-TYPE
    SYNTAX          TimeStamp
    MAX-ACCESS      read-only
    STATUS          current
    DESCRIPTION     "The value of tlsProtMacLastMgmtChange indicates the
                     value of sysUpTime at the time of the last management
                     change of any writable object of this row."
    ::= { tlsProtectedMacEntry 3 }

-- ----------------------------------------------------------------------------
-- svcDhcpLeaseStateModifyTable
--
-- This table is replaced with the svcDhcpLeaseModifyTable
--
-- ----------------------------------------------------------------------------
svcDhcpLeaseStateModifyTable OBJECT-TYPE
    SYNTAX          SEQUENCE OF SvcDhcpLeaseStateModifyEntry
    MAX-ACCESS      not-accessible
    STATUS          obsolete
    DESCRIPTION     "The svcDhcpLeaseStateModifyTable augments the
                     svcDhcpLeaseStateTable.
                     The table allows the operator to modify attributes of the
                     lease state."
    ::= { tmnxSvcObjs 18 }

svcDhcpLeaseStateModifyEntry OBJECT-TYPE
    SYNTAX          SvcDhcpLeaseStateModifyEntry
    MAX-ACCESS      not-accessible
    STATUS          obsolete
    DESCRIPTION     "Each row entry contains parameters that allow to modify a
                     lease-state's  attributes."
    AUGMENTS        { svcDhcpLeaseStateEntry }
    ::= { svcDhcpLeaseStateModifyTable 1 }

SvcDhcpLeaseStateModifyEntry ::=
    SEQUENCE {
        svcDhcpLseStateModifySubIndent   DisplayString,
        svcDhcpLseStateModifySubProfile  DisplayString,
        svcDhcpLseStateModifySlaProfile  DisplayString,
        svcDhcpLseStateEvaluateState     TruthValue,
        svcDhcpLseStateModInterDestId    DisplayString,
        svcDhcpLseStateModifyAncpString  TmnxAncpStringOrZero,
        svcDhcpLseStateModifyAppProfile  DisplayString
    }

svcDhcpLseStateModifySubIndent OBJECT-TYPE
    SYNTAX          DisplayString (SIZE (0..32))
    MAX-ACCESS      read-write
    STATUS          obsolete
    DESCRIPTION     "The value of svcDhcpLseStateModifySubIndent allows to
                     specify a new subscriber name for this lease state.

                     When a SET of this object is done with a non empty string, the
                     system will attempt to assign a new subscriber name.

                     A SET with an empty string has no effect on the system.
                     (NOOP).

                     GETs and GETNEXTs on this variable return an empty string."
    DEFVAL           { ''H }   -- the empty string
    ::= { svcDhcpLeaseStateModifyEntry 1 }

svcDhcpLseStateModifySubProfile OBJECT-TYPE
    SYNTAX          DisplayString (SIZE (0..16))
    MAX-ACCESS      read-write
    STATUS          obsolete
    DESCRIPTION     "The value of svcDhcpLseStateModifySubProfile allows to
                     specify a new subscriber profile string for this lease
                     state.

                     When a SET of this object is done with a non empty string,
                     the system will attempt to assign a new subscriber profile.

                     A SET with an empty string has no effect on the system.
                     (NOOP).

                     GETs and GETNEXTs on this variable return an empty string."
    DEFVAL           { ''H }   -- the empty string
    ::= { svcDhcpLeaseStateModifyEntry 2 }

svcDhcpLseStateModifySlaProfile OBJECT-TYPE
    SYNTAX          DisplayString (SIZE (0..16))
    MAX-ACCESS      read-write
    STATUS          obsolete
    DESCRIPTION     "The value of svcDhcpLseStateModifySlaProfile allows to
                     specify a new SLA profile string for this lease state.

                     When a SET of this object is done with a non empty string,
                     the system will attempt to assign a new SLA profile.

                     A SET with an empty string has no effect on the system.
                     (NOOP).

                     GETs and GETNEXTs on this variable return an empty string."
    DEFVAL           { ''H }   -- the empty string
    ::= { svcDhcpLeaseStateModifyEntry 3 }

svcDhcpLseStateEvaluateState OBJECT-TYPE
    SYNTAX          TruthValue
    MAX-ACCESS      read-write
    STATUS          obsolete
    DESCRIPTION     "The value of svcDhcpLseStateEvaluateState allows to
                     cause a re-evaluation of the specified lease state.

                     When this object is set to 'true', the system will perform
                     a re-evaluation of the lease state.

                     GETs and GETNEXTs on this variable return false.

                     It is not possible to simultaneously request for a
                     lease-state re-evaluation, and modify any of the 
                     svcDhcpLseStateModifySubIndent,
                     svcDhcpLseStateModifySubProfile or 
                     svcDhcpLseStateModifySlaProfile values."
    DEFVAL          { false }
    ::= { svcDhcpLeaseStateModifyEntry 4 }

svcDhcpLseStateModInterDestId OBJECT-TYPE
    SYNTAX          DisplayString (SIZE (0..32))
    MAX-ACCESS      read-write
    STATUS          obsolete
    DESCRIPTION     "The value of svcDhcpLseStateModInterDestId allows to
                     specify a new intermediate destination id for this lease
                     state.

                     When a SET of this object is done with a non empty string,
                     the system will attempt to assign a new intermediate
                     destination id.

                     A SET with an empty string has no effect on the system.
                     (NOOP).

                     GETs and GETNEXTs on this variable return an empty string."
    DEFVAL           { ''H }
    ::= { svcDhcpLeaseStateModifyEntry 5 }

svcDhcpLseStateModifyAncpString OBJECT-TYPE
    SYNTAX          TmnxAncpStringOrZero
    MAX-ACCESS      read-write
    STATUS          obsolete
    DESCRIPTION     "The value of svcDhcpLseStateModifyAncpString allows to
                     specify a new ANCP-string for this lease state.

                     When a SET of this object is done with a non empty string,
                     the system will attempt to assign a new ANCP-string.

                     A SET with an empty string has no effect on the system.
                     (NOOP).

                     GETs and GETNEXTs on this variable return an empty string."
    DEFVAL           { ''H }   -- the empty string
    ::= { svcDhcpLeaseStateModifyEntry 6 }

svcDhcpLseStateModifyAppProfile OBJECT-TYPE
    SYNTAX          DisplayString (SIZE (0..16))
    MAX-ACCESS      read-write
    STATUS          obsolete
    DESCRIPTION     "The value of svcDhcpLseStateModifyAppProfile specifies
                     a new application profile string for this lease state.

                     When a SET of this object is done with a non empty string,
                     the system assigns a new application profile.

                     A SET with an empty string has no effect on the system.
                     (NOOP).

                     GETs and GETNEXTs on this variable return an empty
                     string."
    DEFVAL           { ''H }   -- the empty string
    ::= { svcDhcpLeaseStateModifyEntry 7 }

-- ----------------------------------------------------------------------------
-- DHCP Lease State Modify Table version 2
--
-- The MAC address is part of the key to allow multiple lease states having the
-- same IP address.
--
-- ----------------------------------------------------------------------------
svcDhcpLeaseModifyTable OBJECT-TYPE
    SYNTAX          SEQUENCE OF SvcDhcpLeaseModifyEntry
    MAX-ACCESS      not-accessible
    STATUS          current
    DESCRIPTION     "The svcDhcpLeaseModifyTable augments the
                     svcDhcpLeaseTable.
                     The table allows the operator to modify attributes of the
                     lease state."
    ::= { tmnxSvcObjs 91 }

svcDhcpLeaseModifyEntry OBJECT-TYPE
    SYNTAX          SvcDhcpLeaseModifyEntry
    MAX-ACCESS      not-accessible
    STATUS          current
    DESCRIPTION     "Each row entry contains parameters that allow to modify a
                     lease-state's  attributes."
    AUGMENTS        { svcDhcpLeaseEntry }
    ::= { svcDhcpLeaseModifyTable 1 }

SvcDhcpLeaseModifyEntry ::=
    SEQUENCE {
        svcDhcpLeaseModifySubIndent   DisplayString,
        svcDhcpLeaseModifySubProfile  DisplayString,
        svcDhcpLeaseModifySlaProfile  DisplayString,
        svcDhcpLeaseEvaluateState     TruthValue,
        svcDhcpLeaseModInterDestId    DisplayString,
        svcDhcpLeaseModifyAncpString  TmnxAncpStringOrZero,
        svcDhcpLeaseModifyAppProfile  DisplayString
    }

svcDhcpLeaseModifySubIndent OBJECT-TYPE
    SYNTAX          DisplayString (SIZE (0..32))
    MAX-ACCESS      read-write
    STATUS          current
    DESCRIPTION     "The value of svcDhcpLeaseModifySubIndent allows to
                     specify a new subscriber name for this lease state.

                     When a SET of this object is done with a non empty string, the
                     system will attempt to assign a new subscriber name.

                     A SET with an empty string has no effect on the system.
                     (NOOP).

                     GETs and GETNEXTs on this variable return an empty string."
    DEFVAL           { ''H }   -- the empty string
    ::= { svcDhcpLeaseModifyEntry 1 }

svcDhcpLeaseModifySubProfile OBJECT-TYPE
    SYNTAX          DisplayString (SIZE (0..16))
    MAX-ACCESS      read-write
    STATUS          current
    DESCRIPTION     "The value of svcDhcpLeaseModifySubProfile allows to
                     specify a new subscriber profile string for this lease
                     state.

                     When a SET of this object is done with a non empty string,
                     the system will attempt to assign a new subscriber profile.

                     A SET with an empty string has no effect on the system.
                     (NOOP).

                     GETs and GETNEXTs on this variable return an empty string."
    DEFVAL           { ''H }   -- the empty string
    ::= { svcDhcpLeaseModifyEntry 2 }

svcDhcpLeaseModifySlaProfile OBJECT-TYPE
    SYNTAX          DisplayString (SIZE (0..16))
    MAX-ACCESS      read-write
    STATUS          current
    DESCRIPTION     "The value of svcDhcpLeaseModifySlaProfile allows to
                     specify a new SLA profile string for this lease state.

                     When a SET of this object is done with a non empty string,
                     the system will attempt to assign a new SLA profile.

                     A SET with an empty string has no effect on the system.
                     (NOOP).

                     GETs and GETNEXTs on this variable return an empty string."
    DEFVAL           { ''H }   -- the empty string
    ::= { svcDhcpLeaseModifyEntry 3 }

svcDhcpLeaseEvaluateState OBJECT-TYPE
    SYNTAX          TruthValue
    MAX-ACCESS      read-write
    STATUS          current
    DESCRIPTION     "The value of svcDhcpLeaseEvaluateState allows to
                     cause a re-evaluation of the specified lease state.

                     When this object is set to 'true', the system will perform
                     a re-evaluation of the lease state.

                     GETs and GETNEXTs on this variable return false.

                     It is not possible to simultaneously request for a
                     lease-state re-evaluation, and modify any of the 
                     svcDhcpLeaseModifySubIndent,
                     svcDhcpLeaseModifySubProfile or 
                     svcDhcpLeaseModifySlaProfile values."
    DEFVAL          { false }
    ::= { svcDhcpLeaseModifyEntry 4 }

svcDhcpLeaseModInterDestId OBJECT-TYPE
    SYNTAX          DisplayString (SIZE (0..32))
    MAX-ACCESS      read-write
    STATUS          current
    DESCRIPTION     "The value of svcDhcpLeaseModInterDestId allows to
                     specify a new intermediate destination id for this lease
                     state.

                     When a SET of this object is done with a non empty string,
                     the system will attempt to assign a new intermediate
                     destination id.

                     A SET with an empty string has no effect on the system.
                     (NOOP).

                     GETs and GETNEXTs on this variable return an empty string."
    DEFVAL           { ''H }
    ::= { svcDhcpLeaseModifyEntry 5 }

svcDhcpLeaseModifyAncpString OBJECT-TYPE
    SYNTAX          TmnxAncpStringOrZero
    MAX-ACCESS      read-write
    STATUS          current
    DESCRIPTION     "The value of svcDhcpLeaseModifyAncpString allows to
                     specify a new ANCP-string for this lease state.

                     When a SET of this object is done with a non empty string,
                     the system will attempt to assign a new ANCP-string.

                     A SET with an empty string has no effect on the system.
                     (NOOP).

                     GETs and GETNEXTs on this variable return an empty string."
    DEFVAL           { ''H }   -- the empty string
    ::= { svcDhcpLeaseModifyEntry 6 }

svcDhcpLeaseModifyAppProfile OBJECT-TYPE
    SYNTAX          DisplayString (SIZE (0..16))
    MAX-ACCESS      read-write
    STATUS          current
    DESCRIPTION     "The value of svcDhcpLeaseModifyAppProfile specifies
                     a new application profile string for this lease state.

                     When a SET of this object is done with a non empty string,
                     the system assigns a new application profile.

                     A SET with an empty string has no effect on the system.
                     (NOOP).

                     GETs and GETNEXTs on this variable return an empty
                     string."
    DEFVAL           { ''H }   -- the empty string
    ::= { svcDhcpLeaseModifyEntry 7 }

-- ----------------------------------------
-- svcEndPointTable
-- ----------------------------------------
svcEndPointTable        OBJECT-TYPE
    SYNTAX      SEQUENCE OF SvcEndPointEntry
    MAX-ACCESS  not-accessible
    STATUS      current
    DESCRIPTION "The svcEndPointTable has an entry for each service endpoint
                 configured on this system."
    ::= { tmnxSvcObjs 19 }

svcEndPointEntry        OBJECT-TYPE
    SYNTAX      SvcEndPointEntry
    MAX-ACCESS  not-accessible
    STATUS      current
    DESCRIPTION "Each row entry represents a particular service endpoint. 
                 Entries are created/deleted by the user."
    INDEX       { svcId, svcEndPointName }
    ::= { svcEndPointTable 1 }

SvcEndPointEntry ::=
    SEQUENCE {
        svcEndPointName                 TNamedItem,
        svcEndPointRowStatus            RowStatus,
        svcEndPointDescription          ServObjDesc,
        svcEndPointRevertTime           Integer32,
        svcEndPointTxActiveType         INTEGER,
        svcEndPointTxActivePortId       TmnxPortID,
        svcEndPointTxActiveEncap        TmnxEncapVal,
        svcEndPointTxActiveSdpId        SdpBindId,
        svcEndPointForceSwitchOver      TmnxActionType,
        svcEndPointForceSwitchOverSdpId SdpBindId,
        svcEndPointActiveHoldDelay      Unsigned32, 
        svcEndPointIgnoreStandbySig     TruthValue,
        svcEndPointMacPinning           TmnxEnabledDisabled,
        svcEndPointMacLimit             Integer32,
        svcEndPointSuppressStandbySig   TruthValue,
        svcEndPointRevertTimeCountDn    Integer32,
        svcEndPointTxActiveChangeCount  Counter32,
        svcEndPointTxActiveLastChange   TimeStamp,
        svcEndPointTxActiveUpTime       TimeTicks,
        svcEndPointMCEPId               Unsigned32,
        svcEndPointMCEPPeerAddrType     InetAddressType,
        svcEndPointMCEPPeerAddr         InetAddress,
        svcEndPointMCEPPeerName         TNamedItemOrEmpty,
        svcEndPointBlockOnMeshFail      TruthValue,
        svcEndPointMCEPPsvModeActive    TruthValue,
        svcEndPointStandbySigMaster     TruthValue,
        svcEndPointStandbySigSlave      TruthValue,
        svcEndPointForceSwitchOvrSdpFec TmnxSpokeSdpIdOrZero,
        svcEndPointTxActiveSdpFec       TmnxSpokeSdpIdOrZero,
        svcEndPointRestProtSrcMac       TruthValue,
        svcEndPointRestProtSrcMacAction INTEGER,
        svcEndPointAutoLearnMacProtect  TruthValue,
        svcEndPointCreationOrigin       INTEGER
    }

svcEndPointName         OBJECT-TYPE
    SYNTAX      TNamedItem
    MAX-ACCESS  not-accessible
    STATUS      current
    DESCRIPTION "The value of svcEndPointName specifies the name of the service
                 endpoint."
    ::= { svcEndPointEntry 1 }

svcEndPointRowStatus    OBJECT-TYPE
    SYNTAX      RowStatus
    MAX-ACCESS  read-create
    STATUS      current
    DESCRIPTION "The value of svcEndPointRowStatus is used for the creation and
                 deletion of service endpoints."
    ::= { svcEndPointEntry 2 }

svcEndPointDescription  OBJECT-TYPE
    SYNTAX      ServObjDesc
    MAX-ACCESS  read-create
    STATUS      current
    DESCRIPTION "The value of svcEndPointDescription specifies the textual
                 description of this service endpoint."
    DEFVAL      { "" }
    ::= { svcEndPointEntry 3 }

svcEndPointRevertTime  OBJECT-TYPE
    SYNTAX      Integer32 (-1 | 0..600)
    UNITS       "seconds"
    MAX-ACCESS  read-create
    STATUS      current
    DESCRIPTION "The value of svcEndPointRevertTime specifies the time to wait
                 before reverting back to the primary spoke-sdp defined on this
                 service endpoint, after having failed over to a backup 
                 spoke-sdp. When the value is '-1', the spoke-sdp will never 
                 revert back."
    DEFVAL      { 0 }
    ::= { svcEndPointEntry 4 }

svcEndPointTxActiveType OBJECT-TYPE
    SYNTAX      INTEGER {
                    none    (0), -- No end-point objects are active
                    sap     (1), -- A SAP is Tx active
                    sdpBind (2), -- An SDP bind is Tx Active
                    sdpFec  (3)  -- SDP FEC-129 is Tx Active
                }
    MAX-ACCESS  read-only
    STATUS      current
    DESCRIPTION "The value of svcEndPointTxActiveType indicates the type of
                 end-point object that is current transmit active. "
    ::= { svcEndPointEntry 5 }
        
svcEndPointTxActivePortId       OBJECT-TYPE
    SYNTAX      TmnxPortID
    MAX-ACCESS  read-only
    STATUS      current
    DESCRIPTION "The value of svcEndPointTxActivePortId indicates the Port ID
                 of the SAP that is transmit active. This object is only valid
                 when svcEndPointTxActiveType is 'sap'."
    ::= { svcEndPointEntry 6 }

svcEndPointTxActiveEncap       OBJECT-TYPE
    SYNTAX      TmnxEncapVal
    MAX-ACCESS  read-only
    STATUS      current
    DESCRIPTION "The value of svcEndPointTxActiveEncap indicates the 
                 encapsulation value of the SAP that is transmit active. This
                 object is only valid when svcEndPointTxActiveType is 'sap'."
    ::= { svcEndPointEntry 7 }

svcEndPointTxActiveSdpId       OBJECT-TYPE
    SYNTAX      SdpBindId
    MAX-ACCESS  read-only
    STATUS      current
    DESCRIPTION "The value of svcEndPointTxActiveSdpId indicates the SDP bind
                 ID of the SDP bind that is transmit active. This object is only
                 valid when svcEndPointTxActiveType is 'sdpBind'."
    ::= { svcEndPointEntry 8 }

svcEndPointForceSwitchOver      OBJECT-TYPE
    SYNTAX      TmnxActionType
    MAX-ACCESS  read-create
    STATUS      current
    DESCRIPTION "The value of svcEndPointForceSwitchOver specifies whether to
                 force a switchover of the active SDP bind. When it is set to
                 'doAction', the SDP bind specified by 
                 svcEndPointForceSwitchOverSdpId will become active."
    DEFVAL      { notApplicable }
    ::= { svcEndPointEntry 9 }  

svcEndPointForceSwitchOverSdpId   OBJECT-TYPE
    SYNTAX      SdpBindId
    MAX-ACCESS  read-create
    STATUS      current
    DESCRIPTION "The value of svcEndPointForceSwitchOverSdpId specifies the SDP
                 bind to switch over to when svcEndPointForceSwitchOver is set
                 to 'doAction'. If the value of this object is non default, it 
                 indicates that a forced switchover has taken place. Setting 
                 this object to the default value clears any previous forced 
                 switchover. "
    DEFVAL      { '0000000000000000'H }
    ::= { svcEndPointEntry 10 } 
    
svcEndPointActiveHoldDelay     OBJECT-TYPE
    SYNTAX      Unsigned32 (0..60) 
    UNITS       "deci-seconds"
    MAX-ACCESS  read-create
    STATUS      current
    DESCRIPTION "The value of svcEndPointActiveHoldDelay specifies the amount
                 of time in deci-seconds to hold the active state before going
                 into the standby state when a local MC-LAG SAP goes down."
    DEFVAL      { 0 }
    ::= { svcEndPointEntry 11 } 

svcEndPointIgnoreStandbySig     OBJECT-TYPE
    SYNTAX      TruthValue
    MAX-ACCESS  read-create
    STATUS      current
    DESCRIPTION "The value of svcEndPointIgnoreStandbySig specifies whether the
                 local internal tasks will take into account the 'pseudo-wire
                 forwarding standby' bit received from the LDP peer which is
                 normally ignored.  

                 When set to 'true', this bit is not considered in the internal
                 tasks.

                 A similar object sdpBindTlsIgnoreStandbySig is present at the
                 SDP level. The value of sdpBindTlsIgnoreStandbySig is set to
                 the value of svcEndPointIgnoreStandbySig for the spoke-SDP
                 associated with this endpoint."
    DEFVAL      { false }
    ::= { svcEndPointEntry 12 } 

svcEndPointMacPinning OBJECT-TYPE
    SYNTAX      TmnxEnabledDisabled
    MAX-ACCESS  read-create
    STATUS      current
    DESCRIPTION "The value of svcEndPointMacPinning specifies whether or not
                 MAC address pinning is active on this end-point."
    DEFVAL { disabled }    
    ::= { svcEndPointEntry 13 }

svcEndPointMacLimit OBJECT-TYPE
    SYNTAX      Integer32(0..511999)
    MAX-ACCESS  read-create
    STATUS      current
    DESCRIPTION "The value of the object svcEndPointMacLimit specifies the
                 maximum number of learned and static entries allowed for this
                 end-point.
        
                 The value 0 means: no limit for this end-point. 

                 When the value of TIMETRA-CHASSIS-MIB::tmnxChassisOperMode is
                 'a' or 'b', the maximum value of this object is '131071'.

                 When the value of TIMETRA-CHASSIS-MIB::tmnxChassisOperMode is
                 'c', the maximum value of this object is '196607'.

                 When the value of TIMETRA-CHASSIS-MIB::tmnxChassisOperMode is
                 'd', the maximum value of this object is '511999'."
    DEFVAL          { 0 }
    ::= { svcEndPointEntry 14 }

svcEndPointSuppressStandbySig     OBJECT-TYPE
    SYNTAX      TruthValue
    MAX-ACCESS  read-create
    STATUS      current
    DESCRIPTION "The value of the object svcEndPointSuppressStandbySig specifies
                 whether the 'pseudo wire forwarding standby' bit will be sent
                 to the LDP peer whenever the spoke SDP
                 'svcEndPointTxActiveSdpId' is selected as standby. 

                 When set to 'true', this bit will not be sent."
    DEFVAL      { true }
    ::= { svcEndPointEntry 15 } 

svcEndPointRevertTimeCountDn  OBJECT-TYPE
    SYNTAX      Integer32 (-1 | 0..600)
    UNITS       "seconds"
    MAX-ACCESS  read-only
    STATUS      current
    DESCRIPTION "The value of svcEndPointRevertTimeCountDn indicates the timer
                 count down before reverting back to the primary spoke-sdp
                 defined on this service endpoint, after having failed over to
                 a backup spoke-sdp.

                 This timer count down begins after primary Spoke SDP becomes
                 operational.
                 
                 The value of -1 indicates when revert is not-applicable."
    ::= { svcEndPointEntry 16 }

svcEndPointTxActiveChangeCount  OBJECT-TYPE
    SYNTAX      Counter32
    MAX-ACCESS  read-only
    STATUS      current
    DESCRIPTION "The value of svcEndPointTxActiveChangeCount indicates the
                 number of times active transmit change has taken place in this
                 endpoint."
    ::= { svcEndPointEntry 17 }

svcEndPointTxActiveLastChange  OBJECT-TYPE
    SYNTAX      TimeStamp
    MAX-ACCESS  read-only
    STATUS      current
    DESCRIPTION "The value of svcEndPointTxActiveLastChange indicates the
                 value of sysUpTime at the time of the last active transmit
                 change in this endpoint."
    ::= { svcEndPointEntry 18 }

svcEndPointTxActiveUpTime OBJECT-TYPE
    SYNTAX      TimeTicks
    MAX-ACCESS  read-only
    STATUS      current
    DESCRIPTION "The value of svcEndPointTxActiveUpTime indicates the active
                'up' time (in hundredths of a second) of the end-point object 
                that is current transmit active."
    ::= { svcEndPointEntry 19 }

svcEndPointMCEPId         OBJECT-TYPE
    SYNTAX      Unsigned32
    MAX-ACCESS  read-create
    STATUS      current
    DESCRIPTION "The value of svcEndPointMCEPId specifies the multi-chassis
                 end-point identifier assigned to this endpoint."
    DEFVAL { 0 }
    ::= { svcEndPointEntry 20 }

svcEndPointMCEPPeerAddrType OBJECT-TYPE
    SYNTAX      InetAddressType
    MAX-ACCESS  read-create
    STATUS      current
    DESCRIPTION "The value of svcEndPointMCEPPeerAddrType specifies the 
                 address type of svcEndPointMCEPPeerAddr object.

                 An 'inconsistentValue' error is returned if this object is
                 set to non-default value when svcEndPointMCEPId is set to
                 its default value.

                 An 'inconsistentValue' error is returned if this object is
                 set to non-default value when svcEndPointMCEPPeerName is set
                 to its non-default value."
    DEFVAL { unknown }
    ::= { svcEndPointEntry 21 }

svcEndPointMCEPPeerAddr OBJECT-TYPE
    SYNTAX      InetAddress
    MAX-ACCESS  read-create
    STATUS      current
    DESCRIPTION "The value of svcEndPointMCEPPeerAddr specifies the
                 IP address of multi-chassis end-point peer.

                 An 'inconsistentValue' error is returned if this object is
                 set to non-default value when svcEndPointMCEPId is set to
                 its default value.

                 An 'inconsistentValue' error is returned if this object is
                 set to non-default value when svcEndPointMCEPPeerName is set
                 to its non-default value."
    DEFVAL { ''H }
    ::= { svcEndPointEntry 22 }

svcEndPointMCEPPeerName OBJECT-TYPE
    SYNTAX      TNamedItemOrEmpty
    MAX-ACCESS  read-create
    STATUS      current
    DESCRIPTION "The value of svcEndPointMCEPPeerName specifies the name of
                 multi-chassis end-point peer
                 TIMETRA-MC-REDUNDANCY-MIB::tmnxMcPeerName.
                 
                 An 'inconsistentValue' error is returned if this object is
                 set to non-default value when svcEndPointMCEPId is set to
                 its default value.

                 An 'inconsistentValue' error is returned if this object is
                 set to non-default value when svcEndPointMCEPPeerAddrType and
                 svcEndPointMCEPPeerAddr are set to their non-default values."
    DEFVAL { ''H }
    ::= { svcEndPointEntry 23 }

svcEndPointBlockOnMeshFail     OBJECT-TYPE
    SYNTAX      TruthValue
    MAX-ACCESS  read-create
    STATUS      current
    DESCRIPTION "The value of svcEndPointBlockOnMeshFail specifies that the
                 operational status of spoke-SDPs in the endpoint will be 
                 affected by the operational status of associated mesh SDPs in
                 this service.
                     
                 If there are no mesh SDPs in the service, value of this
                 object is ignored.
                     
                 When this object is set to 'true', then the operational
                 status of the spoke-SDPs in the endpoint will be 'down' until
                 the operational status of at least one mesh SDP in this service
                 is 'up'.

                 When set to 'false', the operational status of the spoke-SDPs
                 in the endpoint will not be affected by the operational status
                 of any mesh SDPs in the service."
    DEFVAL      { false }
    ::= { svcEndPointEntry 24 } 

svcEndPointMCEPPsvModeActive        OBJECT-TYPE
    SYNTAX      TruthValue
    MAX-ACCESS  read-only
    STATUS      current
    DESCRIPTION
        "The value of svcEndPointMCEPPsvModeActive indicates whether
        passive-mode behavior is currently active on this multi-chassis
        end-point."
    ::= { svcEndPointEntry 25 }

svcEndPointStandbySigMaster OBJECT-TYPE
    SYNTAX      TruthValue
    MAX-ACCESS  read-create
    STATUS      current
    DESCRIPTION
        "The value of svcEndPointStandbySigMaster specifies whether
         PW standby bit will be sent to T-LDP peer whenever spoke-SDPs
         of this endpoint are selected as standby."
    DEFVAL { false }
    ::= { svcEndPointEntry 26 }

svcEndPointStandbySigSlave OBJECT-TYPE
    SYNTAX      TruthValue
    MAX-ACCESS  read-create
    STATUS      current
    DESCRIPTION
        "The value of svcEndPointStandbySigSlave specifies whether
         transmission of any spoke in the endpoint will be blocked when the
         spoke receives standby status notification from its peer."
    DEFVAL { false }
    ::= { svcEndPointEntry 27 }

svcEndPointForceSwitchOvrSdpFec   OBJECT-TYPE
    SYNTAX      TmnxSpokeSdpIdOrZero
    MAX-ACCESS  read-create
    STATUS      current
    DESCRIPTION
        "The value of svcEndPointForceSwitchOvrSdpFec specifies the 
         multi-segment pseudo-wire provide-edge identifier           
         to switch over to when svcEndPointForceSwitchOver is set
         to 'doAction'.
         
         If the value of this object is set to non-default, it 
         indicates that a forced switchover has taken place. Setting 
         this object to the default value clears any previous forced 
         switchover."
    DEFVAL      { 0 }
    ::= { svcEndPointEntry 28 } 
    
svcEndPointTxActiveSdpFec       OBJECT-TYPE
    SYNTAX      TmnxSpokeSdpIdOrZero
    MAX-ACCESS  read-only
    STATUS      current
    DESCRIPTION
        "The value of svcEndPointTxActiveSdpFec indicates the multi-
         segment pseudo-wire provider-edge identifier that is transmit active.
         This object is only valid when svcEndPointTxActiveType is set to
         'sdpFec'."
    ::= { svcEndPointEntry 29 }

svcEndPointRestProtSrcMac OBJECT-TYPE
    SYNTAX          TruthValue
    MAX-ACCESS      read-create
    STATUS          current
    DESCRIPTION 
        "The value of the object svcEndPointRestProtSrcMac indicates
         how the agent will handle relearn requests for protected
         MAC addresses received on the SDP belonging to this endpoint.

         When the value of this object is 'true' requests to 
         relearn a protected MAC address will be ignored.

         In addition, if the value of svcEndPointRestProtSrcMacAction
         is 'disable', then the SDP belonging to the endpoint where the
         protected source MAC was seen will be brought operationally down."
    DEFVAL          { false }
    ::= { svcEndPointEntry 30 }

svcEndPointRestProtSrcMacAction OBJECT-TYPE
    SYNTAX          INTEGER {
                        disable      (1),
                        alarmOnly    (2),
                        discardFrame (3)
                    }
    MAX-ACCESS      read-create
    STATUS          current
    DESCRIPTION
        "The value of the object svcEndPointRestProtSrcMacAction
         indicates the action to take whenever a relearn request
         for a protected MAC is received on the SDP belonging to
         this endpoint.

         When the value of this object is 'disable' the SDP belonging
         to this endpoint will be placed in the operational down state,
         with the operating flag 'recProtSrcMac' set.
                     
         When the value of this object is 'alarm-only', the SDP belonging
         to this endpoint will be left up and only a notification,
         TIMETRA-SDP-MIB::sdpBindReceivedProtSrcMac,  will be generated.

         When the value of this object is 'discardFrame', the
         SDP will start discarding the frame in addition to 
         generating TIMETRA-SDP-MIB::sdpBindReceivedProtSrcMac notification."
    DEFVAL          { disable }    
    ::= { svcEndPointEntry 31 }

svcEndPointAutoLearnMacProtect   OBJECT-TYPE
    SYNTAX      TruthValue
    MAX-ACCESS  read-create
    STATUS      current
    DESCRIPTION
        "The value of svcEndPointAutoLearnMacProtect specifies whether
         to enable automatic population of the MAC protect list with
         source MAC addresses learned on the SDP associated with this endpoint."
    DEFVAL { false }
    ::= { svcEndPointEntry 32 }

svcEndPointCreationOrigin OBJECT-TYPE
    SYNTAX          INTEGER {
                        manual  (0),
                        bgpVpws (1)
                    }
    MAX-ACCESS      read-only
    STATUS          current
    DESCRIPTION
        "The value of svcEndPointCreationOrigin indicates the origin
         mechanism used to create this endpoint."
    ::= { svcEndPointEntry 33 }

------------------------------------------
-- iesGrpIfTable
-- ----------------------------------------

iesGrpIfTable   OBJECT-TYPE
    SYNTAX      SEQUENCE OF IesGrpIfEntry
    MAX-ACCESS  not-accessible
    STATUS      current
    DESCRIPTION "The iesGrpIfTable has entry for each group interface
                 configured on this system."
    ::= { tmnxSvcObjs 21 }

iesGrpIfEntry   OBJECT-TYPE
    SYNTAX      IesGrpIfEntry
    MAX-ACCESS  not-accessible
    STATUS      current
    DESCRIPTION "Each row entry represents the attributes of a group interface.
                 Entries are create/destroyed when entries in iesIfEntry with
                 iesIfType 'group' are created/destroyed."
    INDEX       { svcId, iesIfIndex }
    ::= { iesGrpIfTable 1 }

IesGrpIfEntry   ::=
    SEQUENCE {
        iesGrpIfRedInterface             InterfaceIndexOrZero,
        iesGrpIfOperUpWhileEmpty         TruthValue,
        iesGrpIfPolicyControl            TNamedItemOrEmpty,
        iesGrpIfDiameterAuthPolicy       TNamedItemOrEmpty,
        iesGrpIfIpv6AutoReply            BITS
   }

iesGrpIfRedInterface    OBJECT-TYPE
    SYNTAX      InterfaceIndexOrZero
    MAX-ACCESS  read-write
    STATUS      current
    DESCRIPTION "The value of iesGrpIfRedInterface specifies the ifIndex
                 of the redundant interface this group interface is tied to.
                 The interface pointed to by this object must be of
                 type 'redundant'."
    DEFVAL      { 0 }
    ::= { iesGrpIfEntry 1 }

iesGrpIfOperUpWhileEmpty    OBJECT-TYPE
    SYNTAX      TruthValue
    MAX-ACCESS  read-write
    STATUS      current
    DESCRIPTION "The value of iesGrpIfOperUpWhileEmpty specifies the
                 whether that operational status of the the IES group
                 interface, as indicated by iesIfOperStatus, should have
                 a value of 'up' even when there are no SAPs on the
                 group interface.

                 If the value of iesGrpIfOperUpWhileEmpty is 'true', the
                 value of iesIfOperStatus for the IES group interface will
                 be 'up' when there are no SAPs on the group interface. When
                 the value of iesGrpIfOperUpWhileEmpty is 'false', the value
                 of iesIfOperStatus will depend on the operational state of
                 the SAPs on the group interface. The value of
                 iesGrpIfOperUpWhileEmpty will be ignored when there are
                 SAPs on the IES group interface."
    DEFVAL      { false }
    ::= { iesGrpIfEntry 2 }

iesGrpIfPolicyControl    OBJECT-TYPE
    SYNTAX      TNamedItemOrEmpty
    MAX-ACCESS  read-write
    STATUS      current
    DESCRIPTION "The value of iesGrpIfPolicyControl specifies the name
                 of the Policy Control policy for this group interface.
                 
                 For example: the value of this object can be set to
                 the value of the object tmnxDiamAppPlcyId of a conceptual
                 row in the TIMETRA-DIAMETER-MIB::tmnxDiamAppPlcyTable."
    DEFVAL      { "" }
    ::= { iesGrpIfEntry 3 }

iesGrpIfDiameterAuthPolicy OBJECT-TYPE
    SYNTAX      TNamedItemOrEmpty
    MAX-ACCESS  read-write
    STATUS      current
    DESCRIPTION "The value of iesGrpIfDiameterAuthPolicy specifies the name
                 of the DIAMETER authentication policy for this group interface.
                 
                 A non empty value of this object must correspond to a
                 conceptual row in the TIMETRA-DIAMETER-MIB::tmnxDiamApNqTable,
                 the DIAMETER NAS application (NASREQ) table."
    DEFVAL      { "" }
    ::= { iesGrpIfEntry 4 }
    

iesGrpIfIpv6AutoReply OBJECT-TYPE
    SYNTAX      BITS {
                    neighborSolicitation (0),
                    routerSolicitation   (1)
                }
    MAX-ACCESS  read-write
    STATUS      current
    DESCRIPTION "The value of iesGrpIfIpv6AutoReply specifies
                 the automatic reply to Neighbor Solicitation and
                 Router Solicitation messages, for data-triggered static IPv6 hosts.
                 
                 neighborSolicitation (0) - auto-reply for Neighbor Solicitation
                 
                 routerSolicitation (1) - auto-reply for Router Solicitation."
    ::= { iesGrpIfEntry 5 }
    
-- ----------------------------------------
-- svcPEDiscoveryPolicyTable
-- ----------------------------------------
svcPEDiscoveryPolicyTable  OBJECT-TYPE
    SYNTAX        SEQUENCE OF SvcPEDiscoveryPolicyEntry
    MAX-ACCESS    not-accessible
    STATUS        obsolete
    DESCRIPTION   "The svcPEDiscoveryPolicyTable has an entry for each PE policy."      
    ::= { tmnxSvcObjs 22 }
    
svcPEDiscoveryPolicyEntry  OBJECT-TYPE
    SYNTAX      SvcPEDiscoveryPolicyEntry
    MAX-ACCESS  not-accessible
    STATUS      obsolete
    DESCRIPTION
        "svcPEDiscoveryPolicyEntry is an entry (conceptual row) in the
         svcPEDiscoveryPolicyTable. Each entry represents the configuration
         of a PE Discovery Policy.

         Entries in this table can be created and deleted via SNMP SET
         operations to svcPEDiscoveryPolicyRowStatus."
    INDEX {IMPLIED svcPEDiscoveryPolicyName}
    ::= { svcPEDiscoveryPolicyTable 1 }

SvcPEDiscoveryPolicyEntry ::= SEQUENCE {
            svcPEDiscoveryPolicyName          TNamedItem,
            svcPEDiscoveryPolicyRowStatus     RowStatus,    
            svcPEDiscoveryPolicyPassword      OCTET STRING,
            svcPEDiscoveryPolicyInterval      Unsigned32,   
            svcPEDiscoveryPolicyTimeout       Unsigned32                 
}

svcPEDiscoveryPolicyName       OBJECT-TYPE
    SYNTAX           TNamedItem
    MAX-ACCESS       not-accessible
    STATUS           obsolete
    DESCRIPTION      
        "The value of the object svcPEDiscoveryPolicyName specifies the 
         RADIUS PE Discovery Policy name." 
    ::= { svcPEDiscoveryPolicyEntry 1 }

svcPEDiscoveryPolicyRowStatus OBJECT-TYPE
    SYNTAX      RowStatus
    MAX-ACCESS  read-create
    STATUS      obsolete
    DESCRIPTION
        "svcPEDiscoveryPolicyRowStatus controls the creation and deletion
         of rows in the table.

         To create a row in the svcPEDiscoveryPolicyTable,
         set svcPEDiscoveryPolicyRowStatus to 'createAndGo'. All objects will take
         on default values and the agent will change svcPEDiscoveryPolicyRowStatus
         to 'active'.

         To delete a row in the svcPEDiscoveryPolicyTable, set
         svcPEDiscoveryPolicyRowStatus to 'delete'."
    ::= { svcPEDiscoveryPolicyEntry 2 }
               
svcPEDiscoveryPolicyPassword  OBJECT-TYPE
    SYNTAX      OCTET STRING (SIZE(0..32))
    MAX-ACCESS  read-create
    STATUS      obsolete
    DESCRIPTION
        "The value of svcPEDiscoveryPolicyPassword specifies the password that is
         used when contacting the RADIUS server for VPLS auto-discovery.

         GETs and GETNEXTs on this variable return an empty string."
    DEFVAL { ''H }
    ::= { svcPEDiscoveryPolicyEntry 3 }

svcPEDiscoveryPolicyInterval  OBJECT-TYPE
    SYNTAX      Unsigned32 (1..30)
    UNITS       "minutes"
    MAX-ACCESS  read-create
    STATUS      obsolete
    DESCRIPTION
        "The value of svcPEDiscoveryPolicyInterval specifies the polling
         interval for Radius PE discovery in minutes."
    DEFVAL { 5 }
    ::= { svcPEDiscoveryPolicyEntry 4 }

svcPEDiscoveryPolicyTimeout  OBJECT-TYPE
    SYNTAX      Unsigned32 (1..90)
    UNITS       "seconds"
    MAX-ACCESS  read-create
    STATUS      obsolete
    DESCRIPTION
        "The value of svcPEDiscoveryPolicyTimeout specifies the number of 
         seconds to wait before timing out a RADIUS server."
    DEFVAL { 3 }
    ::= { svcPEDiscoveryPolicyEntry 5 }

-- ----------------------------------------
-- svcPEDiscoveryPolicyServerTable
-- ----------------------------------------
svcPEDiscPolServerTable OBJECT-TYPE
    SYNTAX      SEQUENCE OF SvcPEDiscPolServerEntry
    MAX-ACCESS  not-accessible
    STATUS      obsolete
    DESCRIPTION
        "The svcPEDiscPolServerTable has an entry for each RADIUS server.
         The table can have up to a maximum of 5 entries."
::= { tmnxSvcObjs 23 }

svcPEDiscPolServerEntry OBJECT-TYPE
    SYNTAX      SvcPEDiscPolServerEntry
    MAX-ACCESS  not-accessible
    STATUS      obsolete
    DESCRIPTION
        "svcPEDiscPolServerEntry is an entry (conceptual row) in the
         svcPEDiscPolServerTable. Each entry represents the configuration
         for a RADIUS server.

         Entries in this table can be created and deleted via SNMP SET
         operations to svcPEDiscPolServerRowStatus."
    INDEX {svcPEDiscPolServerIndex,
             IMPLIED svcPEDiscoveryPolicyName }
    ::= { svcPEDiscPolServerTable 1 }

SvcPEDiscPolServerEntry ::= SEQUENCE {
    svcPEDiscPolServerIndex           Unsigned32,
    svcPEDiscPolServerRowStatus       RowStatus,
    svcPEDiscPolServerAddressType     InetAddressType,
    svcPEDiscPolServerAddress         InetAddress,
    svcPEDiscPolServerSecret          OCTET STRING,
    svcPEDiscPolServerOperStatus      ServiceOperStatus,
    svcPEDiscPolServerPort            Unsigned32 
}

svcPEDiscPolServerIndex OBJECT-TYPE
    SYNTAX      Unsigned32 (1..5)
    MAX-ACCESS  not-accessible
    STATUS      obsolete
    DESCRIPTION
        "The svcPEDiscPolServerIndex indicates the unique value which 
         identifies a specific radius server."
    ::= { svcPEDiscPolServerEntry 1 }

svcPEDiscPolServerRowStatus OBJECT-TYPE
    SYNTAX      RowStatus
    MAX-ACCESS  read-create
    STATUS      obsolete
    DESCRIPTION
        "svcPEDiscPolServerRowStatus controls the creation and deletion
         of rows in the table."
    ::= { svcPEDiscPolServerEntry 2 }

svcPEDiscPolServerAddressType OBJECT-TYPE
    SYNTAX      InetAddressType
    MAX-ACCESS  read-create
    STATUS      obsolete
    DESCRIPTION
        "The value of svcPEDiscPolServerAddressType is used to configure 
         the address type of svcPEDiscPolServerAddress address.
         
         A valid value for svcPEDiscPolServerAddressType object must be
         specified at the time of creation of entry."
    ::= { svcPEDiscPolServerEntry 3 }

svcPEDiscPolServerAddress OBJECT-TYPE
    SYNTAX      InetAddress
    MAX-ACCESS  read-create
    STATUS      obsolete
    DESCRIPTION
        "The value of svcPEDiscPolServerAddress is used to configure the
         IP address of the RADIUS server.

         A valid value for svcPEDiscPolServerAddress object must be
         specified at the time of creation of entry."
    ::= { svcPEDiscPolServerEntry 4 }

svcPEDiscPolServerSecret OBJECT-TYPE
    SYNTAX      OCTET STRING (SIZE(0..20))
    MAX-ACCESS  read-create
    STATUS      obsolete
    DESCRIPTION
        "The svcPEDiscPolServerSecret is used to configure the secret key
         associated with the RADIUS server.  

         A valid value for svcPEDiscPolServerSecret object must be
         specified at the time of creation of entry.

         The value of svcPEDiscPolServerSecret cannot be set to an empty 
         string.  GETs and GETNEXTs on this variable return an empty string."
    ::= { svcPEDiscPolServerEntry 5 }

svcPEDiscPolServerOperStatus OBJECT-TYPE
    SYNTAX      ServiceOperStatus
    MAX-ACCESS  read-only
    STATUS      obsolete
    DESCRIPTION
        "The svcPEDiscPolServerOperStatus indicates the obsolete status 
         of the RADIUS server."
    ::= { svcPEDiscPolServerEntry 6 }

svcPEDiscPolServerPort  OBJECT-TYPE
    SYNTAX      Unsigned32 (1..65535)
    MAX-ACCESS  read-create
    STATUS      obsolete
    DESCRIPTION
        "The svcPEDiscPolServerPort is used to configure the UDP port 
         number on which to contact the RADIUS server."
     DEFVAL { 1812 }
    ::= { svcPEDiscPolServerEntry 7 }

-- ------------------------------
-- Service Whole saler table
-- ------------------------------

svcWholesalerInfoTable OBJECT-TYPE
    SYNTAX      SEQUENCE OF SvcWholesalerInfoEntry
    MAX-ACCESS  not-accessible
    STATUS      current
    DESCRIPTION
        "The svcWholesalerInfoTable has an entry for each wholesaler service
         associated with a retailer service on this system."
    ::= { tmnxSvcObjs 24 }

svcWholesalerInfoEntry    OBJECT-TYPE
    SYNTAX      SvcWholesalerInfoEntry
    MAX-ACCESS  not-accessible
    STATUS      current
    DESCRIPTION
        "Each row entry represents the attributes of a wholesaler-retailer 
         pairing. Entries are created/destroyed when forwarding interfaces
         are defined."
    INDEX { svcId, svcWholesalerID }
    ::= { svcWholesalerInfoTable 1}

SvcWholesalerInfoEntry ::= SEQUENCE
    {
        svcWholesalerID                  TmnxServId,
        svcWholesalerNumStaticHosts      Unsigned32,
        svcWholesalerNumDynamicHosts     Unsigned32,
        svcWholesalerNumDhcpLeaseStates  Unsigned32,
        svcWholesalerNumPppoeSessions    Unsigned32,
        svcWholesalerNumArpHosts         Unsigned32
      , svcWholesalerNumDhcp6LeaseStates Unsigned32
      , svcWholesalerNumSlaacHosts       Unsigned32
      , svcWholesalerNumStatic6Hosts     Unsigned32
      , svcWholesalerNumIpoeSessions     Unsigned32
      , svcWholesalerNumIpcpHosts        Unsigned32
    }

svcWholesalerID        OBJECT-TYPE
    SYNTAX      TmnxServId
    MAX-ACCESS  not-accessible
    STATUS      current
    DESCRIPTION
        "The value of svcWholesalerID is used to specify the service ID of the
         wholesaler."
    ::= { svcWholesalerInfoEntry 1 }

svcWholesalerNumStaticHosts        OBJECT-TYPE
    SYNTAX      Unsigned32
    MAX-ACCESS  read-only
    STATUS      current
    DESCRIPTION
        "The value of svcWholesalerNumStaticHosts indicates the number of 
         static hosts in the wholesaler indicated by svcWholesalerID that
         belong to subnets of the retailer service."
    ::= { svcWholesalerInfoEntry 2 }

svcWholesalerNumDynamicHosts        OBJECT-TYPE
    SYNTAX      Unsigned32
    MAX-ACCESS  read-only
    STATUS      current
    DESCRIPTION
        "The value of svcWholesalerNumDynamicHosts indicates the number of 
         dynamic hosts in the wholesaler indicated by svcWholesalerID that
         belong to subnets of the retailer service."
    ::= { svcWholesalerInfoEntry 3 }

svcWholesalerNumDhcpLeaseStates     OBJECT-TYPE
    SYNTAX      Unsigned32
    MAX-ACCESS  read-only
    STATUS      current
    DESCRIPTION
        "The value of svcWholesalerNumDhcpLeaseStates indicates the number of
         DHCP lease states in the wholesaler indicated by svcWholesalerID that
         belong to subnets of the retailer service."
    ::= { svcWholesalerInfoEntry 4 }

svcWholesalerNumPppoeSessions       OBJECT-TYPE
    SYNTAX      Unsigned32
    MAX-ACCESS  read-only
    STATUS      current
    DESCRIPTION
        "The value of svcWholesalerNumPppoeSessions indicates the number of
         PPPoE sessions in the wholesaler indicated by svcWholesalerID that
         belong to subnets of the retailer service."
    ::= { svcWholesalerInfoEntry 5 }

svcWholesalerNumArpHosts            OBJECT-TYPE
    SYNTAX      Unsigned32
    MAX-ACCESS  read-only
    STATUS      current
    DESCRIPTION
        "The value of svcWholesalerNumArpHosts indicates the number of
         ARP hosts in the wholesaler indicated by svcWholesalerID that
         belong to subnets of the retailer service."
    ::= { svcWholesalerInfoEntry 6 }

svcWholesalerNumDhcp6LeaseStates OBJECT-TYPE
    SYNTAX      Unsigned32
    MAX-ACCESS  read-only
    STATUS      current
    DESCRIPTION
        "The value of svcWholesalerNumDhcp6LeaseStates indicates the number of
         DHCPv6 lease states in the wholesaler indicated by svcWholesalerID that
         belong to the retailer service."
    ::= { svcWholesalerInfoEntry 7 }

svcWholesalerNumSlaacHosts OBJECT-TYPE
    SYNTAX      Unsigned32
    MAX-ACCESS  read-only
    STATUS      current
    DESCRIPTION
        "The value of svcWholesalerNumSlaacHosts indicates the number of
         SLAAC hosts in the wholesaler indicated by svcWholesalerID that
         belong to the retailer service."
    ::= { svcWholesalerInfoEntry 8 }

svcWholesalerNumStatic6Hosts OBJECT-TYPE
    SYNTAX      Unsigned32
    MAX-ACCESS  read-only
    STATUS      current
    DESCRIPTION
        "The value of svcWholesalerNumStatic6Hosts indicates the number of
         static ipv6 hosts in the wholesaler indicated by svcWholesalerID that
         belong to the retailer service."
    ::= { svcWholesalerInfoEntry 9 }

svcWholesalerNumIpoeSessions OBJECT-TYPE
    SYNTAX      Unsigned32
    MAX-ACCESS  read-only
    STATUS      current
    DESCRIPTION
        "The value of svcWholesalerNumIpoeSessions indicates the number of
         IPoE sessions in the wholesaler indicated by svcWholesalerID that
         belong to the retailer service."
    ::= { svcWholesalerInfoEntry 10 }

svcWholesalerNumIpcpHosts OBJECT-TYPE
    SYNTAX      Unsigned32
    MAX-ACCESS  read-only
    STATUS      current
    DESCRIPTION
        "The value of svcWholesalerNumIpcpHosts indicates the number of
         PPP IPCP hosts in the wholesaler indicated by svcWholesalerID that
         belong to the retailer service."
    ::= { svcWholesalerInfoEntry 11 }

-- ----------------------------------------------------------------------------
-- svcDhcpLeaseStateActionTable
--
-- This table is replaced with the svcDhcpLeaseActionTable
--
-- ----------------------------------------------------------------------------
svcDhcpLeaseStateActionTable OBJECT-TYPE
    SYNTAX          SEQUENCE OF SvcDhcpLeaseStateActionEntry
    MAX-ACCESS      not-accessible
    STATUS          obsolete
    DESCRIPTION     "The svcDhcpLeaseStateActionTable augments the
                     svcDhcpLeaseStateTable.
                     The table allows the operator to perform actions on the
                     lease state."
    ::= { tmnxSvcObjs 25 }

svcDhcpLeaseStateActionEntry OBJECT-TYPE
    SYNTAX          SvcDhcpLeaseStateActionEntry
    MAX-ACCESS      not-accessible
    STATUS          obsolete
    DESCRIPTION     "Each row entry contains parameters that allow to perform
                     an action on the corresponding lease-state."
    AUGMENTS        { svcDhcpLeaseStateEntry }
    ::= { svcDhcpLeaseStateActionTable 1 }

SvcDhcpLeaseStateActionEntry ::=
    SEQUENCE {
        svcDhcpLseStateForceRenew        TruthValue
    }

svcDhcpLseStateForceRenew OBJECT-TYPE
    SYNTAX          TruthValue
    MAX-ACCESS      read-write
    STATUS          obsolete
    DESCRIPTION     "The value of svcDhcpLseStateForceRenew allows to force the
                     DHCP client to renew its lease.

                     When the value of this object is set to 'true', the system
                     will send a forcerenew DHCP message to the client.

                     GETs and GETNEXTs on this variable return false."
    DEFVAL          { false }
    ::= { svcDhcpLeaseStateActionEntry 1 }

-- ----------------------------------------------------------------------------
-- DHCP Lease State Action Table version 2
--
-- The MAC address is part of the key to allow multiple lease states having the
-- same IP address.
--
-- ----------------------------------------------------------------------------
svcDhcpLeaseActionTable OBJECT-TYPE
    SYNTAX          SEQUENCE OF SvcDhcpLeaseActionEntry
    MAX-ACCESS      not-accessible
    STATUS          current
    DESCRIPTION     "The svcDhcpLeaseActionTable augments the
                     svcDhcpLeaseTable.
                     The table allows the operator to perform actions on the
                     lease state."
    ::= { tmnxSvcObjs 92 }

svcDhcpLeaseActionEntry OBJECT-TYPE
    SYNTAX          SvcDhcpLeaseActionEntry
    MAX-ACCESS      not-accessible
    STATUS          current
    DESCRIPTION     "Each row entry contains parameters that allow to perform
                     an action on the corresponding lease-state."
    AUGMENTS        { svcDhcpLeaseEntry }
    ::= { svcDhcpLeaseActionTable 1 }

SvcDhcpLeaseActionEntry ::=
    SEQUENCE {
        svcDhcpLeaseForceRenew        TruthValue
    }

svcDhcpLeaseForceRenew OBJECT-TYPE
    SYNTAX          TruthValue
    MAX-ACCESS      read-write
    STATUS          current
    DESCRIPTION     "The value of svcDhcpLeaseForceRenew allows to force the
                     DHCP client to renew its lease.

                     When the value of this object is set to 'true', the system
                     will send a forcerenew DHCP message to the client.

                     GETs and GETNEXTs on this variable return false."
    DEFVAL          { false }
    ::= { svcDhcpLeaseActionEntry 1 }

--
--  Nokia SROS series Service Itf DHCP6 msg type Stats Table
--
svcIfDHCP6MsgStatTable OBJECT-TYPE
    SYNTAX  SEQUENCE OF SvcIfDHCP6MsgStatEntry
    MAX-ACCESS  not-accessible
    STATUS      current
    DESCRIPTION
        "The vRtrDHCP6MsgStatTable has an entry for each interface defined
         in a service for which DHCP6 can be enabled."
    ::= { tmnxSvcObjs 26 }

svcIfDHCP6MsgStatEntry  OBJECT-TYPE
    SYNTAX      SvcIfDHCP6MsgStatEntry
    MAX-ACCESS  not-accessible
    STATUS      current
    DESCRIPTION
        "Each row entry represents a collection of counters for each DHCP6
         message type for an interface in a service.

        Entries cannot be created and deleted via SNMP SET operations."
    INDEX { svcId,
            iesIfIndex }
    ::= { svcIfDHCP6MsgStatTable 1 }

SvcIfDHCP6MsgStatEntry ::=
     SEQUENCE {
         svcIfDHCP6MsgStatsLstClrd  TimeStamp,
         svcIfDHCP6MsgStatsRcvd     Gauge32,
         svcIfDHCP6MsgStatsSent     Gauge32,
         svcIfDHCP6MsgStatsDropped  Gauge32
     }

svcIfDHCP6MsgStatsLstClrd  OBJECT-TYPE
    SYNTAX      TimeStamp
    MAX-ACCESS  read-only
    STATUS      current
    DESCRIPTION
        "The value of svcIfDHCP6MsgStatsLstClrd indicates the sysUpTime
         when the counters of this row were last reset. A value of zero for
         this object indicates that the counters have not been reset since the
         system has last been initialized." 
    ::= { svcIfDHCP6MsgStatEntry 1 }

svcIfDHCP6MsgStatsRcvd  OBJECT-TYPE
    SYNTAX      Gauge32
    MAX-ACCESS  read-only
    STATUS      current
    DESCRIPTION
        "The value of svcIfDHCP6MsgStatsRcvd indicates the number of
         DHCP6 packets were received on this service interface."
    ::= { svcIfDHCP6MsgStatEntry 2 }

svcIfDHCP6MsgStatsSent  OBJECT-TYPE
    SYNTAX      Gauge32
    MAX-ACCESS  read-only
    STATUS      current
    DESCRIPTION
        "The value of svcIfDHCP6MsgStatsSent indicates the number of
         DHCP6 packets were sent on this service interface."
    ::= { svcIfDHCP6MsgStatEntry 3 }

svcIfDHCP6MsgStatsDropped  OBJECT-TYPE
    SYNTAX      Gauge32
    MAX-ACCESS  read-only
    STATUS      current
    DESCRIPTION
        "The value of svcIfDHCP6MsgStatsDropped indicates the number of
         DHCP6 packets were dropped on this service interface."
    ::= { svcIfDHCP6MsgStatEntry 4 }

-- ----------------------------------------
-- TLS PBB Information Table
-- ----------------------------------------
svcTlsBackboneInfoTable OBJECT-TYPE
    SYNTAX          SEQUENCE OF SvcTlsBackboneInfoEntry
    MAX-ACCESS      not-accessible
    STATUS          current
    DESCRIPTION     "The svcTlsBackboneInfoTable augments the svcTlsInfoTable.
                     The table allows the operator to modify attributes of the
                     Provider Backbone Bridging feature."
    ::= { tmnxSvcObjs 27 }

svcTlsBackboneInfoEntry OBJECT-TYPE
    SYNTAX          SvcTlsBackboneInfoEntry
    MAX-ACCESS      not-accessible
    STATUS          current
    DESCRIPTION     "Each row entry contains objects that allows the
                     modification of the Provider Backbone Bridging feature
                     for a specific TLS service"
    AUGMENTS        { svcTlsInfoEntry }
    ::= { svcTlsBackboneInfoTable 1 }

SvcTlsBackboneInfoEntry ::=
    SEQUENCE {
        svcTlsBackboneSrcMac             MacAddress,
        svcTlsBackboneVplsSvcId          TmnxServId,
        svcTlsBackboneVplsSvcISID        SvcISID,
        svcTlsBackboneOperSrcMac         MacAddress,
        svcTlsBackboneOperVplsSvcISID    SvcISID,
        svcTlsBackboneLDPMacFlush        TruthValue,
        svcTlsBackboneVplsStp            TmnxEnabledDisabled,
        svcTlsBackboneLDPMacFlushNotMine TruthValue,
        svcTlsBackboneUseSapBMac         TruthValue,
        svcTlsBackboneForceQTagFwd       TruthValue,
        svcTlsBackboneUseEsBMac         TruthValue
    }

svcTlsBackboneSrcMac OBJECT-TYPE
    SYNTAX          MacAddress
    MAX-ACCESS      read-write
    STATUS          current
    DESCRIPTION     "The value of svcTlsBackboneSrcMac specifies the Backbone
                     Source MAC-Address for Provider Backbone Bridging packets.
                     If not provisioned, it defaults to the loopback chassis
                     MAC-Address.

                     An inconsistentValue error is returned if an attempt
                     is made to set this object when the value of
                     svcVplsType is not 'bVpls'."
    DEFVAL { '000000000000'h }
    ::= { svcTlsBackboneInfoEntry 1 }

svcTlsBackboneVplsSvcId OBJECT-TYPE
    SYNTAX          TmnxServId
    MAX-ACCESS      read-write
    STATUS          current
    DESCRIPTION     "The value of svcTlsBackboneVplsSvcId specifies the
                     Backbone-VPLS service associated with this service.

                     An inconsistentValue error is returned if an attempt
                     is made to set this object when the value of
                     svcVplsType is not 'iVpls'.
                     
                     Setting the value of this object to its default
                     value will also set the value of
                     svcTlsBackboneVplsStp to its default value."
    DEFVAL          { 0 }
    ::= { svcTlsBackboneInfoEntry 2 }

svcTlsBackboneVplsSvcISID OBJECT-TYPE
    SYNTAX          SvcISID
    MAX-ACCESS      read-write
    STATUS          current
    DESCRIPTION     "The value of the object svcTlsBackboneVplsSvcISID specifies
                     a 24 bit (0..16777215) service instance identifier for
                     this service. As part of the Provider Backbone Bridging
                     frames, it is used at the destination PE as a
                     demultiplexor field.

                     The default value of -1 is used to indicate the value of
                     this object is un-specified.  
                     
                     This object must be set along with svcTlsBackboneVplsSvcId.
                     An inconsistentValue error is returned if an attempt
                     is made to set this object when the value of
                     svcVplsType is not 'iVpls'."
    DEFVAL          { -1 }
    ::= { svcTlsBackboneInfoEntry 3 }

svcTlsBackboneOperSrcMac OBJECT-TYPE
    SYNTAX          MacAddress
    MAX-ACCESS      read-only
    STATUS          current
    DESCRIPTION     "The value of svcTlsBackboneOperSrcMac indicates the
                     operational Backbone Source MAC-Address for Provider
                     Backbone Bridging packets."
    ::= { svcTlsBackboneInfoEntry 4 }

svcTlsBackboneOperVplsSvcISID OBJECT-TYPE
    SYNTAX          SvcISID
    MAX-ACCESS      read-only
    STATUS          current
    DESCRIPTION     "The value of svcTlsBackboneOperVplsSvcISID indicates
                     operational value of service instance identifier used for
                     this service. As part of the Provider Backbone Bridging
                     frames, it is used at the destination PE as a
                     demultiplexor field."
    ::= { svcTlsBackboneInfoEntry 5 }

svcTlsBackboneLDPMacFlush OBJECT-TYPE
    SYNTAX          TruthValue
    MAX-ACCESS      read-write
    STATUS          current
    DESCRIPTION     "The value of svcTlsBackboneLDPMacFlush specifies whether
                     'LDP MAC withdraw all from me' message received in the
                     'iVpls' domain should attempt to generate a new 'LDP MAC
                     withdraw all from me' message in the 'bVpls' domain.
                     Generation of the 'LDP MAC withdraw all from me'
                     message is still constrained by the svcTlsMacFlushOnFail
                     value in the 'bVpls'.

                     An inconsistentValue error is returned if an attempt
                     is made to set this object when the value of
                     svcVplsType is not 'iVpls'."
    DEFVAL          { false }
    ::= { svcTlsBackboneInfoEntry 6 }

svcTlsBackboneVplsStp OBJECT-TYPE
    SYNTAX          TmnxEnabledDisabled
    MAX-ACCESS      read-write
    STATUS          current
    DESCRIPTION     "The value of svcTlsBackboneVplsStp specifies whether
                     STP is enabled on the Backbone VPLS specified by
                     svcTlsBackboneVplsSvcId.

                     An inconsistentValue error is returned if an attempt
                     is made to set this object when the value of
                     svcVplsType is not 'iVpls' or if an attempt is made
                     to set this object to enable when the value of 
                     svcTlsBackboneVplsSvcId is set to the default.
                     
                     The value of this object is set to disable
                     when the value of svcTlsBackboneVplsSvcId is set to
                     default."
    DEFVAL          { disabled }
    ::= { svcTlsBackboneInfoEntry 7 }

svcTlsBackboneLDPMacFlushNotMine OBJECT-TYPE
    SYNTAX          TruthValue
    MAX-ACCESS      read-write
    STATUS          current
    DESCRIPTION     "The value of svcTlsBackboneLDPMacFlush specifies whether
                     'LDP MAC withdraw' message received in the 'iVpls' domain
                     should attempt to generate a new 'LDP MAC withdraw' message
                     in the 'bVpls' domain. Generation of the 'LDP MAC withdraw'
                     message is still constrained by the svcTlsMacFlushOnFail
                     value in the 'bVpls'.

                     An inconsistentValue error is returned if an attempt
                     is made to set this object when the value of
                     svcVplsType is not 'iVpls'."
    DEFVAL          { false }
    ::= { svcTlsBackboneInfoEntry  8}

svcTlsBackboneUseSapBMac OBJECT-TYPE
    SYNTAX          TruthValue
    MAX-ACCESS      read-write
    STATUS          current
    DESCRIPTION     "The value of svcTlsBackboneUseSapBMac specifies 
                     whether to enable dual-homing to use source Backbone
                     MAC-Address allocated for multi-homed SAPs (assigned
                     to an MC-LAG) in the related service with svcVplsType
                     set to 'i-vpls' or with svcType set to 'epipe'."
    DEFVAL { false }
    ::= { svcTlsBackboneInfoEntry 9 }

svcTlsBackboneForceQTagFwd OBJECT-TYPE
    SYNTAX          TruthValue
    MAX-ACCESS      read-write
    STATUS          current
    DESCRIPTION     "The value of svcTlsBackboneForceQTagFwd specifies 
                     whether to enable addition of an IEEE 802.1q tag
                     after the Customer MAC address when the PBB header is
                     built, as it egresses related 'b-vpls' service.

                     An 'inconsistentValue' error is returned when the value
                     of this object is set to the non-default value and 
                     svcVplsType of this service is not set to 'i-vpls'."
    DEFVAL { false }
    ::= { svcTlsBackboneInfoEntry 10 }

svcTlsBackboneUseEsBMac OBJECT-TYPE
    SYNTAX          TruthValue
    MAX-ACCESS      read-write
    STATUS          current
    DESCRIPTION     "The value of svcTlsBackboneUseEsBMac specifies the use of
                     an ESI-BMAC(Ethernet segment identifier-Backbone Mac), derived 
                     from the svcTlsBackboneOperSrcMac and 
                     tmnxSvcSysEthSegSourceBMacLSB."
    DEFVAL { false }
    ::= {svcTlsBackboneInfoEntry 11 }

-- ------------------------------------
-- TLS MFIB Table
-- ------------------------------------
tlsMFibTable OBJECT-TYPE
    SYNTAX          SEQUENCE OF TlsMFibEntry
    MAX-ACCESS      not-accessible
    STATUS          current
    DESCRIPTION     "tlsMFibTable contains the Multicast FIB for this Tls."
    ::= { tmnxSvcObjs 28 }

tlsMFibEntry OBJECT-TYPE
    SYNTAX          TlsMFibEntry
    MAX-ACCESS      not-accessible
    STATUS          current
    DESCRIPTION     "An entry in the tlsMFibTable. Each entry indicates
                     whether  traffic from a certain source to a certain
                     multicast destination (group) needs to be forwarded or
                     blocked on the indicated SAP/SDP."
    INDEX           { svcId,
                      tlsMFibEntryType,
                      tlsMFibGrpMacAddr,
                      tlsMFibGrpInetAddrType,
                      tlsMFibGrpInetAddr,
                      tlsMFibSrcInetAddrType,
                      tlsMFibSrcInetAddr,
                      tlsMFibLocale,
                      tlsMFibPortId,
                      tlsMFibEncapValue,
                      tlsMFibSdpId,
                      tlsMFibVcId }
    ::= { tlsMFibTable 1 }

TlsMFibEntry ::=
    SEQUENCE {
        tlsMFibEntryType            INTEGER,
        tlsMFibGrpMacAddr           MacAddress,
        tlsMFibGrpInetAddrType      InetAddressType,
        tlsMFibGrpInetAddr          InetAddress,
        tlsMFibSrcInetAddrType      InetAddressType,
        tlsMFibSrcInetAddr          InetAddress,
        tlsMFibLocale               MfibLocation,
        tlsMFibPortId               TmnxPortID,
        tlsMFibEncapValue           TmnxEncapVal,
        tlsMFibSdpId                SdpId,
        tlsMFibVcId                 Unsigned32,
        tlsMFibFwdOrBlk             MfibGrpSrcFwdOrBlk,
        tlsMFibSvcId                TmnxServId
    }

tlsMFibEntryType OBJECT-TYPE
    SYNTAX          INTEGER {
                        ipBased  (1),
                        macBased (2)
                    }
    MAX-ACCESS      not-accessible
    STATUS          current
    DESCRIPTION     "The value of the object tlsMFibEntryType indicates
                     the type of this tlsMFibEntry. 

                     - macBased: entry used for macBased multicast, as for
                                 MLD-snooping and 802.1ak MMRP.
                     - ipBased:  entry used for ip_based multicast, as for
                                 IGMP-snooping and PIM-snooping."
    ::= { tlsMFibEntry 1 }

tlsMFibGrpMacAddr OBJECT-TYPE
    SYNTAX          MacAddress
    MAX-ACCESS      not-accessible
    STATUS          current
    DESCRIPTION     "The value of the object tlsMFibGrpMacAddr indicates the
                     MAC address for which this table entry contains
                     information.
                     
                     This value is only meaningful if the value of
                     tlsMFibEntryType is 'macBased (2)'."
    ::= { tlsMFibEntry 2 }

tlsMFibGrpInetAddrType OBJECT-TYPE
    SYNTAX          InetAddressType
    MAX-ACCESS      not-accessible
    STATUS          current
    DESCRIPTION     "The value of the object tlsMFibGrpInetAddrType indicates
                     the type of tlsMFibGrpInetAddr."
    ::= { tlsMFibEntry 3 }

tlsMFibGrpInetAddr OBJECT-TYPE
    SYNTAX          InetAddress (SIZE(0|4|16))
    MAX-ACCESS      not-accessible
    STATUS          current
    DESCRIPTION     "The value of the object tlsMFibGrpInetAddr indicates
                     the multicast destination IP address for which this table
                     entry contains information."
    ::= { tlsMFibEntry 4 }

tlsMFibSrcInetAddrType OBJECT-TYPE
    SYNTAX          InetAddressType
    MAX-ACCESS      not-accessible
    STATUS          current
    DESCRIPTION     "The value of tlsMFibSrcInetAddrType indicates the type
                     of tlsMFibSrcInetAddr."
    ::= { tlsMFibEntry 5 }

tlsMFibSrcInetAddr OBJECT-TYPE
    SYNTAX          InetAddress (SIZE(0|4|16))
    MAX-ACCESS      not-accessible
    STATUS          current
    DESCRIPTION     "The value of tlsMFibSrcInetAddr indicates the unicast
                     source IP address for which this table entry contains
                     information."
    ::= { tlsMFibEntry 6 }

tlsMFibLocale OBJECT-TYPE
    SYNTAX          MfibLocation
    MAX-ACCESS      not-accessible
    STATUS          current
    DESCRIPTION     "The value of tlsMFibLocale indicates if the information in
                     this entry pertains to a 'sap' or to an 'sdp'."
    ::= { tlsMFibEntry 7 }

tlsMFibPortId OBJECT-TYPE
    SYNTAX          TmnxPortID
    MAX-ACCESS      not-accessible
    STATUS          current
    DESCRIPTION     "The value of tlsMFibPortId indicates, together with the
                     object tlsMFibEncapValue, the SAP for which this entry
                     contains information.
                     
                     This value of this object is only meaningful when the
                     value of tlsMFibLocale is 'sap'. Otherwise it contains
                     the value 0."
    ::= { tlsMFibEntry 8 }

tlsMFibEncapValue OBJECT-TYPE
    SYNTAX          TmnxEncapVal
    MAX-ACCESS      not-accessible
    STATUS          current
    DESCRIPTION     "The value of tlsMFibEncapValue indicates, together with
                     the object tlsMFibPortId, the SAP for which this entry
                     contains information.

                     This value of this object is only meaningful when the
                     value of tlsMFibLocale is 'sap'. Otherwise it contains
                     the value 0."
    ::= { tlsMFibEntry 9 }

tlsMFibSdpId OBJECT-TYPE
    SYNTAX          SdpId
    MAX-ACCESS      not-accessible
    STATUS          current
    DESCRIPTION     "The value of tlsMFibSdpId indicates, together with
                     the object tlsMFibVcId, the SDP Binding for which this
                     entry contains information.

                     This value of this object is only meaningful when the
                     value of tlsMFibLocale is 'sdp'. Otherwise it contains
                     the value 0."
    ::= { tlsMFibEntry 10 }

tlsMFibVcId OBJECT-TYPE
    SYNTAX          Unsigned32
    MAX-ACCESS      not-accessible
    STATUS          current
    DESCRIPTION     " The value of tlsMFibVcId indicates, together with
                     the object tlsMFibSdpId, the SDP Binding for which this
                     entry contains information.

                     This value of this object is only meaningful when the
                     value of tlsMFibLocale is 'sdp'. Otherwise it contains
                     the value 0."
    ::= { tlsMFibEntry 11 }

tlsMFibFwdOrBlk OBJECT-TYPE
    SYNTAX          MfibGrpSrcFwdOrBlk
    MAX-ACCESS      read-only
    STATUS          current
    DESCRIPTION     "The value of tlsMFibFwdOrBlk indicates if traffic for the
                     indicated (S,G) pair will be blocked or forwarded on the
                     indicated SAP or SDP."
    ::= { tlsMFibEntry 12 }

tlsMFibSvcId OBJECT-TYPE
    SYNTAX          TmnxServId
    MAX-ACCESS      read-only
    STATUS          current
    DESCRIPTION     "The value of tlsMFibSvcId indicates the TLS service
                     to which the indicated SAP or SDP belongs."
    ::= { tlsMFibEntry 13 }

-- ----------------------------------------
-- TLS MFIB Statistics Table
-- ----------------------------------------
tlsMFibStatsTable OBJECT-TYPE
    SYNTAX          SEQUENCE OF TlsMFibStatsEntry
    MAX-ACCESS      not-accessible
    STATUS          current
    DESCRIPTION     "tlsMFibStatsTable contains statistics for the
                     entries in the IPv4 Multicast FIB for this Tls. These
                     statistics are collected by the forwarding engine."
    ::= { tmnxSvcObjs 29 }

tlsMFibStatsEntry OBJECT-TYPE
    SYNTAX          TlsMFibStatsEntry
    MAX-ACCESS      not-accessible
    STATUS          current
    DESCRIPTION     "An entry in the tlsMFibStatsTable."
    INDEX           { svcId,
                      tlsMFibStatsEntryType,
                      tlsMFibStatsGrpMacAddr,
                      tlsMFibStatsGrpInetAddrType,
                      tlsMFibStatsGrpInetAddr,
                      tlsMFibStatsSrcInetAddrType,
                      tlsMFibStatsSrcInetAddr }
    ::= { tlsMFibStatsTable 1 }

TlsMFibStatsEntry ::=
    SEQUENCE {
        tlsMFibStatsEntryType        INTEGER,
        tlsMFibStatsGrpMacAddr       MacAddress,
        tlsMFibStatsGrpInetAddrType  InetAddressType,
        tlsMFibStatsGrpInetAddr      InetAddress,
        tlsMFibStatsSrcInetAddrType  InetAddressType,
        tlsMFibStatsSrcInetAddr      InetAddress,
        tlsMFibStatsForwardedPkts    Counter64,
        tlsMFibStatsForwardedOctets  Counter64
    }

tlsMFibStatsEntryType OBJECT-TYPE
    SYNTAX          INTEGER {
                        ipBased  (1),
                        macBased (2)
                    }
    MAX-ACCESS      not-accessible
    STATUS          current
    DESCRIPTION     "The value of the object tlsMFibStatsEntryType indicates
                     the type of this tlsMFibStatsEntry.

                     - macBased: entry used for macBased multicast, as for
                                 MLD-snooping and 802.1ak MMRP.
                     - ipBased:  entry used for ip_based multicast, as for
                                 IGMP-snooping and PIM-snooping."
    ::= { tlsMFibStatsEntry 1 }

tlsMFibStatsGrpMacAddr OBJECT-TYPE
    SYNTAX          MacAddress
    MAX-ACCESS      not-accessible
    STATUS          current
    DESCRIPTION     "The value of tlsMFibStatsGrpMacAddr indicates the
                     MAC address for which this table entry contains information.

                     This value is only meaningful if the value of
                     tlsMFibStatsEntryType is 'macBased (2)'."
    ::= { tlsMFibStatsEntry 2 }

tlsMFibStatsGrpInetAddrType OBJECT-TYPE
    SYNTAX          InetAddressType
    MAX-ACCESS      not-accessible
    STATUS          current
    DESCRIPTION     "The value of tlsMFibStatsGrpInetAddrType indicates
                     the type of tlsMFibStatsGrpInetAddr."
    ::= { tlsMFibStatsEntry 3 }

tlsMFibStatsGrpInetAddr OBJECT-TYPE
    SYNTAX          InetAddress (SIZE(0|4|16))
    MAX-ACCESS      not-accessible
    STATUS          current
    DESCRIPTION     "The value of tlsMFibStatsGrpInetAddr indicates
                     the multicast destination IP address for which this table
                     entry contains information."
    ::= { tlsMFibStatsEntry 4 }

tlsMFibStatsSrcInetAddrType OBJECT-TYPE
    SYNTAX          InetAddressType
    MAX-ACCESS      not-accessible
    STATUS          current
    DESCRIPTION     "The value of tlsMFibStatsSrcInetAddrType indicates
                     the type of tlsMFibStatsSrcInetAddr."
    ::= { tlsMFibStatsEntry 5 }

tlsMFibStatsSrcInetAddr OBJECT-TYPE
    SYNTAX          InetAddress (SIZE(0|4|16))
    MAX-ACCESS      not-accessible
    STATUS          current
    DESCRIPTION     "The value of tlsMFibStatsSrcInetAddr indicates the unicast
                     source IP address for which this table entry contains
                     information."
    ::= { tlsMFibStatsEntry 6 }

tlsMFibStatsForwardedPkts OBJECT-TYPE
    SYNTAX          Counter64
    MAX-ACCESS      read-only
    STATUS          current
    DESCRIPTION     "The value of tlsMFibStatsForwardedPkts indicates
                     the number of multicast packets that were forwarded
                     to the SAPs and SDPs listed in the tlsMFibInfoTable."
    ::= { tlsMFibStatsEntry 7 }

tlsMFibStatsForwardedOctets OBJECT-TYPE
    SYNTAX          Counter64
    MAX-ACCESS      read-only
    STATUS          current
    DESCRIPTION     "The value of tlsMFibStatsForwardedOctets indicates
                     the number of octets that were forwarded to the SAPs
                     and SDPs listed in the tlsMFibInfoTable."
    ::= { tlsMFibStatsEntry 8 }

-- ----------------------------------------
-- TLS BGP Auto-Discovery Table
-- ----------------------------------------

svcTlsBgpADTableLastChanged  OBJECT-TYPE
    SYNTAX          TimeStamp
    MAX-ACCESS      read-only
    STATUS          current
    DESCRIPTION     "The value of svcTlsBgpADTableLastChanged indicates the
                     sysUpTime at the time of the last modification
                     of svcTlsBgpADTable.

                     If no changes were made to the entry since the last
                     re-initialization of the local network management subsystem,
                     then this object contains a zero value."
    ::= { tmnxSvcObjs 30 }

svcTlsBgpADTable OBJECT-TYPE
    SYNTAX          SEQUENCE OF SvcTlsBgpADEntry
    MAX-ACCESS      not-accessible
    STATUS          current
    DESCRIPTION     "svcTlsBgpADTable contains entries for BGP Auto-Discovery
                     in a VPLS service context." 
    ::= { tmnxSvcObjs 31 }

svcTlsBgpADEntry    OBJECT-TYPE
    SYNTAX          SvcTlsBgpADEntry
    MAX-ACCESS      not-accessible
    STATUS          current
    DESCRIPTION     "A BGP Auto-Discovery entry in the svcTlsBgpADTable."
    INDEX           { svcId }
    ::= { svcTlsBgpADTable 1}

SvcTlsBgpADEntry ::=    SEQUENCE {
    svcTlsBgpADRowStatus           RowStatus,
    svcTlsBgpADLastChanged         TimeStamp,
    svcTlsBgpADVplsId              TmnxVPNRouteDistinguisher,
    svcTlsBgpADVsiPrefix           Unsigned32,
    svcTlsBgpADVsiRD               TmnxVPNRouteDistinguisher,
    svcTlsBgpADExportRteTarget     TNamedItemOrEmpty,
    svcTlsBgpADVsiExportPolicy1    TPolicyStatementNameOrEmpty,
    svcTlsBgpADVsiExportPolicy2    TPolicyStatementNameOrEmpty,
    svcTlsBgpADVsiExportPolicy3    TPolicyStatementNameOrEmpty,
    svcTlsBgpADVsiExportPolicy4    TPolicyStatementNameOrEmpty,
    svcTlsBgpADVsiExportPolicy5    TPolicyStatementNameOrEmpty,
    svcTlsBgpADImportRteTarget     TNamedItemOrEmpty,
    svcTlsBgpADVsiImportPolicy1    TPolicyStatementNameOrEmpty,
    svcTlsBgpADVsiImportPolicy2    TPolicyStatementNameOrEmpty,
    svcTlsBgpADVsiImportPolicy3    TPolicyStatementNameOrEmpty,
    svcTlsBgpADVsiImportPolicy4    TPolicyStatementNameOrEmpty,
    svcTlsBgpADVsiImportPolicy5    TPolicyStatementNameOrEmpty,
    svcTlsBgpADAdminStatus         TmnxEnabledDisabled,
    svcTlsBgpADCreationOrigin      TmnxCreateOrigin
}

svcTlsBgpADRowStatus        OBJECT-TYPE
    SYNTAX          RowStatus
    MAX-ACCESS      read-create
    STATUS          current
    DESCRIPTION     "The value of svcTlsBgpADRowStatus is used for the
                     creation and deletion of BGP Auto-Discovery
                     context in a VPLS service."
    ::= { svcTlsBgpADEntry 1 }

svcTlsBgpADLastChanged        OBJECT-TYPE
    SYNTAX          TimeStamp
    MAX-ACCESS      read-only
    STATUS          current
    DESCRIPTION     "The value of svcTlsBgpADLastChanged indicates the 
                     sysUpTime at the time of the last modification of
                     this entry.
                     
                     If no changes were made to the entry since the last 
                     re-initialization of the local network management 
                     subsystem, then this object contains a zero value."
    ::= { svcTlsBgpADEntry 2 }

svcTlsBgpADVplsId        OBJECT-TYPE
    SYNTAX          TmnxVPNRouteDistinguisher
    MAX-ACCESS      read-create
    STATUS          current
    DESCRIPTION     "The value of svcTlsBgpADVplsId specifies the globally
                     unique VPLS-id for BGP Auto-Discovery in this VPLS
                     service.

                     The value of svcTlsBgpADAdminStatus cannot be 'enabled'
                     until a VPLS-id has been assigned which is not all zeros."
    DEFVAL          { '0000000000000000'H }
    ::= { svcTlsBgpADEntry 3 }

svcTlsBgpADVsiPrefix OBJECT-TYPE
    SYNTAX          Unsigned32
    MAX-ACCESS      read-create
    STATUS          current
    DESCRIPTION     "The value of svcTlsBgpADVsiPrefix specifies the
                     low-order 4 bytes used to compose the Virtual Switch
                     Instance identifier (VSI-id) to use for NLRI in BGP
                     Auto-Discovery in this VPLS service.

                     If the value of svcTlsBgpADVsiPrefix is 0, the
                     system IP address will be used."
    DEFVAL          { 0 }
    ::= { svcTlsBgpADEntry 4 }

svcTlsBgpADVsiRD     OBJECT-TYPE
    SYNTAX          TmnxVPNRouteDistinguisher
    MAX-ACCESS      read-create
    STATUS          obsolete
    DESCRIPTION     "The value of svcTlsBgpADVsiRD specifies the high-order
                     6 bytes used to compose the Virtual Switch Instance
                     identifier (VSI-id) to use for NLRI in BGP Auto-Discovery
                     in this VPLS service.

                     If the value of svcTlsBgpADVsiRD is 0x0000000000000000,
                     the lower 6 bytes of the VPLS-id, as specified by
                     svcTlsBgpADVplsId, will be used.
                     
                     This object is obsoleted and replaced with
                     svcTlsBgpVsiRD object in 8.0 release."
    DEFVAL          { '0000000000000000'H }
    ::= { svcTlsBgpADEntry 5 }

svcTlsBgpADExportRteTarget       OBJECT-TYPE
    SYNTAX          TNamedItemOrEmpty
    MAX-ACCESS      read-create
    STATUS          obsolete
    DESCRIPTION     "The value of svcTlsBgpADExportRteTarget specifies the
                     extended community name for the default export policy
                     to use for BGP Auto-Discovery in this VPLS service.

                     This object cannot be set to a non-empty if
                     svcTlsBgpADExportRteTarget has a non-empty value, 
                     otherwise an 'inconsistentValue' error will be
                     returned.
                     
                     This object is obsoleted and replaced with
                     svcTlsBgpExportRteTarget object in 8.0 release."
    DEFVAL          { "" }
    ::= { svcTlsBgpADEntry 6 }

svcTlsBgpADVsiExportPolicy1  OBJECT-TYPE
    SYNTAX          TPolicyStatementNameOrEmpty
    MAX-ACCESS      read-create
    STATUS          obsolete
    DESCRIPTION    "The value of svcTlsBgpADVsiExportPolicy1 specifies the
                    name of the first VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU.
                     
                    This object is obsoleted and replaced with 
                    svcTlsBgpVsiExportPolicy1 object in 8.0 release."
    DEFVAL { ''H }      -- the empty string
    ::= { svcTlsBgpADEntry 7 }

svcTlsBgpADVsiExportPolicy2  OBJECT-TYPE
    SYNTAX          TPolicyStatementNameOrEmpty
    MAX-ACCESS      read-create
    STATUS          obsolete
    DESCRIPTION    "The value of svcTlsBgpADVsiExportPolicy2 specifies the
                    name of the second VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU.
                     
                    This object is obsoleted and replaced with
                    svcTlsBgpVsiExportPolicy2 object in 8.0 release."
    DEFVAL { ''H }      -- the empty string
    ::= { svcTlsBgpADEntry 8 }

svcTlsBgpADVsiExportPolicy3  OBJECT-TYPE
    SYNTAX          TPolicyStatementNameOrEmpty
    MAX-ACCESS      read-create
    STATUS          obsolete
    DESCRIPTION    "The value of svcTlsBgpADVsiExportPolicy3 specifies the
                    name of the third VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with
                    svcTlsBgpVsiExportPolicy3 object in 8.0 release."
    DEFVAL { ''H }      -- the empty string
    ::= { svcTlsBgpADEntry 9 }

svcTlsBgpADVsiExportPolicy4  OBJECT-TYPE
    SYNTAX          TPolicyStatementNameOrEmpty
    MAX-ACCESS      read-create
    STATUS          obsolete
    DESCRIPTION    "The value of svcTlsBgpADVsiExportPolicy4 specifies the
                    name of the forth VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU.
                     
                    This object is obsoleted and replaced with
                    svcTlsBgpVsiExportPolicy4 object in 8.0 release."
    DEFVAL { ''H }      -- the empty string
    ::= { svcTlsBgpADEntry 10 }

svcTlsBgpADVsiExportPolicy5  OBJECT-TYPE
    SYNTAX          TPolicyStatementNameOrEmpty
    MAX-ACCESS      read-create
    STATUS          obsolete
    DESCRIPTION    "The value of svcTlsBgpADVsiExportPolicy5 specifies the
                    name of the fifth VSI export policy to be used for BGP
                    Auto-Discovery in this VPLS service.

                    If multiple policy names are specified, the policies are
                    evaluated in the order they are specified.  The first
                    policy that matches is applied.

                    The import policy name list, svcTlsBgpADVsiExportPolicy1
                    through svcTlsBgpADVsiExportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with
                    svcTlsBgpVsiExportPolicy5 object in 8.0 release."
    DEFVAL { ''H }      -- the empty string
    ::= { svcTlsBgpADEntry 11 }

svcTlsBgpADImportRteTarget       OBJECT-TYPE
    SYNTAX          TNamedItemOrEmpty
    MAX-ACCESS      read-create
    STATUS          obsolete
    DESCRIPTION     "The value of svcTlsBgpADImportRteTarget specifies the
                     extended community name for the default import policy
                     to use for BGP Auto-Discovery in this VPLS service.

                     This object cannot be set to a non-empty if
                     svcTlsBgpADImportRteTarget has a non-empty value, 
                     otherwise an 'inconsistentValue' error will be
                     returned.

                     This object is obsoleted and replaced with
                     svcTlsBgpImportRteTarget object in 8.0 release."
    DEFVAL          { "" }
    ::= { svcTlsBgpADEntry 12 }

svcTlsBgpADVsiImportPolicy1  OBJECT-TYPE
    SYNTAX          TPolicyStatementNameOrEmpty
    MAX-ACCESS      read-create
    STATUS          obsolete
    DESCRIPTION    "The value of svcTlsBgpADVsiImportPolicy1 specifies the
                    name of the first VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with
                    svcTlsBgpVsiImportPolicy1 object in 8.0 release."
    DEFVAL { ''H }      -- the empty string
    ::= { svcTlsBgpADEntry 13 }

svcTlsBgpADVsiImportPolicy2  OBJECT-TYPE
    SYNTAX          TPolicyStatementNameOrEmpty
    MAX-ACCESS      read-create
    STATUS          obsolete
    DESCRIPTION    "The value of svcTlsBgpADVsiImportPolicy2 specifies the
                    name of the second VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with
                    svcTlsBgpVsiImportPolicy2 object in 8.0 release."
    DEFVAL { ''H }      -- the empty string
    ::= { svcTlsBgpADEntry 14 }

svcTlsBgpADVsiImportPolicy3  OBJECT-TYPE
    SYNTAX          TPolicyStatementNameOrEmpty
    MAX-ACCESS      read-create
    STATUS          obsolete
    DESCRIPTION    "The value of svcTlsBgpADVsiImportPolicy3 specifies the
                    name of the third VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with 
                    svcTlsBgpVsiImportPolicy3 object in 8.0 release."
    DEFVAL { ''H }      -- the empty string
    ::= { svcTlsBgpADEntry 15 }

svcTlsBgpADVsiImportPolicy4  OBJECT-TYPE
    SYNTAX          TPolicyStatementNameOrEmpty
    MAX-ACCESS      read-create
    STATUS          obsolete
    DESCRIPTION    "The value of svcTlsBgpADVsiImportPolicy4 specifies the
                    name of the forth VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with 
                    svcTlsBgpVsiImportPolicy4 object in 8.0 release."
    DEFVAL { ''H }      -- the empty string
    ::= { svcTlsBgpADEntry 16 }

svcTlsBgpADVsiImportPolicy5  OBJECT-TYPE
    SYNTAX          TPolicyStatementNameOrEmpty
    MAX-ACCESS      read-create
    STATUS          obsolete
    DESCRIPTION    "The value of svcTlsBgpADVsiImportPolicy5 specifies the
                    name of the fifth VSI export policy to be used for BGP
                    Auto-Discovery in this VPLS service.

                    If multiple policy names are specified, the policies are
                    evaluated in the order they are specified.  The first
                    policy that matches is applied.

                    The import policy name list, svcTlsBgpADVsiImportPolicy1
                    through svcTlsBgpADVsiImportPolicy5, is handled by the SNMP
                    agent as a single entity.  When an SNMP SET request is
                    received to modify one or more of the policy names, all
                    the policy variables are first set to the empty
                    string, ''H, and then the new names are set into the
                    specified policy variables within a single SNMP SET PDU.

                    This object is obsoleted and replaced with 
                    svcTlsBgpVsiImportPolicy5 object in 8.0 release."
    DEFVAL { ''H }      -- the empty string
    ::= { svcTlsBgpADEntry 17 }

svcTlsBgpADAdminStatus        OBJECT-TYPE
    SYNTAX          TmnxEnabledDisabled
    MAX-ACCESS      read-create
    STATUS          current
    DESCRIPTION     "The value of svcTlsBgpADAdminStatus specifies the desired
                     administrative state for BGP Auto-Discovery in this VPLS
                     service."
    DEFVAL          { disabled }
    ::= { svcTlsBgpADEntry 18 }

svcTlsBgpADCreationOrigin  OBJECT-TYPE
    SYNTAX          TmnxCreateOrigin
    MAX-ACCESS      read-only
    STATUS          current
    DESCRIPTION     "The value of svcTlsBgpADCreationOrigin indicates the mechanism
                     used to create this entry."
    DEFVAL { manual }
    ::= { svcTlsBgpADEntry 19 }

-- ----------------------------------------
-- PIPE Service Table
-- ----------------------------------------
svcEpipePbbTableLastChanged  OBJECT-TYPE
    SYNTAX          TimeStamp
    MAX-ACCESS      read-only
    STATUS          current
    DESCRIPTION     "The value of svcEpipePbbTableLastChanged indicates the
                     sysUpTime at the time of the last modification of
                     svcEpipePbbTable.

                     If no changes were made to the entry since the last
                     re-initialization of the local network management subsystem,
                     then this object contains a zero value."
    ::= { tmnxSvcObjs 36 }

svcEpipePbbTable OBJECT-TYPE
    SYNTAX          SEQUENCE OF SvcEpipePbbEntry
    MAX-ACCESS      not-accessible
    STATUS          current
    DESCRIPTION     "The svcEpipePbbTable contains objects related to Provider
                     Backbone Bridging (PBB) feature as relates to 'epipe'
                     services.
                     
                     Entries are created and destroyed using svcEpipePbbRowStatus
                     object."
    ::= { tmnxSvcObjs 37 }

svcEpipePbbEntry OBJECT-TYPE
    SYNTAX          SvcEpipePbbEntry
    MAX-ACCESS      not-accessible
    STATUS          current
    DESCRIPTION     "Each row entry contains objects that allows the
                     modification of the PBB objects for an 'epipe' service."
    INDEX        { svcId }
    ::= { svcEpipePbbTable 1 }

SvcEpipePbbEntry ::=
    SEQUENCE {
        svcEpipePbbRowStatus               RowStatus,
        svcEpipePbbLastChngd               TimeStamp,
        svcEpipePbbBvplsSvcId              TmnxServId,
        svcEpipePbbBvplsDstMac             MacAddress,
        svcEpipePbbSvcISID                 SvcISID,
        svcEpipePbbOperState               ServiceOperStatus,
        svcEpipePbbFlooding                TruthValue,
        svcEpipePbbLastStatusChange        TimeStamp,
        svcEpipePbbBvplsOperDstMac         MacAddress,
        svcEpipePbbBvplsDstMacName         TNamedItemOrEmpty
    }

svcEpipePbbRowStatus OBJECT-TYPE
    SYNTAX          RowStatus
    MAX-ACCESS      read-create
    STATUS          current
    DESCRIPTION     "The value of svcEpipePbbRowStatus is used for the
                     creation and deletion of Provider Backbone Bridging
                     information in a EPIPE service.

                     To create an entry in the table, svcEpipePbbBvplsSvcId,
                     svcEpipePbbSvcISID objects must be set along with
                     svcEpipePbbBvplsDstMac or svcEpipePbbBvplsDstMacName object
                     set to non-default value."
    ::= { svcEpipePbbEntry 1 }

svcEpipePbbLastChngd        OBJECT-TYPE
    SYNTAX          TimeStamp
    MAX-ACCESS      read-only
    STATUS          current
    DESCRIPTION     "The value of svcEpipePbbLastChngd indicates the sysUpTime at
                     the time of the last modification of this entry.
                     
                     If no changes were made to the entry since the last 
                     re-initialization of the local network management 
                     subsystem, then this object contains a zero value."
    ::= { svcEpipePbbEntry 2 }

svcEpipePbbBvplsSvcId OBJECT-TYPE
    SYNTAX          TmnxServId
    MAX-ACCESS      read-create
    STATUS          current
    DESCRIPTION     "The value of svcEpipePbbBvplsSvcId specifies the
                     Backbone-VPLS service for the PBB tunnel associated with
                     this service.

                     This object must be set at the creation time and can not
                     be modified later."
    ::= { svcEpipePbbEntry 3 }

svcEpipePbbBvplsDstMac OBJECT-TYPE
    SYNTAX          MacAddress
    MAX-ACCESS      read-create
    STATUS          current
    DESCRIPTION     "The value of svcEpipePbbBvplsDstMac specifies the Backbone
                     Destination MAC-Address for Provider Backbone Bridging
                     packets.

                     An 'inconsistentValue' error is returned if 
                     svcEpipePbbBvplsDstMac or svcEpipePbbBvplsDstMacName object
                     is not set to non-default value."
    DEFVAL { '000000000000'h }
    ::= { svcEpipePbbEntry 4 }

svcEpipePbbSvcISID OBJECT-TYPE
    SYNTAX          SvcISID
    MAX-ACCESS      read-create
    STATUS          current
    DESCRIPTION     "The value of the object svcEpipePbbSvcISID specifies
                     a 24 bit (0..16777215) service instance identifier for the
                     PBB tunnel associated with this service.
                     
                     As part of the Provider Backbone Bridging frames, it is
                     used at the destination PE as a demultiplexor field.

                     This object must be set along with svcEpipePbbBvplsSvcId."
    ::= { svcEpipePbbEntry 5 }

svcEpipePbbOperState OBJECT-TYPE
    SYNTAX          ServiceOperStatus
    MAX-ACCESS      read-only
    STATUS          current
    DESCRIPTION     "The value of the object svcEpipePbbOperState indicates the
                     operating state of PBB tunnel associated with this service."
    ::= { svcEpipePbbEntry 6 }

svcEpipePbbFlooding OBJECT-TYPE
    SYNTAX          TruthValue
    MAX-ACCESS      read-only
    STATUS          current
    DESCRIPTION     "The value of the object svcEpipePbbFlooding indicates
                     the state for traffic flowing into the Backbone-VPLS
                     through PBB tunnel.

                     If the backbone-destination MAC is found in the FDB of
                     Backbone-VPLS then traffic will be sent to specific SAP/SDP
                     and this object will be set to 'false'.
                     
                     In case of SPB Managed Backbone-VPLS, if
                     backbone-destination MAC is not found in the FDB of
                     Backbone-VPLS then traffic will not be sent out of any
                     SAP/SDP and this object will be set to 'false'.
                     Otherwise, traffic will be flooded to all SAP/SDP
                     bindings in the Backbone-VPLS and the object will be set
                     to 'true'."
    ::= { svcEpipePbbEntry 7 }

svcEpipePbbLastStatusChange OBJECT-TYPE
    SYNTAX          TimeStamp
    MAX-ACCESS      read-only
    STATUS          current
    DESCRIPTION     "The value of the object svcEpipePbbLastStatusChange
                     indicates the value of sysUpTime at the time of the most
                     recent operating status change to this tunnel."
    ::= { svcEpipePbbEntry 8 }

svcEpipePbbBvplsOperDstMac OBJECT-TYPE
    SYNTAX          MacAddress
    MAX-ACCESS      read-only
    STATUS          current
    DESCRIPTION     "The value of svcEpipePbbBvplsOperDstMac indicates the
                     operational Backbone Destination MAC-Address for Provider
                     Backbone Bridging packets."
    ::= { svcEpipePbbEntry 9 }

svcEpipePbbBvplsDstMacName OBJECT-TYPE
    SYNTAX          TNamedItemOrEmpty
    MAX-ACCESS      read-create
    STATUS          current
    DESCRIPTION     "The value of svcEpipePbbBvplsDstMacName specifies the
                     Backbone Destination MAC-Address-Name for Provider
                     Backbone Bridging packets.

                     An 'inconsistentValue' error is returned if 
                     svcEpipePbbBvplsDstMac or svcEpipePbbBvplsDstMacName object
                     is not set to non-default value."
    DEFVAL  { ''H }
    ::= { svcEpipePbbEntry 10 }


-- -------------------------------------
-- TLS PIP uplink Table
-- -------------------------------------
tlsPipInfoTable OBJECT-TYPE
    SYNTAX          SEQUENCE OF TlsPipInfoEntry
    MAX-ACCESS      not-accessible
    STATUS          current
    DESCRIPTION
        "A table that contains TLS PIP (Provider Internal Port) uplink
        information. PIP is the virtual link between I and B components of PBB
        (Provider Backbone Bridging) model. I component refers to a service
        with svcVplsType set to 'iVpls (3)' and B component refers to a service
        with svcVplsType set to 'bVpls (2)'. When any form of STP is enabled in
        the iVpls domain, the PIP uplink is modeled as a regular STP port."
    ::= { tmnxSvcObjs 40 }

tlsPipInfoEntry OBJECT-TYPE
    SYNTAX          TlsPipInfoEntry
    MAX-ACCESS      not-accessible
    STATUS          current
    DESCRIPTION     "TLS specific information about PIP uplink."
    INDEX           { svcId }
    ::= { tlsPipInfoTable 1 }

TlsPipInfoEntry ::=
    SEQUENCE {
        tlsPipStpPortState              TStpPortState,
        tlsPipStpPortRole               StpPortRole,
        tlsPipStpDesignatedBridge       BridgeId,
        tlsPipStpDesignatedPort         Integer32,
        tlsPipStpException              StpExceptionCondition,
        tlsPipStpForwardTransitions     Counter32,
        tlsPipStpInConfigBpdus          Counter32,
        tlsPipStpInTcnBpdus             Counter32,
        tlsPipStpInRstBpdus             Counter32,
        tlsPipStpInMstBpdus             Counter32,
        tlsPipStpInBadBpdus             Counter32,
        tlsPipStpOutConfigBpdus         Counter32,
        tlsPipStpOutTcnBpdus            Counter32,
        tlsPipStpOutRstBpdus            Counter32,
        tlsPipStpOutMstBpdus            Counter32,
        tlsPipStpOperStatus             ServiceOperStatus,
        tlsPipStpMvplsPruneState        MvplsPruneState,
        tlsPipStpOperProtocol           StpProtocol,
        tlsPipStpPortNum                Unsigned32,
        tlsPipStpInsideRegion           TruthValue,
        tlsPipInTcBitBpdus              Counter32,
        tlsPipOutTcBitBpdus             Counter32
    }

tlsPipStpPortState OBJECT-TYPE
    SYNTAX          TStpPortState
    MAX-ACCESS      read-only
    STATUS          current
    DESCRIPTION
        "The value of tlsPipStpPortState indicates the PIP uplink's current
        state as defined by application of the Spanning Tree Protocol. This
        state controls what action PIP uplink takes on reception of a frame.
        If the bridge has detected a port that is malfunctioning it will
        place that port into the 'broken (6)' state."
    ::= { tlsPipInfoEntry 1 }

tlsPipStpPortRole OBJECT-TYPE
    SYNTAX          StpPortRole
    MAX-ACCESS      read-only
    STATUS          current
    DESCRIPTION
        "The value of tlsPipStpPortRole indicates the current role of the PIP
        uplink as defined by the Rapid Spanning Tree Protocol."
    ::= { tlsPipInfoEntry 2 }

tlsPipStpDesignatedBridge OBJECT-TYPE
    SYNTAX          BridgeId
    MAX-ACCESS      read-only
    STATUS          current
    DESCRIPTION
        "The value of tlsPipStpDesignatedBridge indicates the Bridge Identifier
        of the bridge which this PIP uplink considers to be the Designated
        Bridge for this port's segment."
    ::= { tlsPipInfoEntry 3 }

tlsPipStpDesignatedPort OBJECT-TYPE
    SYNTAX          Integer32
    MAX-ACCESS      read-only
    STATUS          current
    DESCRIPTION
        "The value of tlsPipStpDesignatedPort indicates the Port Identifier of
        the port on the Designated Bridge for this port's segment."
    ::= { tlsPipInfoEntry 4 }

tlsPipStpException OBJECT-TYPE
    SYNTAX          StpExceptionCondition
    MAX-ACCESS      read-only
    STATUS          current
    DESCRIPTION     "The value of the object tlsPipStpException indicates
                     whether an STP exception condition is present on this
                     Pip.
                     - none : no exception condition found.
                     - oneWayCommuniation : The neighbor RSTP peer on this link
                                            is not able to detect our presence.
                     - downstreamLoopDetected :A loop is detected on this link."
    ::= { tlsPipInfoEntry 5 }

tlsPipStpForwardTransitions OBJECT-TYPE
    SYNTAX          Counter32
    MAX-ACCESS      read-only
    STATUS          current
    DESCRIPTION     "The value of the object tlsPipStpForwardTransitions
                     indicates the number of times this port has transitioned
                     from the Learning state to the Forwarding state."
    ::= { tlsPipInfoEntry 6 }

tlsPipStpInConfigBpdus OBJECT-TYPE
    SYNTAX          Counter32
    MAX-ACCESS      read-only
    STATUS          current
    DESCRIPTION     "The value of the object tlsPipStpInConfigBpdus indicates
                     the number of Configuration BPDUs received on this
                     PIP uplink."
    ::= { tlsPipInfoEntry 7 }

tlsPipStpInTcnBpdus OBJECT-TYPE
    SYNTAX          Counter32
    MAX-ACCESS      read-only
    STATUS          current
    DESCRIPTION     "The value of the object  tlsPipStpInTcnBpdus indicates the
                     number of Topology Change Notification BPDUs received on
                     this PIP uplink."
    ::= { tlsPipInfoEntry 8 }

tlsPipStpInRstBpdus OBJECT-TYPE
    SYNTAX          Counter32
    MAX-ACCESS      read-only
    STATUS          current
    DESCRIPTION     "The value of the object  tlsPipStpInRstBpdus indicates
                     the number of Rapid Spanning Tree (RST) BPDUs received on
                     this PIP uplink."
    ::= { tlsPipInfoEntry 9 }

tlsPipStpInMstBpdus OBJECT-TYPE
    SYNTAX          Counter32
    MAX-ACCESS      read-only
    STATUS          current
    DESCRIPTION     "The value of the object tlsPipStpInMstBpdus indicates
                     the number of Multiple Spanning Tree (MST) BPDUs received
                     on this PIP uplink."
    ::= { tlsPipInfoEntry 10 }

tlsPipStpInBadBpdus OBJECT-TYPE
    SYNTAX          Counter32
    MAX-ACCESS      read-only
    STATUS          current
    DESCRIPTION     "This object specifies the number of bad
                     BPDUs received on this PIP uplink."
    ::= { tlsPipInfoEntry 11 }

tlsPipStpOutConfigBpdus OBJECT-TYPE
    SYNTAX          Counter32
    MAX-ACCESS      read-only
    STATUS          current
    DESCRIPTION     "The value of the object tlsPipStpOutConfigBpdus indicates
                     the number of Configuration BPDUs sent out this PIP uplink."
    ::= { tlsPipInfoEntry 12 }

tlsPipStpOutTcnBpdus OBJECT-TYPE
    SYNTAX          Counter32
    MAX-ACCESS      read-only
    STATUS          current
    DESCRIPTION     "This object specifies the number of Topology
                     Change Notification BPDUs sent out this PIP uplink."
    ::= { tlsPipInfoEntry 13 }

tlsPipStpOutRstBpdus OBJECT-TYPE
    SYNTAX          Counter32
    MAX-ACCESS      read-only
    STATUS          current
    DESCRIPTION     "The value of the  object tlsPipStpOutRstBpdus indicates
                     the number of Rapid Spanning Tree (RST) BPDUs sent out on
                     this PIP uplink."
    ::= { tlsPipInfoEntry 14 }

tlsPipStpOutMstBpdus OBJECT-TYPE
    SYNTAX          Counter32
    MAX-ACCESS      read-only
    STATUS          current
    DESCRIPTION     "The value of the object tlsPipStpOutMstBpdus indicates
                     the number of Multiple Spanning Tree (MST) BPDUs sent out
                     on this PIP uplink."
    ::= { tlsPipInfoEntry 15 }

tlsPipStpOperStatus OBJECT-TYPE
    SYNTAX          ServiceOperStatus
    MAX-ACCESS      read-only
    STATUS          current
    DESCRIPTION     "The value of the object tlsPipStpOperStatus indicates the
                     operational status of this PIP uplink."
    ::= { tlsPipInfoEntry 16 }

tlsPipStpMvplsPruneState OBJECT-TYPE
    SYNTAX          MvplsPruneState
    MAX-ACCESS      read-only
    STATUS          current
    DESCRIPTION     "The value of tlsPipStpMvplsPruneState indicates the mVPLS
                     prune state of this PIP uplink.  The state reflects
                     whether or not this uplink is pruned by the STP instance
                     running in the mVPLS instance."
    ::= { tlsPipInfoEntry 17 }

tlsPipStpOperProtocol OBJECT-TYPE
    SYNTAX          StpProtocol
    MAX-ACCESS      read-only
    STATUS          current
    DESCRIPTION     "The value of tlsPipStpOperProtocol indicates whether 'stp',
                    'rstp' or 'mstp' is running on this PIP uplink. If the
                    protocol is not enabled on this PIP uplink, the value
                    'notApplicable' is returned."
    ::= { tlsPipInfoEntry 18 }

tlsPipStpPortNum OBJECT-TYPE
    SYNTAX          Unsigned32 (0..4094)
    MAX-ACCESS      read-only
    STATUS          current
    DESCRIPTION     "The value of the object tlsPipStpPortNum specifies the
                     value of the port number field which is contained in the
                     least significant 12 bits of the 16-bit Port ID associated
                     with this PIP uplink."
    ::= { tlsPipInfoEntry 19 }
    
tlsPipStpInsideRegion OBJECT-TYPE
    SYNTAX          TruthValue
    MAX-ACCESS      read-only
    STATUS          current
    DESCRIPTION     "The value of the object tlsPipStpInsideRegion indicates
                     whether the network connected to the PIP is in the same
                     MST region. It corresponds to the parameter 'infoInternal'
                     in 802.1Q."
    ::= { tlsPipInfoEntry 20 }
    
tlsPipInTcBitBpdus OBJECT-TYPE
    SYNTAX          Counter32
    MAX-ACCESS      read-only
    STATUS          current
    DESCRIPTION     "The value of the object  tlsPipInTcBitBpdus indicates the
                     number of BPDUs received on this PIP uplink
                     with the Topology Change bit set."
    ::= { tlsPipInfoEntry 21 }

tlsPipOutTcBitBpdus OBJECT-TYPE
    SYNTAX          Counter32
    MAX-ACCESS      read-only
    STATUS          current
    DESCRIPTION     "This object specifies the number of BPDUs sent out
                     this PIP uplink with the Topology Change bit set."
    ::= { tlsPipInfoEntry 22 }

-- -----------------------------------------
-- PIP TLS MSTI Table
-- -----------------------------------------
tlsPipMstiTable OBJECT-TYPE
    SYNTAX          SEQUENCE OF TlsPipMstiEntry
    MAX-ACCESS      not-accessible
    STATUS          current
    DESCRIPTION
        "This table contains Multiple Spanning Tree Instance information for
        the PIP uplink. Each management VPLS running MSTP can have upto 15
        MSTI. An entry in this table is automatically created when a
        tlsMstiEntry is created."
    ::= { tmnxSvcObjs 41 }

tlsPipMstiEntry OBJECT-TYPE
    SYNTAX          TlsPipMstiEntry
    MAX-ACCESS      not-accessible
    STATUS          current
    DESCRIPTION     "Information about a specific MSTI for a PIP uplink."
    INDEX           { svcId, tlsMstiInstanceId}
    ::= { tlsPipMstiTable 1 }

TlsPipMstiEntry ::=
    SEQUENCE {
        tlsPipMstiPortRole          StpPortRole,
        tlsPipMstiPortState         TStpPortState,
        tlsPipMstiDesignatedBridge  BridgeId,
        tlsPipMstiDesignatedPort    Integer32
    }

tlsPipMstiPortRole OBJECT-TYPE
    SYNTAX          StpPortRole
    MAX-ACCESS      read-only
    STATUS          current
    DESCRIPTION     "tlsPipMstiPortRole indicates the current role of the
                     PIP uplink in the MSTI as defined by the Spanning Tree
                     Protocol."
    ::= { tlsPipMstiEntry 1 }

tlsPipMstiPortState OBJECT-TYPE
    SYNTAX          TStpPortState
    MAX-ACCESS      read-only
    STATUS          current
    DESCRIPTION     "The value of the object tlsPipMstiPortState indicates the
                     port's current state as defined by application of the
                     Spanning Tree Protocol. This state controls what action a
                     port takes on reception of a frame. If the bridge has
                     detected a port that is malfunctioning it will
                     place that port into the broken(6) state."
    ::= { tlsPipMstiEntry 2 }

tlsPipMstiDesignatedBridge OBJECT-TYPE
    SYNTAX          BridgeId
    MAX-ACCESS      read-only
    STATUS          current
    DESCRIPTION     "The value of the object tlsPipMstiDesignatedBridge
                     indicates  the Bridge Identifier of the bridge which this
                     port considers to be the Designated Bridge for this port's
                     segment for this MSTI."
    ::= { tlsPipMstiEntry 3 }

tlsPipMstiDesignatedPort OBJECT-TYPE
    SYNTAX          Integer32
    MAX-ACCESS      read-only
    STATUS          current
    DESCRIPTION     "The value of the object tlsPipMstiDesignatedPort indicates
                     the Port Identifier of the port on the Designated Bridge
                     for this port's segment for this MSTI."
    ::= { tlsPipMstiEntry 4 }

-- ----------------------
-- System service objects
-- ----------------------
svcTotalFdbMimDestIdxEntries OBJECT-TYPE
    SYNTAX         Unsigned32
    MAX-ACCESS     read-only
    STATUS         current
    DESCRIPTION    "The value of the object svcTotalFdbMimDestIdxEntries
                    indicates the number of system wide Backbone MAC address
                    indices in use."
    ::= { tmnxSvcObjs 42 }

-- ----------------------------------------
-- DHCP Managed Route Table
-- ----------------------------------------
svcDhcpManagedRouteTable OBJECT-TYPE
    SYNTAX          SEQUENCE OF SvcDhcpManagedRouteEntry
    MAX-ACCESS      not-accessible
    STATUS          current
    DESCRIPTION     "A table that contains DHCP managed routes.
    
                    This table is due to be obsoleted in a future release,
                    use the tmnxSvcDhcpMRtTable instead."
    ::= { tmnxSvcObjs 43 }

svcDhcpManagedRouteEntry OBJECT-TYPE
    SYNTAX          SvcDhcpManagedRouteEntry
    MAX-ACCESS      not-accessible
    STATUS          current
    DESCRIPTION     "A specific DHCP managed route."
    INDEX           { svcId,
                      svcDhcpLeaseCiAddrType,
                      svcDhcpLeaseCiAddr,
                      svcDhcpManagedRouteInetAddrType,
                      svcDhcpManagedRouteInetAddr,
                      svcDhcpManagedRoutePrefixLen }
    ::= { svcDhcpManagedRouteTable 1 }

SvcDhcpManagedRouteEntry ::=
    SEQUENCE {
        svcDhcpManagedRouteInetAddrType  InetAddressType,
        svcDhcpManagedRouteInetAddr      InetAddress,
        svcDhcpManagedRoutePrefixLen     InetAddressPrefixLength,
        svcDhcpManagedRouteStatus        TmnxManagedRouteStatus
       ,svcDhcpManagedRouteMetric        TmnxRadiusFramedRouteMetric,
        svcDhcpManagedRoutePreference    TmnxRadiusFramedRoutePreference,
        svcDhcpManagedRouteTag           TmnxRadiusFramedRouteTag             
    }

svcDhcpManagedRouteInetAddrType OBJECT-TYPE
    SYNTAX          InetAddressType
    MAX-ACCESS      not-accessible
    STATUS          current
    DESCRIPTION     "The value of svcDhcpManagedRouteInetAddrType indicates
                     the address type of svcDhcpManagedRouteInetAddr."
    ::= { svcDhcpManagedRouteEntry 1 }

svcDhcpManagedRouteInetAddr OBJECT-TYPE
    SYNTAX          InetAddress (SIZE(4|16))
    MAX-ACCESS      not-accessible
    STATUS          current
    DESCRIPTION     "The value of svcDhcpManagedRouteInetAddr indicates
                     the IP address of the managed route."
    ::= { svcDhcpManagedRouteEntry 2 }

svcDhcpManagedRoutePrefixLen OBJECT-TYPE
    SYNTAX          InetAddressPrefixLength (0..128)
    MAX-ACCESS      not-accessible
    STATUS          current
    DESCRIPTION     "The value of svcDhcpManagedRoutePrefixLen indicates
                     the prefix length of the subnet associated with
                     svcDhcpManagedRouteInetAddr."
    ::= { svcDhcpManagedRouteEntry 3 }

svcDhcpManagedRouteStatus OBJECT-TYPE
    SYNTAX          TmnxManagedRouteStatus
    MAX-ACCESS      read-only
    STATUS          current
    DESCRIPTION     "The value of svcDhcpManagedRouteStatus indicates
                     the state of this managed route."
    ::= { svcDhcpManagedRouteEntry 4 }

svcDhcpManagedRouteMetric OBJECT-TYPE
    SYNTAX          TmnxRadiusFramedRouteMetric
    MAX-ACCESS      read-only
    STATUS          current
    DESCRIPTION     "The value of tmnxSubSlaacMRtMetric indicates
                     the metric of this managed route as specified
                     in the RADIUS option 22 Framed-Route or 
                     option 99 Framed-IPv6-Route."
    ::= { svcDhcpManagedRouteEntry 5 }

svcDhcpManagedRoutePreference OBJECT-TYPE
    SYNTAX          TmnxRadiusFramedRoutePreference
    MAX-ACCESS      read-only
    STATUS          current
    DESCRIPTION     "The value of tmnxSubSlaacMRtPreference indicates
                     the preference of this managed route as specified
                     in the RADIUS option 22 Framed-Route or 
                     option 99 Framed-IPv6-Route."
    ::= { svcDhcpManagedRouteEntry 6 }

svcDhcpManagedRouteTag OBJECT-TYPE
    SYNTAX          TmnxRadiusFramedRouteTag
    MAX-ACCESS      read-only
    STATUS          current
    DESCRIPTION     "The value of tmnxSubSlaacMRtTag indicates
                     the tag of this managed route as specified
                     in the RADIUS option 22 Framed-Route or 
                     option 99 Framed-IPv6-Route."
    ::= { svcDhcpManagedRouteEntry 7 }

-- --------------------------------------------------------
--  svcArpHostTable
-- --------------------------------------------------------

svcArpHostTableLastChanged         OBJECT-TYPE
    SYNTAX       TimeStamp
    MAX-ACCESS   read-only
    STATUS       current
    DESCRIPTION
        "The value of svcArpHostTableLastChanged indicates the
         sysUpTime at the time of the last modification of an entry in the
         svcArpHostTable.

         If there were no changes in the table since the last re-initialization
         of the local network management subsystem, then this object
         contains a zero value."
    ::= { tmnxSvcObjs 44 }


svcArpHostTable OBJECT-TYPE
    SYNTAX      SEQUENCE OF SvcArpHostEntry
    MAX-ACCESS  not-accessible
    STATUS      current
    DESCRIPTION
        "A table that contains ARP hosts."
    ::= { tmnxSvcObjs 45 }

svcArpHostEntry OBJECT-TYPE
    SYNTAX      SvcArpHostEntry
    MAX-ACCESS  not-accessible
    STATUS      current
    DESCRIPTION
        "Information about a specific ARP host."
    INDEX { svcId,
            svcArpHostIpAddrType,
            svcArpHostIpAddr }
    ::= { svcArpHostTable 1 }

SvcArpHostEntry ::=
    SEQUENCE {
        svcArpHostIpAddrType             InetAddressType,
        svcArpHostIpAddr                 InetAddress,
        svcArpHostLocale                 ServAccessLocation,
        svcArpHostSapPortId              TmnxPortID,
        svcArpHostSapEncapValue          TmnxEncapVal,
        svcArpHostSdpId                  SdpId,
        svcArpHostVcId                   Unsigned32,
        svcArpHostSessionTimeout         Unsigned32,
        svcArpHostStart                  DateAndTime,
        svcArpHostLastAuth               DateAndTime,
        svcArpHostRefresh                DateAndTime,
        svcArpHostRemainingTime          Unsigned32,
        svcArpHostShcvOperState          ServShcvOperState, 
        svcArpHostShcvChecks             Unsigned32,
        svcArpHostShcvReplies            Unsigned32, 
        svcArpHostShcvReplyTime          TimeStamp, 
        svcArpHostSubscrIdent            TmnxSubIdentStringOrEmpty, 
        svcArpHostSubProfString          TmnxSubProfileStringOrEmpty, 
        svcArpHostSlaProfString          TmnxSlaProfileStringOrEmpty, 
        svcArpHostAppProfString          TmnxAppProfileStringOrEmpty, 
        svcArpHostAncpString             TmnxAncpStringOrZero, 
        svcArpHostInterDestId            TmnxSubMgtIntDestIdOrEmpty,
        svcArpHostRetailerSvcId          TmnxServId, 
        svcArpHostRetailerIf             InterfaceIndexOrZero,
        svcArpHostMacAddr                MacAddress,
        svcArpHostPersistKey             Unsigned32,
        svcArpHostCategoryMapName        TNamedItemOrEmpty,
        svcArpHostRadiusClassAttr        OCTET STRING,
        svcArpHostRadiusUserName         DisplayString,
        svcArpHostOriginSubscrId         ArpHostInfoOrigin,
        svcArpHostOriginStrings          ArpHostInfoOrigin
    }
    
svcArpHostIpAddrType OBJECT-TYPE
    SYNTAX          InetAddressType
    MAX-ACCESS      not-accessible
    STATUS          current
    DESCRIPTION     "The value of svcArpHostIpAddrType indicates the
                     address type of svcArpHostIpAddr."
    ::= { svcArpHostEntry 1 }

svcArpHostIpAddr OBJECT-TYPE
    SYNTAX          InetAddress (SIZE(0|4))
    MAX-ACCESS      not-accessible
    STATUS          current
    DESCRIPTION     "The value of svcArpHostIpAddr indicates the IP
                     address of the ARP host."
    ::= { svcArpHostEntry 2 }

svcArpHostLocale OBJECT-TYPE
    SYNTAX          ServAccessLocation
    MAX-ACCESS      read-only
    STATUS          current
    DESCRIPTION     "The value of svcArpHostLocale indicates if the ARP
                     Host is learned via a SAP or spoke SDP."
    ::= { svcArpHostEntry 3 }

svcArpHostSapPortId OBJECT-TYPE
    SYNTAX          TmnxPortID
    MAX-ACCESS      read-only
    STATUS          current
    DESCRIPTION     "When the value of svcArpHostLocale is 'sap', the
                     object svcArpHostSapPortId along with the object
                     svcArpHostSapEncapValue, indicates the SAP where this
                     ARP host is learned. This object is otherwise
                     insignificant and contains the value 0."
    ::= { svcArpHostEntry 4 }

svcArpHostSapEncapValue OBJECT-TYPE
    SYNTAX          TmnxEncapVal
    MAX-ACCESS      read-only
    STATUS          current
    DESCRIPTION     "When the value of svcArpHostLocale is 'sap', the
                     object svcArpHostSapPortId along with the object
                     svcArpHostSapEncapValue, indicates the SAP where this
                     ARP host is learned. This object is otherwise
                     insignificant and contains the value 0."
    ::= { svcArpHostEntry 5 }

svcArpHostSdpId OBJECT-TYPE
    SYNTAX          SdpId
    MAX-ACCESS      read-only
    STATUS          current
    DESCRIPTION     "When the value of svcArpHostLocale is 'sdp', the
                     object svcArpHostSdpId, along with the object
                     svcArpHostVcId, indicates the SDP Binding where this
                     ARP host is learned. This object is otherwise
                     insignificant and contains the value 0."
    ::= { svcArpHostEntry 6 }

svcArpHostVcId OBJECT-TYPE
    SYNTAX          Unsigned32
    MAX-ACCESS      read-only
    STATUS          current
    DESCRIPTION     "When the value of svcArpHostLocale is 'sdp', the
                     object svcArpHostVcId, along with the object
                     svcArpHostSdpId, indicates the SDP Binding where this
                     ARP host is learned. This object is otherwise
                     insignificant and contains the value 0."
    ::= { svcArpHostEntry 7 }

svcArpHostSessionTimeout OBJECT-TYPE
    SYNTAX          Unsigned32
    MAX-ACCESS      read-only
    STATUS          current
    DESCRIPTION     "The value of svcArpHostSessionTimeout indicates the 
                     session timeout of this ARP host.
                     
                     The session timeout can be configured in the Radius server.
                     
                     If no session timeout is specified, its value is equal to
                     the value of the object svcArpHostDefaultSessionTimeout."
    ::= { svcArpHostEntry 8 }

svcArpHostStart OBJECT-TYPE
    SYNTAX          DateAndTime (SIZE (11))
    MAX-ACCESS      read-only
    STATUS          current
    DESCRIPTION     "The value of svcArpHostStart indicates the time of the 
                     creation of this entry."
    ::= { svcArpHostEntry 9 }

svcArpHostLastAuth OBJECT-TYPE
    SYNTAX          DateAndTime (SIZE (11))
    MAX-ACCESS      read-only
    STATUS          current
    DESCRIPTION     "The value of svcArpHostLastAuth indicates the time of the 
                     last authentication."
    ::= { svcArpHostEntry 10 }

svcArpHostRefresh OBJECT-TYPE
    SYNTAX          DateAndTime (SIZE (11))
    MAX-ACCESS      read-only
    STATUS          current
    DESCRIPTION     "The value of svcArpHostRefresh indicates the time of the 
                     last refresh of this ARP host.
                     
                     Note that not every refresh requires authentication."
    ::= { svcArpHostEntry 11 }

svcArpHostRemainingTime OBJECT-TYPE
    SYNTAX          Unsigned32
    UNITS           "seconds"
    MAX-ACCESS      read-only
    STATUS          current
    DESCRIPTION     "The value of svcArpHostRemainingTime indicates the
                     remaining time of this ARP host."
    ::= { svcArpHostEntry 12 }

svcArpHostShcvOperState OBJECT-TYPE
    SYNTAX          ServShcvOperState
    MAX-ACCESS      read-only
    STATUS          current
    DESCRIPTION     "The value of svcArpHostShcvOperState indicates the
                     state of the subscriber host connectivity check for
                     this ARP host."
    ::= { svcArpHostEntry 13 }

svcArpHostShcvChecks OBJECT-TYPE
    SYNTAX          Unsigned32
    MAX-ACCESS      read-only
    STATUS          current
    DESCRIPTION     "The value of svcArpHostShcvChecks indicates the
                     number of host connectivity check requests for 
                     this ARP host."
    ::= { svcArpHostEntry 14 }

svcArpHostShcvReplies OBJECT-TYPE
    SYNTAX          Unsigned32
    MAX-ACCESS      read-only
    STATUS          current
    DESCRIPTION     "The value of svcArpHostShcvReplies indicates the
                     number of host connectivity replies for this ARP host."
    ::= { svcArpHostEntry 15 }

svcArpHostShcvReplyTime OBJECT-TYPE
    SYNTAX          TimeStamp
    MAX-ACCESS      read-only
    STATUS          current
    DESCRIPTION     "The value of svcArpHostShcvReplyTime indicates the
                     time of the last successful host connectivity check for
                     this ARP host."
    ::= { svcArpHostEntry 16 }

svcArpHostSubscrIdent OBJECT-TYPE
    SYNTAX          TmnxSubIdentStringOrEmpty
    MAX-ACCESS      read-only
    STATUS          current
    DESCRIPTION     "The value of svcArpHostSubscrIdent indicates the
                     id of the parent subscriber of this ARP host."
    ::= { svcArpHostEntry 17 }

svcArpHostSubProfString OBJECT-TYPE
    SYNTAX          TmnxSubProfileStringOrEmpty
    MAX-ACCESS      read-only
    STATUS          current
    DESCRIPTION     "The value of svcArpHostSubProfString indicates the
                     subscriber profile string applicable for this ARP host."
    ::= { svcArpHostEntry 18 }

svcArpHostSlaProfString OBJECT-TYPE
    SYNTAX          TmnxSlaProfileStringOrEmpty
    MAX-ACCESS      read-only
    STATUS          current
    DESCRIPTION     "The value of svcArpHostSlaProfString indicates the
                     SLA profile string applicable for this ARP host."
    ::= { svcArpHostEntry 19 }

svcArpHostAppProfString OBJECT-TYPE
    SYNTAX          TmnxAppProfileStringOrEmpty
    MAX-ACCESS      read-only
    STATUS          current
    DESCRIPTION     "The value of svcArpHostAppProfString indicates the
                     application profile string applicable for this ARP host."
    ::= { svcArpHostEntry 20 }

svcArpHostAncpString OBJECT-TYPE
    SYNTAX          TmnxAncpStringOrZero
    MAX-ACCESS      read-only
    STATUS          current
    DESCRIPTION     "The object svcArpHostAncpString indicates the
                     value of the ANCP-string received from the RADIUS server."
    ::= { svcArpHostEntry 21 }

svcArpHostInterDestId OBJECT-TYPE
    SYNTAX          TmnxSubMgtIntDestIdOrEmpty
    MAX-ACCESS      read-only
    STATUS          current
    DESCRIPTION     "The object svcArpHostInterDestId indicates the
                     intermediate destination identifier received from the  
                     RADIUS server."
    ::= { svcArpHostEntry 22 }

svcArpHostRetailerSvcId OBJECT-TYPE  
    SYNTAX          TmnxServId
    MAX-ACCESS      read-only
    STATUS          current
    DESCRIPTION     "The value of svcArpHostRetailerSvcId indicates the
                     service ID of the retailer VPRN service to which this 
                     ARP host belongs. When this object is non zero, the
                     ARP host belongs to a retailer VPRN."
    ::= { svcArpHostEntry 23 }

svcArpHostRetailerIf OBJECT-TYPE
     SYNTAX         InterfaceIndexOrZero
     MAX-ACCESS     read-only
     STATUS         current
     DESCRIPTION    "The value of svcArpHostRetailerIf indicates the
                     interface index of the retailer VPRN interface to 
                     which this ARP host belongs. When this object is 
                     non zero, the ARP host belongs to a retailer VPRN."
     ::= { svcArpHostEntry 24 }

svcArpHostMacAddr OBJECT-TYPE
     SYNTAX         MacAddress
     MAX-ACCESS     read-only
     STATUS         current
     DESCRIPTION    "The value of svcArpHostMacAddr indicates the
                     MAC address of this ARP host."
     ::= { svcArpHostEntry 25 }

svcArpHostPersistKey OBJECT-TYPE
    SYNTAX          Unsigned32
    MAX-ACCESS      read-only
    STATUS          current
    DESCRIPTION     "The value of svcArpHostPersistKey indicates a key
                     value that can be used to track this ARP host in the
                     persistence file."
    ::= { svcArpHostEntry 26 }

svcArpHostCategoryMapName OBJECT-TYPE
    SYNTAX          TNamedItemOrEmpty
    MAX-ACCESS      read-only
    STATUS          current
    DESCRIPTION     "The object svcArpHostCategoryMapName indicates the
                     value of the category map name received from the RADIUS
                     server."
    ::= { svcArpHostEntry 27 }

svcArpHostRadiusClassAttr OBJECT-TYPE
    SYNTAX          OCTET STRING (SIZE (0..253))
    MAX-ACCESS      read-only
    STATUS          current
    DESCRIPTION     "The value of svcArpHostRadiusClassAttr indicates the
                     Class attribute returned by the RADIUS server in an
                     Access-Accept message.
         
                     If no RADIUS authentication is performed for this ARP
                     host, or RADIUS did not return this attribute, the value
                     of this object is empty."
    ::= { svcArpHostEntry 28 }

svcArpHostRadiusUserName OBJECT-TYPE
    SYNTAX          DisplayString (SIZE (0..253))
    MAX-ACCESS      read-only
    STATUS          current
    DESCRIPTION     "The value of svcArpHostRadiusUserName indicates the
                     User-Name attribute returned by the RADIUS server in an
                     Access-Accept message.

                     If RADIUS did not return this attribute, the value of this
                     object is equal to the User-Name attribute sent in the
                     original Access-Request message.
         
                     If no RADIUS authentication is performed for this ARP
                     host, the value of this object is empty."
    ::= { svcArpHostEntry 29 }

svcArpHostOriginSubscrId OBJECT-TYPE
    SYNTAX          ArpHostInfoOrigin
    MAX-ACCESS      read-only
    STATUS          obsolete
    DESCRIPTION     "The value of svcArpHostOriginSubscrId indicates
                     which source provided the subscriber-id."
    ::= { svcArpHostEntry 30 }

svcArpHostOriginStrings OBJECT-TYPE
    SYNTAX          ArpHostInfoOrigin
    MAX-ACCESS      read-only
    STATUS          obsolete
    DESCRIPTION     "The value of svcArpHostOriginStrings indicates
                     which server provided the Sub-profile, SLA profile,
                     Ancp string and Intermediate Destination Id."
    ::= { svcArpHostEntry 31 }

-- ---------------------------------------------------------------------
--  svcArpHostIfTable
--
--
--  Sparse Dependent Extension of the iesIfTable.
--
--  The same indexes are used for both the base table, iesIfTable,
--  and the sparse dependent table, svcArpHostIfTable.
--
--  This in effect extends the iesIfTable with additional columns.
--  A row is automatically created in the svcArpHostIfTable 
--  for each applicable row in the iesIfTable.
--
--  Deletion of a row in the iesIfTable results in the
--  same fate for the row in the svcArpHostIfTable.
-- ---------------------------------------------------------------------

svcArpHostIfTableLastMgmtChange OBJECT-TYPE
    SYNTAX      TimeStamp
    MAX-ACCESS  read-only
    STATUS      current
    DESCRIPTION
        "The value of svcArpHostIfTableLastMgmtChange indicates the sysUpTime 
         at the time of the most recent management-initiated change to the
         svcArpHostIfTable."
    ::= { tmnxSvcObjs 46 }

svcArpHostIfTable OBJECT-TYPE
    SYNTAX      SEQUENCE OF SvcArpHostIfEntry
    MAX-ACCESS  not-accessible
    STATUS      current
    DESCRIPTION
        "A table that contains IES interface ARP host configuration 
         information.

         A row is automatically created in the svcArpHostIfTable for an entry
         in the iesIfTable where either the value of the object iesIfType 
         - is equal to 'group (3)' and the value of the object iesIfGroupInterfaceType is
         equal to 'plain' or 'lns', or 
         - equal to 'subscriber (2)' while the value of the objects iesIfFwdServId and 
         iesIfFwdSubIf are not equal to zero.
         
         The first case is referred to as 'group interface' and the second as
         'retailer interface'."
    ::= { tmnxSvcObjs 47 }

svcArpHostIfEntry OBJECT-TYPE
    SYNTAX      SvcArpHostIfEntry
    MAX-ACCESS  not-accessible
    STATUS      current
    DESCRIPTION
        "ARP host specific information about an IES interface."
    INDEX { svcId,
            iesIfIndex }
    ::= { svcArpHostIfTable 1 }

SvcArpHostIfEntry ::=
    SEQUENCE {
        svcArpHostIfLastMgmtChange       TimeStamp,
        svcArpHostIfAdminState           TmnxAdminState,
        svcArpHostIfMaxNumHosts          Unsigned32,
        svcArpHostIfMaxNumHostsSap       Unsigned32,
        svcArpHostIfMinAuthInterval      Unsigned32,
        svcArpHostIfNumHosts             Gauge32
    }

svcArpHostIfLastMgmtChange OBJECT-TYPE
    SYNTAX      TimeStamp
    MAX-ACCESS  read-only
    STATUS      current
    DESCRIPTION
        "The value of svcArpHostIfLastMgmtChange indicates the sysUpTime at
         the time of the most recent management-initiated change to this
         table row."
    ::= { svcArpHostIfEntry 1 }

svcArpHostIfAdminState OBJECT-TYPE
    SYNTAX      TmnxAdminState
    MAX-ACCESS  read-write
    STATUS      current
    DESCRIPTION
        "The value of the object svcArpHostIfAdminState specifies the
         administrative state of the ARP host functionality on this IES 
         interface.
         
         The default value of this object is equal to 'outOfService', 
         except for a retailer interface, where it is 'inService'."
    ::= { svcArpHostIfEntry 2 }

svcArpHostIfMaxNumHosts OBJECT-TYPE
    SYNTAX      Unsigned32 (1..524287)
    MAX-ACCESS  read-write
    STATUS      current
    DESCRIPTION
        "The value of svcArpHostIfMaxNumHosts specifies the maximum
         number of ARP hosts allowed on this IES interface.
         
         The default value of this object is equal to '1' except for a
         retailer interface, where it is the system limit."
    ::= { svcArpHostIfEntry 3 }

svcArpHostIfMaxNumHostsSap OBJECT-TYPE
    SYNTAX      Unsigned32 (1..131071)
    MAX-ACCESS  read-write
    STATUS      current
    DESCRIPTION
        "The value of svcArpHostIfMaxNumHosts specifies the maximum
         number of ARP hosts per SAP allowed on this IES interface.
         
         The value of this object is not relevant in case of a retailer 
         interface.
         
         In other cases, the default value is equal to '1'."
    ::= { svcArpHostIfEntry 4 }

svcArpHostIfMinAuthInterval OBJECT-TYPE
    SYNTAX      Unsigned32 (1..6000)
    UNITS       "minutes"
    MAX-ACCESS  read-write
    STATUS      current
    DESCRIPTION
        "The value of svcArpHostIfMinAuthInterval specifies the minimum
         interval between two consecutive authentication attempts for the
         same ARP host.
         
         The value of this object is not relevant in case of a retailer 
         interface.
         
         In other cases, the default value is equal to '15'."
    ::= { svcArpHostIfEntry 5 }

svcArpHostIfNumHosts OBJECT-TYPE
    SYNTAX      Gauge32
    MAX-ACCESS  read-only
    STATUS      current
    DESCRIPTION
        "The value of svcArpHostIfNumHosts indicates the actual
         number of ARP hosts on this IES interface."
    ::= { svcArpHostIfEntry 6 }

svcArpHostDefaultSessionTimeout OBJECT-TYPE
    SYNTAX      Unsigned32
    UNITS       "seconds"
    MAX-ACCESS  read-only
    STATUS      current
    DESCRIPTION
        "The value of svcArpHostDefaultSessionTimeout indicates 
         the default value of the ARP host session timeout.
         
         This default value is used if no value was specified, for instance
         by the Radius server."
    ::= { tmnxSvcObjs 48 }

-- ---------------------------------------------------------------------
-- svcIgmpTrkTable
--
--
--  Sparse Dependent Extension of the svcBaseInfoTable.
--
--  The same indexes are used for both the base table, svcBaseInfoTable,
--  and the sparse dependent table, svcIgmpTrkTable.
--
--  This in effect extends the svcBaseInfoTable with additional columns.
--  A row is automatically created in the svcIgmpTrkTable for each row
--  in the svcBaseInfoTable where the value of the object svcType is equal to
--  'tls', 'ies' or 'vprn'.
--
--  Deletion of a row in the svcBaseInfoTable results in the
--  same fate for the row in the svcIgmpTrkTable.
-- ---------------------------------------------------------------------

svcIgmpTrkTableLastMgmtChange OBJECT-TYPE
    SYNTAX      TimeStamp
    MAX-ACCESS  read-only
    STATUS      current
    DESCRIPTION
        "The value of svcIgmpTrkTableLastMgmtChange indicates the sysUpTime 
         at the time of the most recent management-initiated change to the
         svcIgmpTrkTable."
    ::= { tmnxSvcObjs 49 }

svcIgmpTrkTable OBJECT-TYPE
    SYNTAX      SEQUENCE OF SvcIgmpTrkEntry
    MAX-ACCESS  not-accessible
    STATUS      current
    DESCRIPTION 
        "A table that contains IGMP host tracking information of a service."
    ::= { tmnxSvcObjs 50 }

svcIgmpTrkEntry OBJECT-TYPE
    SYNTAX      SvcIgmpTrkEntry
    MAX-ACCESS  not-accessible
    STATUS      current
    DESCRIPTION     
        "IGMP host tracking information about a specific service."
    INDEX { svcId }
    ::= { svcIgmpTrkTable 1 }

SvcIgmpTrkEntry ::=
    SEQUENCE {
        svcIgmpTrkLastMgmtChange         TimeStamp,
        svcIgmpTrkAdminState             TmnxAdminState,
        svcIgmpTrkExpiryTime             Unsigned32
    }       

svcIgmpTrkLastMgmtChange OBJECT-TYPE
    SYNTAX      TimeStamp
    MAX-ACCESS  read-only
    STATUS      current
    DESCRIPTION
        "The value of svcIgmpTrkLastMgmtChange indicates the sysUpTime at
         the time of the most recent management-initiated change to this
         table row."
    ::= { svcIgmpTrkEntry 1 }

svcIgmpTrkAdminState OBJECT-TYPE
    SYNTAX      TmnxAdminState
    MAX-ACCESS  read-write
    STATUS      current
    DESCRIPTION
        "The value of the object svcIgmpTrkAdminState specifies the
         administrative state of the IGMP host tracking in this service."
    DEFVAL { outOfService }
    ::= { svcIgmpTrkEntry 2 }

svcIgmpTrkExpiryTime OBJECT-TYPE
    SYNTAX      Unsigned32 (1..65535)
    UNITS       "seconds"
    MAX-ACCESS  read-write
    STATUS      current
    DESCRIPTION
        "The value of the object svcIgmpTrkExpiryTime specifies
         the time in seconds that this system continues to track an inactive
         host."
    DEFVAL { 260 }
    ::= { svcIgmpTrkEntry 3 }

-- ------------------------------------
-- IPIPE Service Table
-- ------------------------------------

svcIpipeInfoTableLastMgmtChange OBJECT-TYPE
    SYNTAX       TimeStamp
    MAX-ACCESS   read-only
    STATUS       current
    DESCRIPTION
        "The value of svcIpipeInfoTableLastMgmtChange indicates the
        timestamp of last change to the svcIpipeInfoTable."
    ::= { tmnxSvcObjs 51 }

svcIpipeInfoTable OBJECT-TYPE
    SYNTAX          SEQUENCE OF SvcIpipeInfoEntry
    MAX-ACCESS      not-accessible
    STATUS          current
    DESCRIPTION     "A table that contains IPIPE service information."
    ::= { tmnxSvcObjs 52 }

svcIpipeInfoEntry OBJECT-TYPE
    SYNTAX          SvcIpipeInfoEntry
    MAX-ACCESS      not-accessible
    STATUS          current
    DESCRIPTION     "IPIPE specific information about a service."
    INDEX           { svcId }
    ::= { svcIpipeInfoTable 1 }

SvcIpipeInfoEntry ::=
    SEQUENCE {
        svcIpipeInfoLastMgmtChange       TimeStamp,
        svcIpipeCeAddressDiscovery       TmnxEnabledDisabled,
        svcIpipeIpv6CeAddressDiscovery   TmnxEnabledDisabled,
        svcIpipeStackCapabilitySignaling TmnxEnabledDisabled,
        svcIpipeCeAddressDiscoveryKeep   TruthValue,
        svcIpipeEthFaultNotifRecTimer    Unsigned32,
        svcIpipeEthFaultNotifAdminState  TmnxAdminState
    }

svcIpipeInfoLastMgmtChange        OBJECT-TYPE
    SYNTAX      TimeStamp
    MAX-ACCESS  read-only
    STATUS      current
    DESCRIPTION
        "The value of svcIpipeInfoLastMgmtChange indicates the value
        of sysUpTime at the time of the most recent management change to
        this row."
    ::= { svcIpipeInfoEntry 1 }

svcIpipeCeAddressDiscovery OBJECT-TYPE
    SYNTAX          TmnxEnabledDisabled
    MAX-ACCESS      read-write
    STATUS          current
    DESCRIPTION     "The value of the object svcIpipeCeAddressDiscovery
                     specifies whether the service will automatically discover
                     the CE IP addresses.

                     If 'enabled', the addresses will be automatically
                     discovered on SAPs that support address discovery, and on
                     the Spoke SDPs.  When 'enabled', addresses configuration
                     on the Ipipe SAP and Spoke SDPs will not be allowed.

                     If 'disabled', CE IP addresses need to be manually
                     configured for the SAPs to become operationally 'up'.

                     svcIpipeCeAddressDiscovery cannot be disabled if
                     svcIpipeIpv6CeAddressDiscovery is 'enabled'."
    DEFVAL          { disabled }
    ::= { svcIpipeInfoEntry 2 }

svcIpipeIpv6CeAddressDiscovery OBJECT-TYPE
    SYNTAX          TmnxEnabledDisabled
    MAX-ACCESS      read-write
    STATUS          current
    DESCRIPTION     "The value of the object svcIpipeIpv6CeAddressDiscovery
                     specifies whether the service will automatically discover
                     the CE IPv6 addresses.

                     If 'enabled', the addresses will be automatically
                     discovered on SAPs that support address discovery, and on
                     the Spoke SDPs.  When 'enabled', addresses configuration
                     on the Ipipe SAP and Spoke SDPs will not be allowed.

                     If 'disabled', CE IP addresses need to be manually
                     configured for the SAPs to become operationally 'up'.

                     svcIpipeIpv6CeAddressDiscovery can only be enabled if
                     svcIpipeCeAddressDiscovery is 'enabled' first."
    DEFVAL          { disabled }
    ::= { svcIpipeInfoEntry 3 }

svcIpipeStackCapabilitySignaling OBJECT-TYPE
    SYNTAX          TmnxEnabledDisabled
    MAX-ACCESS      read-write
    STATUS          current
    DESCRIPTION     "The value of the object svcIpipeStackCapabilitySignaling
                     specifies whether this service should send the Stack
                     Capability or not, and check whether the capability is
                     received from the peer via LDP interface parameters.

                     If 'enabled' and svcIpipeIpv6CeAddressDiscovery is also
                     'enabled', the Stack Capability interface parameter will
                     be sent via LDP to the far end peer.  As well, if one is
                     not received from the peer, the label for this service
                     will be released.

                     If 'disabled', the capability will not be advertised to
                     the peer, and the presence or absence of this capability
                     from the peer is ignored."
    DEFVAL          { disabled }
    ::= { svcIpipeInfoEntry 4 }

svcIpipeCeAddressDiscoveryKeep OBJECT-TYPE
    SYNTAX          TruthValue
    MAX-ACCESS      read-write
    STATUS          current
    DESCRIPTION     "The value svcIpipeCeAddressDiscoveryKeep specifies whether
                     the discovered CE address is cleared or not when the SAP on
                     which the address was learned changes to operationally down.
                     If the SAP changes to administratively down, the address is
                     cleared regardless of this configuration."
    DEFVAL          { false }
    ::= { svcIpipeInfoEntry 5 }

svcIpipeEthFaultNotifRecTimer OBJECT-TYPE
    SYNTAX          Unsigned32 (10..300)
    UNITS           "deci-seconds"
    MAX-ACCESS      read-write
    STATUS          current
    DESCRIPTION     "The value of svcIpipeEthFaultNotifRecTimer specifies
                     the time provided for the legacy protocols PPP, MLPPP and
                     HDLC to establish before an Ethernet fault is declared."
    DEFVAL          { 100 }
    ::= { svcIpipeInfoEntry 6 }

svcIpipeEthFaultNotifAdminState OBJECT-TYPE
    SYNTAX           TmnxAdminState
    MAX-ACCESS       read-write
    STATUS           current
    DESCRIPTION      "The svcIpipeEthFaultNotifAdminState specifies the desired
                      administrative state for ethernet legacy fault
                      notification feature on this service."
    DEFVAL           { outOfService }
    ::= { svcIpipeInfoEntry 7 }

-- ----------------------------------------
-- svcDhcpLeaseStateBgpTable
-- ----------------------------------------
svcDhcpLeaseStateBgpTable OBJECT-TYPE
    SYNTAX          SEQUENCE OF SvcDhcpLeaseStateBgpEntry
    MAX-ACCESS      not-accessible
    STATUS          obsolete
    DESCRIPTION
        "The svcDhcpLeaseStateBgpTable augments the svcDhcpLeaseStateTable.
         This table contains the parameters used for BGP."
    ::= { tmnxSvcObjs 53 }

svcDhcpLeaseStateBgpEntry OBJECT-TYPE
    SYNTAX          SvcDhcpLeaseStateBgpEntry  
    MAX-ACCESS      not-accessible
    STATUS          current
    DESCRIPTION     
        "Each row entry contains parameters used for BGP."
    AUGMENTS        { svcDhcpLeaseStateEntry }
    ::= { svcDhcpLeaseStateBgpTable 1 }

SvcDhcpLeaseStateBgpEntry ::=
    SEQUENCE {
        svcDhcpLseStateBgpPrngPlcyName   TNamedItemOrEmpty,
        svcDhcpLseStateBgpAuthKeyChain   TNamedItemOrEmpty,
        svcDhcpLseStateBgpMD5AuthKey     OCTET STRING,
        svcDhcpLseStateBgpImportPolicy   TPolicyStatementNameOrEmpty,
        svcDhcpLseStateBgpExportPolicy   TPolicyStatementNameOrEmpty,
        svcDhcpLseStateBgpPeerAS         InetAutonomousSystemNumber,
        svcDhcpLseStateBgpPeeringStatus  BgpPeeringStatus
    }

svcDhcpLseStateBgpPrngPlcyName OBJECT-TYPE
    SYNTAX          TNamedItemOrEmpty
    MAX-ACCESS      read-only
    STATUS          obsolete
    DESCRIPTION
        "The value of svcDhcpLseStateBgpPrngPlcyName indicates the
         peering policy which is used to set up the BGP peer for this
         lease state."
    ::= { svcDhcpLeaseStateBgpEntry 1 }

svcDhcpLseStateBgpAuthKeyChain OBJECT-TYPE
    SYNTAX          TNamedItemOrEmpty
    MAX-ACCESS      read-only
    STATUS          obsolete
    DESCRIPTION
        "The value of svcDhcpLseStateBgpAuthKeyChain indicates the
         keychain which is used to sign and/or authenticate  the BGP
         protocol stream."
    ::= { svcDhcpLeaseStateBgpEntry 2 }

svcDhcpLseStateBgpMD5AuthKey OBJECT-TYPE
    SYNTAX          OCTET STRING (SIZE(0..255))
    MAX-ACCESS      read-only
    STATUS          obsolete
    DESCRIPTION     
        "The value of svcDhcpLseStateBgpMD5AuthKey indicates 
         the authentication key used between BGP
         peers neighbors before establishing sessions. Authentication
         is done using the MD-5 message based digest protocol."
    ::= { svcDhcpLeaseStateBgpEntry 3 }

svcDhcpLseStateBgpImportPolicy OBJECT-TYPE
    SYNTAX          TPolicyStatementNameOrEmpty
    MAX-ACCESS      read-only
    STATUS          obsolete
    DESCRIPTION     
        "The value of svcDhcpLseStateBgpImportPolicy indicates 
         the import policy."
    ::= { svcDhcpLeaseStateBgpEntry 4 }

svcDhcpLseStateBgpExportPolicy OBJECT-TYPE
    SYNTAX          TPolicyStatementNameOrEmpty
    MAX-ACCESS      read-only
    STATUS          obsolete
    DESCRIPTION     
        "The value of svcDhcpLseStateBgpExportPolicy indicates 
         the export policy."
    ::= { svcDhcpLeaseStateBgpEntry 5 }

svcDhcpLseStateBgpPeerAS OBJECT-TYPE
    SYNTAX          InetAutonomousSystemNumber
    MAX-ACCESS      read-only
    STATUS          obsolete
    DESCRIPTION     
        "The value of svcDhcpLseStateBgpPeerAS indicates the Autonomous System
         number for the remote peer."
    ::= { svcDhcpLeaseStateBgpEntry 6 }

svcDhcpLseStateBgpPeeringStatus OBJECT-TYPE
    SYNTAX          BgpPeeringStatus
    MAX-ACCESS      read-only
    STATUS          obsolete
    DESCRIPTION
        "The value of svcDhcpLseStateBgpPeeringStatus indicates
         the status of the BGP peering session."
    ::= { svcDhcpLeaseStateBgpEntry 7 }

-- ----------------------------------------------------------------------------
-- DHCP Lease State BGP Table version 2
--
-- The MAC address is part of the key to allow multiple lease states having the
-- same IP address.
--
-- ----------------------------------------------------------------------------
svcDhcpLeaseBgpTable OBJECT-TYPE
    SYNTAX          SEQUENCE OF SvcDhcpLeaseBgpEntry
    MAX-ACCESS      not-accessible
    STATUS          current
    DESCRIPTION
        "The svcDhcpLeaseBgpTable augments the svcDhcpLeaseTable.
         This table contains the parameters used for BGP."
    ::= { tmnxSvcObjs 93 }

svcDhcpLeaseBgpEntry OBJECT-TYPE
    SYNTAX          SvcDhcpLeaseBgpEntry  
    MAX-ACCESS      not-accessible
    STATUS          current
    DESCRIPTION     
        "Each row entry contains parameters used for BGP."
    AUGMENTS        { svcDhcpLeaseEntry }
    ::= { svcDhcpLeaseBgpTable 1 }

SvcDhcpLeaseBgpEntry ::=
    SEQUENCE {
        svcDhcpLeaseBgpPrngPlcyName      TNamedItemOrEmpty,
        svcDhcpLeaseBgpAuthKeyChain      TNamedItemOrEmpty,
        svcDhcpLeaseBgpMD5AuthKey        OCTET STRING,
        svcDhcpLeaseBgpImportPolicy      TPolicyStatementNameOrEmpty,
        svcDhcpLeaseBgpExportPolicy      TPolicyStatementNameOrEmpty,
        svcDhcpLeaseBgpPeerAS            InetAutonomousSystemNumber,
        svcDhcpLeaseBgpPeeringStatus     BgpPeeringStatus
    }

svcDhcpLeaseBgpPrngPlcyName OBJECT-TYPE
    SYNTAX          TNamedItemOrEmpty
    MAX-ACCESS      read-only
    STATUS          current
    DESCRIPTION
        "The value of svcDhcpLeaseBgpPrngPlcyName indicates the
         peering policy which is used to set up the BGP peer for this
         lease state."
    ::= { svcDhcpLeaseBgpEntry 1 }

svcDhcpLeaseBgpAuthKeyChain OBJECT-TYPE
    SYNTAX          TNamedItemOrEmpty
    MAX-ACCESS      read-only
    STATUS          current
    DESCRIPTION
        "The value of svcDhcpLeaseBgpAuthKeyChain indicates the
         keychain which is used to sign and/or authenticate  the BGP
         protocol stream."
    ::= { svcDhcpLeaseBgpEntry 2 }

svcDhcpLeaseBgpMD5AuthKey OBJECT-TYPE
    SYNTAX          OCTET STRING (SIZE(0..255))
    MAX-ACCESS      read-only
    STATUS          current
    DESCRIPTION     
        "The value of svcDhcpLeaseBgpMD5AuthKey indicates 
         the authentication key used between BGP
         peers neighbors before establishing sessions. Authentication
         is done using the MD-5 message based digest protocol."
    ::= { svcDhcpLeaseBgpEntry 3 }

svcDhcpLeaseBgpImportPolicy OBJECT-TYPE
    SYNTAX          TPolicyStatementNameOrEmpty
    MAX-ACCESS      read-only
    STATUS          current
    DESCRIPTION     
        "The value of svcDhcpLeaseBgpImportPolicy indicates 
         the import policy."
    ::= { svcDhcpLeaseBgpEntry 4 }

svcDhcpLeaseBgpExportPolicy OBJECT-TYPE
    SYNTAX          TPolicyStatementNameOrEmpty
    MAX-ACCESS      read-only
    STATUS          current
    DESCRIPTION     
        "The value of svcDhcpLeaseBgpExportPolicy indicates 
         the export policy."
    ::= { svcDhcpLeaseBgpEntry 5 }

svcDhcpLeaseBgpPeerAS OBJECT-TYPE
    SYNTAX          InetAutonomousSystemNumber
    MAX-ACCESS      read-only
    STATUS          current
    DESCRIPTION     
        "The value of svcDhcpLeaseBgpPeerAS indicates the Autonomous System
         number for the remote peer."
    ::= { svcDhcpLeaseBgpEntry 6 }

svcDhcpLeaseBgpPeeringStatus OBJECT-TYPE
    SYNTAX          BgpPeeringStatus
    MAX-ACCESS      read-only
    STATUS          current
    DESCRIPTION
        "The value of svcDhcpLeaseBgpPeeringStatus indicates
         the status of the BGP peering session."
    ::= { svcDhcpLeaseBgpEntry 7 }

-- ----------------------------------------
-- Arp Host Managed Route Table
-- ----------------------------------------
svcArpHostMRtTable OBJECT-TYPE
    SYNTAX          SEQUENCE OF SvcArpHostMRtEntry
    MAX-ACCESS      not-accessible
    STATUS          current
    DESCRIPTION     "The svcArpHostMRtTable contains managed routes of
                     ARP hosts.

                     Entries in this table are created automatically 
                     by the system."
    ::= { tmnxSvcObjs 54 }

svcArpHostMRtEntry OBJECT-TYPE
    SYNTAX          SvcArpHostMRtEntry
    MAX-ACCESS      not-accessible
    STATUS          current
    DESCRIPTION     "Each row entry represents information on a specific
                     managed route."
    INDEX           { svcId,
                      svcArpHostIpAddrType,
                      svcArpHostIpAddr,
                      svcArpHostMRtAddrType,
                      svcArpHostMRtAddr,
                      svcArpHostMRtPrefixLen }
    ::= { svcArpHostMRtTable 1 }

SvcArpHostMRtEntry ::=
    SEQUENCE {
        svcArpHostMRtAddrType          InetAddressType,
        svcArpHostMRtAddr              InetAddress,
        svcArpHostMRtPrefixLen         InetAddressPrefixLength,
        svcArpHostMRtStatus            TmnxManagedRouteStatus
       ,svcArpHostMRtMetric            TmnxRadiusFramedRouteMetric,
        svcArpHostMRtPreference        TmnxRadiusFramedRoutePreference,
        svcArpHostMRtTag               TmnxRadiusFramedRouteTag             
    }

svcArpHostMRtAddrType OBJECT-TYPE
    SYNTAX          InetAddressType
    MAX-ACCESS      not-accessible
    STATUS          current
    DESCRIPTION     "The value of svcArpHostMRtAddrType indicates
                     the address type of svcArpHostMRtAddr."
    ::= { svcArpHostMRtEntry 1 }

svcArpHostMRtAddr OBJECT-TYPE
    SYNTAX          InetAddress (SIZE(4|16))
    MAX-ACCESS      not-accessible
    STATUS          current
    DESCRIPTION     "The value of svcArpHostMRtAddr indicates
                     the IP address of the managed route."
    ::= { svcArpHostMRtEntry 2 }

svcArpHostMRtPrefixLen OBJECT-TYPE
    SYNTAX          InetAddressPrefixLength
    MAX-ACCESS      not-accessible
    STATUS          current
    DESCRIPTION     "The value of svcArpHostMRtPrefixLen indicates
                     the prefix length of the subnet associated with
                     svcArpHostMRtAddr."
    ::= { svcArpHostMRtEntry 3 }

svcArpHostMRtStatus OBJECT-TYPE
    SYNTAX          TmnxManagedRouteStatus
    MAX-ACCESS      read-only
    STATUS          current
    DESCRIPTION     "The value of svcArpHostMRtStatus indicates
                     the state of this managed route."
    ::= { svcArpHostMRtEntry 4 }

svcArpHostMRtMetric OBJECT-TYPE
    SYNTAX          TmnxRadiusFramedRouteMetric
    MAX-ACCESS      read-only
    STATUS          current
    DESCRIPTION     "The value of tmnxSubPppMRtMetric indicates
                     the metric of this managed route as specified
                     in the RADIUS option 22 Framed-Route or 
                     option 99 Framed-IPv6-Route."
    ::= { svcArpHostMRtEntry 5 }

svcArpHostMRtPreference OBJECT-TYPE
    SYNTAX          TmnxRadiusFramedRoutePreference
    MAX-ACCESS      read-only
    STATUS          current
    DESCRIPTION     "The value of tmnxSubPppMRtPreference indicates
                     the preference of this managed route as specified
                     in the RADIUS option 22 Framed-Route or 
                     option 99 Framed-IPv6-Route."
    ::= { svcArpHostMRtEntry 6 }

svcArpHostMRtTag OBJECT-TYPE
    SYNTAX          TmnxRadiusFramedRouteTag
    MAX-ACCESS      read-only
    STATUS          current
    DESCRIPTION     "The value of tmnxSubPppMRtTag indicates
                     the tag of this managed route as specified
                     in the RADIUS option 22 Framed-Route or 
                     option 99 Framed-IPv6-Route."
    ::= { svcArpHostMRtEntry 7 }

-- ----------------------------------------
-- svcArpHostBgpTable
--
--  Augmentation of the svcArpHostTable
--  Use of AUGMENTS clause implies a one-to-one dependent relationship
--  between the base table, svcArpHostTable, and the augmenting table,
--  svcArpHostBgpTable. This in effect extends the svcArpHostTable
--  with additional columns. Creation (or deletion) of a row in the
--  svcArpHostTable results in the same fate for the row in the
--  svcArpHostBgpTable.
-- ----------------------------------------
svcArpHostBgpTable OBJECT-TYPE
    SYNTAX          SEQUENCE OF SvcArpHostBgpEntry
    MAX-ACCESS      not-accessible
    STATUS          current
    DESCRIPTION
        "The svcArpHostBgpTable augments the svcArpHostTable.
         This table contains the parameters used for BGP."
    ::= { tmnxSvcObjs 55 }

svcArpHostBgpEntry OBJECT-TYPE
    SYNTAX          SvcArpHostBgpEntry  
    MAX-ACCESS      not-accessible
    STATUS          current
    DESCRIPTION     
        "Each row entry contains parameters used for BGP."
    AUGMENTS        { svcArpHostEntry }
    ::= { svcArpHostBgpTable 1 }

SvcArpHostBgpEntry ::=
    SEQUENCE {
        svcArpHostBgpPrngPlcyName         TNamedItemOrEmpty,
        svcArpHostBgpAuthKeyChain         TNamedItemOrEmpty,
        svcArpHostBgpMD5AuthKey           OCTET STRING,
        svcArpHostBgpImportPolicy         TPolicyStatementNameOrEmpty,
        svcArpHostBgpExportPolicy         TPolicyStatementNameOrEmpty,
        svcArpHostBgpPeerAS               InetAutonomousSystemNumber,
        svcArpHostBgpPeeringStatus        BgpPeeringStatus
    }

svcArpHostBgpPrngPlcyName OBJECT-TYPE
    SYNTAX          TNamedItemOrEmpty
    MAX-ACCESS      read-only
    STATUS          current
    DESCRIPTION
        "The value of svcArpHostBgpPrngPlcyName indicates the
         peering policy which is used to set up the BGP peer for this
         ARP host."
    ::= { svcArpHostBgpEntry 1 }

svcArpHostBgpAuthKeyChain OBJECT-TYPE
    SYNTAX          TNamedItemOrEmpty
    MAX-ACCESS      read-only
    STATUS          current
    DESCRIPTION
        "The value of svcArpHostBgpAuthKeyChain indicates 
         the keychain which is used to sign and/or authenticate  the BGP
         protocol stream."
    ::= { svcArpHostBgpEntry 2 }

svcArpHostBgpMD5AuthKey OBJECT-TYPE
    SYNTAX          OCTET STRING (SIZE(0..255))
    MAX-ACCESS      read-only
    STATUS          current
    DESCRIPTION     
        "The value of svcArpHostBgpMD5AuthKey indicates 
         the authentication key used between BGP peers before establishing 
         sessions. 
         
         Authentication is done using the MD-5 message based digest protocol."
    ::= { svcArpHostBgpEntry 3 }

svcArpHostBgpImportPolicy OBJECT-TYPE
    SYNTAX          TPolicyStatementNameOrEmpty
    MAX-ACCESS      read-only
    STATUS          current
    DESCRIPTION     
        "The value of svcArpHostBgpImportPolicy indicates 
         the import policy."
    ::= { svcArpHostBgpEntry 4 }

svcArpHostBgpExportPolicy OBJECT-TYPE
    SYNTAX          TPolicyStatementNameOrEmpty
    MAX-ACCESS      read-only
    STATUS          current
    DESCRIPTION     
        "The value of svcArpHostBgpExportPolicy indicates 
         the export policy."
    ::= { svcArpHostBgpEntry 5 }

svcArpHostBgpPeerAS OBJECT-TYPE
    SYNTAX          InetAutonomousSystemNumber
    MAX-ACCESS      read-only
    STATUS          current
    DESCRIPTION     
        "The value of svcArpHostBgpPeerAS indicates 
         the Autonomous System number for the remote peer."
    ::= { svcArpHostBgpEntry 6 }

svcArpHostBgpPeeringStatus OBJECT-TYPE
    SYNTAX          BgpPeeringStatus
    MAX-ACCESS      read-only
    STATUS          current
    DESCRIPTION
        "The value of svcArpHostBgpPeeringStatus indicates
         the status of the BGP peering session."
    ::= { svcArpHostBgpEntry 7 }

-- ------------------------------------------------
-- svcEpMcEpStatsTable table
-- ------------------------------------------------

svcEpMcEpStatsTable OBJECT-TYPE
    SYNTAX     SEQUENCE OF SvcEpMcEpStatsEntry
    MAX-ACCESS not-accessible
    STATUS     current
    DESCRIPTION
        "The svcEpMcEpStatsTable has an entry for each end-point that
         participates in a multi-chassis configuration for the indicated
         peer."
    ::= { tmnxSvcObjs 56 }

svcEpMcEpStatsEntry OBJECT-TYPE
    SYNTAX     SvcEpMcEpStatsEntry
    MAX-ACCESS not-accessible
    STATUS     current
    DESCRIPTION
        "Each row entry represents a collection of statistics for a end-point
         that participates in a multi-chassis configuration with a given peer.

         Entries cannot be created and deleted via SNMP SET operations."
    INDEX       { svcEndPointMCEPId }
    ::= { svcEpMcEpStatsTable 1 }

SvcEpMcEpStatsEntry ::= SEQUENCE
   {
       svcEpMcEpStatsPktsRxConfig    Counter32,
       svcEpMcEpStatsPktsRxState     Counter32,
       svcEpMcEpStatsPktsTxConfig    Counter32,
       svcEpMcEpStatsPktsTxState     Counter32,
       svcEpMcEpStatsPktsTxFailed    Counter32
   }

svcEpMcEpStatsPktsRxConfig OBJECT-TYPE
    SYNTAX       Counter32
    MAX-ACCESS   read-only
    STATUS       current
    DESCRIPTION
        "The value of svcEpMcEpStatsPktsRxConfig indicates how many
         multi-chassis end-point control packets of type end-point config were
         received on this system from the peer for this end-point."
    ::= { svcEpMcEpStatsEntry 1 }

svcEpMcEpStatsPktsRxState OBJECT-TYPE
    SYNTAX       Counter32
    MAX-ACCESS   read-only
    STATUS       current
    DESCRIPTION
        "The value of svcEpMcEpStatsPktsRxState indicates how many
         multi-chassis end-point control packets of type end-point state were
         received on this system from the peer for this end-point."
    ::= { svcEpMcEpStatsEntry 2 }

svcEpMcEpStatsPktsTxConfig OBJECT-TYPE
    SYNTAX       Counter32
    MAX-ACCESS   read-only
    STATUS       current
    DESCRIPTION
        "The value of svcEpMcEpStatsPktsTxConfig indicates how many
         multi-chassis end-point control packets of type end-point config were
         sent on this system to the peer for this end-point."
    ::= { svcEpMcEpStatsEntry 3 }

svcEpMcEpStatsPktsTxState OBJECT-TYPE
    SYNTAX       Counter32
    MAX-ACCESS   read-only
    STATUS       current
    DESCRIPTION
        "The value of svcEpMcEpStatsPktsTxState indicates how many
         multi-chassis end-point control packets of type end-point state were
         sent on this system to the peer for this end-point."
    ::= { svcEpMcEpStatsEntry 4 }

svcEpMcEpStatsPktsTxFailed OBJECT-TYPE
    SYNTAX       Counter32
    MAX-ACCESS   read-only
    STATUS       current
    DESCRIPTION
        "The value of svcEpMcEpStatsPktsTxFailed indicates how many
         multi-chassis end-point control packets failed to be transmitted on
         this system to the peer for this end-point."
    ::= { svcEpMcEpStatsEntry 5 }

-- -----------------------------
-- svc MAC Name table
-- -----------------------------


svcPbbSrcBVplsMacAddr OBJECT-TYPE
    SYNTAX          MacAddress
    MAX-ACCESS      read-write
    STATUS          current
    DESCRIPTION     "The value of svcPbbSrcBVplsMacAddr specifies the source
                     Backbone MAC-Address to be used for Provider Backbone
                     Bridging (PBB) packets.

                     Value of default for this object indicates that chassis
                     MAC address will be used for PBB packets."
    DEFVAL { '000000000000'h }
    ::= { tmnxSvcObjs 57 }

svcMacNameTableLastChanged  OBJECT-TYPE
    SYNTAX          TimeStamp
    MAX-ACCESS      read-only
    STATUS          current
    DESCRIPTION     "The value of svcMacNameTableLastChanged indicates the
                     sysUpTime at the time of the last modification of
                     svcMacNameTable.

                     If no changes were made to the entry since the last
                     re-initialization of the local network management subsystem,
                     then this object contains a zero value."
    ::= { tmnxSvcObjs 58 }

svcMacNameTable OBJECT-TYPE
    SYNTAX          SEQUENCE OF SvcMacNameEntry
    MAX-ACCESS      not-accessible
    STATUS          current
    DESCRIPTION     "The svcMacNameTable contains objects related to
                     MAC-name feature.
                     
                     Entries are created and destroyed using svcMacNameRowStatus
                     object."
    ::= { tmnxSvcObjs 59 }

svcMacNameEntry OBJECT-TYPE
    SYNTAX          SvcMacNameEntry
    MAX-ACCESS      not-accessible
    STATUS          current
    DESCRIPTION     "Each row entry contains objects that allows the
                     modification of the MAC-name objects."
    INDEX        { svcMacName }
    ::= { svcMacNameTable 1 }

SvcMacNameEntry ::=
    SEQUENCE {
        svcMacName                        TNamedItem,
        svcMacNameRowStatus               RowStatus,
        svcMacNameLastChngd               TimeStamp,
        svcMacNameAddr                    MacAddress
    }

svcMacName OBJECT-TYPE
    SYNTAX          TNamedItem
    MAX-ACCESS      not-accessible
    STATUS          current
    DESCRIPTION     "The value of svcMacName specifies the name 
                     associated with a MAC address."
    ::= { svcMacNameEntry 1 }

svcMacNameRowStatus OBJECT-TYPE
    SYNTAX          RowStatus
    MAX-ACCESS      read-create
    STATUS          current
    DESCRIPTION     "The value of svcMacNameRowStatus is used for the
                     creation and deletion of MAC information.

                     To create an entry in the table, svcMacNameAddr object
                     must be set."
    ::= { svcMacNameEntry 2 }

svcMacNameLastChngd        OBJECT-TYPE
    SYNTAX          TimeStamp
    MAX-ACCESS      read-only
    STATUS          current
    DESCRIPTION     "The value of svcMacNameLastChngd indicates the sysUpTime at
                     the time of the last modification of this entry.
                     
                     If no changes were made to the entry since the last 
                     re-initialization of the local network management 
                     subsystem, then this object contains a zero value."
    ::= { svcMacNameEntry 3 }

svcMacNameAddr OBJECT-TYPE
    SYNTAX          MacAddress
    MAX-ACCESS      read-create
    STATUS          current
    DESCRIPTION     "The value of svcMacNameAddr specifies the MAC-Address
                     associated with the name defined in svcMacName.

                     This object must be set at the creation time."
    ::= { svcMacNameEntry 4 }

-- ------------------------------------
-- Implicit Protected Mac Table
-- ------------------------------------
tlsProtMacImplTable OBJECT-TYPE
    SYNTAX          SEQUENCE OF TlsProtMacImplEntry
    MAX-ACCESS      not-accessible
    STATUS          current
    DESCRIPTION     "A table that contains information about implicitly 
                     protected MAC addresses in a VPLS service."
    ::= { tmnxSvcObjs 61 }

tlsProtMacImplEntry OBJECT-TYPE
    SYNTAX          TlsProtMacImplEntry
    MAX-ACCESS      not-accessible
    STATUS          current
    DESCRIPTION     "Each entry contains information about a specific 
                     implicitly protected MAC address.
                     
                     Rows are created or removed automatically by the system."
    INDEX           { svcId, 
                      tlsProtMacImplMacAddr,
                      tlsProtMacImplLocale,
                      tlsProtMacImplPortId,
                      tlsProtMacImplEncapValue,
                      tlsProtMacImplSdpBindId }
    ::= { tlsProtMacImplTable 1 }

TlsProtMacImplEntry ::=
    SEQUENCE {
        tlsProtMacImplMacAddr           MacAddress,
        tlsProtMacImplLocale            INTEGER,
        tlsProtMacImplPortId            TmnxPortID,
        tlsProtMacImplEncapValue        TmnxEncapVal,
        tlsProtMacImplSdpBindId         SdpBindId,
        tlsProtMacImplCount             Counter32
    }

tlsProtMacImplMacAddr OBJECT-TYPE
    SYNTAX          MacAddress
    MAX-ACCESS      not-accessible
    STATUS          current
    DESCRIPTION     "The value of the object tlsProtMacImplMacAddr indicates the
                     48-bit IEEE 802.3 MAC address that is implicitly protected."
    ::= { tlsProtMacImplEntry 1 }

tlsProtMacImplLocale OBJECT-TYPE
    SYNTAX          INTEGER {
                        any      (0),      
                        sap      (1),
                        sdp      (2)
                    }
    MAX-ACCESS      not-accessible
    STATUS          current
    DESCRIPTION     "The value of the object tlsProtMacImplLocale indicates
                     where the protection of the MAC address defined by 
                     tlsProtMacImplMacAddr is applied: anywhere, or only on
                     a specific SAP or SDP."
    ::= { tlsProtMacImplEntry 2 }

tlsProtMacImplPortId OBJECT-TYPE
    SYNTAX          TmnxPortID
    MAX-ACCESS      not-accessible
    STATUS          current
    DESCRIPTION     "When the value of tlsProtMacImplLocale is 'sap', this
                     object, along with tlsProtMacImplEncapValue, indicates
                     the SAP where this MAC address is protected. 
                     
                     This object is otherwise insignificant and contains the
                     value zero."
    ::= { tlsProtMacImplEntry 3 }

tlsProtMacImplEncapValue OBJECT-TYPE
    SYNTAX          TmnxEncapVal
    MAX-ACCESS      not-accessible
    STATUS          current
    DESCRIPTION     "The value of the object tlsProtMacImplEncapValue indicates, 
                     when the value of tlsProtMacImplLocale is 'sap', along with
                     tlsProtMacImplPortId, the SAP where this MAC address is 
                     protected. 
                     
                     This object is otherwise insignificant and contains the 
                     value zero."
    ::= { tlsProtMacImplEntry 4 }

tlsProtMacImplSdpBindId OBJECT-TYPE
    SYNTAX          SdpBindId
    MAX-ACCESS      not-accessible
    STATUS          current
    DESCRIPTION     "The value of the object tlsProtMacImplSdpBindId indicates, 
                     when the value of tlsProtMacImplLocale is 'sdp', 
                     the SDP Binding where this MAC address is protected. 
                     
                     This object is otherwise insignificant and contains the 
                     value zero."
    ::= { tlsProtMacImplEntry 5 }

tlsProtMacImplCount OBJECT-TYPE
    SYNTAX          Counter32
    MAX-ACCESS      read-only
    STATUS          current
    DESCRIPTION     "The value of the object tlsProtMacImplCount indicates
                     how many times the protection of this MAC was activated
                     at the indicated locale since the last re-initialization 
                     of the local network management subsystem, or the last 
                     time the system statistics were cleared."
    ::= { tlsProtMacImplEntry 6 }

-- -----------------------------
-- svc MAC Notification Group
-- -----------------------------

svcMacNotificationGroup   OBJECT IDENTIFIER ::= { tmnxSvcObjs 60 }

svcMacNotifInterval OBJECT-TYPE
    SYNTAX          Unsigned32 (1..100)
    UNITS           "deci-seconds"
    MAX-ACCESS      read-write
    STATUS          current
    DESCRIPTION     "The value of svcMacNotifInterval specifies time-interval
                     between subsequent MAC notification messages."
    REFERENCE       "ITU-T Y.1731 specification"
    DEFVAL { 1 }
    ::= { svcMacNotificationGroup 1 }

svcMacNotifCount OBJECT-TYPE
    SYNTAX          Unsigned32 (1..10)
    MAX-ACCESS      read-write
    STATUS          current
    DESCRIPTION     "The value of svcMacNotifCount specifies number of
                     MAC notification messages to be sent."
    REFERENCE       "ITU-T Y.1731 specification"
    DEFVAL { 3 }
    ::= { svcMacNotificationGroup 2 }

-- ----------------------
-- svcNameTable
-- ----------------------
svcNameTableLastChanged  OBJECT-TYPE
    SYNTAX          TimeStamp
    MAX-ACCESS      read-only
    STATUS          current
    DESCRIPTION     "The value of svcNameTableLastChanged indicates the
                     sysUpTime at the time of the last modification
                     of svcNameTable.

                     If no changes were made to the entry since the last
                     re-initialization of the local network management subsystem,
                     then this object contains a zero value."
    ::= { tmnxSvcObjs 62 }

svcNameTable OBJECT-TYPE
    SYNTAX          SEQUENCE OF SvcNameEntry
    MAX-ACCESS      not-accessible
    STATUS          current
    DESCRIPTION     "A table that contains basic service information. Entries
                     can be created manually or automatically by the system
                     when svcName object is set for the service."
    ::= { tmnxSvcObjs 63 }

svcNameEntry OBJECT-TYPE
    SYNTAX          SvcNameEntry
    MAX-ACCESS      not-accessible
    STATUS          current
    DESCRIPTION     "Basic information about a specific service."
    INDEX           { svcName }
    ::= { svcNameTable 1 }

SvcNameEntry ::=
    SEQUENCE {
        svcNameId                   TmnxServId,
        svcNameRowStatus            RowStatus,
        svcNameLastChanged          TimeStamp,
        svcNameType                 ServType,
        svcNameCreationOrigin       TmnxCreateOrigin
    }

svcNameId OBJECT-TYPE
    SYNTAX          TmnxServId
    MAX-ACCESS      read-create
    STATUS          current
    DESCRIPTION     "The value of the object svcNameId specifies the Service
                     Identifier associated with this service.
                     
                     An 'inconsistentValue' error is returned if this object
                     is set to default value when svcNameType is set to a 
                     non-default value or when this object is set to non-default
                     value and svcNameType is set to default value."
    DEFVAL { 0 }
    ::= { svcNameEntry 1 }

svcNameRowStatus OBJECT-TYPE
    SYNTAX          RowStatus
    MAX-ACCESS      read-create
    STATUS          current
    DESCRIPTION     "This value of the object  svcRowStatus specifies the
                     status of this row."
    ::= { svcNameEntry 2 }

svcNameLastChanged        OBJECT-TYPE
    SYNTAX          TimeStamp
    MAX-ACCESS      read-only
    STATUS          current
    DESCRIPTION     "The value of svcNameLastChanged indicates the sysUpTime at
                     the time of the last modification of this entry.
                     
                     If no changes were made to the entry since the last 
                     re-initialization of the local network management 
                     subsystem, then this object contains a zero value."
    ::= { svcNameEntry 3 }

svcNameType OBJECT-TYPE
    SYNTAX          ServType
    MAX-ACCESS      read-create
    STATUS          current
    DESCRIPTION     "The value of the object svcNameType specifies the service
                     type: e.g. epipe, tls, etc.
                     
                     An 'inconsistentValue' error is returned if this object
                     is set to default value when svcNameId is set to a 
                     non-default value or when this object is set to non-default
                     value and svcNameId is set to default value."
    DEFVAL { unknown }
    ::= { svcNameEntry 4 }

svcNameCreationOrigin  OBJECT-TYPE
    SYNTAX          TmnxCreateOrigin
    MAX-ACCESS      read-only
    STATUS          current
    DESCRIPTION     "The value of svcNameCreationOrigin indicates the mechanism
                     used to create this entry."
    DEFVAL { manual }
    ::= { svcNameEntry 5 }
-- ----------------------
-- svcMrpPolicyTable
-- ----------------------
svcMrpPlcyTableLastChgd  OBJECT-TYPE
    SYNTAX          TimeStamp
    MAX-ACCESS      read-only
    STATUS          current
    DESCRIPTION
        "The value of svcMrpPlcyTableLastChgd indicates the sysUpTime at
         the time of the last modification of svcMrpPolicyTable.

         If no changes were made to the entry since the last re-initialization
         of the local network management subsystem, then this object contains a
         zero value."
    ::= { tmnxSvcObjs 64 }

svcMrpPolicyTable OBJECT-TYPE
    SYNTAX          SEQUENCE OF SvcMrpPolicyEntry
    MAX-ACCESS      not-accessible
    STATUS          current
    DESCRIPTION
        "The svcMrpPolicyTable has an entry for each mrp-policy."
    ::= { tmnxSvcObjs 65 }

svcMrpPolicyEntry OBJECT-TYPE
    SYNTAX          SvcMrpPolicyEntry
    MAX-ACCESS      not-accessible
    STATUS          current
    DESCRIPTION
        "svcMrpPolicyEntry contains the information about a particular
         mrp-policy."
    INDEX { svcMrpPolicyName }
    ::= { svcMrpPolicyTable 1 }

SvcMrpPolicyEntry ::=
    SEQUENCE {
        svcMrpPolicyName            TNamedItem,
        svcMrpPolicyRowStatus       RowStatus,
        svcMrpPolicyLastChanged     TimeStamp,
        svcMrpPolicyDescription     TItemDescription,
        svcMrpPolicyScope           TItemScope,
        svcMrpPolicyDefaultAction   TMrpPolicyDefaultAction
    }

svcMrpPolicyName OBJECT-TYPE
    SYNTAX          TNamedItem
    MAX-ACCESS      not-accessible
    STATUS          current
    DESCRIPTION
        "The value of svcMrpPolicyName specifies a specific mrp-policy."
    ::= { svcMrpPolicyEntry 1 }

svcMrpPolicyRowStatus OBJECT-TYPE
    SYNTAX          RowStatus
    MAX-ACCESS      read-create
    STATUS          current
    DESCRIPTION
        "This value of the object svcMrpPolicyRowStatus specifies the status of
         this row."
    ::= { svcMrpPolicyEntry 2 }

svcMrpPolicyLastChanged OBJECT-TYPE
    SYNTAX          TimeStamp
    MAX-ACCESS      read-only
    STATUS          current
    DESCRIPTION
        "The value of svcMrpPolicyLastChanged indicates the sysUpTime at the
         time of the last modification of this entry.

         If no changes were made to the entry since the last re-initialization
         of the local network management subsystem, then this object contains a
         zero value."
    ::= { svcMrpPolicyEntry 3 }

svcMrpPolicyDescription OBJECT-TYPE
    SYNTAX          TItemDescription
    MAX-ACCESS      read-create
    STATUS          current
    DESCRIPTION
        "The value of svcMrpPolicyDescription specifies the user provided
         description of this mrp-policy."
    DEFVAL { "" }
    ::= { svcMrpPolicyEntry 4 }

svcMrpPolicyScope  OBJECT-TYPE
    SYNTAX          TItemScope
    MAX-ACCESS      read-create
    STATUS          current
    DESCRIPTION
        "The value of svcMrpPolicyScope specifies the scope of this mrp-policy
         definition. If defined as exclusive(1), this mrp-policy can be
         instantiated only once as compared to the multiple instances that the
         mrp-policy can have if defined as template(2)."
    DEFVAL { template }
    ::= { svcMrpPolicyEntry 5 }

svcMrpPolicyDefaultAction  OBJECT-TYPE
    SYNTAX          TMrpPolicyDefaultAction
    MAX-ACCESS      read-create
    STATUS          current
    DESCRIPTION
        "The value of TMrpPolicyDefaultAction specifies the action to take for
         packets that do not match any mrp-policy entries."
    DEFVAL { allow }
    ::= { svcMrpPolicyEntry 6 }

-- ----------------------
-- svcMrpPolicyParamsTable
-- ----------------------
svcMrpPlcyParamsTblLastChgd  OBJECT-TYPE
    SYNTAX          TimeStamp
    MAX-ACCESS      read-only
    STATUS          current
    DESCRIPTION
        "The value of svcMrpPlcyParamsTblLastChgd indicates the sysUpTime
         at the time of the last modification of svcMrpPolicyParamsTable.

         If no changes were made to the entry since the last re-initialization
         of the local network management subsystem, then this object contains a
         zero value."
    ::= { tmnxSvcObjs 66 }

svcMrpPolicyParamsTable OBJECT-TYPE
    SYNTAX          SEQUENCE OF SvcMrpPolicyParamsEntry
    MAX-ACCESS      not-accessible
    STATUS          current
    DESCRIPTION
        "The svcMrpPolicyParamsTable has an entry for each mrp-policy entry."
    ::= { tmnxSvcObjs 67 }

svcMrpPolicyParamsEntry OBJECT-TYPE
    SYNTAX          SvcMrpPolicyParamsEntry
    MAX-ACCESS      not-accessible
    STATUS          current
    DESCRIPTION
        "svcMrpPolicyParamsEntry contains the information about a particular
         mrp-policy entry."
    INDEX           { svcMrpPolicyName, svcMrpPolicyParamsEntryId }
    ::= { svcMrpPolicyParamsTable 1 }

SvcMrpPolicyParamsEntry ::=
    SEQUENCE {
        svcMrpPolicyParamsEntryId       TEntryId,
        svcMrpPolicyParamsRowStatus     RowStatus,
        svcMrpPolicyParamsLastChanged   TimeStamp,
        svcMrpPolicyParamsDescription   TItemDescription,
        svcMrpPolicyParamsAction        TMrpPolicyAction
    }

svcMrpPolicyParamsEntryId OBJECT-TYPE
    SYNTAX          TEntryId
    MAX-ACCESS      not-accessible
    STATUS          current
    DESCRIPTION
        "The value of svcMrpPolicyParamsEntryId serves as a secondary index for
         each entry of a given mrp-policy."
    ::= { svcMrpPolicyParamsEntry 1 }

svcMrpPolicyParamsRowStatus OBJECT-TYPE
    SYNTAX          RowStatus
    MAX-ACCESS      read-create
    STATUS          current
    DESCRIPTION
        "This value of the object svcMrpPolicyParamsRowStatus specifies the
         status of this row."
    ::= { svcMrpPolicyParamsEntry 2 }

svcMrpPolicyParamsLastChanged OBJECT-TYPE
    SYNTAX          TimeStamp
    MAX-ACCESS      read-only
    STATUS          current
    DESCRIPTION
        "The value of svcMrpPolicyParamsLastChanged indicates the sysUpTime at
         the time of the last modification of this entry.

         If no changes were made to the entry since the last re-initialization
         of the local network management subsystem, then this object contains a
         zero value."
    ::= { svcMrpPolicyParamsEntry 3 }

svcMrpPolicyParamsDescription OBJECT-TYPE
    SYNTAX          TItemDescription
    MAX-ACCESS      read-create
    STATUS          current
    DESCRIPTION
        "The value of svcMrpPolicyParamsDescription specifies the user provided
         description of this mrp-policy entry."
    DEFVAL { "" }
    ::= { svcMrpPolicyParamsEntry 4 }

svcMrpPolicyParamsAction  OBJECT-TYPE
    SYNTAX          TMrpPolicyAction
    MAX-ACCESS      read-create
    STATUS          current
    DESCRIPTION
        "The value of svcMrpPolicyParamsAction specifies the action to take for
         packets that match this mrp-policy entry."
    DEFVAL { none }
    ::= { svcMrpPolicyParamsEntry 5 }


-- ----------------------
-- svcMrpPolicyParamsISIDTable
-- ----------------------
svcMrpPlcyParamsISIDTblLastChgd  OBJECT-TYPE
    SYNTAX          TimeStamp
    MAX-ACCESS      read-only
    STATUS          current
    DESCRIPTION
        "The value of svcMrpPlcyParamsISIDTblLastChgd indicates the sysUpTime
         at the time of the last modification of svcMrpPolicyParamsISIDTable.

         If no changes were made to the entry since the last re-initialization
         of the local network management subsystem, then this object contains a
         zero value."
    ::= { tmnxSvcObjs 68 }

svcMrpPolicyParamsISIDTable OBJECT-TYPE
    SYNTAX          SEQUENCE OF SvcMrpPolicyParamsISIDEntry
    MAX-ACCESS      not-accessible
    STATUS          current
    DESCRIPTION
        "The svcMrpPolicyParamsISIDTable has an entry for each ISID
         value/range in a particular mrp policy entry."
    ::= { tmnxSvcObjs 69 }

svcMrpPolicyParamsISIDEntry OBJECT-TYPE
    SYNTAX          SvcMrpPolicyParamsISIDEntry
    MAX-ACCESS      not-accessible
    STATUS          current
    DESCRIPTION
        "svcMrpPolicyParamsISIDTable contains the information about
         an ISID value/range in a particular mrp-policy entry."
    INDEX { svcMrpPolicyName, svcMrpPolicyParamsEntryId,
            svcMrpPolicyParamsISIDLow }
    ::= { svcMrpPolicyParamsISIDTable 1 }

SvcMrpPolicyParamsISIDEntry ::=
    SEQUENCE {
        svcMrpPolicyParamsISIDLow       SvcISID,
        svcMrpPolicyParamsISIDHigh      SvcISID,
        svcMrpPolicyParamsISIDRowStatus RowStatus,
        svcMrpPolicyParamsISIDLastChgd  TimeStamp
    }

svcMrpPolicyParamsISIDLow OBJECT-TYPE
    SYNTAX       SvcISID (0..16777215)
    MAX-ACCESS   not-accessible
    STATUS       current
    DESCRIPTION
        "The value of svcMrpPolicyParamsISIDLow specifies the lowest value of
         the 24 bit (0..16777215) service instance identifier for this service
         that matches this entry and is used as third key of this MIB table.

         The value of this field can be equal to but not higher than the value
         of the svcMrpPolicyParamsISIDHigh field.
         "
    ::= { svcMrpPolicyParamsISIDEntry 1 }

svcMrpPolicyParamsISIDHigh OBJECT-TYPE
    SYNTAX       SvcISID (0..16777215)
    MAX-ACCESS   read-create
    STATUS       current
    DESCRIPTION
        "The value of svcMrpPolicyParamsISIDHigh specifies the highest value of
         the 24 bit (0..16777215) service instance identifier for this service
         that matches this entry.

         The value of this field can be equal to but not lower than the value
         of the svcMrpPolicyParamsISIDLow field.
         
         If this field is modified in an existing row of this table, the new 
         value will be silently rejected if it's lower than the existing value 
         of svcMrpPolicyParamsISIDHigh.
         "
    ::= { svcMrpPolicyParamsISIDEntry 2 }

svcMrpPolicyParamsISIDRowStatus OBJECT-TYPE
    SYNTAX          RowStatus
    MAX-ACCESS      read-create
    STATUS          current
    DESCRIPTION
        "This value of the object svcMrpPolicyParamsISIDRowStatus specifies the
         status of this row."
    ::= { svcMrpPolicyParamsISIDEntry 3 }

svcMrpPolicyParamsISIDLastChgd OBJECT-TYPE
    SYNTAX          TimeStamp
    MAX-ACCESS      read-only
    STATUS          current
    DESCRIPTION
        "The value of svcMrpPolicyParamsISIDLastChgd indicates the sysUpTime at
         the time of the last modification of this entry.

         If no changes were made to the entry since the last re-initialization
         of the local network management subsystem, then this object contains a
         zero value."
    ::= { svcMrpPolicyParamsISIDEntry 4 }

-- ----------------------------------------
-- EPIPE Service Table
-- ----------------------------------------
svcEpipeTableLastChanged  OBJECT-TYPE
    SYNTAX          TimeStamp
    MAX-ACCESS      read-only
    STATUS          current
    DESCRIPTION     "The value of svcEpipeTableLastChanged indicates the
                     sysUpTime at the time of the last modification of
                     svcEpipeTable.

                     If no changes were made to the entry since the last
                     re-initialization of the local network management subsystem,
                     then this object contains a zero value."
    ::= { tmnxSvcObjs 70 }

svcEpipeTable OBJECT-TYPE
    SYNTAX          SEQUENCE OF SvcEpipeEntry
    MAX-ACCESS      not-accessible
    STATUS          current
    DESCRIPTION     "The svcEpipeTable contains objects related to 'epipe'
                     services.
                     
                     Entries are created and destroyed when 'epipe' services
                     are created and destroyed by the system."
    ::= { tmnxSvcObjs 71 }

svcEpipeEntry OBJECT-TYPE
    SYNTAX          SvcEpipeEntry
    MAX-ACCESS      not-accessible
    STATUS          current
    DESCRIPTION     "Each row entry contains objects that allows the
                     modification of the 'epipe' specific objects."
    INDEX        { svcId }
    ::= { svcEpipeTable 1 }

SvcEpipeEntry ::=
    SEQUENCE {
        svcEpipeLastChngd               TimeStamp,
        svcEpipePerSvcHashing           TmnxEnabledDisabled
    }

svcEpipeLastChngd        OBJECT-TYPE
    SYNTAX          TimeStamp
    MAX-ACCESS      read-only
    STATUS          current
    DESCRIPTION     "The value of svcEpipeLastChngd indicates the sysUpTime at
                     the time of the last modification of this entry.
                     
                     If no changes were made to the entry since the last 
                     re-initialization of the local network management 
                     subsystem, then this object contains a zero value."
    ::= { svcEpipeEntry 1 }

svcEpipePerSvcHashing  OBJECT-TYPE
    SYNTAX          TmnxEnabledDisabled
    MAX-ACCESS      read-write
    STATUS          current
    DESCRIPTION     "The value of svcEpipePerSvcHashing specifies service-level
                     hashing for Ethernet services."
    DEFVAL { disabled }
    ::= { svcEpipeEntry 2 }

-- ----------------------------------------
-- EPIPE service backbone Table
-- ----------------------------------------
svcEpipeBackboneTableLastChanged  OBJECT-TYPE
    SYNTAX          TimeStamp
    MAX-ACCESS      read-only
    STATUS          current
    DESCRIPTION     "The value of svcEpipeBackboneTableLastChanged indicates the
                     sysUpTime at the time of the last modification of
                     svcEpipeBackboneTable.

                     If no changes were made to the entry since the last
                     re-initialization of the local network management subsystem,
                     then this object contains a zero value."
    ::= { tmnxSvcObjs 72 }

svcEpipeBackboneTable OBJECT-TYPE
    SYNTAX          SEQUENCE OF SvcEpipeBackboneEntry
    MAX-ACCESS      not-accessible
    STATUS          current
    DESCRIPTION     "The svcEpipeBackboneTable contains objects related to
                     Provider Backbone Bridging (PBB) feature as relates to
                     'epipe' services.
                     
                     Entries are created and destroyed when 'epipe' services
                     are created and destroyed by the system."
    ::= { tmnxSvcObjs 73 }

svcEpipeBackboneEntry OBJECT-TYPE
    SYNTAX          SvcEpipeBackboneEntry
    MAX-ACCESS      not-accessible
    STATUS          current
    DESCRIPTION     "Each row entry contains objects that allows the
                     modification of the PBB objects for an 'epipe' service."
    INDEX        { svcId }
    ::= { svcEpipeBackboneTable 1 }

SvcEpipeBackboneEntry ::=
    SEQUENCE {
        svcEpipeBackboneLastChngd               TimeStamp,
        svcEpipeBackboneForceQTagFwd            TruthValue
    }

svcEpipeBackboneLastChngd        OBJECT-TYPE
    SYNTAX          TimeStamp
    MAX-ACCESS      read-only
    STATUS          current
    DESCRIPTION     "The value of svcEpipeBackboneLastChngd indicates the
                     sysUpTime at the time of the last modification of this
                     entry.
                     
                     If no changes were made to the entry since the last 
                     re-initialization of the local network management 
                     subsystem, then this object contains a zero value."
    ::= { svcEpipeBackboneEntry 1 }

svcEpipeBackboneForceQTagFwd OBJECT-TYPE
    SYNTAX          TruthValue
    MAX-ACCESS      read-write
    STATUS          current
    DESCRIPTION     "The value of svcEpipeBackboneForceQTagFwd specifies 
                     whether to enable addition of an IEEE 802.1q tag
                     after the Customer MAC address when the PBB header is
                     built, as it egresses related 'b-vpls' service."
    DEFVAL { false }
    ::= { svcEpipeBackboneEntry 2 }

-- ----------------------
-- svcTlsSiteIdTable
-- ----------------------
svcTlsSiteIdTblLastChanged  OBJECT-TYPE
    SYNTAX          TimeStamp
    MAX-ACCESS      read-only
    STATUS          current
    DESCRIPTION
        "The value of svcTlsSiteIdTblLastChanged indicates the sysUpTime
         at the time of the last modification of svcTlsSiteIdTable.

         If no changes were made to the entry since the last re-initialization
         of the local network management subsystem, then this object contains a
         zero value."
    ::= { tmnxSvcObjs 74 }

svcTlsSiteIdTable OBJECT-TYPE
    SYNTAX          SEQUENCE OF SvcTlsSiteIdEntry
    MAX-ACCESS      not-accessible
    STATUS          current
    DESCRIPTION
        "This table maintains the information about different sites defined
         in a service."
    ::= { tmnxSvcObjs 75 } 
    
svcTlsSiteIdEntry OBJECT-TYPE
    SYNTAX          SvcTlsSiteIdEntry
    MAX-ACCESS      not-accessible
    STATUS          current
    DESCRIPTION
        "Information about a particular site in a specific service."
    INDEX { svcId, svcTlsSiteIdName }
    ::= { svcTlsSiteIdTable 1 }

SvcTlsSiteIdEntry ::=
    SEQUENCE {
        svcTlsSiteIdName             TNamedItem,
        svcTlsSiteIdRowStatus        RowStatus,
        svcTlsSiteIdLastChanged      TimeStamp,
        svcTlsSiteIdAdminStatus      TmnxEnabledDisabled,
        svcTlsSiteIdSiteId           TmnxSiteIdOrEmpty,
        svcTlsSiteIdPortId           TmnxPortID,
        svcTlsSiteIdEncapValue       TmnxEncapVal,
        svcTlsSiteIdSdpBindId        SdpBindId,
        svcTlsSiteIdShgName          TNamedItemOrEmpty,
        svcTlsSiteIdShgMeshSdp       TruthValue,
        svcTlsSiteIdFailedThresh     Integer32,
        svcTlsSiteIdOperStatus       TSiteOperStatus,
        svcTlsSiteIdDesignatedFwdr   TruthValue,
        svcTlsSiteIdBootTimer        Integer32,
        svcTlsSiteIdSiteActTimer     Integer32,
        svcTlsSiteIdDfUpTime         Unsigned32,
        svcTlsSiteIdDfChgCnt         Unsigned32,
        svcTlsSiteIdTimerRemain      Unsigned32,
        svcTlsSiteIdMonitorOperGrp   TNamedItemOrEmpty,
        svcTlsSiteIdActTimerRemain   Unsigned32,
        svcTlsSiteIdMinDnTimer     Integer32,
        svcTlsSiteIdMinDnTimerRemain  Unsigned32
    }
    
svcTlsSiteIdName OBJECT-TYPE
    SYNTAX       TNamedItem
    MAX-ACCESS   not-accessible
    STATUS       current
    DESCRIPTION     
        "The value of svcTlsSiteIdName defines the name for the specific site."
    ::= { svcTlsSiteIdEntry 1 }
 
svcTlsSiteIdRowStatus OBJECT-TYPE
    SYNTAX       RowStatus
    MAX-ACCESS   read-create
    STATUS       current
    DESCRIPTION  
         "The value of svcTlsSiteIdRowStatus is used for the creation and 
          deletion of rows in this table."
    ::= { svcTlsSiteIdEntry 2 }   
    
svcTlsSiteIdLastChanged OBJECT-TYPE
    SYNTAX       TimeStamp
    MAX-ACCESS   read-only
    STATUS       current
    DESCRIPTION  
        "The value of svcTlsSiteIdLastChanged indicates the timestamp of
         last change to this row in svcTlsSiteIdTable."
    ::= { svcTlsSiteIdEntry 3 }  
    
svcTlsSiteIdAdminStatus OBJECT-TYPE
    SYNTAX       TmnxEnabledDisabled
    MAX-ACCESS   read-create
    STATUS       current
    DESCRIPTION
        "The value of svcTlsSiteIdAdminStatus specifies the administrative
         state of the site instance associated with this service."
    DEFVAL { disabled }
    ::= { svcTlsSiteIdEntry 4 } 
    
svcTlsSiteIdSiteId OBJECT-TYPE
    SYNTAX       TmnxSiteIdOrEmpty
    MAX-ACCESS   read-create
    STATUS       current
    DESCRIPTION
        "The value of svcTlsSiteIdSiteId specifies the identifier for the site
         in this service.
         
         The value of svcTlsSiteIdSiteId is a two byte identifier usually
         employed for the BGP Multi-homing solution. It identifies the BGP
         Multi-homing site associated with one or a set of objects (SAPs,
         PWs or combination). The value of svcTlsSiteIdSiteId must be
         identical between the two PEs carrying the connection to the access
         device multi-homed to the PEs."
    REFERENCE "RFC-4761"
    DEFVAL { -1 }
    ::= { svcTlsSiteIdEntry 5 }   
    
svcTlsSiteIdPortId OBJECT-TYPE
    SYNTAX       TmnxPortID
    MAX-ACCESS   read-create
    STATUS       current
    DESCRIPTION
        "The value of svcTlsSiteIdPortId specifies the port associated with
         this site.

         The default value for this object indicates an invalid port.
         
         An 'inconsistentValue' error is returned when svcTlsSiteIdPortId is
         set to non-default and svcTlsSiteIdEncapValue is set to its default
         value or when svcTlsSiteIdPortId is set to its default value and 
         svcTlsSiteIdEncapValue is set to non-default value.

         An 'inconsistentValue' error is returned if an attempt is made to
         set the non-default value to more than one of the following object
         groups (SAP, SDP-BIND, Split-Horizon Group name):

         SAP:                      svcTlsSiteIdPortId, svcTlsSiteIdEncapValue
         SDP-BIND:                 svcTlsSiteIdSdpBindId
         Split-Horizon Group name: svcTlsSiteIdShgName."
    DEFVAL { '1E000000'H }
    ::= { svcTlsSiteIdEntry 6 } 
    
svcTlsSiteIdEncapValue OBJECT-TYPE
    SYNTAX       TmnxEncapVal
    MAX-ACCESS   read-create
    STATUS       current
    DESCRIPTION
        "The value of svcTlsSiteIdEncapValue specifies the encap-value of the
         port associated with this site.

         An 'inconsistentValue' error is returned when svcTlsSiteIdPortId is
         set to non-default and svcTlsSiteIdEncapValue is set to its default
         value or when svcTlsSiteIdPortId is set to its default value and 
         svcTlsSiteIdEncapValue is set to non-default value.

         An 'inconsistentValue' error is returned if an attempt is made to
         set the non-default value to more than one of the following object
         groups (SAP, SDP-BIND, Split-Horizon Group name):

         SAP:                      svcTlsSiteIdPortId, svcTlsSiteIdEncapValue
         SDP-BIND:                 svcTlsSiteIdSdpBindId
         Split-Horizon Group name: svcTlsSiteIdShgName."
    DEFVAL { 0 }
    ::= { svcTlsSiteIdEntry 7 }
    
svcTlsSiteIdSdpBindId OBJECT-TYPE
    SYNTAX       SdpBindId
    MAX-ACCESS   read-create
    STATUS       current
    DESCRIPTION
        "The value of the svcTlsSiteIdSdpBindId specifies the value of
         SDP binding associated with this site.

         An 'inconsistentValue' error is returned if an attempt is made to
         set the non-default value to more than one of the following object
         groups (SAP, SDP-BIND, Split-Horizon Group name):

         SAP:                      svcTlsSiteIdPortId, svcTlsSiteIdEncapValue
         SDP-BIND:                 svcTlsSiteIdSdpBindId
         Split-Horizon Group name: svcTlsSiteIdShgName."
    DEFVAL { '0000000000000000'H }
    ::= { svcTlsSiteIdEntry 8 }   
    
svcTlsSiteIdShgName OBJECT-TYPE
    SYNTAX       TNamedItemOrEmpty
    MAX-ACCESS   read-create
    STATUS       current
    DESCRIPTION
        "The value of the svcTlsSiteIdShgName specifies the value of
         split-horizon group associated with this site.

         An 'inconsistentValue' error is returned if an attempt is made to
         set the non-default value to more than one of the following object
         groups (SAP, SDP-BIND, Split-Horizon Group name):

         SAP:                      svcTlsSiteIdPortId, svcTlsSiteIdEncapValue
         SDP-BIND:                 svcTlsSiteIdSdpBindId
         Split-Horizon Group name: svcTlsSiteIdShgName."
    DEFVAL { ''H }
    ::= { svcTlsSiteIdEntry 9 }  
    
svcTlsSiteIdShgMeshSdp OBJECT-TYPE
    SYNTAX       TruthValue
    MAX-ACCESS   read-create
    STATUS       current
    DESCRIPTION
        "The value of the svcTlsSiteIdShgMeshSdp specifies whether this
         site-id is to be applied to all the mesh-SDPs in this service."
    DEFVAL { false }
    ::= { svcTlsSiteIdEntry 10 }
    
svcTlsSiteIdFailedThresh     OBJECT-TYPE
    SYNTAX       Integer32 (-1|1..1000)
    MAX-ACCESS   read-create
    STATUS       current
    DESCRIPTION
        "The value of the svcTlsSiteIdFailedThresh specifies the number of
         objects which are required to be in the 'down' state for this site
         to be declared in the 'down' state.

         The value of '-1' indicates that 'all' objects in this site should be
         down for the site to be declared in the 'down' state."
    DEFVAL { -1 }
    ::= { svcTlsSiteIdEntry 11 }
    
svcTlsSiteIdOperStatus       OBJECT-TYPE
    SYNTAX       TSiteOperStatus
    MAX-ACCESS   read-only
    STATUS       current
    DESCRIPTION
        "The value of the svcTlsSiteIdOperStatus indicates the operational
         status of the site."
    ::= { svcTlsSiteIdEntry 12 }
    
svcTlsSiteIdDesignatedFwdr   OBJECT-TYPE
    SYNTAX       TruthValue
    MAX-ACCESS   read-only
    STATUS       current
    DESCRIPTION
        "The value of the svcTlsSiteIdDesignatedFwdr indicates whether this
         site has been declared as 'designated-forwarder' depending on the
         result of the BGP election."
    ::= { svcTlsSiteIdEntry 13 }
    
svcTlsSiteIdBootTimer OBJECT-TYPE
    SYNTAX       Integer32 (-1|0..600)
    UNITS        "seconds"
    MAX-ACCESS   read-create
    STATUS       current
    DESCRIPTION
        "The value of svcTlsSiteIdBootTimer specifies how long the
        system waits after a node reboot before running the DF (designated-
        forwarder) election algorithm.

        When this object is set to default value, system uses value of
        TIMETRA-MC-REDUNDANCY-MIB::tmnxMcRedBgpMultiHomeBootTimer object."
    DEFVAL { -1 }
    ::= { svcTlsSiteIdEntry 14 }

svcTlsSiteIdSiteActTimer OBJECT-TYPE
    SYNTAX       Integer32 (-1|0..100)
    UNITS        "seconds"
    MAX-ACCESS   read-create
    STATUS       current
    DESCRIPTION
        "The value of svcTlsSiteIdSiteActTimer specifies the time-period
        the system keeps the local sites in standby status, waiting for BGP
        updates from remote PEs before running the DF (designated-forwarder)
        election algorithm to decide whether the site should be unblocked.

        When this object is set to default value, system uses value of
        TIMETRA-MC-REDUNDANCY-MIB::tmnxMcRedBgpMultiHomeSiteTimer object."
    DEFVAL { -1 }
    ::= { svcTlsSiteIdEntry 15 }

svcTlsSiteIdDfUpTime OBJECT-TYPE
    SYNTAX       Unsigned32
    UNITS        "seconds"
    MAX-ACCESS   read-only
    STATUS       current
    DESCRIPTION  
        "The value of svcTlsSiteIdDfUpTime indicates the uptime of the
         designated forwarder for this site."
    ::= { svcTlsSiteIdEntry 16 }  
    
svcTlsSiteIdDfChgCnt OBJECT-TYPE
    SYNTAX       Unsigned32
    MAX-ACCESS   read-only
    STATUS       current
    DESCRIPTION  
        "The value of svcTlsSiteIdDfChgCnt indicates the number of times
         designated forwarder has changed."
    ::= { svcTlsSiteIdEntry 17 }  
    
svcTlsSiteIdTimerRemain OBJECT-TYPE
    SYNTAX       Unsigned32
    UNITS        "seconds"
    MAX-ACCESS   read-only
    STATUS       current
    DESCRIPTION
        "The value of svcTlsSiteIdTimerRemain indicates remaining time
        in the boot timer for this site."
    ::= { svcTlsSiteIdEntry 18 }

svcTlsSiteIdMonitorOperGrp OBJECT-TYPE
    SYNTAX          TNamedItemOrEmpty
    MAX-ACCESS      read-create
    STATUS          current
    DESCRIPTION     
        "The value of the svcTlsSiteIdMonitorOperGrp specifies the
         Operational-Group identifier which will affect the state
         of this site."
    DEFVAL { "" }
    ::= { svcTlsSiteIdEntry 19 }

svcTlsSiteIdActTimerRemain OBJECT-TYPE
    SYNTAX       Unsigned32
    UNITS        "seconds"
    MAX-ACCESS   read-only
    STATUS       current
    DESCRIPTION
        "The value of svcTlsSiteIdActTimerRemain indicates remaining time
        in the activation timer for this site."
    ::= { svcTlsSiteIdEntry 20 }

svcTlsSiteIdMinDnTimer OBJECT-TYPE
    SYNTAX       Integer32 (-1|0..100)
    UNITS        "seconds"
    MAX-ACCESS   read-create
    STATUS       current
    DESCRIPTION
        "The value of svcTlsSiteIdMinDnTimer specifies the minimum
        time-period the system keeps the site down when a site goes down.

        When this object is set to default value, system uses value of
        TIMETRA-MC-REDUNDANCY-MIB::tmnxMcRedBgpMHSiteMinDnTimer object."
    DEFVAL { -1 }
    ::= { svcTlsSiteIdEntry 21 }

svcTlsSiteIdMinDnTimerRemain OBJECT-TYPE
    SYNTAX       Unsigned32
    UNITS        "seconds"
    MAX-ACCESS   read-only
    STATUS       current
    DESCRIPTION
        "The value of svcTlsSiteIdMinDnTimerRemain indicates remaining time
        in the svcTlsSiteIdMinDnTimer for this site."
    ::= { svcTlsSiteIdEntry 22 }

-- ----------------------
-- svcBgpVplsTable
-- ----------------------
svcBgpVplsTblLastChanged  OBJECT-TYPE
    SYNTAX          TimeStamp
    MAX-ACCESS      read-only
    STATUS          current
    DESCRIPTION
        "The value of svcBgpVplsTblLastChanged indicates the sysUpTime
         at the time of the last modification of svcBgpVplsTable.

         If no changes were made to the entry since the last re-initialization
         of the local network management subsystem, then this object contains a
         zero value."
    ::= { tmnxSvcObjs 78 }

svcBgpVplsTable OBJECT-TYPE
    SYNTAX          SEQUENCE OF SvcBgpVplsEntry
    MAX-ACCESS      not-accessible
    STATUS          current
    DESCRIPTION
        "This table maintains the information about BGP-VPLS feature information
         for a service."
    ::= { tmnxSvcObjs 79 } 
    
svcBgpVplsEntry OBJECT-TYPE
    SYNTAX          SvcBgpVplsEntry
    MAX-ACCESS      not-accessible
    STATUS          current
    DESCRIPTION
        "Information about BGP-VPLS feature for a specific service."
    INDEX { svcId }
    ::= { svcBgpVplsTable 1 }

SvcBgpVplsEntry ::=
    SEQUENCE {
        svcBgpVplsRowStatus        RowStatus,
        svcBgpVplsLastChanged      TimeStamp,
        svcBgpVplsMaxVeId          Integer32,
        svcBgpVplsAdminStatus      TmnxEnabledDisabled,
        svcBgpVplsVeName           TNamedItemOrEmpty,
        svcBgpVplsVeId             TmnxSiteIdOrEmpty,
        svcBgpVplsPwTemplateId     PWTemplateId
    }
    
svcBgpVplsRowStatus OBJECT-TYPE
    SYNTAX       RowStatus
    MAX-ACCESS   read-create
    STATUS       current
    DESCRIPTION  
         "The value of svcBgpVplsRowStatus is used for the creation and 
          deletion of rows in this table."
    ::= { svcBgpVplsEntry 1 }   

svcBgpVplsLastChanged OBJECT-TYPE
    SYNTAX       TimeStamp
    MAX-ACCESS   read-only
    STATUS       current
    DESCRIPTION  
        "The value of svcBgpVplsLastChanged indicates the timestamp of last
        change to this row in svcBgpVplsTable."
    ::= { svcBgpVplsEntry 2 }  
    
svcBgpVplsMaxVeId OBJECT-TYPE
    SYNTAX       Integer32 (-1|1..65535)
    MAX-ACCESS   read-create
    STATUS       current
    DESCRIPTION
         "The value of the svcBgpVplsMaxVeId specifies the value of
          vpls-edge-range for this service."
    DEFVAL { -1 }
    ::= { svcBgpVplsEntry 3 }   
    
svcBgpVplsAdminStatus OBJECT-TYPE
    SYNTAX       TmnxEnabledDisabled
    MAX-ACCESS   read-create
    STATUS       current
    DESCRIPTION
        "The value of svcBgpVplsAdminStatus specifies the administrative
         state of the vpls-edge instance associated with this service."
    DEFVAL { disabled }
    ::= { svcBgpVplsEntry 4 } 
    
svcBgpVplsVeName OBJECT-TYPE
    SYNTAX       TNamedItemOrEmpty
    MAX-ACCESS   read-create
    STATUS       current
    DESCRIPTION     
        "The value of svcBgpVplsVeName specifies the name for the specific
         vpls-edge."
    DEFVAL { ''H }
    ::= { svcBgpVplsEntry 5 }
 
svcBgpVplsVeId OBJECT-TYPE
    SYNTAX       TmnxSiteIdOrEmpty
    MAX-ACCESS   read-create
    STATUS       current
    DESCRIPTION
        "The value of svcBgpVplsVeId specifies the identifier for the
         vpls-edge in this service.

         The svcBgpVplsVeId is a two bytes identifier that represents the
         local bridging instance in a VPLS and is advertised through the BGP
         Network Layer Reachability Information (NLRI).
         
         An 'inconsistentValue' error is returned if value of svcBgpVplsVeId is
         set to the value of svcBgpVplsMaxVeId or lower.
         
         An 'inconsistentError' is returned if this object is set to
         non-default value when svcBgpVplsVeName is set to its default
         value."
    REFERENCE "RFC-4761"
    DEFVAL { -1 }
    ::= { svcBgpVplsEntry 6 }   
    
svcBgpVplsPwTemplateId OBJECT-TYPE
    SYNTAX     PWTemplateId
    MAX-ACCESS read-only
    STATUS     current
    DESCRIPTION
        "The value of svcBgpVplsPwTemplateId indicates the pseudo-wire template
         used in transmitting BGP-VPLS NLRI information for this VPLS edge in
         this service."
    ::= { svcBgpVplsEntry 7 }   

-- ----------------------------------------
-- Vpls BGP Table
-- ----------------------------------------

svcTlsBgpTableLastChanged  OBJECT-TYPE
    SYNTAX          TimeStamp
    MAX-ACCESS      read-only
    STATUS          current
    DESCRIPTION     "The value of svcTlsBgpTableLastChanged indicates the
                     sysUpTime at the time of the last modification
                     of svcTlsBgpTable.

                     If no changes were made to the entry since the last
                     re-initialization of the local network management subsystem,
                     then this object contains a zero value."
    ::= { tmnxSvcObjs 80 }

svcTlsBgpTable OBJECT-TYPE
    SYNTAX          SEQUENCE OF SvcTlsBgpEntry
    MAX-ACCESS      not-accessible
    STATUS          current
    DESCRIPTION     "svcTlsBgpTable contains entries for BGP
                     in a VPLS service context." 
    ::= { tmnxSvcObjs 81 }

svcTlsBgpEntry    OBJECT-TYPE
    SYNTAX          SvcTlsBgpEntry
    MAX-ACCESS      not-accessible
    STATUS          current
    DESCRIPTION     "A BGP entry in the svcTlsBgpTable."
    INDEX           { svcId }
    ::= { svcTlsBgpTable 1}

SvcTlsBgpEntry ::=    SEQUENCE {
    svcTlsBgpLastChanged         TimeStamp,
    svcTlsBgpVsiRD               TmnxVPNRouteDistinguisher,
    svcTlsBgpExportRteTarget     TNamedItemOrEmpty,
    svcTlsBgpVsiExportPolicy1    TPolicyStatementNameOrEmpty,
    svcTlsBgpVsiExportPolicy2    TPolicyStatementNameOrEmpty,
    svcTlsBgpVsiExportPolicy3    TPolicyStatementNameOrEmpty,
    svcTlsBgpVsiExportPolicy4    TPolicyStatementNameOrEmpty,
    svcTlsBgpVsiExportPolicy5    TPolicyStatementNameOrEmpty,
    svcTlsBgpImportRteTarget     TNamedItemOrEmpty,
    svcTlsBgpVsiImportPolicy1    TPolicyStatementNameOrEmpty,
    svcTlsBgpVsiImportPolicy2    TPolicyStatementNameOrEmpty,
    svcTlsBgpVsiImportPolicy3    TPolicyStatementNameOrEmpty,
    svcTlsBgpVsiImportPolicy4    TPolicyStatementNameOrEmpty,
    svcTlsBgpVsiImportPolicy5    TPolicyStatementNameOrEmpty,
    svcTlsBgpRowStatus           RowStatus,
    svcTlsBgpCreationOrigin      TmnxCreateOrigin,
    svcTlsBgpOperImportRteTgtOrigin TmnxRouteTargetOrigin,
    svcTlsBgpOperImportRteTarget    TNamedItemOrEmpty,
    svcTlsBgpOperExportRteTgtOrigin TmnxRouteTargetOrigin,
    svcTlsBgpOperExportRteTarget    TNamedItemOrEmpty
}

svcTlsBgpLastChanged        OBJECT-TYPE
    SYNTAX          TimeStamp
    MAX-ACCESS      read-only
    STATUS          current
    DESCRIPTION     "The value of svcTlsBgpLastChanged indicates the 
                     sysUpTime at the time of the last modification of
                     this entry.
                     
                     If no changes were made to the entry since the last 
                     re-initialization of the local network management 
                     subsystem, then this object contains a zero value."
    ::= { svcTlsBgpEntry 1 }

svcTlsBgpVsiRD     OBJECT-TYPE
    SYNTAX          TmnxVPNRouteDistinguisher
    MAX-ACCESS      read-create
    STATUS          current
    DESCRIPTION     "The value of svcTlsBgpVsiRD specifies the high-order
                     6 bytes used to compose the Virtual Switch Instance
                     identifier (VSI-id) to use for NLRI in BGP 
                     in this VPLS service.

                     If the value of svcTlsBgpVsiRD is 0x0000000000000000,
                     the lower 6 bytes of the VPLS-id, as specified by
                     svcTlsBgpADVplsId, will be used.
                     "
    DEFVAL          { '0000000000000000'H }
    ::= { svcTlsBgpEntry 2 }

svcTlsBgpExportRteTarget       OBJECT-TYPE
    SYNTAX          TNamedItemOrEmpty
    MAX-ACCESS      read-create
    STATUS          current
    DESCRIPTION     "The value of svcTlsBgpExportRteTarget specifies the
                     extended community name for the default export policy
                     to use for BGP  in this VPLS service.

                     This object cannot be set to a non-empty if
                     svcTlsBgpExportRteTarget has a non-empty value, 
                     otherwise an 'inconsistentValue' error will be
                     returned."
    DEFVAL          { "" }
    ::= { svcTlsBgpEntry 3 }

svcTlsBgpVsiExportPolicy1  OBJECT-TYPE
    SYNTAX          TPolicyStatementNameOrEmpty
    MAX-ACCESS      read-create
    STATUS          current
    DESCRIPTION    "The value of svcTlsBgpVsiExportPolicy1 specifies the
                    name of the first VSI export policy to be used for BGP
                     in this VPLS service.

                    If multiple policy names are specified, the policies are
                    evaluated in the order they are specified.  The first
                    policy that matches is applied.

                    The import policy name list, svcTlsBgpVsiExportPolicy1
                    through svcTlsBgpVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 4 }

svcTlsBgpVsiExportPolicy2  OBJECT-TYPE
    SYNTAX          TPolicyStatementNameOrEmpty
    MAX-ACCESS      read-create
    STATUS          current
    DESCRIPTION    "The value of svcTlsBgpVsiExportPolicy2 specifies the
                    name of the second VSI export policy to be used for BGP
                     in this VPLS service.

                    If multiple policy names are specified, the policies are
                    evaluated in the order they are specified.  The first
                    policy that matches is applied.

                    The import policy name list, svcTlsBgpVsiExportPolicy1
                    through svcTlsBgpVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 5 }

svcTlsBgpVsiExportPolicy3  OBJECT-TYPE
    SYNTAX          TPolicyStatementNameOrEmpty
    MAX-ACCESS      read-create
    STATUS          current
    DESCRIPTION    "The value of svcTlsBgpVsiExportPolicy3 specifies the
                    name of the third VSI export policy to be used for BGP
                     in this VPLS service.

                    If multiple policy names are specified, the policies are
                    evaluated in the order they are specified.  The first
                    policy that matches is applied.

                    The import policy name list, svcTlsBgpVsiExportPolicy1
                    through svcTlsBgpVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 6 }

svcTlsBgpVsiExportPolicy4  OBJECT-TYPE
    SYNTAX          TPolicyStatementNameOrEmpty
    MAX-ACCESS      read-create
    STATUS          current
    DESCRIPTION    "The value of svcTlsBgpVsiExportPolicy4 specifies the
                    name of the forth VSI export policy to be used for BGP
                     in this VPLS service.

                    If multiple policy names are specified, the policies are
                    evaluated in the order they are specified.  The first
                    policy that matches is applied.

                    The import policy name list, svcTlsBgpVsiExportPolicy1
                    through svcTlsBgpVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 7 }

svcTlsBgpVsiExportPolicy5  OBJECT-TYPE
    SYNTAX          TPolicyStatementNameOrEmpty
    MAX-ACCESS      read-create
    STATUS          current
    DESCRIPTION    "The value of svcTlsBgpVsiExportPolicy5 specifies the
                    name of the fifth VSI export policy to be used for BGP
                     in this VPLS service.

                    If multiple policy names are specified, the policies are
                    evaluated in the order they are specified.  The first
                    policy that matches is applied.

                    The import policy name list, svcTlsBgpVsiExportPolicy1
                    through svcTlsBgpVsiExportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 8 }

svcTlsBgpImportRteTarget       OBJECT-TYPE
    SYNTAX          TNamedItemOrEmpty
    MAX-ACCESS      read-create
    STATUS          current
    DESCRIPTION     "The value of svcTlsBgpImportRteTarget specifies the
                     extended community name for the default import policy
                     to use for BGP  in this VPLS service.

                     This object cannot be set to a non-empty if
                     svcTlsBgpImportRteTarget has a non-empty value, 
                     otherwise an 'inconsistentValue' error will be
                     returned."
    DEFVAL          { "" }
    ::= { svcTlsBgpEntry 9 }

svcTlsBgpVsiImportPolicy1  OBJECT-TYPE
    SYNTAX          TPolicyStatementNameOrEmpty
    MAX-ACCESS      read-create
    STATUS          current
    DESCRIPTION    "The value of svcTlsBgpVsiImportPolicy1 specifies the
                    name of the first VSI export policy to be used for BGP
                     in this VPLS service.

                    If multiple policy names are specified, the policies are
                    evaluated in the order they are specified.  The first
                    policy that matches is applied.

                    The import policy name list, svcTlsBgpVsiImportPolicy1
                    through svcTlsBgpVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 10 }

svcTlsBgpVsiImportPolicy2  OBJECT-TYPE
    SYNTAX          TPolicyStatementNameOrEmpty
    MAX-ACCESS      read-create
    STATUS          current
    DESCRIPTION    "The value of svcTlsBgpVsiImportPolicy2 specifies the
                    name of the second VSI export policy to be used for BGP
                     in this VPLS service.

                    If multiple policy names are specified, the policies are
                    evaluated in the order they are specified.  The first
                    policy that matches is applied.

                    The import policy name list, svcTlsBgpVsiImportPolicy1
                    through svcTlsBgpVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 11 }

svcTlsBgpVsiImportPolicy3  OBJECT-TYPE
    SYNTAX          TPolicyStatementNameOrEmpty
    MAX-ACCESS      read-create
    STATUS          current
    DESCRIPTION    "The value of svcTlsBgpVsiImportPolicy3 specifies the
                    name of the third VSI export policy to be used for BGP
                     in this VPLS service.

                    If multiple policy names are specified, the policies are
                    evaluated in the order they are specified.  The first
                    policy that matches is applied.

                    The import policy name list, svcTlsBgpVsiImportPolicy1
                    through svcTlsBgpVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 12 }

svcTlsBgpVsiImportPolicy4  OBJECT-TYPE
    SYNTAX          TPolicyStatementNameOrEmpty
    MAX-ACCESS      read-create
    STATUS          current
    DESCRIPTION    "The value of svcTlsBgpVsiImportPolicy4 specifies the
                    name of the forth VSI export policy to be used for BGP
                     in this VPLS service.

                    If multiple policy names are specified, the policies are
                    evaluated in the order they are specified.  The first
                    policy that matches is applied.

                    The import policy name list, svcTlsBgpVsiImportPolicy1
                    through svcTlsBgpVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 13 }

svcTlsBgpVsiImportPolicy5  OBJECT-TYPE
    SYNTAX          TPolicyStatementNameOrEmpty
    MAX-ACCESS      read-create
    STATUS          current
    DESCRIPTION    "The value of svcTlsBgpVsiImportPolicy5 specifies the
                    name of the fifth VSI export policy to be used for BGP
                     in this VPLS service.

                    If multiple policy names are specified, the policies are
                    evaluated in the order they are specified.  The first
                    policy that matches is applied.

                    The import policy name list, svcTlsBgpVsiImportPolicy1
                    through svcTlsBgpVsiImportPolicy5, is handled by the SNMP
                    agent as a single entity.  When an SNMP SET request is
                    received to modify one or more of the policy names, all
                    the policy variables are first set to the empty
                    string, ''H, and then the new names are set into the
                    specified policy variables within a single SNMP SET PDU."
    DEFVAL { ''H }      -- the empty string
    ::= { svcTlsBgpEntry 14 }

svcTlsBgpRowStatus OBJECT-TYPE
    SYNTAX       RowStatus
    MAX-ACCESS   read-create
    STATUS       current
    DESCRIPTION  "The value of svcTlsBgpRowStatus is used for the creation and 
                  deletion of rows in this table."
    ::= { svcTlsBgpEntry 15 }

svcTlsBgpCreationOrigin  OBJECT-TYPE
    SYNTAX          TmnxCreateOrigin
    MAX-ACCESS      read-only
    STATUS          current
    DESCRIPTION     "The value of svcTlsBgpCreationOrigin indicates the mechanism
                     used to create this entry."
    DEFVAL { manual }
    ::= { svcTlsBgpEntry 16 }

svcTlsBgpOperImportRteTgtOrigin       OBJECT-TYPE
    SYNTAX          TmnxRouteTargetOrigin
    MAX-ACCESS      read-only
    STATUS          current
    DESCRIPTION
        "The value of svcTlsBgpOperImportRteTgtOrigin indicates the origin of
         the route target import policy in use for BGP in this VPLS service."
    ::= { svcTlsBgpEntry 20 }
    
svcTlsBgpOperImportRteTarget       OBJECT-TYPE
    SYNTAX          TNamedItemOrEmpty
    MAX-ACCESS      read-only
    STATUS          current
    DESCRIPTION
        "The value of svcTlsBgpOperImportRteTarget indicates the
         extended community name for the import policy
         in use for BGP  in this VPLS service.
         
         This value will be Empty if the svcTlsBgpOperImportRteTgtOrigin is
         set to 'vsi'."
    ::= { svcTlsBgpEntry 21 }

svcTlsBgpOperExportRteTgtOrigin       OBJECT-TYPE
    SYNTAX          TmnxRouteTargetOrigin
    MAX-ACCESS      read-only
    STATUS          current
    DESCRIPTION
        "The value of svcTlsBgpOperExportRteTgtOrigin indicates the origin of
         the route target import policy in use for BGP in this VPLS service."
    ::= { svcTlsBgpEntry 22 }
    
svcTlsBgpOperExportRteTarget       OBJECT-TYPE
    SYNTAX          TNamedItemOrEmpty
    MAX-ACCESS      read-only
    STATUS          current
    DESCRIPTION
        "The value of svcTlsBgpOperExportRteTarget indicates the origin of
         extended community name for the export policy
         in use for BGP  in this VPLS service.

         This value will be Empty if the svcTlsBgpOperImportRteTgtOrigin is
         set to 'vsi'."
    ::= { svcTlsBgpEntry 23 }

--
-- svcTlsPbbIgmpSnpgMRtrTable
--
svcTlsPbbIgmpSnpgMRtrTable OBJECT-TYPE
    SYNTAX          SEQUENCE OF SvcTlsPbbIgmpSnpgMRtrEntry
    MAX-ACCESS      not-accessible
    STATUS          current
    DESCRIPTION     "A table that contains 
                     Provider Backbone Bridging (PBB/IEEE 802.1ah) IGMP 
                     Snooping MRouter Destination information."
    ::= { tmnxSvcObjs 82 }

svcTlsPbbIgmpSnpgMRtrEntry OBJECT-TYPE
    SYNTAX          SvcTlsPbbIgmpSnpgMRtrEntry
    MAX-ACCESS      not-accessible
    STATUS          current
    DESCRIPTION     "PBB I-Component instance-specific information about a 
                     specific IGMP Snooping MRouter in the B-Component instance.
    
                     Entries in this table can be created or deleted 
                     via SNMP operations."
    INDEX           { svcTlsPbbIgmpSnpgMRtrSvcIdIVpls,
                      svcTlsPbbIgmpSnpgMRtrSvcIdBVpls, 
                      IMPLIED svcTlsPbbIgmpSnpgMRtrMacName
                    }
    ::= { svcTlsPbbIgmpSnpgMRtrTable 1 }

SvcTlsPbbIgmpSnpgMRtrEntry ::=
    SEQUENCE {
        svcTlsPbbIgmpSnpgMRtrSvcIdIVpls  TmnxServId,
        svcTlsPbbIgmpSnpgMRtrSvcIdBVpls  TmnxServId,
        svcTlsPbbIgmpSnpgMRtrMacName     TNamedItem,
        svcTlsPbbIgmpSnpgMRtrRowStatus   RowStatus,
        svcTlsPbbIgmpSnpgMRtrLastCh      TimeStamp
    }

svcTlsPbbIgmpSnpgMRtrSvcIdIVpls OBJECT-TYPE
    SYNTAX          TmnxServId
    MAX-ACCESS      not-accessible
    STATUS          current
    DESCRIPTION     "The value of the object svcTlsPbbIgmpSnpgMRtrSvcIdIVpls 
                     specifies the Service identifier of the I-Component 
                     instance."
    ::= { svcTlsPbbIgmpSnpgMRtrEntry 1 }

svcTlsPbbIgmpSnpgMRtrSvcIdBVpls OBJECT-TYPE
    SYNTAX          TmnxServId
    MAX-ACCESS      not-accessible
    STATUS          current
    DESCRIPTION     "The value of the object svcTlsPbbIgmpSnpgMRtrSvcIdBVpls 
                     specifies the Service identifier of the B-Component 
                     instance."
    ::= { svcTlsPbbIgmpSnpgMRtrEntry 2 }

svcTlsPbbIgmpSnpgMRtrMacName OBJECT-TYPE
    SYNTAX          TNamedItem
    MAX-ACCESS      not-accessible
    STATUS          current
    DESCRIPTION     "The value of svcTlsPbbIgmpSnpgMRtrMacName specifies 
                     the Destination MAC-Address-Name in the Backbone VPLS 
                     to reach a specific IGMP Snooping MRouter.
                     
                     In the case of an I-Component instance that is multi-homed
                     on 2 physical nodes, an I-component instance, after
                     becoming active, uses this MAC address as the destination
                     MAC address to reach that IGMP Snooping MRouter.

                     This allows to maintain the communication with that 
                     MRouter while no IGMP Queries from that MRouter have been
                     snooped by this I-component instance."
    ::= { svcTlsPbbIgmpSnpgMRtrEntry 3 }

svcTlsPbbIgmpSnpgMRtrRowStatus OBJECT-TYPE
    SYNTAX          RowStatus
    MAX-ACCESS      read-create
    STATUS          current
    DESCRIPTION     "The value of svcTlsPbbIgmpSnpgMRtrRowStatus specifies 
                     the row status of this row. 
                     
                     The only values supported during a set operation are
                     'createAndGo' and 'destroy'."
    ::= { svcTlsPbbIgmpSnpgMRtrEntry 4 }

svcTlsPbbIgmpSnpgMRtrLastCh OBJECT-TYPE
    SYNTAX          TimeStamp
    MAX-ACCESS      read-only
    STATUS          current
    DESCRIPTION
                    "The value of svcTlsPbbIgmpSnpgMRtrLastCh indicates 
                     the sysUpTime at the time of the most recent 
                     management-initiated change to this table row."
    ::= { svcTlsPbbIgmpSnpgMRtrEntry 5 }

-- -------------------------
-- BGP multi-home L2 Route Table
-- -------------------------

svcL2MhRteTable       OBJECT-TYPE
    SYNTAX          SEQUENCE OF SvcL2MhRteEntry
    MAX-ACCESS      not-accessible
    STATUS          current
    DESCRIPTION     "svcL2MhRteTable contains multi-home entries for L2 routes."
    ::= { tmnxSvcObjs 83 }

svcL2MhRteEntry       OBJECT-TYPE
    SYNTAX          SvcL2MhRteEntry
    MAX-ACCESS      not-accessible
    STATUS          current
    DESCRIPTION     "A multi-home L2 route entry in the svcL2MhRteTable."
    INDEX           { svcId,
                      svcL2MhRteSiteId,
                      svcL2MhRteRouteDistinguisher,
                      svcL2MhRteNextHopType,
                      svcL2MhRteNextHop }
    ::= { svcL2MhRteTable 1}

SvcL2MhRteEntry ::= SEQUENCE {
    svcL2MhRteSiteId              TmnxSiteId,
    svcL2MhRteRouteDistinguisher  TmnxVPNRouteDistinguisher,
    svcL2MhRteNextHopType         InetAddressType,
    svcL2MhRteNextHop             InetAddress,
    svcL2MhRteState               INTEGER,
    svcL2MhRteDf                  TruthValue,
    svcL2MhRteVplsPreference      Integer32
}

svcL2MhRteSiteId   OBJECT-TYPE
    SYNTAX          TmnxSiteId
    MAX-ACCESS      not-accessible
    STATUS          current
    DESCRIPTION     "The value of svcL2MhRteSiteId is the site-id 
                     for this L2 route."
    ::= { svcL2MhRteEntry 1 }

svcL2MhRteRouteDistinguisher  OBJECT-TYPE
    SYNTAX          TmnxVPNRouteDistinguisher
    MAX-ACCESS      not-accessible
    STATUS          current
    DESCRIPTION     "The value of svcL2MhRteRouteDistinguisher is the high-order
                     6 bytes of the Virtual Switch Instance identifier (VSI-id)
                     of the remote VSI for this L2 route."
    ::= { svcL2MhRteEntry 2 }

svcL2MhRteNextHopType OBJECT-TYPE
    SYNTAX          InetAddressType
    MAX-ACCESS      not-accessible
    STATUS          current
    DESCRIPTION     "The value of svcL2MhRteNextHopType indicates the address
                     type of svcL2MhRteNextHop."
    ::= { svcL2MhRteEntry 3 }

svcL2MhRteNextHop     OBJECT-TYPE
    SYNTAX          InetAddress
    MAX-ACCESS      not-accessible
    STATUS          current
    DESCRIPTION     "The value of svcL2MhRteNextHop indicates the IP next hop
                     for this L2 route. This value is equivilant to the
                     IP address of the Far End of this L2 route."
    ::= { svcL2MhRteEntry 4 }

svcL2MhRteState     OBJECT-TYPE
    SYNTAX          INTEGER {
                        up   (1),
                        down (2)
                    }
    MAX-ACCESS      read-only
    STATUS          current
    DESCRIPTION     "The value of svcL2MhRteState indicates the state of this
                     multi-home L2 route entry."
    ::= { svcL2MhRteEntry 5 }

svcL2MhRteDf  OBJECT-TYPE
    SYNTAX          TruthValue
    MAX-ACCESS      read-only
    STATUS          current
    DESCRIPTION     "The value of svcL2MhRteDf indicates the value of DF bit
                     associated with this multi-home L2 route entry."
    ::= { svcL2MhRteEntry 6 }

svcL2MhRteVplsPreference  OBJECT-TYPE
    SYNTAX          Integer32
    MAX-ACCESS      read-only
    STATUS          current
    DESCRIPTION     "The value of svcL2MhRteVplsPreference indicates the VPLS
                     preference value associated with this multi-home L2
                     route entry."
    ::= { svcL2MhRteEntry 7 }

--
-- svcTmplTable
--

svcTmplTblLastChanged  OBJECT-TYPE
    SYNTAX          TimeStamp
    MAX-ACCESS      read-only
    STATUS          current
    DESCRIPTION
        "The value of svcTmplTblLastChanged indicates the sysUpTime
         at the time of the last modification of svcTmplTable.

         If no changes were made to the entry since the last re-initialization
         of the local network management subsystem, then this object contains a
         zero value."
    ::= { tmnxSvcObjs 85 }

svcTmplTable OBJECT-TYPE
    SYNTAX          SEQUENCE OF SvcTmplEntry
    MAX-ACCESS      not-accessible
    STATUS          current
    DESCRIPTION     "A table that contains basic service template information."
    ::= { tmnxSvcObjs 86 }

svcTmplEntry OBJECT-TYPE
    SYNTAX          SvcTmplEntry
    MAX-ACCESS      not-accessible
    STATUS          current
    DESCRIPTION     "Basic information about a specific service template."
    INDEX           { svcTmplName }
    ::= { svcTmplTable 1 }

SvcTmplEntry ::=
    SEQUENCE {
        svcTmplName               TNamedItem,
        svcTmplRowStatus          RowStatus,
        svcTmplLastChanged        TimeStamp,
        svcTmplSvcCount           Unsigned32,
        svcTmplType               ServType,
        svcTmplMtu                INTEGER,
        svcTmplCustId             TmnxCustId
    }       

svcTmplName OBJECT-TYPE
    SYNTAX          TNamedItem
    MAX-ACCESS      not-accessible
    STATUS          current
    DESCRIPTION
        "The value of the svcTmplName specifies the
        Service template name. This name should unique within
        the service template domain."
    ::= { svcTmplEntry 1 }

svcTmplRowStatus OBJECT-TYPE
    SYNTAX          RowStatus
    MAX-ACCESS      read-create
    STATUS          current
    DESCRIPTION
        "This value of the object  svcTmplRowStatus specifies the
         status of this row."
    ::= { svcTmplEntry 2 }

svcTmplLastChanged OBJECT-TYPE
    SYNTAX       TimeStamp
    MAX-ACCESS   read-only
    STATUS       current
    DESCRIPTION  
        "The value of svcTmplLastChanged indicates the timestamp of last
        change to this row in svcTmplTable."
    ::= { svcTmplEntry 3 }  
    
svcTmplSvcCount OBJECT-TYPE
    SYNTAX       Unsigned32
    MAX-ACCESS   read-only
    STATUS       current
    DESCRIPTION  
        "The value of svcTmplSvcCount indicates the number of instantiated
        services created using this template."
    ::= { svcTmplEntry 4 }  
    
svcTmplType OBJECT-TYPE
    SYNTAX          ServType
    MAX-ACCESS      read-create
    STATUS          current
    DESCRIPTION
        "The value of the object svcTmplType specifies the service
         type: e.g. epipe, tls, etc. The value of this object
         must be specified when the row is created and cannot be
         changed while the row status is 'active'.
         
         An 'inconsistentValue' error is returned if an attempt is made to 
         change the value of this object after row creation."
    ::= { svcTmplEntry 5 }

svcTmplMtu OBJECT-TYPE
    SYNTAX          INTEGER (0..9194)
    MAX-ACCESS      read-create
    STATUS          current
    DESCRIPTION
        "The value of the object svcTmplMtu specifies the largest frame
         size (in octets) that this service can handle.
         
         The default value of this object depends on the service type:
         1514 octets for epipe and tls, 1508 for apipe
         and fpipe, and 1500 octets for vprn, ipipe and ies, 1514
         octets for cpipe."
    ::= { svcTmplEntry 6 }

svcTmplCustId OBJECT-TYPE
    SYNTAX          TmnxCustId
    MAX-ACCESS      read-create
    STATUS          current
    DESCRIPTION
        "The value of the object svcTmplCustId specifies the
        customer identifier of the service."
    DEFVAL { 0 }
    ::= { svcTmplEntry 7 }

--
-- svcTmplTlsTable
--

svcTmplTlsTblLastChanged  OBJECT-TYPE
    SYNTAX          TimeStamp
    MAX-ACCESS      read-only
    STATUS          current
    DESCRIPTION
        "The value of svcTmplTlsTblLastChanged indicates the sysUpTime
         at the time of the last modification of svcTmplTlsTable.

         If no changes were made to the entry since the last re-initialization
         of the local network management subsystem, then this object contains a
         zero value."
    ::= { tmnxSvcObjs 94 }

svcTmplTlsTable OBJECT-TYPE
    SYNTAX          SEQUENCE OF SvcTmplTlsEntry
    MAX-ACCESS      not-accessible
    STATUS          current
    DESCRIPTION
        "A table that contains VPLS service template information."
    ::= { tmnxSvcObjs 95 }

svcTmplTlsEntry OBJECT-TYPE
    SYNTAX          SvcTmplTlsEntry
    MAX-ACCESS      not-accessible
    STATUS          current
    DESCRIPTION
        "This table contains basic information about a specific VPLS
        service template. An entry in this table is created when an entry
        is created in the svcTmplTable with svcTmplType set to 'tls'.
        Entry is deleted when corrosponding entry is deleted in the
        svcTmplTable."
    INDEX           { svcTmplName }
    ::= { svcTmplTlsTable 1 }

SvcTmplTlsEntry ::=
    SEQUENCE {
        svcTmplTlsLastChanged                   TimeStamp,
        svcTmplTlsMacLearning                   TmnxEnabledDisabled,
        svcTmplTlsDiscardUnknownDest            TmnxEnabledDisabled,
        svcTmplTlsFdbTableSize                  Integer32,
        svcTmplTlsFdbLocalAgeTime               Integer32,
        svcTmplTlsFdbRemoteAgeTime              Integer32,
        svcTmplTlsStpAdminStatus                TmnxEnabledDisabled,
        svcTmplTlsStpPriority                   Integer32,
        svcTmplTlsStpBridgeMaxAge               Integer32,
        svcTmplTlsStpBridgeHelloTime            Integer32,
        svcTmplTlsStpBridgeForwardDelay         Integer32,
        svcTmplTlsMacAgeing                     TmnxEnabledDisabled,
        svcTmplTlsFdbTableFullHighWMark         Integer32,
        svcTmplTlsFdbTableFullLowWMark          Integer32,
        svcTmplTlsStpVersion                    INTEGER,
        svcTmplTlsStpHoldCount                  Integer32,
        svcTmplTlsPerSvcHashing                 TmnxEnabledDisabled,
        svcTmplTlsTempFloodTime                 Integer32,
        svcTmplTlsMacMoveMaxRate                Unsigned32,
        svcTmplTlsMacMoveRetryTimeout           Unsigned32,
        svcTmplTlsMacMoveAdminStatus            TmnxEnabledDisabled,
        svcTmplTlsPriPortsCumFactor             Unsigned32,
        svcTmplTlsSecPortsCumFactor             Unsigned32,
        svcTmplTlsMacMoveNumRetries             Unsigned32,
        svcTmplTlsSpiLoadBalancing              TmnxEnabledDisabled,
        svcTmplTlsTeidLoadBalancing             TmnxEnabledDisabled
     }

svcTmplTlsLastChanged OBJECT-TYPE
    SYNTAX          TimeStamp
    MAX-ACCESS      read-only
    STATUS          current
    DESCRIPTION     "The value of svcTmplTlsLastChanged indicates the
                     timestamp of last change to this row in svcTmplTlsTable."
    ::= { svcTmplTlsEntry 1 }  

svcTmplTlsMacLearning OBJECT-TYPE
    SYNTAX          TmnxEnabledDisabled
    MAX-ACCESS      read-write
    STATUS          current
    DESCRIPTION     "The value of the object svcTmplTlsMacLearning specifies
                     whether the MAC learning process is enabled in this TLS."
    DEFVAL          { enabled }
    ::= { svcTmplTlsEntry 2 }

svcTmplTlsDiscardUnknownDest OBJECT-TYPE
    SYNTAX          TmnxEnabledDisabled
    MAX-ACCESS      read-write
    STATUS          current
    DESCRIPTION     "The value of the object svcTmplTlsDiscardUnknownDest
                     specifies whether frames received with an unknown
                     destination MAC are discarded in this TLS."
    DEFVAL          { disabled }
    ::= { svcTmplTlsEntry 3 }

svcTmplTlsFdbTableSize OBJECT-TYPE
    SYNTAX          Integer32 (1..511999)
    MAX-ACCESS      read-write
    STATUS          current
    DESCRIPTION     "The value of svcTmplTlsFdbTableSize specifies the
                     maximum number of learned and static entries allowed in
                     the FDB of this service."
    DEFVAL          { 250 }
    ::= { svcTmplTlsEntry 4 }

svcTmplTlsFdbLocalAgeTime OBJECT-TYPE
    SYNTAX          Integer32 (60..86400)
    UNITS           "seconds"
    MAX-ACCESS      read-write
    STATUS          current
    DESCRIPTION     "The value of the object svcTmplTlsFdbLocalAgeTime specifies
                     the number of seconds used to age out TLS FDB entries
                     learned on local SAPs."
    DEFVAL          { 300 }
    ::= { svcTmplTlsEntry 5 }

svcTmplTlsFdbRemoteAgeTime OBJECT-TYPE
    SYNTAX          Integer32 (60..86400)
    UNITS           "seconds"
    MAX-ACCESS      read-write
    STATUS          current
    DESCRIPTION     "The value of svcTmplTlsFdbRemoteAgeTime specifies
                     the number of seconds used to age out TLS FDB entries
                     learned on an SDP. These entries correspond to MAC
                     addresses learned on remote SAPs."
    DEFVAL          { 900 }
    ::= { svcTmplTlsEntry 6 }

svcTmplTlsStpAdminStatus OBJECT-TYPE
    SYNTAX          TmnxEnabledDisabled
    MAX-ACCESS      read-write
    STATUS          current
    DESCRIPTION     "The value of svcTmplTlsStpAdminStatus specifies the
                     administrative state of the Spanning Tree Protocol
                     instance associated with this service."
    DEFVAL          { disabled }
    ::= { svcTmplTlsEntry 7 }

svcTmplTlsStpPriority OBJECT-TYPE
    SYNTAX          Integer32 (0..65535)
    MAX-ACCESS      read-write
    STATUS          current
    DESCRIPTION     "The value of  svcTmplTlsStpPriority specifies
                     the priority of the Spanning Tree Protocol instance
                     associated with this service.
                     It is used as the highest 4 bits of the Bridge ID
                     included in the Configuration BPDU's generated by
                     this bridge.
                     The svcTmplTlsStpPriority can only take-on values which
                     multiples of 4096 (4k). If a value is specified which
                     is not a multiple of 4K, then this value will be
                     replaced by the closest multiple of 4K which is lower
                     then the value entered."
    DEFVAL          { 32768 }
    ::= { svcTmplTlsEntry 8 }

svcTmplTlsStpBridgeMaxAge OBJECT-TYPE
    SYNTAX          Integer32 (6..40)
    UNITS           "seconds"
    MAX-ACCESS      read-write
    STATUS          current
    DESCRIPTION     "The value of svcTmplTlsStpBridgeMaxAge specifies
                     the value that all bridges should use for 'MaxAge' when
                     this bridge is acting as the root bridge."
    ::= { svcTmplTlsEntry 9 }

svcTmplTlsStpBridgeHelloTime OBJECT-TYPE
    SYNTAX          Integer32 (1..10)
    UNITS           "seconds"
    MAX-ACCESS      read-write
    STATUS          current
    DESCRIPTION     "The value of svcTmplTlsStpBridgeHelloTime specifies
                     the value that all bridges should use for 'HelloTime' when
                     this bridge is acting as the root bridge."
    ::= { svcTmplTlsEntry 10 }

svcTmplTlsStpBridgeForwardDelay OBJECT-TYPE
    SYNTAX          Integer32 (4..30)
    UNITS           "seconds"
    MAX-ACCESS      read-write
    STATUS          current
    DESCRIPTION     "The value of svcTmplTlsStpBridgeForwardDelay
                     specifies the value that all bridges should use for
                     'ForwardDelay' when this bridge is acting as the root
                     bridge."
    ::= { svcTmplTlsEntry 11 }

svcTmplTlsMacAgeing OBJECT-TYPE
    SYNTAX          TmnxEnabledDisabled
    MAX-ACCESS      read-write
    STATUS          current
    DESCRIPTION     "The value of svcTmplTlsMacAgeing specifies whether
                     the MAC aging process is enabled in this TLS."
    DEFVAL          { enabled }
    ::= { svcTmplTlsEntry 12 }

svcTmplTlsFdbTableFullHighWMark OBJECT-TYPE
    SYNTAX          Integer32 (0..100)
    MAX-ACCESS      read-write
    STATUS          current
    DESCRIPTION     "The value of svcTmplTlsFdbTableFullHighWMark
                     specifies the utilization of the FDB table of this TLS
                     service at which a table full alarm will be raised
                     by the agent."
    DEFVAL          { 95 }
    ::= { svcTmplTlsEntry 13 }

svcTmplTlsFdbTableFullLowWMark OBJECT-TYPE
    SYNTAX          Integer32 (0..100)
    MAX-ACCESS      read-write
    STATUS          current
    DESCRIPTION     "The value of svcTmplTlsFdbTableFullLowWMark
                     specifies the utilization of the FDB table of this TLS
                     service at which a table full alarm will be cleared
                     by the agent."
    DEFVAL          { 90 }
    ::= { svcTmplTlsEntry 14 }

svcTmplTlsStpVersion OBJECT-TYPE
    SYNTAX          INTEGER {
                        rstp         (2),
                        compDot1w    (3),
                        dot1w        (4),
                        mstp         (5),
                        pmstp        (6)
                    }
    MAX-ACCESS      read-write
    STATUS          current
    DESCRIPTION     "The value of svcTmplTlsStpVersion specifies the
                     version of Spanning Tree Protocol the bridge is currently
                     running.

                     The value 'rstp' corresponds to  the Rapid Spanning
                     Tree Protocol specified in IEEE 802.1D/D4-2003.

                     The value 'compDot1w' corresponds to the mode where the
                     Rapid Spanning Tree is backward compatible with IEEE
                     802.1w.

                     The value 'dot1w' corresponds to  the Rapid Spanning
                     Tree Protocol fully conformant to IEEE 802.1w.

                     The value 'mstp' corresponds to the Multiple Spanning
                     Tree Protocol specified in IEEE 802.1Q-REV/D3.0-04/2005.
                     
                     The value 'pmstp' corresponds to Provider MSTP protocol
                     compliant with IEEE-802.1ad-2005.

                     New values may be defined as future versions of the
                     protocol become available."
    DEFVAL          { rstp }
    ::= { svcTmplTlsEntry 15 }

svcTmplTlsStpHoldCount OBJECT-TYPE
    SYNTAX          Integer32 (1..20)
    MAX-ACCESS      read-write
    STATUS          current
    DESCRIPTION     "The value of svcTmplTlsStpHoldCount specifies the
                     maximum number of BPDUs that are transmitted in any
                     'HelloTime' interval.
                     The value used by the bridge to limit the maximum
                     transmission rate of BPDUs."
    REFERENCE
                    "IEEE 802.1w clause 17.16.6"
    DEFVAL          { 6 }
    ::= { svcTmplTlsEntry 16 }

svcTmplTlsPerSvcHashing  OBJECT-TYPE
    SYNTAX          TmnxEnabledDisabled
    MAX-ACCESS      read-write
    STATUS          current
    DESCRIPTION     "The value of svcTmplTlsPerSvcHashing specifies service-level
                     hashing for Ethernet services.

                     An 'inconsistentValue' error is returned if this object is
                     set to non-default value when svcVplsType for the service
                     is set to 'bVpls'."
    DEFVAL { disabled }
    ::= { svcTmplTlsEntry 17 }

svcTmplTlsTempFloodTime OBJECT-TYPE
    SYNTAX          Integer32 (-1|3..600)
    UNITS           "seconds"
    MAX-ACCESS      read-write
    STATUS          current
    DESCRIPTION     "The value of svcTmplTlsTempFloodTime specifies
                     duration of time traffic will be flooded on a TLS status
                     change in this TLS.

                     Value of '-1' disables this flooding behavior."
    DEFVAL          { -1 }
    ::= { svcTmplTlsEntry 18 }

svcTmplTlsMacMoveMaxRate OBJECT-TYPE
    SYNTAX          Unsigned32 (1..10)
    UNITS           "per-second"
    MAX-ACCESS      read-write
    STATUS          current
    DESCRIPTION     "The value of svcTmplTlsMacMoveMaxRate specifies the
                     maximum rate at which MAC's can be re-learned in this TLS
                     service, before the SAP where the moving MAC was last seen
                     is automatically disabled in order to protect the system
                     against undetected loops or duplicate MAC's.
                     The rate is computed as the maximum number of re-learns
                     allowed in a 5 second interval: e.g. the default rate
                     of 2 re-learns per second corresponds to 10 re-learns
                     in a 5 second period."
    DEFVAL          { 2 }
    ::= { svcTmplTlsEntry 19 }

svcTmplTlsMacMoveRetryTimeout OBJECT-TYPE
    SYNTAX          Unsigned32 (0..600)
    UNITS           "seconds"
    MAX-ACCESS      read-write
    STATUS          current
    DESCRIPTION     "The value of  svcTmplTlsMacMoveRetryTimeout
                     specifies the time in seconds to wait before a SAP that
                     has been disabled after exceeding the maximum re-learn
                     rate is re-enabled.

                     A value of zero indicates that the SAP will not be
                     automatically re-enabled after being disabled. If after
                     the SAP is re-enabled it is disabled again, the effective
                     retry timeout is doubled in order to avoid thrashing.
                     
                     An inconsistentValue error is returned if the value of this
                     object is set to less than fie times the value of 
                     svcTmplTlsSecPortsCumFactor."
    DEFVAL { 10 }
    ::= { svcTmplTlsEntry 20 }

svcTmplTlsMacMoveAdminStatus OBJECT-TYPE
    SYNTAX          TmnxEnabledDisabled
    MAX-ACCESS      read-write
    STATUS          current
    DESCRIPTION     "The value of svcTmplTlsMacMoveAdminStatus
                     specifies the administrative state of the
                     MAC movement feature associated with this service."
    DEFVAL          { disabled }
    ::= { svcTmplTlsEntry 21 }

svcTmplTlsPriPortsCumFactor OBJECT-TYPE
    SYNTAX          Unsigned32 (3..10)
    MAX-ACCESS      read-write
    STATUS          current
    DESCRIPTION     "The value of svcTmplTlsPriPortsCumFactor
                     specifies a factor for the primary ports defining how
                     many MAC-relearn periods should be used to measure the
                     MAC-relearn rate, svcTmplTlsMacMoveMaxRate. This rate must
                     be exceeded during consecutive periods before the
                     corresponding ports (SAP and/or spoke-SDP) are blocked by
                     the MAC-move feature.

                     An inconsistentValue error is returned if an attempt is
                     made to set the value of svcTmplTlsPriPortsCumFactor to
                     a value lower than or equal to
                     svcTmplTlsSecPortsCumFactor."
    DEFVAL          { 3 }
    ::= { svcTmplTlsEntry 22 }

svcTmplTlsSecPortsCumFactor OBJECT-TYPE
    SYNTAX          Unsigned32 (2..9)
    MAX-ACCESS      read-write
    STATUS          current
    DESCRIPTION     "The value of svcTmplTlsSecPortsCumFactor
                     specifies a factor for the secondary ports defining how
                     many MAC-relearn periods should be used to measure the
                     MAC-relearn rate, svcTmplTlsMacMoveMaxRate. This rate must
                     be exceeded during consecutive periods before the
                     corresponding ports (SAP and/or spoke-SDP) are blocked by
                     the MAC-move feature.

                     An inconsistentValue error is returned if an attempt is
                     made to set the value of svcTmplTlsSecPortsCumFactor to
                     a value greater than or equal to
                     svcTmplTlsPriPortsCumFactor."
    DEFVAL          { 2 }
    ::= { svcTmplTlsEntry 23 }

svcTmplTlsMacMoveNumRetries OBJECT-TYPE
    SYNTAX          Unsigned32 (0..255)
    MAX-ACCESS      read-write
    STATUS          current
    DESCRIPTION     "The value of  svcTmplTlsMacMoveNumRetries
                     specifies the number of times retries are performed for
                     reenabling the SAP/SDP.

                     A value of zero indicates unlimited number of retries."
                     
    DEFVAL { 3 }
    ::= { svcTmplTlsEntry 24 }

svcTmplTlsSpiLoadBalancing OBJECT-TYPE
    SYNTAX          TmnxEnabledDisabled
    MAX-ACCESS      read-write
    STATUS          current
    DESCRIPTION
        "The value of svcTmplTlsSpiLoadBalancing specifies whether SPI use in 
         hashing is enabled on this service template."
    DEFVAL  { disabled }
    ::= { svcTmplTlsEntry 25 }

svcTmplTlsTeidLoadBalancing OBJECT-TYPE
    SYNTAX          TmnxEnabledDisabled
    MAX-ACCESS      read-write
    STATUS          current
    DESCRIPTION
        "The value of svcTmplTlsTeidLoadBalancing specifies whether
         TEID load balancing is enabled for this service template."
    DEFVAL  { disabled }
    ::= { svcTmplTlsEntry 26 }

--
-- svcTlsGroupTable
--
svcTlsGroupTblLastChanged  OBJECT-TYPE
    SYNTAX          TimeStamp
    MAX-ACCESS      read-only
    STATUS          current
    DESCRIPTION
        "The value of svcTlsGroupTblLastChanged indicates the sysUpTime
         at the time of the last modification of svcTlsGroupTable.

         If no changes were made to the entry since the last re-initialization
         of the local network management subsystem, then this object contains a
         zero value."
    ::= { tmnxSvcObjs 87 }

svcTlsGroupTable OBJECT-TYPE
    SYNTAX          SEQUENCE OF SvcTlsGroupEntry
    MAX-ACCESS      not-accessible
    STATUS          current
    DESCRIPTION     "A table that contains TLS service range information for 
                     the service."
    ::= { tmnxSvcObjs 88 }

svcTlsGroupEntry OBJECT-TYPE
    SYNTAX          SvcTlsGroupEntry
    MAX-ACCESS      not-accessible
    STATUS          current
    DESCRIPTION     "TLS service range specific information for this service."
    INDEX           { svcId, svcTlsGroupId }
    ::= { svcTlsGroupTable 1 }

SvcTlsGroupEntry ::=
    SEQUENCE {
        svcTlsGroupId                 TmnxTlsGroupId,
        svcTlsGroupRowStatus          RowStatus,
        svcTlsGroupLastChanged        TimeStamp,
        svcTlsGroupAdminStatus        ServiceAdminStatus,
        svcTlsGroupStart              TmnxServId,
        svcTlsGroupEnd                TmnxServId,
        svcTlsGroupStartVlanTag       QTagOrZero,
        svcTlsGroupSvcTmplName        TNamedItemOrEmpty,
        svcTlsGroupSapTmplName        TNamedItemOrEmpty,
        svcTlsGroupMvrpControl        TruthValue,
        svcTlsGroupOperStatus         INTEGER,
        svcTlsGroupLastError          DisplayString
    }       

svcTlsGroupId OBJECT-TYPE
    SYNTAX          TmnxTlsGroupId
    MAX-ACCESS      not-accessible
    STATUS          current
    DESCRIPTION
        "The value of the object svcTlsGroupId specifies the
         Service range identifier under this service."
    ::= { svcTlsGroupEntry 1 }

svcTlsGroupRowStatus OBJECT-TYPE
    SYNTAX          RowStatus
    MAX-ACCESS      read-create
    STATUS          current
    DESCRIPTION
        "This value of the object  svcTlsGroupRowStatus specifies the
         status of this row."
    ::= { svcTlsGroupEntry 2 }

svcTlsGroupLastChanged OBJECT-TYPE
    SYNTAX       TimeStamp
    MAX-ACCESS   read-only
    STATUS       current
    DESCRIPTION  
        "The value of svcTlsGroupLastChanged indicates the timestamp of last
        change to this row in svcTlsGroupTable."
    ::= { svcTlsGroupEntry 3 }  
    
svcTlsGroupAdminStatus OBJECT-TYPE
    SYNTAX          ServiceAdminStatus
    MAX-ACCESS      read-create
    STATUS          current
    DESCRIPTION     
        "The value of svcTlsGroupAdminStatus specifies the desired state of
        this service-range."
    DEFVAL          { down }
    ::= { svcTlsGroupEntry 4 }

svcTlsGroupStart OBJECT-TYPE
    SYNTAX          TmnxServId
    MAX-ACCESS      read-create
    STATUS          current
    DESCRIPTION
        "The value of the object svcTlsGroupStart specifies the start of the
         service identifier range.

         An 'inconsistentValue' error is returned when the value of
         svcTlsGroupStart is set to larger than the value of svcTlsGroupEnd.

         An 'inconsistentValue' error is also returned when the value of
         svcTlsGroupStart is set to default and svcTlsGroupStartVlanTag is set
         to non-default value.
         
         An 'inconsistentValue' error is also returned when the value of
         svcTlsGroupEnd is set to non-default value and svcTlsGroupStart is
         set to the default value."
    DEFVAL { 0 }
    ::= { svcTlsGroupEntry 5 }

svcTlsGroupEnd OBJECT-TYPE
    SYNTAX          TmnxServId
    MAX-ACCESS      read-create
    STATUS          current
    DESCRIPTION
        "The value of the object svcTlsGroupEnd specifies the end of the
         service identifier range.

         An 'inconsistentValue' error is returned when the value of
         svcTlsGroupStart is set to larger than the value of svcTlsGroupEnd.

         An 'inconsistentValue' error is also returned when the value of
         svcTlsGroupEnd is set to non-default value and svcTlsGroupStart is
         set to the default value."
    DEFVAL { 0 }
    ::= { svcTlsGroupEntry 6 }

svcTlsGroupStartVlanTag OBJECT-TYPE
    SYNTAX          QTagOrZero
    MAX-ACCESS      read-create
    STATUS          current
    DESCRIPTION
        "The value of the object svcTlsGroupStartVlanTag specifies the start
         of the VLAN tag range.

         An 'inconsistentValue' error is also returned when the value of
         svcTlsGroupStart is set to default and svcTlsGroupStartVlanTag is set
         to non-default value."
    DEFVAL { 0 }
    ::= { svcTlsGroupEntry 7 }

svcTlsGroupSvcTmplName OBJECT-TYPE
    SYNTAX          TNamedItemOrEmpty
    MAX-ACCESS      read-create
    STATUS          current
    DESCRIPTION
        "The value of the object svcTlsGroupSvcTmplName specifies the
         service template name associated with this service-range."
    DEFVAL { ''H }
    ::= { svcTlsGroupEntry 8 }

svcTlsGroupSapTmplName OBJECT-TYPE
    SYNTAX          TNamedItemOrEmpty
    MAX-ACCESS      read-create
    STATUS          current
    DESCRIPTION
        "The value of the object svcTlsGroupSapTmplName specifies the
         SAP template name associated with this service-range."
    DEFVAL { ''H }
    ::= { svcTlsGroupEntry 9 }

svcTlsGroupMvrpControl OBJECT-TYPE
    SYNTAX          TruthValue
    MAX-ACCESS      read-create
    STATUS          current
    DESCRIPTION
        "The value of the object svcTlsGroupMvrpControl specifies whether
         MVRP control is enabled on this service-range."
    DEFVAL { false }
    ::= { svcTlsGroupEntry 10 }

svcTlsGroupOperStatus OBJECT-TYPE
    SYNTAX          INTEGER {
                        up   (1),
                        down (2),
                        inProgress (3)
                    }
    MAX-ACCESS      read-only
    STATUS          current
    DESCRIPTION
        "The value of svcTlsGroupOperStatus indicates service instantiation
        status of this service group.

        A value of 'down' indicates:
           -- svcTmplGroupAdminStatus is set to 'disabled' or
           -- services for this group are being instantiated or
           -- service instantiation failed for this group. svcTlsGroupLastError
              provide information on the error encountered.

        A value of 'up' indicates that all services for this group have been
        successfully instantiated.
        
        A value of 'inProgress' indicates that this group is in process of
        transitioning to another state."
    ::= { svcTlsGroupEntry 11 }

svcTlsGroupLastError OBJECT-TYPE
    SYNTAX          DisplayString
    MAX-ACCESS      read-only
    STATUS          current
    DESCRIPTION
        "The value of the object svcTlsGroupLastError indicates the last error
        encountered trying to instantiate services for this group."
    ::= { svcTlsGroupEntry 12 }

-- Service template users table

svcTmplUserTable OBJECT-TYPE
    SYNTAX          SEQUENCE OF SvcTmplUserEntry
    MAX-ACCESS      not-accessible
    STATUS          current
    DESCRIPTION
        "A table that contains services which are created using Service
        templates."
    ::= { tmnxSvcObjs 96 }

svcTmplUserEntry OBJECT-TYPE
    SYNTAX          SvcTmplUserEntry
    MAX-ACCESS      not-accessible
    STATUS          current
    DESCRIPTION
        "This table provides information about services created using a
        service template.

        Entries are created and deleted by the system."
    INDEX    { svcTmplName, svcId }
    ::= { svcTmplUserTable 1 }

SvcTmplUserEntry ::=
    SEQUENCE {
        svcTmplUserCreationOrigin    INTEGER,
        svcTmplUserCreatorSvcId             TmnxServId
    }

svcTmplUserCreationOrigin OBJECT-TYPE
    SYNTAX          INTEGER {
                         mVpls(1)
                         }
    MAX-ACCESS      read-only
    STATUS          current
    DESCRIPTION
        "The value svcTmplUserCreationOrigin indicates how the service was
        created using this specific service template."
    ::= { svcTmplUserEntry 1 }

svcTmplUserCreatorSvcId OBJECT-TYPE
    SYNTAX          TmnxServId
    MAX-ACCESS      read-only
    STATUS          current
    DESCRIPTION
        "The value svcTmplUserCreatorSvcId indicates the service identifier
        which created this particular service using this template.

        A value of zero indicates that the service is not created by another
        service."
    ::= { svcTmplUserEntry 2 }


-- ------------------------------------
-- TLS Service Extension Table
-- ------------------------------------
svcTlsExtTable OBJECT-TYPE
    SYNTAX          SEQUENCE OF SvcTlsExtEntry
    MAX-ACCESS      not-accessible
    STATUS          current
    DESCRIPTION     "A table that extends svcTlsInfoTable."
    ::= { tmnxSvcObjs 97 }

svcTlsExtEntry OBJECT-TYPE
    SYNTAX          SvcTlsExtEntry
    MAX-ACCESS      not-accessible
    STATUS          current
    DESCRIPTION     "svcTlsExtEntry extends svcTlsInfoEntry."
    AUGMENTS        { svcTlsInfoEntry }
    ::= { svcTlsExtTable 1 }

SvcTlsExtEntry ::=
    SEQUENCE {
        svcTlsExtMvrpMaxAttributes              Unsigned32,
        svcTlsExtMvrpRegAttrCnt                 Unsigned32,
        svcTlsExtMvrpDeclaredAttrCnt            Unsigned32,
        svcTlsExtMvrpFailedRegCnt               Unsigned32,
        svcTlsExtMvrpAttrTblHighWM              Integer32,
        svcTlsExtMvrpAttrTblLowWM               Integer32,
        svcTlsExtMvrpHoldTime                   Unsigned32,
        svcTlsExtMvrpAdminStatus                TmnxEnabledDisabled,
        svcTlsExtMvrpOperStatus                 INTEGER,
        svcTlsExtMmrpAdminStatus                TmnxEnabledDisabled,
        svcTlsExtMmrpOperStatus                 INTEGER,
        svcTlsExtMmrpRegAttrCnt                 Unsigned32,
        svcTlsExtMmrpDeclaredAttrCnt            Unsigned32,
        svcTlsExtMmrpFailedRegCnt               Unsigned32,
        svcTlsExtMvrpAttributeCount             Unsigned32,
        svcTlsExtMmrpEndStationOnly             TruthValue,
        svcTlsExtMacReNotifInterval             Unsigned32,
        svcTlsExtSpbmCtrlVpls                   TmnxServId,
        svcTlsExtSpbmFid                        TmnxSpbFidOrZero,
        svcTlsExtSpiLoadBalancing               TmnxEnabledDisabled,
        svcTlsExtTeidLoadBalancing              TmnxEnabledDisabled
     }

svcTlsExtMvrpMaxAttributes OBJECT-TYPE
    SYNTAX          Unsigned32 (1..4095)
    MAX-ACCESS      read-write
    STATUS          current
    DESCRIPTION
        "The value of the object svcTlsExtMvrpMaxAttributes indicates
        maximum number of MVRP attributes supported in this TLS.

        An 'inconsitentValue' error is returned if this object is set to
        non-default value when svcMgmtVpls of the service is not set to 'true'."
    DEFVAL { 4095 }
    ::= { svcTlsExtEntry 1 }

svcTlsExtMvrpRegAttrCnt OBJECT-TYPE
    SYNTAX          Unsigned32
    MAX-ACCESS      read-only
    STATUS          current
    DESCRIPTION     
        "The value of the object svcTlsExtMvrpRegAttrCnt indicates
        the number of MVRP attributes currently associated to the
        TLS by being registered."
    ::= { svcTlsExtEntry 2 }

svcTlsExtMvrpDeclaredAttrCnt OBJECT-TYPE
    SYNTAX          Unsigned32
    MAX-ACCESS      read-only
    STATUS          current
    DESCRIPTION     
        "The value of the object svcTlsExtMvrpDeclaredAttrCnt indicates
        the number of MVRP attributes currently associated to the
        TLS by being declared."
    ::= { svcTlsExtEntry 3 }

svcTlsExtMvrpFailedRegCnt OBJECT-TYPE
    SYNTAX          Unsigned32
    MAX-ACCESS      read-only
    STATUS          current
    DESCRIPTION     
        "The value of the object svcTlsExtMvrpFailedRegCnt
         indicates number of failed MVRP attribute registrations in
         this TLS."
    ::= { svcTlsExtEntry 4 }

svcTlsExtMvrpAttrTblHighWM OBJECT-TYPE
    SYNTAX          Integer32 (0..100)
    MAX-ACCESS      read-write
    STATUS          current
    DESCRIPTION     
        "The value of the object svcTlsExtMvrpAttrTblHighWM
        specifies the utilization of the MVRP attribute table of
        this TLS service at which a table full alarm will be raised
        by the agent.

        An 'inconsitentValue' error is returned if this object is set to
        non-default value when svcMgmtVpls of the service is not set to 'true'."
    DEFVAL          { 95 }
    ::= { svcTlsExtEntry 5 }

svcTlsExtMvrpAttrTblLowWM OBJECT-TYPE
    SYNTAX          Integer32 (0..100)
    MAX-ACCESS      read-write
    STATUS          current
    DESCRIPTION     
        "The value of the object svcTlsExtMvrpAttrTblLowWM
        specifies utilization of the MVRP attribute table of this
        TLS service at which a table full alarm will be cleared by
        the agent.

        An 'inconsitentValue' error is returned if this object is set to
        non-default value when svcMgmtVpls of the service is not set to 'true'."
    DEFVAL          { 90 }
    ::= { svcTlsExtEntry 6 }

svcTlsExtMvrpHoldTime OBJECT-TYPE
    SYNTAX          Unsigned32 (0|1..30)
    UNITS           "minutes"
    MAX-ACCESS      read-write
    STATUS          current
    DESCRIPTION     
        "The value of the object svcTlsExtMvrpHoldTime specifies
        the amount of time in minutes in reporting to MVRP
        that the last provisioned SAP in VPLS is down.

        A value of '0' disables tracking of the operational status for the
        last active SAP in the VPLS.

        An 'inconsitentValue' error is returned if this object is set to
        non-default value when svcMgmtVpls of the service is not set to 'true'."
    DEFVAL          { 0 }
    ::= { svcTlsExtEntry 7 }

svcTlsExtMvrpAdminStatus OBJECT-TYPE
    SYNTAX          TmnxEnabledDisabled
    MAX-ACCESS      read-write
    STATUS          current
    DESCRIPTION     
        "The value of the object svcTlsExtMvrpAdminStatus specifies
        whether the Multiple VLAN Registration Protocol (MVRP) is
        enabled in this TLS.

        An 'inconsitentValue' error is returned if this object is set to
        non-default value when svcMgmtVpls of the service is not set to 'true'."
    DEFVAL          { disabled }
    ::= { svcTlsExtEntry 8 }

svcTlsExtMvrpOperStatus OBJECT-TYPE
    SYNTAX          INTEGER {
                        up (1),
                        down (2)
                    }
    MAX-ACCESS      read-only
    STATUS          current
    DESCRIPTION     
        "The value of the object svcTlsExtMvrpOperStatus indicates
        the operational status of Multiple VLAN Registration Protocol (MVRP)
        in this TLS."
    ::= { svcTlsExtEntry 9 }

svcTlsExtMmrpAdminStatus OBJECT-TYPE
    SYNTAX          TmnxEnabledDisabled
    MAX-ACCESS      read-write
    STATUS          current
    DESCRIPTION     
        "The value of the object svcTlsExtMmrpAdminStatus specifies
        whether the Multiple MAC Registration Protocol (MMRP) is
        enabled in this TLS.

        Default value of this object is set to 'enabled' when
        svcVplsType of this service is set to 'bVpls' otherwise
        this is set to 'disabled'."
    ::= { svcTlsExtEntry 10 }

svcTlsExtMmrpOperStatus OBJECT-TYPE
    SYNTAX          INTEGER {
                        up (1),
                        down (2)
                    }
    MAX-ACCESS      read-only
    STATUS          current
    DESCRIPTION     
        "The value of the object svcTlsExtMmrpOperStatus indicates
        the operational status of Multiple MAC Registration Protocol (MMRP)
        in this TLS."
    ::= { svcTlsExtEntry 11 }

svcTlsExtMmrpRegAttrCnt OBJECT-TYPE
    SYNTAX          Unsigned32
    MAX-ACCESS      read-only
    STATUS          current
    DESCRIPTION     
        "The value of the object svcTlsExtMmrpRegAttrCnt indicates
        the number of MMRP attributes currently associated to the
        TLS by being registered."
    ::= { svcTlsExtEntry 12 }

svcTlsExtMmrpDeclaredAttrCnt OBJECT-TYPE
    SYNTAX          Unsigned32
    MAX-ACCESS      read-only
    STATUS          current
    DESCRIPTION     
        "The value of the object svcTlsExtMmrpDeclaredAttrCnt indicates
        the number of MMRP attributes currently associated to the
        TLS by being declared."
    ::= { svcTlsExtEntry 13 }

svcTlsExtMmrpFailedRegCnt OBJECT-TYPE
    SYNTAX          Unsigned32
    MAX-ACCESS      read-only
    STATUS          current
    DESCRIPTION     
        "The value of the object svcTlsExtMvrpFailedRegCnt
         indicates number of failed MMRP attribute registrations in
         this TLS."
    ::= { svcTlsExtEntry 14 }

svcTlsExtMvrpAttributeCount OBJECT-TYPE
    SYNTAX          Unsigned32
    MAX-ACCESS      read-only
    STATUS          current
    DESCRIPTION
        "The value of the object svcTlsExtMvrpAttributeCount indicates
        the number of MVRP attributes currently associated to the
        TLS by either being registered or declared."
    ::= { svcTlsExtEntry 15 }

svcTlsExtMmrpEndStationOnly OBJECT-TYPE
    SYNTAX          TruthValue
    MAX-ACCESS      read-write
    STATUS          current
    DESCRIPTION
        "The value of the object svcTlsExtMmrpEndStationOnly specifies
        whether all SAP/SDP in this service are MMRP end-stations only."
    DEFVAL  { false }
    ::= { svcTlsExtEntry 16 }

svcTlsExtMacReNotifInterval OBJECT-TYPE
    SYNTAX          Unsigned32 (0|240..840)
    UNITS           "seconds"
    MAX-ACCESS      read-write
    STATUS          current
    DESCRIPTION     "The value of svcTlsExtMacReNotifInterval specifies
                     time-interval between subsequent burst of MAC notification
                     messages.

                     The default value indicates that the re-notification is
                     disabled."
    REFERENCE       "ITU-T Y.1731 specification"
    DEFVAL { 0 }
    ::= { svcTlsExtEntry 17 }

svcTlsExtSpbmCtrlVpls OBJECT-TYPE
    SYNTAX          TmnxServId
    MAX-ACCESS      read-write
    STATUS          current
    DESCRIPTION
        "The value of the object svcTlsExtSpbmCtrlVpls specifies the controlling
         Shortest Path Bridging (SPB) VPLS for this user SPB VPLS.

         An 'inconsistentValue' error is returned if svcTlsExtSpbmCtrlVpls is
         set to default and svcTlsExtSpbmFid is set to its non-default value or
         when svcTlsExtSpbmCtrlVpls is set to non-default and svcTlsExtSpbmFid
         is set to its default value."
    DEFVAL  { 0 }
    ::= { svcTlsExtEntry 18 }

svcTlsExtSpbmFid OBJECT-TYPE
    SYNTAX          TmnxSpbFidOrZero
    MAX-ACCESS      read-write
    STATUS          current
    DESCRIPTION
        "The value of the object svcTlsExtSpbmFid specifies the forwarding
         database identifier used by the user SPB VPLS.

         An 'inconsistentValue' error is returned if svcTlsExtSpbmCtrlVpls is
         set to default and svcTlsExtSpbmFid is set to its non-default value or
         when svcTlsExtSpbmCtrlVpls is set to non-default and svcTlsExtSpbmFid
         is set to its default value."
    DEFVAL  { 0 }
    ::= { svcTlsExtEntry 19 }

svcTlsExtSpiLoadBalancing OBJECT-TYPE
    SYNTAX          TmnxEnabledDisabled
    MAX-ACCESS      read-write
    STATUS          current
    DESCRIPTION
        "The value of svcTlsExtSpiLoadBalancing specifies whether SPI use in 
         hashing is enabled on this service."
    DEFVAL  { disabled }
    ::= { svcTlsExtEntry 20 }

svcTlsExtTeidLoadBalancing OBJECT-TYPE
    SYNTAX          TmnxEnabledDisabled
    MAX-ACCESS      read-write
    STATUS          current
    DESCRIPTION
        "The value of svcTlsExtTeidLoadBalancing specifies whether
         TEID load balancing is enabled for this service."
    DEFVAL  { disabled }
    ::= { svcTlsExtEntry 21 }
--
-- service psudeo-wire prefix table
-- 
svcPwRtLclPrefixTblLastChanged  OBJECT-TYPE
    SYNTAX          TimeStamp
    MAX-ACCESS      read-only
    STATUS          current
    DESCRIPTION
        "The value of svcPwRtLclPrefixTblLastChanged indicates the sysUpTime
         at the time of the last modification of svcPwRtLclPrefixTable.

         If no changes were made to the entry since the last re-initialization
         of the local network management subsystem, then this object contains a
         zero value."
    ::= { tmnxSvcObjs 98 }

svcPwRtLclPrefixTable OBJECT-TYPE
    SYNTAX          SEQUENCE OF SvcPwRtLclPrefixEntry
    MAX-ACCESS      not-accessible
    STATUS          current
    DESCRIPTION
        "A table that contains pseudo-wire routing local prefix information."
    ::= { tmnxSvcObjs 99 }

svcPwRtLclPrefixEntry OBJECT-TYPE
    SYNTAX          SvcPwRtLclPrefixEntry
    MAX-ACCESS      not-accessible
    STATUS          current
    DESCRIPTION
        "An entry indicating pseudo-wire routing local prefix information."
    INDEX           { svcPwRtLclPrefixGlobalId, svcPwRtLclPrefix }
    ::= { svcPwRtLclPrefixTable 1 }

SvcPwRtLclPrefixEntry ::=
    SEQUENCE {
        svcPwRtLclPrefixGlobalId           TmnxPwGlobalId,
        svcPwRtLclPrefix                   Unsigned32,
        svcPwRtLclPrefixRowStatus          RowStatus,
        svcPwRtLclPrefixLastChange         TimeStamp
    }       

svcPwRtLclPrefixGlobalId OBJECT-TYPE
    SYNTAX          TmnxPwGlobalId
    MAX-ACCESS      not-accessible
    STATUS          current
    DESCRIPTION
        "The value of the object svcPwRtLclPrefixGlobalId specifies the
         pseudo-wire routing global identifier."
    ::= { svcPwRtLclPrefixEntry 1 }

svcPwRtLclPrefix OBJECT-TYPE
    SYNTAX          Unsigned32 (1..4294967295)
    MAX-ACCESS      not-accessible
    STATUS          current
    DESCRIPTION
        "The value of the object svcPwRtLclPrefix specifies prefix value
         used by this pseudo-wire instance for redundancy."
    ::= { svcPwRtLclPrefixEntry 2 }

svcPwRtLclPrefixRowStatus OBJECT-TYPE
    SYNTAX          RowStatus
    MAX-ACCESS      read-create
    STATUS          current
    DESCRIPTION
        "This value of the object svcPwRtLclPrefixRowStatus specifies the
         status of this row."
    ::= { svcPwRtLclPrefixEntry 3 }

svcPwRtLclPrefixLastChange OBJECT-TYPE
    SYNTAX       TimeStamp
    MAX-ACCESS   read-only
    STATUS       current
    DESCRIPTION  
        "The value of svcPwRtLclPrefixLastChange indicates the timestamp of last
        change to this row in svcPwRtLclPrefixTable."
    ::= { svcPwRtLclPrefixEntry 4 }  
    
--
-- svcPwRtPathTable
--
svcPwRtPathTblLastChanged  OBJECT-TYPE
    SYNTAX          TimeStamp
    MAX-ACCESS      read-only
    STATUS          current
    DESCRIPTION
        "The value of svcPwRtPathTblLastChanged indicates the sysUpTime
         at the time of the last modification of svcPwRtPathTable.

         If no changes were made to the entry since the last re-initialization
         of the local network management subsystem, then this object contains a
         zero value."
    ::= { tmnxSvcObjs 100 }

svcPwRtPathTable OBJECT-TYPE
    SYNTAX          SEQUENCE OF SvcPwRtPathEntry
    MAX-ACCESS      not-accessible
    STATUS          current
    DESCRIPTION
        "A table that contains pseudo-wire routing global path information."
    ::= { tmnxSvcObjs 101 }

svcPwRtPathEntry OBJECT-TYPE
    SYNTAX          SvcPwRtPathEntry
    MAX-ACCESS      not-accessible
    STATUS          current
    DESCRIPTION
        "An entry indicating global pseudo-wire routing path information."
    INDEX           { svcPwRtPathName }
    ::= { svcPwRtPathTable 1 }

SvcPwRtPathEntry ::=
    SEQUENCE {
        svcPwRtPathName               TNamedItem,
        svcPwRtPathRowStatus          RowStatus,
        svcPwRtPathLastChange         TimeStamp,
        svcPwRtPathAdminStatus        ServiceAdminStatus
    }       

svcPwRtPathName OBJECT-TYPE
    SYNTAX          TNamedItem
    MAX-ACCESS      not-accessible
    STATUS          current
    DESCRIPTION
        "The value of the object svcPwRtPathName specifies the path name
         in pseudo-wire routing global instance."
    ::= { svcPwRtPathEntry 1 }

svcPwRtPathRowStatus OBJECT-TYPE
    SYNTAX          RowStatus
    MAX-ACCESS      read-create
    STATUS          current
    DESCRIPTION
        "This value of the object svcPwRtPathRowStatus specifies the
         status of this row."
    ::= { svcPwRtPathEntry 2 }

svcPwRtPathLastChange OBJECT-TYPE
    SYNTAX       TimeStamp
    MAX-ACCESS   read-only
    STATUS       current
    DESCRIPTION  
        "The value of svcPwRtPathLastChange indicates the timestamp of last
        change to this row in svcPwRtPathTable."
    ::= { svcPwRtPathEntry 3 }  

svcPwRtPathAdminStatus OBJECT-TYPE
    SYNTAX          ServiceAdminStatus
    MAX-ACCESS      read-create
    STATUS          current
    DESCRIPTION     
        "The value of svcPwRtPathAdminStatus specifies the administrative
        state of this path."
    DEFVAL          { down }
    ::= { svcPwRtPathEntry 4 }
    
--
-- svcPwRtPathHopTable
--
svcPwRtPathHopTblLastChgd  OBJECT-TYPE
    SYNTAX          TimeStamp
    MAX-ACCESS      read-only
    STATUS          current
    DESCRIPTION
        "The value of svcPwRtPathHopTblLastChgd indicates the sysUpTime
         at the time of the last modification of svcPwRtPathHopTable.

         If no changes were made to the entry since the last re-initialization
         of the local network management subsystem, then this object contains a
         zero value."
    ::= { tmnxSvcObjs 102 }

svcPwRtPathHopTable OBJECT-TYPE
    SYNTAX          SEQUENCE OF SvcPwRtPathHopEntry
    MAX-ACCESS      not-accessible
    STATUS          current
    DESCRIPTION
        "A table that contains hop information per path in the pseudo-wire
         routing instances."
    ::= { tmnxSvcObjs 103 }

svcPwRtPathHopEntry OBJECT-TYPE
    SYNTAX          SvcPwRtPathHopEntry
    MAX-ACCESS      not-accessible
    STATUS          current
    DESCRIPTION
        "An entry indicating specific pseudo-wire routing path hop information."
    INDEX           { svcPwRtPathName,
                      svcPwRtPathHopIndex }
    ::= { svcPwRtPathHopTable 1 }

SvcPwRtPathHopEntry ::=
    SEQUENCE {
        svcPwRtPathHopIndex              TmnxPwPathHopId,
        svcPwRtPathHopRowStatus          RowStatus,
        svcPwRtPathHopLastChange         TimeStamp,
        svcPwRtPathHopAddrType           InetAddressType,
        svcPwRtPathHopAddr               InetAddress
    }       

svcPwRtPathHopIndex OBJECT-TYPE
    SYNTAX          TmnxPwPathHopId
    MAX-ACCESS      not-accessible
    STATUS          current
    DESCRIPTION
        "The value of the object svcPwRtPathHopIndex specifies the hop
         index for the path in pseudo-wire routing global instance."
    ::= { svcPwRtPathHopEntry 1 }

svcPwRtPathHopRowStatus OBJECT-TYPE
    SYNTAX          RowStatus
    MAX-ACCESS      read-create
    STATUS          current
    DESCRIPTION
        "This value of the object svcPwRtPathHopRowStatus specifies the
         status of this row."
    ::= { svcPwRtPathHopEntry 2 }

svcPwRtPathHopLastChange OBJECT-TYPE
    SYNTAX       TimeStamp
    MAX-ACCESS   read-only
    STATUS       current
    DESCRIPTION  
        "The value of svcPwRtPathHopLastChange indicates the timestamp
         of last change to this row in svcPwRtPathHopTable."
    ::= { svcPwRtPathHopEntry 3 }  

svcPwRtPathHopAddrType OBJECT-TYPE
    SYNTAX       InetAddressType
    MAX-ACCESS   read-create
    STATUS       current
    DESCRIPTION  
        "The value of svcPwRtPathHopAddrType specifies the address type
         of the address specified by svcPwRtPathHopAddr."
    DEFVAL { unknown }
    ::= { svcPwRtPathHopEntry 4 }  

svcPwRtPathHopAddr OBJECT-TYPE
    SYNTAX       InetAddress (SIZE(0|4|16))
    MAX-ACCESS   read-create
    STATUS       current
    DESCRIPTION  
        "The value of svcPwRtPathHopAddr specifies the address associated
         with this hop."
    DEFVAL { ''H }
    ::= { svcPwRtPathHopEntry 5 }  

--
-- svcPwRtStaticRtTable
--
svcPwRtStaticRtTblLastChgd  OBJECT-TYPE
    SYNTAX          TimeStamp
    MAX-ACCESS      read-only
    STATUS          current
    DESCRIPTION
        "The value of svcPwRtStaticRtTblLastChgd indicates the sysUpTime
         at the time of the last modification of svcPwRtStaticRtTable.

         If no changes were made to the entry since the last re-initialization
         of the local network management subsystem, then this object contains a
         zero value."
    ::= { tmnxSvcObjs 104 }

svcPwRtStaticRtTable OBJECT-TYPE
    SYNTAX          SEQUENCE OF SvcPwRtStaticRtEntry
    MAX-ACCESS      not-accessible
    STATUS          current
    DESCRIPTION
        "A table that contains static-route information for the pseudo-wire
         routing instances."
    ::= { tmnxSvcObjs 105 }

svcPwRtStaticRtEntry OBJECT-TYPE
    SYNTAX          SvcPwRtStaticRtEntry
    MAX-ACCESS      not-accessible
    STATUS          current
    DESCRIPTION
        "An entry indicating specific static-route for the pseudo-wire routing
         instance."
    INDEX           {
                      svcPwRtStaticRtDstGlobalId,
                      svcPwRtStaticRtDstPrefix,
                      svcPwRtStaticRtDstAddrType,
                      svcPwRtStaticRtDstAddr
                    }
    ::= { svcPwRtStaticRtTable 1 }

SvcPwRtStaticRtEntry ::=
    SEQUENCE {
        svcPwRtStaticRtDstGlobalId        TmnxPwGlobalIdOrZero,
        svcPwRtStaticRtDstPrefix          Unsigned32,
        svcPwRtStaticRtDstAddrType        InetAddressType,
        svcPwRtStaticRtDstAddr            InetAddress,
        svcPwRtStaticRtRowStatus          RowStatus,
        svcPwRtStaticRtLastChange         TimeStamp
    }       

svcPwRtStaticRtDstGlobalId OBJECT-TYPE
    SYNTAX          TmnxPwGlobalIdOrZero
    MAX-ACCESS      not-accessible
    STATUS          current
    DESCRIPTION
        "The value of the object svcPwRtStaticRtDstGlobalId specifies the
         pseudo-wire global routing index of the destination."
    ::= { svcPwRtStaticRtEntry 1 }

svcPwRtStaticRtDstPrefix OBJECT-TYPE
    SYNTAX          Unsigned32
    MAX-ACCESS      not-accessible
    STATUS          current
    DESCRIPTION
        "The value of the object svcPwRtStaticRtDstPrefix specifies the
         prefix of the global routing index of the destination."
    ::= { svcPwRtStaticRtEntry 2 }

svcPwRtStaticRtDstAddrType OBJECT-TYPE
    SYNTAX       InetAddressType
    MAX-ACCESS   not-accessible
    STATUS       current
    DESCRIPTION  
        "The value of svcPwRtStaticRtDstAddrType specifies the address type
         of the address specified by svcPwRtStaticRtDstAddr."
    ::= { svcPwRtStaticRtEntry 3 }  

svcPwRtStaticRtDstAddr OBJECT-TYPE
    SYNTAX       InetAddress (SIZE(0|4|16))
    MAX-ACCESS   not-accessible
    STATUS       current
    DESCRIPTION  
        "The value of svcPwRtStaticRtDstAddr specifies the destination address
         of this static-route entry."
    ::= { svcPwRtStaticRtEntry 4 }  

svcPwRtStaticRtRowStatus OBJECT-TYPE
    SYNTAX          RowStatus
    MAX-ACCESS      read-create
    STATUS          current
    DESCRIPTION
        "This value of the object svcPwRtStaticRtRowStatus specifies the
         status of this row."
    ::= { svcPwRtStaticRtEntry 5 }

svcPwRtStaticRtLastChange OBJECT-TYPE
    SYNTAX       TimeStamp
    MAX-ACCESS   read-only
    STATUS       current
    DESCRIPTION  
        "The value of svcPwRtStaticRtLastChange indicates the timestamp
         of last change to this row in svcPwRtStaticRtTable."
    ::= { svcPwRtStaticRtEntry 6 }  

--
-- svcMSPwPeTable
--
svcMSPwPeTblLastChanged  OBJECT-TYPE
    SYNTAX          TimeStamp
    MAX-ACCESS      read-only
    STATUS          current
    DESCRIPTION
        "The value of svcMSPwPeTblLastChanged indicates the sysUpTime
         at the time of the last modification of svcMSPwPeTable.

         If no changes were made to the entry since the last re-initialization
         of the local network management subsystem, then this object contains a
         zero value."
    ::= { tmnxSvcObjs 106 }

svcMSPwPeTable OBJECT-TYPE
    SYNTAX          SEQUENCE OF SvcMSPwPeEntry
    MAX-ACCESS      not-accessible
    STATUS          current
    DESCRIPTION     "A table that contains multi-segment pseudo-wire provider-
                     edge information for the service."
    ::= { tmnxSvcObjs 107 }

svcMSPwPeEntry OBJECT-TYPE
    SYNTAX          SvcMSPwPeEntry
    MAX-ACCESS      not-accessible
    STATUS          current
    DESCRIPTION     "Multi-segment pseudo-wire provider-edge specific
                     information for this service."
    INDEX           { svcId, svcMSPwPeId }
    ::= { svcMSPwPeTable 1 }

SvcMSPwPeEntry ::=
    SEQUENCE {
        svcMSPwPeId                 TmnxSpokeSdpId,
        svcMSPwPeRowStatus          RowStatus,
        svcMSPwPeLastChange         TimeStamp,
        svcMSPwPeAdminStatus        ServiceAdminStatus,
        svcMSPwPeFecType            TmnxLdpFECType,
        svcMSPwPeAiiType            TmnxAiiType,
        svcMSPwPeSignaling          TmnxMsPwPeSignaling,
        svcMSPwPeAutoConfig         TruthValue,
        svcMSPwPeAgi                TmnxVPNRouteDistinguisher,
        svcMSPwPePolicyId           PWTemplateId,
        svcMSPwPePrecedence         Unsigned32,
        svcMSPwPeRetryTimer         Unsigned32,
        svcMSPwPeRetryCount         Unsigned32,
        svcMSPwPeSaiiGlobalId       TmnxPwGlobalIdOrZero,
        svcMSPwPeSaiiPrefix         Unsigned32,
        svcMSPwPeSaiiAcId           Unsigned32,
        svcMSPwPeTaiiGlobalId       TmnxPwGlobalIdOrZero,
        svcMSPwPeTaiiPrefix         Unsigned32,
        svcMSPwPeTaiiAcId           Unsigned32,
        svcMSPwPePathName           TNamedItemOrEmpty,
        svcMSPwPeEndPoint           TNamedItemOrEmpty,
        svcMSPwPeStandbySigSlave    TruthValue,
        svcMSPwPeIsICB              TruthValue,
        svcMSPwPeTimeRemain         Unsigned32,
        svcMSPwPeRetryRemain        Unsigned32,
        svcMSPwPeOperSdpBind        SdpBindId,
        svcMSPwPeRetryExpired       TruthValue,
        svcMSPwPeLastError          DisplayString
    }       

svcMSPwPeId OBJECT-TYPE
    SYNTAX          TmnxSpokeSdpId
    MAX-ACCESS      not-accessible
    STATUS          current
    DESCRIPTION
        "The value of the object svcMSPwPeId specifies the
         multi-segment pseudo-wire provider-edge identifier for this service."
    ::= { svcMSPwPeEntry 1 }

svcMSPwPeRowStatus OBJECT-TYPE
    SYNTAX          RowStatus
    MAX-ACCESS      read-create
    STATUS          current
    DESCRIPTION
        "This value of the object svcMSPwPeRowStatus specifies the
         status of this row."
    ::= { svcMSPwPeEntry 2 }

svcMSPwPeLastChange OBJECT-TYPE
    SYNTAX       TimeStamp
    MAX-ACCESS   read-only
    STATUS       current
    DESCRIPTION  
        "The value of svcMSPwPeLastChange indicates the timestamp of last
        change to this row in svcMSPwPeTable."
    ::= { svcMSPwPeEntry 3 }  
    
svcMSPwPeAdminStatus OBJECT-TYPE
    SYNTAX          ServiceAdminStatus
    MAX-ACCESS      read-create
    STATUS          current
    DESCRIPTION     
        "The value of svcMSPwPeAdminStatus specifies the administrative state of
        this multi-segment pseudo-wire provider-edge for this service."
    DEFVAL          { down }
    ::= { svcMSPwPeEntry 4 }

svcMSPwPeFecType OBJECT-TYPE
    SYNTAX          TmnxLdpFECType
    MAX-ACCESS      read-create
    STATUS          current
    DESCRIPTION     
        "The value of svcMSPwPeFecType specifies the LDP FEC type to be used on
        this multi-segment pseudo-wire provider-edge for this service."
    DEFVAL          { vpws }
    ::= { svcMSPwPeEntry 5 }

svcMSPwPeAiiType OBJECT-TYPE
    SYNTAX          TmnxAiiType
    MAX-ACCESS      read-create
    STATUS          current
    DESCRIPTION     
        "The value of svcMSPwPeAiiType specifies the Attachment Individual
        Identifier (AII) type to be used on this multi-segment pseudo-wire
        provider-edge for this service."
    DEFVAL          { aiiType2 }
    ::= { svcMSPwPeEntry 6 }

svcMSPwPeSignaling OBJECT-TYPE
    SYNTAX     TmnxMsPwPeSignaling
    MAX-ACCESS read-create
    STATUS     current
    DESCRIPTION
        "The value of svcMSPwPeSignaling specifies the type of signaling used
         by this multi-segment pseudo-wire provider-edge for this service."
    DEFVAL { auto }
    ::= { svcMSPwPeEntry 7 }

svcMSPwPeAutoConfig OBJECT-TYPE
    SYNTAX     TruthValue
    MAX-ACCESS read-create
    STATUS     current
    DESCRIPTION
        "The value of svcMSPwPeAutoConfig specifies whether multi-segment 
         pseudo-wire provider-edge for this service should use
         auto-configuration."
    DEFVAL { false }
    ::= { svcMSPwPeEntry 8 }

svcMSPwPeAgi OBJECT-TYPE
    SYNTAX     TmnxVPNRouteDistinguisher
    MAX-ACCESS read-create
    STATUS     current
    DESCRIPTION
        "The value of svcMSPwPeAgi specifies the Attachment Group Identifier
         (AGI) portion of the Generalized Id FEC element of the pseudo-wire
         setup for this provider-edge in this service."
    DEFVAL          { '0000000000000000'H }
    ::= { svcMSPwPeEntry 9 }

svcMSPwPePolicyId OBJECT-TYPE
    SYNTAX     PWTemplateId
    MAX-ACCESS read-create
    STATUS     current
    DESCRIPTION
        "The value of svcMSPwPePolicyId specifies the pseudo-wite template
         policy to be used on this multi-segment pseudo-wire provider-edge."
    DEFVAL { 0 }
    ::= { svcMSPwPeEntry 10 }

svcMSPwPePrecedence OBJECT-TYPE
    SYNTAX     Unsigned32 (0..4)
    MAX-ACCESS read-create
    STATUS     current
    DESCRIPTION
        "The value of svcMSPwPePrecedence specifies the precedence of this
         multi-segment pseudo-wire provider-edge in this service."
    DEFVAL { 4 }
    ::= { svcMSPwPeEntry 11 }

svcMSPwPeRetryTimer OBJECT-TYPE
    SYNTAX     Unsigned32 (0|10..480)
    UNITS      "seconds"
    MAX-ACCESS read-create
    STATUS     current
    DESCRIPTION
        "The value of svcMSPwPeRetryTimer specifies the retry timer value
         to be used by this multi-segment pseudo-wire provider-edge in this
         service.
         
         System uses the value of svcPwRtRetryTimer when value of this object
         is set to the default."
    DEFVAL { 0 }
    ::= { svcMSPwPeEntry 12 }

svcMSPwPeRetryCount OBJECT-TYPE 
    SYNTAX     Unsigned32 (0|10..10000)
    MAX-ACCESS read-create
    STATUS     current
    DESCRIPTION
        "The value of svcMSPwPeRetryCount specifies the retry count value
         to be used by this multi-segment pseudo-wire provider-edge in this
         service.

         System uses the value of svcPwRtRetryCount when value of this object
         is set to the default."
    DEFVAL { 0 }
    ::= { svcMSPwPeEntry 13 }

svcMSPwPeSaiiGlobalId OBJECT-TYPE
    SYNTAX     TmnxPwGlobalIdOrZero
    MAX-ACCESS read-create
    STATUS     current
    DESCRIPTION
        "The value of svcMSPwPeSaiiGlobalId specifies the global identifier of
         Source Attachment Individual Identifier (SAII) portion
         of the Generalized Id FEC element as used by
         this multi-segment pseudo-wire provider-edge in this service."
    DEFVAL { 0 }
    ::= { svcMSPwPeEntry 14 }

svcMSPwPeSaiiPrefix OBJECT-TYPE
    SYNTAX     Unsigned32
    MAX-ACCESS read-create
    STATUS     current
    DESCRIPTION
        "The value of svcMSPwPeSaiiPrefix specifies the prefix to the
         Source Attachment Individual Identifier (SAII) portion
         of the Generalized Id FEC element as used by
         this multi-segment pseudo-wire provider-edge in this service."
    DEFVAL { 0 }
    ::= { svcMSPwPeEntry 15 }

svcMSPwPeSaiiAcId OBJECT-TYPE
    SYNTAX     Unsigned32
    MAX-ACCESS read-create
    STATUS     current
    DESCRIPTION
        "The value of svcMSPwPeSaiiAcId specifies the attachment circuit
         identifier part of Source Attachment Individual Identifier (SAII)
         portion of the Generalized Id FEC element as used by
         this multi-segment pseudo-wire provider-edge in this service."
    DEFVAL { 0 }
    ::= { svcMSPwPeEntry 16 }

svcMSPwPeTaiiGlobalId OBJECT-TYPE
    SYNTAX     TmnxPwGlobalIdOrZero
    MAX-ACCESS read-create
    STATUS     current
    DESCRIPTION
        "The value of svcMSPwPeTaiiGlobalId specifies the global identifier of
         Target Attachment Individual Identifier (TAII) portion
         of the Generalized Id FEC element as used by
         this multi-segment pseudo-wire provider-edge in this service."
    DEFVAL { 0 }
    ::= { svcMSPwPeEntry 17 }

svcMSPwPeTaiiPrefix OBJECT-TYPE
    SYNTAX     Unsigned32
    MAX-ACCESS read-create
    STATUS     current
    DESCRIPTION
        "The value of svcMSPwPeTaiiPrefix specifies the prefix to the
         Target Attachment Individual Identifier (TAII) portion
         of the Generalized Id FEC element as used by
         this multi-segment pseudo-wire provider-edge in this service."
    DEFVAL { 0 }
    ::= { svcMSPwPeEntry 18 }

svcMSPwPeTaiiAcId OBJECT-TYPE
    SYNTAX     Unsigned32
    MAX-ACCESS read-create
    STATUS     current
    DESCRIPTION
        "The value of svcMSPwPeTaiiAcId specifies the attachment circuit
         identifier part of Target Attachment Individual Identifier (TAII)
         portion of the Generalized Id FEC element as used by
         this multi-segment pseudo-wire provider-edge in this service."
    DEFVAL { 0 }
    ::= { svcMSPwPeEntry 19 }

svcMSPwPePathName OBJECT-TYPE
    SYNTAX     TNamedItemOrEmpty
    MAX-ACCESS read-create
    STATUS     current
    DESCRIPTION
        "The value of svcMSPwPePathName specifies the path name used by
         this multi-segment pseudo-wire provider-edge in this service."
    DEFVAL { ''H }
    ::= { svcMSPwPeEntry 20 }

svcMSPwPeEndPoint OBJECT-TYPE
    SYNTAX     TNamedItemOrEmpty
    MAX-ACCESS read-create
    STATUS     current
    DESCRIPTION
        "The value of svcMSPwPeEndPoint specifies the endpoint used by
         this multi-segment pseudo-wire provider-edge in this service."
    DEFVAL { ''H }
    ::= { svcMSPwPeEntry 21 }

svcMSPwPeStandbySigSlave OBJECT-TYPE
    SYNTAX      TruthValue
    MAX-ACCESS  read-create
    STATUS      current
    DESCRIPTION
        "The value of svcMSPwPeStandbySigSlave specifies whether
         transmission of any spoke in the endpoint will be blocked when the
         spoke receives standby status notification from its peer."
    DEFVAL { false }
    ::= { svcMSPwPeEntry 22 }

svcMSPwPeIsICB OBJECT-TYPE
    SYNTAX      TruthValue
    MAX-ACCESS  read-create
    STATUS      current
    DESCRIPTION
        "The value of svcMSPwPeIsICB specifies whether this sdp-binding is an 
         inter-chassis backup SDP bind."
    DEFVAL { false }
    ::= { svcMSPwPeEntry 23 }

svcMSPwPeTimeRemain OBJECT-TYPE
    SYNTAX       Unsigned32
    UNITS        "seconds"
    MAX-ACCESS   read-only
    STATUS       current
    DESCRIPTION
        "The value of svcMSPwPeTimeRemain indicates remaining time in the retry
         timer for this multi-segment pseudo-wire provider-edge in this
         service."
    ::= { svcMSPwPeEntry 24 }

svcMSPwPeRetryRemain OBJECT-TYPE
    SYNTAX       Unsigned32
    MAX-ACCESS   read-only
    STATUS       current
    DESCRIPTION
        "The value of svcMSPwPeRetryRemain indicates remaining retries
         for this multi-segment pseudo-wire provider-edge in this service."
    ::= { svcMSPwPeEntry 25 }

svcMSPwPeOperSdpBind OBJECT-TYPE
    SYNTAX          SdpBindId
    MAX-ACCESS      read-only
    STATUS          current
    DESCRIPTION
        "The value of svcMSPwPeOperSdpBind indicates operational SDP-bind
         used for this multi-segment pseudo-wire provider-edge in this service."
    ::= { svcMSPwPeEntry 26 }

svcMSPwPeRetryExpired OBJECT-TYPE
    SYNTAX       TruthValue
    MAX-ACCESS   read-only
    STATUS       current
    DESCRIPTION
        "The value of svcMSPwPeRetryExpired indicates whether all retries have
         expired for this multi-segment pseudo-wire provider-edge in this
         service."
    ::= { svcMSPwPeEntry 27 }

svcMSPwPeLastError OBJECT-TYPE
    SYNTAX          DisplayString
    MAX-ACCESS      read-only
    STATUS          current
    DESCRIPTION
        "The value of the object svcMSPwPeLastError indicates the last error
        encountered trying to bring up this multi-segment pseudo-wire
        provider-edge in this service."
    ::= { svcMSPwPeEntry 28 }

--
-- Operational-Group
--
svcOperGrpTblLastChanged  OBJECT-TYPE
    SYNTAX          TimeStamp
    MAX-ACCESS      read-only
    STATUS          current
    DESCRIPTION
        "The value of svcOperGrpTblLastChanged indicates the sysUpTime
         at the time of the last modification of svcOperGrpTable.

         If no changes were made to the entry since the last re-initialization
         of the local network management subsystem, then this object contains a
         zero value."
    ::= { tmnxSvcObjs 108 }

svcOperGrpTable OBJECT-TYPE
    SYNTAX          SEQUENCE OF SvcOperGrpEntry
    MAX-ACCESS      not-accessible
    STATUS          current
    DESCRIPTION     "A table that contains Operational-Group information."
    ::= { tmnxSvcObjs 109 }

svcOperGrpEntry OBJECT-TYPE
    SYNTAX          SvcOperGrpEntry
    MAX-ACCESS      not-accessible
    STATUS          current
    DESCRIPTION     "Each row specifies information about a specific
                     Operational-Group."
    INDEX           { svcOperGrpName }
    ::= { svcOperGrpTable 1 }

SvcOperGrpEntry ::=
    SEQUENCE {
        svcOperGrpName               TNamedItem,
        svcOperGrpRowStatus          RowStatus,
        svcOperGrpLastChange         TimeStamp,
        svcOperGrpOperStatus         ServiceOperStatus,
        svcOperGrpHoldDownTime       TmnxOperGrpHoldDownTime,
        svcOperGrpCreationOrigin     TmnxSvcOperGrpCreationOrigin,
        svcOperGrpHoldUpTime         TmnxOperGrpHoldUpTime,
        svcOperGrpHoldUpTimeRemain   TmnxOperGrpHoldUpTime,
        svcOperGrpHoldDownTimeRemain TmnxOperGrpHoldDownTime,
        svcOperGrpNumMembers         Gauge32,
        svcOperGrpNumMonitoring      Gauge32
    }       

svcOperGrpName OBJECT-TYPE
    SYNTAX          TNamedItem
    MAX-ACCESS      not-accessible
    STATUS          current
    DESCRIPTION
        "The value of the object svcOperGrpName specifies the
         Operational-Group identifier."
    ::= { svcOperGrpEntry 1 }

svcOperGrpRowStatus OBJECT-TYPE
    SYNTAX          RowStatus
    MAX-ACCESS      read-create
    STATUS          current
    DESCRIPTION
        "This value of the object svcOperGrpRowStatus specifies the
         status of this row."
    ::= { svcOperGrpEntry 2 }

svcOperGrpLastChange OBJECT-TYPE
    SYNTAX       TimeStamp
    MAX-ACCESS   read-only
    STATUS       current
    DESCRIPTION  
        "The value of svcOperGrpLastChange indicates the timestamp of last
        change to this row in svcOperGrpTable."
    ::= { svcOperGrpEntry 3 }  
    
svcOperGrpOperStatus OBJECT-TYPE
    SYNTAX          ServiceOperStatus
    MAX-ACCESS      read-only
    STATUS          current
    DESCRIPTION     
        "The value of svcOperGrpOperStatus indicates the operational
        state of this group."
    ::= { svcOperGrpEntry 4 }
    
svcOperGrpHoldDownTime OBJECT-TYPE
    SYNTAX          TmnxOperGrpHoldDownTime
    UNITS           "seconds"
    MAX-ACCESS      read-create
    STATUS          current
    DESCRIPTION     
        "The value of svcOperGrpHoldDownTime specifies number of seconds to
        wait before notifying clients monitoring this group when its
        operational status transitions from up to down."
    DEFVAL { 0 }
    ::= { svcOperGrpEntry 5 }
    
svcOperGrpCreationOrigin   OBJECT-TYPE
    SYNTAX          TmnxSvcOperGrpCreationOrigin
    MAX-ACCESS      read-only
    STATUS          current
    DESCRIPTION
        "The value of svcOperGrpCreationOrigin indicates the protocol or 
         mechanism which created this group."
    ::= { svcOperGrpEntry 6 }

svcOperGrpHoldUpTime OBJECT-TYPE
    SYNTAX          TmnxOperGrpHoldUpTime
    UNITS           "seconds"
    MAX-ACCESS      read-create
    STATUS          current
    DESCRIPTION     
        "The value of svcOperGrpHoldUpTime specifies number of seconds to
        wait before notifying clients monitoring this group when its
        operational status transitions from down to up."
    DEFVAL { 4 }
    ::= { svcOperGrpEntry 7 }

svcOperGrpHoldUpTimeRemain OBJECT-TYPE
    SYNTAX         TmnxOperGrpHoldUpTime
    UNITS          "seconds"
    MAX-ACCESS     read-only
    STATUS         current
    DESCRIPTION 
        "The value of svcOperGrpHoldUpTimeRemain indicates the number of
        seconds remaining in the svcOperGrpHoldUpTime."
    ::= { svcOperGrpEntry 8 }

svcOperGrpHoldDownTimeRemain OBJECT-TYPE
    SYNTAX         TmnxOperGrpHoldDownTime
    UNITS          "seconds"
    MAX-ACCESS     read-only
    STATUS         current
    DESCRIPTION 
        "The value of svcOperGrpHoldDownTimeRemain indicates the number of
        seconds remaining in the svcOperGrpHoldDownTime."
    ::= { svcOperGrpEntry 9 }

svcOperGrpNumMembers OBJECT-TYPE
    SYNTAX         Gauge32
    MAX-ACCESS     read-only
    STATUS         current
    DESCRIPTION 
        "The value of svcOperGrpNumMembers indicates the number of
        members as part of this operational-group."
    ::= { svcOperGrpEntry 10 }

svcOperGrpNumMonitoring OBJECT-TYPE
    SYNTAX         Gauge32
    MAX-ACCESS     read-only
    STATUS         current
    DESCRIPTION 
        "The value of svcOperGrpNumMonitoring indicates the number of
        objects monitoring this operational-group."
    ::= { svcOperGrpEntry 11 }


--
--
-- The DHCP Lease State Access Loop Encapsulation Table
--

svcDhcpLeaseAleTable   OBJECT-TYPE
    SYNTAX      SEQUENCE OF SvcDhcpLeaseAleEntry
    MAX-ACCESS  not-accessible
    STATUS      current
    DESCRIPTION
       "The svcDhcpLeaseAleTable contains Access Loop Encapsulation information
        for DHCP lease states.

        Entries in this table are created and destroyed by the system.
        
        This table is a sparse augment of the svcDhcpLeaseTable: entries
        are created only for DHCP lease states 
        for which Access Loop Encapsulation information is available."
    ::= { tmnxSvcObjs 110 }

svcDhcpLeaseAleEntry   OBJECT-TYPE
    SYNTAX      SvcDhcpLeaseAleEntry
    MAX-ACCESS  not-accessible
    STATUS      current
    DESCRIPTION
       "Each conceptual row represents access loop encapsulation information
        of a DHCP lease state."
    INDEX { svcId,
            svcDhcpLeaseCiAddrType,
            svcDhcpLeaseCiAddr,
            svcDhcpLeaseNextHopMacAddr }
    ::= { svcDhcpLeaseAleTable 1 }

SvcDhcpLeaseAleEntry ::= 
    SEQUENCE {
        svcDhcpLeaseAleDatalink          TmnxAccessLoopEncapDataLink,
        svcDhcpLeaseAleEncaps1           TmnxAccessLoopEncaps1,      
        svcDhcpLeaseAleEncaps2           TmnxAccessLoopEncaps2               
    }
        
svcDhcpLeaseAleDatalink OBJECT-TYPE
    SYNTAX          TmnxAccessLoopEncapDataLink
    MAX-ACCESS      read-only
    STATUS          current
    DESCRIPTION     "The value of svcDhcpLeaseAleDatalink indicates 
                     the data link used by the subscriber host 
                     on the DSL access loop."
    ::= { svcDhcpLeaseAleEntry 1 }

svcDhcpLeaseAleEncaps1 OBJECT-TYPE
    SYNTAX          TmnxAccessLoopEncaps1
    MAX-ACCESS      read-only
    STATUS          current
    DESCRIPTION     "The value of svcDhcpLeaseAleEncaps1 indicates 
                     the encapsulation used by the subscriber host 
                     on the DSL access loop."
    ::= { svcDhcpLeaseAleEntry 2 }

svcDhcpLeaseAleEncaps2 OBJECT-TYPE
    SYNTAX          TmnxAccessLoopEncaps2
    MAX-ACCESS      read-only
    STATUS          current
    DESCRIPTION     "The value of svcDhcpLeaseAleEncaps2 indicates 
                     the encapsulation used by the subscriber host 
                     on the DSL access loop."
    ::= { svcDhcpLeaseAleEntry 3 }

--
--  SVC ETH-CFM Table
--
svcEthCfmTblLastChanged  OBJECT-TYPE
    SYNTAX          TimeStamp
    MAX-ACCESS      read-only
    STATUS          current
    DESCRIPTION
        "The value of svcEthCfmTblLastChanged indicates the sysUpTime
         at the time of the last modification of svcEthCfmTable.

         If no changes were made to the entry since the last re-initialization
         of the local network management subsystem, then this object contains a
         zero value."
    ::= { tmnxSvcObjs 111 }

svcEthCfmTable         OBJECT-TYPE
    SYNTAX      SEQUENCE OF SvcEthCfmEntry
    MAX-ACCESS  not-accessible
    STATUS      current
    DESCRIPTION
       "The svcEthCfmTable contains Ethernet Connectivity Fault Management (CFM)
        information for Ethernet capable Services."
    ::= { tmnxSvcObjs 112 }

svcEthCfmEntry         OBJECT-TYPE
    SYNTAX      SvcEthCfmEntry
    MAX-ACCESS  not-accessible
    STATUS      current
    DESCRIPTION
        "The svcEthCfmEntry consists of the Eth-CFM objects used to maintain
         Ethernet CFM functionality for the specified Ethernet capable Service."
    INDEX       { svcId }
    ::= { svcEthCfmTable 1 }

SvcEthCfmEntry                   ::= SEQUENCE {
    svcEthCfmTunnelFaultNotification INTEGER,
    svcEthCfmVMepExtensions          TmnxEnabledDisabled
}

svcEthCfmTunnelFaultNotification OBJECT-TYPE
    SYNTAX      INTEGER {
                    accept (1),
                    ignore (2)
                }
    MAX-ACCESS  read-create
    STATUS      current
    DESCRIPTION "The value of svcEthCfmTunnelFaultNotification specifies whether
                 the service will 'accept (1)' CFM fault notification from a
                 Tunnel MEP and process the notification (i.e. do fault handling
                 and/or fault propagation), or 'ignore (2)' the notification.

                 Both TIMETRA-SAP-MIB::sapEthCfmTunnelFaultNotification and
                 this object MUST be set to 'accept (1)' for an individual
                 SAP to process the notification."
    DEFVAL { ignore }
    ::= { svcEthCfmEntry 1 }

svcEthCfmVMepExtensions          OBJECT-TYPE
    SYNTAX      TmnxEnabledDisabled
    MAX-ACCESS  read-create
    STATUS      current
    DESCRIPTION
        "The value of svcEthCfmVMepExtensions specifies whether enhanced Virtual
         MEP functionality is enabled on the service or not. This object is used
         by TLS (VPLS) services only, and has no effect nor can it be modified
         on other service types.

         On services that do not support VMEP extensions this object is fixed to
         the value 'disabled (2)'."
    DEFVAL { disabled }
    ::= { svcEthCfmEntry 2 }

-- ----------------------
-- System service group objects
-- ----------------------
tmnxSvcGrpObjs OBJECT IDENTIFIER ::= { tmnxSvcObjs 113 }

svcMacFdbRecords OBJECT-TYPE
    SYNTAX         Unsigned32
    MAX-ACCESS     read-only
    STATUS         current
    DESCRIPTION 
        "The value of the object svcMacFdbRecords
        indicates the number of system wide FDB records in use."
    ::= { tmnxSvcGrpObjs 1 }

svcPwRtSpeAddrGlobalId OBJECT-TYPE
    SYNTAX         TmnxPwGlobalIdOrZero
    MAX-ACCESS     read-write
    STATUS         current
    DESCRIPTION
        "The value of the object svcPwRtSpeAddrGlobalId specifies the pseudo-
        wire routing global identifier of the switch-point node.
                    
        An 'inconsistentValue' error is returned if svcPwRtSpeAddrGlobalId is
        set to default when svcPwRtSpeAddrPrefix is set to non-default value or
        svcPwRtSpeAddrGlobalId is set to non-default when svcPwRtSpeAddrPrefix
        is set to default value."
    DEFVAL { 0 }
    ::= { tmnxSvcGrpObjs 2 }

svcPwRtSpeAddrPrefix OBJECT-TYPE
    SYNTAX         Unsigned32
    MAX-ACCESS     read-write
    STATUS         current
    DESCRIPTION 
        "The value of the object svcPwRtSpeAddrPrefix specifies the
        pseudo-wire routing prefix of the switch-point node.

        An 'inconsistentValue' error is returned if svcPwRtSpeAddrGlobalId is
        set to default when svcPwRtSpeAddrPrefix is set to non-default value or
        svcPwRtSpeAddrGlobalId is set to non-default when svcPwRtSpeAddrPrefix
        is set to default value."
    DEFVAL { 0 }
    ::= { tmnxSvcGrpObjs 3 }

svcPwRtBootTimer OBJECT-TYPE
    SYNTAX         Integer32 (0..600)
    UNITS          "seconds"
    MAX-ACCESS     read-write
    STATUS         current
    DESCRIPTION 
        "The value of the object svcPwRtBootTimer specifies how long the
        system waits after the reboot before trying to establish multi-segment
        pseudo-wire provider-edge connections."
    DEFVAL { 10 }
    ::= { tmnxSvcGrpObjs 4 }

svcPwRtRetryTimer OBJECT-TYPE
    SYNTAX        Unsigned32 (10..480)
    UNITS         "seconds"
    MAX-ACCESS    read-write
    STATUS        current
    DESCRIPTION
        "The value of svcPwRtRetryTimer specifies the retry timer value
         to be used by this multi-segment pseudo-wire provider-edge in this
         service."
    DEFVAL { 30 }
    ::= { tmnxSvcGrpObjs 5 }

svcPwRtRetryCount OBJECT-TYPE 
    SYNTAX        Unsigned32 (10..10000)
    MAX-ACCESS    read-write
    STATUS        current
    DESCRIPTION
        "The value of svcPwRtRetryCount specifies the retry count value
         to be used by this multi-segment pseudo-wire provider-edge in this
         service."
    DEFVAL { 30 }
    ::= { tmnxSvcGrpObjs 6 }

svcPwRtBgpRoutes OBJECT-TYPE 
    SYNTAX        Gauge32
    MAX-ACCESS    read-only
    STATUS        current
    DESCRIPTION
        "The value of svcPwRtBgpRoutes indicates the number of BGP routes
        in the TIMETRA-VRTR-MIB::vRtrMsPwL2RtTable."
    ::= { tmnxSvcGrpObjs 7 }

svcPwRtStaticRoutes OBJECT-TYPE 
    SYNTAX        Gauge32
    MAX-ACCESS    read-only
    STATUS        current
    DESCRIPTION
        "The value of svcPwRtStaticRoutes indicates the number of static
        routes in the TIMETRA-VRTR-MIB::vRtrMsPwL2RtTable."
    ::= { tmnxSvcGrpObjs 8 }

svcPwRtLocalRoutes OBJECT-TYPE 
    SYNTAX        Gauge32
    MAX-ACCESS    read-only
    STATUS        current
    DESCRIPTION
        "The value of svcPwRtLocalRoutes indicates the number of local
        routes in the TIMETRA-VRTR-MIB::vRtrMsPwL2RtTable."
    ::= { tmnxSvcGrpObjs 9 }

svcPwRtHostRoutes OBJECT-TYPE 
    SYNTAX        Gauge32
    MAX-ACCESS    read-only
    STATUS        current
    DESCRIPTION
        "The value of svcPwRtHostRoutes indicates the number of host
        routes in the TIMETRA-VRTR-MIB::vRtrMsPwL2RtTable."
    ::= { tmnxSvcGrpObjs 10 }

svcPwRtBootTimerRemain OBJECT-TYPE
    SYNTAX         Integer32 (0..600)
    UNITS          "seconds"
    MAX-ACCESS     read-only
    STATUS         current
    DESCRIPTION 
        "The value of svcPwRtBootTimerRemain indicates the number of seconds
        remaining in the svcPwRtBootTimer."
    ::= { tmnxSvcGrpObjs 11 }

-- --------------------------------------------------------------
-- service pseduo-wire local-prefix route-distinguisher table
-- --------------------------------------------------------------
svcPwRtLclPfxRDTblLastChanged  OBJECT-TYPE
    SYNTAX          TimeStamp
    MAX-ACCESS      read-only
    STATUS          current
    DESCRIPTION
        "The value of svcPwRtLclPfxRDTblLastChanged indicates the sysUpTime
         at the time of the last modification of svcPwRtLclPfxRDTable.

         If no changes were made to the entry since the last re-initialization
         of the local network management subsystem, then this object contains a
         zero value."
    ::= { tmnxSvcObjs 114 }

svcPwRtLclPfxRDTable OBJECT-TYPE
    SYNTAX          SEQUENCE OF SvcPwRtLclPfxRDEntry
    MAX-ACCESS      not-accessible
    STATUS          current
    DESCRIPTION
        "A table that contains pseudo-wire routing local prefix route-
        distingiusher information."
    ::= { tmnxSvcObjs 115 }

svcPwRtLclPfxRDEntry OBJECT-TYPE
    SYNTAX          SvcPwRtLclPfxRDEntry
    MAX-ACCESS      not-accessible
    STATUS          current
    DESCRIPTION
        "An entry indicating pseudo-wire routing local prefix route-
        distinguisher information."
    INDEX { svcPwRtLclPrefixGlobalId, svcPwRtLclPrefix, svcPwRtLclPfxRD }
    ::= { svcPwRtLclPfxRDTable 1 }

SvcPwRtLclPfxRDEntry ::=
    SEQUENCE {
        svcPwRtLclPfxRD                   TmnxVPNRouteDistinguisher,
        svcPwRtLclPfxRDRowStatus          RowStatus,
        svcPwRtLclPfxRDLastChange         TimeStamp,
        svcPwRtLclPfxRDCommunity          Unsigned32
    }       

svcPwRtLclPfxRD OBJECT-TYPE
    SYNTAX          TmnxVPNRouteDistinguisher
    MAX-ACCESS      not-accessible
    STATUS          current
    DESCRIPTION
        "The value of svcPwRtLclPfxRD specifies the route-disinguisher
         assoicated with this prefix."
    ::= { svcPwRtLclPfxRDEntry 1 }

svcPwRtLclPfxRDRowStatus OBJECT-TYPE
    SYNTAX          RowStatus
    MAX-ACCESS      read-create
    STATUS          current
    DESCRIPTION
        "This value of the object svcPwRtLclPfxRDRowStatus specifies the
         status of this row."
    ::= { svcPwRtLclPfxRDEntry 2 }

svcPwRtLclPfxRDLastChange OBJECT-TYPE
    SYNTAX       TimeStamp
    MAX-ACCESS   read-only
    STATUS       current
    DESCRIPTION  
        "The value of svcPwRtLclPfxRDLastChange indicates the timestamp of last
         change to this row in svcPwRtLclPfxRDTable."
    ::= { svcPwRtLclPfxRDEntry 3 }  
    
svcPwRtLclPfxRDCommunity OBJECT-TYPE
    SYNTAX          Unsigned32
    MAX-ACCESS      read-create
    STATUS          current
    DESCRIPTION
        "The value of the object svcPwRtLclPfxRDCommunity specifies the BGP
         community associated with the route-distinguisher."
    DEFVAL { 0 }
    ::= { svcPwRtLclPfxRDEntry 4 }

--
-- Service psuedo-wire switch-point node information by SAII
--
svcPwSpeSaiiTable OBJECT-TYPE
    SYNTAX          SEQUENCE OF SvcPwSpeSaiiEntry
    MAX-ACCESS      not-accessible
    STATUS          current
    DESCRIPTION
        "A table that contains pseudo-wire switch-point node information by
        Source Attachment Individual Identifier (SAII)."
    ::= { tmnxSvcObjs 116 }

svcPwSpeSaiiEntry OBJECT-TYPE
    SYNTAX          SvcPwSpeSaiiEntry
    MAX-ACCESS      not-accessible
    STATUS          current
    DESCRIPTION 
        "An entry that contains pseudo-wire switch-point node information by
        Source Attachment Individual Identifier (SAII)."
    INDEX           {
                       svcMSPwPeSaiiGlobalId,
                       svcMSPwPeSaiiPrefix,
                       svcMSPwPeSaiiAcId
                   }
    ::= { svcPwSpeSaiiTable 1 }

SvcPwSpeSaiiEntry ::=
    SEQUENCE {
        svcPwSpeSaiiTaiiGlobalId       TmnxPwGlobalIdOrZero,
        svcPwSpeSaiiTaiiPrefix         Unsigned32,
        svcPwSpeSaiiTaiiAcId           Unsigned32,
        svcPwSpeSaiiSvcId              TmnxServId,
        svcPwSpeSaiiOperSdpBind1       SdpBindId,
        svcPwSpeSaiiOperSdpBind2       SdpBindId
    }       


svcPwSpeSaiiTaiiGlobalId OBJECT-TYPE
    SYNTAX     TmnxPwGlobalIdOrZero
    MAX-ACCESS read-only
    STATUS     current
    DESCRIPTION
        "The value of svcPwSpeSaiiTaiiGlobalId indicates the global identifier
         of Target Attachment Individual Identifier (TAII) portion
         of the Generalized Id FEC element on switch-point node."
    ::= { svcPwSpeSaiiEntry 1 }

svcPwSpeSaiiTaiiPrefix OBJECT-TYPE
    SYNTAX     Unsigned32
    MAX-ACCESS read-only
    STATUS     current
    DESCRIPTION
        "The value of svcPwSpeSaiiTaiiPrefix indicates the prefix to the
         Target Attachment Individual Identifier (TAII) portion
         of the Generalized Id FEC element on switch-point node."
    ::= { svcPwSpeSaiiEntry 2 }

svcPwSpeSaiiTaiiAcId OBJECT-TYPE
    SYNTAX     Unsigned32
    MAX-ACCESS read-only
    STATUS     current
    DESCRIPTION
        "The value of svcPwSpeSaiiTaiiAcId indicates the attachment circuit
         identifier part of Source Attachment Individual Identifier (SAII)
         portion of the Generalized Id FEC element on switch-point node."
    ::= { svcPwSpeSaiiEntry 3 }

svcPwSpeSaiiSvcId OBJECT-TYPE
    SYNTAX          TmnxServId
    MAX-ACCESS      read-only
    STATUS          current
    DESCRIPTION 
        "The value of svcPwSpeSaiiSvcId indicates the Service identifier on
        this switch-point node."
    ::= { svcPwSpeSaiiEntry 4 }

svcPwSpeSaiiOperSdpBind1 OBJECT-TYPE
    SYNTAX          SdpBindId
    MAX-ACCESS      read-only
    STATUS          current
    DESCRIPTION
        "The value of svcPwSpeSaiiOperSdpBind1 indicates the first operational
        SDP-bind on this switch-point node."
    ::= { svcPwSpeSaiiEntry 5 }

svcPwSpeSaiiOperSdpBind2 OBJECT-TYPE
    SYNTAX          SdpBindId
    MAX-ACCESS      read-only
    STATUS          current
    DESCRIPTION
        "The value of svcPwSpeSaiiOperSdpBind2 indicates the other operational
        SDP-bind on this switch-point node."
    ::= { svcPwSpeSaiiEntry 6 }

--
-- Service psuedo-wire switch-point node information by TAII
--
svcPwSpeTaiiTable OBJECT-TYPE
    SYNTAX          SEQUENCE OF SvcPwSpeTaiiEntry
    MAX-ACCESS      not-accessible
    STATUS          current
    DESCRIPTION
        "A table that contains pseudo-wire switch-point node information by
        Target Attachment Individual Identifier (TAII)."
    ::= { tmnxSvcObjs 117 }

svcPwSpeTaiiEntry OBJECT-TYPE
    SYNTAX          SvcPwSpeTaiiEntry
    MAX-ACCESS      not-accessible
    STATUS          current
    DESCRIPTION 
        "An entry that contains pseudo-wire switch-point node information by
        Target Attachment Individual Identifier (TAII)."
    INDEX           {
                       svcMSPwPeTaiiGlobalId,
                       svcMSPwPeTaiiPrefix,
                       svcMSPwPeTaiiAcId
                   }
    ::= { svcPwSpeTaiiTable 1 }

SvcPwSpeTaiiEntry ::=
    SEQUENCE {
        svcPwSpeTaiiSaiiGlobalId       TmnxPwGlobalIdOrZero,
        svcPwSpeTaiiSaiiPrefix         Unsigned32,
        svcPwSpeTaiiSaiiAcId           Unsigned32,
        svcPwSpeTaiiSvcId              TmnxServId,
        svcPwSpeTaiiOperSdpBind1       SdpBindId,
        svcPwSpeTaiiOperSdpBind2       SdpBindId
    }       


svcPwSpeTaiiSaiiGlobalId OBJECT-TYPE
    SYNTAX     TmnxPwGlobalIdOrZero
    MAX-ACCESS read-only
    STATUS     current
    DESCRIPTION
        "The value of svcPwSpeTaiiSaiiGlobalId indicates the global identifier
         of Source Attachment Individual Identifier (SAII) portion
         of the Generalized Id FEC element on switch-point node."
    ::= { svcPwSpeTaiiEntry 1 }

svcPwSpeTaiiSaiiPrefix OBJECT-TYPE
    SYNTAX     Unsigned32
    MAX-ACCESS read-only
    STATUS     current
    DESCRIPTION
        "The value of svcPwSpeTaiiSaiiPrefix indicates the prefix to the
         Source Attachment Individual Identifier (SAII) portion
         of the Generalized Id FEC element on switch-point node."
    ::= { svcPwSpeTaiiEntry 2 }

svcPwSpeTaiiSaiiAcId OBJECT-TYPE
    SYNTAX     Unsigned32
    MAX-ACCESS read-only
    STATUS     current
    DESCRIPTION
        "The value of svcPwSpeTaiiSaiiAcId indicates the attachment circuit
         identifier part of Target Attachment Individual Identifier (TAII)
         portion of the Generalized Id FEC element on switch-point node."
    ::= { svcPwSpeTaiiEntry 3 }

svcPwSpeTaiiSvcId OBJECT-TYPE
    SYNTAX          TmnxServId
    MAX-ACCESS      read-only
    STATUS          current
    DESCRIPTION 
        "The value of svcPwSpeTaiiSvcId indicates the Service identifier on
        this switch-point node."
    ::= { svcPwSpeTaiiEntry 4 }

svcPwSpeTaiiOperSdpBind1 OBJECT-TYPE
    SYNTAX          SdpBindId
    MAX-ACCESS      read-only
    STATUS          current
    DESCRIPTION
        "The value of svcPwSpeTaiiOperSdpBind1 indicates the first operational
         SDP-bind on this switch-point node."
    ::= { svcPwSpeTaiiEntry 5 }

svcPwSpeTaiiOperSdpBind2 OBJECT-TYPE
    SYNTAX          SdpBindId
    MAX-ACCESS      read-only
    STATUS          current
    DESCRIPTION
        "The value of svcPwSpeTaiiOperSdpBind2 indicates the other operational
         SDP-bind on this switch-point node."
    ::= { svcPwSpeTaiiEntry 6 }

--
--      The DHCP Lease State Overrides Table
--

svcDhcpLeaseOvrTable   OBJECT-TYPE
    SYNTAX      SEQUENCE OF SvcDhcpLeaseOvrEntry
    MAX-ACCESS  not-accessible
    STATUS      current
    DESCRIPTION
       "The svcDhcpLeaseOvrTable contains QoS (Quality of Service) overrides
        for DHCP lease states.

        Entries in this table are created and destroyed by the system.
        
        This table is a sparse augment of the svcDhcpLeaseTable: entries
        are created only for DHCP lease states 
        for which QoS overrides information is available."
    ::= { tmnxSvcObjs 118 }

svcDhcpLeaseOvrEntry   OBJECT-TYPE
    SYNTAX      SvcDhcpLeaseOvrEntry
    MAX-ACCESS  not-accessible
    STATUS      current
    DESCRIPTION
       "Each conceptual row represents QoS overrides information
        of a DHCP lease state."
    INDEX { svcId,
            svcDhcpLeaseCiAddrType,
            svcDhcpLeaseCiAddr,
            svcDhcpLeaseNextHopMacAddr,
            svcDhcpLeaseOvrDirection,
            svcDhcpLeaseOvrType,
            svcDhcpLeaseOvrTypeId,
            svcDhcpLeaseOvrTypeName
        }
    ::= { svcDhcpLeaseOvrTable 1 }

SvcDhcpLeaseOvrEntry ::= 
    SEQUENCE {
        svcDhcpLeaseOvrDirection        TDirectionIngEgr,
        svcDhcpLeaseOvrType             TQosOverrideType,
        svcDhcpLeaseOvrTypeId           Integer32,
        svcDhcpLeaseOvrTypeName         TNamedItemOrEmpty,
        svcDhcpLeaseOvrPIR              TQosQueuePIRRateOverride,
        svcDhcpLeaseOvrCIR              TQosQueueCIRRateOverride,
        svcDhcpLeaseOvrCBS              TBurstSizeBytesOvr,
        svcDhcpLeaseOvrMBS              TBurstSizeBytesOvr,
        svcDhcpLeaseOvrWrrWeight        THsmdaWrrWeightOverride,
        svcDhcpLeaseOvrSummedCIR        TruthValue
    }
        
svcDhcpLeaseOvrDirection OBJECT-TYPE
    SYNTAX          TDirectionIngEgr
    MAX-ACCESS      not-accessible
    STATUS          current
    DESCRIPTION     "The value of svcDhcpLeaseOvrDirection indicates if
                     this row specifies ingress or egress qos override 
                     parameters."
    ::= { svcDhcpLeaseOvrEntry 1 }

svcDhcpLeaseOvrType OBJECT-TYPE
    SYNTAX          TQosOverrideType
    MAX-ACCESS      not-accessible
    STATUS          current
    DESCRIPTION     "The value of svcDhcpLeaseOvrType indicates what field
                     has been overridden by this row."
    ::= { svcDhcpLeaseOvrEntry 2 }

svcDhcpLeaseOvrTypeId OBJECT-TYPE
    SYNTAX          Integer32
    MAX-ACCESS      not-accessible
    STATUS          current
    DESCRIPTION     "The value of svcDhcpLeaseOvrTypeId indicates the ID of
                     the queue/policer that has been overridden by this row.
                     
                     If the value of svcDhcpLeaseOvrType is not 'queue (1)'
                     or 'policer (2)', this field must be set to zero (0)."
    ::= { svcDhcpLeaseOvrEntry 3 }

svcDhcpLeaseOvrTypeName OBJECT-TYPE
    SYNTAX          TNamedItemOrEmpty
    MAX-ACCESS      not-accessible
    STATUS          current
    DESCRIPTION     "The value of svcDhcpLeaseOvrTypeName indicates the
                     name of the scheduler/arbiter that has been overridden by
                     this row.
                     
                     If the value of svcDhcpLeaseOvrType is not 
                     'arbiter (4)' or 'scheduler (5)', this field must be set to
                     zero (0)."
    ::= { svcDhcpLeaseOvrEntry 4 }

svcDhcpLeaseOvrPIR OBJECT-TYPE
    SYNTAX          TQosQueuePIRRateOverride
    MAX-ACCESS      read-only
    STATUS          current
    DESCRIPTION     "The value of svcDhcpLeaseOvrPIR indicates the PIR rate
                     in kbps allowed for the object overridden by this row."
    ::= { svcDhcpLeaseOvrEntry 5 }

svcDhcpLeaseOvrCIR OBJECT-TYPE
    SYNTAX          TQosQueueCIRRateOverride
    MAX-ACCESS      read-only
    STATUS          current
    DESCRIPTION     "The value of svcDhcpLeaseOvrCIR indicates the CIR rate
                     in kbps allowed for the object overridden by this row."
    ::= { svcDhcpLeaseOvrEntry 6 }

svcDhcpLeaseOvrCBS OBJECT-TYPE
    SYNTAX          TBurstSizeBytesOvr
    MAX-ACCESS      read-only
    STATUS          current
    DESCRIPTION     "The value of svcDhcpLeaseOvrCBS indicates the amount of
                     reserved buffer space (in bytes) for the object
                     overridden by this row."
    ::= { svcDhcpLeaseOvrEntry 7 }

svcDhcpLeaseOvrMBS OBJECT-TYPE
    SYNTAX          TBurstSizeBytesOvr
    MAX-ACCESS      read-only
    STATUS          current
    DESCRIPTION     "The value of svcDhcpLeaseOvrMBS indicates the maximum
                     amount of reserved buffer space (in bytes) for the object
                     overridden by this row."
    ::= { svcDhcpLeaseOvrEntry 8 }

svcDhcpLeaseOvrWrrWeight OBJECT-TYPE
    SYNTAX          THsmdaWrrWeightOverride
    MAX-ACCESS      read-only
    STATUS          current
    DESCRIPTION     
    "The value of svcDhcpLeaseOvrWrrWeight specifies the weight of this queue
     for the HSMDA scheduler.
     
     The weight determines how much bandwidth this queue gets out of the 
     total rate for the scheduling class.
     
     The value of svcDhcpLeaseOvrWrrWeight is only relevant if the value of
     svcDhcpLeaseOvrType is equal to 'queue', and if the queue specified in
     svcDhcpLeaseOvrTypeId is referenced in the value of 
     TIMETRA-QOS-MIB::tHsmdaWrrPolicyIncludeQueues of the Weighted Round Robin
     policy associated wit this PPP session."
    ::= { svcDhcpLeaseOvrEntry 9 }

svcDhcpLeaseOvrSummedCIR OBJECT-TYPE
    SYNTAX      TruthValue
    MAX-ACCESS  read-only
    STATUS      current
    DESCRIPTION
        "The value of svcDhcpLeaseOvrSummedCIR indicates if the CIR should
         be used as the summed CIR values of the children schedulers or queues.
         If set to 'true', the applicable scheduler CIR (svcDhcpLeaseOvrCIR)
         loses its meaning."
    ::= { svcDhcpLeaseOvrEntry 10 }

-- ----------------------------------------
-- b-VPLS Shortest Path Bridging (SPB) Table
-- ----------------------------------------

svcTlsSpbTableLastChanged  OBJECT-TYPE
    SYNTAX          TimeStamp
    MAX-ACCESS      read-only
    STATUS          current
    DESCRIPTION     "The value of svcTlsSpbTableLastChanged indicates the
                     sysUpTime at the time of the last modification
                     of svcTlsSpbTable.

                     If no changes were made to the entry since the last
                     re-initialization of the local network management subsystem,
                     then this object contains a zero value."
    ::= { tmnxSvcObjs 119 }

svcTlsSpbTable OBJECT-TYPE
    SYNTAX          SEQUENCE OF SvcTlsSpbEntry
    MAX-ACCESS      not-accessible
    STATUS          current
    DESCRIPTION     "svcTlsSpbTable contains entries for Shortest Path Bridging
                     in a VPLS service context." 
    ::= { tmnxSvcObjs 120 }

svcTlsSpbEntry    OBJECT-TYPE
    SYNTAX          SvcTlsSpbEntry
    MAX-ACCESS      not-accessible
    STATUS          current
    DESCRIPTION     "A Shortest Path Bridging entry in the svcTlsSpbTable."
    INDEX           { svcId }
    ::= { svcTlsSpbTable 1}

SvcTlsSpbEntry ::=    SEQUENCE {
    svcTlsSpbRowStatus           RowStatus,
    svcTlsSpbLastChanged         TimeStamp,
    svcTlsSpbIsisInstance        Integer32,
    svcTlsSpbFid                 TmnxSpbFid,
    svcTlsSpbL1BridgePriority    TmnxSpbBridgePriority,
    svcTlsSpbL1FwdTreeTopoUcast  INTEGER,
    svcTlsSpbAdminState          TmnxAdminState,
    svcTlsSpbL1FwdTreeTopoMcast  INTEGER,
    svcTlsSpbL1BridgeId            BridgeId,
    svcTlsSpbL1McastDesigBridgeId  BridgeId
}

svcTlsSpbRowStatus        OBJECT-TYPE
    SYNTAX          RowStatus
    MAX-ACCESS      read-create
    STATUS          current
    DESCRIPTION
        "The value of svcTlsSpbRowStatus is used for the creation and deletion
         of Shortest Path Bridging context in a VPLS service."
    ::= { svcTlsSpbEntry 1 }

svcTlsSpbLastChanged        OBJECT-TYPE
    SYNTAX          TimeStamp
    MAX-ACCESS      read-only
    STATUS          current
    DESCRIPTION
        "The value of svcTlsSpbLastChanged indicates the sysUpTime at the time
         of the last modification of this entry.
                     
         If no changes were made to the entry since the last re-initialization
         of the local network management subsystem, then this object contains a
         zero value."
    ::= { svcTlsSpbEntry 2 }

svcTlsSpbIsisInstance        OBJECT-TYPE
    SYNTAX          Integer32 (1024..2047)
    MAX-ACCESS      read-create
    STATUS          current
    DESCRIPTION
        "The value of svcTlsSpbIsisInstance specifies the
         ISIS-MIB::isisSysInstance to be used with this Shortest Path Bridging
         context in this VPLS service.
         
         An 'inconsistentValue' error is returned if value of 
         svcTlsSpbIsisInstance is set to a different value after the
         row-creation time."
    DEFVAL { 1024 }
    ::= { svcTlsSpbEntry 3 }

svcTlsSpbFid        OBJECT-TYPE
    SYNTAX          TmnxSpbFid
    MAX-ACCESS      read-create
    STATUS          current
    DESCRIPTION
        "The value of svcTlsSpbFid specifies forwarding database identifier
         associated with this Shortest Path Bridging context in this VPLS
         service.

         An 'inconsistentValue' error is returned if value of svcTlsSpbFid is
         set to a different value after the row-creation time."
    DEFVAL { 1 }
    ::= { svcTlsSpbEntry 4 }

svcTlsSpbL1BridgePriority        OBJECT-TYPE
    SYNTAX          TmnxSpbBridgePriority
    MAX-ACCESS      read-create
    STATUS          current
    DESCRIPTION
        "The value of svcTlsSpbL1BridgePriority specifies the level 1 four bit
         bridge priority associated with this Shortest Path Bridging context
         in this VPLS service."
    DEFVAL { 8 }
    ::= { svcTlsSpbEntry 5 }

svcTlsSpbL1FwdTreeTopoUcast        OBJECT-TYPE
    SYNTAX          INTEGER {
                       spf (0),
                       st  (1)
                    }
    MAX-ACCESS      read-create
    STATUS          current
    DESCRIPTION
        "The value of svcTlsSpbL1FwdTreeTopoUcast specifies level 1 unicast
         forwarding to follow the shortest path tree or to follow a single
         tree for this Shortest Path Bridging context in this VPLS service."
    DEFVAL { spf }
    ::= { svcTlsSpbEntry 6 }

svcTlsSpbAdminState OBJECT-TYPE
    SYNTAX      TmnxAdminState
    MAX-ACCESS  read-create
    STATUS      current
    DESCRIPTION
        "The svcTlsSpbAdminState indicates the  desired administrative state
         for Shortest Path Bridging on this VPLS service."
    DEFVAL { outOfService }
    ::= { svcTlsSpbEntry 7 }
     
svcTlsSpbL1FwdTreeTopoMcast        OBJECT-TYPE
    SYNTAX          INTEGER {
                       spf (0),
                       st  (1)
                    }
    MAX-ACCESS      read-only
    STATUS          current
    DESCRIPTION
        "The value of svcTlsSpbL1FwdTreeTopoMcast indicates level 1 multicast
         forwarding to follow the shortest path tree or to follow a single
         tree for this Shortest Path Bridging context in this VPLS service."
    ::= { svcTlsSpbEntry 8 }

svcTlsSpbL1BridgeId   OBJECT-TYPE
    SYNTAX      BridgeId
    MAX-ACCESS  read-only
    STATUS      current
    DESCRIPTION
        "The svcTlsSpbL1BridgeId indicates the level 1 designated bridge
         identifier for Shortest Path Bridging context on this VPLS service."
    ::= { svcTlsSpbEntry 9 }

svcTlsSpbL1McastDesigBridgeId   OBJECT-TYPE
    SYNTAX      BridgeId
    MAX-ACCESS  read-only
    STATUS      current
    DESCRIPTION
        "The svcTlsSpbL1McastDesigBridgeId indicates the level 1 designated
         bridge identifier for multicast traffic for Shortest Path Bridging
         on this VPLS service."
    ::= { svcTlsSpbEntry 10 }

-- ----------------------------------------
-- VLL BGP Table
-- ----------------------------------------

svcVllBgpTableLastChanged  OBJECT-TYPE
    SYNTAX          TimeStamp
    MAX-ACCESS      read-only
    STATUS          current
    DESCRIPTION     "The value of svcVllBgpTableLastChanged indicates the
                     sysUpTime at the time of the last modification
                     of svcVllBgpTable.

                     If no changes were made to the entry since the last
                     re-initialization of the local network management subsystem,
                     then this object contains a zero value."
    ::= { tmnxSvcObjs 121 }

svcVllBgpTable OBJECT-TYPE
    SYNTAX          SEQUENCE OF SvcVllBgpEntry
    MAX-ACCESS      not-accessible
    STATUS          current
    DESCRIPTION     "The svcVllBgpTable contains entries for BGP
                     in a VLL service context." 
    ::= { tmnxSvcObjs 122 }

svcVllBgpEntry    OBJECT-TYPE
    SYNTAX          SvcVllBgpEntry
    MAX-ACCESS      not-accessible
    STATUS          current
    DESCRIPTION     "The svcVllBgpEntry contains BGP related information for a
                     specific service."
    INDEX           { svcId }
    ::= { svcVllBgpTable 1}

SvcVllBgpEntry ::=    SEQUENCE {
    svcVllBgpRowStatus           RowStatus,
    svcVllBgpLastChanged         TimeStamp,
    svcVllBgpVsiRD               TmnxVPNRouteDistinguisher,
    svcVllBgpExportRteTarget     TNamedItemOrEmpty,
    svcVllBgpImportRteTarget     TNamedItemOrEmpty
}

svcVllBgpRowStatus        OBJECT-TYPE
    SYNTAX          RowStatus
    MAX-ACCESS      read-create
    STATUS          current
    DESCRIPTION     "The value of svcVllBgpRowStatus is used for the creation
                     and deletion of Shortest Path Bridging context in a VPLS
                     service."
    ::= { svcVllBgpEntry 1 }

svcVllBgpLastChanged        OBJECT-TYPE
    SYNTAX          TimeStamp
    MAX-ACCESS      read-only
    STATUS          current
    DESCRIPTION     "The value of svcVllBgpLastChanged indicates the 
                     sysUpTime at the time of the last modification of
                     this entry.
                     
                     If no changes were made to the entry since the last 
                     re-initialization of the local network management 
                     subsystem, then this object contains a zero value."
    ::= { svcVllBgpEntry 2 }

svcVllBgpVsiRD     OBJECT-TYPE
    SYNTAX          TmnxVPNRouteDistinguisher
    MAX-ACCESS      read-create
    STATUS          current
    DESCRIPTION     "The value of svcVllBgpVsiRD specifies the high-order
                     6 bytes used to compose the Virtual Switch Instance
                     identifier (VSI-id) to use for NLRI in BGP 
                     in this VLL service.
                     "
    DEFVAL          { '0000000000000000'H }
    ::= { svcVllBgpEntry 3 }

svcVllBgpExportRteTarget       OBJECT-TYPE
    SYNTAX          TNamedItemOrEmpty
    MAX-ACCESS      read-create
    STATUS          current
    DESCRIPTION     "The value of svcVllBgpExportRteTarget specifies the
                     extended community name for the default export policy
                     to use for BGP  in this VLL service.

                     This object cannot be set to a non-empty if
                     svcVllBgpExportRteTarget has a non-empty value, 
                     otherwise an 'inconsistentValue' error will be
                     returned."
    DEFVAL          { "" }
    ::= { svcVllBgpEntry 4 }

svcVllBgpImportRteTarget       OBJECT-TYPE
    SYNTAX          TNamedItemOrEmpty
    MAX-ACCESS      read-create
    STATUS          current
    DESCRIPTION     "The value of svcVllBgpImportRteTarget specifies the
                     extended community name for the default import policy
                     to use for BGP  in this VLL service.

                     This object cannot be set to a non-empty if
                     svcVllBgpImportRteTarget has a non-empty value, 
                     otherwise an 'inconsistentValue' error will be
                     returned."
    DEFVAL          { "" }
    ::= { svcVllBgpEntry 5 }


-- ----------------------
-- svcVllSiteIdTable
-- ----------------------
svcVllSiteIdTblLastChanged  OBJECT-TYPE
    SYNTAX          TimeStamp
    MAX-ACCESS      read-only
    STATUS          current
    DESCRIPTION
        "The value of svcVllSiteIdTblLastChanged indicates the sysUpTime
         at the time of the last modification of svcVllSiteIdTable.

         If no changes were made to the entry since the last re-initialization
         of the local network management subsystem, then this object contains a
         zero value."
    ::= { tmnxSvcObjs 123 }

svcVllSiteIdTable OBJECT-TYPE
    SYNTAX          SEQUENCE OF SvcVllSiteIdEntry
    MAX-ACCESS      not-accessible
    STATUS          current
    DESCRIPTION
        "This table maintains the information about different sites defined
         in a service."
    ::= { tmnxSvcObjs 124 } 
    
svcVllSiteIdEntry OBJECT-TYPE
    SYNTAX          SvcVllSiteIdEntry
    MAX-ACCESS      not-accessible
    STATUS          current
    DESCRIPTION
        "The svcVllSiteIdEntry contains information about a particular site in
         a specific service."
    INDEX { svcId, svcVllSiteIdName }
    ::= { svcVllSiteIdTable 1 }

SvcVllSiteIdEntry ::=
    SEQUENCE {
        svcVllSiteIdName             TNamedItem,
        svcVllSiteIdRowStatus        RowStatus,
        svcVllSiteIdLastChanged      TimeStamp,
        svcVllSiteIdAdminStatus      TmnxEnabledDisabled,
        svcVllSiteIdSiteId           TmnxSiteIdOrEmpty,
        svcVllSiteIdPortId           TmnxPortID,
        svcVllSiteIdEncapValue       TmnxEncapVal,
        svcVllSiteIdOperStatus       TSiteOperStatus,
        svcVllSiteIdDesignatedFwdr   TruthValue,
        svcVllSiteIdBootTimer        Integer32,
        svcVllSiteIdSiteActTimer     Integer32,
        svcVllSiteIdDfUpTime         Unsigned32,
        svcVllSiteIdDfChgCnt         Unsigned32,
        svcVllSiteIdTimerRemain      Unsigned32,
        svcVllSiteIdPreference       Unsigned32,
        svcVllSiteIdActTimerRemain   Unsigned32,
        svcVllSiteIdMinDnTimer     Integer32,
        svcVllSiteIdMinDnTimerRemain  Unsigned32
    }
    
svcVllSiteIdName OBJECT-TYPE
    SYNTAX       TNamedItem
    MAX-ACCESS   not-accessible
    STATUS       current
    DESCRIPTION     
        "The value of svcVllSiteIdName defines the name for the specific site."
    ::= { svcVllSiteIdEntry 1 }
 
svcVllSiteIdRowStatus OBJECT-TYPE
    SYNTAX       RowStatus
    MAX-ACCESS   read-create
    STATUS       current
    DESCRIPTION  
         "The value of svcVllSiteIdRowStatus is used for the creation and 
          deletion of rows in this table."
    ::= { svcVllSiteIdEntry 2 }   
    
svcVllSiteIdLastChanged OBJECT-TYPE
    SYNTAX       TimeStamp
    MAX-ACCESS   read-only
    STATUS       current
    DESCRIPTION  
        "The value of svcVllSiteIdLastChanged indicates the timestamp of
         last change to this row in svcVllSiteIdTable."
    ::= { svcVllSiteIdEntry 3 }  
    
svcVllSiteIdAdminStatus OBJECT-TYPE
    SYNTAX       TmnxEnabledDisabled
    MAX-ACCESS   read-create
    STATUS       current
    DESCRIPTION
        "The value of svcVllSiteIdAdminStatus specifies the administrative
         state of the site instance associated with this service."
    DEFVAL { disabled }
    ::= { svcVllSiteIdEntry 4 } 
    
svcVllSiteIdSiteId OBJECT-TYPE
    SYNTAX       TmnxSiteIdOrEmpty
    MAX-ACCESS   read-create
    STATUS       current
    DESCRIPTION
        "The value of svcVllSiteIdSiteId specifies the identifier for the site
         in this service."
    DEFVAL { -1 }
    ::= { svcVllSiteIdEntry 5 }   
   
svcVllSiteIdPortId OBJECT-TYPE
    SYNTAX       TmnxPortID
    MAX-ACCESS   read-create
    STATUS       current
    DESCRIPTION
        "The value of svcVllSiteIdPortId specifies the port associated with
         this site.

         The default value for this object indicates an invalid port.
         
         An 'inconsistentValue' error is returned when svcVllSiteIdPortId is
         set to non-default and svcVllSiteIdEncapValue is set to its default
         value or when svcVllSiteIdPortId is set to its default value and 
         svcVllSiteIdEncapValue is set to non-default value."
    DEFVAL { '1E000000'H }
    ::= { svcVllSiteIdEntry 6 } 
    
svcVllSiteIdEncapValue OBJECT-TYPE
    SYNTAX       TmnxEncapVal
    MAX-ACCESS   read-create
    STATUS       current
    DESCRIPTION
        "The value of svcVllSiteIdEncapValue specifies the encap-value of the
         port associated with this site.

         An 'inconsistentValue' error is returned when svcVllSiteIdPortId is
         set to non-default and svcVllSiteIdEncapValue is set to its default
         value or when svcVllSiteIdPortId is set to its default value and 
         svcVllSiteIdEncapValue is set to non-default value."
    DEFVAL { 0 }
    ::= { svcVllSiteIdEntry 7 }
    
svcVllSiteIdOperStatus       OBJECT-TYPE
    SYNTAX       TSiteOperStatus
    MAX-ACCESS   read-only
    STATUS       current
    DESCRIPTION
        "The value of the svcVllSiteIdOperStatus indicates the operational
         status of the site."
    ::= { svcVllSiteIdEntry 8 }
    
svcVllSiteIdDesignatedFwdr   OBJECT-TYPE
    SYNTAX       TruthValue
    MAX-ACCESS   read-only
    STATUS       current
    DESCRIPTION
        "The value of the svcVllSiteIdDesignatedFwdr indicates whether this
         site has been declared as 'designated-forwarder' depending on the
         result of the BGP election."
    ::= { svcVllSiteIdEntry 9 }
    
svcVllSiteIdBootTimer OBJECT-TYPE
    SYNTAX       Integer32 (-1|0..600)
    UNITS        "seconds"
    MAX-ACCESS   read-create
    STATUS       current
    DESCRIPTION
        "The value of svcVllSiteIdBootTimer specifies how long the
        system waits after a node reboot before running the DF (designated-
        forwarder) election algorithm.

        When this object is set to default value, system uses value of
        TIMETRA-MC-REDUNDANCY-MIB::tmnxMcRedBgpMultiHomeBootTimer object."
    DEFVAL { -1 }
    ::= { svcVllSiteIdEntry 10 }

svcVllSiteIdSiteActTimer OBJECT-TYPE
    SYNTAX       Integer32 (-1|0..100)
    UNITS        "seconds"
    MAX-ACCESS   read-create
    STATUS       current
    DESCRIPTION
        "The value of svcVllSiteIdSiteActTimer specifies the time-period
        the system keeps the local sites in standby status, waiting for BGP
        updates from remote PEs before running the DF (designated-forwarder)
        election algorithm to decide whether the site should be unblocked.

        When this object is set to default value, system uses value of
        TIMETRA-MC-REDUNDANCY-MIB::tmnxMcRedBgpMultiHomeSiteTimer object."
    DEFVAL { -1 }
    ::= { svcVllSiteIdEntry 11 }

svcVllSiteIdDfUpTime OBJECT-TYPE
    SYNTAX       Unsigned32
    UNITS        "seconds"
    MAX-ACCESS   read-only
    STATUS       current
    DESCRIPTION  
        "The value of svcVllSiteIdDfUpTime indicates the uptime of the
         designated forwarder for this site."
    ::= { svcVllSiteIdEntry 12 }  
    
svcVllSiteIdDfChgCnt OBJECT-TYPE
    SYNTAX       Unsigned32
    MAX-ACCESS   read-only
    STATUS       current
    DESCRIPTION  
        "The value of svcVllSiteIdDfChgCnt indicates the number of times
         designated forwarder has changed."
    ::= { svcVllSiteIdEntry 13 }  
    
svcVllSiteIdTimerRemain OBJECT-TYPE
    SYNTAX       Unsigned32
    UNITS        "seconds"
    MAX-ACCESS   read-only
    STATUS       current
    DESCRIPTION
        "The value of svcVllSiteIdTimerRemain indicates remaining time
        in the boot timer for this site."
    ::= { svcVllSiteIdEntry 14 }

svcVllSiteIdPreference OBJECT-TYPE
    SYNTAX       Unsigned32 (0..65535)
    MAX-ACCESS   read-create
    STATUS       current
    DESCRIPTION
        "The value of svcVllSiteIdPreference specifies preference value
        to advertise in the NLRI L2 extended community for this site.

        A value of zero for this object indicates preference value in the L2
        extended community of BGP-MH or BGP-VPWS NLRIs will not be trasmitted."
    DEFVAL { 0 }
    ::= { svcVllSiteIdEntry 15 }

svcVllSiteIdActTimerRemain OBJECT-TYPE
    SYNTAX       Unsigned32
    UNITS        "seconds"
    MAX-ACCESS   read-only
    STATUS       current
    DESCRIPTION
        "The value of svcVllSiteIdTimerRemain indicates remaining time
        in the activation timer for this site."
    ::= { svcVllSiteIdEntry 16 }

svcVllSiteIdMinDnTimer OBJECT-TYPE
    SYNTAX       Integer32 (-1|0..100)
    UNITS        "seconds"
    MAX-ACCESS   read-create
    STATUS       current
    DESCRIPTION
        "The value of svcVllSiteIdMinDnTimer specifies the minimum
        time-period the system keeps the site down when a site goes down.

        When this object is set to default value, system uses value of
        TIMETRA-MC-REDUNDANCY-MIB::tmnxMcRedBgpMHSiteMinDnTimer object."
    DEFVAL { -1 }
    ::= { svcVllSiteIdEntry 21 }

svcVllSiteIdMinDnTimerRemain OBJECT-TYPE
    SYNTAX       Unsigned32
    UNITS        "seconds"
    MAX-ACCESS   read-only
    STATUS       current
    DESCRIPTION
        "The value of svcVllSiteIdMinDnTimerRemain indicates remaining time
        in the svcVllSiteIdMinDnTimer for this site."
    ::= { svcVllSiteIdEntry 22 }
 
-- ----------------------------------------
-- P2MP VPLS Table
-- ----------------------------------------

svcTlsPmsiTableLastChanged  OBJECT-TYPE
    SYNTAX          TimeStamp
    MAX-ACCESS      read-only
    STATUS          current
    DESCRIPTION
        "The value of svcTlsPmsiTableLastChanged indicates the
         sysUpTime at the time of the last modification
         of svcTlsPmsiTable.

         If no changes were made to the entry since the last
         re-initialization of the local network management subsystem,
         then this object contains a zero value."
    ::= { tmnxSvcObjs 125 }

svcTlsPmsiTable OBJECT-TYPE
    SYNTAX          SEQUENCE OF SvcTlsPmsiEntry
    MAX-ACCESS      not-accessible
    STATUS          current
    DESCRIPTION
        "The svcTlsPmsiTable contains entries for provider-tunnel
         in a VPLS service context." 
    ::= { tmnxSvcObjs 126 }

svcTlsPmsiEntry    OBJECT-TYPE
    SYNTAX          SvcTlsPmsiEntry
    MAX-ACCESS      not-accessible
    STATUS          current
    DESCRIPTION
        "The svcTlsPmsiEntry contains provider-tunnel related objects."
    INDEX           { svcId }
    ::= { svcTlsPmsiTable 1}

SvcTlsPmsiEntry ::=    SEQUENCE {
    svcTlsPmsiRowStatus              RowStatus,
    svcTlsPmsiLastChanged            TimeStamp,
    svcTlsIPmsiAdminState            TmnxAdminState,
    svcTlsIPmsiDataDelayIntvl        Integer32,
    svcTlsIPmsiType                  INTEGER,
    svcTlsIPmsiLspTmpl               TNamedItemOrEmpty,
    svcTlsIPmsiRootAndLeaf           TruthValue,
    svcTlsIPmsiRemainDataDelayIntvl  Integer32,
    svcTlsIPmsiLspName               TLNamedItemOrEmpty
}

svcTlsPmsiRowStatus        OBJECT-TYPE
    SYNTAX          RowStatus
    MAX-ACCESS      read-create
    STATUS          current
    DESCRIPTION
        "The value of svcTlsPmsiRowStatus is used for the creation and
         deletion of provider-tunnel context in a VPLS service."
    ::= { svcTlsPmsiEntry 1 }

svcTlsPmsiLastChanged        OBJECT-TYPE
    SYNTAX          TimeStamp
    MAX-ACCESS      read-only
    STATUS          current
    DESCRIPTION
        "The value of svcTlsPmsiLastChanged indicates the sysUpTime at the
         time of the last modification of this entry.
                     
         If no changes were made to the entry since the last re-initialization
         of the local network management subsystem, then this object contains a
         zero value."
    ::= { svcTlsPmsiEntry 2 }

svcTlsIPmsiAdminState OBJECT-TYPE
    SYNTAX      TmnxAdminState
    MAX-ACCESS  read-create
    STATUS      current
    DESCRIPTION
        "The value of the object svcTlsIPmsiAdminState specifies the
         administrative state of the inclusive provider tunnel in this service.
         
         An 'inconsistentValue' error is retuned when attempting to set
         svcTlsIPmsiAdminState to 'inService' when svcTlsIPmsiType is set to
         'none' or svcTlsIPmsiLspTmpl is set to its default value."
    DEFVAL { outOfService }
    ::= { svcTlsPmsiEntry 3 }

svcTlsIPmsiDataDelayIntvl OBJECT-TYPE
    SYNTAX      Integer32 (3..180)
    UNITS       "seconds"
    MAX-ACCESS  read-create
    STATUS      current
    DESCRIPTION
        "The value of the object svcTlsIPmsiDataDelayIntvl specifies the
         data delay interval associated for the inclusive provider tunnel in
         this service."
    DEFVAL { 15 }
    ::= { svcTlsPmsiEntry 4 }

svcTlsIPmsiType OBJECT-TYPE
    SYNTAX      INTEGER {
                    none (0),
                    rsvp (1),
                    ldp  (2)
                }
    MAX-ACCESS  read-create
    STATUS      current
    DESCRIPTION
        "The value of the object svcTlsIPmsiType specifies the type of protocol
         supported for the inclusive provider tunnel in this service."
    DEFVAL { none }
    ::= { svcTlsPmsiEntry 5 }

svcTlsIPmsiLspTmpl OBJECT-TYPE
    SYNTAX      TNamedItemOrEmpty
    MAX-ACCESS  read-create
    STATUS      current
    DESCRIPTION
        "The value of the object svcTlsIPmsiLspTmpl specifies the
         name of the TIMETRA-MPLS-MIB::vRtrMplsLspTemplateName to be used
         for signalling inclusive provider tunnel in this service.

         An 'inconsistentValue' error is returned if svcTlsIPmsiLspTmpl does
         not exist in TIMETRA-MPLS-MIB::vRtrMplsLspTemplateTable.
         
         An 'inconsistentValue' error is returned if this object is set to 
         non-default when svcTlsIPmsiType is set to 'none'."
    DEFVAL { ''H }
    ::= { svcTlsPmsiEntry 6 }

svcTlsIPmsiRootAndLeaf OBJECT-TYPE
    SYNTAX      TruthValue
    MAX-ACCESS  read-create
    STATUS      current
    DESCRIPTION
        "The value of the object svcTlsIPmsiRootAndLeaf specifies
         whether the node acts as both a root and leaf or only act as a leaf
         for P2MP LSP."
    DEFVAL { false }
    ::= { svcTlsPmsiEntry 7 }

svcTlsIPmsiRemainDataDelayIntvl OBJECT-TYPE
    SYNTAX      Integer32
    UNITS       "seconds"
    MAX-ACCESS  read-only
    STATUS      current
    DESCRIPTION
        "The value of the object svcTlsIPmsiRemainDataDelayIntvl indicates the
         remaining data delay interval for the inclusive provider tunnel
         in this service."
    ::= { svcTlsPmsiEntry 8 }

svcTlsIPmsiLspName OBJECT-TYPE
    SYNTAX      TLNamedItemOrEmpty
    MAX-ACCESS  read-only
    STATUS      current
    DESCRIPTION
        "The value of the object svcTlsIPmsiLspTmpl indicates the
         LSP name used for signalling inclusive provider tunnel in this
         service."
    ::= { svcTlsPmsiEntry 9 }

-- ----------------------------------------------------------------------------
-- DHCP Lease State WPP Table
-- ----------------------------------------------------------------------------
svcDhcpLeaseWppTable OBJECT-TYPE
    SYNTAX          SEQUENCE OF SvcDhcpLeaseWppEntry
    MAX-ACCESS      not-accessible
    STATUS          current
    DESCRIPTION
        "The svcDhcpLeaseWppTable is a sparse augment of the svcDhcpLeaseTable.
        
         It contains Web Portal Protocol (WPP) information associated with
         DHCP lease states."
    ::= { tmnxSvcObjs 127 }

svcDhcpLeaseWppEntry OBJECT-TYPE
    SYNTAX          SvcDhcpLeaseWppEntry  
    MAX-ACCESS      not-accessible
    STATUS          current
    DESCRIPTION     
        "Each row entry contains WPP information associated with a particular
         DHCP lease state."
    INDEX { svcId,
            svcDhcpLeaseCiAddrType,
            svcDhcpLeaseCiAddr,
            svcDhcpLeaseNextHopMacAddr }
    ::= { svcDhcpLeaseWppTable 1 }

SvcDhcpLeaseWppEntry ::=
    SEQUENCE {
        svcDhcpLeaseWppState             INTEGER,
        svcDhcpLeaseWppPortalRouter      TmnxVRtrIDOrZero,
        svcDhcpLeaseWppPortalName        TNamedItemOrEmpty,
        svcDhcpLeaseWppRestoreOnDiscon   TruthValue,
        svcDhcpLeaseWppIsTriggered       TruthValue,
        svcDhcpLeaseWppInitialSubProfile TNamedItemOrEmpty,
        svcDhcpLeaseWppInitialSLAProfile TNamedItemOrEmpty,
        svcDhcpLeaseWppInitialAppProfile TNamedItemOrEmpty,
        svcDhcpLeaseWppLocalUserDb       TNamedItemOrEmpty,
        svcDhcpLeaseWppAuthPolicy         TNamedItemOrEmpty
    }

svcDhcpLeaseWppState OBJECT-TYPE
    SYNTAX          INTEGER {
                        initial                          (1),
                        registering                      (2),
                        registered                       (3),
                        authenticating                   (4),
                        authenticated                    (5)
                    }
    MAX-ACCESS      read-only
    STATUS          current
    DESCRIPTION
        "The value of svcDhcpLeaseWppState indicates the
         WPP state for this lease state."
    ::= { svcDhcpLeaseWppEntry 1 }

svcDhcpLeaseWppPortalRouter OBJECT-TYPE
    SYNTAX          TmnxVRtrIDOrZero
    MAX-ACCESS      read-only
    STATUS          current
    DESCRIPTION
        "The value of svcDhcpLeaseWppPortalRouter indicates the
         routing instance identifier of the WPP portal used for this lease state.
         
         The value zero indicates that the WPP portal is currently unknown."
    ::= { svcDhcpLeaseWppEntry 2 }

svcDhcpLeaseWppPortalName OBJECT-TYPE
    SYNTAX          TNamedItemOrEmpty
    MAX-ACCESS      read-only
    STATUS          current
    DESCRIPTION     
        "The value of svcDhcpLeaseWppPortalName indicates the
         name of the WPP portal used for this lease state.
     
         The value zero indicates that the WPP portal is currently unknown.
         
         The values of svcDhcpLeaseWppPortalRouter and svcDhcpLeaseWppPortalName
         refer to a conceptual row 
         in the TIMETRA-WEB-PORTAL-MIB::tmnxWppPortalTable."
    ::= { svcDhcpLeaseWppEntry 3 }

svcDhcpLeaseWppRestoreOnDiscon OBJECT-TYPE
    SYNTAX          TruthValue
    MAX-ACCESS      read-only
    STATUS          current
    DESCRIPTION     
        "The value of svcDhcpLeaseWppRestoreOnDiscon indicates whether
         the initial profiles must be restored after this lease state has
         disconnected."
    ::= { svcDhcpLeaseWppEntry 4 }

svcDhcpLeaseWppIsTriggered OBJECT-TYPE
    SYNTAX                 TruthValue
    MAX-ACCESS      read-only
    STATUS          current
    DESCRIPTION     
        "The value of svcDhcpLeaseWppIsTriggered indicates whether
         the creation of this lease state is triggered by the portal."
    ::= { svcDhcpLeaseWppEntry 5 }
    
svcDhcpLeaseWppInitialSubProfile OBJECT-TYPE
    SYNTAX           TNamedItemOrEmpty
    MAX-ACCESS      read-only
    STATUS          current
    DESCRIPTION     
        "The value of svcDhcpLeaseWppInitialSubProfile indicates the
         initial subscriber profile that probably will be used when
         the initial profiles must be restored.

         It is possible that another initial subscriber profile will
         be used due to recent changes in the svcDhcpLeaseWppLocalUserDb
         user database."
    ::= { svcDhcpLeaseWppEntry 6 }
    
svcDhcpLeaseWppInitialSLAProfile OBJECT-TYPE
    SYNTAX          TNamedItemOrEmpty
    MAX-ACCESS      read-only
    STATUS          current
    DESCRIPTION     
        "The value of svcDhcpLeaseWppInitialSLAProfile indicates the
         initial SLA profile that probably will be used when the
         initial profiles must be restored.

         It is possible that another initial SLA profile will
         be used due to recent changes in the svcDhcpLeaseWppLocalUserDb
         user database."
    ::= { svcDhcpLeaseWppEntry 7 }
    
svcDhcpLeaseWppInitialAppProfile OBJECT-TYPE
    SYNTAX           TNamedItemOrEmpty
    MAX-ACCESS      read-only
    STATUS          current
    DESCRIPTION     
        "The value of svcDhcpLeaseWppInitialAppProfile indicates the
         initial application profile that probably will be used when the
         initial profiles must be restored.

         It is possible that another initial application profile will
         be used due to recent changes in the svcDhcpLeaseWppLocalUserDb
         user database."
    ::= { svcDhcpLeaseWppEntry 8 }
    
svcDhcpLeaseWppLocalUserDb OBJECT-TYPE
    SYNTAX                 TNamedItemOrEmpty
    MAX-ACCESS      read-only
    STATUS          current
    DESCRIPTION     
        "The value of svcDhcpLeaseWppLocalUserDb indicates the
         the user database that will be used to retrieve the initial profiles
         for this lease state when these must be restored."
    ::= { svcDhcpLeaseWppEntry 9 }
        
svcDhcpLeaseWppAuthPolicy OBJECT-TYPE
    SYNTAX          TNamedItemOrEmpty
    MAX-ACCESS      read-only
    STATUS          current
    DESCRIPTION     
        "The value of svcDhcpLeaseWppAuthPolicy indicates
         the Radius authentication policy used for this lease state."
    ::= { svcDhcpLeaseWppEntry 10 }
        
--
--      The Group Interface (internal) SAP configuration Table
--
--      Sparse augment of the TIMETRA-SERV-MIB::iesIfTable

svcIfSapCfgTableLastChanged  OBJECT-TYPE
    SYNTAX          TimeStamp
    MAX-ACCESS      read-only
    STATUS          current
    DESCRIPTION
        "The value of svcIfSapCfgTableLastChanged indicates the
         sysUpTime at the time of the last modification
         of svcIfSapCfgTable.

         If no changes were made to the entry since the last
         re-initialization of the local network management subsystem,
         then this object contains a zero value."
    ::= { tmnxSvcObjs 128 }

svcIfSapCfgTable   OBJECT-TYPE
    SYNTAX      SEQUENCE OF SvcIfSapCfgEntry
    MAX-ACCESS  not-accessible
    STATUS      current
    DESCRIPTION
       "The svcIfSapCfgTable contains objects to configure 
        (internal) SAP parameters for applicable group interfaces.
        
        Conceptual rows in this table are created and destroyed by the system.
        
        The system automatically creates a row in this table for each
        applicable row in the TIMETRA-SERV-MIB::iesIfTable;
        currently, applicable rows have the value of iesIfType
        is equal to 'group' and the value of 
        iesIfGroupInterfaceType is equal to 'lns' or 'softGre'. 
        
        Deletion of such a row in the iesIfTable results in the same fate
        for the corresponding row in this table."
    ::= { tmnxSvcObjs 129 }

svcIfSapCfgEntry OBJECT-TYPE
    SYNTAX      SvcIfSapCfgEntry
    MAX-ACCESS  not-accessible
    STATUS      current
    DESCRIPTION
        "SAP configuration applicable to internal SAP's associated
         with a specific group interface.
        
         Unlike regular subscriber traffic, that enters the system through
         Service Access Points (SAP) on a group-interface, 
         some user traffic enters the system through a plain layer 3 interface; 
         this traffic is relayed for processing to an ISA MDA; 
         it re-enters through an internal SAP on an internal group interface;
         this entry allows to configure certain SAP parameters for
         those internal SAP's.
         
         Current examples of such traffic are
         - traffic for PPP subscriber sessions terminated by the LNS function,
         - Wifi offload traffic, entering the system through a Soft-GRE tunnel."
    INDEX { svcId, iesIfIndex }
    ::= { svcIfSapCfgTable 1 }

SvcIfSapCfgEntry ::=
    SEQUENCE {
        svcIfSapCfgLastMgmtChange        TimeStamp,
        svcIfSapCfgDescription           TItemDescription,
        svcIfSapCfgDefSubProfile         TNamedItemOrEmpty,
        svcIfSapCfgDefSlaProfile         TNamedItemOrEmpty,
        svcIfSapCfgDefAppProfile         TNamedItemOrEmpty,
        svcIfSapCfgSubIdentPolicy        TNamedItemOrEmpty,
        svcIfSapCfgDefSubIdent           TmnxDefSubIdSource,
        svcIfSapCfgDefSubIdentString     DisplayString,
        svcIfSapCfgDefFilterProfile      TNamedItemOrEmpty,
        svcIfSapCfgAntiSpoof             INTEGER
    }

svcIfSapCfgLastMgmtChange OBJECT-TYPE
    SYNTAX      TimeStamp
    MAX-ACCESS  read-only
    STATUS      current
    DESCRIPTION
        "The value of svcIfSapCfgLastMgmtChange indicates the sysUpTime at
         the time of the most recent management-initiated change to this
         table row."
    ::= { svcIfSapCfgEntry 1 }

svcIfSapCfgDescription OBJECT-TYPE
    SYNTAX      TItemDescription
    MAX-ACCESS  read-create
    STATUS      current
    DESCRIPTION
       "The value of svcIfSapCfgDescription specifies the
        description of this conceptual row."
    DEFVAL { "" }
    ::= { svcIfSapCfgEntry 2 }

svcIfSapCfgDefSubProfile OBJECT-TYPE
    SYNTAX      TNamedItemOrEmpty
    MAX-ACCESS  read-create
    STATUS      current
    DESCRIPTION
       "The value of svcIfSapCfgDefSubProfile specifies the
        default subscriber profile."
    DEFVAL { "" }
    ::= { svcIfSapCfgEntry 3 }

svcIfSapCfgDefSlaProfile OBJECT-TYPE
    SYNTAX      TNamedItemOrEmpty
    MAX-ACCESS  read-create
    STATUS      current
    DESCRIPTION
       "The value of svcIfSapCfgDefSlaProfile specifies the
        default SLA profile."
    DEFVAL { "" }
    ::= { svcIfSapCfgEntry 4 }

svcIfSapCfgDefAppProfile OBJECT-TYPE
    SYNTAX      TNamedItemOrEmpty
    MAX-ACCESS  read-create
    STATUS      current
    DESCRIPTION
       "The value of svcIfSapCfgDefSlaProfile specifies the
        default application profile."
    DEFVAL { "" }
    ::= { svcIfSapCfgEntry 5 }

svcIfSapCfgSubIdentPolicy OBJECT-TYPE
    SYNTAX      TNamedItemOrEmpty
    MAX-ACCESS  read-create
    STATUS      current
    DESCRIPTION
       "The value of svcIfSapCfgSubIdentPolicy specifies the
        subscriber identification policy."
    DEFVAL { "" }
    ::= { svcIfSapCfgEntry 6 }

svcIfSapCfgDefSubIdent OBJECT-TYPE
    SYNTAX      TmnxDefSubIdSource
    MAX-ACCESS  read-create
    STATUS      current
    DESCRIPTION
       "The value of svcIfSapCfgDefSubIdent specifies the
        default subscriber identification.
        This value is used in case no other source (like Radius) provides a 
        subscriber identification string.

        If the value of this object is set to 'useSapId', the SAP-id will
        be used as the default subscriber identification string; in this case,
        svcIfSapCfgDefSubIdentString must contain the empty string, so any
        non-empty string in svcIfSapCfgDefSubIdentString will be set to an 
        empty string.

        If the value of this object is set to 'useAutoId', the auto-generated
        subscriber identification string, as defined in
        tmnxSubMgmtAutoSubIdObjs, is used as the default subscriber
        identification string. In this case, svcIfSapCfgDefSubIdentString must
        contain the empty string, so any non-empty string in
        svcIfSapCfgDefSubIdentString will be set to an empty string.

        If the value of this object is set to 'useString', the value of
        svcIfSapCfgDefSubIdentString will be used as the default subscriber 
        identification string; in this case, an empty 
        svcIfSapCfgDefSubIdentString means that there is no default subscriber 
        identification configured."
    DEFVAL { useString }
    ::= { svcIfSapCfgEntry 7 }

svcIfSapCfgDefSubIdentString OBJECT-TYPE
    SYNTAX      DisplayString (SIZE (0..32))
    MAX-ACCESS  read-create
    STATUS      current
    DESCRIPTION
       "The value of svcIfSapCfgDefSubIdentString specifies the
        default subscriber identification string."
    DEFVAL { "" }
    ::= { svcIfSapCfgEntry 8 }

svcIfSapCfgDefFilterProfile OBJECT-TYPE
    SYNTAX      TNamedItemOrEmpty
    MAX-ACCESS  read-create
    STATUS      current
    DESCRIPTION 
       "The value of the object svcIfSapCfgDefFilterProfile specifies the
        default filter profile. The specified filter
        profile needs to exists in the
        TIMETRA-SUBSCRIBER-MGMT-MIB::tmnxSubFilterProfileTable."
    DEFVAL { "" }
    ::= { svcIfSapCfgEntry 9 }

svcIfSapCfgAntiSpoof OBJECT-TYPE
    SYNTAX      INTEGER {
                    ipMac (3),
                    nhMac (4)
                }
    MAX-ACCESS  read-create
    STATUS      current
    DESCRIPTION
        "The value of svcIfSapCfgAntiSpoof indicates the type of
         anti-spoofing for WLAN-GW group-interfaces.
         
         ipMac (3)    - Interface is set to IP-MAC anti-spoofing, which is
                        the default setting for WLAN-GW group-interfaces.
         
         nhMac (4)    - Interface is set to NH-MAC anti-spoofing."
    DEFVAL { ipMac }
    ::= { svcIfSapCfgEntry 10 }


-- --------------------------------------------
-- VPLS SPB Control svcs to User services table
-- --------------------------------------------
svcTlsSpbUserSvcTable OBJECT-TYPE
    SYNTAX          SEQUENCE OF SvcTlsSpbUserSvcEntry
    MAX-ACCESS      not-accessible
    STATUS          current
    DESCRIPTION
        "The svcTlsSpbUserSvcTable contains entries for user VPLS for
        each control VPLS per forwarding data-base identifier."
    ::= { tmnxSvcObjs 130 }

svcTlsSpbUserSvcEntry    OBJECT-TYPE
    SYNTAX          SvcTlsSpbUserSvcEntry
    MAX-ACCESS      not-accessible
    STATUS          current
    DESCRIPTION
        "The svcTlsSpbUserSvcEntry contains user VPLS information for
        each control VPLS per forwarding data-base identfier."
    INDEX           { svcId, svcTlsSpbFid, svcTlsSpbUserSvcId }
    ::= { svcTlsSpbUserSvcTable 1}

SvcTlsSpbUserSvcEntry ::=    SEQUENCE {
    svcTlsSpbUserSvcId              TmnxServId,
    svcTlsSpbUserSvcLastUpdate      TimeStamp
}

svcTlsSpbUserSvcId OBJECT-TYPE
    SYNTAX          TmnxServId
    MAX-ACCESS      not-accessible
    STATUS          current
    DESCRIPTION
        "The value of svcTlsSpbUserSvcId is used for the creation and
         deletion of provider-tunnel context in a VPLS service."
    ::= { svcTlsSpbUserSvcEntry 1 }

svcTlsSpbUserSvcLastUpdate OBJECT-TYPE
    SYNTAX      TimeStamp
    MAX-ACCESS  read-only
    STATUS      current
    DESCRIPTION
        "The value of svcTlsSpbUserSvcLastUpdate indicates the sysUpTime at
         the time this entry was last updated."
    ::= { svcTlsSpbUserSvcEntry 2 }

-- ------------------------------------
-- TLS SPB FDB Table
-- ------------------------------------
tlsSpbFdbTable OBJECT-TYPE
    SYNTAX          SEQUENCE OF TlsSpbFdbEntry
    MAX-ACCESS      not-accessible
    STATUS          current
    DESCRIPTION
        "The tlsSpbFdbTable contains user VPLS Shortest Path Bridging (SPB)
        Forwarding Data-Base (FDB) information."
    ::= { tmnxSvcObjs 131 }

tlsSpbFdbEntry OBJECT-TYPE
    SYNTAX          TlsSpbFdbEntry
    MAX-ACCESS      not-accessible
    STATUS          current
    DESCRIPTION     
        "The tlsSpbFdbEntry contains a specific user VPLS SPB FDB
        mac-address related information."
    INDEX           { svcId, tlsSpbFdbMacAddr }
    ::= { tlsSpbFdbTable 1 }

TlsSpbFdbEntry ::=
    SEQUENCE {
        tlsSpbFdbMacAddr           MacAddress,
        tlsSpbFdbLocale            TmnxSpbFdbLocale,
        tlsSpbFdbPortId            TmnxPortID,
        tlsSpbFdbEncapValue        TmnxEncapVal,
        tlsSpbFdbSdpId             SdpId,
        tlsSpbFdbVcId              Unsigned32,
        tlsSpbFdbState             TmnxSpbFdbState,
        tlsSpbFdbMLocale           TmnxSpbFdbLocale,
        tlsSpbFdbMPortId           TmnxPortID,
        tlsSpbFdbMEncapValue       TmnxEncapVal,
        tlsSpbFdbMSdpId            SdpId,
        tlsSpbFdbMVcId             Unsigned32,
        tlsSpbFdbMState            TmnxSpbFdbState
    }

tlsSpbFdbMacAddr OBJECT-TYPE
    SYNTAX          MacAddress
    MAX-ACCESS      not-accessible
    STATUS          current
    DESCRIPTION     
        "The value of the object tlsSpbFdbMacAddr indicates the
         48-bit IEEE 802.3 MAC address."
    ::= { tlsSpbFdbEntry 1 }

tlsSpbFdbLocale OBJECT-TYPE
    SYNTAX          TmnxSpbFdbLocale
    MAX-ACCESS      read-only
    STATUS          current
    DESCRIPTION     
        "The value of the object tlsSpbFdbLocale indicates locality of the
        this FDB entry."
    ::= { tlsSpbFdbEntry 4 }

tlsSpbFdbPortId OBJECT-TYPE
    SYNTAX          TmnxPortID
    MAX-ACCESS      read-only
    STATUS          current
    DESCRIPTION     
        "The value of tlsSpbFdbPortId indicates the port-id of the SAP for this
         FDB entry.

         This object is valid only when tlsSpbFdbLocale is set to 'sap'.
         This object is otherwise insignificant and should contain a value
         of 0."
    ::= { tlsSpbFdbEntry 5 }

tlsSpbFdbEncapValue OBJECT-TYPE
    SYNTAX          TmnxEncapVal
    MAX-ACCESS      read-only
    STATUS          current
    DESCRIPTION     
        "The value of tlsSpbFdbEncapValue indicates the encap-value of the SAP
         for this FDB entry.
         
         This object is valid only when tlsSpbFdbLocale is set to 'sap'.
         This object is otherwise insignificant and should contain a value
         of 0."
    ::= { tlsSpbFdbEntry 6 }

tlsSpbFdbSdpId OBJECT-TYPE
    SYNTAX          SdpId
    MAX-ACCESS      read-only
    STATUS          current
    DESCRIPTION     
        "The value of tlsSpbFdbSdpId indicates the sdp identifier of the 
         SDP binding of the SDP for this FDB entry.

         This object is valid only when tlsSpbFdbLocale is set to 'sdp'.
         This object is other-wise insignificant and should contain a value
         of 0."
    ::= { tlsSpbFdbEntry 7 }

tlsSpbFdbVcId OBJECT-TYPE
    SYNTAX          Unsigned32
    MAX-ACCESS      read-only
    STATUS          current
    DESCRIPTION     
        "The value of tlsSpbFdbPortId indicates the virtual-circuit identifier
         (vc-id) of the SDP binding of the SDP for this FDB entry.

         This object is valid only when tlsSpbFdbLocale is set to 'sdp'.
         This object is other-wise insignificant and should contain a value
         of 0."
    ::= { tlsSpbFdbEntry 8 }

tlsSpbFdbState OBJECT-TYPE
    SYNTAX          TmnxSpbFdbState
    MAX-ACCESS      read-only
    STATUS          current
    DESCRIPTION     
        "The tlsSpbFdbState indicates the state of this FDB entry in the user
         VPLS."
    ::= { tlsSpbFdbEntry 9 }

tlsSpbFdbMLocale OBJECT-TYPE
    SYNTAX          TmnxSpbFdbLocale
    MAX-ACCESS      read-only
    STATUS          current
    DESCRIPTION     
        "The value of the object tlsSpbFdbMLocale indicates locality of
        this FDB entry for multicast traffic."
    ::= { tlsSpbFdbEntry 10 }

tlsSpbFdbMPortId OBJECT-TYPE
    SYNTAX          TmnxPortID
    MAX-ACCESS      read-only
    STATUS          current
    DESCRIPTION     
        "The value of tlsSpbFdbMPortId indicates the port-id of the SAP for this
         FDB entry for multicast traffic.

         This object is valid only when tlsSpbFdbMLocale is set to 'sap'.
         This object is otherwise insignificant and should contain a value
         of 0."
    ::= { tlsSpbFdbEntry 11 }

tlsSpbFdbMEncapValue OBJECT-TYPE
    SYNTAX          TmnxEncapVal
    MAX-ACCESS      read-only
    STATUS          current
    DESCRIPTION     
        "The value of tlsSpbFdbMEncapValue indicates the encap-value of the SAP
         for this FDB entry for multicast traffic.
         
         This object is valid only when tlsSpbFdbMLocale is set to 'sap'.
         This object is otherwise insignificant and should contain a value
         of 0."
    ::= { tlsSpbFdbEntry 12 }

tlsSpbFdbMSdpId OBJECT-TYPE
    SYNTAX          SdpId
    MAX-ACCESS      read-only
    STATUS          current
    DESCRIPTION     
        "The value of tlsSpbFdbMSdpId indicates the sdp identifier of the 
         SDP binding of the SDP for this FDB entry for multicast traffic.

         This object is valid only when tlsSpbFdbMLocale is set to 'sdp'.
         This object is other-wise insignificant and should contain a value
         of 0."
    ::= { tlsSpbFdbEntry 13 }

tlsSpbFdbMVcId OBJECT-TYPE
    SYNTAX          Unsigned32
    MAX-ACCESS      read-only
    STATUS          current
    DESCRIPTION     
        "The value of tlsSpbFdbMPortId indicates the virtual-circuit identifier
         (vc-id) of the SDP binding of the SDP for this FDB entry for
         multicast traffic.

         This object is valid only when tlsSpbFdbMLocale is set to 'sdp'.
         This object is other-wise insignificant and should contain a value
         of 0."
    ::= { tlsSpbFdbEntry 14 }

tlsSpbFdbMState OBJECT-TYPE
    SYNTAX          TmnxSpbFdbState
    MAX-ACCESS      read-only
    STATUS          current
    DESCRIPTION     
        "The tlsSpbFdbMState indicates the state of this FDB entry for multicast
         traffic in the user VPLS."
    ::= { tlsSpbFdbEntry 15 }

-- ------------------------------------
-- TLS SPB FDB Table
-- ------------------------------------
tlsSpbFidFdbTable OBJECT-TYPE
    SYNTAX          SEQUENCE OF TlsSpbFidFdbEntry
    MAX-ACCESS      not-accessible
    STATUS          current
    DESCRIPTION
        "The tlsSpbFidFdbTable contains control VPLS Shortest Path Bridging
        (SPB) Forwarding Data-Base (FDB) information."
    ::= { tmnxSvcObjs 132 }

tlsSpbFidFdbEntry OBJECT-TYPE
    SYNTAX          TlsSpbFidFdbEntry
    MAX-ACCESS      not-accessible
    STATUS          current
    DESCRIPTION     
        "The tlsSpbFidFdbEntry contains a specific control VPLS SPB FDB
        mac-address related information."
    INDEX           { svcId, svcTlsSpbFid, tlsSpbFidFdbMacAddr }
    ::= { tlsSpbFidFdbTable 1 }

TlsSpbFidFdbEntry ::=
    SEQUENCE {
        tlsSpbFidFdbMacAddr           MacAddress,
        tlsSpbFidFdbLocale            TmnxSpbFdbLocale,
        tlsSpbFidFdbPortId            TmnxPortID,
        tlsSpbFidFdbEncapValue        TmnxEncapVal,
        tlsSpbFidFdbSdpId             SdpId,
        tlsSpbFidFdbVcId              Unsigned32,
        tlsSpbFidFdbMLocale           TmnxSpbFdbLocale,
        tlsSpbFidFdbMPortId           TmnxPortID,
        tlsSpbFidFdbMEncapValue       TmnxEncapVal,
        tlsSpbFidFdbMSdpId            SdpId,
        tlsSpbFidFdbMVcId             Unsigned32,
        tlsSpbFidFdbLastUpdate        TimeStamp,
        tlsSpbFidFdbMLastUpdate       TimeStamp
    }

tlsSpbFidFdbMacAddr OBJECT-TYPE
    SYNTAX          MacAddress
    MAX-ACCESS      not-accessible
    STATUS          current
    DESCRIPTION     
        "The value of the object tlsSpbFidFdbMacAddr indicates the
         48-bit IEEE 802.3 MAC address."
    ::= { tlsSpbFidFdbEntry 1 }

tlsSpbFidFdbLocale OBJECT-TYPE
    SYNTAX          TmnxSpbFdbLocale
    MAX-ACCESS      read-only
    STATUS          current
    DESCRIPTION     
        "The value of the object tlsSpbFidFdbLocale indicates locality of the
        this FDB entry."
    ::= { tlsSpbFidFdbEntry 4 }

tlsSpbFidFdbPortId OBJECT-TYPE
    SYNTAX          TmnxPortID
    MAX-ACCESS      read-only
    STATUS          current
    DESCRIPTION     
        "The value of tlsSpbFidFdbPortId indicates the port-id of the SAP for
         this FDB entry.

         This object is valid only when tlsSpbFidFdbLocale is set to 'sap'.
         This object is otherwise insignificant and should contain a value
         of 0."
    ::= { tlsSpbFidFdbEntry 5 }

tlsSpbFidFdbEncapValue OBJECT-TYPE
    SYNTAX          TmnxEncapVal
    MAX-ACCESS      read-only
    STATUS          current
    DESCRIPTION     
        "The value of tlsSpbFidFdbEncapValue indicates the encap-value of the
         SAP for this FDB entry.
         
         This object is valid only when tlsSpbFidFdbLocale is set to 'sap'.
         This object is otherwise insignificant and should contain a value
         of 0."
    ::= { tlsSpbFidFdbEntry 6 }

tlsSpbFidFdbSdpId OBJECT-TYPE
    SYNTAX          SdpId
    MAX-ACCESS      read-only
    STATUS          current
    DESCRIPTION     
        "The value of tlsSpbFidFdbSdpId indicates the sdp identifier of the 
         SDP binding of the SDP for this FDB entry.

         This object is valid only when tlsSpbFidFdbLocale is set to 'sdp'.
         This object is other-wise insignificant and should contain a value
         of 0."
    ::= { tlsSpbFidFdbEntry 7 }

tlsSpbFidFdbVcId OBJECT-TYPE
    SYNTAX          Unsigned32
    MAX-ACCESS      read-only
    STATUS          current
    DESCRIPTION     
        "The value of tlsSpbFidFdbPortId indicates the virtual-circuit identifier
         (vc-id) of the SDP binding of the SDP for this FDB entry.

         This object is valid only when tlsSpbFidFdbLocale is set to 'sdp'.
         This object is other-wise insignificant and should contain a value
         of 0."
    ::= { tlsSpbFidFdbEntry 8 }

tlsSpbFidFdbMLocale OBJECT-TYPE
    SYNTAX          TmnxSpbFdbLocale
    MAX-ACCESS      read-only
    STATUS          current
    DESCRIPTION     
        "The value of the object tlsSpbFidFdbMLocale indicates locality of the
        this FDB entry for multicast traffic."
    ::= { tlsSpbFidFdbEntry 9 }

tlsSpbFidFdbMPortId OBJECT-TYPE
    SYNTAX          TmnxPortID
    MAX-ACCESS      read-only
    STATUS          current
    DESCRIPTION     
        "The value of tlsSpbFidFdbMPortId indicates the port-id of the SAP for
         this FDB entry for multicast traffic.

         This object is valid only when tlsSpbFidFdbMLocale is set to 'sap'.
         This object is otherwise insignificant and should contain a value
         of 0."
    ::= { tlsSpbFidFdbEntry 10 }

tlsSpbFidFdbMEncapValue OBJECT-TYPE
    SYNTAX          TmnxEncapVal
    MAX-ACCESS      read-only
    STATUS          current
    DESCRIPTION     
        "The value of tlsSpbFidFdbMEncapValue indicates the encap-value of the
         SAP for this FDB entry for multicast traffic.
         
         This object is valid only when tlsSpbFidFdbMLocale is set to 'sap'.
         This object is otherwise insignificant and should contain a value
         of 0."
    ::= { tlsSpbFidFdbEntry 11 }

tlsSpbFidFdbMSdpId OBJECT-TYPE
    SYNTAX          SdpId
    MAX-ACCESS      read-only
    STATUS          current
    DESCRIPTION     
        "The value of tlsSpbFidFdbMSdpId indicates the sdp identifier of the 
         SDP binding of the SDP for this FDB entry for multicast traffic.

         This object is valid only when tlsSpbFidFdbMLocale is set to 'sdp'.
         This object is other-wise insignificant and should contain a value
         of 0."
    ::= { tlsSpbFidFdbEntry 12 }

tlsSpbFidFdbMVcId OBJECT-TYPE
    SYNTAX          Unsigned32
    MAX-ACCESS      read-only
    STATUS          current
    DESCRIPTION     
        "The value of tlsSpbFidFdbMPortId indicates the virtual-circuit
         identifier (vc-id) of the SDP binding of the SDP for this FDB entry
         for multicast traffic.

         This object is valid only when tlsSpbFidFdbMLocale is set to 'sdp'.
         This object is other-wise insignificant and should contain a value
         of 0."
    ::= { tlsSpbFidFdbEntry 13 }

tlsSpbFidFdbLastUpdate OBJECT-TYPE
    SYNTAX      TimeStamp
    MAX-ACCESS  read-only
    STATUS      current
    DESCRIPTION
        "The value of tlsSpbFidFdbLastUpdate indicates the sysUpTime at
         the time unicast SAP/SDP information of this entry was last updated."
    ::= { tlsSpbFidFdbEntry 14 }

tlsSpbFidFdbMLastUpdate OBJECT-TYPE
    SYNTAX      TimeStamp
    MAX-ACCESS  read-only
    STATUS      current
    DESCRIPTION
        "The value of tlsSpbFidFdbLastUpdate indicates the sysUpTime at
         the time multicast SAP/SDP information of this entry was last updated."
    ::= { tlsSpbFidFdbEntry 15 }


-- ------------------------------------------
-- TLS SPB MFIB Table (User VPLS)
-- ------------------------------------------
tlsSpbMFibTable OBJECT-TYPE
    SYNTAX          SEQUENCE OF TlsSpbMFibEntry
    MAX-ACCESS      not-accessible
    STATUS          current
    DESCRIPTION
        "The tlsSpbMFibTable contains user VPLS Shortest Path Bridging
        (SPB) multicast forwarding data-base (Mfib) information."
    ::= { tmnxSvcObjs 133 }

tlsSpbMFibEntry OBJECT-TYPE
    SYNTAX          TlsSpbMFibEntry
    MAX-ACCESS      not-accessible
    STATUS          current
    DESCRIPTION     
        "The tlsSpbMFibEntry contains an entry for specific SAP or SDP in the
        multicast forwarding data-base of the user VPLS for the group
        MAC address."
    INDEX   { svcId, tlsSpbMFibMacAddr }
    ::= { tlsSpbMFibTable 1 }

TlsSpbMFibEntry ::=
    SEQUENCE {
        tlsSpbMFibMacAddr           MacAddress,
        tlsSpbMFibIsid              Unsigned32,
        tlsSpbMFibState             BITS
    }

tlsSpbMFibMacAddr OBJECT-TYPE
    SYNTAX          MacAddress
    MAX-ACCESS      not-accessible
    STATUS          current
    DESCRIPTION     
        "The value of the object tlsSpbMFibMacAddr indicates the
         48-bit IEEE 802.3 group MAC address."
    ::= { tlsSpbMFibEntry 1 }

tlsSpbMFibIsid OBJECT-TYPE
    SYNTAX      Unsigned32
    MAX-ACCESS  read-only
    STATUS      current
    DESCRIPTION
        "The value of tlsSpbMFibIsid indicates the value of ISID of the
         group MAC address of this entry."
    ::= { tlsSpbMFibEntry 2 }

tlsSpbMFibState OBJECT-TYPE
    SYNTAX      BITS {
                      ok            (0),
                      addModPending (1),
                      delPending    (2),
                      sysMFibLimit  (3),
                      noFateShared  (4),
                      spbMFibLimit  (5),
                      useDefMCTree  (6)
                }
    MAX-ACCESS  read-only
    STATUS      current
    DESCRIPTION
        "The tlsSpbMFibState indicates the state of this FDB entry in the user
        VPLS."
    ::= { tlsSpbMFibEntry 3 }

-- ------------------------------------------
-- TLS SPB FID MFIB Table (Controlling VPLS)
-- ------------------------------------------
tlsSpbFidMFibTable OBJECT-TYPE
    SYNTAX          SEQUENCE OF TlsSpbFidMFibEntry
    MAX-ACCESS      not-accessible
    STATUS          current
    DESCRIPTION
        "The tlsSpbFidMFibTable contains control VPLS Shortest Path Bridging
        (SPB) multicast forwarding data-base (MFib) information."
    ::= { tmnxSvcObjs 134 }

tlsSpbFidMFibEntry OBJECT-TYPE
    SYNTAX          TlsSpbFidMFibEntry
    MAX-ACCESS      not-accessible
    STATUS          current
    DESCRIPTION     
        "The tlsSpbFidMFibEntry contains an entry for specific SAP or SDP in the
        multicast forwarding data-base of the controlling vpls for the group
        MAC address."
    INDEX   { svcId, svcTlsSpbFid, tlsSpbFidMFibMacAddr, tlsSpbFidMFibLocale,
              tlsSpbFidMFibPortId,tlsSpbFidMFibEncapValue,
              tlsSpbFidMFibSdpId, tlsSpbFidMFibVcId}
    ::= { tlsSpbFidMFibTable 1 }

TlsSpbFidMFibEntry ::=
    SEQUENCE {
        tlsSpbFidMFibMacAddr           MacAddress,
        tlsSpbFidMFibLocale            TmnxSpbFdbLocale,
        tlsSpbFidMFibPortId            TmnxPortID,
        tlsSpbFidMFibEncapValue        TmnxEncapVal,
        tlsSpbFidMFibSdpId             SdpId,
        tlsSpbFidMFibVcId              Unsigned32,
        tlsSpbFidMFibIsid              Unsigned32,
        tlsSpbFidMFibLastUpdate        TimeStamp
    }

tlsSpbFidMFibMacAddr OBJECT-TYPE
    SYNTAX          MacAddress
    MAX-ACCESS      not-accessible
    STATUS          current
    DESCRIPTION     
        "The value of the object tlsSpbFidMFibMacAddr indicates the
         48-bit IEEE 802.3 group MAC address."
    ::= { tlsSpbFidMFibEntry 1 }

tlsSpbFidMFibLocale OBJECT-TYPE
    SYNTAX          TmnxSpbFdbLocale
    MAX-ACCESS      not-accessible
    STATUS          current
    DESCRIPTION     
        "The value of the object tlsSpbFidMFibLocale indicates locality of the
        this FDB entry."
    ::= { tlsSpbFidMFibEntry 2 }

tlsSpbFidMFibPortId OBJECT-TYPE
    SYNTAX          TmnxPortID
    MAX-ACCESS      not-accessible
    STATUS          current
    DESCRIPTION     
        "The value of tlsSpbFidMFibPortId indicates the port-id of the SAP
         for this multicast forwarding data-base (MFIB) entry.

         This object is valid only when tlsSpbFidFdbLocale is set to 'sap'.
         This object is otherwise insignificant and should contain a value
         of 0."
    ::= { tlsSpbFidMFibEntry 3 }

tlsSpbFidMFibEncapValue OBJECT-TYPE
    SYNTAX          TmnxEncapVal
    MAX-ACCESS      not-accessible
    STATUS          current
    DESCRIPTION     
        "The value of tlsSpbFidMFibEncapValue indicates the encap-value of
         the SAP for this multicast forwarding data-base (MFIB) entry.

         This object is valid only when tlsSpbFidFdbLocale is set to 'sap'.
         This object is otherwise insignificant and should contain a value
         of 0."
    ::= { tlsSpbFidMFibEntry 4 }

tlsSpbFidMFibSdpId OBJECT-TYPE
    SYNTAX          SdpId
    MAX-ACCESS      not-accessible
    STATUS          current
    DESCRIPTION     
        "The value of tlsSpbFidMFibSdpId indicates the sdp identifier of the 
         SDP binding of the SDP for this FDB entry.

         This object is valid only when tlsSpbFidMFibLocale is set to 'sdp'.
         This object is other-wise insignificant and should contain a value
         of 0."
    ::= { tlsSpbFidMFibEntry 5 }

tlsSpbFidMFibVcId OBJECT-TYPE
    SYNTAX          Unsigned32
    MAX-ACCESS      not-accessible
    STATUS          current
    DESCRIPTION     
        "The value of tlsSpbFidMFibPortId indicates the virtual-circuit
         identifier (vc-id) of the SDP binding of the SDP for this FDB entry.

         This object is valid only when tlsSpbFidMFibLocale is set to 'sdp'.
         This object is other-wise insignificant and should contain a value
         of 0."
    ::= { tlsSpbFidMFibEntry 6 }

tlsSpbFidMFibIsid OBJECT-TYPE
    SYNTAX      Unsigned32
    MAX-ACCESS  read-only
    STATUS      current
    DESCRIPTION
        "The value of tlsSpbFidMFibIsid indicates the value of ISID of the
         group MAC address of this entry."
    ::= { tlsSpbFidMFibEntry 7 }

tlsSpbFidMFibLastUpdate OBJECT-TYPE
    SYNTAX      TimeStamp
    MAX-ACCESS  read-only
    STATUS      current
    DESCRIPTION
        "The value of tlsSpbFidMFibLastUpdate indicates the sysUpTime at
         the time this entry was last updated."
    ::= { tlsSpbFidMFibEntry 8 }

-- ------------------------------------
-- SPB interface information Table
-- ------------------------------------
svcSpbIfTable OBJECT-TYPE
    SYNTAX          SEQUENCE OF SvcSpbIfEntry
    MAX-ACCESS      not-accessible
    STATUS          current
    DESCRIPTION
        "The svcSpbIfTable contains Shortest Path Bridging (SPB) interface
         information."
    ::= { tmnxSvcObjs 135 }

svcSpbIfEntry OBJECT-TYPE
    SYNTAX          SvcSpbIfEntry
    MAX-ACCESS      not-accessible
    STATUS          current
    DESCRIPTION     
        "The svcSpbIfEntry contains a specific SPB interface related
        information."
    INDEX  { svcSpbIfIndex }
    ::= { svcSpbIfTable 1 }

SvcSpbIfEntry ::=
    SEQUENCE {
        svcSpbIfIndex             InterfaceIndex,
        svcSpbIfLocale            TmnxSpbFdbLocale,
        svcSpbIfPortId            TmnxPortID,
        svcSpbIfEncapValue        TmnxEncapVal,
        svcSpbIfSdpId             SdpId,
        svcSpbIfVcId              Unsigned32,
        svcSpbIfSvcId             TmnxServId,
        svcSpbIfIsisInstance      Integer32
    }

svcSpbIfIndex OBJECT-TYPE
    SYNTAX          InterfaceIndex
    MAX-ACCESS      not-accessible
    STATUS          current
    DESCRIPTION     
        "The value of the object svcSpbIfIndex indicates the interface index."
    ::= { svcSpbIfEntry 1 }

svcSpbIfLocale OBJECT-TYPE
    SYNTAX          TmnxSpbFdbLocale
    MAX-ACCESS      read-only
    STATUS          current
    DESCRIPTION     
        "The value of the object svcSpbIfLocale indicates locality of the
        this interface entry."
    ::= { svcSpbIfEntry 4 }

svcSpbIfPortId OBJECT-TYPE
    SYNTAX          TmnxPortID
    MAX-ACCESS      read-only
    STATUS          current
    DESCRIPTION     
        "The value of svcSpbIfPortId indicates the port-id of the SAP for this
         interface entry.

         This object is valid only when svcSpbIfLocale is set to 'sap'.
         This object is otherwise insignificant and should contain a value
         of 0."
    ::= { svcSpbIfEntry 5 }

svcSpbIfEncapValue OBJECT-TYPE
    SYNTAX          TmnxEncapVal
    MAX-ACCESS      read-only
    STATUS          current
    DESCRIPTION     
        "The value of svcSpbIfEncapValue indicates the encap-value of the SAP
         for this interface entry.
         
         This object is valid only when svcSpbIfLocale is set to 'sap'.
         This object is otherwise insignificant and should contain a value
         of 0."
    ::= { svcSpbIfEntry 6 }

svcSpbIfSdpId OBJECT-TYPE
    SYNTAX          SdpId
    MAX-ACCESS      read-only
    STATUS          current
    DESCRIPTION     
        "The value of svcSpbIfSdpId indicates the sdp identifier of the 
         SDP binding of the SDP for this interface entry.

         This object is valid only when svcSpbIfLocale is set to 'sdp'.
         This object is other-wise insignificant and should contain a value
         of 0."
    ::= { svcSpbIfEntry 7 }

svcSpbIfVcId OBJECT-TYPE
    SYNTAX          Unsigned32
    MAX-ACCESS      read-only
    STATUS          current
    DESCRIPTION     
        "The value of svcSpbIfPortId indicates the virtual-circuit identifier
         (vc-id) of the SDP binding of the SDP for this interface entry.

         This object is valid only when svcSpbIfLocale is set to 'sdp'.
         This object is other-wise insignificant and should contain a value
         of 0."
    ::= { svcSpbIfEntry 8 }

svcSpbIfSvcId OBJECT-TYPE
    SYNTAX          TmnxServId
    MAX-ACCESS      read-only
    STATUS          current
    DESCRIPTION
        "The value of svcSpbIfSvcId indicates the service identifier of this
         Shortest Path Bridging interface."
    ::= { svcSpbIfEntry 9 }

svcSpbIfIsisInstance OBJECT-TYPE
    SYNTAX          Integer32
    MAX-ACCESS      read-only
    STATUS          current
    DESCRIPTION
        "The value of svcSpbIfIsisInstance indicates the
         ISIS-MIB::isisSysInstance used with this Shortest Path Bridging
         interface."
    ::= { svcSpbIfEntry 10 }

-- ------------------------------------
-- ARP Host Overrides Table
-- ------------------------------------
svcArpHostOvrTable OBJECT-TYPE
    SYNTAX          SEQUENCE OF SvcArpHostOvrEntry
    MAX-ACCESS      not-accessible
    STATUS          current
    DESCRIPTION
        "The svcArpHostOvrTable contains QoS (Quality of Service)
         overrides for ARP hosts.

         Entries in this table are created and destroyed by the system.
         
         This table is a sparse augment of the svcArpHostTable: entries
         are created only for ARH hosts for which QoS overrides information 
         is available."
    ::= { tmnxSvcObjs 136 }

svcArpHostOvrEntry OBJECT-TYPE
    SYNTAX SvcArpHostOvrEntry
    MAX-ACCESS  not-accessible
    STATUS      current
    DESCRIPTION
       "Each conceptual row represents QoS overrides information
        of an ARP Host."
    INDEX { svcId,
            svcArpHostIpAddrType,
            svcArpHostIpAddr,
            svcArpHostOvrDirection,
            svcArpHostOvrType,
            svcArpHostOvrTypeId,
            svcArpHostOvrTypeName }
    ::= { svcArpHostOvrTable 1 }
    
SvcArpHostOvrEntry ::=
    SEQUENCE {
        svcArpHostOvrDirection         TDirectionIngEgr,
        svcArpHostOvrType              TQosOverrideType,
        svcArpHostOvrTypeId            Integer32,
        svcArpHostOvrTypeName          TNamedItemOrEmpty,
        svcArpHostOvrPIR               TQosQueuePIRRateOverride,
        svcArpHostOvrCIR               TQosQueueCIRRateOverride,
        svcArpHostOvrCBS               TBurstSizeBytesOvr,
        svcArpHostOvrMBS               TBurstSizeBytesOvr,
        svcArpHostOvrWrrWeight         THsmdaWrrWeightOverride,
        svcArpHostOvrSummedCIR         TruthValue
    }

svcArpHostOvrDirection OBJECT-TYPE
    SYNTAX          TDirectionIngEgr
    MAX-ACCESS      not-accessible
    STATUS          current
    DESCRIPTION     "The value of svcArpHostOvrDirection indicates if
                     this row specifies ingress or egress qos override 
                     parameters."
    ::= { svcArpHostOvrEntry 1 }

svcArpHostOvrType OBJECT-TYPE
    SYNTAX          TQosOverrideType
    MAX-ACCESS      not-accessible
    STATUS          current
    DESCRIPTION     "The value of svcArpHostOvrType indicates what field
                     has been overridden by this row."
    ::= { svcArpHostOvrEntry 2 }

svcArpHostOvrTypeId OBJECT-TYPE
    SYNTAX          Integer32
    MAX-ACCESS      not-accessible
    STATUS          current
    DESCRIPTION     "The value of svcArpHostOvrTypeId indicates the ID of
                     the queue/policer that has been overridden by this row.
                         
                     If the value of svcArpHostOvrType is not 'queue (1)'
                     or 'policer (2)', this field must be set to zero (0)."
    ::= { svcArpHostOvrEntry 3 }

svcArpHostOvrTypeName OBJECT-TYPE
    SYNTAX          TNamedItemOrEmpty
    MAX-ACCESS      not-accessible
    STATUS          current
    DESCRIPTION     "The value of svcArpHostOvrTypeName indicates the
                     name of the scheduler/arbiter that has been overridden by
                     this row.
                         
                     If the value of svcArpHostOvrType is not 
                     'arbiter (4)' or 'scheduler (5)', this field must be set to
                     zero (0)."
    ::= { svcArpHostOvrEntry 4 }

svcArpHostOvrPIR OBJECT-TYPE
    SYNTAX          TQosQueuePIRRateOverride
    MAX-ACCESS      read-only
    STATUS          current
    DESCRIPTION     "The value of svcArpHostOvrPIR indicates the PIR rate
                     in kbps allowed for the object overridden by this row."
    ::= { svcArpHostOvrEntry 5 }

svcArpHostOvrCIR OBJECT-TYPE
    SYNTAX          TQosQueueCIRRateOverride
    MAX-ACCESS      read-only
    STATUS          current
    DESCRIPTION     "The value of svcArpHostOvrCIR indicates the CIR rate
                     in kbps allowed for the object overridden by this row."
    ::= { svcArpHostOvrEntry 6 }

svcArpHostOvrCBS OBJECT-TYPE
    SYNTAX          TBurstSizeBytesOvr
    MAX-ACCESS      read-only
    STATUS          current
    DESCRIPTION     "The value of svcArpHostOvrCBS indicates the amount of
                     reserved buffer space (in bytes) for the object
                     overridden by this row."
    ::= { svcArpHostOvrEntry 7 }

svcArpHostOvrMBS OBJECT-TYPE
    SYNTAX          TBurstSizeBytesOvr
    MAX-ACCESS      read-only
    STATUS          current
    DESCRIPTION     "The value of svcArpHostOvrMBS indicates the maximum
                     amount of reserved buffer space (in bytes) for the object
                     overridden by this row."
    ::= { svcArpHostOvrEntry 8 }

svcArpHostOvrWrrWeight OBJECT-TYPE
    SYNTAX          THsmdaWrrWeightOverride
    MAX-ACCESS      read-only
    STATUS          current
    DESCRIPTION     
    "The value of svcArpHostOvrWrrWeight specifies the weight of this queue
     for the HSMDA scheduler.
         
     The weight determines how much bandwidth this queue gets out of the 
     total rate for the scheduling class.
         
     The value of svcArpHostOvrWrrWeight is only relevant if the value of
     svcArpHostOvrType is equal to 'queue', and if the queue specified in
     svcArpHostOvrTypeId is referenced in the value of 
     TIMETRA-QOS-MIB::tHsmdaWrrPolicyIncludeQueues of the Weighted Round Robin
     policy associated with this ARP Host."
    ::= { svcArpHostOvrEntry 9 }

svcArpHostOvrSummedCIR OBJECT-TYPE
    SYNTAX      TruthValue
    MAX-ACCESS  read-only
    STATUS      current
    DESCRIPTION
        "The value of svcArpHostOvrSummedCIR indicates if the CIR should
         be used as the summed CIR values of the children schedulers or queues.
         If set to 'true', the applicable scheduler CIR (svcArpHostOvrCIR)
         loses its meaning."
    ::= { svcArpHostOvrEntry 10 }

-- ----------------------------------------
-- IES interface ISA Tunnel Next-Hop Table
-- ----------------------------------------
iesIfIsaTnlNHTableLastChanged  OBJECT-TYPE
    SYNTAX          TimeStamp
    MAX-ACCESS      read-only
    STATUS          current
    DESCRIPTION
        "The value of iesIfIsaTnlNHTableLastChanged indicates the
         sysUpTime at the time of the last modification
         of iesIfIsaTnlNHTable.

         If no changes were made to the entry since the last
         re-initialization of the local network management subsystem,
         then this object contains a zero value."
    ::= { tmnxSvcObjs 137 }

iesIfIsaTnlNHTable OBJECT-TYPE
    SYNTAX          SEQUENCE OF IesIfIsaTnlNHEntry
    MAX-ACCESS      not-accessible
    STATUS          current
    DESCRIPTION
        "The iesIfIsaTnlNHTable contains entries for IES interface ISA tunnel
         next-hop information in an IES service context."
    ::= { tmnxSvcObjs 138 }

iesIfIsaTnlNHEntry    OBJECT-TYPE
    SYNTAX          IesIfIsaTnlNHEntry
    MAX-ACCESS      not-accessible
    STATUS          current
    DESCRIPTION
        "The iesIfIsaTnlNHEntry contains IES service ISA tunnel next-hop
         information per service interface."
    INDEX           { svcId, iesIfIndex }
    ::= { iesIfIsaTnlNHTable 1}

IesIfIsaTnlNHEntry ::=    SEQUENCE {
    iesIfIsaTnlNHLastChanged            TimeStamp,
    iesIfIsaTnlNHStaticAddrType         InetAddressType,
    iesIfIsaTnlNHStaticAddr             InetAddress,
    iesIfIsaTnlNHDynAddrType            InetAddressType,
    iesIfIsaTnlNHDynAddr                InetAddress
}

iesIfIsaTnlNHLastChanged        OBJECT-TYPE
    SYNTAX          TimeStamp
    MAX-ACCESS      read-only
    STATUS          current
    DESCRIPTION
        "The value of iesIfIsaTnlNHLastChanged indicates the sysUpTime at the
         time of the last modification of this entry.
                     
         If no changes were made to the entry since the last re-initialization
         of the local network management subsystem, then this object contains a
         zero value."
    ::= { iesIfIsaTnlNHEntry 1 }

iesIfIsaTnlNHStaticAddrType OBJECT-TYPE
    SYNTAX      InetAddressType
    MAX-ACCESS  read-write
    STATUS      current
    DESCRIPTION
        "The value of iesIfIsaTnlNHStaticAddrType specifies the address type
         of iesIfIsaTnlNHStaticAddr object."
    DEFVAL { ipv4 }
    ::= { iesIfIsaTnlNHEntry 2 }

iesIfIsaTnlNHStaticAddr OBJECT-TYPE
    SYNTAX      InetAddress (SIZE(0|4|16|20))
    MAX-ACCESS  read-write
    STATUS      current
    DESCRIPTION
        "The value of iesIfIsaTnlNHStaticAddr specifies the IP address of
         the redundant next-hop for static ISA tunnels on this interface."
    DEFVAL { ''H }
    ::= { iesIfIsaTnlNHEntry 3 }

iesIfIsaTnlNHDynAddrType OBJECT-TYPE
    SYNTAX      InetAddressType
    MAX-ACCESS  read-write
    STATUS      current
    DESCRIPTION
        "The value of iesIfIsaTnlNHDynAddrType specifies the address type
         of iesIfIsaTnlNHStaticAddr object."
    DEFVAL { ipv4 }
    ::= { iesIfIsaTnlNHEntry 4 }

iesIfIsaTnlNHDynAddr OBJECT-TYPE
    SYNTAX      InetAddress (SIZE(0|4|16|20))
    MAX-ACCESS  read-write
    STATUS      current
    DESCRIPTION
        "The value of iesIfIsaTnlNHDynAddr specifies the IP address of
         the redundant next-hop for dynamic ISA tunnels on this interface."
    DEFVAL { ''H }
    ::= { iesIfIsaTnlNHEntry 5 }

-- ----------------------------------------------------
-- svcBgpVpwsTable (VPWS: Virtual Private Wire Service)
-- ----------------------------------------------------
svcBgpVpwsTblLastChanged  OBJECT-TYPE
    SYNTAX          TimeStamp
    MAX-ACCESS      read-only
    STATUS          current
    DESCRIPTION
        "The value of svcBgpVpwsTblLastChanged indicates the sysUpTime
         at the time of the last modification of svcBgpVpwsTable.

         If no changes were made to the entry since the last re-initialization
         of the local network management subsystem, then this object contains a
         zero value."
    ::= { tmnxSvcObjs 139 }

svcBgpVpwsTable OBJECT-TYPE
    SYNTAX          SEQUENCE OF SvcBgpVpwsEntry
    MAX-ACCESS      not-accessible
    STATUS          current
    DESCRIPTION
        "This table maintains the information about BGP VPWS (Virtual Private
         Wire Service) feature information for a service."
    ::= { tmnxSvcObjs 140 } 
    
svcBgpVpwsEntry OBJECT-TYPE
    SYNTAX          SvcBgpVpwsEntry
    MAX-ACCESS      not-accessible
    STATUS          current
    DESCRIPTION
        "Information about BGP-VPWS feature for a specific service."
    INDEX { svcId }
    ::= { svcBgpVpwsTable 1 }

SvcBgpVpwsEntry ::=
    SEQUENCE {
        svcBgpVpwsRowStatus        RowStatus,
        svcBgpVpwsLastChanged      TimeStamp,
        svcBgpVpwsAdminStatus      TmnxEnabledDisabled,
        svcBgpVpwsVeName           TNamedItemOrEmpty,
        svcBgpVpwsVeId             TmnxSiteIdOrEmpty,
        svcBgpVpwsPwTemplateId     PWTemplateId
    }
    
svcBgpVpwsRowStatus OBJECT-TYPE
    SYNTAX       RowStatus
    MAX-ACCESS   read-create
    STATUS       current
    DESCRIPTION  
         "The value of svcBgpVpwsRowStatus is used for the creation and 
          deletion of rows in this table."
    ::= { svcBgpVpwsEntry 1 }   

svcBgpVpwsLastChanged OBJECT-TYPE
    SYNTAX       TimeStamp
    MAX-ACCESS   read-only
    STATUS       current
    DESCRIPTION  
        "The value of svcBgpVpwsLastChanged indicates the timestamp of last
        change to this row in svcBgpVpwsTable."
    ::= { svcBgpVpwsEntry 2 }  
    
svcBgpVpwsAdminStatus OBJECT-TYPE
    SYNTAX       TmnxEnabledDisabled
    MAX-ACCESS   read-create
    STATUS       current
    DESCRIPTION
        "The value of svcBgpVpwsAdminStatus specifies the administrative
         state of the VPWS edge instance associated with this service."
    DEFVAL { disabled }
    ::= { svcBgpVpwsEntry 3 } 
    
svcBgpVpwsVeName OBJECT-TYPE
    SYNTAX       TNamedItemOrEmpty
    MAX-ACCESS   read-create
    STATUS       current
    DESCRIPTION     
        "The value of svcBgpVpwsVeName specifies the name for the specific
         VPWS edge."
    DEFVAL { ''H }
    ::= { svcBgpVpwsEntry 4 }
 
svcBgpVpwsVeId OBJECT-TYPE
    SYNTAX       TmnxSiteIdOrEmpty
    MAX-ACCESS   read-create
    STATUS       current
    DESCRIPTION
        "The value of svcBgpVpwsVeId specifies the identifier for the
         VPWS edge in this service.

         The svcBgpVpwsVeId is a two bytes identifier that represents the
         local instance in a VPWS and is advertised through the BGP
         Network Layer Reachability Information (NLRI).
         
         An 'inconsistentValue' error is returned if this object is set to
         non-default value when svcBgpVpwsVeName is set to its default
         value."
    REFERENCE "http://tools.ietf.org/html/draft-kompella-l2vpn-l2vpn-10"
    DEFVAL { -1 }
    ::= { svcBgpVpwsEntry 5 }

svcBgpVpwsPwTemplateId OBJECT-TYPE
    SYNTAX     PWTemplateId
    MAX-ACCESS read-only
    STATUS     current
    DESCRIPTION
        "The value of svcBgpVpwsPwTemplateId indicates the pseudo-wire template
         used in transmitting BGP-VPWS NLRI information for this VPWS edge in
         this service."
    ::= { svcBgpVpwsEntry 6 }

-- ----------------------------------------------------
-- svcBgpVpwsRemoteVeTable (VPWS: Virtual Private Wire Service)
-- ----------------------------------------------------
svcBgpVpwsRemoteVeTblLastChanged  OBJECT-TYPE
    SYNTAX          TimeStamp
    MAX-ACCESS      read-only
    STATUS          current
    DESCRIPTION
        "The value of svcBgpVpwsRemoteVeTblLastChanged indicates the sysUpTime
         at the time of the last modification of svcBgpVpwsRemoteVeTable.

         If no changes were made to the entry since the last re-initialization
         of the local network management subsystem, then this object contains a
         zero value."
    ::= { tmnxSvcObjs 141 }

svcBgpVpwsRemoteVeTable OBJECT-TYPE
    SYNTAX          SEQUENCE OF SvcBgpVpwsRemoteVeEntry
    MAX-ACCESS      not-accessible
    STATUS          current
    DESCRIPTION
        "This table maintains the information about BGP VPWS (Virtual Private
         Wire Service) remote edge information for a service."
    ::= { tmnxSvcObjs 142 } 
    
svcBgpVpwsRemoteVeEntry OBJECT-TYPE
    SYNTAX          SvcBgpVpwsRemoteVeEntry
    MAX-ACCESS      not-accessible
    STATUS          current
    DESCRIPTION
        "Information about BGP VPWS remote edge for a specific service."
    INDEX { svcId, svcBgpVpwsRemoteVeName }
    ::= { svcBgpVpwsRemoteVeTable 1 }

SvcBgpVpwsRemoteVeEntry ::=
    SEQUENCE {
        svcBgpVpwsRemoteVeName           TNamedItem,
        svcBgpVpwsRemoteVeRowStatus      RowStatus,
        svcBgpVpwsRemoteVeLastChanged    TimeStamp,
        svcBgpVpwsRemoteVeId             TmnxSiteIdOrEmpty
    }
    
svcBgpVpwsRemoteVeName OBJECT-TYPE
    SYNTAX       TNamedItem
    MAX-ACCESS   not-accessible
    STATUS       current
    DESCRIPTION     
        "The value of svcBgpVpwsRemoteVeName specifies the name for the specific
         VPWS edge."
    ::= { svcBgpVpwsRemoteVeEntry 1 }

svcBgpVpwsRemoteVeRowStatus OBJECT-TYPE
    SYNTAX       RowStatus
    MAX-ACCESS   read-create
    STATUS       current
    DESCRIPTION  
         "The value of svcBgpVpwsRemoteVeRowStatus is used for the creation and 
          deletion of rows in this table."
    ::= { svcBgpVpwsRemoteVeEntry 2 }   

svcBgpVpwsRemoteVeLastChanged OBJECT-TYPE
    SYNTAX       TimeStamp
    MAX-ACCESS   read-only
    STATUS       current
    DESCRIPTION  
        "The value of svcBgpVpwsRemoteVeLastChanged indicates the timestamp of
         last change to this row in svcBgpVpwsRemoteVeTable."
    ::= { svcBgpVpwsRemoteVeEntry 3 }  
    
svcBgpVpwsRemoteVeId OBJECT-TYPE
    SYNTAX       TmnxSiteIdOrEmpty
    MAX-ACCESS   read-create
    STATUS       current
    DESCRIPTION
        "The value of svcBgpVpwsRemoteVeId specifies the identifier for the
         VPWS edge in this service.

         The svcBgpVpwsRemoteVeId is a two bytes identifier that represents the
         remote bridging instance in a VPWS and is advertised through the BGP
         Network Layer Reachability Information (NLRI)."
    REFERENCE "RFC-4761"
    DEFVAL { -1 }
    ::= { svcBgpVpwsRemoteVeEntry 4 }   

-- --------------------------------------------------
-- svc ISID policy table
-- --------------------------------------------------
svcTlsIsidPlcyRangeTable OBJECT-TYPE
    SYNTAX          SEQUENCE OF SvcTlsIsidPlcyRangeEntry
    MAX-ACCESS      not-accessible
    STATUS          current
    DESCRIPTION
        "This table maintains the ISID policy information for VPLS services."
    ::= { tmnxSvcObjs 148 } 
    
svcTlsIsidPlcyRangeEntry OBJECT-TYPE
    SYNTAX          SvcTlsIsidPlcyRangeEntry
    MAX-ACCESS      not-accessible
    STATUS          current
    DESCRIPTION
        "This entry maintains the ISID policy information for a specific
         VPLS service."
    INDEX { svcId, svcTlsIsidPlcyRangeId }
    ::= { svcTlsIsidPlcyRangeTable 1 }

SvcTlsIsidPlcyRangeEntry ::=
    SEQUENCE {
        svcTlsIsidPlcyRangeId              Unsigned32,
        svcTlsIsidPlcyRangeRowStatus       RowStatus,
        svcTlsIsidPlcyRangeLastChanged     TimeStamp,
        svcTlsIsidPlcyRangeLow             TmnxISID,
        svcTlsIsidPlcyRangeHigh            TmnxISID,
        svcTlsIsidPlcyRangeUseDefMCTree    TruthValue,
        svcTlsIsidPlcyRangeAdvLocal        TruthValue
    }
    
svcTlsIsidPlcyRangeId OBJECT-TYPE
    SYNTAX       Unsigned32 (1..8191)
    MAX-ACCESS   not-accessible
    STATUS       current
    DESCRIPTION     
        "The value of svcTlsIsidPlcyRangeId specifies the range identifier for
         the ISID policy."
    ::= { svcTlsIsidPlcyRangeEntry 1 }

svcTlsIsidPlcyRangeRowStatus OBJECT-TYPE
    SYNTAX       RowStatus
    MAX-ACCESS   read-create
    STATUS       current
    DESCRIPTION  
         "The value of svcTlsIsidPlcyRangeRowStatus is used for the creation and 
          deletion of rows in this table."
    ::= { svcTlsIsidPlcyRangeEntry 2 }   

svcTlsIsidPlcyRangeLastChanged OBJECT-TYPE
    SYNTAX       TimeStamp
    MAX-ACCESS   read-only
    STATUS       current
    DESCRIPTION  
        "The value of svcTlsIsidPlcyRangeLastChanged indicates the timestamp of
         last change to this row in svcTlsIsidPlcyRangeTable."
    ::= { svcTlsIsidPlcyRangeEntry 3 }  
    
svcTlsIsidPlcyRangeLow OBJECT-TYPE
    SYNTAX       TmnxISID
    MAX-ACCESS   read-create
    STATUS       current
    DESCRIPTION  
         "The value of svcTlsIsidPlcyRangeLow specifies the low value of the
          range for this entry."
    DEFVAL { 0 }
    ::= { svcTlsIsidPlcyRangeEntry 4 }   

svcTlsIsidPlcyRangeHigh OBJECT-TYPE
    SYNTAX       TmnxISID
    MAX-ACCESS   read-create
    STATUS       current
    DESCRIPTION  
         "The value of svcTlsIsidPlcyRangeHigh specifies the high value of the
          range for this entry."
    DEFVAL { 0 }
    ::= { svcTlsIsidPlcyRangeEntry 5 }   

svcTlsIsidPlcyRangeUseDefMCTree OBJECT-TYPE
    SYNTAX       TruthValue
    MAX-ACCESS   read-create
    STATUS       current
    DESCRIPTION  
         "The value of svcTlsIsidPlcyRangeUseDefMCTree specifies whether to
          use default multicast tree to propagate ISID range."
    DEFVAL { false }
    ::= { svcTlsIsidPlcyRangeEntry 6 }

svcTlsIsidPlcyRangeAdvLocal OBJECT-TYPE
    SYNTAX       TruthValue
    MAX-ACCESS   read-create
    STATUS       current
    DESCRIPTION  
         "The value of svcTlsIsidPlcyRangeAdvLocal specifies whether to
          advertize locally the ISID range in this entry."
    DEFVAL { true }
    ::= { svcTlsIsidPlcyRangeEntry 7 }

-- ------------------------------------
-- TLS Conditional MAC Table
-- ------------------------------------
tlsCondStaticMacTblLastChanged  OBJECT-TYPE
    SYNTAX          TimeStamp
    MAX-ACCESS      read-only
    STATUS          current
    DESCRIPTION
        "The value of tlsCondStaticMacTblLastChanged indicates the sysUpTime
         at the time of the last modification of tlsCondStaticMacTable.

         If no changes were made to the entry since the last re-initialization
         of the local network management subsystem, then this object contains a
         zero value."
    ::= { tmnxSvcTimeObjs 1 }

tlsCondStaticMacTable OBJECT-TYPE
    SYNTAX          SEQUENCE OF TlsCondStaticMacEntry
    MAX-ACCESS      not-accessible
    STATUS          current
    DESCRIPTION 
        "A table that contains TLS conditional static MAC address information."
    ::= { tmnxSvcObjs 149 }

tlsCondStaticMacEntry OBJECT-TYPE
    SYNTAX          TlsCondStaticMacEntry
    MAX-ACCESS      not-accessible
    STATUS          current
    DESCRIPTION     
        "Information about a specific TLS conditional static MAC address."
    INDEX           { svcId, tlsCondStaticMacAddr, tlsCondStaticMacPreference }
    ::= { tlsCondStaticMacTable 1 }

TlsCondStaticMacEntry ::=
    SEQUENCE {
        tlsCondStaticMacAddr              MacAddress,
        tlsCondStaticMacPreference        Unsigned32,
        tlsCondStaticMacRowStatus         RowStatus,
        tlsCondStaticMacLastChanged       TimeStamp,
        tlsCondStaticMacLocale            INTEGER,
        tlsCondStaticMacPortId            TmnxPortID,
        tlsCondStaticMacEncapValue        TmnxEncapVal,
        tlsCondStaticMacSdpId             SdpId,
        tlsCondStaticMacVcId              Unsigned32,
        tlsCondStaticMacMonitor           INTEGER
    }

tlsCondStaticMacAddr OBJECT-TYPE
    SYNTAX          MacAddress
    MAX-ACCESS      read-only
    STATUS          current
    DESCRIPTION     
        "The value of the object tlsCondStaticMacAddr specifies the
         static 48-bit IEEE 802.3 MAC address which will be programmed in the
         FDB based on status of tlsCondStaticMacMonitor and 
         tlsCondStaticMacPreference."
    ::= { tlsCondStaticMacEntry 1 }

tlsCondStaticMacPreference OBJECT-TYPE
    SYNTAX          Unsigned32 (1..1)
    MAX-ACCESS      read-only
    STATUS          current
    DESCRIPTION     
        "The value of the object tlsCondStaticMacPreference specifies the
         preference of this entry relative to other entries for the same MAC
         address."
    ::= { tlsCondStaticMacEntry 2 }

tlsCondStaticMacRowStatus OBJECT-TYPE
    SYNTAX          RowStatus
    MAX-ACCESS      read-create
    STATUS          current
    DESCRIPTION     
        "The value of the object tlsCondStaticMacRowStatus specifies the
         status of this row. The only values supported during a set
         operation are 'createAndGo' and 'destroy'."
    ::= { tlsCondStaticMacEntry 3 }

tlsCondStaticMacLastChanged OBJECT-TYPE
    SYNTAX       TimeStamp
    MAX-ACCESS   read-only
    STATUS       current
    DESCRIPTION  
        "The value of tlsCondStaticMacLastChanged indicates the timestamp of
         last change to this row in tlsCondStaticMacTable."
    ::= { tlsCondStaticMacEntry 4 }  
    
tlsCondStaticMacLocale OBJECT-TYPE
    SYNTAX          INTEGER {
                        sap      (1),
                        sdp      (2)
                    }
    MAX-ACCESS      read-create
    STATUS          current
    DESCRIPTION     
        "The value of the object tlsCondStaticMacLocale specifies for TLS
         FDB entries defined on a local SAP the value 'sap',
         remote entries defined on an SDP have the value 'sdp'.

         The value of this object must be specified when
         the row is created and cannot be changed while
         the row status is 'active'."
    ::= { tlsCondStaticMacEntry 5 }

tlsCondStaticMacPortId OBJECT-TYPE
    SYNTAX          TmnxPortID
    MAX-ACCESS      read-create
    STATUS          current
    DESCRIPTION     
        "When the value of tlsCondStaticMacLocale is 'sap', this
         object, along with tlsCondStaticMacEncapValue, specifies
         the SAP associated with the MAC address defined
         by tlsCondStaticMacAddr. This object is otherwise
         insignificant and should contain a value of 0."
    DEFVAL { 0 }
    ::= { tlsCondStaticMacEntry 6 }

tlsCondStaticMacEncapValue OBJECT-TYPE
    SYNTAX          TmnxEncapVal
    MAX-ACCESS      read-create
    STATUS          current
    DESCRIPTION     
        "The value of the object tlsCondStaticMacEncapValue specifies, when
         the value of tlsCondStaticMacLocale is 'sap', along with
         tlsCondStaticMacPortId, SAP associated with the MAC address defined
         by tlsCondStaticMacAddr. This object is otherwise insignificant
         and should contain a value of 0."
    DEFVAL { 0 }
    ::= { tlsCondStaticMacEntry 7 }

tlsCondStaticMacSdpId OBJECT-TYPE
    SYNTAX          SdpId
    MAX-ACCESS      read-create
    STATUS          current
    DESCRIPTION     
        "The value of the object tlsCondStaticMacSdpId specifies, when the
         value of tlsCondStaticMacLocale is 'sdp', along with tlsCondStaticMacVcId,the
         SDP Binding associated with the MAC address
         defined by tlsCondStaticMacAddr. This object is other-
         wise insignificant and should contain a value of 0."
    DEFVAL { 0 }
    ::= { tlsCondStaticMacEntry 8 }

tlsCondStaticMacVcId OBJECT-TYPE
    SYNTAX          Unsigned32
    MAX-ACCESS      read-create
    STATUS          current
    DESCRIPTION     
        "The value of the object tlsCondStaticMacVcId specifies, when the
         value of tlsCondStaticMacLocale is 'sdp', along with 
         tlsCondStaticMacSdpId, the SDP Binding associated with the MAC 
         address defined by tlsCondStaticMacAddr. This object is other-wise
         insignificant and should contain a value of 0."
    DEFVAL { 0 }
    ::= { tlsCondStaticMacEntry 9 }

tlsCondStaticMacMonitor OBJECT-TYPE
    SYNTAX          INTEGER {
                        none      (0),
                        fwdStatus (1)
                    }
    MAX-ACCESS      read-create
    STATUS          current
    DESCRIPTION     
        "The value of the object tlsCondStaticMacMonitor specifies the entity
         to be monitored to decide whether this this entry can be installed
         in the FDB.
         
         An 'inconsistentValue' error is returned if tlsCondStaticMacMonitor
         is not set at the creation time of the entry."
    DEFVAL { none }
    ::= { tlsCondStaticMacEntry 10 }

-- -------------------------------------------------------------
-- count of MAC address entries of different FDB type in a vpls
-- -------------------------------------------------------------
svcTlsFdbMacStatsTable OBJECT-TYPE
    SYNTAX          SEQUENCE OF SvcTlsFdbMacStatsEntry
    MAX-ACCESS      not-accessible
    STATUS          current
    DESCRIPTION
        "This table maintains the count of MAC address entries per FDB
         type for VPLS services."
    ::= { tmnxSvcObjs 150 } 
    
svcTlsFdbMacStatsEntry OBJECT-TYPE
    SYNTAX          SvcTlsFdbMacStatsEntry
    MAX-ACCESS      not-accessible
    STATUS          current
    DESCRIPTION
        "This entry maintains the count of MAC address entries per FDB
         type for a VPLS service."
    INDEX { svcId, tlsFdbType }
    ::= { svcTlsFdbMacStatsTable 1 }

SvcTlsFdbMacStatsEntry ::=
    SEQUENCE {
        svcTlsFdbMacStatsNumEntries Unsigned32
    }

svcTlsFdbMacStatsNumEntries OBJECT-TYPE
    SYNTAX Unsigned32
    MAX-ACCESS read-only
    STATUS current
    DESCRIPTION
        "The value of svcTlsFdbMacStatsNumEntries indicates the number of MAC
         address entries of the FDB type in this service."
    ::= { svcTlsFdbMacStatsEntry 1 }

-- -------------------------------------
-- Oper-group BFD Interface Table
-- -------------------------------------

svcOperGrpBfdTblLastChgd OBJECT-TYPE
    SYNTAX      TimeStamp
    MAX-ACCESS  read-only
    STATUS      current
    DESCRIPTION
        "The value of svcOperGrpBfdTblLastChgd indicates the sysUpTime
         at the time of the last modification of svcOperGrpBfdTable.

         If no changes were made to the entry since the last re-initialization
         of the local network management subsystem, then this object contains a
         zero value."
    ::= { tmnxSvcTimeObjs 2 }

svcOperGrpBfdTable OBJECT-TYPE
    SYNTAX       SEQUENCE OF SvcOperGrpBfdEntry
    MAX-ACCESS   not-accessible
    STATUS       current
    DESCRIPTION  
        "The svcOperGrpBfdTable maintains BFD information for operational
         groups."
    ::= { tmnxSvcObjs 151 }

svcOperGrpBfdEntry OBJECT-TYPE
    SYNTAX       SvcOperGrpBfdEntry
    MAX-ACCESS   not-accessible
    STATUS       current
    DESCRIPTION 
        "The svcOperGrpBfdTable maintains BFD information for a specific
         operational group."
    INDEX { svcOperGrpName }
    ::= { svcOperGrpBfdTable 1 }

SvcOperGrpBfdEntry ::= 
    SEQUENCE {
        svcOperGrpBfdRowStatus        RowStatus,
        svcOperGrpBfdLastChgd         TimeStamp,
        svcOperGrpBfdSvcId            TmnxServId,
        svcOperGrpBfdIfName           TNamedItemOrEmpty,
        svcOperGrpBfdDestIpType       InetAddressType,
        svcOperGrpBfdDestIp           InetAddress,
        svcOperGrpBfdSrcIpType        InetAddressType,
        svcOperGrpBfdSrcIp            InetAddress,
        svcOperGrpBfdSessOperState    TmnxBfdIntfSessOperState
    }

svcOperGrpBfdRowStatus  OBJECT-TYPE
    SYNTAX       RowStatus
    MAX-ACCESS   read-create
    STATUS       current
    DESCRIPTION 
        "This object svcOperGrpBfdRowStatus is used for creation or
         deletion of entries in the svcOperGrpBfdEntry."
    ::= { svcOperGrpBfdEntry 1 }    

svcOperGrpBfdLastChgd  OBJECT-TYPE
    SYNTAX       TimeStamp
    MAX-ACCESS   read-only
    STATUS       current
    DESCRIPTION 
        "The value of svcOperGrpBfdLastChgd specifies the
         time stamp of the last change to this row of this table."
    ::= { svcOperGrpBfdEntry 2 } 
   
svcOperGrpBfdSvcId OBJECT-TYPE
    SYNTAX       TmnxServId
    MAX-ACCESS   read-create
    STATUS       current
    DESCRIPTION
        "The value of svcOperGrpBfdSvcId specifies the service
         ID of the interface running BFD."
    DEFVAL { 0 }
    ::= { svcOperGrpBfdEntry 3 }

svcOperGrpBfdIfName OBJECT-TYPE
    SYNTAX       TNamedItemOrEmpty
    MAX-ACCESS   read-create
    STATUS       current
    DESCRIPTION         
        "The value of svcOperGrpBfdIfName specifies the name of the
         interface running BFD."
    DEFVAL { ''H }
    ::= { svcOperGrpBfdEntry 4 }

svcOperGrpBfdDestIpType OBJECT-TYPE
    SYNTAX       InetAddressType
    MAX-ACCESS   read-create
    STATUS       current
    DESCRIPTION
        "The value of svcOperGrpBfdDestIpType specifies the address type
         of svcOperGrpBfdDestIp object."
    DEFVAL { unknown }
    ::= { svcOperGrpBfdEntry 5 }

svcOperGrpBfdDestIp OBJECT-TYPE
    SYNTAX       InetAddress (SIZE (0|4|16))
    MAX-ACCESS   read-create
    STATUS       current
    DESCRIPTION
        "The value of svcOperGrpBfdDestIp specifies the destination
         IP address on the interface running BFD."
    DEFVAL { ''H }
    ::= { svcOperGrpBfdEntry 6 }

svcOperGrpBfdSrcIpType OBJECT-TYPE
    SYNTAX       InetAddressType
    MAX-ACCESS   read-only
    STATUS       current
    DESCRIPTION
        "The value of svcOperGrpBfdSrcIpType indicates the address type
         of svcOperGrpBfdSrcIp object."
    ::= { svcOperGrpBfdEntry 7 }

svcOperGrpBfdSrcIp OBJECT-TYPE
    SYNTAX       InetAddress (SIZE (0|4|16))
    MAX-ACCESS   read-only
    STATUS       current
    DESCRIPTION
        "The value of svcOperGrpBfdSrcIp indicates the source
         IP address on the interface running BFD."
    ::= { svcOperGrpBfdEntry 8 }

svcOperGrpBfdSessOperState OBJECT-TYPE
    SYNTAX       TmnxBfdIntfSessOperState
    MAX-ACCESS   read-only
    STATUS       current
    DESCRIPTION
        "The value of svcOperGrpBfdSessOperState indicates the operational
         state of the BFD session the operation-group is relying upon for its
         fast triggering mechanism."
    ::= { svcOperGrpBfdEntry 9 }


-- --------------------------------------------------
-- VPLS - VXLAN VNI table
-- --------------------------------------------------

svcTlsVxlanTblLastChgd OBJECT-TYPE
    SYNTAX      TimeStamp
    MAX-ACCESS  read-only
    STATUS      current
    DESCRIPTION
        "The value of svcTlsVxlanTblLastChgd indicates the sysUpTime
         at the time of the last modification of svcTlsVxlanTable.

         If no changes were made to the entry since the last re-initialization
         of the local network management subsystem, then this object contains a
         zero value."
    ::= { tmnxSvcTimeObjs 3 }

svcTlsVxlanTable OBJECT-TYPE
    SYNTAX       SEQUENCE OF SvcTlsVxlanEntry
    MAX-ACCESS   not-accessible
    STATUS       current
    DESCRIPTION  
        "The svcTlsVxlanTable maintains VXLAN Network Identifiers (VNIs) for VPLS services."
    ::= { tmnxSvcObjs 152 }

svcTlsVxlanEntry OBJECT-TYPE
    SYNTAX       SvcTlsVxlanEntry
    MAX-ACCESS   not-accessible
    STATUS       current
    DESCRIPTION 
        "The svcTlsVxlanTable maintains VXLAN Network Identifiers (VNIs) for VPLS services."
    INDEX { svcId, svcTlsVxlanVni }
    ::= { svcTlsVxlanTable 1 }

SvcTlsVxlanEntry ::= 
    SEQUENCE {
        svcTlsVxlanVni              Unsigned32,
        svcTlsVxlanRowStatus        RowStatus,
        svcTlsVxlanLastChgd         TimeStamp,
        svcTlsVxlanCreationOrigin   TmnxCreateOrigin
    }

svcTlsVxlanVni OBJECT-TYPE
    SYNTAX       Unsigned32 (1..16777215)
    MAX-ACCESS   not-accessible
    STATUS       current
    DESCRIPTION         
        "The value of svcTlsVxlanVni specifies the VNI of the VXLAN created by 
         the VPLS service."
    ::= { svcTlsVxlanEntry 1 }

svcTlsVxlanRowStatus  OBJECT-TYPE
    SYNTAX       RowStatus
    MAX-ACCESS   read-create
    STATUS       current
    DESCRIPTION 
        "This object svcTlsVxlanRowStatus is used for creation or
         deletion of entries in the svcTlsVxlanEntry."
    ::= { svcTlsVxlanEntry 2 }    

svcTlsVxlanLastChgd  OBJECT-TYPE
    SYNTAX       TimeStamp
    MAX-ACCESS   read-only
    STATUS       current
    DESCRIPTION 
        "The value of svcTlsVxlanLastChgd specifies the
         time stamp of the last change to this row of this table."
    ::= { svcTlsVxlanEntry 3 } 

svcTlsVxlanCreationOrigin  OBJECT-TYPE
    SYNTAX          TmnxCreateOrigin
    MAX-ACCESS      read-only
    STATUS          current
    DESCRIPTION     "The value of svcTlsVxlanCreationOrigin indicates the mechanism
                     used to create this entry."
    DEFVAL { manual }
    ::= { svcTlsVxlanEntry 4 }



-- ----------------------------------------
-- BGP Ethernet VPN Table
-- ----------------------------------------
svcBgpEvpnTableLastChanged  OBJECT-TYPE
    SYNTAX          TimeStamp
    MAX-ACCESS      read-only
    STATUS          current
    DESCRIPTION     
        "The value of svcBgpEvpnTableLastChanged indicates the sysUpTime at 
         the time of the last modification of svcBgpEvpnTable."
    ::= { tmnxSvcTimeObjs 4 }

svcBgpEvpnTable OBJECT-TYPE
    SYNTAX          SEQUENCE OF SvcBgpEvpnEntry
    MAX-ACCESS      not-accessible
    STATUS          current
    DESCRIPTION
        "svcBgpEvpnTable contains configuration information for Border Gateway
         Protocol Ethernet Virtual Private Networks (BGP-EVPNs) in a VPLS
         service context."
    REFERENCE
        "RFC 7348, 'VXLAN: A Framework for Overlaying Virtualized Layer 2
         Networks over Layer 3 Networks', August 2014.
         IETF draft-ietf-l2vpn-evpn-11, 'BGP MPLS Based Ethernet VPN', October
         18, 2014"
    ::= { tmnxSvcObjs 153 }

svcBgpEvpnEntry    OBJECT-TYPE
    SYNTAX          SvcBgpEvpnEntry
    MAX-ACCESS      not-accessible
    STATUS          current
    DESCRIPTION     "A BGP EVPN entry in the svcBgpEvpnTable."
    INDEX           { svcId }
    ::= { svcBgpEvpnTable 1}

SvcBgpEvpnEntry ::=    SEQUENCE {
    svcBgpEvpnRowStatus             RowStatus,
    svcBgpEvpnLastChanged           TimeStamp,
    svcBgpEvpnMacAdvertisement      TruthValue,
    svcBgpEvpnMacAdvDefaultRoute    TruthValue,
    svcBgpEvpnVxlanAdminStatus      TmnxEnabledDisabled,
    svcBgpEvpnCreationOrigin        TmnxCreateOrigin,
    svcBgpEvpnMacDupDetNumMoves     Unsigned32,
    svcBgpEvpnMacDupDetWindow       Unsigned32,
    svcBgpEvpnMacDupDetRetry        Unsigned32,
    svcBgpEvpnMacDupDetNumDups      Unsigned32,
    svcBgpEvpnIpRouteAdvertisement  TruthValue,
    svcBgpEvpnIpRouteAdverInclHost  TruthValue,
    svcBgpEvpnEvi Unsigned32,
    svcBgpEvpnCfmMacAdvertisement   TruthValue
}

svcBgpEvpnRowStatus        OBJECT-TYPE
    SYNTAX          RowStatus
    MAX-ACCESS      read-create
    STATUS          current
    DESCRIPTION
        "The value of svcBgpEvpnRowStatus is used for the creation and deletion
         of BGP EVPN context in a DC PE VPLS instance."
    ::= { svcBgpEvpnEntry 1 }

svcBgpEvpnLastChanged        OBJECT-TYPE
    SYNTAX          TimeStamp
    MAX-ACCESS      read-only
    STATUS          current
    DESCRIPTION
        "The value of svcBgpEvpnLastChanged indicates the sysUpTime at the 
         time of the last modification of this entry."
    ::= { svcBgpEvpnEntry 2 }

svcBgpEvpnMacAdvertisement  OBJECT-TYPE
    SYNTAX       TruthValue
    MAX-ACCESS   read-create
    STATUS       current
    DESCRIPTION
        "The value of svcBgpEvpnMacAdvertisement specifies whether all the 
         non BGP EVPN macs will be advertised to BGP or not."
    DEFVAL { true }
    ::= { svcBgpEvpnEntry 3 }

svcBgpEvpnMacAdvDefaultRoute   OBJECT-TYPE
    SYNTAX       TruthValue
    MAX-ACCESS   read-create
    STATUS       current
    DESCRIPTION
        "The value of svcBgpEvpnMacAdvDefaultRoute specifies whether the default
         mac will be advertised to BGP or not.

         When the value of svcBgpEvpnMacAdvDefaultRoute is true, only the 
         Default-mac is advertised."
    DEFVAL { false }
    ::= { svcBgpEvpnEntry 4 }

svcBgpEvpnVxlanAdminStatus        OBJECT-TYPE
    SYNTAX          TmnxEnabledDisabled
    MAX-ACCESS      read-create
    STATUS          current
    DESCRIPTION
        "The value of svcBgpEvpnVxlanAdminStatus specifies the desired
         administrative state for VXLANs under the BGP EVPN context in this VPLS
         service."
    DEFVAL { disabled }
    ::= { svcBgpEvpnEntry 5 }

svcBgpEvpnCreationOrigin  OBJECT-TYPE
    SYNTAX          TmnxCreateOrigin
    MAX-ACCESS      read-only
    STATUS          current
    DESCRIPTION     "The value of svcBgpEvpnCreationOrigin indicates
                     mechanism used to create this entry."
    DEFVAL { manual }
    ::= { svcBgpEvpnEntry 6 }

svcBgpEvpnMacDupDetNumMoves  OBJECT-TYPE
    SYNTAX          Unsigned32 (3..10)
    MAX-ACCESS      read-create
    STATUS          current
    DESCRIPTION     "The value of svcBgpEvpnMacDupDetNumMoves specifies number
                     of moves with in svcBgpEvpnMacDupDetWindow between evpn
                     and non-evpn destinations above which a MAC is considered
                     duplicate. This can be due to loops, incorrect
                     configuration in the network etc."
    DEFVAL { 5 }
    ::= { svcBgpEvpnEntry 7 }

svcBgpEvpnMacDupDetWindow  OBJECT-TYPE
    SYNTAX          Unsigned32 (1..15)
    UNITS           "minutes"
    MAX-ACCESS      read-create
    STATUS          current
    DESCRIPTION     "The value of svcBgpEvpnMacDupDetWindow specifies the
                     length of the window in minutes."
    DEFVAL { 3 }
    ::= { svcBgpEvpnEntry 8 }

svcBgpEvpnMacDupDetRetry  OBJECT-TYPE
    SYNTAX          Unsigned32 (0|2..60)
    UNITS           "minutes"
    MAX-ACCESS      read-create
    STATUS          current
    DESCRIPTION     "The value of svcBgpEvpnMacDupDetRetry indicates the hold
                     down time in minutes. This value is expected to be equal
                     to or more than two times that of
                     svcBgpEvpnMacDupDetWindow. If svcBgpEvpnMacDupDetRetry
                     is set to its default value, this implies that once a
                     duplicate MAC is detected, until a user intervenes or a
                     network event (MAC flush) occurs, updates for that MAC will
                     be held down. In the absence of the above mentioned events,
                     MAC duplication detection will be tried again after
                     svcBgpEvpnMacDupDetRetry time. This value is expected to be
                     either 0 (= no auto retry) or equal to more than two times
                     that of svcBgpEvpnMacDupDetWindow."
    DEFVAL { 9 }
    ::= { svcBgpEvpnEntry 9 }

svcBgpEvpnMacDupDetNumDups  OBJECT-TYPE
    SYNTAX          Unsigned32
    MAX-ACCESS      read-only
    STATUS          current
    DESCRIPTION     "The value of svcBgpEvpnMacDupDetNumDups indicates the
                     number of duplicate MAC addresses in BGP-EVPN in a
                     VPLS service context."
    ::= { svcBgpEvpnEntry 10 }


svcBgpEvpnIpRouteAdvertisement  OBJECT-TYPE
    SYNTAX       TruthValue
    MAX-ACCESS   read-create
    STATUS       current
    DESCRIPTION
        "The value of svcBgpEvpnIpRouteAdvertisement specifies whether IP Routes
        will be advertised by BGP EVPN or not."
    DEFVAL { false }
    ::= { svcBgpEvpnEntry 11 }

svcBgpEvpnIpRouteAdverInclHost  OBJECT-TYPE
    SYNTAX       TruthValue
    MAX-ACCESS   read-create
    STATUS       current
    DESCRIPTION
        "The value of svcBgpEvpnIpRouteAdverInclHost specifies whether IP
         Routes advertised by BGP EVPN will include '/32' host routes.
         
         An 'inconsistentValue' error is returned if
         svcBgpEvpnIpRouteAdverInclHost is set to 'true' when
         svcBgpEvpnIpRouteAdvertisement is set to 'false'."
    DEFVAL { false }
    ::= { svcBgpEvpnEntry 12 }

svcBgpEvpnEvi              OBJECT-TYPE
    SYNTAX        Unsigned32 (0|1..65535)
    MAX-ACCESS    read-create
    STATUS        current
    DESCRIPTION
        "BGP EVPN identifier used for the service-carving algorithm used
         for multi-homing and for auto-deriving the Route-distinguisher and
         Route-target."
    DEFVAL { 0 }
    ::= { svcBgpEvpnEntry 13 }

svcBgpEvpnCfmMacAdvertisement    OBJECT-TYPE
    SYNTAX       TruthValue
    MAX-ACCESS   read-create
    STATUS       current
    DESCRIPTION
        "The value of svcBgpEvpnCfmMacAdvertisement specifies whether or not to
         advertise the VPLS service's operational Up MEP, MIP, and Virtual MEP
         (VMEP) MAC addresses over BGP-EVPN.

         If svcBgpEvpnCfmMacAdvertisement is 'true(1)', the MAC addresses are
         advertised.

         If svcBgpEvpnCfmMacAdvertisement is 'false(2)', the MAC addresses are
         not advertised."
    DEFVAL { false }
    ::= { svcBgpEvpnEntry 14 }
--
--  Nokia SROS series Ies Interface Router Solicit Table
--
--  Augmentation of the iesIfTable.
--  Use of AUGMENTS clause implies a one-to-one dependent relationship between
--  the base table, iesIfTable, and the augmenting table,
--  tmnxIesIfRtrSolicitTable.
--  This in effect extends the iesIfTable with additional columns.
--  Creation (or deletion) of a row in the iesIfTable results in the same
--  fate for the row in the tmnxIesIfRtrSolicitTable.
--

tmnxIesIfRtrSolTableLastChanged  OBJECT-TYPE
    SYNTAX          TimeStamp
    MAX-ACCESS      read-only
    STATUS          current
    DESCRIPTION
        "The value of tmnxIesIfRtrSolTableLastChanged indicates the sysUpTime
         at the time of the last modification of tmnxIesIfRtrSolicitTable."
    ::= { tmnxSvcTimeObjs 5 }

tmnxIesIfRtrSolicitTable  OBJECT-TYPE
    SYNTAX      SEQUENCE OF TmnxIesIfRtrSolicitEntry
    MAX-ACCESS  not-accessible
    STATUS      current
    DESCRIPTION
        "The tmnxIesIfRtrSolicitTable has an entry for each IES interface
         configured in the system."
    ::= { tmnxSvcObjs 154 }

tmnxIesIfRtrSolicitEntry  OBJECT-TYPE
    SYNTAX      TmnxIesIfRtrSolicitEntry
    MAX-ACCESS  not-accessible
    STATUS      current
    DESCRIPTION
        "Each row entry contains information about an IES interface.
         Entries cannot be created and deleted via SNMP SET operations."
    AUGMENTS { iesIfEntry }
    ::= { tmnxIesIfRtrSolicitTable 1 }

TmnxIesIfRtrSolicitEntry ::=
    SEQUENCE {
        tmnxIesIfRtrSolLastMgmtChange   TimeStamp,
        tmnxIesIfRtrSolAdminStatus      TmnxEnabledDisabled,
        tmnxIesIfRtrSolUserDb           TNamedItemOrEmpty,
        tmnxIesIfRtrSolMinAuthInterval  Unsigned32,
        tmnxIesIfRtrSolInactivityTimer  Unsigned32
    }

tmnxIesIfRtrSolLastMgmtChange OBJECT-TYPE
    SYNTAX          TimeStamp
    MAX-ACCESS      read-only
    STATUS          current
    DESCRIPTION
        "The value of tmnxIesIfRtrSolLastMgmtChange indicates
         the value of the object sysUpTime at the time of the
         most recent management-initiated change to this row."
    ::= { tmnxIesIfRtrSolicitEntry 1 }

tmnxIesIfRtrSolAdminStatus OBJECT-TYPE
    SYNTAX      TmnxEnabledDisabled
    MAX-ACCESS  read-write
    STATUS      current
    DESCRIPTION
        "The value of tmnxIesIfRtrSolAdminStatus specifies the
         desired administrative state of this row."
    DEFVAL { disabled }
    ::= { tmnxIesIfRtrSolicitEntry 2 }

tmnxIesIfRtrSolUserDb OBJECT-TYPE
    SYNTAX          TNamedItemOrEmpty
    MAX-ACCESS      read-write
    STATUS          current
    DESCRIPTION
        "The value of tmnxIesIfRtrSolUserDb specifies the local
         user database to use for router solicit based authentication.

         If no authentication with the local user database is required,
         the value of this object must be set to the empty string."
    DEFVAL { "" }
    ::= { tmnxIesIfRtrSolicitEntry 3 }

tmnxIesIfRtrSolMinAuthInterval OBJECT-TYPE
    SYNTAX          Unsigned32 (1..360000)
    UNITS           "seconds"
    MAX-ACCESS      read-write
    STATUS          current
    DESCRIPTION
        "The value of tmnxIesIfRtrSolMinAuthInterval specifies the minimum
         interval between two consecutive authentication attempts for the
         same host."
    DEFVAL { 300 }
    ::= { tmnxIesIfRtrSolicitEntry 4 }

tmnxIesIfRtrSolInactivityTimer OBJECT-TYPE
    SYNTAX          Unsigned32 (1..31536000|4294967295)
    UNITS           "seconds"
    MAX-ACCESS      read-write
    STATUS          current
    DESCRIPTION
        "The value of tmnxIesIfRtrSolInactivityTimer specifies 
         the time before an inactive host is removed.

         A value of 0xFFFFFFFF specifies the inactivity timer is disabled."
    DEFVAL { 300 }
    ::= { tmnxIesIfRtrSolicitEntry 5}

-- ------------------------------------
-- VPRN Info Table
-- ------------------------------------
svcVprnInfoTableLastChanged         OBJECT-TYPE
    SYNTAX          TimeStamp
    MAX-ACCESS      read-only
    STATUS          current
    DESCRIPTION
        "The value of svcVprnInfoTableLastChanged indicates the sysUpTime at
         the time of the last modification of svcVprnInfoTable."
    ::= { tmnxSvcTimeObjs 12 }

svcVprnInfoTable                    OBJECT-TYPE
    SYNTAX          SEQUENCE OF SvcVprnInfoEntry
    MAX-ACCESS      not-accessible
    STATUS          current
    DESCRIPTION
        "The value of svcVprnInfoTable specifies VPRN service specific
         information."
    ::= { tmnxSvcObjs 167 }

svcVprnInfoEntry                    OBJECT-TYPE
    SYNTAX          SvcVprnInfoEntry
    MAX-ACCESS      not-accessible
    STATUS          current
    DESCRIPTION
        "The value of svcVprnInfoEntry has information specific to VPRN
         services."
    INDEX { svcId }
    ::= { svcVprnInfoTable 1 }

SvcVprnInfoEntry ::=
    SEQUENCE {
        svcVprnInfoEntryLastChanged        TimeStamp,
        svcNetIngQosPolicyId               TPolicyID,
        svcNetIngQosFPQGrp                 TNamedItemOrEmpty,
        svcNetIngQosFPQGrpInstanceId       TQosQGrpInstanceIDorZero,
        svcNetIngIPFilterId                TIPFilterID,
        svcNetIngIPv6FilterId              TIPFilterID
     }

svcVprnInfoEntryLastChanged         OBJECT-TYPE
    SYNTAX          TimeStamp
    MAX-ACCESS      read-only
    STATUS          current
    DESCRIPTION
        "The value of svcVprnInfoEntryLastChanged indicates the value of
         sysUpTime at the time of the last management change to any writable
         objects of this entry."
    ::= { svcVprnInfoEntry 1 }

svcNetIngQosPolicyId                OBJECT-TYPE
    SYNTAX      TPolicyID
    MAX-ACCESS  read-create
    STATUS      current
    DESCRIPTION
        "The value of svcNetIngQosPolicyId associates pre-existing
         network-policy-id to the network ingress traffic of this VPRN service."
    DEFVAL { 0 }
    ::= { svcVprnInfoEntry 2 }

svcNetIngQosFPQGrp OBJECT-TYPE
    SYNTAX          TNamedItemOrEmpty
    MAX-ACCESS      read-create
    STATUS          current
    DESCRIPTION
        "The value of svcNetIngQosFPQGrp specifies the network ingress
         forwarding-plane queue-group name for this VPRN service.

         This object must be set along with svcNetIngQosFPQGrpInstanceId
         object."
    DEFVAL { ''H }
    ::= { svcVprnInfoEntry 3 }

svcNetIngQosFPQGrpInstanceId        OBJECT-TYPE
    SYNTAX          TQosQGrpInstanceIDorZero
    MAX-ACCESS      read-create
    STATUS          current
    DESCRIPTION
        "The value of svcNetIngQosFPQGrpInstanceId specifies the instance of the
         network ingress forwarding-plane queue-group for this VPRN service.

        This object must be set along with svcNetIngQosFPQGrp object."
    DEFVAL { 0 }
    ::= { svcVprnInfoEntry 4 }

svcNetIngIPFilterId    OBJECT-TYPE
    SYNTAX      TIPFilterID
    MAX-ACCESS  read-create
    STATUS      current
    DESCRIPTION
        "The value of the object svcNetIngIPFilterId if different from '0'
        specifies the ID of configured IP filter which will be deployed on
        all line cards with network port interfaces. The filter applies to
        all traffic arriving on auto-bind and/or explicit spoke SDPs within
        this VPRN. This filter will not be applied to VPRN spoke-SDP interfaces,
        SAPs or R-VPLS endpoints.

        Chassis network mode D or higher is required otherwise the setting
        will be blocked.

        Network port L3 service aware filters do not support
        flowspec, TPSDA(Radius/Gx injected entries in a pre-reserved
        filter range), LI (cannot use filter inside LI
        infrastructure nor have LI sources within the VPRN filter)."
    DEFVAL { 0 }
    ::= { svcVprnInfoEntry 5 }

svcNetIngIPv6FilterId    OBJECT-TYPE
    SYNTAX      TIPFilterID
    MAX-ACCESS  read-create
    STATUS      current
    DESCRIPTION
        "The value of the object svcNetIngIPv6FilterId if different from '0'
        specifies the ID of configured IPv6 filter which will be deployed on
        all line cards with network port interfaces. The filter applies to all
        traffic arriving on auto-bind and/or explicit spoke SDPs within
        this VPRN. This filter will not be applied to VPRN spoke-SDP interfaces,
        SAPs or R-VPLS endpoints.

        Chassis network mode D or higher is required otherwise the setting
        will be blocked.

        Network port L3 service aware filters do not support
        flowspec, TPSDA(Radius/Gx injected entries in a pre-reserved
        filter range), LI (cannot use filter inside LI
        infrastructure nor have LI sources within the VPRN filter)."
    DEFVAL { 0 }
    ::= { svcVprnInfoEntry 6 }



-- ------------------------------------------
-- VSD Domain Table
-- ------------------------------------------

svcVsdDomainTblLastChngd  OBJECT-TYPE
    SYNTAX          TimeStamp
    MAX-ACCESS      read-only
    STATUS          current
    DESCRIPTION
        "The value of svcVsdDomainTblLastChngd indicates the sysUpTime at
         the time of the last modification of svcVsdDomainTable."
    ::= { tmnxSvcTimeObjs 6 }

svcVsdDomainTable      OBJECT-TYPE
    SYNTAX          SEQUENCE OF SvcVsdDomainEntry
    MAX-ACCESS      not-accessible
    STATUS          current
    DESCRIPTION
        "svcVsdDomainTable contains entries for each VSD static+dynamic
         domain configuration in the system.
         A domain is defined as a logical switch/router that enables Layer-2
         and Layer-3 communication."
    ::= { tmnxSvcObjs 155 }

svcVsdDomainEntry    OBJECT-TYPE
    SYNTAX          SvcVsdDomainEntry
    MAX-ACCESS      not-accessible
    STATUS          current
    DESCRIPTION     "A VSD domain entry in the svcVsdDomainTable."
    INDEX           { svcVsdDomainName  }
    ::= { svcVsdDomainTable 1}

SvcVsdDomainEntry ::=    SEQUENCE {
    svcVsdDomainRowStatus          RowStatus,
    svcVsdDomainDescription        TItemDescription,
    svcVsdDomainType               INTEGER,
    svcVsdDomainAdminState         TmnxAdminState,
    svcVsdDomainCreationOrigin     INTEGER,
    svcVsdDomainLastErrStr         TLDisplayString,
    svcVsdDomainVsdLastErrStr      TLDisplayString,
    svcVsdDomainRecParams          OCTET STRING,
    svcVsdDomainExecParams         OCTET STRING
}

svcVsdDomainRowStatus        OBJECT-TYPE
    SYNTAX          RowStatus
    MAX-ACCESS      read-create
    STATUS          current
    DESCRIPTION
        "The value of svcVsdDomainRowStatus is used for the creation and
         deletion of entries in the svcVsdDomainEntry."
    ::= { svcVsdDomainEntry 1 }

svcVsdDomainDescription OBJECT-TYPE
    SYNTAX     TItemDescription
    MAX-ACCESS read-create
    STATUS     current
    DESCRIPTION
        "The value of svcVsdDomainDescription specifies the textual description
         for this domain.
         
         An 'inconsistentValue' error is returned when this object is set to
         a different value and svcVsdDomainAdminState is set to 'inService'."
    DEFVAL { "" }
    ::= { svcVsdDomainEntry 2 }

svcVsdDomainType  OBJECT-TYPE
    SYNTAX  INTEGER {
                l2Domain   (1),
                vrfGre     (2),
                vrfVxlan   (3),
                l2DomainIrb (4)
            }
    MAX-ACCESS      read-create
    STATUS          current
    DESCRIPTION
        "The value of svcVsdDomainType specifies the type of the domain.

         An 'inconsistentValue' error is returned if the value of this object
         is set to a different value after the entry is created."
     ::= { svcVsdDomainEntry 3 }

svcVsdDomainAdminState OBJECT-TYPE
    SYNTAX      TmnxAdminState
    MAX-ACCESS  read-create
    STATUS      current
    DESCRIPTION
        "The value of svcVsdDomainAdminState specifies the administrative
         state of this domain."
    DEFVAL { outOfService }
    ::= { svcVsdDomainEntry 4 }

svcVsdDomainCreationOrigin  OBJECT-TYPE
    SYNTAX  INTEGER {
             manual   (0),
             vsd      (1)
            }
    MAX-ACCESS      read-only
    STATUS          current
    DESCRIPTION
        "The value of svcVsdDomainCreationOrigin indicates whether
         the entry was created by the User or by the VSD."
    ::= { svcVsdDomainEntry 5 }

svcVsdDomainLastErrStr  OBJECT-TYPE
    SYNTAX      TLDisplayString (SIZE (0..320))
    MAX-ACCESS  read-only
    STATUS      current
    DESCRIPTION
        "The value of svcVsdDomainLastErrStr indicates the last error to VSD
         for with this domain."
    ::= { svcVsdDomainEntry 6 }

svcVsdDomainVsdLastErrStr  OBJECT-TYPE
    SYNTAX      TLDisplayString (SIZE (0..320))
    MAX-ACCESS  read-only
    STATUS      current
    DESCRIPTION
        "The value of svcVsdDomainVsdLastErrStr indicates the last error
         from VSD to this domain."
    ::= { svcVsdDomainEntry 7 }

svcVsdDomainRecParams OBJECT-TYPE
    SYNTAX      OCTET STRING (SIZE (0..1000))
    MAX-ACCESS  read-only
    STATUS      current
    DESCRIPTION
        "The value of svcVsdDomainRecParams indicates the
         parameter string of the script instance last received from
         the VSD." 
    ::= { svcVsdDomainEntry 8 }

svcVsdDomainExecParams OBJECT-TYPE
    SYNTAX      OCTET STRING (SIZE (0..1000))
    MAX-ACCESS  read-only
    STATUS      current
    DESCRIPTION
        "The value of svcVsdDomainExecParams indicates the parameter
         string of the script instance that was last executed 
         successfully." 
    ::= { svcVsdDomainEntry 9 }

-- ------------------------------------------
-- Proxy ARP Table
-- ------------------------------------------

svcTlsProxyArpTblLastChngd  OBJECT-TYPE
    SYNTAX          TimeStamp
    MAX-ACCESS      read-only
    STATUS          current
    DESCRIPTION
        "The value of svcTlsProxyArpTblLastChngd indicates the sysUpTime at
         the time of the last modification of svcTlsProxyArpTable."
    ::= { tmnxSvcTimeObjs 7 }

svcTlsProxyArpTable      OBJECT-TYPE
    SYNTAX          SEQUENCE OF SvcProxyArpEntry
    MAX-ACCESS      not-accessible
    STATUS          current
    DESCRIPTION
        "svcTlsProxyArpTable contains entries for each host in the system."
    ::= { tmnxSvcObjs 156 }

svcTlsProxyArpEntry    OBJECT-TYPE
    SYNTAX          SvcProxyArpEntry
    MAX-ACCESS      not-accessible
    STATUS          current
    DESCRIPTION     "A Proxy ARP entry in the svcTlsProxyArpTable."
    INDEX           { svcId, svcTlsProxyArpIpAddrType, svcTlsProxyArpIpAddr}
    ::= { svcTlsProxyArpTable 1}

SvcProxyArpEntry ::=    SEQUENCE {
    svcTlsProxyArpIpAddrType       InetAddressType,
    svcTlsProxyArpIpAddr           InetAddress,
    svcTlsProxyArpMacAddr          MacAddress,
    svcTlsProxyArpType             TmnxProxyEntryType,
    svcTlsProxyArpLastChgd         TimeStamp,
    svcTlsProxyArpStatus           INTEGER
}

svcTlsProxyArpIpAddrType OBJECT-TYPE
    SYNTAX          InetAddressType
    MAX-ACCESS      not-accessible
    STATUS          current
    DESCRIPTION     "The value of svcArpHostIpAddrType indicates the
                     address type of svcTlsProxyArpIpAddr."
    ::= { svcTlsProxyArpEntry 1 }

svcTlsProxyArpIpAddr OBJECT-TYPE
    SYNTAX          InetAddress (SIZE(0|4))
    MAX-ACCESS      not-accessible
    STATUS          current
    DESCRIPTION     "The value of svcTlsProxyArpIpAddr indicates the IP
                     address of the host."
    ::= { svcTlsProxyArpEntry 2 }

svcTlsProxyArpMacAddr OBJECT-TYPE
    SYNTAX          MacAddress
    MAX-ACCESS      read-only
    STATUS          current
    DESCRIPTION     "The value of svcTlsProxyArpIpAddr indicates the MAC address
                     mapping for the ARP host indicated by svcTlsProxyArpIpAddr."
    ::= { svcTlsProxyArpEntry 3 }

svcTlsProxyArpType OBJECT-TYPE
    SYNTAX          TmnxProxyEntryType
    MAX-ACCESS      read-only
    STATUS          current
    DESCRIPTION     "The value of svcTlsProxyArpType indicates the type
                     of proxy ARP entry."
    ::= { svcTlsProxyArpEntry 4 }

svcTlsProxyArpLastChgd        OBJECT-TYPE
    SYNTAX          TimeStamp
    MAX-ACCESS      read-only
    STATUS          current
    DESCRIPTION     "The value of svcTlsProxyArpLastChgd indicates the
                     sysUpTime at the time of the last modification of this
                     entry."
    ::= { svcTlsProxyArpEntry 5 }

svcTlsProxyArpStatus        OBJECT-TYPE
    SYNTAX          INTEGER {
                          active  (1),
                          inActv  (2),
                          pendng  (3) -- confirm-pending
                    }
    MAX-ACCESS      read-only
    STATUS          current
    DESCRIPTION     "The value of svcTlsProxyArpStatus indicates if proxy ARP
                     will respond to ARP request for the IP address
                     corresponding to this entry."
    ::= { svcTlsProxyArpEntry 6 }

-- ------------------------------------------
-- VSD Reference Table
-- ------------------------------------------

svcVsdDomainToSvcTblLastChngd  OBJECT-TYPE
     SYNTAX          TimeStamp
     MAX-ACCESS      read-only
     STATUS          current
     DESCRIPTION
         "The value of svcVsdDomainToSvcTblLastChngd indicates the sysUpTime at
          the time of the last modification of svcVsdDomainToSvcTable."
     ::= { tmnxSvcTimeObjs 8 }

svcVsdDomainToSvcTable      OBJECT-TYPE
     SYNTAX          SEQUENCE OF SvcVsdDomainToSvcEntry
     MAX-ACCESS      not-accessible
     STATUS          current
     DESCRIPTION
         "svcVsdDomainToSvcTable contains information about services associated 
          with the VSD domain."
     ::= { tmnxSvcObjs 157 }

svcVsdDomainToSvcEntry    OBJECT-TYPE
     SYNTAX          SvcVsdDomainToSvcEntry
     MAX-ACCESS      not-accessible
     STATUS          current
     DESCRIPTION     "An entry about a service associated with the VSD domain."
     INDEX           { 
                        svcVsdDomainName,
                        svcId
                     }
     ::= { svcVsdDomainToSvcTable 1}

SvcVsdDomainToSvcEntry ::=    SEQUENCE {
     svcVsdDomainToSvcRowStatus            RowStatus,
     svcVsdDomainToSvcCreationOrigin         INTEGER
}

svcVsdDomainToSvcRowStatus        OBJECT-TYPE
    SYNTAX          RowStatus
    MAX-ACCESS      read-create
    STATUS          current
    DESCRIPTION
        "The value of svcVsdDomainToSvcRowStatus is used for the creation and deletion
         of entries in the svcVsdDomainToSvcEntry."
    ::= { svcVsdDomainToSvcEntry 1 }

svcVsdDomainToSvcCreationOrigin  OBJECT-TYPE
    SYNTAX  INTEGER {
             manual   (0),
             vsd      (1)
            }
    MAX-ACCESS      read-only
    STATUS          current
    DESCRIPTION
        "The value of the object svcVsdDomainToSvcCreationOrigin  specifies whether
         the entry was created by the User or by the VSD."
     ::= { svcVsdDomainToSvcEntry  2 }


-- ----------------------------------------
-- Detected Duplicate Macs Table
-- ----------------------------------------

svcBgpEvpnDetDupMacTable OBJECT-TYPE
    SYNTAX          SEQUENCE OF SvcBgpEvpnDetDupMacEntry
    MAX-ACCESS      not-accessible
    STATUS          current
    DESCRIPTION     "svcBgpEvpnDetDupMacTable contains entries for MACs that
                     are detected as duplicates in a VPLS service context."
    ::= { tmnxSvcObjs 158 }

svcBgpEvpnDetDupMacEntry    OBJECT-TYPE
    SYNTAX          SvcBgpEvpnDetDupMacEntry
    MAX-ACCESS      not-accessible
    STATUS          current
    DESCRIPTION     "A duplicate MAC hold down entry in the
                     svcBgpEvpnDetDupMacTable."
    INDEX           { svcId, svcBgpEvpnDetDupMacAddress }
    ::= { svcBgpEvpnDetDupMacTable 1}

SvcBgpEvpnDetDupMacEntry ::=    SEQUENCE {
    svcBgpEvpnDetDupMacAddress               MacAddress,
    svcBgpEvpnDetDupMacTime                  TimeStamp
}

svcBgpEvpnDetDupMacAddress  OBJECT-TYPE
    SYNTAX          MacAddress
    MAX-ACCESS      read-only
    STATUS          current
    DESCRIPTION     "The value of svcBgpEvpnDetDupMacAddress indicates the MAC
                     Address that is detected as a duplicate in a VPLS
                     instance."
    ::= { svcBgpEvpnDetDupMacEntry 1 }

svcBgpEvpnDetDupMacTime  OBJECT-TYPE
    SYNTAX          TimeStamp
    MAX-ACCESS      read-only
    STATUS          current
    DESCRIPTION     "The value of svcBgpEvpnDetDupMacTime indicates the time
                     when the MAC address indicated by
                     svcBgpEvpnDetDupMacAddress was detected as duplicate."
    ::= { svcBgpEvpnDetDupMacEntry 2 }


-- ----------------------------------------
-- Service VTEP Table
-- ----------------------------------------

svcVTEPTable        OBJECT-TYPE
    SYNTAX          SEQUENCE OF SvcVTEPEntry
    MAX-ACCESS      not-accessible
    STATUS          current
    DESCRIPTION     "svcVTEPTable contains entries for all the VTEP Addresses
                     in the system."
    ::= { tmnxSvcObjs 159 }

svcVTEPEntry        OBJECT-TYPE
    SYNTAX          SvcVTEPEntry
    MAX-ACCESS      not-accessible
    STATUS          current
    DESCRIPTION     "A VTEP entry in the svcVTEPTable."
    INDEX           { svcVTEPAddrType, svcVTEPAddress }
    ::= { svcVTEPTable 1}

SvcVTEPEntry ::=    SEQUENCE {
    svcVTEPAddrType     InetAddressType,
    svcVTEPAddress      InetAddress,
    svcVTEPNumEgrVNIs   Unsigned32,
    svcVTEPOperState    ServiceOperStatus
}

svcVTEPAddrType     OBJECT-TYPE
    SYNTAX          InetAddressType
    MAX-ACCESS      read-only
    STATUS          current
    DESCRIPTION     "The value of the object svcVTEPAddrType indicates the type
                     of the address associated with svcVTEPAddress."
    ::= { svcVTEPEntry 1 }

svcVTEPAddress      OBJECT-TYPE
    SYNTAX          InetAddress (SIZE(4))
    MAX-ACCESS      read-only
    STATUS          current
    DESCRIPTION     "The value of the object svcVTEPAddress indicates a VXLAN
                     (virtual extensible LAN) Tunnel Endpoint address present in
                     the system."
    ::= { svcVTEPEntry 2 }

svcVTEPNumEgrVNIs   OBJECT-TYPE
    SYNTAX          Unsigned32
    MAX-ACCESS      read-only
    STATUS          current
    DESCRIPTION     "The value of the object svcVTEPNumEgrVNIs indicates the
                     number of egress VNIs associated with this VTEP in the
                     system."
    ::= { svcVTEPEntry 3 }

svcVTEPOperState    OBJECT-TYPE
    SYNTAX          ServiceOperStatus
    MAX-ACCESS      read-only
    STATUS          current
    DESCRIPTION     "The value of the object svcVTEPOperState indicates the
                     operational status of the VTEP."
    ::= { svcVTEPEntry 4 }

-- ----------------------------------------
-- Service VPLS Egress VNI Table
-- ----------------------------------------

svcTlsVTEPEgrVNITable OBJECT-TYPE
    SYNTAX          SEQUENCE OF SvcTlsVTEPEgrVNIEntry
    MAX-ACCESS      not-accessible
    STATUS          current
    DESCRIPTION     "svcTlsVTEPEgrVNITable contains entries for all the VTEP
                     addresses and Egress VNIs associated with a VPLS service."
    ::= { tmnxSvcObjs 160 }

svcTlsVTEPEgrVNIEntry        OBJECT-TYPE
    SYNTAX          SvcTlsVTEPEgrVNIEntry
    MAX-ACCESS      not-accessible
    STATUS          current
    DESCRIPTION     "A VTEP entry in the svcTlsVTEPEgrVNITable."
    INDEX           { svcId, svcTlsVTEPEgrVNIVTEPAddrType,
                        svcTlsVTEPEgrVNIVTEPAddress,
                        svcTlsVTEPEgrVNIEgrVNI }
    ::= { svcTlsVTEPEgrVNITable 1}

SvcTlsVTEPEgrVNIEntry ::=    SEQUENCE {
    svcTlsVTEPEgrVNIVTEPAddrType    InetAddressType,
    svcTlsVTEPEgrVNIVTEPAddress     InetAddress,
    svcTlsVTEPEgrVNIEgrVNI          Unsigned32,
    svcTlsVTEPEgrVNINumMACs         Unsigned32,
    svcTlsVTEPEgrVNIInMcastList     TruthValue,
    svcTlsVTEPEgrVNIOperState       ServiceOperStatus,
    svcTlsVTEPEgrVNIL2EsPbr         TruthValue
}

svcTlsVTEPEgrVNIVTEPAddrType     OBJECT-TYPE
    SYNTAX          InetAddressType
    MAX-ACCESS      read-only
    STATUS          current
    DESCRIPTION     "The value of the object svcTlsVTEPEgrVNIVTEPAddrType
                     indicates the type of the address associated with
                     svcTlsVTEPEgrVNIVTEPAddress."
    ::= { svcTlsVTEPEgrVNIEntry 1 }

svcTlsVTEPEgrVNIVTEPAddress OBJECT-TYPE
    SYNTAX          InetAddress (SIZE(4))
    MAX-ACCESS      read-only
    STATUS          current
    DESCRIPTION     "The value of the object svcTlsVTEPEgrVNIVTEPAddress
                     indicates a VXLAN (virtual extensible LAN) Tunnel Endpoint
                     address associated with the VPLS service."
    ::= { svcTlsVTEPEgrVNIEntry 2 }

svcTlsVTEPEgrVNIEgrVNI    OBJECT-TYPE
    SYNTAX          Unsigned32 (1..16777215)
    MAX-ACCESS      read-only
    STATUS          current
    DESCRIPTION     "The value of svcTlsVTEPEgrVNIEgrVNI indicates the VNI of
                     the VXLAN created by the VPLS service."
    ::= { svcTlsVTEPEgrVNIEntry 3 }

svcTlsVTEPEgrVNINumMACs   OBJECT-TYPE
    SYNTAX          Unsigned32
    MAX-ACCESS      read-only
    STATUS          current
    DESCRIPTION     "The value of the object svcTlsVTEPEgrVNINumMACs indicates
                     the number of MACs associated with the VPLS service."
    ::= { svcTlsVTEPEgrVNIEntry 4 }

svcTlsVTEPEgrVNIInMcastList    OBJECT-TYPE
    SYNTAX          TruthValue
    MAX-ACCESS      read-only
    STATUS          current
    DESCRIPTION     "The value of the object svcTlsVTEPEgrVNIInMcastList
                     indicates if the VPLS service is included in the multicast
                     list."
    ::= { svcTlsVTEPEgrVNIEntry 5 }

svcTlsVTEPEgrVNIOperState    OBJECT-TYPE
    SYNTAX          ServiceOperStatus
    MAX-ACCESS      read-only
    STATUS          current
    DESCRIPTION     "The value of the object svcTlsVTEPEgrVNIOperState
                     indicates the operational status of the VTEP-Egress VNI
                     associated with the VPLS service."
    ::= { svcTlsVTEPEgrVNIEntry 6 }

svcTlsVTEPEgrVNIL2EsPbr     OBJECT-TYPE
    SYNTAX          TruthValue
    MAX-ACCESS      read-only
    STATUS          current
    DESCRIPTION     "The value of the object svcTlsVTEPEgrVNIL2EsPbr
                     indicates if the VTEP-VNI is programmed due to PBR."
    ::= { svcTlsVTEPEgrVNIEntry 7 }                  

-- ----------------------------------------
-- Service VTEP Egress VNI Table
-- ----------------------------------------

svcVTEPEgrVNITable  OBJECT-TYPE
    SYNTAX          SEQUENCE OF SvcVTEPEgrVNIEntry
    MAX-ACCESS      not-accessible
    STATUS          current
    DESCRIPTION     "svcVTEPEgrVNITable contains entries for all VTEP and Egress
                     VNIs in the system."
    ::= { tmnxSvcObjs 161 }

svcVTEPEgrVNIEntry  OBJECT-TYPE
    SYNTAX          SvcVTEPEgrVNIEntry
    MAX-ACCESS      not-accessible
    STATUS          current
    DESCRIPTION     "An entry in the svcVTEPEgrVNITable."
    INDEX           { svcVTEPEgrVNIVTEPAddrType, svcVTEPEgrVNIVTEPAddress,
                      svcVTEPEgrVNIEgrVNI}
    ::= { svcVTEPEgrVNITable 1 }

SvcVTEPEgrVNIEntry ::=    SEQUENCE {
    svcVTEPEgrVNIVTEPAddrType   InetAddressType,
    svcVTEPEgrVNIVTEPAddress    InetAddress,
    svcVTEPEgrVNIEgrVNI         Unsigned32,
    svcVTEPEgrVNISvcId          TmnxServId
}

svcVTEPEgrVNIVTEPAddrType OBJECT-TYPE
    SYNTAX          InetAddressType
    MAX-ACCESS      read-only
    STATUS          current
    DESCRIPTION     "The value of the object svcVTEPEgrVNIVTEPAddrType indicates
                     the type of the address associated with
                     svcVTEPEgrVNIVTEPAddress."
    ::= { svcVTEPEgrVNIEntry 1 }

svcVTEPEgrVNIVTEPAddress OBJECT-TYPE
    SYNTAX          InetAddress (SIZE(4))
    MAX-ACCESS      read-only
    STATUS          current
    DESCRIPTION     "The value of the object svcVTEPEgrVNIVTEPAddress indicates
                     a VXLAN (virtual extensible LAN) Tunnel Endpoint address."
    ::= { svcVTEPEgrVNIEntry 2 }

svcVTEPEgrVNIEgrVNI OBJECT-TYPE
    SYNTAX          Unsigned32
    MAX-ACCESS      read-only
    STATUS          current
    DESCRIPTION     "The value of the object svcVTEPEgrVNIEgrVNI indicates the
                     value of the VNI of the VXLAN."
    ::= { svcVTEPEgrVNIEntry 3 }

svcVTEPEgrVNISvcId  OBJECT-TYPE
    SYNTAX          TmnxServId
    MAX-ACCESS      read-only
    STATUS          current
    DESCRIPTION     "The value of the object svcVTEPEgrVNISvcId indicates the
                     service associated with the VTEP-Egress VNI."
    ::= { svcVTEPEgrVNIEntry 4 }


-- ------------------------------
-- PBB MLD-Snooping Mrouter Table
-- ------------------------------
svcTlsPbbMldSnpgMRtrTable OBJECT-TYPE
    SYNTAX          SEQUENCE OF SvcTlsPbbMldSnpgMRtrEntry
    MAX-ACCESS      not-accessible
    STATUS          current
    DESCRIPTION     "A table that contains 
                     Provider Backbone Bridging (PBB/IEEE 802.1ah) MLD 
                     Snooping MRouter Destination information."
    ::= { tmnxSvcObjs 162 }

svcTlsPbbMldSnpgMRtrEntry OBJECT-TYPE
    SYNTAX          SvcTlsPbbMldSnpgMRtrEntry
    MAX-ACCESS      not-accessible
    STATUS          current
    DESCRIPTION     "PBB I-Component instance-specific information about a 
                     specific MLD Snooping MRouter in the B-Component instance.
    
                     Entries in this table can be created or deleted 
                     via SNMP operations."
    INDEX           { svcTlsPbbMldSnpgMRtrSvcIdIVpls,
                      svcTlsPbbMldSnpgMRtrSvcIdBVpls, 
                      IMPLIED svcTlsPbbMldSnpgMRtrMacName
                    }
    ::= { svcTlsPbbMldSnpgMRtrTable 1 }

SvcTlsPbbMldSnpgMRtrEntry ::=
    SEQUENCE {
        svcTlsPbbMldSnpgMRtrSvcIdIVpls   TmnxServId,
        svcTlsPbbMldSnpgMRtrSvcIdBVpls   TmnxServId,
        svcTlsPbbMldSnpgMRtrMacName      TNamedItem,
        svcTlsPbbMldSnpgMRtrRowStatus    RowStatus,
        svcTlsPbbMldSnpgMRtrLastCh       TimeStamp
    }

svcTlsPbbMldSnpgMRtrSvcIdIVpls OBJECT-TYPE
    SYNTAX          TmnxServId
    MAX-ACCESS      not-accessible
    STATUS          current
    DESCRIPTION     "The value of the object svcTlsPbbMldSnpgMRtrSvcIdIVpls 
                     specifies the Service identifier of the I-Component 
                     instance."
    ::= { svcTlsPbbMldSnpgMRtrEntry 1 }

svcTlsPbbMldSnpgMRtrSvcIdBVpls OBJECT-TYPE
    SYNTAX          TmnxServId
    MAX-ACCESS      not-accessible
    STATUS          current
    DESCRIPTION     "The value of the object svcTlsPbbMldSnpgMRtrSvcIdBVpls 
                     specifies the Service identifier of the B-Component 
                     instance."
    ::= { svcTlsPbbMldSnpgMRtrEntry 2 }

svcTlsPbbMldSnpgMRtrMacName OBJECT-TYPE
    SYNTAX          TNamedItem
    MAX-ACCESS      not-accessible
    STATUS          current
    DESCRIPTION     "The value of svcTlsPbbMldSnpgMRtrMacName specifies 
                     the Destination MAC-Address-Name in the Backbone VPLS 
                     to reach a specific MLD Snooping MRouter.
                     
                     In the case of an I-Component instance that is multi-homed
                     on 2 physical nodes, an I-component instance, after
                     becoming active, uses this MAC address as the destination
                     MAC address to reach that MLD Snooping MRouter.

                     This allows to maintain the communication with that 
                     MRouter while no MLD Queries from that MRouter have been
                     snooped by this I-component instance."
    ::= { svcTlsPbbMldSnpgMRtrEntry 3 }

svcTlsPbbMldSnpgMRtrRowStatus OBJECT-TYPE
    SYNTAX          RowStatus
    MAX-ACCESS      read-create
    STATUS          current
    DESCRIPTION     "The value of svcTlsPbbMldSnpgMRtrRowStatus specifies 
                     the row status of this row. 
                     
                     The only values supported during a set operation are
                     'createAndGo' and 'destroy'."
    ::= { svcTlsPbbMldSnpgMRtrEntry 4 }

svcTlsPbbMldSnpgMRtrLastCh OBJECT-TYPE
    SYNTAX          TimeStamp
    MAX-ACCESS      read-only
    STATUS          current
    DESCRIPTION
                    "The value of svcTlsPbbMldSnpgMRtrLastCh indicates 
                     the sysUpTime at the time of the most recent 
                     management-initiated change to this table row."
    ::= { svcTlsPbbMldSnpgMRtrEntry 5 }

-- ------------------------------
-- IES interface IPoE Table
-- ------------------------------
tmnxSvcIesIfIpoeTableLastChanged OBJECT-TYPE
    SYNTAX          TimeStamp
    MAX-ACCESS      read-only
    STATUS          current
    DESCRIPTION
        "The value of tmnxSvcIesIfIpoeTableLastChanged indicates the sysUpTime
         at the time of the last modification of tmnxSvcIesIfIpoeTable."
    ::= { tmnxSvcTimeObjs 9 }

tmnxSvcIesIfIpoeTable            OBJECT-TYPE
    SYNTAX      SEQUENCE OF TmnxSvcIesIfIpoeEntry
    MAX-ACCESS  not-accessible
    STATUS      current
    DESCRIPTION
        "The table tmnxSvcIesIfIpoeTable contains IES interface IPoE 
         configuration information.
         
         A row is automatically created in the tmnxSvcIesIfIpoeTable for  
         an entry in the iesIfTable depending on the value of the object
         iesIfType."
    ::= { tmnxSvcObjs 163  }

tmnxSvcIesIfIpoeEntry            OBJECT-TYPE
    SYNTAX      TmnxSvcIesIfIpoeEntry
    MAX-ACCESS  not-accessible
    STATUS      current
    DESCRIPTION
        "Each row entry represents information related to IPoE session for 
         an IES interface in the system.

         Rows in table tmnxSvcIesIfIpoeTable cannot be created and deleted via
         SNMP SET operations, they are dependent on rows in table iesIfTable
         with indexes matching svcId and iesIfIndex."
    INDEX       { svcId, iesIfIndex }
    ::= { tmnxSvcIesIfIpoeTable 1 }

TmnxSvcIesIfIpoeEntry ::=
    SEQUENCE {
        tmnxSvcIesIfIpoeLastChange       TimeStamp,
        tmnxSvcIesIfIpoeAdminState       TmnxEnabledDisabled,
        tmnxSvcIesIfIpoeDescription      TItemDescription,
        tmnxSvcIesIfIpoePolicy           TNamedItemOrEmpty,
        tmnxSvcIesIfIpoeUserDb           TNamedItemOrEmpty,
        tmnxSvcIesIfIpoeSessionLimit     Unsigned32,
        tmnxSvcIesIfIpoeSapSessionLimit  Unsigned32,
        tmnxSvcIesIfIpoeMinAuthInterval  Unsigned32,
        tmnxSvcIesIfIpoeForceAuth        BITS
    }

tmnxSvcIesIfIpoeLastChange       OBJECT-TYPE
    SYNTAX          TimeStamp
    MAX-ACCESS      read-only
    STATUS          current
    DESCRIPTION
        "The value of tmnxSvcIesIfIpoeLastChange indicates
         the value of the object sysUpTime at the time of the
         most recent management-initiated change to this row."
    ::= { tmnxSvcIesIfIpoeEntry 1 }

tmnxSvcIesIfIpoeAdminState       OBJECT-TYPE
    SYNTAX      TmnxEnabledDisabled
    MAX-ACCESS  read-write
    STATUS      current
    DESCRIPTION
        "The value of tmnxSvcIesIfIpoeAdminState specifies the
         desired administrative state of this row."
    DEFVAL { disabled }
    ::= { tmnxSvcIesIfIpoeEntry 2 }
   
tmnxSvcIesIfIpoeDescription      OBJECT-TYPE
    SYNTAX      TItemDescription
    MAX-ACCESS  read-write
    STATUS      current
    DESCRIPTION
        "The value of the object tmnxSvcIesIfIpoeDescription specifies a user
         provided description for IPoE on this interface."
    DEFVAL { "" }
    ::= { tmnxSvcIesIfIpoeEntry 3 }

tmnxSvcIesIfIpoePolicy           OBJECT-TYPE
    SYNTAX      TNamedItemOrEmpty
    MAX-ACCESS  read-write
    STATUS      current
    DESCRIPTION
        "The value of tmnxSvcIesIfIpoePolicy specifies the IPoE policy
         applicable on this interface."
    DEFVAL { "" }
    ::= { tmnxSvcIesIfIpoeEntry 4 }
    
tmnxSvcIesIfIpoeUserDb           OBJECT-TYPE
    SYNTAX      TNamedItemOrEmpty
    MAX-ACCESS  read-write
    STATUS      current
    DESCRIPTION
        "The value of tmnxSvcIesIfIpoeUserDb specifies the local
         user database to use for authentication.

         If no authentication with the local user database is required,
         the value of this object must be set to the empty string."
    DEFVAL { "" }
    ::= { tmnxSvcIesIfIpoeEntry 5 }
    
tmnxSvcIesIfIpoeSessionLimit     OBJECT-TYPE
    SYNTAX      Unsigned32 (1..262143 | 4294967295)
    MAX-ACCESS  read-write
    STATUS      current
    DESCRIPTION
        "The value of tmnxSvcIesIfIpoeSessionLimit specifies the maximum
         number of IPoE sessions allowed per group or retail interface.
         
         The value of 4294967295 (0xFFFFFFFF) means that there is no limit."
    DEFVAL { 4294967295 }
    ::= { tmnxSvcIesIfIpoeEntry 6 }

tmnxSvcIesIfIpoeSapSessionLimit  OBJECT-TYPE
    SYNTAX      Unsigned32 (1..131071)
    MAX-ACCESS  read-write
    STATUS      current
    DESCRIPTION
        "The value of tmnxSvcIesIfIpoeSapSessionLimit specifies the maximum
         number of IPoE sessions allowed per SAP."
    DEFVAL { 1 }
    ::= { tmnxSvcIesIfIpoeEntry 7 }
    
tmnxSvcIesIfIpoeMinAuthInterval  OBJECT-TYPE
    SYNTAX          Unsigned32 (0..32000000| 4294967295)
    UNITS           "seconds"
    MAX-ACCESS      read-write
    STATUS          current
    DESCRIPTION
        "The value of tmnxSvcIesIfIpoeMinAuthInterval specifies the minimum
         interval between two consecutive authentication attempts for the
         same host.
         
         Re-authentication can be enforced by setting the value to 0. 
         
         A value of 0xFFFFFFFF specifies that re-authentication is 
         disabled.
         
         The value of tmnxSvcIesIfIpoeMinAuthInterval is ignored when
         re-authentication is forced by tmnxSvcIesIfIpoeForceAuth."
    DEFVAL { 4294967295 }
    ::= { tmnxSvcIesIfIpoeEntry 8 }

tmnxSvcIesIfIpoeForceAuth        OBJECT-TYPE
    SYNTAX BITS {
        disabled      (0),
        cidChange     (1),
        ridChange     (2)
    }
    MAX-ACCESS  read-write
    STATUS      current
    DESCRIPTION
        "The value of tmnxSvcIesIfIpoeForceAuth specifies whether an 
         IPoE session re-authentication should be forced independent of  
         the value of tmnxSvcIesIfIpoeMinAuthInterval. 
         
         A value disabled (0) specifies that tmnxSvcIesIfIpoeMinAuthInterval
         never is ignored.
                
         Following packets by default always trigger an IPoE session
         re-authentication:
         
         cidChange (1) - the circuit-id in the IPoE session
         trigger packet is not empty and different from the circuit-id
         stored in the IPoE session data
         
         ridChange (2) - the remore-id in the IPoE session
         trigger packet is not empty and different from the remote-id
         stored in the IPoE session data."
    DEFVAL {{cidChange, ridChange}}
    ::= { tmnxSvcIesIfIpoeEntry 9 }

-- VSD Domain Stats table
svcVsdDomainStatTable      OBJECT-TYPE
    SYNTAX          SEQUENCE OF SvcVsdDomainStatEntry
    MAX-ACCESS      not-accessible
    STATUS          current
    DESCRIPTION
        "svcVsdDomainStatTable contains entries for each VSD static+dynamic
         domain statistics in the system."
    ::= { tmnxSvcObjs 165 }

svcVsdDomainStatEntry    OBJECT-TYPE
    SYNTAX          SvcVsdDomainStatEntry
    MAX-ACCESS      not-accessible
    STATUS          current
    DESCRIPTION
        "A VSD domain statistics entry in the svcVsdDomainStatTable."
    INDEX           { svcVsdDomainName  }
    ::= { svcVsdDomainStatTable 1}

SvcVsdDomainStatEntry ::=    SEQUENCE {
    svcVsdDomainStatCfgChgEvtRcvd      Unsigned32,
    svcVsdDomainStatLastCfgChgEvt      TimeStamp,
    svcVsdDomainStatCfgUpdRcvd         Unsigned32,
    svcVsdDomainStatLastCfgUpdRcvd     TimeStamp,
    svcVsdDomainStatLastCfgUpdDone     TimeStamp,
    svcVsdDomainStatCfgSuccess         Unsigned32,
    svcVsdDomainStatCfgFailed          Unsigned32
}

svcVsdDomainStatCfgChgEvtRcvd        OBJECT-TYPE
    SYNTAX          Unsigned32
    MAX-ACCESS      read-only
    STATUS          current
    DESCRIPTION
        "The value of svcVsdDomainStatCfgChgEvtRcvd indicates the number of
         publish notification received for this domain."
    ::= { svcVsdDomainStatEntry 1 }

svcVsdDomainStatLastCfgChgEvt        OBJECT-TYPE
    SYNTAX          TimeStamp
    MAX-ACCESS      read-only
    STATUS          current
    DESCRIPTION
        "The value of svcVsdDomainStatLastCfgChgEvt indicates the time of last
         publish notification received for this domain."
    ::= { svcVsdDomainStatEntry 2 }

svcVsdDomainStatCfgUpdRcvd        OBJECT-TYPE
    SYNTAX          Unsigned32
    MAX-ACCESS      read-only
    STATUS          current
    DESCRIPTION
        "The value of svcVsdDomainStatCfgUpdRcvd indicates the number of
         IQ (get) response received for this domain."
    ::= { svcVsdDomainStatEntry 3 }

svcVsdDomainStatLastCfgUpdRcvd        OBJECT-TYPE
    SYNTAX          TimeStamp
    MAX-ACCESS      read-only
    STATUS          current
    DESCRIPTION
        "The value of svcVsdDomainStatLastCfgUpdRcvd indicates the time of last
         configuration update request received for this domain."
    ::= { svcVsdDomainStatEntry 4 }

svcVsdDomainStatLastCfgUpdDone        OBJECT-TYPE
    SYNTAX          TimeStamp
    MAX-ACCESS      read-only
    STATUS          current
    DESCRIPTION
        "The value of svcVsdDomainStatLastCfgUpdDone indicates the time of last
         configuration update request processed for this domain."
    ::= { svcVsdDomainStatEntry 5 }

svcVsdDomainStatCfgSuccess        OBJECT-TYPE
    SYNTAX          Unsigned32
    MAX-ACCESS      read-only
    STATUS          current
    DESCRIPTION
        "The value of svcVsdDomainStatCfgSuccess indicates the number of
         successful configuration execution requests for this domain."
    ::= { svcVsdDomainStatEntry 6 }

svcVsdDomainStatCfgFailed        OBJECT-TYPE
    SYNTAX          Unsigned32
    MAX-ACCESS      read-only
    STATUS          current
    DESCRIPTION
        "The value of svcVsdDomainStatCfgFailed indicates the number of
         failed configuration execution requests for this domain."
    ::= { svcVsdDomainStatEntry 7 }

-- ------------------------------------------
-- TLS Proxy ARP Table
-- ------------------------------------------

svcTlsProxyArpCfgTblLastChngd  OBJECT-TYPE
    SYNTAX          TimeStamp
    MAX-ACCESS      read-only
    STATUS          current
    DESCRIPTION
        "The value of svcTlsProxyArpCfgTblLastChngd indicates the sysUpTime at
         the time of the last modification of svcTlsProxyArpCfgTable."
    ::= { tmnxSvcTimeObjs 11 }

svcTlsProxyArpCfgTable      OBJECT-TYPE
    SYNTAX          SEQUENCE OF SvcTlsProxyArpCfgEntry
    MAX-ACCESS      not-accessible
    STATUS          current
    DESCRIPTION
        "svcTlsProxyArpCfgTable contains entries for proxy ARP configuration 
         for each VPLS service in the system."
    ::= { tmnxSvcObjs 166 }

svcTlsProxyArpCfgEntry    OBJECT-TYPE
    SYNTAX          SvcTlsProxyArpCfgEntry
    MAX-ACCESS      not-accessible
    STATUS          current
    DESCRIPTION
        "A svcTlsProxyArpCfgEntry maintains proxy ARP entry for specific VPLS
         service."
    INDEX           { svcId  }
    ::= { svcTlsProxyArpCfgTable 1}

SvcTlsProxyArpCfgEntry ::=    SEQUENCE {
    svcTlsProxyArpCfgRowStatus          RowStatus,
    svcTlsProxyArpCfgLastChgd           TimeStamp,
    svcTlsProxyArpCfgAdminState         TmnxEnabledDisabled,
    svcTlsProxyArpDynPopulate           TruthValue,
    svcTlsProxyArpAgeTime               Integer32,
    svcTlsProxyArpSendRefresh           Integer32,
    svcTlsProxyArpAntiSpoofingMac       MacAddress,
    svcTlsProxyArpDupDetectWindow       Integer32,
    svcTlsProxyArpAntiSpoofNumMoves     Integer32,
    svcTlsProxyArpAntiSpoofHoldDown     Integer32,
    svcTlsProxyArpUnknReqFloodEvpn      TruthValue,
    svcTlsProxyArpTableSize             Integer32,
    svcTlsProxyArpGarpFloodEvpn         TruthValue
}
  
svcTlsProxyArpCfgRowStatus        OBJECT-TYPE
    SYNTAX          RowStatus
    MAX-ACCESS      read-create
    STATUS          current
    DESCRIPTION     
        "The value of svcTlsProxyArpCfgRowStatus is used for the creation and
         deletion of PROXY ARP context in a VPLS instance."
    ::= { svcTlsProxyArpCfgEntry 1 }

svcTlsProxyArpCfgLastChgd        OBJECT-TYPE
    SYNTAX          TimeStamp
    MAX-ACCESS      read-only
    STATUS          current
    DESCRIPTION     
        "The value of svcTlsProxyArpCfgLastChgd indicates the sysUpTime at the 
         time of the last modification of this entry."
    ::= { svcTlsProxyArpCfgEntry 2 }

svcTlsProxyArpCfgAdminState OBJECT-TYPE
    SYNTAX      TmnxEnabledDisabled
    MAX-ACCESS  read-create
    STATUS      current
    DESCRIPTION
        "The value of svcTlsProxyArpCfgAdminState specifies the administrative
         state of this proxy ARP entry."
    DEFVAL { disabled }
    ::= { svcTlsProxyArpCfgEntry 3 }

svcTlsProxyArpDynPopulate OBJECT-TYPE
    SYNTAX      TruthValue
    MAX-ACCESS  read-create
    STATUS      current
    DESCRIPTION
        "The value of svcTlsProxyArpDynPopulate specifies whether system will
         populate proxy ARP entries from snooped GARP/ARP/ND messages on
         SAPs and SDP-BINDs in addition to the entries coming from EVPN
         (when EVPN is enabled). These entries will be shown as dynamic as
         opposed to evpn entries or static entries."
    DEFVAL { false }
    ::= { svcTlsProxyArpCfgEntry 4 }

svcTlsProxyArpAgeTime OBJECT-TYPE
    SYNTAX      Integer32 (0|60..86400)
    UNITS       "seconds"
    MAX-ACCESS  read-create
    STATUS      current
    DESCRIPTION
        "The value of svcTlsProxyArpAgeTime specifies the aging timer value
         for the proxy ARP entries.

         When the aging expires, the entry is flushed. The aging is reset when
         a new ARP/GARP for the same mac-ip is received.

         If the FDB MAC entry is flushed, the corresponding proxy ARP/ND entry
         goes oper-down and ARP/ND lookups will be treated as 'missed'.
         EVPN will withdraw the MAC-IP if the entry goes oper-down."
    DEFVAL { 0 }
    ::= { svcTlsProxyArpCfgEntry 5 }

svcTlsProxyArpSendRefresh OBJECT-TYPE
    SYNTAX      Integer32 (0|120..86400)
    MAX-ACCESS  read-create
    STATUS      current
    DESCRIPTION
        "The value of svcTlsProxyArpSendRefresh specifies whether system
         will attempt to send 3 ARP requests (with senders IP address as zeros)
         within the aging-timer window, trying to refresh the proxy ARP entry."
    DEFVAL { 0 }
    ::= { svcTlsProxyArpCfgEntry 6 }

svcTlsProxyArpAntiSpoofingMac OBJECT-TYPE
    SYNTAX      MacAddress
    MAX-ACCESS  read-create
    STATUS      current
    DESCRIPTION
        "The value of svcTlsProxyArpAntiSpoofingMac specifies the MAC address
         associated with the optional anti-spoofing mechanism."
    DEFVAL { '000000000000'h }
    ::= { svcTlsProxyArpCfgEntry 7 }

svcTlsProxyArpDupDetectWindow OBJECT-TYPE
    SYNTAX      Integer32 (1..15)
    UNITS       "minutes"
    MAX-ACCESS  read-create
    STATUS      current
    DESCRIPTION
        "The value of svcTlsProxyArpDupDetectWindow specifies the time
         to monitor the MAC address in the anti-spoofing mechanism."
    DEFVAL { 3 }
    ::= { svcTlsProxyArpCfgEntry 8 }

svcTlsProxyArpAntiSpoofNumMoves OBJECT-TYPE
    SYNTAX      Integer32 (3..10)
    MAX-ACCESS  read-create
    STATUS      current
    DESCRIPTION
        "The value of svcTlsProxyArpAntiSpoofNumMoves specifies the override
         count associated with anti-spoofing mechanism for proxy ARP entry."
    DEFVAL { 5 }
    ::= { svcTlsProxyArpCfgEntry 9 }

svcTlsProxyArpAntiSpoofHoldDown OBJECT-TYPE
    SYNTAX      Integer32 (-1|2..60)
    UNITS       "minutes"
    MAX-ACCESS  read-create
    STATUS      current
    DESCRIPTION
        "The value of svcTlsProxyArpAntiSpoofHoldDown specifies the time
         to hold down the MAC address in the anti-spoofing mechanism.
         
         A permanent hold is indicated with the value of '-1'."
    DEFVAL { 9 }
    ::= { svcTlsProxyArpCfgEntry 10 }

svcTlsProxyArpUnknReqFloodEvpn OBJECT-TYPE
    SYNTAX      TruthValue
    MAX-ACCESS  read-create
    STATUS      current
    DESCRIPTION
        "The value of svcTlsProxyArpUnknReqFloodEvpn specifies whether to flood
         ARP requests and ND solicitations (with source squelching) when there
         is not a hit in the proxy-arp/nd table."
    DEFVAL { true }
    ::= { svcTlsProxyArpCfgEntry 11 }

svcTlsProxyArpTableSize OBJECT-TYPE
    SYNTAX          Integer32 (1..16383)
    MAX-ACCESS      read-create
    STATUS          current
    DESCRIPTION
        "The value of the object svcTlsProxyArpTableSize specifies the
         maximum number of learned and static entries allowed in
         the proxy ARP table of this service."
    DEFVAL          { 250 }
    ::= { svcTlsProxyArpCfgEntry 12 }

svcTlsProxyArpGarpFloodEvpn OBJECT-TYPE
    SYNTAX      TruthValue
    MAX-ACCESS  read-create
    STATUS      current
    DESCRIPTION
        "The value of svcTlsProxyArpGarpFloodEvpn specifies whether to flood
         GARP requests or replys into EVPN."
    DEFVAL { true }
    ::= { svcTlsProxyArpCfgEntry 13 }

-- proxy ARP static entries table

svcTlsProxyArpStaticTblLastChngd  OBJECT-TYPE
    SYNTAX          TimeStamp
    MAX-ACCESS      read-only
    STATUS          current
    DESCRIPTION
        "The value of svcTlsProxyArpStaticTblLastChngd indicates the sysUpTime at
         the time of the last modification of svcTlsProxyArpStaticTable."
    ::= { tmnxSvcTimeObjs 13 }

svcTlsProxyArpStaticTable      OBJECT-TYPE
    SYNTAX          SEQUENCE OF SvcTlsProxyArpStaticEntry
    MAX-ACCESS      not-accessible
    STATUS          current
    DESCRIPTION
        "svcTlsProxyArpStaticTable contains static address entries for proxy
         ARP configuration for each VPLS service in the system."
    ::= { tmnxSvcObjs 168 }

svcTlsProxyArpStaticEntry    OBJECT-TYPE
    SYNTAX          SvcTlsProxyArpStaticEntry
    MAX-ACCESS      not-accessible
    STATUS          current
    DESCRIPTION
        "A svcTlsProxyArpStaticEntry maintains proxy ARP static address entry
         for specific VPLS service."
    INDEX  { svcId, 
             svcTlsProxyArpStaticInetAddrType, 
             svcTlsProxyArpStaticInetAddress  }
    ::= { svcTlsProxyArpStaticTable 1}

SvcTlsProxyArpStaticEntry ::=    SEQUENCE {
        svcTlsProxyArpStaticInetAddrType    InetAddressType,
        svcTlsProxyArpStaticInetAddress     InetAddress,
        svcTlsProxyArpStaticRowStatus       RowStatus,
        svcTlsProxyArpStaticLastChgd        TimeStamp,
        svcTlsProxyArpStaticMac             MacAddress
    }

svcTlsProxyArpStaticInetAddrType OBJECT-TYPE
    SYNTAX          InetAddressType
    MAX-ACCESS      not-accessible
    STATUS          current
    DESCRIPTION
        "The value of the object svcTlsProxyArpStaticInetAddrType indicates
         the type of the address associated with svcTlsProxyArpStaticInetAddress."
    ::= { svcTlsProxyArpStaticEntry 1 }

svcTlsProxyArpStaticInetAddress OBJECT-TYPE
    SYNTAX          InetAddress (SIZE(4))
    MAX-ACCESS      not-accessible
    STATUS          current
    DESCRIPTION
        "The value of the object svcTlsProxyArpStaticInetAddress indicates
         IP address of the static proxy ARP entry."
    ::= { svcTlsProxyArpStaticEntry 2 }

svcTlsProxyArpStaticRowStatus        OBJECT-TYPE
    SYNTAX          RowStatus
    MAX-ACCESS      read-create
    STATUS          current
    DESCRIPTION
        "The value of svcTlsProxyArpStaticRowStatus is used for the creation and
         deletion of entries in the svcTlsProxyArpStaticEntry."
    ::= { svcTlsProxyArpStaticEntry 3 }

svcTlsProxyArpStaticLastChgd        OBJECT-TYPE
    SYNTAX          TimeStamp
    MAX-ACCESS      read-only
    STATUS          current
    DESCRIPTION
        "The value of svcTlsProxyArpStaticLastChgd indicates the time of last
         proxy ARP configuration change on this service."
    ::= { svcTlsProxyArpStaticEntry 4 }

svcTlsProxyArpStaticMac OBJECT-TYPE
    SYNTAX          MacAddress
    MAX-ACCESS      read-create
    STATUS          current
    DESCRIPTION
        "The value of svcTlsProxyArpStaticMac specifies the MAC address
         associated with this IP address."
    DEFVAL { '000000000000'h }
    ::= { svcTlsProxyArpStaticEntry 5 }

-- ------------------------------------------
-- TLS Proxy Neighbor Discovery (ND) Table
-- ------------------------------------------

svcTlsProxyNdCfgTblLastChngd  OBJECT-TYPE
    SYNTAX          TimeStamp
    MAX-ACCESS      read-only
    STATUS          current
    DESCRIPTION
        "The value of svcTlsProxyNdCfgTblLastChngd indicates the sysUpTime at
         the time of the last modification of svcTlsProxyNdCfgTable."
    ::= { tmnxSvcTimeObjs 14 }

svcTlsProxyNdCfgTable      OBJECT-TYPE
    SYNTAX          SEQUENCE OF SvcTlsProxyNdCfgEntry
    MAX-ACCESS      not-accessible
    STATUS          current
    DESCRIPTION
        "svcTlsProxyNdCfgTable contains entries for proxy Neighbor Discovery
         (ND) configuration for each VPLS service in the system."
    ::= { tmnxSvcObjs 169 }

svcTlsProxyNdCfgEntry    OBJECT-TYPE
    SYNTAX          SvcTlsProxyNdCfgEntry
    MAX-ACCESS      not-accessible
    STATUS          current
    DESCRIPTION
        "A svcTlsProxyNdCfgEntry maintains proxy Neighbor Discovery (ND)
         entry for specific VPLS service."
    INDEX           { svcId  }
    ::= { svcTlsProxyNdCfgTable 1}

SvcTlsProxyNdCfgEntry ::=    SEQUENCE {
    svcTlsProxyNdCfgRowStatus          RowStatus,
    svcTlsProxyNdCfgLastChgd           TimeStamp,
    svcTlsProxyNdCfgAdminState         TmnxEnabledDisabled,
    svcTlsProxyNdDynPopulate           TruthValue,
    svcTlsProxyNdAgeTime               Integer32,
    svcTlsProxyNdSendRefresh           Integer32,
    svcTlsProxyNdAntiSpoofingMac       MacAddress,
    svcTlsProxyNdDupDetectWindow       Integer32,
    svcTlsProxyNdAntiSpoofNumMoves     Integer32,
    svcTlsProxyNdAntiSpoofHoldDown     Integer32,
    svcTlsProxyNdUnknSolFloodEvpn      TruthValue,
    svcTlsProxyNdTableSize             Integer32,
    svcTlsProxyNdRtrUnSolNAFloodEvpn   TruthValue,
    svcTlsProxyNdHstUnSolNAFloodEvpn   TruthValue,
    svcTlsProxyNdEvpnNdAdvRouter       TruthValue
}
  
svcTlsProxyNdCfgRowStatus        OBJECT-TYPE
    SYNTAX          RowStatus
    MAX-ACCESS      read-create
    STATUS          current
    DESCRIPTION     
        "The value of svcTlsProxyNdCfgRowStatus is used for the creation and
         deletion of PROXY Neighbor Discovery (ND) context in a VPLS instance."
    ::= { svcTlsProxyNdCfgEntry 1 }

svcTlsProxyNdCfgLastChgd        OBJECT-TYPE
    SYNTAX          TimeStamp
    MAX-ACCESS      read-only
    STATUS          current
    DESCRIPTION     
        "The value of svcTlsProxyNdCfgLastChgd indicates the sysUpTime at the 
         time of the last modification of this entry."
    ::= { svcTlsProxyNdCfgEntry 2 }

svcTlsProxyNdCfgAdminState OBJECT-TYPE
    SYNTAX      TmnxEnabledDisabled
    MAX-ACCESS  read-create
    STATUS      current
    DESCRIPTION
        "The value of svcTlsProxyNdCfgAdminState specifies the administrative
         state of this proxy Neighbor Discovery (ND) entry."
    DEFVAL { disabled }
    ::= { svcTlsProxyNdCfgEntry 3 }

svcTlsProxyNdDynPopulate OBJECT-TYPE
    SYNTAX      TruthValue
    MAX-ACCESS  read-create
    STATUS      current
    DESCRIPTION
        "The value of svcTlsProxyNdDynPopulate specifies whether system will
         populate proxy Neighbor Discovery (ND) entries from snooped
         GARP/ARP/ND messages on SAPs and SDP-BINDs in addition to the entries
         coming from EVPN (when EVPN is enabled).
         
         These entries will be shown as dynamic as opposed to evpn entries or
         static entries."
    DEFVAL { false }
    ::= { svcTlsProxyNdCfgEntry 4 }

svcTlsProxyNdAgeTime OBJECT-TYPE
    SYNTAX      Integer32 (0|60..86400)
    UNITS       "seconds"
    MAX-ACCESS  read-create
    STATUS      current
    DESCRIPTION
        "The value of svcTlsProxyNdAgeTime specifies the aging timer value
         for the proxy Neighbor Discovery (ND) entries.

         When the aging expires, the entry is flushed. The aging is reset when
         a new ARP/GARP for the same mac-ip is received.

         If the FDB MAC entry is flushed, the corresponding proxy ARP/ND entry
         goes oper-down and ARP/ND lookups will be treated as 'missed'.
         EVPN will withdraw the MAC-IP if the entry goes oper-down."
    DEFVAL { 0 }
    ::= { svcTlsProxyNdCfgEntry 5 }

svcTlsProxyNdSendRefresh OBJECT-TYPE
    SYNTAX      Integer32 (0|120..86400)
    MAX-ACCESS  read-create
    STATUS      current
    DESCRIPTION
        "The value of svcTlsProxyNdSendRefresh specifies whether system
         will attempt to send 3 Neighbor Discovery (ND) requests (with senders
         IP address as zeros) within the aging-timer window, trying to refresh
         the proxy Neighbor Discovery (ND) entry."
    DEFVAL { 0 }
    ::= { svcTlsProxyNdCfgEntry 6 }

svcTlsProxyNdAntiSpoofingMac OBJECT-TYPE
    SYNTAX      MacAddress
    MAX-ACCESS  read-create
    STATUS      current
    DESCRIPTION
        "The value of svcTlsProxyNdAntiSpoofingMac specifies the MAC address
         associated with the optional anti-spoofing mechanism."
    DEFVAL { '000000000000'h }
    ::= { svcTlsProxyNdCfgEntry 7 }

svcTlsProxyNdDupDetectWindow OBJECT-TYPE
    SYNTAX      Integer32 (1..15)
    UNITS       "minutes"
    MAX-ACCESS  read-create
    STATUS      current
    DESCRIPTION
        "The value of svcTlsProxyNdDupDetectWindow specifies the time
         to monitor the MAC address in the anti-spoofing mechanism."
    DEFVAL { 3 }
    ::= { svcTlsProxyNdCfgEntry 8 }

svcTlsProxyNdAntiSpoofNumMoves OBJECT-TYPE
    SYNTAX      Integer32 (3..10)
    MAX-ACCESS  read-create
    STATUS      current
    DESCRIPTION
        "The value of svcTlsProxyNdAntiSpoofNumMoves specifies the override
         count associated with anti-spoofing mechanism for proxy Neighbor
         Discovery (ND) entry."
    DEFVAL { 5 }
    ::= { svcTlsProxyNdCfgEntry 9 }

svcTlsProxyNdAntiSpoofHoldDown OBJECT-TYPE
    SYNTAX      Integer32 (-1|2..60)
    UNITS       "minutes"
    MAX-ACCESS  read-create
    STATUS      current
    DESCRIPTION
        "The value of svcTlsProxyNdAntiSpoofHoldDown specifies the time
         to hold down the MAC address in the anti-spoofing mechanism.
         
         A permanent hold is indicated with the value of '-1'."
    DEFVAL { 9 }
    ::= { svcTlsProxyNdCfgEntry 10 }

svcTlsProxyNdUnknSolFloodEvpn OBJECT-TYPE
    SYNTAX      TruthValue
    MAX-ACCESS  read-create
    STATUS      current
    DESCRIPTION
        "The value of svcTlsProxyNdUnknSolFloodEvpn specifies whether to flood
         Neighbor Discovery (ND) solicitations (with source squelching) when
         there is not a hit in the proxy-arp/nd table."
    DEFVAL { true }
    ::= { svcTlsProxyNdCfgEntry 11 }

svcTlsProxyNdTableSize OBJECT-TYPE
    SYNTAX          Integer32 (1..16383)
    MAX-ACCESS      read-create
    STATUS          current
    DESCRIPTION
        "The value of the object svcTlsProxyNdTableSize specifies the
         maximum number of learned and static entries allowed in
         the proxy Neighbor Discovery (ND) table of this service." 
    DEFVAL          { 250 }
    ::= { svcTlsProxyNdCfgEntry 12 }

svcTlsProxyNdRtrUnSolNAFloodEvpn OBJECT-TYPE
    SYNTAX      TruthValue
    MAX-ACCESS  read-create
    STATUS      current
    DESCRIPTION
        "The value of svcTlsProxyNdRtrUnSolNAFloodEvpn specifies whether to
         flood EVPN with Neighbor Advertisement (NA) replies for router-type."
    DEFVAL { true }
    ::= { svcTlsProxyNdCfgEntry 13 }

svcTlsProxyNdHstUnSolNAFloodEvpn OBJECT-TYPE
    SYNTAX      TruthValue
    MAX-ACCESS  read-create
    STATUS      current
    DESCRIPTION
        "The value of svcTlsProxyNdHstUnSolNAFloodEvpn specifies whether to
         flood EVPN with Neighbor Advertisement (NA) replies for host-type."
    DEFVAL { true }
    ::= { svcTlsProxyNdCfgEntry 14 }

svcTlsProxyNdEvpnNdAdvRouter OBJECT-TYPE
    SYNTAX      TruthValue
    MAX-ACCESS  read-create
    STATUS      current
    DESCRIPTION
        "The value of svcTlsProxyNdEvpnNdAdvRouter specifies whether to
         advertise router entries or host entries in the EVPN. It also
         specifies whether to reply to Neighbor Solicitations for EVPN entries
         with the router flag 0 or 1."
    DEFVAL { true }
    ::= { svcTlsProxyNdCfgEntry 15 }

-- proxy Neighbor Discovery (ND) static entries table
svcTlsProxyNdStaticTblLastChngd  OBJECT-TYPE
    SYNTAX          TimeStamp
    MAX-ACCESS      read-only
    STATUS          current
    DESCRIPTION
        "The value of svcTlsProxyNdStaticTblLastChngd indicates the sysUpTime at
         the time of the last modification of svcTlsProxyNdStaticTable."
    ::= { tmnxSvcTimeObjs 15 }

svcTlsProxyNdStaticTable      OBJECT-TYPE
    SYNTAX          SEQUENCE OF SvcTlsProxyNdStaticEntry
    MAX-ACCESS      not-accessible
    STATUS          current
    DESCRIPTION
        "svcTlsProxyNdStaticTable contains static IPv6 address entries for proxy
         Neighbor Discovery (ND) configuration for each VPLS service in the
         system."
    ::= { tmnxSvcObjs 170 }

svcTlsProxyNdStaticEntry    OBJECT-TYPE
    SYNTAX          SvcTlsProxyNdStaticEntry
    MAX-ACCESS      not-accessible
    STATUS          current
    DESCRIPTION
        "A svcTlsProxyNdStaticEntry maintains proxy Neighbor Discovery (ND)
         static address entry for specific VPLS service."
    INDEX  { svcId, 
             svcTlsProxyNdStaticInetAddrType, 
             svcTlsProxyNdStaticInetAddress  }
    ::= { svcTlsProxyNdStaticTable 1}

SvcTlsProxyNdStaticEntry ::=    SEQUENCE {
        svcTlsProxyNdStaticInetAddrType    InetAddressType,
        svcTlsProxyNdStaticInetAddress     InetAddress,
        svcTlsProxyNdStaticRowStatus       RowStatus,
        svcTlsProxyNdStaticLastChgd        TimeStamp,
        svcTlsProxyNdStaticMac             MacAddress,
        svcTlsProxyNdStaticIsRouter        TruthValue
    }

svcTlsProxyNdStaticInetAddrType OBJECT-TYPE
    SYNTAX          InetAddressType
    MAX-ACCESS      not-accessible
    STATUS          current
    DESCRIPTION
        "The value of the object svcTlsProxyNdStaticInetAddrType indicates
         the type of the address associated with svcTlsProxyNdStaticInetAddress."
    ::= { svcTlsProxyNdStaticEntry 1 }

svcTlsProxyNdStaticInetAddress OBJECT-TYPE
    SYNTAX          InetAddress (SIZE(16))
    MAX-ACCESS      not-accessible
    STATUS          current
    DESCRIPTION
        "The value of the object svcTlsProxyNdStaticInetAddress indicates
         IP address of the static proxy Neighbor Discovery (ND) entry."
    ::= { svcTlsProxyNdStaticEntry 2 }

svcTlsProxyNdStaticRowStatus        OBJECT-TYPE
    SYNTAX          RowStatus
    MAX-ACCESS      read-create
    STATUS          current
    DESCRIPTION
        "The value of svcTlsProxyNdStaticRowStatus is used for the creation and
         deletion of entries in the svcTlsProxyNdStaticEntry."
    ::= { svcTlsProxyNdStaticEntry 3 }

svcTlsProxyNdStaticLastChgd        OBJECT-TYPE
    SYNTAX          TimeStamp
    MAX-ACCESS      read-only
    STATUS          current
    DESCRIPTION
        "The value of svcTlsProxyNdStaticLastChgd indicates the time of last
         proxy Neighbor Discovery (ND) configuration change on this service."
    ::= { svcTlsProxyNdStaticEntry 4 }

svcTlsProxyNdStaticMac OBJECT-TYPE
    SYNTAX          MacAddress
    MAX-ACCESS      read-create
    STATUS          current
    DESCRIPTION
        "The value of svcTlsProxyNdStaticMac specifies the MAC address
         associated with this IP address."
    DEFVAL { '000000000000'h }
    ::= { svcTlsProxyNdStaticEntry 5 }

svcTlsProxyNdStaticIsRouter OBJECT-TYPE
    SYNTAX          TruthValue
    MAX-ACCESS      read-create
    STATUS          current
    DESCRIPTION
        "The value of svcTlsProxyNdStaticIsRouter specifies whether entry is
         router type."
    DEFVAL { true }
    ::= { svcTlsProxyNdStaticEntry 6 }

-- ------------------------------------------
-- Proxy ND read-only Table
-- ------------------------------------------

svcTlsProxyNdTblLastChngd  OBJECT-TYPE
    SYNTAX          TimeStamp
    MAX-ACCESS      read-only
    STATUS          current
    DESCRIPTION
        "The value of svcTlsProxyNdTblLastChngd indicates the sysUpTime at
         the time of the last modification of svcTlsProxyNdTable."
    ::= { tmnxSvcTimeObjs 16 }

svcTlsProxyNdTable      OBJECT-TYPE
    SYNTAX          SEQUENCE OF SvcTlsProxyNdEntry
    MAX-ACCESS      not-accessible
    STATUS          current
    DESCRIPTION
        "svcTlsProxyNdTable contains entries for each host in the system.
         Proxy Neighbor Discovery (ND) is always enabled in an EVPN enabled
         service and disabled otherwise."
    ::= { tmnxSvcObjs 171 }

svcTlsProxyNdEntry    OBJECT-TYPE
    SYNTAX          SvcTlsProxyNdEntry
    MAX-ACCESS      not-accessible
    STATUS          current
    DESCRIPTION     "A Proxy Neighbor Discovery (ND) entry in the
                     svcTlsProxyNdTable."
    INDEX           { svcId, svcTlsProxyNdIpAddrType, svcTlsProxyNdIpAddr}
    ::= { svcTlsProxyNdTable 1}

SvcTlsProxyNdEntry ::=    SEQUENCE {
    svcTlsProxyNdIpAddrType       InetAddressType,
    svcTlsProxyNdIpAddr           InetAddress,
    svcTlsProxyNdMacAddr          MacAddress,
    svcTlsProxyNdType             TmnxProxyEntryType,
    svcTlsProxyNdLastChgd         TimeStamp,
    svcTlsProxyNdStatus           INTEGER,
    svcTlsProxyNdIsRouter         TruthValue
}

svcTlsProxyNdIpAddrType OBJECT-TYPE
    SYNTAX          InetAddressType
    MAX-ACCESS      not-accessible
    STATUS          current
    DESCRIPTION     "The value of svcTlsProxyNdIpAddrType indicates the
                     address type of svcTlsProxyNdIpAddr."
    ::= { svcTlsProxyNdEntry 1 }

svcTlsProxyNdIpAddr OBJECT-TYPE
    SYNTAX          InetAddress (SIZE(0|16))
    MAX-ACCESS      not-accessible
    STATUS          current
    DESCRIPTION     "The value of svcTlsProxyNdIpAddr indicates the IP
                     address of the host."
    ::= { svcTlsProxyNdEntry 2 }

svcTlsProxyNdMacAddr OBJECT-TYPE
    SYNTAX          MacAddress
    MAX-ACCESS      read-only
    STATUS          current
    DESCRIPTION     "The value of svcTlsProxyNdIpAddr indicates the MAC address
                     mapping for the Neighbor Discovery (ND) host indicated by
                     svcTlsProxyNdIpAddr."
    ::= { svcTlsProxyNdEntry 3 }

svcTlsProxyNdType OBJECT-TYPE
    SYNTAX          TmnxProxyEntryType
    MAX-ACCESS      read-only
    STATUS          current
    DESCRIPTION     "The value of svcTlsProxyNdType indicates the type
                     of proxy Neighbor Discovery (ND) entry."
    ::= { svcTlsProxyNdEntry 4 }

svcTlsProxyNdLastChgd        OBJECT-TYPE
    SYNTAX          TimeStamp
    MAX-ACCESS      read-only
    STATUS          current
    DESCRIPTION     "The value of svcTlsProxyNdLastChgd indicates the
                     sysUpTime at the time of the last modification of this
                     entry."
    ::= { svcTlsProxyNdEntry 5 }

svcTlsProxyNdStatus        OBJECT-TYPE
    SYNTAX          INTEGER {
                          active  (1),
                          inActv  (2),
                          pendng  (3) -- confirm-pending
                    }
    MAX-ACCESS      read-only
    STATUS          current
    DESCRIPTION     "The value of svcTlsProxyNdStatus indicates if proxy
                     Neighbor Discovery (ND) will respond to ND request for
                     the IP address corresponding to this entry."
    ::= { svcTlsProxyNdEntry 6 }

svcTlsProxyNdIsRouter OBJECT-TYPE
    SYNTAX          TruthValue
    MAX-ACCESS      read-only
    STATUS          current
    DESCRIPTION
        "The value of svcTlsProxyNdIsRouter indicates whether entry is
         router type."
    ::= { svcTlsProxyNdEntry 7 }


svcBgpEvpnMplsTableLastChanged  OBJECT-TYPE
    SYNTAX          TimeStamp
    MAX-ACCESS      read-only
    STATUS          current
    DESCRIPTION
        "The value of svcBgpEvpnMplsTableLastChanged indicates the sysUpTime at
         the time of the last modification of svcBgpEvpnMplsTable."
    ::= { tmnxSvcTimeObjs 17 }

svcBgpEvpnMplsTable OBJECT-TYPE
    SYNTAX          SEQUENCE OF SvcBgpEvpnMplsEntry
    MAX-ACCESS      not-accessible
    STATUS          current
    DESCRIPTION     
        "svcBgpEvpnMplsTable contains entries for BGP EVPN MPLS in 
         a VPLS service context." 
    ::= { tmnxSvcObjs 173 }

svcBgpEvpnMplsEntry    OBJECT-TYPE
    SYNTAX          SvcBgpEvpnMplsEntry
    MAX-ACCESS      not-accessible
    STATUS          current
    DESCRIPTION     "A BGP EVPN MPLS entry in the svcBgpEvpnMplsTable."
    INDEX           { svcId }
    ::= { svcBgpEvpnMplsTable 1}

SvcBgpEvpnMplsEntry ::=    SEQUENCE {
    svcBgpEvpnMplsLastChanged          TimeStamp,
    svcBgpEvpnMplsForceVlanVcFwding    TruthValue,
    svcBgpEvpnMplsControlWord          TruthValue,
    svcBgpEvpnMplsShgName              TNamedItemOrEmpty,
    svcBgpEvpnMplsIngressRepBumLabel   TruthValue,
    svcBgpEvpnMplsMaxEcmpRoutes        Integer32,
    svcBgpEvpnMplsIngressLabel         Integer32,
    svcBgpEvpnMplsIngressBumLabel      Integer32,
    svcBgpEvpnMplsAdminState           TmnxEnabledDisabled
}

svcBgpEvpnMplsLastChanged        OBJECT-TYPE
    SYNTAX          TimeStamp
    MAX-ACCESS      read-only
    STATUS          current
    DESCRIPTION     "The value of svcBgpEvpnMplsLastChanged indicates the
                     sysUpTime at the time of the last modification of this
                     entry.
                     
                     If no changes were made to the entry since the last 
                     re-initialization of the local network management 
                     subsystem, then this object contains a zero value."
    ::= { svcBgpEvpnMplsEntry 1 }

svcBgpEvpnMplsForceVlanVcFwding OBJECT-TYPE
    SYNTAX           TruthValue
    MAX-ACCESS       read-write
    STATUS           current
    DESCRIPTION
        "The value of svcBgpEvpnMplsForceVlanVcFwding specifies whether or not
         vc-vlan-type forwarding is forced in the data-path for BGP EVPN MPLS.
         When set to 'true' vc-vlan-type forwarding is forced."

    DEFVAL  { false }
    ::= { svcBgpEvpnMplsEntry 2 }

svcBgpEvpnMplsControlWord OBJECT-TYPE
    SYNTAX           TruthValue
    MAX-ACCESS       read-write
    STATUS           current
    DESCRIPTION
        "The value of svcBgpEvpnMplsControlWord specifies whether the use of 
         'ControlWord' is enabled on BGP EVPN MPLS or not. 
           
         When the value of the object is set to 'true', all MPLS packets
         are encapsulated with the control word when sent over the BGP EVPN.
         When the value of the object is set to 'false', the use of 
         'ControlWord' is disabled."
    DEFVAL  { false }
    ::= { svcBgpEvpnMplsEntry 3 }


svcBgpEvpnMplsShgName OBJECT-TYPE
    SYNTAX       TNamedItemOrEmpty
    MAX-ACCESS   read-write
    STATUS       current
    DESCRIPTION
        "The value of the svcBgpEvpnMplsShgName specifies the value of
         split-horizon group associated with this BGP EVPN MPLS.
         By default, BGP EVPN MPLS connections do not belong to any user
         configured split-horizon group."
    DEFVAL { ''H }
    ::= { svcBgpEvpnMplsEntry 4 }


svcBgpEvpnMplsIngressRepBumLabel OBJECT-TYPE
    SYNTAX           TruthValue
    MAX-ACCESS       read-write
    STATUS           current
    DESCRIPTION
        "The value of svcBgpEvpnMplsIngressRepBumLabel specifies whether
         to advertise a different label for inclusive multicast routes,
         or use the same label as the one advertised for unicast traffic.
           
         When the value of the object is set to 'false', all MPLS packets
         use same lable as the one advertised for unicast traffic when sent
         over the BGP EVPN. When the value of the object is set to 'true',
         the system sends different label"
    DEFVAL  { false }
    ::= { svcBgpEvpnMplsEntry 5 }

svcBgpEvpnMplsMaxEcmpRoutes OBJECT-TYPE
    SYNTAX           Integer32 (0..32)
    MAX-ACCESS       read-write
    STATUS           current
    DESCRIPTION
        "The value of svcBgpEvpnMplsMaxEcmpRoutes specifies the maximum ECMP
         routes required for controlling all-active routing to MAC/IP with the
         same ethernet-segment-identifier (ESI)."
    DEFVAL { 0 }
    ::= { svcBgpEvpnMplsEntry 6 }

svcBgpEvpnMplsIngressLabel OBJECT-TYPE
    SYNTAX           Integer32
    MAX-ACCESS       read-only
    STATUS           current
    DESCRIPTION
        "The value of svcBgpEvpnMplsIngressLabel indicates the label advertised
         for ingress unicast traffic for the EVPN MPLS instance.
             
         The value of -1 indicates that the label is not allocated."
    ::= { svcBgpEvpnMplsEntry 7 }

svcBgpEvpnMplsIngressBumLabel OBJECT-TYPE
    SYNTAX           Integer32
    MAX-ACCESS       read-only
    STATUS           current
    DESCRIPTION
        "The value of svcBgpEvpnMplsIngressBumLabel indicates the label
         advertised for ingress multicast traffic for the EVPN MPLS instance.
         
         The value of -1 indicates that the label is not allocated."
    ::= { svcBgpEvpnMplsEntry 8 }

svcBgpEvpnMplsAdminState        OBJECT-TYPE
    SYNTAX          TmnxEnabledDisabled
    MAX-ACCESS      read-write
    STATUS          current
    DESCRIPTION
        "The value of svcBgpEvpnMplsAdminState specifies the desired
         administrative state for MPLS under BGP EVPN context."
    DEFVAL { disabled }
    ::= { svcBgpEvpnMplsEntry 9 }

-- ----------------------------------------
-- Service EVPN MPLS tunnel endpoint Table
-- ----------------------------------------

svcEvpnMplsTEPTable        OBJECT-TYPE
    SYNTAX          SEQUENCE OF SvcEvpnMplsTEPEntry
    MAX-ACCESS      not-accessible
    STATUS          current
    DESCRIPTION
        "The svcEvpnMplsTEPTable contains entries for all the EVPN MPLS
         tunnel endpoint addresse specific information in the system."
    ::= { tmnxSvcObjs 174 }

svcEvpnMplsTEPEntry        OBJECT-TYPE
    SYNTAX          SvcEvpnMplsTEPEntry
    MAX-ACCESS      not-accessible
    STATUS          current
    DESCRIPTION
        "The svcEvpnMplsTEPEntry contains specific EVPN MPLS tunnel endpoint
         address entry information."
    INDEX  { svcEvpnMplsTEPAddrType, svcEvpnMplsTEPAddress }
    ::= { svcEvpnMplsTEPTable 1}

SvcEvpnMplsTEPEntry ::=    SEQUENCE {
    svcEvpnMplsTEPAddrType        InetAddressType,
    svcEvpnMplsTEPAddress         InetAddress,
    svcEvpnMplsTEPNumEvpnMplsDest Unsigned32,
    svcEvpnMplsTEPNumESDest       Unsigned32,
    svcEvpnMplsTEPNumESBMacDest   Unsigned32
}

svcEvpnMplsTEPAddrType     OBJECT-TYPE
    SYNTAX          InetAddressType
    MAX-ACCESS      read-only
    STATUS          current
    DESCRIPTION
        "The value of svcEvpnMplsTEPAddrType indicates the type
         of the address associated with svcEvpnMplsTEPAddress."
    ::= { svcEvpnMplsTEPEntry 1 }

svcEvpnMplsTEPAddress      OBJECT-TYPE
    SYNTAX          InetAddress (SIZE(4))
    MAX-ACCESS      read-only
    STATUS          current
    DESCRIPTION
        "The value of svcEvpnMplsTEPAddress indicates a EVPN 
         MPLS tunnel endpoint address present in the system."
    ::= { svcEvpnMplsTEPEntry 2 }

svcEvpnMplsTEPNumEvpnMplsDest    OBJECT-TYPE
    SYNTAX          Unsigned32
    MAX-ACCESS      read-only
    STATUS          current
    DESCRIPTION
        "The value of svcEvpnMplsTEPNumEvpnMplsDest indicates the number of
         EVPN MPLS destinations for the EVPN MPLS tunnel endpoint address."
    ::= { svcEvpnMplsTEPEntry 3 }

svcEvpnMplsTEPNumESDest    OBJECT-TYPE
    SYNTAX          Unsigned32
    MAX-ACCESS      read-only
    STATUS          current
    DESCRIPTION
        "The value of svcEvpnMplsTEPNumESDest indicates the number of
         ethernet segment destinations for the EVPN MPLS tunnel endpoint
         address."
    ::= { svcEvpnMplsTEPEntry 4 }

svcEvpnMplsTEPNumESBMacDest    OBJECT-TYPE
    SYNTAX          Unsigned32
    MAX-ACCESS      read-only
    STATUS          current
    DESCRIPTION
        "The value of svcEvpnMplsTEPNumESBMacDest indicates the number of
         ethernet segment back-bone MAC destinations for the EVPN
         MPLS tunnel endpoint address."
    ::= { svcEvpnMplsTEPEntry 5 }

svcTlsBgpEvpnABTnlTblLastChanged OBJECT-TYPE
    SYNTAX      TimeStamp
    MAX-ACCESS  read-only
    STATUS      current
    DESCRIPTION
        "The value of svcTlsBgpEvpnABTnlTblLastChanged indicates the
         sysUpTime at the time of the last modification of
         svcTlsBgpEvpnAutoBindTnlTable."
    ::= { tmnxSvcTimeObjs 18 }

svcTlsBgpEvpnAutoBindTnlTable    OBJECT-TYPE
    SYNTAX      SEQUENCE OF SvcTlsBgpEvpnAutoBindTnlEntry
    MAX-ACCESS  not-accessible
    STATUS      current
    DESCRIPTION    
        "The svcTlsBgpEvpnAutoBindTnlTable contains entries for supported
         tunnel type which may be chosen as tunnel type within service."
    ::= { tmnxSvcObjs 175 }

svcTlsBgpEvpnAutoBindTnlEntry    OBJECT-TYPE
    SYNTAX      SvcTlsBgpEvpnAutoBindTnlEntry
    MAX-ACCESS  not-accessible
    STATUS      current
    DESCRIPTION
        "An Auto bind tunnel entry in the svcTlsBgpEvpnAutoBindTnlTable.
         Each row entry contains the type of tunnel chosen within service.

         The entries in this table are created and destroyed by SNMP SET
         operations."
    INDEX       { svcId }
    ::= { svcTlsBgpEvpnAutoBindTnlTable 1}

SvcTlsBgpEvpnAutoBindTnlEntry ::=    SEQUENCE {
    svcTlsBgpEvpnAutoBindTnlLastChg    TimeStamp,
    svcTlsBgpEvpnAutoBindTnlLdp        TruthValue,
    svcTlsBgpEvpnAutoBindTnlRsvpTe     TruthValue,
    svcTlsBgpEvpnAutoBindTnlSrIsis     TruthValue,
    svcTlsBgpEvpnAutoBindTnlSrOspf     TruthValue,
    svcTlsBgpEvpnAutoBndTnlStatus      TResolveStatus,
    svcTlsBgpEvpnAutoBindTnlBgp        TruthValue
}

svcTlsBgpEvpnAutoBindTnlLastChg  OBJECT-TYPE
    SYNTAX      TimeStamp
    MAX-ACCESS  read-only
    STATUS      current
    DESCRIPTION
        "The value of svcTlsBgpEvpnAutoBindTnlLastChg indicates the
         sysUpTime at the time of the last modification of this
         entry."
    ::= { svcTlsBgpEvpnAutoBindTnlEntry 1 }

svcTlsBgpEvpnAutoBindTnlLdp      OBJECT-TYPE
    SYNTAX      TruthValue
    MAX-ACCESS  read-write
    STATUS      current
    DESCRIPTION
        "The value of svcTlsBgpEvpnAutoBindTnlLdp specifies whether LDP type
         tunnel may be chosen as the tunnel within the service."
    DEFVAL { false }
    ::= { svcTlsBgpEvpnAutoBindTnlEntry 2 }

svcTlsBgpEvpnAutoBindTnlRsvpTe   OBJECT-TYPE
    SYNTAX      TruthValue
    MAX-ACCESS  read-write
    STATUS      current
    DESCRIPTION
        "The value of svcTlsBgpEvpnAutoBindTnlRsvpTe specifies whether RSVP TE
         type tunnel may be chosen as the tunnel within the service."
    DEFVAL { false }
    ::= { svcTlsBgpEvpnAutoBindTnlEntry 3 }

svcTlsBgpEvpnAutoBindTnlSrIsis   OBJECT-TYPE
    SYNTAX      TruthValue
    MAX-ACCESS  read-write
    STATUS      current
    DESCRIPTION
        "The value of svcTlsBgpEvpnAutoBindTnlSrIsis specifies whether a tunnel
         to next-hop of the L2 VPN prefix route is selected from the lowest
         numbered ISIS instance."
    DEFVAL { false }
    ::= { svcTlsBgpEvpnAutoBindTnlEntry 4 }

svcTlsBgpEvpnAutoBindTnlSrOspf   OBJECT-TYPE
    SYNTAX      TruthValue
    MAX-ACCESS  read-write
    STATUS      current
    DESCRIPTION
        "The value of svcTlsBgpEvpnAutoBindTnlSrOspf specifies whether a tunnel
         to next-hop of the L2 VPN prefix route is selected from the lowest
         numbered ISIS instance."
    DEFVAL { false }
    ::= { svcTlsBgpEvpnAutoBindTnlEntry 5 }

svcTlsBgpEvpnAutoBndTnlStatus OBJECT-TYPE
    SYNTAX      TResolveStatus
    MAX-ACCESS  read-write
    STATUS      current
    DESCRIPTION
        "The value of svcTlsBgpEvpnAutoBndTnlStatus specifies the 
         resolution status of this entry."
    DEFVAL { disabled }
    ::= { svcTlsBgpEvpnAutoBindTnlEntry 6 }

svcTlsBgpEvpnAutoBindTnlBgp      OBJECT-TYPE
    SYNTAX      TruthValue
    MAX-ACCESS  read-write
    STATUS      current
    DESCRIPTION
        "The value of svcTlsBgpEvpnAutoBindTnlBgp specifies whether BGP type
         tunnel may be chosen as the tunnel within the service."
    DEFVAL { false }
    ::= { svcTlsBgpEvpnAutoBindTnlEntry 7 }

-- auto-bind-tunnel table for vprn
svcVprnBgpAutoBindTblLastChgd OBJECT-TYPE
    SYNTAX      TimeStamp
    MAX-ACCESS  read-only
    STATUS      current
    DESCRIPTION
        "The value of svcVprnBgpAutoBindTblLastChgd indicates the
         sysUpTime at the time of the last modification of
         svcVprnBgpAutoBindTable."
    ::= { tmnxSvcTimeObjs 19 }

svcVprnBgpAutoBindTable    OBJECT-TYPE
    SYNTAX      SEQUENCE OF SvcVprnBgpAutoBindEntry
    MAX-ACCESS  not-accessible
    STATUS      current
    DESCRIPTION    
        "The svcVprnBgpAutoBindTable contains entries for supported
         tunnel type which may be chosen as tunnel type within service."
    ::= { tmnxSvcObjs 176 }

svcVprnBgpAutoBindEntry    OBJECT-TYPE
    SYNTAX      SvcVprnBgpAutoBindEntry
    MAX-ACCESS  not-accessible
    STATUS      current
    DESCRIPTION
        "The svcVprnBgpAutoBindEntry is an Auto bind tunnel entry in the
         svcVprnBgpAutoBindTable. Each row entry contains the type of
         tunnel chosen within service.

         The entries in this table are created and destroyed by SNMP SET
         operations."
    INDEX       { svcId }
    ::= { svcVprnBgpAutoBindTable 1}

SvcVprnBgpAutoBindEntry ::=    SEQUENCE {
    svcVprnBgpAutoBindLastChg    TimeStamp,
    svcVprnBgpAutoBindLdp        TruthValue,
    svcVprnBgpAutoBindRsvpTe     TruthValue,
    svcVprnBgpAutoBindSrIsis     TruthValue,
    svcVprnBgpAutoBindSrOspf     TruthValue,
    svcVprnBgpAutoBindGre        TruthValue,
    svcVprnBgpAutoBindTnlStatus  TResolveStatus
}

svcVprnBgpAutoBindLastChg  OBJECT-TYPE
    SYNTAX      TimeStamp
    MAX-ACCESS  read-only
    STATUS      current
    DESCRIPTION
        "The value of svcVprnBgpAutoBindLastChg indicates the
         sysUpTime at the time of the last modification of this
         entry."
    ::= { svcVprnBgpAutoBindEntry 1 }

svcVprnBgpAutoBindLdp      OBJECT-TYPE
    SYNTAX      TruthValue
    MAX-ACCESS  read-create
    STATUS      current
    DESCRIPTION
        "The value of svcVprnBgpAutoBindLdp specifies whether LDP type
         tunnel may be chosen as the tunnel within the service."
    DEFVAL { false }
    ::= { svcVprnBgpAutoBindEntry 2 }

svcVprnBgpAutoBindRsvpTe   OBJECT-TYPE
    SYNTAX      TruthValue
    MAX-ACCESS  read-create
    STATUS      current
    DESCRIPTION
        "The value of svcVprnBgpAutoBindRsvpTe specifies whether RSVP TE
         type tunnel may be chosen as the tunnel within the service."
    DEFVAL { false }
    ::= { svcVprnBgpAutoBindEntry 3 }

svcVprnBgpAutoBindSrIsis   OBJECT-TYPE
    SYNTAX      TruthValue
    MAX-ACCESS  read-create
    STATUS      current
    DESCRIPTION
        "The value of svcVprnBgpAutoBindSrIsis specifies whether a tunnel
         to next-hop of the L2 VPN prefix route is selected from the lowest
         numbered ISIS instance."
    DEFVAL { false }
    ::= { svcVprnBgpAutoBindEntry 4 }

svcVprnBgpAutoBindSrOspf   OBJECT-TYPE
    SYNTAX      TruthValue
    MAX-ACCESS  read-create
    STATUS      current
    DESCRIPTION
        "The value of svcVprnBgpAutoBindSrOspf specifies whether a tunnel
         to next-hop of the L2 VPN prefix route is selected from the lowest
         numbered ISIS instance."
    DEFVAL { false }
    ::= { svcVprnBgpAutoBindEntry 5 }

svcVprnBgpAutoBindGre      OBJECT-TYPE
    SYNTAX      TruthValue
    MAX-ACCESS  read-create
    STATUS      current
    DESCRIPTION
        "The value of svcVprnBgpAutoBindGre specifies whether GRE type
         tunnel may be chosen as the tunnel within the service."
    DEFVAL { false }
    ::= { svcVprnBgpAutoBindEntry 6 }

svcVprnBgpAutoBindTnlStatus OBJECT-TYPE
    SYNTAX      TResolveStatus
    MAX-ACCESS  read-create
    STATUS      current
    DESCRIPTION
        "The value of svcVprnBgpAutoBindTnlStatus specifies the 
         administrative status of this entry."
    DEFVAL { disabled }
    ::= { svcVprnBgpAutoBindEntry 7 }

-- ------------------------------------
-- TLS MFIB NG Table
-- ------------------------------------
tlsMFibNgTable OBJECT-TYPE
    SYNTAX          SEQUENCE OF TlsMFibNgEntry
    MAX-ACCESS      not-accessible
    STATUS          current
    DESCRIPTION     "tlsMFibNgTable contains the Multicast FIB for this Tls."
    ::= { tmnxSvcObjs 177 }

tlsMFibNgEntry OBJECT-TYPE
    SYNTAX          TlsMFibNgEntry
    MAX-ACCESS      not-accessible
    STATUS          current
    DESCRIPTION     "An entry in the tlsMFibNgTable. Each entry indicates
                     whether  traffic from a certain source to a certain
                     multicast destination (group) needs to be forwarded or
                     blocked on the indicated SAP/SDP/VXLAN."
    INDEX           { svcId,
                      tlsMFibNgEntryType,
                      tlsMFibNgGrpMacAddr,
                      tlsMFibNgGrpInetAddrType,
                      tlsMFibNgGrpInetAddr,
                      tlsMFibNgSrcInetAddrType,
                      tlsMFibNgSrcInetAddr,
                      tlsMFibNgLocale,
                      tlsMFibNgLocaleId }
    ::= { tlsMFibNgTable 1 }

TlsMFibNgEntry ::=
    SEQUENCE {
        tlsMFibNgEntryType          INTEGER,
        tlsMFibNgGrpMacAddr         MacAddress,
        tlsMFibNgGrpInetAddrType    InetAddressType,
        tlsMFibNgGrpInetAddr        InetAddress,
        tlsMFibNgSrcInetAddrType    InetAddressType,
        tlsMFibNgSrcInetAddr        InetAddress,
        tlsMFibNgLocale             MfibLocation,
        tlsMFibNgLocaleId           OCTET STRING,
        
--      tlsMFibNgPortId             TmnxPortID,
--      tlsMFibNgEncapValue         TmnxEncapVal,
--      tlsMFibNgSdpId              SdpId,
--      tlsMFibNgVcId               Unsigned32,
--      tlsMFibNgVTEPAddr           IpAddress,
--      tlsMFibNgVNI                Unsigned32,
        
        tlsMFibNgFwdOrBlk           MfibGrpSrcFwdOrBlk,
        tlsMFibNgSvcId              TmnxServId
    }

tlsMFibNgEntryType OBJECT-TYPE
    SYNTAX          INTEGER {
                        ipBased  (1),
                        macBased (2)
                    }
    MAX-ACCESS      not-accessible
    STATUS          current
    DESCRIPTION     "The value of the object tlsMFibNgEntryType indicates
                     the type of this tlsMFibNgEntry. 

                     - macBased: entry used for macBased multicast, as for
                                 MLD-snooping and 802.1ak MMRP.
                     - ipBased:  entry used for ip_based multicast, as for
                                 IGMP-snooping and PIM-snooping."
    ::= { tlsMFibNgEntry 1 }

tlsMFibNgGrpMacAddr OBJECT-TYPE
    SYNTAX          MacAddress
    MAX-ACCESS      not-accessible
    STATUS          current
    DESCRIPTION     "The value of the object tlsMFibNgGrpMacAddr indicates the
                     MAC address for which this table entry contains
                     information.
                     
                     This value is only meaningful if the value of
                     tlsMFibNgEntryType is 'macBased (2)'."
    ::= { tlsMFibNgEntry 2 }

tlsMFibNgGrpInetAddrType OBJECT-TYPE
    SYNTAX          InetAddressType
    MAX-ACCESS      not-accessible
    STATUS          current
    DESCRIPTION     "The value of the object tlsMFibNgGrpInetAddrType indicates
                     the type of tlsMFibNgGrpInetAddr."
    ::= { tlsMFibNgEntry 3 }

tlsMFibNgGrpInetAddr OBJECT-TYPE
    SYNTAX          InetAddress (SIZE(0|4|16))
    MAX-ACCESS      not-accessible
    STATUS          current
    DESCRIPTION     "The value of the object tlsMFibNgGrpInetAddr indicates
                     the multicast destination IP address for which this table
                     entry contains information."
    ::= { tlsMFibNgEntry 4 }

tlsMFibNgSrcInetAddrType OBJECT-TYPE
    SYNTAX          InetAddressType
    MAX-ACCESS      not-accessible
    STATUS          current
    DESCRIPTION     "The value of tlsMFibNgSrcInetAddrType indicates the type
                     of tlsMFibNgSrcInetAddr."
    ::= { tlsMFibNgEntry 5 }

tlsMFibNgSrcInetAddr OBJECT-TYPE
    SYNTAX          InetAddress (SIZE(0|4|16))
    MAX-ACCESS      not-accessible
    STATUS          current
    DESCRIPTION     "The value of tlsMFibNgSrcInetAddr indicates the unicast
                     source IP address for which this table entry contains
                     information."
    ::= { tlsMFibNgEntry 6 }

tlsMFibNgLocale OBJECT-TYPE
    SYNTAX          MfibLocation
    MAX-ACCESS      not-accessible
    STATUS          current
    DESCRIPTION     "The value of tlsMFibNgLocale indicates if the information
                     in this entry pertains to a 'sap', an 'sdp' or a 'vxlan'."
    ::= { tlsMFibNgEntry 7 }

tlsMFibNgLocaleId OBJECT-TYPE
    SYNTAX          OCTET STRING (SIZE (0..32))
    MAX-ACCESS      not-accessible
    STATUS          current
    DESCRIPTION     "The value of tlsMFibNgLocaleId dependes on tlsMFibNgLocale:
    
                     If tlsMFibNgLocale='sap' then tlsMFibNgLocaleId contains
                     the sapPortId (TmnxPortID) and sapEncapValue (TmnxEncapVal).
                     
                     If tlsMFibNgLocale='sdp' then tlsMFibNgLocaleId contains
                     the sdpId (SdpId) and vcId (Unsigned32).
                     
                     If tlsMFibNgLocale='vxlan' then tlsMFibNgLocaleId contains
                     the VTEPAddr (IpAddress) and VNI (Unsigned32)."
    ::= { tlsMFibNgEntry 8 }

tlsMFibNgFwdOrBlk OBJECT-TYPE
    SYNTAX          MfibGrpSrcFwdOrBlk
    MAX-ACCESS      read-only
    STATUS          current
    DESCRIPTION     "The value of tlsMFibNgFwdOrBlk indicates if traffic for the
                     indicated (S,G) pair will be blocked or forwarded on the
                     indicated SAP, SDP or VXLAN."
    ::= { tlsMFibNgEntry 9 }

tlsMFibNgSvcId OBJECT-TYPE
    SYNTAX          TmnxServId
    MAX-ACCESS      read-only
    STATUS          current
    DESCRIPTION     "The value of tlsMFibNgSvcId indicates the TLS service
                     to which the indicated SAP, SDP or VXLAN belongs."
    ::= { tlsMFibNgEntry 10 }


-- ----------------------------------------
--  svcDhcpLeaseRipTable
--
--  Augmentation of the svcDhcpLeaseTable
--  Use of AUGMENTS clause implies a one-to-one dependent relationship
--  between the base table, svcDhcpLeaseTable, and the augmenting table,
--  svcDhcpLeaseRipTable. This in effect extends the svcDhcpLeaseTable
--  with additional columns. Creation (or deletion) of a row in the
--  svcDhcpLeaseTable results in the same fate for the row in the
--  svcDhcpLeaseRipTable.
-- ----------------------------------------

svcDhcpLeaseRipTable OBJECT-TYPE
    SYNTAX          SEQUENCE OF SvcDhcpLeaseRipEntry
    MAX-ACCESS      not-accessible
    STATUS          current
    DESCRIPTION
        "The svcDhcpLeaseRipTable augments the svcDhcpLeaseTable.
         This table contains the parameters used for RIP."
    ::= { tmnxSvcObjs 179 }

svcDhcpLeaseRipEntry OBJECT-TYPE
    SYNTAX          SvcDhcpLeaseRipEntry  
    MAX-ACCESS      not-accessible
    STATUS          current
    DESCRIPTION     
        "Each row entry contains parameters used for RIP."
    AUGMENTS        { svcDhcpLeaseEntry }
    ::= { svcDhcpLeaseRipTable 1 }

SvcDhcpLeaseRipEntry ::=
    SEQUENCE {
        svcDhcpLeaseRipPlcyName          TNamedItemOrEmpty,
        svcDhcpLeaseRipListenerStatus    TmnxRipListenerStatus
    }

svcDhcpLeaseRipPlcyName OBJECT-TYPE
    SYNTAX          TNamedItemOrEmpty
    MAX-ACCESS      read-only
    STATUS          current
    DESCRIPTION
        "The value of svcDhcpLeaseRipPlcyName indicates the
         RIP policy which is used to set up the RIP listener for this
         lease state."
    ::= { svcDhcpLeaseRipEntry 1 }

svcDhcpLeaseRipListenerStatus OBJECT-TYPE
    SYNTAX          TmnxRipListenerStatus
    MAX-ACCESS      read-only
    STATUS          current
    DESCRIPTION
        "The value of svcDhcpLeaseRipListenerStatus indicates
         the status of the RIP listener."
    ::= { svcDhcpLeaseRipEntry 2 }

    
-- ----------------------------------------
-- svcArpHostRipTable
--
--  Augmentation of the svcArpHostTable
--  Use of AUGMENTS clause implies a one-to-one dependent relationship
--  between the base table, svcArpHostTable, and the augmenting table,
--  svcArpHostRipTable. This in effect extends the svcArpHostTable
--  with additional columns. Creation (or deletion) of a row in the
--  svcArpHostTable results in the same fate for the row in the
--  svcArpHostRipTable.
-- ----------------------------------------

svcArpHostRipTable OBJECT-TYPE
    SYNTAX          SEQUENCE OF SvcArpHostRipEntry
    MAX-ACCESS      not-accessible
    STATUS          current
    DESCRIPTION
        "The svcArpHostRipTable augments the svcArpHostTable.
         This table contains the parameters used for RIP."
    ::= { tmnxSvcObjs 180 }

svcArpHostRipEntry OBJECT-TYPE
    SYNTAX          SvcArpHostRipEntry  
    MAX-ACCESS      not-accessible
    STATUS          current
    DESCRIPTION     
        "Each row entry contains parameters used for RIP."
    AUGMENTS        { svcArpHostEntry }
    ::= { svcArpHostRipTable 1 }

SvcArpHostRipEntry ::=
    SEQUENCE {
        svcArpHostRipPlcyName             TNamedItemOrEmpty,
        svcArpHostRipListenerStatus       TmnxRipListenerStatus
    }

svcArpHostRipPlcyName OBJECT-TYPE
    SYNTAX          TNamedItemOrEmpty
    MAX-ACCESS      read-only
    STATUS          current
    DESCRIPTION
        "The value of svcArpHostRipPlcyName indicates the
         RIP policy which is used to set up the RIP listener for this
         ARP host."
    ::= { svcArpHostRipEntry 1 }

svcArpHostRipListenerStatus OBJECT-TYPE
    SYNTAX          TmnxRipListenerStatus
    MAX-ACCESS      read-only
    STATUS          current
    DESCRIPTION
        "The value of svcArpHostRipListenerStatus indicates
         the status of the RIP listener."
    ::= { svcArpHostRipEntry 2 }
    
    
-- ----------------------------------------
-- Service EVPN-MPLS egress bindings Table
-- ----------------------------------------

svcEvpnMplsTEPEgrLblTable OBJECT-TYPE
    SYNTAX          SEQUENCE OF SvcEvpnMplsTEPEgrLblEntry
    MAX-ACCESS      not-accessible
    STATUS          current
    DESCRIPTION     "svcEvpnMplsTEPEgrLblTable contains entries for all the 
                     BGP EVPN-MPLS TEP and egress label pairs for a particular
                     VPLS service."
    ::= { tmnxSvcObjs 181 }

svcEvpnMplsTEPEgrLblEntry        OBJECT-TYPE
    SYNTAX          SvcEvpnMplsTEPEgrLblEntry
    MAX-ACCESS      not-accessible
    STATUS          current
    DESCRIPTION     "A egress binding entry in the svcEvpnMplsTEPEgrLblTable."
    INDEX           { svcId, svcEvpnMplsTEPEgrLblTEPAddrType,
                      svcEvpnMplsTEPEgrLblTEPAddress,
                      svcEvpnMplsTEPEgrLblTEPLabel }
    ::= { svcEvpnMplsTEPEgrLblTable 1}

SvcEvpnMplsTEPEgrLblEntry ::=    SEQUENCE {
    svcEvpnMplsTEPEgrLblTEPAddrType    InetAddressType,
    svcEvpnMplsTEPEgrLblTEPAddress     InetAddress,
    svcEvpnMplsTEPEgrLblTEPLabel       Unsigned32,
    svcEvpnMplsTEPEgrLblNumMACs        Unsigned32,
    svcEvpnMplsTEPEgrLblInMcastList    TruthValue,
    svcEvpnMplsTEPEgrLblLastChanged    TimeStamp,
    svcEvpnMplsTEPEgrLblTunnelType     TmnxTunnelTypeExt
}

svcEvpnMplsTEPEgrLblTEPAddrType     OBJECT-TYPE
    SYNTAX          InetAddressType
    MAX-ACCESS      read-only
    STATUS          current
    DESCRIPTION     "The value of the object svcEvpnMplsTEPEgrLblTEPAddrType
                     indicates the type of the address associated with
                     svcEvpnMplsTEPEgrLblTEPAddress."
    ::= { svcEvpnMplsTEPEgrLblEntry 1 }

svcEvpnMplsTEPEgrLblTEPAddress      OBJECT-TYPE
    SYNTAX          InetAddress (SIZE(4))
    MAX-ACCESS      read-only
    STATUS          current
    DESCRIPTION     "The value of the object svcEvpnMplsTEPEgrLblTEPAddress
                     indicates a Tunnel Endpoint address associated with the
                     BGP EVPN-MPLS VPLS service."
    ::= { svcEvpnMplsTEPEgrLblEntry 2 }

svcEvpnMplsTEPEgrLblTEPLabel        OBJECT-TYPE
    SYNTAX          Unsigned32
    MAX-ACCESS      read-only
    STATUS          current
    DESCRIPTION     "The value of svcEvpnMplsTEPEgrLblTEPLabel indicates the
                     egress label created by the BGP EVPN-MPLS VPLS service."
    ::= { svcEvpnMplsTEPEgrLblEntry 3 }

svcEvpnMplsTEPEgrLblNumMACs         OBJECT-TYPE
    SYNTAX          Unsigned32
    MAX-ACCESS      read-only
    STATUS          current
    DESCRIPTION     "The value of the object svcEvpnMplsTEPEgrLblNumMACs
                     indicates the number of MACs associated with TEP and
                     egress label in the BGP EVPN-MPLS VPLS service."
    ::= { svcEvpnMplsTEPEgrLblEntry 4 }

svcEvpnMplsTEPEgrLblInMcastList    OBJECT-TYPE
    SYNTAX          TruthValue
    MAX-ACCESS      read-only
    STATUS          current
    DESCRIPTION     "The value of the object svcEvpnMplsTEPEgrLblInMcastList
                     indicates if the  TEP and egress label is included in the
                     multicast list for the BGP EVPN-MPLS VPLS service."
    ::= { svcEvpnMplsTEPEgrLblEntry 5 }

svcEvpnMplsTEPEgrLblLastChanged    OBJECT-TYPE
    SYNTAX          TimeStamp
    MAX-ACCESS      read-only
    STATUS          current
    DESCRIPTION     "The value of the object svcEvpnMplsTEPEgrLblLastChanged
                     indicates the timestamp when the EVPN MPLS TEP was setup."
    ::= { svcEvpnMplsTEPEgrLblEntry 6 }

svcEvpnMplsTEPEgrLblTunnelType    OBJECT-TYPE
    SYNTAX          TmnxTunnelTypeExt
    MAX-ACCESS      read-only
    STATUS          current
    DESCRIPTION     "The value of svcEvpnMplsTEPEgrLblTunnelType indicates the
                     type of tunnel used for this entry."
    ::= { svcEvpnMplsTEPEgrLblEntry 7 }

------------------------------------------
-- tmnxSvcGrpIfTable
-- ----------------------------------------

tmnxSvcGrpIfTable   OBJECT-TYPE
    SYNTAX      SEQUENCE OF TmnxSvcGrpIfEntry
    MAX-ACCESS  not-accessible
    STATUS      current
    DESCRIPTION "The tmnxSvcGrpIfTable contains the group interfaces
                 ordered by their parent subscriber interfaces.
                 
                 The system automatically creates and destroys conceptual rows in this table
                 when rows in the iesIfTable with iesIfType equal to 'group'
                 are created and destroyed.

                 This table is only meant to order group interfaces per subscriber interface,
                 actual data objects are in other tables such as the iesGrpIfTable."
    ::= { tmnxSvcObjs 182 }

tmnxSvcGrpIfEntry   OBJECT-TYPE
    SYNTAX      TmnxSvcGrpIfEntry
    MAX-ACCESS  not-accessible
    STATUS      current
    DESCRIPTION "Each row entry represents a group interface."
    INDEX       { svcId, tmnxSvcGrpIfParentIfIndex, tmnxSvcGrpIfIndex }
    ::= { tmnxSvcGrpIfTable 1 }

TmnxSvcGrpIfEntry   ::=
    SEQUENCE {
        tmnxSvcGrpIfParentIfIndex        InterfaceIndex,
        tmnxSvcGrpIfIndex                InterfaceIndex,
        tmnxSvcGrpIfVRouterId            TmnxVRtrID
    }

tmnxSvcGrpIfParentIfIndex    OBJECT-TYPE
    SYNTAX      InterfaceIndex
    MAX-ACCESS  not-accessible
    STATUS      current
    DESCRIPTION "The value of tmnxSvcGrpIfParentIfIndex indicates
                 the index of the parent subscriber interface."
    ::= { tmnxSvcGrpIfEntry 1 }

tmnxSvcGrpIfIndex    OBJECT-TYPE
    SYNTAX      InterfaceIndex
    MAX-ACCESS  not-accessible
    STATUS      current
    DESCRIPTION "The value of tmnxSvcGrpIfIndex indicates
                 the index of this group interface."
    ::= { tmnxSvcGrpIfEntry 2 }

tmnxSvcGrpIfVRouterId OBJECT-TYPE
    SYNTAX      TmnxVRtrID
    MAX-ACCESS  read-only
    STATUS      current
    DESCRIPTION "The value of the object tmnxSvcGrpIfVRouterId indicates
                 the associated virtual router instance.

                 The value of this object, in combination with the value
                 of tmnxSvcGrpIfIndex, allows to retrieve the corresponding
                 row in the TIMETRA-VRTR-MIB::vRtrIfTable."
    ::= { tmnxSvcGrpIfEntry 3 }


tmnxSvcSysBgpEvpnObjs    OBJECT IDENTIFIER ::= { tmnxSvcObjs 183 }

tmnxSvcSysBgpEvpnRD OBJECT-TYPE
    SYNTAX          TmnxVPNRouteDistinguisher
    MAX-ACCESS      read-write
    STATUS          current
    DESCRIPTION
        "The value of tmnxSvcSysBgpEvpnRD specifies system wide BGP EVPN
         route-distinguisher which is used for ethernet segment (ES) routes
         and 'A-D' routes per ethernet-segment-identifier (ESI).
         This is a 'Type-1' route-distinguisher.

         System will use 'system-ip:0' when this object is set to the default
         value."
    DEFVAL { '0000000000000000'H }
    ::= { tmnxSvcSysBgpEvpnObjs 1 }

-- -------------------------
-- Ethernet segment table
-- -------------------------

tmnxSvcSysEthSegTblLastChanged OBJECT-TYPE
    SYNTAX      TimeStamp
    MAX-ACCESS  read-only
    STATUS      current
    DESCRIPTION
        "The value of tmnxSvcSysEthSegTblLastChanged indicates the
         sysUpTime at the time of the last modification of
         tmnxSvcSysEthSegTable."
    ::= { tmnxSvcTimeObjs 20 }

tmnxSvcSysEthSegTable    OBJECT-TYPE
    SYNTAX      SEQUENCE OF TmnxSvcSysEthSegEntry
    MAX-ACCESS  not-accessible
    STATUS      current
    DESCRIPTION    
        "The tmnxSvcSysEthSegTable contains entries for ethernet segment
         defined in the services."
    ::= { tmnxSvcObjs 184 }

tmnxSvcSysEthSegEntry    OBJECT-TYPE
    SYNTAX      TmnxSvcSysEthSegEntry
    MAX-ACCESS  not-accessible
    STATUS      current
    DESCRIPTION
        "An ethernet segment entry in the tmnxSvcSysEthSegTable."
    INDEX       { tmnxSvcSysEthSegName }
    ::= { tmnxSvcSysEthSegTable 1}

TmnxSvcSysEthSegEntry ::=    SEQUENCE {
    tmnxSvcSysEthSegName          TNamedItem,
    tmnxSvcSysEthSegRowStatus     RowStatus,
    tmnxSvcSysEthSegLastChg       TimeStamp,
    tmnxSvcSysEthSegAdminState    TmnxEnabledDisabled,
    tmnxSvcSysEthSegEsi           OCTET STRING,
    tmnxSvcSysEthSegMultiHoming   TmnxEvpnMultiHomingState,
    tmnxSvcSysEthSegSvcCarving    INTEGER,
    tmnxSvcSysEthSegLagId         LAGInterfaceNumberOrZero,
    tmnxSvcSysEthSegPortId        TmnxPortID,
    tmnxSvcSysEthSegSdpId         SdpId,
    tmnxSvcSysEthSegEsActTimer    Integer32,
    tmnxSvcSysEthSegSourceBMacLSB Integer32,
    tmnxSvcSysEthSegBMacTblSize  Integer32,
    tmnxSvcSysEthSegBMacTblEntries Integer32,
    tmnxSvcSysEthSegOperMultiHoming TmnxEvpnMultiHomingState,
    tmnxSvcSysEthSegOperState     ServiceOperStatus,
    tmnxSvcSysEthSegSHGLabel      Integer32
}

tmnxSvcSysEthSegName OBJECT-TYPE
    SYNTAX      TNamedItem (SIZE(1..28))
    MAX-ACCESS  not-accessible
    STATUS      current
    DESCRIPTION
        "The value of tmnxSvcSysEthSegName specifies the ethernet segment
         name for the entry."
    ::= { tmnxSvcSysEthSegEntry 1 }

tmnxSvcSysEthSegRowStatus OBJECT-TYPE
    SYNTAX      RowStatus
    MAX-ACCESS  read-create
    STATUS      current
    DESCRIPTION
        "The value of tmnxSvcSysEthSegRowStatus specifies the creation
         and deletion of entries in the TmnxSvcSysEthSegEntry."
    ::= { tmnxSvcSysEthSegEntry 2 }

tmnxSvcSysEthSegLastChg  OBJECT-TYPE
    SYNTAX      TimeStamp
    MAX-ACCESS  read-only
    STATUS      current
    DESCRIPTION
        "The value of tmnxSvcSysEthSegLastChg indicates the
         sysUpTime at the time of the last modification of this
         entry."
    ::= { tmnxSvcSysEthSegEntry 3 }

tmnxSvcSysEthSegAdminState OBJECT-TYPE
    SYNTAX      TmnxEnabledDisabled
    MAX-ACCESS  read-create
    STATUS      current
    DESCRIPTION
        "The value of tmnxSvcSysEthSegAdminState specifies the 
         administrative state of this entry."

    DEFVAL { disabled }
    ::= { tmnxSvcSysEthSegEntry 4 }

tmnxSvcSysEthSegEsi OBJECT-TYPE
    SYNTAX      OCTET STRING (SIZE(10))
    MAX-ACCESS  read-create
    STATUS      current
    DESCRIPTION
        "The value of tmnxSvcSysEthSegEsi specifies the ethernet segment
         identifier value associated with this ethernet segment entry."
    DEFVAL { '00000000000000000000'H }
    ::= { tmnxSvcSysEthSegEntry 5 }

tmnxSvcSysEthSegMultiHoming OBJECT-TYPE
    SYNTAX      TmnxEvpnMultiHomingState
    MAX-ACCESS  read-create
    STATUS      current
    DESCRIPTION
        "The value of tmnxSvcSysEthSegMultiHoming specifies the state of
         multi-homing status of the ethernet segment entry.

         Values other than 'disabled' indicates that the use of ESI label is
         enabled thus avoiding transient loops unless user overrides.

         When 'singleActiveNoEsiLabel' is specified, system does not allocate a
         label for the ESI and hence advertise ESI label 0 to peers. If a peers
         sends label for the ESI and locally 'singleActiveNoEsiLabel' is
         configured, system adds the ESI label when sending traffic to that
         peer."
    DEFVAL { disabled }
    ::= { tmnxSvcSysEthSegEntry 6 }

tmnxSvcSysEthSegSvcCarving OBJECT-TYPE
    SYNTAX      INTEGER {
                    auto (1),
                    manual (2),
                    off (3)
                }
    MAX-ACCESS  read-create
    STATUS      current
    DESCRIPTION
        "The value of tmnxSvcSysEthSegSvcCarving specifies the mode of service
         carving enabled per EVPN associated with this ethernet segment entry.

         auto    As defined in EVPN draft 
         manual  Designated-Forwarder (DF) when EVI/ISID is configured as
                 primary in svcEthSegCarvEviRngTable/svcEthSegCarvIsidRngTable
                 or if there is no other PEs that advertise this
                 Ethernet Segment
         off     Ethernet Segment is Designated-Forwarder or
                 Non-Designated-Forwarder (NDF) for all services."
    REFERENCE   "IETF L2VPN EVPN draft"
    DEFVAL { auto }
    ::= { tmnxSvcSysEthSegEntry 7 }

tmnxSvcSysEthSegLagId OBJECT-TYPE
    SYNTAX      LAGInterfaceNumberOrZero
    MAX-ACCESS  read-create
    STATUS      current
    DESCRIPTION
        "The value of tmnxSvcSysEthSegLagId specifies the LAG identifier
         value associated with this ethernet segment entry.
         
         An 'inconsistentValue' error is returned if more than one of
         tmnxSvcSysEthSegLagId, tmnxSvcSysEthSegPortId, tmnxSvcSysEthSegSdpId
         is set to non-default value."
    DEFVAL { 0 }
    ::= { tmnxSvcSysEthSegEntry 8 }

tmnxSvcSysEthSegPortId OBJECT-TYPE
    SYNTAX      TmnxPortID
    MAX-ACCESS  read-create
    STATUS      current
    DESCRIPTION
        "The value of tmnxSvcSysEthSegPortId specifies the port
         associated with this ethernet segment entry.
         
         The default value indicates an invalid port.

         An 'inconsistentValue' error is returned if more than one of
         tmnxSvcSysEthSegLagId, tmnxSvcSysEthSegPortId, tmnxSvcSysEthSegSdpId
         is set to non-default value."
    DEFVAL { '1E000000'H }
    ::= { tmnxSvcSysEthSegEntry 9 }

tmnxSvcSysEthSegSdpId OBJECT-TYPE
    SYNTAX      SdpId
    MAX-ACCESS  read-create
    STATUS      current
    DESCRIPTION
        "The value of tmnxSvcSysEthSegSdpId specifies the SDP identifier
         associated with this ethernet segment entry.

         An 'inconsistentValue' error is returned if more than one of
         tmnxSvcSysEthSegLagId, tmnxSvcSysEthSegPortId, tmnxSvcSysEthSegSdpId
         is set to non-default value."
    DEFVAL { 0 }
    ::= { tmnxSvcSysEthSegEntry 10 }

tmnxSvcSysEthSegEsActTimer OBJECT-TYPE
    SYNTAX      Integer32 (-1|0..100)
    MAX-ACCESS  read-create
    STATUS      current
    DESCRIPTION
        "The value of tmnxSvcSysEthSegEsActTimer specifies the activation
         timer per ES(Ethernet segment).

         This timer is disabled by default, the global ES activation timer
         is used instead.

         Value of '-1' indicates the use of the global ES activation timer
         under TIMETRA-MC-REDUNDANCY::tmnxMcRedBgpEvpnMHEsActTimer."
    DEFVAL { -1 }
    ::= { tmnxSvcSysEthSegEntry 11 }

tmnxSvcSysEthSegSourceBMacLSB    OBJECT-TYPE
    SYNTAX          Integer32 (0|1..65535)
    MAX-ACCESS      read-create
    STATUS          current
    DESCRIPTION
        "The value of tmnxSvcSysEthSegSourceBMacLSB specifies the 16 least
         significant bits (lsb) which when combined with the 32 most
         significant bits of the PBB source-bmac specified by
         svcPbbSrcBVplsMacAddr, forms the virtual backbone MAC address."
    DEFVAL { 0 }
    ::= { tmnxSvcSysEthSegEntry 12 }

tmnxSvcSysEthSegBMacTblSize OBJECT-TYPE
    SYNTAX          Integer32 (1..511999)
    MAX-ACCESS      read-create
    STATUS          current
    DESCRIPTION
        "The value of tmnxSvcSysEthSegBMacTblSize specifies the size of
         VBMAC table for this ethernet segment.
         
         An 'inconsistentValue' error is returned if
         tmnxSvcSysEthSegBMacTblSize is set to non-default when
         tmnxSvcSysEthSegSourceBMacLSB is set to its default value."
    DEFVAL { 8 }
    ::= { tmnxSvcSysEthSegEntry 13 }

tmnxSvcSysEthSegBMacTblEntries OBJECT-TYPE
    SYNTAX          Integer32
    MAX-ACCESS      read-only
    STATUS          current
    DESCRIPTION
        "The value of tmnxSvcSysEthSegBMacTblEntries indicates the size of
         VBMAC table used for this ethernet segment."
    ::= { tmnxSvcSysEthSegEntry 14 }
         
tmnxSvcSysEthSegOperMultiHoming OBJECT-TYPE
    SYNTAX      TmnxEvpnMultiHomingState
    MAX-ACCESS  read-create
    STATUS      current
    DESCRIPTION
        "The value of tmnxSvcSysEthSegOperMultiHoming indicates the operational
         state of multi-homing of the ethernet segment entry."
    ::= { tmnxSvcSysEthSegEntry 15 }

tmnxSvcSysEthSegOperState OBJECT-TYPE
    SYNTAX      ServiceOperStatus
    MAX-ACCESS  read-only
    STATUS      current
    DESCRIPTION
        "The value of tmnxSvcSysEthSegOperState indicates the operational
         state of the ethernet segment entry."
    ::= { tmnxSvcSysEthSegEntry 16 }

tmnxSvcSysEthSegSHGLabel OBJECT-TYPE
    SYNTAX      Integer32
    MAX-ACCESS  read-only
    STATUS      current
    DESCRIPTION
        "The value of tmnxSvcSysEthSegSHGLabel indicates the split horizon 
         group label advertised for the ethernet segment.
         
         The value of -1 indicates that the label is not allocated."
    ::= { tmnxSvcSysEthSegEntry 17 }

--
-- Ethernet segment EVI ranges
--
svcEthSegCarvEviRngTblLastChgd OBJECT-TYPE
    SYNTAX      TimeStamp
    MAX-ACCESS  read-only
    STATUS      current
    DESCRIPTION
        "The value of svcEthSegCarvEviRngTblLastChgd indicates the
         sysUpTime at the time of the last modification of
         svcEthSegCarvEviRngTable."
    ::= { tmnxSvcTimeObjs 21 }

svcEthSegCarvEviRngTable    OBJECT-TYPE
    SYNTAX      SEQUENCE OF SvcEthSegCarvEviRngEntry
    MAX-ACCESS  not-accessible
    STATUS      current
    DESCRIPTION    
        "The tmnxSvcSysEthSegTable contains entries for ethernet segment
        service-carving EVI ranges defined in the services."
    ::= { tmnxSvcObjs 186 }

svcEthSegCarvEviRngEntry    OBJECT-TYPE
    SYNTAX      SvcEthSegCarvEviRngEntry
    MAX-ACCESS  not-accessible
    STATUS      current
    DESCRIPTION
        "An ethernet segment serivce-carving EVI range entry in the
        svcEthSegCarvEviRngTable."
    INDEX       { tmnxSvcSysEthSegName, svcEthSegCarvEviRngFrom }
    ::= { svcEthSegCarvEviRngTable 1}

SvcEthSegCarvEviRngEntry ::=    SEQUENCE {
    svcEthSegCarvEviRngFrom      TmnxSvcEvi,
    svcEthSegCarvEviRngRowStatus RowStatus,
    svcEthSegCarvEviRngLastChg   TimeStamp,
    svcEthSegCarvEviRngTo        TmnxSvcEviOrZero
}

svcEthSegCarvEviRngFrom OBJECT-TYPE
    SYNTAX      TmnxSvcEvi
    MAX-ACCESS  not-accessible
    STATUS      current
    DESCRIPTION
        "The value of svcEthSegCarvEviRngFrom specifies the starting value
         of the EVI range associated with service-carving of the associated
         ethernet segment."
    ::= { svcEthSegCarvEviRngEntry 1 }

svcEthSegCarvEviRngRowStatus OBJECT-TYPE
    SYNTAX      RowStatus
    MAX-ACCESS  read-create
    STATUS      current
    DESCRIPTION
        "The value of svcEthSegCarvEviRngRowStatus specifies the creation
         and deletion of entries in the svcEthSegCarvEviRngTable."
    ::= { svcEthSegCarvEviRngEntry 2 }

svcEthSegCarvEviRngLastChg  OBJECT-TYPE
    SYNTAX      TimeStamp
    MAX-ACCESS  read-only
    STATUS      current
    DESCRIPTION
        "The value of svcEthSegCarvEviRngLastChg indicates the
         sysUpTime at the time of the last modification of this entry."
    ::= { svcEthSegCarvEviRngEntry 3 }

svcEthSegCarvEviRngTo OBJECT-TYPE
    SYNTAX      TmnxSvcEviOrZero
    MAX-ACCESS  read-create
    STATUS      current
    DESCRIPTION
        "The value of svcEthSegCarvEviRngFrom specifies the ending value
         of the EVI range associated with service-carving of the associated
         ethernet segment."
    DEFVAL { 0 }
    ::= { svcEthSegCarvEviRngEntry 4 }

--
-- Ethernet segment ISID ranges
--
svcEthSegCarvIsidRngTblLastChgd OBJECT-TYPE
    SYNTAX      TimeStamp
    MAX-ACCESS  read-only
    STATUS      current
    DESCRIPTION
        "The value of svcEthSegCarvIsidRngTblLastChgd indicates the
         sysUpTime at the time of the last modification of
         svcEthSegCarvIsidRngTable."
    ::= { tmnxSvcTimeObjs 22 }

svcEthSegCarvIsidRngTable    OBJECT-TYPE
    SYNTAX      SEQUENCE OF SvcEthSegCarvIsidRngEntry
    MAX-ACCESS  not-accessible
    STATUS      current
    DESCRIPTION    
        "The tmnxSvcSysEthSegTable contains entries for ethernet segment
        service-carving ISID ranges defined in the services."
    ::= { tmnxSvcObjs 187 }

svcEthSegCarvIsidRngEntry    OBJECT-TYPE
    SYNTAX      SvcEthSegCarvIsidRngEntry
    MAX-ACCESS  not-accessible
    STATUS      current
    DESCRIPTION
        "An ethernet segment serivce-carving ISID range entry in the
        svcEthSegCarvIsidRngTable."
    INDEX       { tmnxSvcSysEthSegName, svcEthSegCarvIsidRngFrom }
    ::= { svcEthSegCarvIsidRngTable 1}

SvcEthSegCarvIsidRngEntry ::=    SEQUENCE {
    svcEthSegCarvIsidRngFrom      TmnxISIDNoZero,
    svcEthSegCarvIsidRngRowStatus RowStatus,
    svcEthSegCarvIsidRngLastChg   TimeStamp,
    svcEthSegCarvIsidRngTo        TmnxISID
}

svcEthSegCarvIsidRngFrom OBJECT-TYPE
    SYNTAX      TmnxISIDNoZero
    MAX-ACCESS  not-accessible
    STATUS      current
    DESCRIPTION
        "The value of svcEthSegCarvIsidRngFrom specifies the starting value
         of the ISID range associated with service-carving of the associated
         ethernet segment."
    ::= { svcEthSegCarvIsidRngEntry 1 }

svcEthSegCarvIsidRngRowStatus OBJECT-TYPE
    SYNTAX      RowStatus
    MAX-ACCESS  read-create
    STATUS      current
    DESCRIPTION
        "The value of svcEthSegCarvIsidRngRowStatus specifies the creation
         and deletion of entries in the svcEthSegCarvIsidRngTable."
    ::= { svcEthSegCarvIsidRngEntry 2 }

svcEthSegCarvIsidRngLastChg  OBJECT-TYPE
    SYNTAX      TimeStamp
    MAX-ACCESS  read-only
    STATUS      current
    DESCRIPTION
        "The value of svcEthSegCarvIsidRngLastChg indicates the
         sysUpTime at the time of the last modification of this entry."
    ::= { svcEthSegCarvIsidRngEntry 3 }

svcEthSegCarvIsidRngTo OBJECT-TYPE
    SYNTAX      TmnxISID
    MAX-ACCESS  read-create
    STATUS      current
    DESCRIPTION
        "The value of svcEthSegCarvIsidRngFrom specifies the ending value
         of the ISID range associated with service-carving of the associated
         ethernet segment."
    DEFVAL { 0 }
    ::= { svcEthSegCarvIsidRngEntry 4 }

--
-- Ethernet segment Evi readonly table
--
svcEvpnMHEthSegEviTable     OBJECT-TYPE
    SYNTAX      SEQUENCE OF SvcEvpnMHEthSegEviEntry
    MAX-ACCESS  not-accessible
    STATUS      current
    DESCRIPTION
        "The svcEvpnMHEthSegEviTable contains entries for ethernet segment
        EVI read only objects."
    ::= { tmnxSvcObjs 188 }

svcEvpnMHEthSegEviEntry    OBJECT-TYPE
    SYNTAX      SvcEvpnMHEthSegEviEntry
    MAX-ACCESS  not-accessible
    STATUS      current
    DESCRIPTION
        "An ethernet segment EVI entry in the svcEvpnMHEthSegEviTable."
    INDEX       { tmnxSvcSysEthSegName, svcEvpnMHEthSegEvi }
    ::= { svcEvpnMHEthSegEviTable 1}

SvcEvpnMHEthSegEviEntry ::=    SEQUENCE {
    svcEvpnMHEthSegEvi              TmnxISIDNoZero,
    svcEvpnMHEthSegEviIsDF          TruthValue,
    svcEvpnMHEthSegEviActTimRem     Integer32,
    svcEvpnMHEthSegEviSvcId         TmnxServId,
    svcEvpnMHEthSegEviDFLastChanged   TimeStamp
}

svcEvpnMHEthSegEvi OBJECT-TYPE
    SYNTAX      TmnxISIDNoZero
    MAX-ACCESS  not-accessible
    STATUS      current
    DESCRIPTION
        "The value of svcEvpnMHEthSegEvi specifies the ISID value
         associated with service-carving of the associated
         Evi ethernet segment."
    ::= { svcEvpnMHEthSegEviEntry 1 }

svcEvpnMHEthSegEviIsDF OBJECT-TYPE
    SYNTAX      TruthValue
    MAX-ACCESS  read-only
    STATUS      current
    DESCRIPTION
        "The value of svcEvpnMHEthSegEviIsDF indicates if the ethernet segment
         EVI entry is a designated forwarder."
    ::= { svcEvpnMHEthSegEviEntry 2 }

svcEvpnMHEthSegEviActTimRem OBJECT-TYPE
    SYNTAX      Integer32
    UNITS       "seconds"
    MAX-ACCESS  read-only
    STATUS      current
    DESCRIPTION
        "The value of svcEvpnMHEthSegEviActTimRem indicates the value of the
         remaining activation timer for the EVI entry."
    ::= { svcEvpnMHEthSegEviEntry 3 }

svcEvpnMHEthSegEviSvcId OBJECT-TYPE
    SYNTAX          TmnxServId
    MAX-ACCESS      read-only
    STATUS          current
    DESCRIPTION   
        "The value of the object svcEvpnMHEthSegEviSvcId specifies the
         EVI Service identifier. This value should be unique within the
         service domain."
    ::= { svcEvpnMHEthSegEviEntry 4 }

svcEvpnMHEthSegEviDFLastChanged  OBJECT-TYPE
    SYNTAX          TimeStamp
    MAX-ACCESS      read-only
    STATUS          current
    DESCRIPTION     "The value of svcEvpnMHEthSegEviDFLastChanged indicates the
                     sysUpTime at the time of the last modification of EVI DF."
    ::= { svcEvpnMHEthSegEviEntry 5 }
--
-- Ethernet segment ISID readonly table
--
svcEvpnMHEthSegIsidTable     OBJECT-TYPE
    SYNTAX      SEQUENCE OF SvcEvpnMHEthSegIsidEntry
    MAX-ACCESS  not-accessible
    STATUS      current
    DESCRIPTION
        "The svcEvpnMHEthSegIsidTable contains entries for ISID ethernet segment
        read only objects."
    ::= { tmnxSvcObjs 195 }

svcEvpnMHEthSegIsidEntry    OBJECT-TYPE
    SYNTAX      SvcEvpnMHEthSegIsidEntry
    MAX-ACCESS  not-accessible
    STATUS      current
    DESCRIPTION
        "An ISID ethernet segment entry in the svcEvpnMHEthSegIsidTable."
    INDEX       { tmnxSvcSysEthSegName, svcEvpnMHEthSegIsid }
    ::= { svcEvpnMHEthSegIsidTable 1}

SvcEvpnMHEthSegIsidEntry ::=    SEQUENCE {
    svcEvpnMHEthSegIsid                TmnxISIDNoZero,
    svcEvpnMHEthSegIsidIsDF            TruthValue,
    svcEvpnMHEthSegIsidActTimRem       Integer32,
    svcEvpnMHEthSegIsidSvcId           TmnxServId,
    svcEvpnMHEthSegIsidDFLastChanged   TimeStamp 
}

svcEvpnMHEthSegIsid OBJECT-TYPE
    SYNTAX      TmnxISIDNoZero
    MAX-ACCESS  not-accessible
    STATUS      current
    DESCRIPTION
        "The value of svcEvpnMHEthSegIsid specifies the ISID value
         associated with service-carving of the associated
         ISID ethernet segment."
    ::= { svcEvpnMHEthSegIsidEntry 1 }

svcEvpnMHEthSegIsidIsDF OBJECT-TYPE
    SYNTAX      TruthValue
    MAX-ACCESS  read-only
    STATUS      current
    DESCRIPTION
        "The value of svcEvpnMHEthSegIsidIsDF indicates if the ISID ethernet segment
         entry is a designated forwarder."
    ::= { svcEvpnMHEthSegIsidEntry 2 }

svcEvpnMHEthSegIsidActTimRem OBJECT-TYPE
    SYNTAX      Integer32
    UNITS       "seconds"
    MAX-ACCESS  read-only
    STATUS      current
    DESCRIPTION
        "The value of svcEvpnMHEthSegIsidActTimRem indicates the value of the
         remaining activation timer for the ISID entry."
    ::= { svcEvpnMHEthSegIsidEntry 3 }

svcEvpnMHEthSegIsidSvcId OBJECT-TYPE
    SYNTAX          TmnxServId
    MAX-ACCESS      read-only
    STATUS          current
    DESCRIPTION 
        "The value of the object svcEvpnMHEthSegIsidSvcId specifies the
         ISID Service identifier. This value should be unique within the
         service domain."
    ::= { svcEvpnMHEthSegIsidEntry 4 }

svcEvpnMHEthSegIsidDFLastChanged  OBJECT-TYPE
    SYNTAX          TimeStamp
    MAX-ACCESS      read-only
    STATUS          current
    DESCRIPTION     "The value of svcEvpnMHEthSegIsidDFLastChanged indicates the
                     sysUpTime at the time of the last modification of Isid DF."
    ::= { svcEvpnMHEthSegIsidEntry 5 }

--
-- Ethernet segment candidate EVI designated forwarder table
--
svcEvpnMHEthSegEviDFCndtTable     OBJECT-TYPE
    SYNTAX      SEQUENCE OF SvcEvpnMHEthSegEviDFCndtEntry
    MAX-ACCESS  not-accessible
    STATUS      current
    DESCRIPTION
        "The svcEvpnMHEthSegEviDFCndtTable contains entries for EVI ethernet
         segment candidate designated forwarders."
    ::= { tmnxSvcObjs 189 }

svcEvpnMHEthSegEviDFCndtEntry    OBJECT-TYPE
    SYNTAX      SvcEvpnMHEthSegEviDFCndtEntry
    MAX-ACCESS  not-accessible
    STATUS      current
    DESCRIPTION
        "An EVI ethernet segment candidate designated forwarder entry in the
         svcEvpnMHEthSegEviDFCndtTable."
    INDEX       { tmnxSvcSysEthSegName, svcEvpnMHEthSegEvi,
                  svcEvpnMHEthSegEviDFCndtAddrType,
                  svcEvpnMHEthSegEviDFCndtAddress}
    ::= { svcEvpnMHEthSegEviDFCndtTable 1}

SvcEvpnMHEthSegEviDFCndtEntry ::=    SEQUENCE {
    svcEvpnMHEthSegEviDFCndtAddrType         InetAddressType,
    svcEvpnMHEthSegEviDFCndtAddress          InetAddress,
    svcEvpnMHEthSegEviDFCndtAdded            TimeStamp
}

svcEvpnMHEthSegEviDFCndtAddrType OBJECT-TYPE
    SYNTAX      InetAddressType
    MAX-ACCESS  not-accessible
    STATUS      current
    DESCRIPTION
        "The value of svcEvpnMHEthSegEviDFCndtAddrType indicates the type of the
         EVI candidate PE IP address."
    ::= { svcEvpnMHEthSegEviDFCndtEntry 1 }

svcEvpnMHEthSegEviDFCndtAddress OBJECT-TYPE
    SYNTAX      InetAddress (SIZE(4))
    MAX-ACCESS  not-accessible
    STATUS      current
    DESCRIPTION
        "The value of svcEvpnMHEthSegEviDFCndtAddress indicates the value of the
         EVI candidate PE IP address."
    ::= { svcEvpnMHEthSegEviDFCndtEntry 2 }

svcEvpnMHEthSegEviDFCndtAdded OBJECT-TYPE
    SYNTAX          TimeStamp
    MAX-ACCESS      read-only
    STATUS          current
    DESCRIPTION
        "The value of svcEvpnMHEthSegEviDFCndtAdded indicates the time at
         which this entry was added in the EVI DF candidate list."
    ::= { svcEvpnMHEthSegEviDFCndtEntry 3 }

--
-- Ethernet segment candidate ISID designated forwarder table
--
svcEvpnMHEthSegIsidDFCndtTable     OBJECT-TYPE
    SYNTAX      SEQUENCE OF SvcEvpnMHEthSegIsidDFCndtEntry
    MAX-ACCESS  not-accessible
    STATUS      current
    DESCRIPTION
        "The svcEvpnMHEthSegIsidDFCndtTable contains entries for ISID ethernet
         segment candidate designated forwarders."
    ::= { tmnxSvcObjs 196 }

svcEvpnMHEthSegIsidDFCndtEntry    OBJECT-TYPE
    SYNTAX      SvcEvpnMHEthSegIsidDFCndtEntry
    MAX-ACCESS  not-accessible
    STATUS      current
    DESCRIPTION
        "An ethernet segment ISID candidate designated forwarder entry in the
         svcEvpnMHEthSegIsidDFCndtTable."
    INDEX       { tmnxSvcSysEthSegName, svcEvpnMHEthSegIsid,
                  svcEvpnMHEthSegIsidDFCndtAdType,
                  svcEvpnMHEthSegIsidDFCndtAddress}
    ::= { svcEvpnMHEthSegIsidDFCndtTable 1}

SvcEvpnMHEthSegIsidDFCndtEntry ::=    SEQUENCE {
    svcEvpnMHEthSegIsidDFCndtAdType           InetAddressType,
    svcEvpnMHEthSegIsidDFCndtAddress          InetAddress,
    svcEvpnMHEthSegIsidDFCndtAdded        TimeStamp
}

svcEvpnMHEthSegIsidDFCndtAdType OBJECT-TYPE
    SYNTAX      InetAddressType
    MAX-ACCESS  not-accessible
    STATUS      current
    DESCRIPTION
        "The value of svcEvpnMHEthSegIsidDFCndtAdType indicates the type of the
         ISID candidate PE IP address."
    ::= { svcEvpnMHEthSegIsidDFCndtEntry 1 }

svcEvpnMHEthSegIsidDFCndtAddress OBJECT-TYPE
    SYNTAX      InetAddress (SIZE(4))
    MAX-ACCESS  not-accessible
    STATUS      current
    DESCRIPTION
        "The value of svcEvpnMHEthSegIsidDFCndtAddress indicates the value of the
         ISID candidate PE IP address."
    ::= { svcEvpnMHEthSegIsidDFCndtEntry 2 }

svcEvpnMHEthSegIsidDFCndtAdded OBJECT-TYPE
    SYNTAX          TimeStamp
    MAX-ACCESS      read-only
    STATUS          current
    DESCRIPTION
        "The value of svcEvpnMHEthSegIsidDFCndtAdded indicates the time at
         which this entry was added in the ISID DF candidate list."
    ::= { svcEvpnMHEthSegIsidDFCndtEntry 3 }

--
-- Ethernet segment backbone MAC address table
--
svcSysEthSegBMacTable     OBJECT-TYPE
    SYNTAX      SEQUENCE OF SvcSysEthSegBMacEntry
    MAX-ACCESS  not-accessible
    STATUS      current
    DESCRIPTION
        "The svcSysEthSegBMacTable contains entries for ethernet segment
         backbone MAC address read only objects."
    ::= { tmnxSvcObjs 199 }

svcSysEthSegBMacEntry    OBJECT-TYPE
    SYNTAX      SvcSysEthSegBMacEntry
    MAX-ACCESS  not-accessible
    STATUS      current
    DESCRIPTION
        "An ethernet segment backbone MAC address entry in the
         svcSysEthSegBMacTable."
    INDEX       { tmnxSvcSysEthSegName, svcId }
    ::= { svcSysEthSegBMacTable 1}

SvcSysEthSegBMacEntry ::= SEQUENCE {
    svcSysEthSegBMacAddress          MacAddress
}

svcSysEthSegBMacAddress OBJECT-TYPE
    SYNTAX      MacAddress
    MAX-ACCESS  read-only
    STATUS      current
    DESCRIPTION
        "The value of svcSysEthSegBMacAddress indicates the backbone MAC address
         associated with this entry."
    ::= { svcSysEthSegBMacEntry 1 }

-- ----------------------------------------
-- Interface Ipv6 Host Info Table
-- Sparse augment of the TIMETRA-SERV-MIB::iesIfTable
-- ----------------------------------------
tmnxIesIfIpv6HostInfoTable   OBJECT-TYPE
    SYNTAX      SEQUENCE OF TmnxIesIfIpv6HostInfoEntry
    MAX-ACCESS  not-accessible
    STATUS      current
    DESCRIPTION     "The tmnxIesIfIpv6HostInfoTable contains IPv6 information
                     related to routed CO subscriber for a specific interface.
                     This table complements iesIfTable, rows in this table are
                     created and deleted automatically by the system."
    ::= { tmnxSvcObjs 185 }

tmnxIesIfIpv6HostInfoEntry OBJECT-TYPE
    SYNTAX      TmnxIesIfIpv6HostInfoEntry
    MAX-ACCESS  not-accessible
    STATUS      current
    DESCRIPTION     "IPv6 interface specific information for routed CO 
                     subscribers."
    INDEX { svcId, iesIfIndex }
    ::= { tmnxIesIfIpv6HostInfoTable 1 }

TmnxIesIfIpv6HostInfoEntry ::=
    SEQUENCE {
        tmnxIesIfIpv6IpoeDhcp6Hosts      Unsigned32,
        tmnxIesIfIpv6PppDhcp6Hosts       Unsigned32,
        tmnxIesIfIpv6PppSLAACHosts       Unsigned32,
        tmnxIesIfIpv6IpoeSLAACHosts      Unsigned32,
        tmnxIesIfIpv6StaticHostsUp       Unsigned32
    }

tmnxIesIfIpv6IpoeDhcp6Hosts OBJECT-TYPE
    SYNTAX          Unsigned32
    MAX-ACCESS      read-only
    STATUS          current
    DESCRIPTION     "The value of the object tmnxIesIfIpv6IpoeDhcp6Hosts
                     indicates the number of IPoE DHCPv6 hosts for this
                     interface."
    ::= { tmnxIesIfIpv6HostInfoEntry 1 }

tmnxIesIfIpv6PppDhcp6Hosts OBJECT-TYPE
    SYNTAX          Unsigned32
    MAX-ACCESS      read-only
    STATUS          current
    DESCRIPTION     "The value of the object tmnxIesIfIpv6PppDhcp6Hosts
                     indicates the number of PPP DHCPv6 hosts for this 
                     interface."
    ::= { tmnxIesIfIpv6HostInfoEntry 2 }

tmnxIesIfIpv6PppSLAACHosts OBJECT-TYPE
    SYNTAX          Unsigned32
    MAX-ACCESS      read-only
    STATUS          current
    DESCRIPTION     "The value of the object tmnxIesIfIpv6PppSLAACHosts
                     indicates the number of PPP SLAAC hosts for this 
                     interface."
    ::= { tmnxIesIfIpv6HostInfoEntry 3 }

tmnxIesIfIpv6IpoeSLAACHosts OBJECT-TYPE
    SYNTAX          Unsigned32
    MAX-ACCESS      read-only
    STATUS          current
    DESCRIPTION     "The value of the object tmnxIesIfIpv6IpoeSLAACHosts
                     indicates the number of IPoE SLAAC hosts for this 
                     interface."
    ::= { tmnxIesIfIpv6HostInfoEntry 4 }

tmnxIesIfIpv6StaticHostsUp OBJECT-TYPE
    SYNTAX          Unsigned32
    MAX-ACCESS      read-only
    STATUS          current
    DESCRIPTION     "The value of the object tmnxIesIfIpv6StaticHostsUp
                     indicates the number of IPv6 static IPoE hosts
                     for this interface where the value of 
                     ?sapStatHost6AdminStatus? is equal to 'up'."
    ::= { tmnxIesIfIpv6HostInfoEntry 5 }

svcTlsProxyArpCountTable      OBJECT-TYPE
    SYNTAX          SEQUENCE OF SvcTlsProxyArpCountEntry
    MAX-ACCESS      not-accessible
    STATUS          current
    DESCRIPTION
        "svcTlsProxyArpCountTable contains counts for various type
         of proxy ARP entries for each VPLS service in the system."
    ::= { tmnxSvcObjs 190 }

svcTlsProxyArpCountEntry    OBJECT-TYPE
    SYNTAX          SvcTlsProxyArpCountEntry
    MAX-ACCESS      not-accessible
    STATUS          current
    DESCRIPTION
        "A svcTlsProxyArpCountEntry maintains count for specific type of
         proxy ARP entry for specific VPLS service."
    INDEX           { svcId, svcTlsProxyArpType }
    ::= { svcTlsProxyArpCountTable 1}

SvcTlsProxyArpCountEntry ::=    SEQUENCE {
    svcTlsProxyArpCount          Counter32
}

svcTlsProxyArpCount OBJECT-TYPE
    SYNTAX          Counter32
    MAX-ACCESS      read-only
    STATUS          current
    DESCRIPTION     
        "The svcTlsProxyArpCount indicates the count of this type of 
         entry in this VPLS instance."
    ::= { svcTlsProxyArpCountEntry 1 }

svcTlsProxyNdCountTable      OBJECT-TYPE
    SYNTAX          SEQUENCE OF SvcTlsProxyNdCountEntry
    MAX-ACCESS      not-accessible
    STATUS          current
    DESCRIPTION
        "svcTlsProxyNdCountTable contains counts for various type
         of proxy ARP entries for each VPLS service in the system."
    ::= { tmnxSvcObjs 191 }

svcTlsProxyNdCountEntry    OBJECT-TYPE
    SYNTAX          SvcTlsProxyNdCountEntry
    MAX-ACCESS      not-accessible
    STATUS          current
    DESCRIPTION
        "A svcTlsProxyNdCountEntry maintains count for specific type of
         proxy ARP entry for specific VPLS service."
    INDEX           { svcId, svcTlsProxyNdType }
    ::= { svcTlsProxyNdCountTable 1}

SvcTlsProxyNdCountEntry ::=    SEQUENCE {
    svcTlsProxyNdCount          Counter32
}

svcTlsProxyNdCount OBJECT-TYPE
    SYNTAX          Counter32
    MAX-ACCESS      read-only
    STATUS          current
    DESCRIPTION     
        "The svcTlsProxyNdCount indicates the count of this type of 
         entry in this VPLS instance."
    ::= { svcTlsProxyNdCountEntry 1 }

-- ----------------------------------------
-- DHCP Managed Route Table
-- ----------------------------------------
tmnxSvcDhcpMRtTable OBJECT-TYPE
    SYNTAX          SEQUENCE OF TmnxSvcDhcpMRtEntry
    MAX-ACCESS      not-accessible
    STATUS          current
    DESCRIPTION     "A table that contains DHCP managed routes."
    ::= { tmnxSvcObjs 192 }

tmnxSvcDhcpMRtEntry OBJECT-TYPE
    SYNTAX          TmnxSvcDhcpMRtEntry
    MAX-ACCESS      not-accessible
    STATUS          current
    DESCRIPTION     "A specific DHCP managed route."
    INDEX { svcId,
            svcDhcpLeaseCiAddrType,
            svcDhcpLeaseCiAddr,
            svcDhcpLeaseNextHopMacAddr,
            tmnxSvcDhcpMRtInetAddrType,
            tmnxSvcDhcpMRtInetAddr,
            tmnxSvcDhcpMRtPrefixLen }
    ::= { tmnxSvcDhcpMRtTable 1 }

TmnxSvcDhcpMRtEntry ::=
    SEQUENCE {
        tmnxSvcDhcpMRtInetAddrType       InetAddressType,
        tmnxSvcDhcpMRtInetAddr           InetAddress,
        tmnxSvcDhcpMRtPrefixLen          InetAddressPrefixLength,
        tmnxSvcDhcpMRtStatus             TmnxManagedRouteStatus,
        tmnxSvcDhcpMRtMetric             TmnxRadiusFramedRouteMetric,
        tmnxSvcDhcpMRtPreference         TmnxRadiusFramedRoutePreference,
        tmnxSvcDhcpMRtTag                TmnxRadiusFramedRouteTag             
    }

tmnxSvcDhcpMRtInetAddrType OBJECT-TYPE
    SYNTAX          InetAddressType
    MAX-ACCESS      not-accessible
    STATUS          current
    DESCRIPTION     
        "The value of tmnxSvcDhcpMRtInetAddrType indicates
         the address type of tmnxSvcDhcpMRtInetAddr."
    ::= { tmnxSvcDhcpMRtEntry 1 }

tmnxSvcDhcpMRtInetAddr OBJECT-TYPE
    SYNTAX          InetAddress (SIZE(4|16))
    MAX-ACCESS      not-accessible
    STATUS          current
    DESCRIPTION
         "The value of tmnxSvcDhcpMRtInetAddr indicates
          the IP address of the managed route."
    ::= { tmnxSvcDhcpMRtEntry 2 }

tmnxSvcDhcpMRtPrefixLen OBJECT-TYPE
    SYNTAX          InetAddressPrefixLength (0..128)
    MAX-ACCESS      not-accessible
    STATUS          current
    DESCRIPTION
         "The value of tmnxSvcDhcpMRtPrefixLen indicates
          the prefix length of the subnet associated with
          tmnxSvcDhcpMRtInetAddr."
    ::= { tmnxSvcDhcpMRtEntry 3 }

tmnxSvcDhcpMRtStatus OBJECT-TYPE
    SYNTAX          TmnxManagedRouteStatus
    MAX-ACCESS      read-only
    STATUS          current
    DESCRIPTION
         "The value of tmnxSvcDhcpMRtStatus indicates
          the state of this managed route."
    ::= { tmnxSvcDhcpMRtEntry 4 }

tmnxSvcDhcpMRtMetric OBJECT-TYPE
    SYNTAX          TmnxRadiusFramedRouteMetric
    MAX-ACCESS      read-only
    STATUS          current
    DESCRIPTION
         "The value of tmnxSubSlaacMRtMetric indicates
          the metric of this managed route as specified
          in the RADIUS option 22 Framed-Route or 
          option 99 Framed-IPv6-Route."
    ::= { tmnxSvcDhcpMRtEntry 5 }

tmnxSvcDhcpMRtPreference OBJECT-TYPE
    SYNTAX          TmnxRadiusFramedRoutePreference
    MAX-ACCESS      read-only
    STATUS          current
    DESCRIPTION
         "The value of tmnxSubSlaacMRtPreference indicates
          the preference of this managed route as specified
          in the RADIUS option 22 Framed-Route or 
          option 99 Framed-IPv6-Route."
    ::= { tmnxSvcDhcpMRtEntry 6 }

tmnxSvcDhcpMRtTag OBJECT-TYPE
    SYNTAX          TmnxRadiusFramedRouteTag
    MAX-ACCESS      read-only
    STATUS          current
    DESCRIPTION
         "The value of tmnxSubSlaacMRtTag indicates
          the tag of this managed route as specified
          in the RADIUS option 22 Framed-Route or 
          option 99 Framed-IPv6-Route."
    ::= { tmnxSvcDhcpMRtEntry 7 }



svcEvpnMplsESDestTEPTable OBJECT-TYPE
    SYNTAX          SEQUENCE OF SvcEvpnMplsEthSegDestEntry
    MAX-ACCESS      not-accessible
    STATUS          current
    DESCRIPTION
        "The svcEvpnMplsESDestTEPTable contains entries for all the 
         BGP EVPN-MPLS Tunnel End-Point and ethernet segment pairs for a
         particular VPLS service."
    ::= { tmnxSvcObjs 194 }

svcEvpnMplsESDestTEPEntry        OBJECT-TYPE
    SYNTAX          SvcEvpnMplsEthSegDestEntry
    MAX-ACCESS      not-accessible
    STATUS          current
    DESCRIPTION
        "A BGP EVPN-MPLS Tunnel End-Point and ethernet segment binding entry in
         the svcEvpnMplsESDestTEPTable."
    INDEX { svcId, tmnxSvcSysEthSegEsi,
            svcEvpnMplsESDestTEPAddrType, svcEvpnMplsESDestTEPAddress }
    ::= { svcEvpnMplsESDestTEPTable 1}

SvcEvpnMplsEthSegDestEntry ::=    SEQUENCE {
    svcEvpnMplsESDestTEPAddrType    InetAddressType,
    svcEvpnMplsESDestTEPAddress     InetAddress,
    svcEvpnMplsESDestTEPLabel       Unsigned32,
    svcEvpnMplsESDestTEPLastChanged    TimeStamp,
    svcEvpnMplsESDestTEPTunnelType     TmnxTunnelTypeExt
}

svcEvpnMplsESDestTEPAddrType     OBJECT-TYPE
    SYNTAX          InetAddressType
    MAX-ACCESS      not-accessible
    STATUS          current
    DESCRIPTION
        "The value of the object svcEvpnMplsESDestTEPAddrType
         indicates the type of the address associated with
         svcEvpnMplsESDestTEPAddress."
    ::= { svcEvpnMplsESDestTEPEntry 1 }

svcEvpnMplsESDestTEPAddress      OBJECT-TYPE
    SYNTAX          InetAddress (SIZE(4))
    MAX-ACCESS      not-accessible
    STATUS          current
    DESCRIPTION
        "The value of the object svcEvpnMplsESDestTEPAddress
         indicates a Tunnel Endpoint address associated with this entry."
    ::= { svcEvpnMplsESDestTEPEntry 2 }

svcEvpnMplsESDestTEPLabel        OBJECT-TYPE
    SYNTAX          Unsigned32
    MAX-ACCESS      read-only
    STATUS          current
    DESCRIPTION
        "The value of svcEvpnMplsESDestTEPLabel indicates the
         label associated with the Tunnel End-Point address in the service."
    ::= { svcEvpnMplsESDestTEPEntry 3 }

svcEvpnMplsESDestTEPLastChanged    OBJECT-TYPE
    SYNTAX          TimeStamp
    MAX-ACCESS      read-only
    STATUS          current
    DESCRIPTION     "The value of the object svcEvpnMplsESDestTEPLastChanged
                     indicates the timestamp of the modification of the ethernet
                     segment destination entry."
    ::= { svcEvpnMplsESDestTEPEntry 4 }

svcEvpnMplsESDestTEPTunnelType     OBJECT-TYPE
    SYNTAX          TmnxTunnelTypeExt
    MAX-ACCESS      read-only
    STATUS          current
    DESCRIPTION     "The value of svcEvpnMplsESDestTEPTunnelType indicates the
                     type of tunnel used for this entry."
    ::= { svcEvpnMplsESDestTEPEntry 5 }

--
-- Virtual Backbone MAC binding to EVPN tunnel destination address table
--
svcEvpnMplsPbbESDestTEPTable OBJECT-TYPE
    SYNTAX          SEQUENCE OF SvcEvpnMplsPbbESDestEntry
    MAX-ACCESS      not-accessible
    STATUS          current
    DESCRIPTION
        "The svcEvpnMplsPbbESDestTEPTable contains entries for all the 
         BGP EVPN-MPLS Tunnel End-Point and virtual backbone MAC address pairs
         for a particular VPLS service."
    ::= { tmnxSvcObjs 198 }

svcEvpnMplsPbbESDestTEPEntry        OBJECT-TYPE
    SYNTAX          SvcEvpnMplsPbbESDestEntry
    MAX-ACCESS      not-accessible
    STATUS          current
    DESCRIPTION
        "A BGP EVPN-MPLS Tunnel End-Point and virtual backbone MAC address
         binding entry in the svcEvpnMplsPbbESDestTEPTable."
    INDEX { svcId, svcEvpnMplsPbbESDestTEPBMac,
            svcEvpnMplsPbbESDestTEPAddrType, svcEvpnMplsPbbESDestTEPAddress }
    ::= { svcEvpnMplsPbbESDestTEPTable 1}

SvcEvpnMplsPbbESDestEntry ::=    SEQUENCE {
    svcEvpnMplsPbbESDestTEPBMac          MacAddress,
    svcEvpnMplsPbbESDestTEPAddrType    InetAddressType,
    svcEvpnMplsPbbESDestTEPAddress     InetAddress,
    svcEvpnMplsPbbESDestTEPLabel       Unsigned32,
    svcEvpnMplsPbbESDestTEPLstChg    TimeStamp,
    svcEvpnMplsPbbESDestTEPTnlType     TmnxTunnelTypeExt
}

svcEvpnMplsPbbESDestTEPBMac     OBJECT-TYPE
    SYNTAX          MacAddress
    MAX-ACCESS      not-accessible
    STATUS          current
    DESCRIPTION
        "The value of the object svcEvpnMplsPbbESDestTEPBMac
         indicates the virtual backbone MAC address of this entry."
    ::= { svcEvpnMplsPbbESDestTEPEntry 1 }

svcEvpnMplsPbbESDestTEPAddrType     OBJECT-TYPE
    SYNTAX          InetAddressType
    MAX-ACCESS      not-accessible
    STATUS          current
    DESCRIPTION
        "The value of the object svcEvpnMplsPbbESDestTEPAddrType
         indicates the type of the address associated with
         svcEvpnMplsPbbESDestTEPAddress."
    ::= { svcEvpnMplsPbbESDestTEPEntry 2 }

svcEvpnMplsPbbESDestTEPAddress      OBJECT-TYPE
    SYNTAX          InetAddress (SIZE(4))
    MAX-ACCESS      not-accessible
    STATUS          current
    DESCRIPTION
        "The value of the object svcEvpnMplsPbbESDestTEPAddress
         indicates a Tunnel Endpoint address associated with this entry."
    ::= { svcEvpnMplsPbbESDestTEPEntry 3 }

svcEvpnMplsPbbESDestTEPLabel        OBJECT-TYPE
    SYNTAX          Unsigned32
    MAX-ACCESS      read-only
    STATUS          current
    DESCRIPTION
        "The value of svcEvpnMplsPbbESDestTEPLabel indicates the
         label associated with the Tunnel End-Point address in the service."
    ::= { svcEvpnMplsPbbESDestTEPEntry 4 }

svcEvpnMplsPbbESDestTEPLstChg    OBJECT-TYPE
    SYNTAX          TimeStamp
    MAX-ACCESS      read-only
    STATUS          current
    DESCRIPTION     "The value of the object svcEvpnMplsPbbESDestTEPLstChg
                     indicates the timestamp of the modification of this entry."
    ::= { svcEvpnMplsPbbESDestTEPEntry 5 }

svcEvpnMplsPbbESDestTEPTnlType     OBJECT-TYPE
    SYNTAX          TmnxTunnelTypeExt
    MAX-ACCESS      read-only
    STATUS          current
    DESCRIPTION     "The value of svcEvpnMplsPbbESDestTEPTnlType indicates the
                     type of tunnel used for this entry."
    ::= {svcEvpnMplsPbbESDestTEPEntry 6 }

-- svcEvpnMplsESDestTable
svcEvpnMplsESDestTable OBJECT-TYPE
    SYNTAX          SEQUENCE OF SvcEvpnMplsESDestEntry
    MAX-ACCESS      not-accessible
    STATUS          current
    DESCRIPTION
        "The svcEvpnMplsESDestTable contains entries for all the 
         BGP EVPN-MPLS Tunnel ethernet segment destination for a
         particular VPLS service."
    ::= { tmnxSvcObjs 202 }

svcEvpnMplsESDestEntry        OBJECT-TYPE
    SYNTAX          SvcEvpnMplsESDestEntry
    MAX-ACCESS      not-accessible
    STATUS          current
    DESCRIPTION
        "A BGP EVPN-MPLS Tunnel End-Point and ethernet segment binding entry
         in the svcEvpnMplsESDestTable."
    INDEX { svcId, tmnxSvcSysEthSegEsi }
    ::= { svcEvpnMplsESDestTable 1}

SvcEvpnMplsESDestEntry ::=    SEQUENCE {
    svcEvpnMplsESDestNumMacs      Unsigned32,
    svcEvpnMplsESDestLastChanged    TimeStamp
}

svcEvpnMplsESDestNumMacs     OBJECT-TYPE
    SYNTAX          Unsigned32
    MAX-ACCESS      read-only
    STATUS          current
    DESCRIPTION
        "The value of svcEvpnMplsESDestNumMacs indicates number of
         labels associated with this entry."
    ::= { svcEvpnMplsESDestEntry 1 }

svcEvpnMplsESDestLastChanged    OBJECT-TYPE
    SYNTAX          TimeStamp
    MAX-ACCESS      read-only
    STATUS          current
    DESCRIPTION     "The value of the object svcEvpnMplsESDestLastChanged
                     indicates the timestamp of the modification of the ethernet
                     segment destination entry."
    ::= { svcEvpnMplsESDestEntry 2 }

-- svcEvpnMplsPbbESegDestTable
svcEvpnMplsPbbESegDestTable OBJECT-TYPE
    SYNTAX          SEQUENCE OF SvcEvpnMplsPbbESegDestEntry
    MAX-ACCESS      not-accessible
    STATUS          current
    DESCRIPTION
        "The svcEvpnMplsPbbESegDestTable contains entries for all the 
         BGP EVPN-MPLS Tunnel PBB ethernet segment destination for a
         particular VPLS service."
    ::= { tmnxSvcObjs 203 }

svcEvpnMplsPbbESegDestEntry        OBJECT-TYPE
    SYNTAX          SvcEvpnMplsPbbESegDestEntry
    MAX-ACCESS      not-accessible
    STATUS          current
    DESCRIPTION
        "A BGP EVPN-MPLS Tunnel End-Point and ethernet segment binding entry
         in the svcEvpnMplsPbbESegDestTable."
    INDEX { svcId, svcEvpnMplsPbbESDestTEPBMac }
    ::= { svcEvpnMplsPbbESegDestTable 1}

SvcEvpnMplsPbbESegDestEntry ::=    SEQUENCE {
    svcEvpnMplsPbbESegDestNumMacs      Unsigned32,
    svcEvpnMplsPbbESegDestLstChg         TimeStamp
}

svcEvpnMplsPbbESegDestNumMacs     OBJECT-TYPE
    SYNTAX          Unsigned32
    MAX-ACCESS      read-only
    STATUS          current
    DESCRIPTION
        "The value of svcEvpnMplsPbbESegDestNumMacs indicates number of
         labels associated with this entry."
    ::= { svcEvpnMplsPbbESegDestEntry 1 }

svcEvpnMplsPbbESegDestLstChg    OBJECT-TYPE
    SYNTAX          TimeStamp
    MAX-ACCESS      read-only
    STATUS          current
    DESCRIPTION     "The value of the object svcEvpnMplsPbbESegDestLstChg
                     indicates the timestamp of the modification of this entry."
    ::= { svcEvpnMplsPbbESegDestEntry 2 }

-- ------------------------------
-- Service trap objects
-- ------------------------------
macPinningMacAddress OBJECT-TYPE
    SYNTAX         MacAddress
    MAX-ACCESS     accessible-for-notify
    STATUS         current
    DESCRIPTION    "The value of the object macPinningMacAddress indicates
                    the pinned MAC address."
    ::= { tmnxSvcNotifyObjs 1 }

macPinningPinnedRow OBJECT-TYPE
    SYNTAX         RowPointer
    MAX-ACCESS     accessible-for-notify
    STATUS         current
    DESCRIPTION    "The value of the object macPinningPinnedRow indicates
                    where the MAC address is currently pinned on.
                    Its value will be the OID of the first accessible
                    object in the row of the sapTlsInfoTable or in the
                    sdpBindTable, depending on whether the MAC address is
                    pinned on a SAP or a SDP Bind."
    ::= { tmnxSvcNotifyObjs 2 }

macPinningPinnedRowDescr OBJECT-TYPE
    SYNTAX         DisplayString
    MAX-ACCESS     accessible-for-notify
    STATUS         current
    DESCRIPTION    "The value of the object macPinningPinnedRowDescr indicates
                    where the MAC address is currently pinned on. The value
                    will either be a SAP-id or a SDP id, presented in readable
                    format, depending on whether the MAC is pinned to a SAP
                    or a SDP."
    ::= { tmnxSvcNotifyObjs 3 }

macPinningViolatingRow OBJECT-TYPE
    SYNTAX         RowPointer
    MAX-ACCESS     accessible-for-notify
    STATUS         current
    DESCRIPTION    "The value of the object macPinningViolatingRow indicates
                    where the MAC address relearn attempt was detected.
                    Its value will be the OID of the first accessible object
                    in the row of the sapTlsInfoTable or in the sdpBindTable,
                    depending on whether the MAC address is pinned on a SAP
                    or a SDP Bind."
    ::= { tmnxSvcNotifyObjs 4 }

macPinningViolatingRowDescr OBJECT-TYPE
    SYNTAX         DisplayString
    MAX-ACCESS     accessible-for-notify
    STATUS         current
    DESCRIPTION    "The value of the object macPinningViolatingRowDescr
                    indicates where the MAC address relearn attempt was
                    detected. The value will either be a SAP-id or a SDP id,
                    presented in readable format, depending on whether the
                    MAC address relearn attempt was detected on a SAP or a
                    SDP."
    ::= { tmnxSvcNotifyObjs 5 }

tlsDHCPClientLease OBJECT-TYPE
    SYNTAX         Integer32
    MAX-ACCESS     accessible-for-notify
    STATUS         obsolete
    DESCRIPTION    "The value of the object tlsDHCPClientLease indicates the
                    lease time specified in the PDU causing the trap.
                    Used by tmnxVRtrDHCPAFEntriesExceeded to report the lease
                    time.
                    This object was made obsolete in the 4.0 release."
    ::= { tmnxSvcNotifyObjs 6 }

tlsDhcpLseStateOldCiAddr OBJECT-TYPE
    SYNTAX         IpAddress
    MAX-ACCESS     accessible-for-notify
    STATUS         obsolete
    DESCRIPTION    "The value of the object tlsDhcpLseStateOldCiAddr indicates
                    the Client IP address that was formerly assigned to this
                    Least state. Used in sapTlsDHCPLeaseStateOverride trap.
                    This object was made obsolete in the 4.0 release."
    ::= { tmnxSvcNotifyObjs 7 }

tlsDhcpLseStateOldChAddr OBJECT-TYPE
    SYNTAX         MacAddress
    MAX-ACCESS     accessible-for-notify
    STATUS         obsolete
    DESCRIPTION    "The value of the object tlsDhcpLseStateOldChAddr indicates
                    the Client MAC address that was formerly assigned to this
                    Least state. Used in sapTlsDHCPLeaseStateOverride trap.
                    This object was made obsolete in the 4.0 release."
    ::= { tmnxSvcNotifyObjs 8 }

tlsDhcpLseStateNewCiAddr OBJECT-TYPE
    SYNTAX         IpAddress
    MAX-ACCESS     accessible-for-notify
    STATUS         obsolete
    DESCRIPTION    "The value of the object tlsDhcpLseStateNewCiAddr indicates
                    the Client IP address specified in the PDU causing
                    the trap.
                    This object was made obsolete in the 4.0 release."
    ::= { tmnxSvcNotifyObjs 9 }

tlsDhcpLseStateNewChAddr OBJECT-TYPE
    SYNTAX         MacAddress
    MAX-ACCESS     accessible-for-notify
    STATUS         obsolete
    DESCRIPTION    "The value of the object tlsDhcpLseStateNewChAddr indicates
                    the Client MAC address specified in the PDU causing
                    the trap.
                    This object was made obsolete in the 4.0 release."
    ::= { tmnxSvcNotifyObjs 10 }

tlsDhcpRestoreLseStateCiAddr OBJECT-TYPE
    SYNTAX         IpAddress
    MAX-ACCESS     accessible-for-notify
    STATUS         obsolete
    DESCRIPTION    "The value of the object tlsDhcpRestoreLseStateCiAddr
                    indicates the IP address specified in the persistency
                    record causing the trap.
                    This object was made obsolete in the 4.0 release."
    ::= { tmnxSvcNotifyObjs 11 }

tlsDhcpRestoreLseStateSvcId OBJECT-TYPE
    SYNTAX         TmnxServId
    MAX-ACCESS     accessible-for-notify
    STATUS         obsolete
    DESCRIPTION    "The value of the object tlsDhcpRestoreLseStateSvcId
                    indicates the serviceId specified in the persistency record
                    causing the trap.
                    This object was made obsolete in the 4.0 release."
    ::= { tmnxSvcNotifyObjs 12 }

tlsDhcpRestoreLseStatePortId OBJECT-TYPE
    SYNTAX         TmnxPortID
    MAX-ACCESS     accessible-for-notify
    STATUS         obsolete
    DESCRIPTION    "The value of the object tlsDhcpRestoreLseStatePortId
                    indicates the Port ID specified in the persistency record
                    causing the trap.
                    This object was made obsolete in the 4.0 release."
    ::= { tmnxSvcNotifyObjs 13 }

tlsDhcpRestoreLseStateEncapVal OBJECT-TYPE
    SYNTAX         TmnxEncapVal
    MAX-ACCESS     accessible-for-notify
    STATUS         obsolete
    DESCRIPTION    "The value of the object tlsDhcpRestoreLseStateEncapVal
                    indicates the SAP encap value specified in the persistency
                    record causing the trap.
                    This object was made obsolete in the 4.0 release."
    ::= { tmnxSvcNotifyObjs 14 }

tlsDhcpRestoreLseStateProblem OBJECT-TYPE
    SYNTAX         DisplayString
    MAX-ACCESS     accessible-for-notify
    STATUS         obsolete
    DESCRIPTION    "The value of the object tlsDhcpRestoreLseStateProblem
                    indicates why the persistency record cannot be restored.
                    This object was made obsolete in the 4.0 release."
    ::= { tmnxSvcNotifyObjs 15 }

tlsDhcpPacketProblem OBJECT-TYPE
    SYNTAX         DisplayString
    MAX-ACCESS     accessible-for-notify
    STATUS         obsolete
    DESCRIPTION    "The value of the object tlsDhcpPacketProblem indicates
                    information on a received DHCP packet is considered
                    suspicious by the system.
                    This object was made obsolete in the 4.0 release."
    ::= { tmnxSvcNotifyObjs 16 }

tlsDhcpLseStatePopulateError OBJECT-TYPE
    SYNTAX         DisplayString
    MAX-ACCESS     accessible-for-notify
    STATUS         obsolete
    DESCRIPTION    "The value of the object tlsDhcpLseStatePopulateError
                    indicates  why the system was unable to update the
                    Lease State Table upon reception of a DHCP ACK message.
                    This object was made obsolete in the 4.0 release."
    ::= { tmnxSvcNotifyObjs 17 }

svcDhcpRestoreLseStateCiAddr OBJECT-TYPE
    SYNTAX         IpAddress
    MAX-ACCESS     accessible-for-notify
    STATUS         current
    DESCRIPTION    "The value of the object svcDhcpRestoreLseStateCiAddr
                    indicates the IP address specified in the persistency
                    record causing the trap."
    ::= { tmnxSvcNotifyObjs 18 }

svcDhcpRestoreLseStateProblem OBJECT-TYPE
    SYNTAX         DisplayString
    MAX-ACCESS     accessible-for-notify
    STATUS         current
    DESCRIPTION    "The value of the object svcDhcpRestoreLseStateProblem
                    indicates why the persistency record cannot be restored."
    ::= { tmnxSvcNotifyObjs 19 }

svcDhcpLseStateOldCiAddr OBJECT-TYPE
    SYNTAX         IpAddress
    MAX-ACCESS     accessible-for-notify
    STATUS         current
    DESCRIPTION    "The value of the object svcDhcpLseStateOldCiAddr indicates
                    the client IP address that was formerly assigned to the
                    specified DHCP lease state."
    ::= { tmnxSvcNotifyObjs 20 }

svcDhcpLseStateOldChAddr OBJECT-TYPE
    SYNTAX         MacAddress
    MAX-ACCESS     accessible-for-notify
    STATUS         current
    DESCRIPTION    "The value of the object svcDhcpLseStateOldChAddr indicates
                    the client MAC address that was formerly assigned to the
                    specified DHCP lease state."
    ::= { tmnxSvcNotifyObjs 21 }

svcDhcpLseStateNewCiAddr OBJECT-TYPE
    SYNTAX         IpAddress
    MAX-ACCESS     accessible-for-notify
    STATUS         current
    DESCRIPTION    "The value of the object svcDhcpLseStateNewCiAddr indicates
                    the client IP address specified in the DHCP PDU causing the
                    trap."
    ::= { tmnxSvcNotifyObjs 22 }

svcDhcpLseStateNewChAddr OBJECT-TYPE
    SYNTAX         MacAddress
    MAX-ACCESS     accessible-for-notify
    STATUS         current
    DESCRIPTION    "The value of the object svcDhcpLseStateNewChAddr indicates
                    the client MAC address specified in the DHCP PDU causing
                    the trap."
    ::= { tmnxSvcNotifyObjs 23 }

svcDhcpClientLease OBJECT-TYPE
    SYNTAX         Integer32
    MAX-ACCESS     accessible-for-notify
    STATUS         current
    DESCRIPTION    "The value of the object svcDhcpClientLease indicates the
                    lease time specified in the DHCP PDU causing the trap."
    ::= { tmnxSvcNotifyObjs 24 }

svcDhcpPacketProblem OBJECT-TYPE
    SYNTAX         DisplayString
    MAX-ACCESS     accessible-for-notify
    STATUS         current
    DESCRIPTION    "The value of the object svcDhcpPacketProblem indicates
                    information on a received DHCP packet that is considered
                    suspicious by the system."
    ::= { tmnxSvcNotifyObjs 25 }

svcDhcpLseStatePopulateError OBJECT-TYPE
    SYNTAX         DisplayString
    MAX-ACCESS     accessible-for-notify
    STATUS         current
    DESCRIPTION    "The value of the object svcDhcpLseStatePopulateError
                    indicates the reason why the system was unable to update
                    the Lease State table upon reception of a DHCP ACK
                    message."
    ::= { tmnxSvcNotifyObjs 26 }

hostConnectivityCiAddrType OBJECT-TYPE
    SYNTAX         InetAddressType
    MAX-ACCESS     accessible-for-notify
    STATUS         current
    DESCRIPTION    "The value of the object hostConnectivityCiAddrType indicates
                    the client address type causing the trap."
    ::= { tmnxSvcNotifyObjs 27 }

hostConnectivityCiAddr OBJECT-TYPE
    SYNTAX         InetAddress
    MAX-ACCESS     accessible-for-notify
    STATUS         current
    DESCRIPTION    "The value of the object hostConnectivityCiAddr indicates
                    the client INET address causing the trap."
    ::= { tmnxSvcNotifyObjs 28 }

hostConnectivityChAddr OBJECT-TYPE
    SYNTAX         MacAddress
    MAX-ACCESS     accessible-for-notify
    STATUS         current
    DESCRIPTION    "The value of the object hostConnectivityChAddr indicates
                    the client MAC address causing the trap."
    ::= { tmnxSvcNotifyObjs 29 }

protectedMacForNotify OBJECT-TYPE
    SYNTAX         MacAddress
    MAX-ACCESS     accessible-for-notify
    STATUS         current
    DESCRIPTION    "The value of the object protectedMacForNotify indicates
                    the protected MAC address that was received, causing the
                    sapReceivedProtSrcMac notification."
    ::= { tmnxSvcNotifyObjs 30 }

staticHostDynamicMacIpAddress OBJECT-TYPE
    SYNTAX         IpAddress
    MAX-ACCESS     accessible-for-notify
    STATUS         current
    DESCRIPTION    "The value of the object staticHostDynamicMacIpAddress
                    indicates the IP address of the static host for which the
                    sapStaticHostDynMacConflict notification is generated."
    ::= { tmnxSvcNotifyObjs 31 }

staticHostDynamicMacConflict OBJECT-TYPE
    SYNTAX         DisplayString
    MAX-ACCESS     accessible-for-notify
    STATUS         current
    DESCRIPTION    "The value of the object staticHostDynamicMacConflict
                    indicates the reason causing the sapStaticHostDynMacConflict
                    notification."
    ::= { tmnxSvcNotifyObjs 32 }

tmnxSvcObjRow OBJECT-TYPE
    SYNTAX         RowPointer
    MAX-ACCESS     accessible-for-notify
    STATUS         current
    DESCRIPTION    "The value of the object tmnxSvcObjRow indicates
                    the object that has failed to perform the set action
                    requested by the Time-Of-Day Suite.
                    Its value will be the OID of the first accessible
                    object in the row of the sapBaseInfoTable or in the
                    custMultiServiceSiteTable, depending on whether the object
                    is a SAP or a Customer Multi-Service Site."
    ::= { tmnxSvcNotifyObjs 33 }

tmnxSvcObjRowDescr OBJECT-TYPE
    SYNTAX         DisplayString
    MAX-ACCESS     accessible-for-notify
    STATUS         current
    DESCRIPTION    "The value of the object tmnxSvcObjRowDescr indicates
                    the object that has failed to perform the set action
                    requested by the Time-Of-Day Suite. 
                    The value will either be a SAP-id or 
                    a Customer Multi-Service Site id, presented in readable
                    format, depending on whether the object
                    is a SAP or a Customer Multi-Service Site."
    ::= { tmnxSvcNotifyObjs 34 }

tmnxSvcObjTodSuite OBJECT-TYPE
    SYNTAX     DisplayString
    MAX-ACCESS accessible-for-notify
    STATUS     current
    DESCRIPTION
        "The value of the object tmnxSvcObjTodSuite indicates the name of the
         involved ToD Suite."
    ::= { tmnxSvcNotifyObjs 35 }

tmnxFailureDescription OBJECT-TYPE
    SYNTAX         DisplayString
    MAX-ACCESS     accessible-for-notify
    STATUS         current
    DESCRIPTION    "The value of the object tmnxFailureDescription is a
                    printable character string which contains information about
                    the reason why the notification is sent."
    ::= { tmnxSvcNotifyObjs 36 }

svcDhcpProxyError OBJECT-TYPE
    SYNTAX         DisplayString
    MAX-ACCESS     accessible-for-notify
    STATUS         current
    DESCRIPTION    "The value of the object svcDhcpProxyError indicates
                    the reason why the proxy server failed to operate."
    ::= { tmnxSvcNotifyObjs 37 }

svcDhcpCoAError OBJECT-TYPE
    SYNTAX         DisplayString
    MAX-ACCESS     accessible-for-notify
    STATUS         current
    DESCRIPTION    "The value of the object svcDhcpCoAError indicates
                    the reason why the node failed to process a Change of
                    Authorization (CoA) request from a Radius server."
    ::= { tmnxSvcNotifyObjs 38 }

svcDhcpSubAuthError OBJECT-TYPE
    SYNTAX         DisplayString
    MAX-ACCESS     accessible-for-notify
    STATUS         current
    DESCRIPTION    "The value of the object svcDhcpSubAuthError is a printable
                    character string which contains information about the
                    problem that occurred while trying to authenticate the
                    subscriber."
    ::= { tmnxSvcNotifyObjs 39 }

svcTlsMrpAttrRegFailedReason OBJECT-TYPE
    SYNTAX         INTEGER {
                      unknown                   (1),
                      attribute-limit-reached   (2),
                      system-attr-limit-reached (3),
                      unsupported-attribute     (4),
                      mfib-entry-create-failed  (5)
                      }
    MAX-ACCESS     accessible-for-notify
    STATUS         current
    DESCRIPTION    "The value of the object svcTlsMrpAttrRegFailedReason
                    indicates the reason for MRP attribute registration
                    failure."
    ::= { tmnxSvcNotifyObjs 40 }

svcTlsMrpAttrType OBJECT-TYPE
    SYNTAX         Unsigned32 (1..255)
    MAX-ACCESS     accessible-for-notify
    STATUS         current
    DESCRIPTION    "The value of the object svcTlsMrpAttrType indicates the
                    type of MRP attribute."
    ::= { tmnxSvcNotifyObjs 41 }

svcTlsMrpAttrValue OBJECT-TYPE
    SYNTAX         OCTET STRING (SIZE(0..255))
    MAX-ACCESS     accessible-for-notify
    STATUS         current
    DESCRIPTION    "The value of the object svcTlsMrpAttrValue indicates the
                    value of MRP attribute."
    ::= { tmnxSvcNotifyObjs 42 }

svcMstiInstanceId OBJECT-TYPE
    SYNTAX         MstiInstanceId
    MAX-ACCESS     accessible-for-notify
    STATUS         current
    DESCRIPTION    "The value of the object svcMstiInstanceId indicates the
                    Multiple Spanning Tree Instance."
    ::= { tmnxSvcNotifyObjs 43 }

-- V7v0 feature, not in V6v1 :
svcNotifSapPortId OBJECT-TYPE
    SYNTAX         TmnxPortID
    MAX-ACCESS     accessible-for-notify
    STATUS         current
    DESCRIPTION    "The ID of the access port where the SAP is defined."
    ::= { tmnxSvcNotifyObjs 44 }

svcNotifSapEncapValue OBJECT-TYPE
    SYNTAX         TmnxEncapVal
    MAX-ACCESS     accessible-for-notify
    STATUS         current
    DESCRIPTION    "The value of the label used to identify the
                    SAP on the access port specified by sapPortId."
    ::= { tmnxSvcNotifyObjs 45 }

svcArpHostPopulateError OBJECT-TYPE
    SYNTAX         DisplayString
    MAX-ACCESS     accessible-for-notify
    STATUS         current
    DESCRIPTION    "The value of the object svcArpHostPopulateError
                    indicates the reason why the system failed to update
                    the ARP Host table upon reception of an ARP message."
    ::= { tmnxSvcNotifyObjs 46 }

svcHostAddrType OBJECT-TYPE
    SYNTAX         InetAddressType
    MAX-ACCESS     accessible-for-notify
    STATUS         current
    DESCRIPTION    "The value of the object svcHostAddrType
                    indicates the address type of svcHostAddr."
    ::= { tmnxSvcNotifyObjs 47 }

svcHostAddr OBJECT-TYPE
    SYNTAX         InetAddress (SIZE(0|4|16))
    MAX-ACCESS     accessible-for-notify
    STATUS         current
    DESCRIPTION    "The value of the object svcHostAddr
                    indicates the IP address specified in the persistency
                    record causing the trap."
    ::= { tmnxSvcNotifyObjs 48 }

svcNotifSiteName OBJECT-TYPE
    SYNTAX       TNamedItem
    MAX-ACCESS   accessible-for-notify
    STATUS       current
    DESCRIPTION     
        "The value of svcNotifSiteName indicates the name for the specific
         site."
    ::= { tmnxSvcNotifyObjs 49 }
 
svcNotifSiteMinDnTimerState OBJECT-TYPE
    SYNTAX       INTEGER {
                       started (1),
                       cancelled (2),
                       extended (3),
                       expired (4)
                 }
    MAX-ACCESS   accessible-for-notify
    STATUS       current
    DESCRIPTION
        "The value of svcNotifSiteMinDnTimerState indicate state of
         minimum-down-timer for the site."
    ::= { tmnxSvcNotifyObjs 50 }

svcNotifSiteMinDnTimer OBJECT-TYPE
    SYNTAX       Integer32 (0..100)
    UNITS        "seconds"
    MAX-ACCESS   accessible-for-notify
    STATUS       current
    DESCRIPTION
        "The value of svcNotifSiteMinDnTimer indicate the minimum
        time-period the system keeps the site down when a site goes down."
    ::= { tmnxSvcNotifyObjs 51 }

svcNotifSiteMinDnTimerRemain OBJECT-TYPE
    SYNTAX       Unsigned32
    UNITS        "seconds"
    MAX-ACCESS   accessible-for-notify
    STATUS       current
    DESCRIPTION
        "The value of svcNotifSiteMinDnTimerRemain indicates remaining time
        in the svcNotifSiteMinDnTimer for this site."
    ::= { tmnxSvcNotifyObjs 52 }

svcNotifTlsProxyMacAddr OBJECT-TYPE
    SYNTAX         MacAddress
    MAX-ACCESS     accessible-for-notify
    STATUS         current
    DESCRIPTION
        "The value of svcNotifTlsProxyMacAddr indicates the new MAC address
         detected with the proxy ARP/ND entry."
    ::= { tmnxSvcNotifyObjs 53 }

svcNotifyMacAddress OBJECT-TYPE
    SYNTAX         MacAddress
    MAX-ACCESS     accessible-for-notify
    STATUS         current
    DESCRIPTION    "The value of the object svcNotifyMacAddress indicates a MAC address."
    ::= { tmnxSvcNotifyObjs 54 }

svcNotifyText  OBJECT-TYPE
    SYNTAX      DisplayString
    MAX-ACCESS  accessible-for-notify
    STATUS      current
    DESCRIPTION
        "The value of svcNotifyText indicates a text."
    ::= { tmnxSvcNotifyObjs 55 }


-- ------------------------------------
-- Service traps
-- ------------------------------------
svcCreated NOTIFICATION-TYPE
    OBJECTS {
        custId,
        svcId,
        svcVpnId,
        svcType
    }
    STATUS          obsolete
    DESCRIPTION     "This trap is sent when a new row is created
                     in the svcBaseInfoTable. The object is obsoleted and 
                     replaced with tmnxConfigModify notification."
    ::= { svcTraps 1 }

svcDeleted NOTIFICATION-TYPE
    OBJECTS {
        custId,
        svcId,
        svcVpnId
    }
    STATUS          obsolete
    DESCRIPTION     "This trap is sent when an existing row is
                     deleted from the svcBaseInfoTable. The object is obsoleted 
                     and replaced with tmnxConfigModify notification."
    ::= { svcTraps 2 }

svcStatusChanged NOTIFICATION-TYPE
    OBJECTS {
        custId,
        svcId,
        svcVpnId,
        svcAdminStatus,
        svcOperStatus
    }
    STATUS          current
    DESCRIPTION     "The svcStatusChanged notification is generated when
                     there is a change in the administrative or operating
                     status of a service."
    ::= { svcTraps 3 }

svcTlsFdbTableFullAlarmRaised NOTIFICATION-TYPE
    OBJECTS {
        custId,
        svcId,
        svcVpnId
    }
    STATUS          current
    DESCRIPTION     "The svcTlsFdbTableFullAlarmRaised notification is
                     generated when the utilization of the FDB table
                     increases to reach the value specified by
                     svcTlsFdbTableFullHighWatermark."
    ::= { svcTraps 4 }

svcTlsFdbTableFullAlarmCleared NOTIFICATION-TYPE
    OBJECTS {
        custId,
        svcId,
        svcVpnId
    }
    STATUS          current
    DESCRIPTION     "The svcTlsFdbTableFullAlarmCleared notification is
                     generated when the utilization of the FDB table 
                     drops to the value specified by
                     svcTlsFdbTableFullLowWatermark."
    ::= { svcTraps 5 }

iesIfCreated NOTIFICATION-TYPE
    OBJECTS {
        custId,
        svcId,
        svcVpnId,
        iesIfIndex
    }
    STATUS          obsolete
    DESCRIPTION     "The iesIfCreated notification is generated
                     when a new row is created in the iesIfTable. The object is 
                     obsoleted and replaced with tmnxConfigModify notification."
    ::= { svcTraps 6 }

iesIfDeleted NOTIFICATION-TYPE
    OBJECTS {
        custId,
        svcId,
        svcVpnId,
        iesIfIndex
    }
    STATUS          obsolete
    DESCRIPTION     "The iesIfDeleted notification is sent when an existing
                     row is deleted from the iesIfTable. The object is 
                     obsoleted and replaced with tmnxConfigModify notification."
    ::= { svcTraps 7 }

iesIfStatusChanged NOTIFICATION-TYPE
    OBJECTS {
        custId,
        svcId,
        svcVpnId,
        iesIfIndex,
        iesIfAdminStatus,
        iesIfOperStatus
    }
    STATUS          current
    DESCRIPTION     "The iesIfStatusChanged notification is generated
                     when there is a change in the administrative or
                     operating status of an IES interface."
    ::= { svcTraps 8 }

svcTlsMfibTableFullAlarmRaised NOTIFICATION-TYPE
    OBJECTS {
        custId,
        svcId,
        svcVpnId
    }
    STATUS          current
    DESCRIPTION     "The svcTlsMfibTableFullAlarmRaised notification is
                     generated when the utilization of the MFIB table increases
                     to reach the value specified by
                     svcTlsMfibTableFullHighWatermark."
    ::= { svcTraps 9 }

svcTlsMfibTableFullAlarmCleared NOTIFICATION-TYPE
    OBJECTS {
        custId,
        svcId,
        svcVpnId
    }
    STATUS          current
    DESCRIPTION     "The svcTlsMfibTableFullAlarmCleared notification is
                     generated when the utilization of the MFIB table 
                     drops to the value specified by 
                     svcTlsMfibTableFullLowWatermark."
    ::= { svcTraps 10 }

svcTlsMacPinningViolation NOTIFICATION-TYPE
    OBJECTS {
        custId,
        svcId,
        svcVpnId,
        macPinningMacAddress,
        macPinningPinnedRow,
        macPinningPinnedRowDescr,
        macPinningViolatingRow,
        macPinningViolatingRowDescr
    }
    STATUS          current
    DESCRIPTION     "The svcTlsMacPinningViolation notification is
                     generated when an attempt is made to assign a MAC
                     address to another interface while this MAC address
                     is pinned (i.e. assigned fixed to an interface)."
    ::= { svcTraps 11 }

svcTlsDHCPLseStRestoreProblem NOTIFICATION-TYPE
    OBJECTS {
        tlsDhcpRestoreLseStateSvcId,
        tlsDhcpRestoreLseStatePortId,
        tlsDhcpRestoreLseStateEncapVal,
        tlsDhcpRestoreLseStateCiAddr,
        tlsDhcpRestoreLseStateProblem
    }
    STATUS          obsolete
    DESCRIPTION     "The svcTlsDHCPLseStRestoreProblem notification is
                     generated when an an error is detected while
                     processing a persistency record."
    ::= { svcTraps 12 }

svcTlsDHCPLseStatePopulateErr NOTIFICATION-TYPE
    OBJECTS {
        custId,
        svcId,
        tlsDhcpLseStatePopulateError
    }
    STATUS          obsolete
    DESCRIPTION     "The svcTlsDHCPLseStatePopulateErr notification
                     indicates that the system was unable to update the
                     Lease State Table with the information contained in
                     the DHCP ACK message. The DHCP ACK message has been
                     discarded."
    ::= { svcTraps 13 }

svcDHCPLseStateRestoreProblem NOTIFICATION-TYPE
    OBJECTS {
        svcDhcpRestoreLseStateCiAddr,
        svcDhcpRestoreLseStateProblem
    }
    STATUS          current
    DESCRIPTION     "The svcDHCPLseStateRestoreProblem notification is
                     generated when an an error is detected while processing a
                     persistency record."
    ::= { svcTraps 14 }

tmnxSvcObjTodSuiteApplicFailed NOTIFICATION-TYPE
    OBJECTS {
        tmnxSvcObjRow,
        tmnxSvcObjRowDescr,
        tmnxSvcObjTodSuite,
        tmnxFailureDescription
    }
    STATUS          current
    DESCRIPTION     "The tmnxSvcObjTodSuiteApplicFailed notification is
                     generated when the object has failed to perform the set
                     action requested by the Time-Of-Day Suite. The object can
                     be either a SAP or a Customer Multi-Service Site."
    ::= { svcTraps 15 }

tmnxEndPointTxActiveChanged       NOTIFICATION-TYPE
    OBJECTS {
        svcEndPointTxActiveType,
        svcEndPointTxActivePortId,
        svcEndPointTxActiveEncap,
        svcEndPointTxActiveSdpId
    }
    STATUS          current
    DESCRIPTION     "The tmnxEndPointTxActiveChanged notification is generated
                     when the transmit active object on an endpoint changes."
    ::= { svcTraps 16 }

tmnxSvcPEDiscPolServOperStatChg NOTIFICATION-TYPE
    OBJECTS {
        svcPEDiscPolServerAddressType,
        svcPEDiscPolServerAddress,
        svcPEDiscPolServerOperStatus
    }
    STATUS  obsolete
    DESCRIPTION
        "The tmnxSvcPEDiscPolServOperStatChg notification is generated 
         when the operational status of a Radius server, configured for use 
         as PE Discovery Policy Server, has transitioned either from 'up' to 
         'down' or from 'down' to 'up'."
    ::= { svcTraps 17 }

svcEndPointMacLimitAlarmRaised  NOTIFICATION-TYPE
    OBJECTS {
        custId,
        svcId,
        svcVpnId,
        svcEndPointMacLimit
    }
    STATUS          current
    DESCRIPTION
        "The svcEndPointMacLimitAlarmRaised notification is sent whenever the
        number of MAC addresses stored in the FDB for this endpoint exceeds the
        watermark specified by the object svcTlsFdbTableFullHighWatermark.

        This alarm also takes into consideration static MAC addresses
        configured on the endpoint and learned MAC addresses in all spokes
        associated with this endpoint."
    ::= { svcTraps 18 }

svcEndPointMacLimitAlarmCleared  NOTIFICATION-TYPE
    OBJECTS {
        custId,
        svcId,
        svcVpnId,
        svcEndPointMacLimit
    }
    STATUS          current
    DESCRIPTION
        "The svcEndPointMacLimitAlarmCleared notification is sent whenever the
        number of MAC addresses stored in the FDB for this endpoint drops below
        the watermark specified by the object svcTlsFdbTableFullLowWatermark.

        This alarm also takes into consideration static MAC addresses
        configured on the endpoint and learned MAC addresses in all spokes
        associated with this endpoint."
    ::= { svcTraps 19 }

svcTlsMrpAttrRegistrationFailed NOTIFICATION-TYPE
    OBJECTS {
        custId,
        svcId,
        svcTlsMrpAttrRegFailedReason,
        svcTlsMrpAttrType,
        svcTlsMrpAttrValue
    }
    STATUS          current
    DESCRIPTION     "The svcTlsMrpAttrRegistrationFailed notification is
                     generated when registration fails for an MRP attribute."
    ::= { svcTraps 20 }

svcFdbMimDestTblFullAlrm NOTIFICATION-TYPE
    OBJECTS {
            svcTotalFdbMimDestIdxEntries
    }
    STATUS          current
    DESCRIPTION     "The svcFdbMimDestTblFullAlrm notification is raised
                     when system limit of Backbone MAC address indices limit is
                     reached.
                     
                     Further traps are not generated as long as the value of
                     svcTotalFdbMimDestIdxEntries object remains under 5
                     percent of the limit."
   ::= { svcTraps 21 }

svcFdbMimDestTblFullAlrmCleared NOTIFICATION-TYPE
    OBJECTS {
            svcTotalFdbMimDestIdxEntries
    }
    STATUS          current
    DESCRIPTION     "The svcFdbMimDestTblFullAlrmCleared notification is raised
                     when number of Backbone MAC address indices used reaches
                     under 95 percent of the system limit after
                     svcFdbMimDestTblFullAlrm notification had been raised."
   ::= { svcTraps 22 }

svcDHCPMiscellaneousProblem NOTIFICATION-TYPE
    OBJECTS {
            tmnxFailureDescription
    }
    STATUS          current
    DESCRIPTION     "The svcDHCPMiscellaneousProblem notification is
                     generated on miscellaneous DHCP problems."
    ::= { svcTraps 23 }

svcPersistencyProblem NOTIFICATION-TYPE
    OBJECTS {
            svcId,
            tmnxFailureDescription
    }
    STATUS          current
    DESCRIPTION     "The svcPersistencyProblem notification is generated
                     on persistency problems."
    ::= { svcTraps 24 }

svcTlsMrpAttrTblFullAlarmRaised NOTIFICATION-TYPE
    OBJECTS {
        custId,
        svcId,
        svcVpnId
    }
    STATUS          current
    DESCRIPTION     "The svcTlsMrpAttrTblFullAlarmRaised notification is
                     generated when the utilization of the MRP attribute table
                     is above the value specified by
                     svcTlsMrpAttrTblHighWatermark."
    ::= { svcTraps 25 }

svcTlsMrpAttrTblFullAlarmCleared NOTIFICATION-TYPE
    OBJECTS {
        custId,
        svcId,
        svcVpnId
    }
    STATUS          current
    DESCRIPTION     "The svcTlsMrpAttrTblFullAlarmCleared notification is
                     generated when the utilization of the MRP attribute table
                     is below the value specified by
                     svcTlsMrpAttrTblLowWatermark."
    ::= { svcTraps 26 }

-- V7v0 feature, not in V6v1 :
svcArpHostPopulateErr NOTIFICATION-TYPE
    OBJECTS {
        svcId,
        svcNotifSapPortId,
        svcNotifSapEncapValue,
        svcArpHostPopulateError
    }
    STATUS          current
    DESCRIPTION     "The svcArpHostPopulateErr notification indicates that
                     the system failed to update the ARP Host table
                     with the information contained in the ARP message."
    ::= { svcTraps 27 }

svcEpipePbbOperStatusChanged NOTIFICATION-TYPE
    OBJECTS {
        svcEpipePbbOperState
    }
    STATUS          current
    DESCRIPTION     "The svcEpipePbbOperStatusChanged notification is generated
                     when there is a change in the operating status of the
                     PBB tunnel associated with this E-pipe service."
    ::= { svcTraps 28 }

svcEPMCEPConfigMismatch NOTIFICATION-TYPE
   OBJECTS {
        svcEndPointMCEPId
   }
   STATUS       current
   DESCRIPTION  "The svcEPMCEPConfigMismatch notification is generated
                 when service multi-chassis endpoint detects a mismatch in the
                 config of the multi-chassis endpoint peer."
    ::= { svcTraps 29 }

svcEPMCEPConfigMismatchResolved NOTIFICATION-TYPE
   OBJECTS {
        svcEndPointMCEPId
   }
   STATUS       current
   DESCRIPTION  "The svcEPMCEPConfigMismatchResolved notification is generated
                 when multi-chassis endpoint resolves the mismatch in the config
                 of the multi-chassis endpoint peer."
    ::= { svcTraps 30 }

svcEPMCEPPassiveModeActive  NOTIFICATION-TYPE
    OBJECTS      { 
        svcEndPointMCEPId
    }
    STATUS       current
    DESCRIPTION
         "The svcEPMCEPPassiveModeActive notification is generated when 
         multi-chassis endpoint on a multi-chassis peer in passive-mode 
         (of multi-chassis peer) becomes passive-mode active by detecting more
         than one active spoke-sdp in the multi-chassis endpoint with
         'pwFwdingStandby' bit cleared per sdpBindPwPeerStatusBits object."
    ::= { svcTraps 31 }

svcEPMCEPPassiveModePassive  NOTIFICATION-TYPE
    OBJECTS      { 
        svcEndPointMCEPId
    }
    STATUS       current
    DESCRIPTION
         "The svcEPMCEPPassiveModePassive notification is generated when 
         multi-chassis endpoint on a multi-chassis peer in passive-mode 
         (of multi-chassis peer) becomes passive-mode passive by detecting at
         most one active spoke-sdp in the multi-chassis endpoint with
         'pwFwdingStandby' bit set per sdpBindPwPeerStatusBits object."
    ::= { svcTraps 32 }

svcRestoreHostProblem NOTIFICATION-TYPE
    OBJECTS {
        svcHostAddrType,
        svcHostAddr,
        tmnxFailureDescription
    }
    STATUS          current
    DESCRIPTION     "The svcRestoreHostProblem notification is
                     generated when an an error is detected while processing a
                     host persistency record.
                     
                     From release 9.0 of SROS onwards, the notification
                     TIMETRA-SYSTEM-MIB::persistenceRestoreProblem is used
                     instead."
    ::= { svcTraps 33 }

svcTlsSiteDesigFwdrChg NOTIFICATION-TYPE
    OBJECTS {
        svcTlsSiteIdDesignatedFwdr
    }
    STATUS          current
    DESCRIPTION     "The svcTlsSiteDesigFwdrChg notification is
                     generated when there is a change in the
                     'designated forwarder' status for the TLS site."
    ::= { svcTraps 34 }

svcTlsGroupOperStatusChanged NOTIFICATION-TYPE
   OBJECTS {
       svcTlsGroupOperStatus,
       svcTlsGroupLastError
   }
   STATUS          current
   DESCRIPTION     "The svcTlsGroupOperStatusChanged notification is generated
                    when there is a change in the value of
                    svcTlsGroupOperStatus object.

                    svcTlsGroupLastError provides information related
                    to svcTlsGroupOperStatus object."
   ::= { svcTraps 35 }

svcMacFdbTblFullAlarm NOTIFICATION-TYPE
    OBJECTS {
            svcMacFdbRecords
    }
    STATUS          current
    DESCRIPTION
        "[CAUSE] The svcMacFdbTblFullAlarm notification is raised when system
        limit of FDB records is reached.
                     
        Further traps are not generated as long as the value of
        svcMacFdbRecords object remains under 5 percent of the limit.

        [EFFECT] System will not be able to add new MAC addresses to the FDB
        table.
        
        [RECOVERY] Optimize the MAC FDB addresses assigned to different
        services."
   ::= { svcTraps 36 }

svcMacFdbTblFullAlarmCleared NOTIFICATION-TYPE
    OBJECTS {
            svcMacFdbRecords
    }
    STATUS          current
    DESCRIPTION
        "[CAUSE] The svcMacFdbTblFullAlarmCleared notification is raised
        when number of FDB records used reaches under 95 percent of the system
        limit after svcMacFdbTblFullAlarm notification had been raised.
        
        [EFFECT] System will now be able to add new MAC addresses to the FDB
        table.
        
        [RECOVERY] None."
   ::= { svcTraps 37 }

svcMSPwRtMisconfig NOTIFICATION-TYPE
    OBJECTS {
               svcMSPwPeSaiiGlobalId,
               svcMSPwPeSaiiPrefix,
               svcMSPwPeSaiiAcId,
               svcMSPwPeTaiiGlobalId,
               svcMSPwPeTaiiPrefix,
               svcMSPwPeTaiiAcId
    }
    STATUS          current
    DESCRIPTION
        "[CAUSE] The svcMSPwRtMisconfig notification is raised
        when there is mis-configuration discovered between two signalling
        multi-segment pseudo-wires. The following misconfiguration would cause
        this notification:

          - Both multi-segment pseudo-wires are configured to be master
        
        [EFFECT] Communication between the multi-segment pseudo-wires will fail.
        
        [RECOVERY] Mis-configuration between the two multi-segment pseudo-wire
        needs to be corrected."
   ::= { svcTraps 38 }

svcOperGrpOperStatusChanged NOTIFICATION-TYPE
   OBJECTS {
       svcOperGrpOperStatus
   }
   STATUS          current
   DESCRIPTION     
        "[CAUSE] The svcOperGrpOperStatusChanged notification is generated when
        there is a change in the value of svcOperGrpOperStatus.

        [EFFECT] Status of the one or more of the members of the operational 
        group has changed.

        [RECOVERY] Operational status of the members of the operational-group
        will need to be investigated."
   ::= { svcTraps 39 }

svcMSPwRetryExpiredNotif NOTIFICATION-TYPE
    OBJECTS {
        svcMSPwPeRetryExpired
    }
    STATUS          current
    DESCRIPTION
        "[CAUSE] The svcMSPwRetryExpiredNotif notification is raised
        when retry-timer expires for this multi-segment pseudo-wire
        provider-edge (svcMSPwPeId) in the service.
        
        [EFFECT] There will be no more retries to establish connection from this
        svcMSPwPeId.
        
        [RECOVERY] svcMSPwPeId may need to be shutdown and may need to restart
        the retries."
   ::= { svcTraps 40 }

svcVllSiteDesigFwdrChg NOTIFICATION-TYPE
    OBJECTS {
        svcVllSiteIdDesignatedFwdr
    }
    STATUS          current
    DESCRIPTION
        "[CAUSE] The svcVllSiteDesigFwdrChg notification is generated when
        there is a change in the 'designated forwarder' status for the site.

        [EFFECT] The new designated forwarder will be used to forward traffic.

        [RECOVERY] None needed."
    ::= { svcTraps 41 }

svcBgpEvpnDupMacAddrsDetected NOTIFICATION-TYPE
    OBJECTS {
        svcId
    }
    STATUS          current
    DESCRIPTION
        "[CAUSE] The svcBgpEvpnDupMacAddrsDetected notification is generated
         when at least one MAC address is detected as duplicate in a VPLS EVPN
         context.

         [EFFECT] At least one MAC address is detected as duplicate.

         [RECOVERY] None needed."
    ::= { svcTraps 42 }

svcBgpEvpnDupMacAddrsCleared NOTIFICATION-TYPE
    OBJECTS {
        svcId
    }
    STATUS          current
    DESCRIPTION
        "[CAUSE] The svcBgpEvpnDupMacAddrsCleared notification is generated
         when no more MAC addresses are detected as duplicate in a VPLS EVPN
         context.

         [EFFECT] No MAC addresses are detected as duplicate.

         [RECOVERY] None needed."
    ::= { svcTraps 43 }

svcTlsDupVTEPEgrVNIDetected NOTIFICATION-TYPE
    OBJECTS {
        svcVTEPEgrVNIVTEPAddrType,
        svcVTEPEgrVNIVTEPAddress,
        svcVTEPEgrVNIEgrVNI
    }
    STATUS          current
    DESCRIPTION
        "[CAUSE] The svcTlsDupVTEPEgrVNIDetected notification is generated
         when an attempt is made to use the same VTEP-Egress VNI in more
         than one service in the system.

         [EFFECT] A VTEP-Egress VNI is detected as duplicate.

         [RECOVERY] None needed."
    ::= { svcTraps 44 }

svcTlsDupVTEPEgrVNICleared NOTIFICATION-TYPE
    OBJECTS {
        svcVTEPEgrVNIVTEPAddrType,
        svcVTEPEgrVNIVTEPAddress,
        svcVTEPEgrVNIEgrVNI
    }
    STATUS          current
    DESCRIPTION
        "[CAUSE] The svcTlsDupVTEPEgrVNICleared notification is generated
         when a previously duplicate VTEP-Egress VNI is no longer used in more
         than one service in the system.

         [EFFECT] The VTEP-Egress VNI is no longer duplicate.

         [RECOVERY] None needed."
    ::= { svcTraps 45 }

svcTlsVTEPHiUsageAlarmRaised NOTIFICATION-TYPE
    STATUS          current
    DESCRIPTION
        "[CAUSE] The svcTlsVTEPHiUsageAlarmRaised notification is generated
         when the number of VTEPs in the system exceeds 95% of the system VTEP
         limit.

         [EFFECT] 95% of the system VTEP limit is reached.

         [RECOVERY] None needed."
    ::= { svcTraps 46 }

svcTlsVTEPHiUsageAlarmCleared NOTIFICATION-TYPE
    STATUS          current
    DESCRIPTION
        "[CAUSE] The svcTlsVTEPHiUsageAlarmCleared notification is generated
         when the number of VTEPs in the system drops below 90% of system VTEP
         limit.

         [EFFECT] 90% of the system VTEP limit is reached.

         [RECOVERY] None needed."
    ::= { svcTraps 47 }

svcTlsVTEPEgrVniSysHiUsgAlarmSet NOTIFICATION-TYPE
    STATUS          current
    DESCRIPTION
        "[CAUSE] The svcTlsVTEPEgrVniSysHiUsgAlarmSet notification is generated
         when the number of VTEP-Egress VNIs in the system exceeds 95% of the
         system VTEP-Egress VNI limit.

         [EFFECT] 95% of the system VTEP-Egress VNI limit is reached.

         [RECOVERY] None needed."
    ::= { svcTraps 48 }

svcTlsVTEPEgrVniSysHiUsgAlarmClr NOTIFICATION-TYPE
    STATUS          current
    DESCRIPTION
        "[CAUSE] The svcTlsVTEPEgrVniSysHiUsgAlarmClr notification is generated
         when the number of VTEP-Egress VNIs in the system drops below 90% of
         the system VTEP-Egress VNI limit.

         [EFFECT] 90% of the system VTEP-Egress VNI limit is reached.

         [RECOVERY] None needed."
    ::= { svcTraps 49 }

svcTlsVTEPEgrVniSvcHiUsgAlarmSet NOTIFICATION-TYPE
    OBJECTS {
        svcId
    }
    STATUS          current
    DESCRIPTION
        "[CAUSE] The svcTlsVTEPEgrVniSvcHiUsgAlarmSet notification is generated
         when the number of VTEP-Egress VNIs in a VPLS service exceeds 95% of
         the per-service VTEP-Egress VNI multicast limit.

         [EFFECT] The VPLS service has reached 95% of the VTEP-Egress VNI multicast limit.

         [RECOVERY] None needed."
    ::= { svcTraps 50 }

svcTlsVTEPEgrVniSvcHiUsgAlarmClr NOTIFICATION-TYPE
    OBJECTS {
        svcId
    }
    STATUS          current
    DESCRIPTION
        "[CAUSE] The svcTlsVTEPEgrVniSvcHiUsgAlarmClr notification is generated
         when the number of VTEP-Egress VNIs in a VPLS service drops below 90%
         of the per-service VTEP-Egress VNI multicast limit.

         [EFFECT] The VPLS service has reached 90% of the VTEP-Egress VNI multicast limit.

         [RECOVERY] None needed."
    ::= { svcTraps 51 }

svcBindSysHiUsageAlarmRaised NOTIFICATION-TYPE
    STATUS          current
    DESCRIPTION
        "[CAUSE] The svcBindSysHiUsageAlarmRaised notification is generated when
         the number of VXLAN binds exceeds 95% of the system VXLAN bind limit.

         [EFFECT] 95% of the system VXLAN bind limit is reached.

         [RECOVERY] None needed."
    ::= { svcTraps 52 }

svcBindSysHiUsageAlarmCleared NOTIFICATION-TYPE
    STATUS          current
    DESCRIPTION
        "[CAUSE] The svcBindSysHiUsageAlarmCleared notification is generated
         when the number of VXLAN binds drops below 90% of the system VXLAN bind
         limit.

         [EFFECT] 90% of the system VXLAN bind limit is reached.

         [RECOVERY] None needed."
    ::= { svcTraps 53 }

svcTlsRvplsEgrVniSysHiUsgAlrmSet NOTIFICATION-TYPE
    STATUS          current
    DESCRIPTION
        "[CAUSE] The svcTlsRvplsEgrVniSysHiUsgAlrmSet notification is generated
         when the number of RVPLS-Egress VNIs in the system exceeds 95% of the
         system RVPLS-Egress VNI limit.

         [EFFECT] 95% of the system RVPLS-Egress VNI limit is reached.

         [RECOVERY] None needed."
    ::= { svcTraps 54 }

svcTlsRvplsEgrVniSysHiUsgAlrmClr NOTIFICATION-TYPE
    STATUS          current
    DESCRIPTION
        "[CAUSE] The svcTlsRvplsEgrVniSysHiUsgAlrmClr notification is generated
         when the number of RVPLS-Egress VNIs in the system drops below 90% of
         the system RVPLS-Egress VNI limit.

         [EFFECT] 90% of the system RVPLS-Egress VNI limit is reached.

         [RECOVERY] None needed."
    ::= { svcTraps 55 }

svcTlsProxyArpDupDetect NOTIFICATION-TYPE
    OBJECTS {
        svcTlsProxyArpMacAddr,
        svcNotifTlsProxyMacAddr
    }
    STATUS          current
    DESCRIPTION
        "[CAUSE] The svcTlsProxyArpDupDetect notification is generated
         when duplicate detection criteria is met when a new mac address
         overwrites the existing mac address for the proxy arp entry.

         [EFFECT] A traffic disruption may occur if both sytems are active.

         [RECOVERY] Identify and correct configuration of one of the systems."
    ::= { svcTraps 56 }

svcTlsProxyArpDupClear NOTIFICATION-TYPE
    OBJECTS {
        svcTlsProxyArpMacAddr
    }
    STATUS          current
    DESCRIPTION
        "[CAUSE] The svcTlsProxyArpDupClear notification is generated
         when duplicate ARP entry is cleared.

         [EFFECT] The proxy ARP entry is deleted or is overwritten by static
         entry.

         [RECOVERY] None needed."
    ::= { svcTraps 57 }

svcTlsProxyNdDupDetect NOTIFICATION-TYPE
    OBJECTS {
        svcTlsProxyNdMacAddr,
        svcNotifTlsProxyMacAddr
    }
    STATUS          current
    DESCRIPTION
        "[CAUSE] The svcTlsProxyNdDupDetect notification is generated
         when duplicate detection criteria is met when a new mac address
         overwrites the existing mac address for the proxy ND entry.

         [EFFECT] A traffic disruption may occur if both sytems are active.

         [RECOVERY] Identify and correct configuration of one of the systems."
    ::= { svcTraps 58 }

svcTlsProxyNdDupClear NOTIFICATION-TYPE
    OBJECTS {
        svcTlsProxyNdMacAddr
    }
    STATUS          current
    DESCRIPTION
        "[CAUSE] The svcTlsProxyNdDupClear notification is generated
         when duplicate Neighbor Discovery (ND) entry is cleared.

         [EFFECT] The proxy ND entry is deleted or is overwritten by static
         entry.

         [RECOVERY] None needed."
    ::= { svcTraps 59 }

svcTlsEvpnTunnNHopHiUsgAlarmSet NOTIFICATION-TYPE
    OBJECTS {
        svcId
    }
    STATUS          current
    DESCRIPTION
        "[CAUSE] The svcTlsEvpnTunnNHopHiUsgAlarmSet notification is generated
         when the number of EVPN tunnels next-hops in the service exceeds 95%
         of the limit.

         [EFFECT] Reached 95% of EVPN tunnel interface IP next-hop limit for
         service.

         [RECOVERY] Verify the BGP-EVPN configuration to see if configuration
         changes are needed to reduce this."
    ::= { svcTraps 60 }

svcTlsEvpnTunnNHopHiUsgAlarmClr NOTIFICATION-TYPE
    OBJECTS {
        svcId
    }
    STATUS          current
    DESCRIPTION
        "[CAUSE] The svcTlsEvpnTunnNHopHiUsgAlarmClr notification is generated
         when the number of EVPN tunnels next-hop in the service drops to 90%
         of the limit.

         [EFFECT] Dropped below 90% of EVPN tunnel interface IP next-hop limit for
         service.

         [RECOVERY] None needed."
    ::= { svcTraps 61 }

svcEvpnMplsTEPHiUsageRaised NOTIFICATION-TYPE
    STATUS          current
    DESCRIPTION
        "[CAUSE] The svcEvpnMplsTEPHiUsageRaised notification is generated
         when the number of EVPN MPLS tunnel endpoints in the system exceeds
         95% of the system limit.

         [EFFECT] 95% of the system EVPN MPLS tunnel endpoint limit is reached.

         [RECOVERY] None needed."
    ::= { svcTraps 62 }

svcEvpnMplsTEPHiUsageCleared NOTIFICATION-TYPE
    STATUS          current
    DESCRIPTION
        "[CAUSE] The svcEvpnMplsTEPHiUsageCleared notification is generated
         when the number of EVPN MPLS tunnel endpoints in the system drops
         below 90% of system limit.

         [EFFECT] 90% of the system EVPN MPLS tunnel endpoint limit is reached.

         [RECOVERY] None needed."
    ::= { svcTraps 63 }

svcEvpnMplsTEPEgrBndSysHiUsgSet NOTIFICATION-TYPE
    STATUS          current
    DESCRIPTION
        "[CAUSE] The svcEvpnMplsTEPEgrBndSysHiUsgSet notification is
         generated when the number of EVPN MPLS tunnel endpoint-egress binds in
         the system exceeds 95% of the system limit.

         [EFFECT] 95% of the system EVPN MPLS tunnel endpoint-egress binds limit
         is reached.

         [RECOVERY] None needed."
    ::= { svcTraps 64 }

svcEvpnMplsTEPEgrBndSysHiUsgClr NOTIFICATION-TYPE
    STATUS          current
    DESCRIPTION
        "[CAUSE] The svcEvpnMplsTEPEgrBndSysHiUsgClr notification is
         generated when the number of EVPN MPLS tunnel endpoint-egress binds in
         the system drops below 90% of the system limit.

         [EFFECT] 90% of the system EVPN MPLS tunnel endpoint-egress binds limit
         is reached.

         [RECOVERY] None needed."
    ::= { svcTraps 65 }

svcEvpnMplsTEPEgrBndSvcHiUsgSet NOTIFICATION-TYPE
    OBJECTS {
        svcId
    }
    STATUS          current
    DESCRIPTION
        "[CAUSE] The svcEvpnMplsTEPEgrBndSvcHiUsgSet notification is
         generated when the number of EVPN MPLS tunnel endpoint-egress multicast
         binds in a VPLS service exceeds 95% of the per-service limit.

         [EFFECT] The VPLS service has reached 95% of the EVPN MPLS tunnel
         endpoint-egress multicast binds limit.

         [RECOVERY] None needed."
    ::= { svcTraps 66 }

svcEvpnMplsTEPEgrBndSvcHiUsgClr NOTIFICATION-TYPE
    OBJECTS {
        svcId
    }
    STATUS          current
    DESCRIPTION
        "[CAUSE] The svcEvpnMplsTEPEgrBndSvcHiUsgClr notification is
         generated when the number of EVPN MPLS tunnel endpoint-egress
         multicast binds in a VPLS service drops below 90% of the per-service
         limit.

         [EFFECT] The VPLS service has reached 90% of the EVPN MPLS tunnel
         endpoint-egress multicast binds limit.

         [RECOVERY] None needed."
    ::= { svcTraps 67 }

-- Proxy ARP entries usage
svcTlsProxyArpSysHiUsgSet NOTIFICATION-TYPE
    STATUS          current
    DESCRIPTION
        "[CAUSE] The svcTlsProxyArpSysHiUsgSet notification is
         generated when the number of proxy ARP entries in
         the system exceeds 95% of the system limit.

         [EFFECT] 95% of the system proxy ARP entries limit is reached.

         [RECOVERY] None needed."
    ::= { svcTraps 68 }

svcTlsProxyArpSysHiUsgClr NOTIFICATION-TYPE
    STATUS          current
    DESCRIPTION
        "[CAUSE] The svcTlsProxyArpSysHiUsgClr notification is
         generated when the number of proxy ARP entries in
         the system drops below 90% of the system limit.

         [EFFECT] 90% of the system proxy ARP entries limit is reached.

         [RECOVERY] None needed."
    ::= { svcTraps 69 }

svcTlsProxyArpSvcHiUsgSet NOTIFICATION-TYPE
    OBJECTS {
        svcId
    }
    STATUS          current
    DESCRIPTION
        "[CAUSE] The svcTlsProxyArpSvcHiUsgSet notification is
         generated when the number of proxy ARP entries 
         in a VPLS service exceeds 95% of the per-service limit.

         [EFFECT] The VPLS service has reached 95% of the proxy ARP limit.

         [RECOVERY] None needed."
    ::= { svcTraps 70 }

svcTlsProxyArpSvcHiUsgClr NOTIFICATION-TYPE
    OBJECTS {
        svcId
    }
    STATUS          current
    DESCRIPTION
        "[CAUSE] The svcTlsProxyArpSvcHiUsgClr notification is
         generated when the number of proxy ARP entries
         in a VPLS service drops below 90% of the per-service limit.

         [EFFECT] The VPLS service has reached 90% of the proxy ARP limit.

         [RECOVERY] None needed."
    ::= { svcTraps 71 }

-- Proxy ND entries usage
svcTlsProxyNdSysHiUsgSet NOTIFICATION-TYPE
    STATUS          current
    DESCRIPTION
        "[CAUSE] The svcTlsProxyNdSysHiUsgSet notification is generated when
         the number of proxy Neighbor Discovery (ND) entries in
         the system exceeds 95% of the system limit.

         [EFFECT] 95% of the system proxy Neighbor Discovery (ND) entries
         limit is reached.

         [RECOVERY] None needed."
    ::= { svcTraps 72 }

svcTlsProxyNdSysHiUsgClr NOTIFICATION-TYPE
    STATUS          current
    DESCRIPTION
        "[CAUSE] The svcTlsProxyNdSysHiUsgClr notification is
         generated when the number of proxy Neighbor Discovery (ND) entries
         in the system drops below 90% of the system limit.

         [EFFECT] 90% of the system proxy Neighbor Discovery (ND) entries
         limit is reached.

         [RECOVERY] None needed."
    ::= { svcTraps 73 }

svcTlsProxyNdSvcHiUsgSet NOTIFICATION-TYPE
    OBJECTS {
        svcId
    }
    STATUS          current
    DESCRIPTION
        "[CAUSE] The svcTlsProxyNdSvcHiUsgSet notification is
         generated when the number of proxy Neighbor Discovery (ND) entries 
         in a VPLS service exceeds 95% of the per-service limit.

         [EFFECT] The VPLS service has reached 95% of the proxy Neighbor
         Discovery (ND) limit.

         [RECOVERY] None needed."
    ::= { svcTraps 74 }

svcTlsProxyNdSvcHiUsgClr NOTIFICATION-TYPE
    OBJECTS {
        svcId
    }
    STATUS          current
    DESCRIPTION
        "[CAUSE] The svcTlsProxyNdSvcHiUsgClr notification is
         generated when the number of Neighbor Discovery (ND) entries
         in a VPLS service drops below 90% of the per-service limit.

         [EFFECT] The VPLS service has reached 90% of the proxy Neighbor
         Discovery (ND) limit.

         [RECOVERY] None needed."
    ::= { svcTraps 75 }

svcSiteMinDnTimerStateChg NOTIFICATION-TYPE
    OBJECTS {
        svcId,
        svcNotifSiteName,
        svcNotifSiteMinDnTimerState,
        svcNotifSiteMinDnTimer,
        svcNotifSiteMinDnTimerRemain
    }
    STATUS          current
    DESCRIPTION
        "[CAUSE] The svcSiteMinDnTimerStateChg notification is generated when
         site specific minimum-down-timer starts/canceled/extended/expires.

         [EFFECT] svcNotifSiteMinDnTimerState indicate the new state of the
         site minimum-down-timer.

         [RECOVERY] None needed."
    ::= { svcTraps 76 }

svcArpHostOverride NOTIFICATION-TYPE
    OBJECTS {
        svcArpHostMacAddr,
        svcNotifyMacAddress
    }
    STATUS          current
    DESCRIPTION
        "The system generates an svcArpHostOverride notification
         when it overrides the MAC address of an ARP host.
         
         The new MAC address is in svcArpHostMacAddr, while the old MAC address is in svcNotifyMacAddress.
                     
         [CAUSE] The system overrides the MAC address of an ARP host, because an ARP host with the same
         IP address as a known ARP host has appeared with a different MAC address.
         
         [EFFECT] The MAC address of the known ARP host has changed.
         
         [RECOVERY] No recovery required."
    ::= { svcTraps 77 }

svcEvpnDestSysHiUsgSet NOTIFICATION-TYPE
    STATUS          current
    DESCRIPTION
        "[CAUSE] The svcEvpnDestSysHiUsgSet notification is
         generated when the number of EVPN destinations(MPLS and VXLAN) in
         the system exceeds 95% of the system limit.

         [EFFECT] 95% of the system EVPN destinations(MPLS and VXLAN) limit
         is reached.

         [RECOVERY] None needed."
     ::= { svcTraps 78 }

svcEvpnDestSysHiUsgClr NOTIFICATION-TYPE
    STATUS          current
    DESCRIPTION
        "[CAUSE] The svcEvpnDestSysHiUsgClr notification is
         generated when the number of EVPN destinations(MPLS and VXLAN) in
         the system drops below 90% of the system limit.

         [EFFECT] The system EVPN destinations(MPLS and VXLAN) limit
         drops below 90%.

         [RECOVERY] None needed."
     ::= { svcTraps 79 }

svcEvpnMHEsEviDFStateChgd NOTIFICATION-TYPE
    OBJECTS {
        svcEvpnMHEthSegEviIsDF
    }
    STATUS          current
    DESCRIPTION
        "[CAUSE] The svcEvpnMHEsEviDFStateChgd notification is 
         generated when there is a change in the ethernet segment
         EVI designated forwarder state.

         [EFFECT] The forwarding state of the ethernet segment evi is changed.

         [RECOVERY] None needed."
    ::= { svcTraps 80 }
    
svcEvpnMHEsIsidDFStateChgd NOTIFICATION-TYPE
    OBJECTS {
        svcEvpnMHEthSegIsidIsDF
    }
    STATUS          current
    DESCRIPTION
        "[CAUSE] The svcEvpnMHEsIsidDFStateChgd notification is 
         generated when there is a change in the ethernet segment
         ISID designated forwarder state.

         [EFFECT] The forwarding state of the ethernet segment isid is changed.

         [RECOVERY] None needed."
    ::= { svcTraps 81 }

-- --------------------------------------------------
-- TLS STP trap notification objects
-- --------------------------------------------------
tmnxCustomerBridgeId OBJECT-TYPE
    SYNTAX         BridgeId
    MAX-ACCESS     accessible-for-notify
    STATUS         current
    DESCRIPTION    "tmnxCustomerBridgeId specifies the bridge identifier
                    of the customer's device "
    ::= { tmnxTstpNotifyObjs 1 }

tmnxCustomerRootBridgeId OBJECT-TYPE
    SYNTAX         BridgeId
    MAX-ACCESS     accessible-for-notify
    STATUS         current
    DESCRIPTION    "tmnxCustomerRootBridgeId specifies the bridge identifier
                    of the customer's designated root."
    ::= { tmnxTstpNotifyObjs 2 }

tmnxOtherBridgeId OBJECT-TYPE
    SYNTAX         BridgeId
    MAX-ACCESS     accessible-for-notify
    STATUS         current
    DESCRIPTION    "tmnxOtherBridgeId specifies the bridge identifier of
                    the device from which a BPDU was received."
    ::= { tmnxTstpNotifyObjs 3 }

tmnxOldSdpBindTlsStpPortState OBJECT-TYPE
    SYNTAX         TStpPortState
    MAX-ACCESS     accessible-for-notify
    STATUS         current
    DESCRIPTION    "tmnxOldSdpBindTlsStpPortState specifies the previous
                    state of an SDP binding."
    ::= { tmnxTstpNotifyObjs 4 }

tmnxVcpState OBJECT-TYPE
    SYNTAX         TStpPortState
    MAX-ACCESS     accessible-for-notify
    STATUS         current
    DESCRIPTION    "tmnxVcpState specifies the current state of a Virtual
                    Core Port (VCP)."
    ::= { tmnxTstpNotifyObjs 5 }

-- ------------------------------------
-- TLS STP traps
-- ------------------------------------
topologyChangeVcpState NOTIFICATION-TYPE
    OBJECTS {
        custId,
        svcId,
        tmnxVcpState
    }
    STATUS          current
    DESCRIPTION     "The topologyChangeVcpState   notification is generated
                     when a VCP has transitioned its state from disabled to
                     forwarding   or   from  forwarding  to  disabled.  The
                     spanning  tree  topology  has been modified and it may
                     denote  loss  of  customer access or redundancy. Check
                     the  new  topology against the provisioned topology to
                     determine severity of connectivity loss."
    ::= { tstpTraps 3 }

newRootVcpState NOTIFICATION-TYPE
    OBJECTS {
        custId,
        svcId
    }
    STATUS          current
    DESCRIPTION     "The newRootVcpState notification is generated when the
                     previous  root bridge has been aged out and a new root
                     bridge has been elected. The new root bridge creates a
                     new  spanning  tree topology and it may denote loss of
                     customer  access or redundancy. Check the new topology
                     against the provisioned topology to determine severity
                     of connectivity loss."
    ::= { tstpTraps 4 }

newRootBridge NOTIFICATION-TYPE
    OBJECTS {
        custId,
        svcId
    }
    STATUS          current
    DESCRIPTION     "The newRootBridge  notification is generated when this
                     bridge  has been elected as the new root bridge. A new
                     root  bridge  creates a new spanning tree topology and
                     may  denote  loss  of  customer  access or redundancy.
                     Check   the   new  topology  against  the  provisioned
                     topology to determine severity of connectivity loss."
    ::= { tstpTraps 7 }

vcpActiveProtocolChange NOTIFICATION-TYPE
    OBJECTS {
        custId,
        svcId,
        svcTlsStpVcpOperProtocol
    }
    STATUS          current
    DESCRIPTION     "The  vcpActiveProtocolChange notification is generated
                     when  the  spanning  tree protocol on this VCP changes
                     from  rstp  to  stp  or  vise  versa.  No  recovery is
                     needed."
    ::= { tstpTraps 32 }

tmnxNewCistRegionalRootBridge NOTIFICATION-TYPE
    OBJECTS {
        svcId,
        svcTlsStpCistRegionalRoot
    }
    STATUS          current
    DESCRIPTION     "The tmnxNewCistRegionalRootBridge notification is
                     generated when a new regional root bridge has been elected
                     for the Common and Internal Spanning Tree. A new regional
                     root bridge  creates a new spanning tree topology and may
                     denote  loss  of  customer  access or redundancy. Check
                     the   new  topology  against  the provisioned  topology
                     to determine severity of connectivity loss."
    ::= { tstpTraps 33 }

tmnxNewMstiRegionalRootBridge NOTIFICATION-TYPE
    OBJECTS {
        svcId,
        svcMstiInstanceId,
        tlsMstiRegionalRoot
    }
    STATUS          current
    DESCRIPTION     "The tmnxNewMstiRegionalRootBridge notification is
                     generated when a new regional root bridge has been elected
                     for the Multiple Spanning Tree Instance. A new regional
                     root bridge  creates a new spanning tree topology and may
                     denote  loss  of  customer  access or redundancy. Check
                     the   new  topology  against  the provisioned  topology
                     to determine severity of connectivity loss."
    ::= { tstpTraps 34 }

topologyChangePipMajorState NOTIFICATION-TYPE
    OBJECTS {
        custId,
        svcId
    }
    STATUS         current
    DESCRIPTION
        "The topologyChangePipMajorState notification is generated when
        a PIP Uplink has transitioned its state from learning to forwarding or
        from forwarding to blocking or broken. The spanning tree topology has
        been modified and it may denote loss of customer access or redundancy.
        Check the new topology against the provisioned topology to determine the
        severity of connectivity loss."
    ::= { tstpTraps 39 }

topologyChangePipState NOTIFICATION-TYPE
    OBJECTS {
        custId,
        svcId
    }
    STATUS          current
    DESCRIPTION
        "The topologyChangePipState notification is generated when a PIP Uplink
        has transitioned state to blocking or broken from a state other than
        forwarding. This event complements what is not covered by
        topologyChangePipMajorState. The spanning tree topology has been
        modified and it may denote loss of customer access or redundancy. Check
        the new topology against the provisioned topology to determine severity
        of connectivity loss."
    ::= { tstpTraps 40 }

tmnxPipStpExcepCondStateChng NOTIFICATION-TYPE
    OBJECTS {
        custId,
        svcId,
        tlsPipStpException
    }
    STATUS          current
    DESCRIPTION
        "The tmnxPipStpExcepCondStateChng notification is generated when the
        value of the object tlsPipStpException has changed, i.e. when the
        exception condition changes on the indicated PIP Uplink."
    ::= { tstpTraps 41 }

pipActiveProtocolChange NOTIFICATION-TYPE
    OBJECTS {
        custId,
        svcId
    }
    STATUS          current
    DESCRIPTION
        "The pipActiveProtocolChange notification is generated when the
        spanning tree protocol on this PIP Uplink changes from rstp to stp or
        vice-versa.  No recovery is needed."
    ::= { tstpTraps 42 }

-- ----------------------------------------------------------------------------
-- Conformance Information
-- ----------------------------------------------------------------------------
tmnxCustCompliances OBJECT IDENTIFIER ::= { tmnxCustConformance 1 }
tmnxCustGroups      OBJECT IDENTIFIER ::= { tmnxCustConformance 2 }

tmnxSvcCompliances  OBJECT IDENTIFIER ::= { tmnxSvcConformance 1 }
tmnxSvcGroups       OBJECT IDENTIFIER ::= { tmnxSvcConformance 2 }

tmnxTstpCompliances OBJECT IDENTIFIER ::= { tmnxTstpConformance 1 }
tmnxTstpGroups      OBJECT IDENTIFIER ::= { tmnxTstpConformance 2 }

-- ----------------------------------------------
-- Compliance Statements
-- ----------------------------------------------
tmnxCustCompliance MODULE-COMPLIANCE
    STATUS  obsolete
    DESCRIPTION
        "The compliance statement for management of services customers
         on Nokia SROS series systems."
    MODULE  -- this module
        MANDATORY-GROUPS
        {
            tmnxCustV6v0Group
        }
    ::= { tmnxCustCompliances 100 }

tmnxCustV8v0Compliance MODULE-COMPLIANCE
    STATUS  obsolete
    DESCRIPTION
        "The compliance statement for management of services customers
         on Nokia SROS series systems."
    MODULE  -- this module
        MANDATORY-GROUPS
        {
            tmnxCustV8v0Group
        }
    ::= { tmnxCustCompliances 101 }

tmnxCustV9v0Compliance MODULE-COMPLIANCE
    STATUS  obsolete
    DESCRIPTION
        "The compliance statement for management of services customers
         on Nokia SROS series systems."
    MODULE  -- this module
        MANDATORY-GROUPS
        {
            tmnxCustV8v0Group,
            tmnxCustV9v0Group
        }
    ::= { tmnxCustCompliances 102 }

tmnxCustV11v0Compliance MODULE-COMPLIANCE
    STATUS  obsolete
    DESCRIPTION
        "The compliance statement for management of services customers
         on Nokia SROS series systems."
    MODULE  -- this module
        MANDATORY-GROUPS
        {
            tmnxCustV9v0Group,
            tmnxCustV11v0Group
        }
    ::= { tmnxCustCompliances 103 }

tmnxSvc7450V6v0Compliance MODULE-COMPLIANCE
    STATUS  obsolete
    DESCRIPTION
        "The compliance statement for management of services
         on Nokia 7450 ESS series systems release R6.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group,
            -- tmnxApipeV3v0Group
            -- tmnxSvcRoutedCOV5v0Group
            tmnxSvcBsxV6v0Group
        }
    ::= { tmnxSvcCompliances 100 }

tmnxSvc7750V6v0Compliance MODULE-COMPLIANCE
    STATUS  obsolete
    DESCRIPTION
        "The compliance statement for management of services
         on Nokia 7750 SR series systems release R6.0."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group,
            tmnxSvcBsxV6v0Group
        }
    ::= { tmnxSvcCompliances 101 }

tmnxSvc7710V6v0Compliance MODULE-COMPLIANCE
    STATUS  obsolete
    DESCRIPTION
        "The compliance statement for management of services
         on Nokia 7710 SR series systems release R6.0."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v0Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group
            -- tmnxSvcBsxV6v0Group   no Application Assurance on 7710
        }
    ::= { tmnxSvcCompliances 102 }

tmnxSvc7450V6v1Compliance MODULE-COMPLIANCE
    STATUS  obsolete
    DESCRIPTION
        "The compliance statement for management of services
         on Nokia 7450 ESS series systems release R6.1."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV6v0Group,
            tmnxSvcObsoletedV6v0Group,
            tmnxSvcNotifyV6v0Group,
            -- tmnxApipeV3v0Group
            -- tmnxSvcRoutedCOV5v0Group
            tmnxSvcBsxV6v0Group
        }
    ::= { tmnxSvcCompliances 103 }

tmnxSvc7750V6v1Compliance MODULE-COMPLIANCE
    STATUS  obsolete
    DESCRIPTION
        "The compliance statement for management of services
         on Nokia 7750 SR series systems release R6.1."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group,
            tmnxSvcBsxV6v0Group
        }
    ::= { tmnxSvcCompliances 104 }

tmnxSvc7710V6v1Compliance MODULE-COMPLIANCE
    STATUS  obsolete
    DESCRIPTION
        "The compliance statement for management of services
         on Nokia 7710 SR series systems release R6.1."
    MODULE  -- this module
        MANDATORY-GROUPS
        {
            tmnxSvcV6v0Group,
            tmnxSvcTlsV6v0Group,
            tmnxSvcTlsFdbV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV6v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV6v0Group,
            tmnxSvcObsoletedV6v0Group,
            tmnxSvcNotifyV6v0Group,
            tmnxApipeV3v0Group,
            tmnxSvcRoutedCOV5v0Group,
            tmnxSvcDhcpBgpV7v0Group
            -- tmnxSvcBsxV6v0Group   no Application Assurance on 7710
        }
    ::= { tmnxSvcCompliances 105 }

tmnxSvc7450V7v0Compliance MODULE-COMPLIANCE
    STATUS  obsolete
    DESCRIPTION
        "The compliance statement for management of services
         on Nokia 7450 ESS series systems release R7.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV7v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV7v0Group,
            tmnxSvcObsoletedV6v0Group,
            tmnxSvcNotifyV7v0Group,
            -- tmnxApipeV3v0Group
            -- tmnxSvcRoutedCOV7v0Group
            tmnxSvcBsxV6v0Group,
            tmnxArpHostGroup,
            tmnxArpHostNotifyGroup,
            tmnxArpHostBgpGroup,
            svcIgmpTrkGroup,
            svcTlsMacV7v0Group,
            svcTlsEndPointV7v0Group,
            tmnxSvcIpipeV7v0Group,
            tmnxSvcMCEPNotifyGroup,
            tmnxSvcDhcpBgpV7v0Group,
            tmnxSvcV7v0Group,
            tmnxSvcTlsV7v0Group,
            tmnxSvcIesIfV7v0Group,
            tmnxSvcPbbMacV7v0Group
        }
    ::= { tmnxSvcCompliances 106 }

tmnxSvc7750V7v0Compliance MODULE-COMPLIANCE
    STATUS  obsolete
    DESCRIPTION
        "The compliance statement for management of services
         on Nokia 7750 SR series systems release R7.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV7v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV7v0Group,
            tmnxSvcObsoletedV6v0Group,
            tmnxSvcNotifyV7v0Group,
            tmnxApipeV3v0Group,
            tmnxSvcRoutedCOV7v0Group,
            tmnxSvcBsxV6v0Group,
            tmnxArpHostGroup,
            tmnxArpHostNotifyGroup,
            tmnxArpHostBgpGroup,
            svcIgmpTrkGroup,
            svcTlsMacV7v0Group,
            svcTlsEndPointV7v0Group,
            tmnxSvcIpipeV7v0Group,
            tmnxSvcMCEPNotifyGroup,
            tmnxSvcDhcpBgpV7v0Group,
            tmnxSvcV7v0Group,
            tmnxSvcTlsV7v0Group,
            tmnxSvcIesIfV7v0Group,
            tmnxSvcPbbMacV7v0Group
        }
    ::= { tmnxSvcCompliances 107 }

tmnxSvc7710V7v0Compliance MODULE-COMPLIANCE
    STATUS  obsolete
    DESCRIPTION
        "The compliance statement for management of services
         on Nokia 7710 SR series systems release R7.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV7v0Group,
            tmnxSvcEndPointV6v0Group,
            tmnxSvcPEV6v0Group,
            tmnxSvcIfDHCP6V6v0Group,
            tmnxSvcTlsBackbone6v1Group,
            tmnxSvcTlsBgpV6v0Group,
            tmnxSvcEpipeV6v0Group,
            tmnxSvcTlsPipV7v0Group,
            tmnxSvcObsoletedV6v0Group,
            tmnxSvcNotifyV7v0Group,
            tmnxApipeV3v0Group,
            tmnxSvcRoutedCOV7v0Group,
            -- tmnxSvcBsxV8v0Group   no Application Assurance on 7710
            tmnxArpHostGroup,
            tmnxArpHostNotifyGroup,
            tmnxArpHostBgpGroup,
            svcIgmpTrkGroup,
            svcTlsMacV7v0Group,
            svcTlsEndPointV7v0Group,
            tmnxSvcIpipeV7v0Group,
            tmnxSvcMCEPNotifyGroup,
            tmnxSvcV7v0Group,
            tmnxSvcTlsV7v0Group,
            tmnxSvcIesIfV7v0Group,
            tmnxSvcPbbMacV7v0Group
        }
    ::= { tmnxSvcCompliances 108 }

-- 8.0 Compliance 
tmnxSvc7450V8v0Compliance MODULE-COMPLIANCE
    STATUS obsolete 
    DESCRIPTION
        "The compliance statement for management of services
         on Nokia 7450 ESS series systems release R8.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            -- tmnxApipeV3v0Group
            -- tmnxSvcRoutedCOV8v0Group
            tmnxSvcBsxV8v0Group,
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcTlsPipV8v0Group,
            tmnxSvcMacReNotifyGroup
        }
    ::= { tmnxSvcCompliances 109 }

tmnxSvc7750V8v0Compliance MODULE-COMPLIANCE
    STATUS obsolete 
    DESCRIPTION
        "The compliance statement for management of services
         on Nokia 7750 SR series systems release R8.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            tmnxApipeV3v0Group,
            tmnxSvcRoutedCOV8v0Group,
            tmnxSvcBsxV8v0Group,
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcTlsPipV8v0Group,
            tmnxSvcMacReNotifyGroup
        }
    ::= { tmnxSvcCompliances 110 }

tmnxSvc7710V8v0Compliance MODULE-COMPLIANCE
    STATUS obsolete 
    DESCRIPTION
        "The compliance statement for management of services
         on Nokia 7710 SR series systems release R8.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            tmnxApipeV3v0Group,
            tmnxSvcRoutedCOV8v0Group,
            -- tmnxSvcBsxV8v0Group   no Application Assurance on 7710
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcTlsPipV8v0Group,
            tmnxSvcMacReNotifyGroup
        }
    ::= { tmnxSvcCompliances 111 }

-- 9.0 Compliance 
tmnxSvc7450V9v0Compliance MODULE-COMPLIANCE
    STATUS  obsolete
    DESCRIPTION
        "The compliance statement for management of services
         on Nokia 7450 ESS series systems release R9.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            -- tmnxApipeV3v0Group
            tmnxSvcRoutedCOV9v0Group,
            tmnxSvcBsxV8v0Group,
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcMacReNotifyGroup
        }
    ::= { tmnxSvcCompliances 112 }

tmnxSvc7750V9v0Compliance MODULE-COMPLIANCE
    STATUS  obsolete
    DESCRIPTION
        "The compliance statement for management of services
         on Nokia 7750 SR series systems release R9.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            tmnxApipeV3v0Group,
            tmnxSvcRoutedCOV9v0Group,
            tmnxSvcBsxV8v0Group,
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcApipeInfoV9v0Group,
            tmnxSvcMacReNotifyGroup
        }
    ::= { tmnxSvcCompliances 113 }

tmnxSvc7710V9v0Compliance MODULE-COMPLIANCE
    STATUS  obsolete
    DESCRIPTION
        "The compliance statement for management of services
         on Nokia 7710 SR series systems release R9.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            tmnxApipeV3v0Group,
            tmnxSvcRoutedCOV9v0Group,
            -- tmnxSvcBsxV8v0Group   no Application Assurance on 7710
            tmnxArpHostV8v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcMSPwPeV9v0Group,
            tmnxSvcV9v0Group,
            tmnxSvcNotifyV9v0Group,
            tmnxSvcEthCfmGroup,
            tmnxSvcV9v0R4Group,
            tmnxSvcApipeInfoV9v0Group,
            tmnxSvcMacReNotifyGroup
        }
    ::= { tmnxSvcCompliances 114 }

-- 10.0 Compliance 
tmnxSvc7450V10v0Compliance MODULE-COMPLIANCE
    STATUS  obsolete
    DESCRIPTION
        "The compliance statement for management of services
         on Nokia 7450 ESS series systems release R10.0."
    MODULE  -- this module
        MANDATORY-GROUPS
        {
            tmnxSvcV6v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcDhcpV10v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV7v0Group,
            -- tmnxApipeV3v0Group
            tmnxSvcRoutedCOV9v0Group,
            tmnxSvcRoutedCOV10v0Group,
            tmnxSvcBsxV8v0Group,
            tmnxArpHostV10v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group
        }
    ::= { tmnxSvcCompliances 115 }

tmnxSvc7750V10v0Compliance MODULE-COMPLIANCE
    STATUS  obsolete
    DESCRIPTION
        "The compliance statement for management of services
         on Nokia 7750 SR series systems release R10.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcDhcpV10v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            tmnxSvcBsxV8v0Group,
            tmnxArpHostV10v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group
        }
    ::= { tmnxSvcCompliances 116 }

tmnxSvc7710V10v0Compliance MODULE-COMPLIANCE
    STATUS  obsolete
    DESCRIPTION
        "The compliance statement for management of services
         on Nokia 7710 SR series systems release R10.0."
    MODULE  -- this module
        MANDATORY-GROUPS
        {
            tmnxSvcV6v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV8v0Group,
            tmnxSvcDhcpV9v0Group,
            tmnxSvcDhcpV10v0Group,
            tmnxSvcEndPointV6v0Group,
            tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            -- tmnxSvcBsxV8v0Group   no Application Assurance on 7710
            tmnxArpHostV10v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcMSPwPeV9v0Group,
            tmnxSvcV9v0Group,
            tmnxSvcNotifyV9v0Group,
            tmnxSvcEthCfmGroup,
            tmnxSvcV9v0R4Group,
            tmnxSvcApipeInfoV9v0Group,
            tmnxSvcMacReNotifyGroup,
            tmnxSvcSpbGroup,
            tmnxSvcVllBgpGroup,
            tmnxSvcV10v0Group,
            tmnxSvcIesIfNHV10v0Group,
            tmnxSvcP2mpGroup,
            tmnxSvcNotifyV10v0Group
        }
    ::= { tmnxSvcCompliances 117 }

-- 11.0 Compliance 
tmnxSvc7450V11v0Compliance MODULE-COMPLIANCE
    STATUS  obsolete
    DESCRIPTION
        "The compliance statement for management of services
         on Nokia 7450 ESS series systems release R11.0."
    MODULE  -- this module
        MANDATORY-GROUPS
        {
            tmnxSvcV13v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            -- tmnxApipeV3v0Group
            tmnxSvcRoutedCOV9v0Group,
            tmnxSvcRoutedCOV10v0Group,
            tmnxSvcBsxV8v0Group,
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcSpbV11v0Group,
            tmnxSvcMHGroup,
            tmnxSvcCondStaticMacGroup,
            tmnxSvcSchedulerRateV11v0Group
        }
    ::= { tmnxSvcCompliances 118 }

tmnxSvc7750V11v0Compliance MODULE-COMPLIANCE
    STATUS  obsolete
    DESCRIPTION
        "The compliance statement for management of services
         on Nokia 7750 SR series systems release R11.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            tmnxSvcBsxV8v0Group,
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcSpbV11v0Group,
            tmnxSvcMHGroup,
            tmnxSvcCondStaticMacGroup,
            tmnxSvcSchedulerRateV11v0Group
        }
    ::= { tmnxSvcCompliances 119 }

tmnxSvc7710V11v0Compliance MODULE-COMPLIANCE
    STATUS  obsolete
    DESCRIPTION
        "The compliance statement for management of services
         on Nokia 7710 SR series systems release R11.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            -- tmnxSvcBsxV8v0Group   no Application Assurance on 7710
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcMSPwPeV9v0Group,
            tmnxSvcV9v0Group,
            tmnxSvcNotifyV9v0Group,
            tmnxSvcEthCfmGroup,
            tmnxSvcV9v0R4Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcSpbV11v0Group,
            tmnxSvcMHGroup,
            tmnxSvcCondStaticMacGroup,
            tmnxSvcSchedulerRateV11v0Group            
        }
    ::= { tmnxSvcCompliances 120 }

-- 12.0 Compliance 
tmnxSvc7450V12v0Compliance MODULE-COMPLIANCE
    STATUS  obsolete
    DESCRIPTION
        "The compliance statement for management of services
         on Nokia 7450 ESS series systems release R12.0."
    MODULE  -- this module
        MANDATORY-GROUPS
        {
            tmnxSvcV13v0Group,
            tmnxSvcTlsV6v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            -- tmnxApipeV3v0Group
            tmnxSvcRoutedCOV9v0Group,
            tmnxSvcRoutedCOV10v0Group,
            tmnxSvcBsxV8v0Group,
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcPbbMacV12v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            svcVsdGroup,
            tmnxSvcQosV12v0Group,
            svcBgpEvpnNotifGroup,
            svcVxlanNotifGroup,
            svcBgpEvpnIPRouteGroup
        }
    ::= { tmnxSvcCompliances 121 }

tmnxSvc7750V12v0Compliance MODULE-COMPLIANCE
    STATUS  obsolete
    DESCRIPTION
        "The compliance statement for management of services
         on Nokia 7750 SR series systems release R12.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            tmnxSvcBsxV8v0Group,
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcPbbMacV12v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            tmnxSvcQosV12v0Group
        }
    ::= { tmnxSvcCompliances 122 }

tmnxSvc7710V12v0Compliance MODULE-COMPLIANCE
    STATUS  obsolete
    DESCRIPTION
        "The compliance statement for management of services
         on Nokia 7710 SR series systems release R12.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxSvcDhcpV11v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            -- tmnxSvcBsxV8v0Group   no Application Assurance on 7710
            tmnxArpHostV11v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcPbbMacV12v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcMSPwPeV9v0Group,
            tmnxSvcV9v0Group,
            tmnxSvcNotifyV9v0Group,
            tmnxSvcEthCfmGroup,
            tmnxSvcV9v0R4Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            tmnxSvcQosV12v0Group,
tmnxSvcTestGroup,
tmnxSvcTlsProxyArpGroup,
            tmnxSvcCreation12v0Group
        }
    ::= { tmnxSvcCompliances 123 }

-- 13.0 Compliance 
tmnxSvc7450V13v0Compliance MODULE-COMPLIANCE
    STATUS  current
    DESCRIPTION
        "The compliance statement for management of services
         on Nokia 7450 ESS series systems release R13.0."
    MODULE  -- this module
        MANDATORY-GROUPS
        {
            tmnxSvcV13v0Group,
            tmnxSvcTlsV6v0Group,
            tmnxSvcIesIfV6v0Group,
            tmnxSvcTlsShgV6v0Group,
            tmnxSvcTlsMFibV6v0Group,
            tmnxSvcTlsMFibV13v0Group,
            tmnxSvcRdntV6v0Group,
            tmnxSvcTlsMstiV6v0Group,
            tmnxSvcTlsEgrV6v0Group,
            tmnxCustV9v0Group,
            tmnxSvcDhcpV11v0Group,
            tmnxSvcDhcpV13v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            -- tmnxApipeV3v0Group
            tmnxSvcRoutedCOV9v0Group,
            tmnxSvcRoutedCOV10v0Group,
            tmnxSvcBsxV8v0Group,
            tmnxArpHostV11v0Group,
            tmnxArpHostV13v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcTlsV7v0Group,
            tmnxSvcIesIfV7v0Group,
            tmnxSvcPbbMacV7v0Group,
            tmnxSvcPbbMacV12v0Group,
            tmnxSvcV8v0Group,
            tmnxSvcMrpPolicyV8v0Group,
            tmnxSvcSiteV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group, 
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            svcVsdGroup,
            tmnxSvcQosV12v0Group,
            svcBgpEvpnNotifGroup,
            svcVxlanNotifGroup,
            svcBgpEvpnIPRouteGroup,
            tmnxSvcGrpIfGroup,
            tmnxSvcIesIfIpoeV13v0Group,
            tmnxSvcIpipeFaultPropGroup,
            tmnxSvcQosSchedV13v0Group,
            tmnxSvcTlsProxyArpGroup,
            tmnxSvcTlsProxyNdGroup,
            svcTlsProxyNdNotifGroup,
            svcTlsProxyArpNotifyObjsGroup,
            tmnxSvcTlsProxyArpEnhGroup,
            svcTlsProxyArpNotifGroup,
            tmnxSvcTlsEvpnProxyArpGroup,
            tmnxSvcVprnV13v0Group,
            tmnxSvcIesIfV13v0Group,
            svcBgpEvpnMplsGroup,
            svcBgpEvpnMplsMhGroup,
            svcAutoBindTunnelGroup,
            svcEvpnMplsNotifGroup,
            tmnxSvcQosRateV13v0Group,
            svcBgpMHSiteGroup,
            svcSiteMinDnTimerNotifyObjsGroup,
            svcSiteMinDnTimerNotifGroup,
            tmnxSvcShcvPolicyGroup,
            tmnxCustV13v0Group,
            svcArpHostNotifGroup,
            svcEvpnDestNotifGroup,
            svcEvpnMhEsDFNotifGroup
        }
    ::= { tmnxSvcCompliances 124 }

tmnxSvc7750V13v0Compliance MODULE-COMPLIANCE
    STATUS  current
    DESCRIPTION
        "The compliance statement for management of services
         on Nokia 7750 SR series systems release R13.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxCustV9v0Group,
            tmnxSvcDhcpV11v0Group,
            tmnxSvcDhcpV13v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            tmnxSvcRoutedCOV13v0Group,
            tmnxSvcBsxV8v0Group,
            tmnxArpHostV11v0Group,
            tmnxArpHostV13v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcDhcpBgpV7v0Group,
            tmnxSvcV7v0Group,
            tmnxSvcV8v0Group,
            tmnxSvcTlsV7v0Group,
            tmnxSvcIesIfV7v0Group,
            tmnxSvcPbbMacV7v0Group,
            tmnxSvcPbbMacV12v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcNotifyV9v0Group,
            tmnxSvcMSPwPeV9v0Group,
            tmnxSvcV9v0Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group,
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            tmnxSvcQosV12v0Group,
            tmnxSvcIesIfIpoeV13v0Group,
            tmnxSvcIpipeFaultPropGroup,
           tmnxSvcQosSchedV13v0Group,
            tmnxSvcTlsProxyArpGroup,
            tmnxSvcTlsProxyNdGroup,
            svcTlsProxyNdNotifGroup,
            svcTlsProxyArpNotifyObjsGroup,
            tmnxSvcTlsProxyArpEnhGroup,
            svcTlsProxyArpNotifGroup,
            tmnxSvcTlsEvpnProxyArpGroup,
            tmnxSvcVprnV13v0Group,
            svcBgpEvpnMplsGroup,
            svcBgpEvpnMplsMhGroup,
            svcAutoBindTunnelGroup,
            svcEvpnMplsNotifGroup,
            svcRipListenerGroup,
            tmnxSvcQosRateV13v0Group,
            tmnxSvcGrpIfGroup,
            svcBgpMHSiteGroup,
            svcSiteMinDnTimerNotifyObjsGroup,
            svcSiteMinDnTimerNotifGroup,
            tmnxCustV13v0Group,
            svcArpHostNotifGroup,
            svcEvpnDestNotifGroup,
            svcEvpnMhEsDFNotifGroup
        }
    ::= { tmnxSvcCompliances 125 }

tmnxSvc7710V13v0Compliance MODULE-COMPLIANCE
    STATUS  current
    DESCRIPTION
        "The compliance statement for management of services
         on Nokia 7710 SR series systems release R13.0."
    MODULE  -- this module
        MANDATORY-GROUPS
        {
            tmnxSvcV13v0Group,
            tmnxSvcTlsV6v0Group,
            tmnxSvcTlsFdbV7v0Group,
            tmnxSvcIesIfV6v0Group,
            tmnxSvcTlsShgV6v0Group,
            tmnxSvcTlsMFibV6v0Group,
            tmnxSvcRdntV6v0Group,
            tmnxSvcTlsMstiV6v0Group,
            tmnxSvcTlsEgrV6v0Group,
            tmnxCustV9v0Group,
            tmnxSvcDhcpV11v0Group,
            tmnxSvcDhcpV13v0Group,
            tmnxSvcEndPointV6v0Group,
            -- tmnxSvcPEV6v0Group,
            tmnxSvcIfDHCP6V6v0Group,
            tmnxSvcTlsBackbone6v1Group,
            tmnxSvcTlsBgpV8v0Group,
            tmnxSvcEpipeV6v0Group,
            tmnxSvcTlsPipV7v0Group,
            tmnxSvcObsoletedV6v0Group,
            tmnxSvcNotifyV11v0Group,
            tmnxApipeV3v0Group,
            tmnxSvcRoutedCOV9v0Group,
            tmnxSvcRoutedCOV10v0Group,
            -- tmnxSvcBsxV8v0Group   no Application Assurance on 7710
            tmnxArpHostV11v0Group,
            tmnxArpHostV13v0Group,
            tmnxArpHostNotifyGroup,
            tmnxArpHostBgpGroup,
            svcIgmpTrkGroup,
            svcTlsMacV7v0Group,
            svcTlsEndPointV7v0Group,
            tmnxSvcIpipeV8v0Group,
            tmnxSvcMCEPNotifyGroup,
            tmnxSvcV7v0Group,
            tmnxSvcV8v0Group,
            tmnxSvcTlsV7v0Group,
            tmnxSvcIesIfV7v0Group,
            tmnxSvcPbbMacV7v0Group,
            tmnxSvcPbbMacV12v0Group,
            tmnxSvcMrpPolicyV8v0Group,
            tmnxSvcSiteV8v0Group,
            tmnxSvcObsoletedV8v0Group,
            tmnxSvcRoutedVplsV8v0Group,
            tmnxSvcNotifyV8v0Group,
            tmnxSvcPwV8v0Group,
            tmnxSvcMvrpV8v0Group,
            tmnxSvcIesIfV8v0Group,
            tmnxSvcInterAsV8v0Group,
            tmnxSvcTlsPipV8v0Group,
            tmnxSvcOperGrpV9v0Group,
            tmnxSvcMSPwPeV9v0Group,
            tmnxSvcV9v0Group,
            tmnxSvcNotifyV9v0Group,
            tmnxSvcEthCfmGroup,
            tmnxSvcV9v0R4Group,
            tmnxSvcApipeInfoV9v0Group,
            tmnxSvcMacReNotifyGroup,
            tmnxSvcSpbGroup,
            tmnxSvcVllBgpGroup,
            tmnxSvcV10v0Group,
            tmnxSvcIesIfV10v0Group,
            tmnxSvcIesIfNHV10v0Group,
            tmnxSvcP2mpGroup,
            tmnxSvcNotifyV10v0Group,
            tmnxSvcPEObsoletedGroup,
            tmnxSvcNotifyObsoletedV11v0Group,
            svcBgpVpwsGroup,
            tmnxSvcIesIfV11v0Group, 
            tmnxSvcIesIfV12v0Group,
            tmnxSvcSpbV11v0Group,
            tmnxSvcCondStaticMacGroup,
            tmnxSvcSchedulerRateV11v0Group,
            svcTlsFdbMacStatsGroup,
            svcOperGrpBfdGroup,
            svcTlsEtreeGroup,
            svcVxlanGroup,
            svcBgpEvpnGroup,
            tmnxIesIfRtrSolicitGroup,
            tmnxSvcMHGroup,
            tmnxSvcV12v0Group,
            tmnxSvcQosV12v0Group,
tmnxSvcTestGroup,
            tmnxSvcCreation12v0Group,
            tmnxSvcIesIfIpoeV13v0Group,
            tmnxSvcIpipeFaultPropGroup,
           tmnxSvcQosSchedV13v0Group,
            tmnxSvcTlsProxyArpGroup,
            tmnxSvcTlsProxyNdGroup,
            svcTlsProxyNdNotifGroup,
            svcTlsProxyArpNotifyObjsGroup,
            tmnxSvcTlsProxyArpEnhGroup,
            svcTlsProxyArpNotifGroup,
            tmnxSvcTlsEvpnProxyArpGroup,
            tmnxSvcVprnV13v0Group,
            svcBgpEvpnMplsGroup,
            svcBgpEvpnMplsMhGroup,
            svcAutoBindTunnelGroup,
            svcEvpnMplsNotifGroup,
            svcSpiLoadBalGroup,
            svcTeidLoadBalGroup,
            svcRipListenerGroup,
            tmnxSvcQosRateV13v0Group,
            tmnxSvcGrpIfGroup,
            svcBgpMHSiteGroup,
            svcSiteMinDnTimerNotifyObjsGroup,
            svcSiteMinDnTimerNotifGroup,
            tmnxCustV13v0Group,
            svcArpHostNotifGroup,
            svcEvpnDestNotifGroup,
            svcEvpnMhEsDFNotifGroup
        }
    ::= { tmnxSvcCompliances 126 }
    
-- ----------------------------------------------
-- customer OBJECT-GROUPs
-- ----------------------------------------------
tmnxCustV6v0Group OBJECT-GROUP
    OBJECTS {
      custNumEntries,
      custNextFreeId,
      custId,
      custRowStatus,
      custDescription,
      custContact,
      custPhone,
      custLastMgmtChange,
      custMultSvcSiteName,
      custMultSvcSiteRowStatus,
      custMultSvcSiteDescription,
      custMultSvcSiteScope,
      custMultSvcSiteAssignment,
      custMultSvcSiteIngressSchedulerPolicy,
      custMultSvcSiteEgressSchedulerPolicy,
      custMultSvcSiteLastMgmtChange,
      custMultSvcSiteTodSuite,
      custMultSvcSiteCurrentIngrSchedPlcy,
      custMultSvcSiteCurrentEgrSchedPlcy,
      custMultSvcSiteEgressAggRateLimit,
      custMultSvcSiteIntendedIngrSchedPlcy,
      custMultSvcSiteIntendedEgrSchedPlcy,
      custMultSvcSiteFrameBasedAccnt,
      custIngQosSchedStatsForwardedPackets,
      custIngQosSchedStatsForwardedOctets,
      custEgrQosSchedStatsForwardedPackets,
      custEgrQosSchedStatsForwardedOctets,
      custIngQosPortSchedFwdPkts,
      custIngQosPortSchedFwdOctets,
      custEgrQosPortSchedFwdPkts,
      custEgrQosPortSchedFwdOctets,
      custMssIngQosSRowStatus,
      custMssIngQosSLastMgmtChange,
      custMssIngQosSOverrideFlags,
      custMssIngQosSPIR,
      custMssIngQosSCIR,
      custMssIngQosSSummedCIR,
      custMssEgrQosSRowStatus,
      custMssEgrQosSLastMgmtChange,
      custMssEgrQosSOverrideFlags,
      custMssEgrQosSPIR,
      custMssEgrQosSCIR,
      custMssEgrQosSSummedCIR,
      custIngSchedPlcyStatsFwdPkt,
      custIngSchedPlcyStatsFwdOct,
      custEgrSchedPlcyStatsFwdPkt,
      custEgrSchedPlcyStatsFwdOct,
      custIngSchedPlcyPortStatsFwdPkt,
      custIngSchedPlcyPortStatsFwdOct,
      custEgrSchedPlcyPortStatsFwdPkt,
      custEgrSchedPlcyPortStatsFwdOct,
      custMultSvcSiteFrameBasedAccnt
    }
    STATUS      obsolete
    DESCRIPTION
        "The group of objects supporting management of Services customers
         general capabilities on Nokia SROS series systems."
    ::= { tmnxCustGroups 100 }

tmnxCustV8v0Group OBJECT-GROUP
    OBJECTS {
      custNumEntries,
      custNextFreeId,
      custId,
      custRowStatus,
      custDescription,
      custContact,
      custPhone,
      custLastMgmtChange,
      custMultSvcSiteName,
      custMultSvcSiteRowStatus,
      custMultSvcSiteDescription,
      custMultSvcSiteScope,
      custMultSvcSiteAssignment,
      custMultSvcSiteIngressSchedulerPolicy,
      custMultSvcSiteEgressSchedulerPolicy,
      custMultSvcSiteLastMgmtChange,
      custMultSvcSiteTodSuite,
      custMultSvcSiteCurrentIngrSchedPlcy,
      custMultSvcSiteCurrentEgrSchedPlcy,
      custMultSvcSiteEgressAggRateLimit,
      custMultSvcSiteIntendedIngrSchedPlcy,
      custMultSvcSiteIntendedEgrSchedPlcy,
      custMultSvcSiteFrameBasedAccnt,
      custIngQosSchedStatsForwardedPackets,
      custIngQosSchedStatsForwardedOctets,
      custEgrQosSchedStatsForwardedPackets,
      custEgrQosSchedStatsForwardedOctets,
      custIngQosPortSchedFwdPkts,
      custIngQosPortSchedFwdOctets,
      custEgrQosPortSchedFwdPkts,
      custEgrQosPortSchedFwdOctets,
      custMssIngQosSRowStatus,
      custMssIngQosSLastMgmtChange,
      custMssIngQosSOverrideFlags,
      custMssIngQosSPIR,
      custMssIngQosSCIR,
      custMssIngQosSSummedCIR,
      custMssEgrQosSRowStatus,
      custMssEgrQosSLastMgmtChange,
      custMssEgrQosSOverrideFlags,
      custMssEgrQosSPIR,
      custMssEgrQosSCIR,
      custMssEgrQosSSummedCIR,
      custIngSchedPlcyStatsFwdPkt,
      custIngSchedPlcyStatsFwdOct,
      custEgrSchedPlcyStatsFwdPkt,
      custEgrSchedPlcyStatsFwdOct,
      custIngSchedPlcyPortStatsFwdPkt,
      custIngSchedPlcyPortStatsFwdOct,
      custEgrSchedPlcyPortStatsFwdPkt,
      custEgrSchedPlcyPortStatsFwdOct,
      custMultSvcSiteFrameBasedAccnt,
      custMultSvcSiteSubscriberMss
    }
    STATUS      obsolete
    DESCRIPTION
        "The group of objects supporting management of Services customers
         general capabilities on Nokia SROS series systems."
    ::= { tmnxCustGroups 102 }

tmnxCustV9v0Group OBJECT-GROUP
    OBJECTS {
      custMultSvcSiteIngPolcrCtrlPolcy,
      custMultSvcSiteEgrPolcrCtrlPolcy
      }
    STATUS      current
    DESCRIPTION
        "The group of objects supporting management of Services customers
         general capabilities on Nokia SROS series systems."
    ::= { tmnxCustGroups 103 }

-- ----------------------------------------------
-- service OBJECT-GROUPs
-- ----------------------------------------------
tmnxSvcV6v0Group OBJECT-GROUP
    OBJECTS {
      svcNumEntries,
      svcId,
      svcRowStatus,
      svcType,
      svcCustId,
      svcIpRouting,
      svcDescription,
      svcMtu,
      svcAdminStatus,
      svcOperStatus,
      svcNumSaps,
      svcNumSdps,
      svcLastMgmtChange,
      svcDefMeshVcId,
      svcVpnId,
      svcVRouterId,
      svcAutoBind,
      svcLastStatusChange,
      svcVllType,
      svcMgmtVpls,
      svcRadiusDiscovery,
      svcRadiusUserName,
      svcRadiusUserNameType,
      svcVcSwitching,
      svcRadiusPEDiscPolicy,
      svcRadiusDiscoveryShutdown,
      svcVplsType,
      svcTotalFdbMimDestIdxEntries
    }
    STATUS      obsolete
    DESCRIPTION
        "The group of objects supporting management of Services 
         general capabilities on Nokia SROS series systems."
    ::= { tmnxSvcGroups 101 }

tmnxSvcTlsV6v0Group OBJECT-GROUP
    OBJECTS {
      svcTlsMacLearning,
      svcTlsDiscardUnknownDest,
      svcTlsFdbTableSize,
      svcTlsFdbNumEntries,
      svcTlsFdbNumStaticEntries,
      svcTlsFdbLocalAgeTime,
      svcTlsFdbRemoteAgeTime,
      svcTlsStpAdminStatus,
      svcTlsStpPriority,
      svcTlsStpBridgeAddress,
      svcTlsStpTimeSinceTopologyChange,
      svcTlsStpTopologyChanges,
      svcTlsStpDesignatedRoot,
      svcTlsStpRootCost,
      svcTlsStpRootPort,
      svcTlsStpMaxAge,
      svcTlsStpHelloTime,
      svcTlsStpForwardDelay,
      svcTlsStpBridgeMaxAge,
      svcTlsStpBridgeHelloTime,
      svcTlsStpBridgeForwardDelay,
      svcTlsStpOperStatus,
      svcTlsStpVirtualRootBridgeStatus,
      svcTlsMacAgeing,
      svcTlsStpTopologyChangeActive,
      svcTlsFdbTableFullHighWatermark,
      svcTlsFdbTableFullLowWatermark,
      svcTlsVpnId,
      svcTlsCustId,
      svcTlsStpVersion,
      svcTlsStpHoldCount,
      svcTlsStpPrimaryBridge,
      svcTlsStpBridgeInstanceId,
      svcTlsStpVcpOperProtocol,
      svcTlsMacMoveMaxRate,
      svcTlsMacMoveRetryTimeout,
      svcTlsMacMoveAdminStatus,
      svcTlsMacRelearnOnly,
      svcTlsMfibTableSize,
      svcTlsMfibTableFullHighWatermark,
      svcTlsMfibTableFullLowWatermark,
      svcTlsMacFlushOnFail,
      svcTlsStpRegionName,
      svcTlsStpRegionRevision,
      svcTlsStpBridgeMaxHops,
      svcTlsStpCistRegionalRoot,
      svcTlsStpCistIntRootCost,
      svcTlsStpCistRemainingHopCount,
      svcTlsStpCistRegionalRootPort,
      svcTlsFdbNumLearnedEntries,
      svcTlsFdbNumOamEntries,
      svcTlsFdbNumDhcpEntries,
      svcTlsFdbNumHostEntries,
      svcTlsShcvAction,
      svcTlsShcvSrcIp,
      svcTlsShcvSrcMac,
      svcTlsShcvInterval,
      svcTlsPriPortsCumulativeFactor,
      svcTlsSecPortsCumulativeFactor,
      svcTlsL2ptTermEnabled,
      svcTlsPropagateMacFlush,
      svcTlsMrpAdminStatus,
      svcTlsMrpMaxAttributes,
      svcTlsMrpAttributeCount,
      svcTlsMrpFailedRegisterCount,
      svcTlsMrpFloodTime,
      svcTlsMrpAttrTblHighWatermark,
      svcTlsMrpAttrTblLowWatermark,
      svcTlsMcPathMgmtPlcyName,
      tlsEgrMcGrpAdminQinqFixedTagVal
    }
    STATUS      current
    DESCRIPTION
        "The group of objects supporting management of Services TLS
         general capabilities on Nokia SROS series systems."
    ::= { tmnxSvcGroups 102 }

tmnxSvcTlsFdbV6v0Group OBJECT-GROUP
    OBJECTS {
      tlsFdbMacAddr,
      tlsFdbRowStatus,
      tlsFdbType,
      tlsFdbLocale,
      tlsFdbPortId,
      tlsFdbEncapValue,
      tlsFdbSdpId,
      tlsFdbVcId,
      tlsFdbVpnId,
      tlsFdbCustId,
      tlsFdbLastStateChange,
      tlsFdbProtected,
      tlsFdbBackboneDstMac,
      tlsFdbNumIVplsMac,
      tlsFdbEndPointName,
      tlsFdbEPMacOperSdpId,
      tlsFdbEPMacOperVcId,
      tlsFdbPbbNumEpipes,
      tlsProtMacRowStatus,
      tlsProtMacLastMgmtChange
    }
    STATUS      obsolete
    DESCRIPTION
        "The group of objects supporting management of Services TLS FDB
         capabilities on Nokia SROS series systems."
    ::= { tmnxSvcGroups 103 }

tmnxSvcIesIfV6v0Group OBJECT-GROUP
    OBJECTS {
      iesIfIndex,
      iesIfRowStatus,
      iesIfName,
      iesIfDescription,
      iesIfAdminStatus,
      iesIfOperStatus,
      iesIfLastMgmtChange,
      iesIfVpnId,
      iesIfCustId,
      iesIfLoopback,
      iesIfLastStatusChange,
      iesIfType,
      iesIfShcvSource,
      iesIfShcvAction,
      iesIfShcvInterval,
      iesGrpIfOperUpWhileEmpty
    }
    STATUS      current
    DESCRIPTION
        "The group of objects supporting management of Services IES
         interface capabilities on Nokia SROS series systems."
    ::= { tmnxSvcGroups 104 }

tmnxSvcTlsShgV6v0Group OBJECT-GROUP
    OBJECTS {
      tlsShgRowStatus,
      tlsShgCustId,
      tlsShgInstanceId,
      tlsShgDescription,
      tlsShgLastMgmtChange,
      tlsShgResidential,
      tlsShgRestProtSrcMac,
      tlsShgRestUnprotDstMac,
      tlsShgCreationOrigin,
      tlsShgRestProtSrcMacAction
    }
    STATUS      current
    DESCRIPTION
        "The group of objects supporting management of Services TLS
         Split Hoirizon Group capabilities on Nokia SROS series systems."
    ::= { tmnxSvcGroups 105 }

tmnxSvcTlsMFibV6v0Group OBJECT-GROUP
    OBJECTS {
      tlsMFibFwdOrBlk,
      tlsMFibSvcId,
      tlsMFibStatsForwardedPkts,
      tlsMFibStatsForwardedOctets
    }
    STATUS      current
    DESCRIPTION
        "The group of objects supporting management of Services TLS MFib
         capabilities on Nokia SROS series systems."
    ::= { tmnxSvcGroups 106 }

tmnxSvcRdntV6v0Group OBJECT-GROUP
    OBJECTS {
      tlsRdntGrpRowStatus,
      tlsRdntGrpDescription,
      tlsRdntGrpLastMgmtChange,
      tlsRdntGrpMemberRowStatus,
      tlsRdntGrpMemberLastMgmtChange
    }
    STATUS      current
    DESCRIPTION
        "The group of objects supporting management of Services Redundancy
         group capabilities on Nokia SROS series systems."
    ::= { tmnxSvcGroups 107 }

tmnxSvcTlsMstiV6v0Group OBJECT-GROUP
    OBJECTS {
      tlsMstiRowStatus,
      tlsMstiPriority,
      tlsMstiLastMgmtChange,
      tlsMstiRegionalRoot,
      tlsMstiIntRootCost,
      tlsMstiRemainingHopCount,
      tlsMstiRegionalRootPort,
      tlsMstiMvplsRowStatus
    }
    STATUS      current
    DESCRIPTION
        "The group of objects supporting management of Services TLS MSTI
         capabilities on Nokia SROS series systems."
    ::= { tmnxSvcGroups 108 }

tmnxSvcTlsEgrV6v0Group OBJECT-GROUP
    OBJECTS {
      tlsEgrMcGrpRowStatus,
      tlsEgrMcGrpLastMgmtChange,
      tlsEgrMcGrpDescription,
      tlsEgrMcGrpChainLimit,
      tlsEgrMcGrpEncapType,
      tlsEgrMcGrpDot1qEtherType,
      tlsEgrMcGrpQinqEtherType,
      tlsEgrMcGrpMacFilterId,
      tlsEgrMcGrpIpFilterId,
      tlsEgrMcGrpIpv6FilterId,
      tlsEgrMcGrpQinqFixedTagPosition,
      tlsEgrMcGrpOperQinqFixedTagVal
    }
    STATUS      current
    DESCRIPTION
        "The group of objects supporting management of Services TLS Egress
         capabilities on Nokia SROS series systems."
    ::= { tmnxSvcGroups 109 }
      
tmnxSvcDhcpV6v0Group OBJECT-GROUP
    OBJECTS {
      svcDhcpLseStateLocale,
      svcDhcpLseStatePortId,
      svcDhcpLseStateEncapValue,
      svcDhcpLseStateSdpId,
      svcDhcpLseStateVcId,
      svcDhcpLseStateChAddr,
      svcDhcpLseStateRemainLseTime,
      svcDhcpLseStateOption82,
      svcDhcpLseStatePersistKey,
      svcDhcpLseStateSubscrIdent,
      svcDhcpLseStateSubProfString,
      svcDhcpLseStateSlaProfString,
      svcDhcpLseStateShcvOperState,
      svcDhcpLseStateShcvChecks,
      svcDhcpLseStateShcvReplies,
      svcDhcpLseStateShcvReplyTime,
      svcDhcpLseStateClientId,
      svcDhcpLseStateIAID,
      svcDhcpLseStateIAIDType,
      svcDhcpLseStateCiAddrMaskLen,
      svcDhcpLseStateRetailerSvcId,
      svcDhcpLseStateRetailerIf,
      svcDhcpLseStateAncpString,
      svcDhcpLseStateFramedIpNetMaskTp,
      svcDhcpLseStateFramedIpNetMask,
      svcDhcpLseStateBCastIpAddrType,
      svcDhcpLseStateBCastIpAddr,
      svcDhcpLseStateDefaultRouterTp,
      svcDhcpLseStateDefaultRouter,
      svcDhcpLseStatePrimaryDnsType,
      svcDhcpLseStatePrimaryDns,
      svcDhcpLseStateSecondaryDnsType,
      svcDhcpLseStateSecondaryDns,
      svcDhcpLseStateSessionTimeout,
      svcDhcpLseStateServerLeaseStart,
      svcDhcpLseStateServerLastRenew,
      svcDhcpLseStateServerLeaseEnd,
      svcDhcpLseStateDhcpServerAddrType,
      svcDhcpLseStateDhcpServerAddr,
      svcDhcpLseStateOriginSubscrId,
      svcDhcpLseStateOriginStrings,
      svcDhcpLseStateOriginLeaseInfo,
      svcDhcpLseStateDhcpClientAddrType,
      svcDhcpLseStateDhcpClientAddr,
      svcDhcpLseStateLeaseSplitActive,
      svcDhcpLseStateInterDestId,
      svcDhcpLseStatePrimaryNbnsType,
      svcDhcpLseStatePrimaryNbns,
      svcDhcpLseStateSecondaryNbnsType,
      svcDhcpLseStateSecondaryNbns,
      svcDhcpLseStateNextHopMacAddr,
      svcDhcpLseStateModifySubIndent,
      svcDhcpLseStateModifySubProfile,
      svcDhcpLseStateModifySlaProfile,
      svcDhcpLseStateEvaluateState,
      svcDhcpLseStateModInterDestId,
      svcDhcpLseStateModifyAncpString,
      svcDhcpLseStateForceRenew,
      svcDhcpManagedRouteStatus
    }
    STATUS      obsolete
    DESCRIPTION
        "The group of objects supporting management of Services DHCP Lease
         capabilities on Nokia SROS series systems."
    ::= { tmnxSvcGroups 110 }

tmnxSvcEndPointV6v0Group OBJECT-GROUP
    OBJECTS {
      svcEndPointRowStatus,
      svcEndPointDescription,
      svcEndPointTxActiveType,
      svcEndPointTxActivePortId,
      svcEndPointTxActiveEncap,
      svcEndPointTxActiveSdpId,
      svcEndPointForceSwitchOver,
      svcEndPointForceSwitchOverSdpId,
      svcEndPointActiveHoldDelay,
      svcEndPointIgnoreStandbySig,
      svcEndPointMacPinning,
      svcEndPointMacLimit,
      svcEndPointSuppressStandbySig,
      svcEndPointTxActiveChangeCount,
      svcEndPointTxActiveLastChange,
      svcEndPointTxActiveUpTime,
      svcEndPointRevertTime,
      svcEndPointRevertTimeCountDn
    }
    STATUS      current
    DESCRIPTION
        "The group of objects supporting management of Services endpoint
         capabilities on Nokia SROS series systems."
    ::= { tmnxSvcGroups 111 }

tmnxSvcPEV6v0Group OBJECT-GROUP
    OBJECTS {
      svcPEDiscoveryPolicyRowStatus,
      svcPEDiscoveryPolicyPassword,
      svcPEDiscoveryPolicyInterval,
      svcPEDiscoveryPolicyTimeout,
      svcPEDiscPolServerRowStatus,
      svcPEDiscPolServerAddressType,
      svcPEDiscPolServerAddress,
      svcPEDiscPolServerSecret,
      svcPEDiscPolServerOperStatus,
      svcPEDiscPolServerPort
    }
    STATUS      obsolete
    DESCRIPTION
        "The group of objects supporting management of Services PE Discovery
         capabilities on Nokia SROS series systems."
    ::= { tmnxSvcGroups 112 }

tmnxSvcIfDHCP6V6v0Group OBJECT-GROUP
    OBJECTS {
      svcIfDHCP6MsgStatsLstClrd,
      svcIfDHCP6MsgStatsRcvd,
      svcIfDHCP6MsgStatsSent,
      svcIfDHCP6MsgStatsDropped
    }
    STATUS      current
    DESCRIPTION
        "The group of objects supporting management of Services interface DHCP
         capabilities on Nokia SROS series systems."
    ::= { tmnxSvcGroups 114 }

tmnxSvcTlsBackbone6v0Group OBJECT-GROUP
    OBJECTS {
      svcTlsBackboneSrcMac,
      svcTlsBackboneVplsSvcId,
      svcTlsBackboneVplsSvcISID,
      svcTlsBackboneOperSrcMac,
      svcTlsBackboneOperVplsSvcISID,
      svcTlsBackboneLDPMacFlush,
      svcTlsBackboneVplsStp
    }
    STATUS      obsolete
    DESCRIPTION
        "The group of objects supporting management of Services PBB
         capabilities on Nokia SROS series systems."
    ::= { tmnxSvcGroups 115 }

tmnxSvcTlsBgpV6v0Group OBJECT-GROUP
    OBJECTS {
      svcTlsBgpADTableLastChanged,
      svcTlsBgpADRowStatus,
      svcTlsBgpADLastChanged,
      svcTlsBgpADVplsId,
      svcTlsBgpADVsiPrefix,
      svcTlsBgpADVsiRD,
      svcTlsBgpADExportRteTarget,
      svcTlsBgpADVsiExportPolicy1,
      svcTlsBgpADVsiExportPolicy2,
      svcTlsBgpADVsiExportPolicy3,
      svcTlsBgpADVsiExportPolicy4,
      svcTlsBgpADVsiExportPolicy5,
      svcTlsBgpADImportRteTarget,
      svcTlsBgpADVsiImportPolicy1,
      svcTlsBgpADVsiImportPolicy2,
      svcTlsBgpADVsiImportPolicy3,
      svcTlsBgpADVsiImportPolicy4,
      svcTlsBgpADVsiImportPolicy5,
      svcTlsBgpADAdminStatus
    }
    STATUS      obsolete
    DESCRIPTION
        "The group of objects supporting management of Services BGP AD
         capabilities on Nokia SROS series systems."
    ::= { tmnxSvcGroups 116 }
      
tmnxSvcEpipeV6v0Group OBJECT-GROUP
    OBJECTS {
      svcEpipePbbTableLastChanged,
      svcEpipePbbRowStatus,
      svcEpipePbbLastChngd,
      svcEpipePbbBvplsSvcId,
      svcEpipePbbBvplsDstMac,
      svcEpipePbbSvcISID,
      svcEpipePbbOperState,
      svcEpipePbbFlooding,
      svcEpipePbbLastStatusChange
    }
    STATUS      current
    DESCRIPTION
        "The group of objects supporting management of Services PBB Epipe
         capabilities on Nokia SROS series systems."
    ::= { tmnxSvcGroups 117 }

tmnxSvcTlsPipV6v0Group OBJECT-GROUP
    OBJECTS {
      tlsPipStpPortState,
      tlsPipStpPortRole,
      tlsPipStpDesignatedBridge,
      tlsPipStpDesignatedPort,
      tlsPipStpException,
      tlsPipStpForwardTransitions,
      tlsPipStpInConfigBpdus,
      tlsPipStpInTcnBpdus,
      tlsPipStpInRstBpdus,
      tlsPipStpInMstBpdus,
      tlsPipStpInBadBpdus,
      tlsPipStpOutConfigBpdus,
      tlsPipStpOutTcnBpdus,
      tlsPipStpOutRstBpdus,
      tlsPipStpOutMstBpdus,
      tlsPipStpOperStatus,
      tlsPipStpMvplsPruneState,
      tlsPipStpOperProtocol,
      tlsPipStpPortNum,
      tlsPipMstiPortRole,
      tlsPipMstiPortState,
      tlsPipMstiDesignatedBridge,
      tlsPipMstiDesignatedPort
    }
    STATUS      obsolete
    DESCRIPTION
        "The group of objects supporting management of Services TLS PIP
         capabilities on Nokia SROS series systems."
    ::= { tmnxSvcGroups 118 }

-- This groups is not in 7450
tmnxApipeV3v0Group OBJECT-GROUP
    OBJECTS {
        svcApipeInterworking
    }
    STATUS      current
    DESCRIPTION
        "The  group  of  objects supporting management of APIPE services on
         Nokia SROS series systems release 3.0."
    ::= { tmnxSvcGroups 119 }

-- This groups is not in 7450
tmnxSvcRoutedCOV5v0Group OBJECT-GROUP
    OBJECTS {
        iesIfParentIf,
        iesIfFwdServId,
        iesIfFwdSubIf,
        iesGrpIfRedInterface,
        svcWholesalerNumStaticHosts,
        svcWholesalerNumDynamicHosts
    }
    STATUS      obsolete
    DESCRIPTION
        "The group of objects supporting routed CO Nokia SROS systems."
    ::= { tmnxSvcGroups 120 }

tmnxArpHostGroup OBJECT-GROUP
    OBJECTS {
        svcArpHostTableLastChanged,
        svcArpHostLocale,
        svcArpHostSapPortId,
        svcArpHostSapEncapValue,
        svcArpHostSdpId,
        svcArpHostVcId,
        svcArpHostSessionTimeout,
        svcArpHostStart,
        svcArpHostLastAuth,
        svcArpHostRefresh,
        svcArpHostRemainingTime,
        svcArpHostShcvOperState,
        svcArpHostShcvChecks,
        svcArpHostShcvReplies,
        svcArpHostShcvReplyTime,
        svcArpHostSubscrIdent,
        svcArpHostSubProfString,
        svcArpHostSlaProfString,
        svcArpHostAppProfString,
        svcArpHostAncpString,
        svcArpHostInterDestId,
        svcArpHostRetailerSvcId,
        svcArpHostRetailerIf,
        svcArpHostMacAddr,
        svcArpHostPersistKey,
        svcArpHostCategoryMapName,
        svcArpHostRadiusClassAttr,
        svcArpHostRadiusUserName,
        svcArpHostIfTableLastMgmtChange,
        svcArpHostIfLastMgmtChange,
        svcArpHostIfAdminState,
        svcArpHostIfMaxNumHosts,
        svcArpHostIfMaxNumHostsSap,
        svcArpHostIfMinAuthInterval,
        svcArpHostIfNumHosts,
        svcArpHostDefaultSessionTimeout,
        svcArpHostMRtStatus
    }
    STATUS      obsolete
    DESCRIPTION
        "The group of objects supporting management of Services ARP hosts
         capabilities on Nokia SROS series systems."
    ::= { tmnxSvcGroups 130 }

-- This group is not in 7710
tmnxSvcBsxV6v0Group OBJECT-GROUP
    OBJECTS {
      svcDhcpLseStateAppProfString,
      svcDhcpLseStateModifyAppProfile
    }
    STATUS      obsolete
    DESCRIPTION
        "The group of objects supporting management of BSX (Application
         Assurance) capabilities on Nokia SROS series systems."
    ::= { tmnxSvcGroups 121 }

tmnxSvcTlsBackbone6v1Group OBJECT-GROUP
    OBJECTS {
      svcTlsBackboneSrcMac,
      svcTlsBackboneVplsSvcId,
      svcTlsBackboneVplsSvcISID,
      svcTlsBackboneOperSrcMac,
      svcTlsBackboneOperVplsSvcISID,
      svcTlsBackboneLDPMacFlush,
      svcTlsBackboneLDPMacFlushNotMine,
      svcTlsBackboneVplsStp
    }
    STATUS      current
    DESCRIPTION
        "The group of objects supporting management of Services PBB
         capabilities on Nokia SROS series systems."
    ::= { tmnxSvcGroups 122 }

svcIgmpTrkGroup OBJECT-GROUP
    OBJECTS {
        svcIgmpTrkTableLastMgmtChange,
        svcIgmpTrkLastMgmtChange,
        svcIgmpTrkAdminState,
        svcIgmpTrkExpiryTime
    }
    STATUS      current
    DESCRIPTION
        "The group of objects supporting management of Services IGMP host
         tracking capabilities on Nokia SROS series systems."
    ::= { tmnxSvcGroups 131 }

svcTlsMacV7v0Group OBJECT-GROUP
    OBJECTS {
       svcTlsMacMoveNumRetries,
       svcTlsMacSubNetLen,
       svcTlsSendFlushOnBVplsFail,
       svcTlsPropMacFlushFromBVpls
    }
    STATUS      current
    DESCRIPTION
        "The group of objects supporting management of Services mac-related
         capabilities on Nokia SROS series systems in 7.0 release."
    ::= { tmnxSvcGroups 132 }

-- This group is not in 7450
tmnxSvcRoutedCOV7v0Group OBJECT-GROUP
    OBJECTS {
        iesIfParentIf,
        iesIfFwdServId,
        iesIfFwdSubIf,
        iesGrpIfRedInterface,
        svcWholesalerNumStaticHosts,
        svcWholesalerNumDynamicHosts,
        iesIfPrivateRetailSubnets,
        svcWholesalerNumDhcpLeaseStates,
        svcWholesalerNumPppoeSessions,
        svcWholesalerNumArpHosts
    }
    STATUS      obsolete
    DESCRIPTION
        "The group of objects supporting routed CO Nokia SROS systems."
    ::= { tmnxSvcGroups 133 }

svcTlsEndPointV7v0Group OBJECT-GROUP
    OBJECTS {
       svcEndPointMCEPId,  
       svcEndPointMCEPPeerAddr,  
       svcEndPointMCEPPeerAddrType,  
       svcEndPointMCEPPeerName,
       svcEndPointMCEPPsvModeActive,
       svcEndPointBlockOnMeshFail,
       svcEpMcEpStatsPktsRxConfig,  
       svcEpMcEpStatsPktsRxState,  
       svcEpMcEpStatsPktsTxConfig,  
       svcEpMcEpStatsPktsTxFailed,  
       svcEpMcEpStatsPktsTxState
    }
    STATUS      current
    DESCRIPTION
        "The group of objects supporting management of Services End-point
         capabilities on Nokia SROS series systems in 7.0 release."
    ::= { tmnxSvcGroups 134 }

tmnxSvcIpipeV7v0Group OBJECT-GROUP
    OBJECTS {
      svcIpipeInfoLastMgmtChange,
      svcIpipeCeAddressDiscovery,
      svcIpipeInfoTableLastMgmtChange
    }
    STATUS      obsolete
    DESCRIPTION
        "The group of objects supporting management of IPIPE Service
         on Nokia SROS series systems."
    ::= { tmnxSvcGroups 135 }

tmnxSvcDhcpBgpV7v0Group OBJECT-GROUP
    OBJECTS {
      svcDhcpLseStateBgpPrngPlcyName,
      svcDhcpLseStateBgpAuthKeyChain,
      svcDhcpLseStateBgpMD5AuthKey,
      svcDhcpLseStateBgpImportPolicy,
      svcDhcpLseStateBgpExportPolicy,
      svcDhcpLseStateBgpPeerAS,
      svcDhcpLseStateBgpPeeringStatus     
    }
    STATUS      current
    DESCRIPTION
        "The group of objects containing the BGP-parameters set by DHCP."
    ::= { tmnxSvcGroups 136 }

tmnxSvcTlsPipV7v0Group OBJECT-GROUP
    OBJECTS {
      tlsPipStpPortState,
      tlsPipStpPortRole,
      tlsPipStpDesignatedBridge,
      tlsPipStpDesignatedPort,
      tlsPipStpException,
      tlsPipStpForwardTransitions,
      tlsPipStpInConfigBpdus,
      tlsPipStpInTcnBpdus,
      tlsPipStpInRstBpdus,
      tlsPipStpInMstBpdus,
      tlsPipStpInBadBpdus,
      tlsPipStpOutConfigBpdus,
      tlsPipStpOutTcnBpdus,
      tlsPipStpOutRstBpdus,
      tlsPipStpOutMstBpdus,
      tlsPipStpOperStatus,
      tlsPipStpMvplsPruneState,
      tlsPipStpOperProtocol,
      tlsPipStpPortNum,
      tlsPipMstiPortRole,
      tlsPipMstiPortState,
      tlsPipMstiDesignatedBridge,
      tlsPipMstiDesignatedPort,
      tlsPipStpInsideRegion
    }
    STATUS      current
    DESCRIPTION
        "The group of objects supporting management of Services TLS PIP
         capabilities on Nokia SROS series systems."
    ::= { tmnxSvcGroups 137 }

tmnxArpHostBgpGroup OBJECT-GROUP
    OBJECTS {
        svcArpHostBgpPrngPlcyName,
        svcArpHostBgpAuthKeyChain,
        svcArpHostBgpMD5AuthKey,
        svcArpHostBgpImportPolicy,
        svcArpHostBgpExportPolicy,
        svcArpHostBgpPeerAS,
        svcArpHostBgpPeeringStatus
    }
    STATUS      current
    DESCRIPTION
        "The group of objects supporting management of Services ARP hosts'
         BGP capabilities on Nokia SROS series systems."
    ::= { tmnxSvcGroups 138 }

tmnxSvcDhcpV7v0Group OBJECT-GROUP
    OBJECTS {
      svcDhcpLseStateLocale,
      svcDhcpLseStatePortId,
      svcDhcpLseStateEncapValue,
      svcDhcpLseStateSdpId,
      svcDhcpLseStateVcId,
      svcDhcpLseStateChAddr,
      svcDhcpLseStateRemainLseTime,
      svcDhcpLseStateOption82,
      svcDhcpLseStatePersistKey,
      svcDhcpLseStateSubscrIdent,
      svcDhcpLseStateSubProfString,
      svcDhcpLseStateSlaProfString,
      svcDhcpLseStateShcvOperState,
      svcDhcpLseStateShcvChecks,
      svcDhcpLseStateShcvReplies,
      svcDhcpLseStateShcvReplyTime,
      svcDhcpLseStateClientId,
      svcDhcpLseStateIAID,
      svcDhcpLseStateIAIDType,
      svcDhcpLseStateCiAddrMaskLen,
      svcDhcpLseStateRetailerSvcId,
      svcDhcpLseStateRetailerIf,
      svcDhcpLseStateAncpString,
      svcDhcpLseStateFramedIpNetMaskTp,
      svcDhcpLseStateFramedIpNetMask,
      svcDhcpLseStateBCastIpAddrType,
      svcDhcpLseStateBCastIpAddr,
      svcDhcpLseStateDefaultRouterTp,
      svcDhcpLseStateDefaultRouter,
      svcDhcpLseStatePrimaryDnsType,
      svcDhcpLseStatePrimaryDns,
      svcDhcpLseStateSecondaryDnsType,
      svcDhcpLseStateSecondaryDns,
      svcDhcpLseStateSessionTimeout,
      svcDhcpLseStateServerLeaseStart,
      svcDhcpLseStateServerLastRenew,
      svcDhcpLseStateServerLeaseEnd,
      svcDhcpLseStateDhcpServerAddrType,
      svcDhcpLseStateDhcpServerAddr,
      svcDhcpLseStateOriginSubscrId,
      svcDhcpLseStateOriginStrings,
      svcDhcpLseStateOriginLeaseInfo,
      svcDhcpLseStateDhcpClientAddrType,
      svcDhcpLseStateDhcpClientAddr,
      svcDhcpLseStateLeaseSplitActive,
      svcDhcpLseStateInterDestId,
      svcDhcpLseStatePrimaryNbnsType,
      svcDhcpLseStatePrimaryNbns,
      svcDhcpLseStateSecondaryNbnsType,
      svcDhcpLseStateSecondaryNbns,
      svcDhcpLseStateNextHopMacAddr,
      svcDhcpLseStateCategoryMapName,
      svcDhcpLseStateNakNextRenew,
      svcDhcpLseStateRadiusClassAttr,
      svcDhcpLseStateRadiusUserName,
      svcDhcpLseStateModifySubIndent,
      svcDhcpLseStateModifySubProfile,
      svcDhcpLseStateModifySlaProfile,
      svcDhcpLseStateEvaluateState,
      svcDhcpLseStateModInterDestId,
      svcDhcpLseStateModifyAncpString,
      svcDhcpLseStateForceRenew,
      svcDhcpManagedRouteStatus
    }
    STATUS      obsolete
    DESCRIPTION
        "The group of objects supporting management of Services DHCP Lease
         capabilities on Nokia SROS series systems."
    ::= { tmnxSvcGroups 139 }

tmnxSvcPbbMacV7v0Group OBJECT-GROUP
    OBJECTS {
     svcEpipePbbBvplsDstMacName,
     svcEpipePbbBvplsOperDstMac,
     svcMacNameAddr,  
     svcMacNameLastChngd,
     svcMacNameRowStatus,
     svcMacNameTableLastChanged,
     svcPbbSrcBVplsMacAddr,
     svcMacNotifCount,  
     svcMacNotifInterval,  
     svcTlsMacNotifAdminState,  
     svcTlsMacNotifCount,  
     svcTlsMacNotifInterval,
     svcTlsBackboneUseSapBMac,
     svcTlsPbbIgmpSnpgMRtrRowStatus,
     svcTlsPbbIgmpSnpgMRtrLastCh,
     svcTlsBackboneUseEsBMac
    }
    STATUS      current
    DESCRIPTION
        "The group of objects supporting management of Services PBB MAC
         capabilities on Nokia SROS series systems."
    ::= { tmnxSvcGroups 140 }

tmnxSvcTlsFdbV7v0Group OBJECT-GROUP
    OBJECTS {
      tlsFdbMacAddr,
      tlsFdbRowStatus,
      tlsFdbType,
      tlsFdbLocale,
      tlsFdbPortId,
      tlsFdbEncapValue,
      tlsFdbSdpId,
      tlsFdbVcId,
      tlsFdbVpnId,
      tlsFdbCustId,
      tlsFdbLastStateChange,
      tlsFdbProtected,
      tlsFdbBackboneDstMac,
      tlsFdbNumIVplsMac,
      tlsFdbEndPointName,
      tlsFdbEPMacOperSdpId,
      tlsFdbEPMacOperVcId,
      tlsFdbPbbNumEpipes,
      tlsProtMacRowStatus,
      tlsProtMacLastMgmtChange,
      tlsProtMacImplCount
    }
    STATUS      current
    DESCRIPTION
        "The group of objects supporting management of Services TLS FDB
         capabilities on Nokia SROS series systems."
    ::= { tmnxSvcGroups 141 }

tmnxSvcV7v0Group OBJECT-GROUP
    OBJECTS {
      svcNumMcStandbySaps
    }
    STATUS      current
    DESCRIPTION
        "The group of objects supporting management of Services
         capabilities on Nokia SROS series systems added in release 7.0."
    ::= { tmnxSvcGroups 142 }

tmnxSvcTlsV7v0Group OBJECT-GROUP
    OBJECTS {
      svcTlsShcvRetryTimeout,
      svcTlsShcvRetryCount
    }
    STATUS      current
    DESCRIPTION
        "The group of objects supporting management of Services TLS
         general capabilities on Nokia SROS series systems
         added in release 7.0."
    ::= { tmnxSvcGroups 152 }

tmnxSvcIesIfV7v0Group OBJECT-GROUP
    OBJECTS {
      iesIfShcvRetryTimeout,
      iesIfShcvRetryCount
    }
    STATUS      current
    DESCRIPTION
        "The group of objects supporting management of Services IES
         interface capabilities on Nokia SROS series systems
         added in release 7.0."
    ::= { tmnxSvcGroups 153 }

tmnxSvcV8v0Group OBJECT-GROUP
    OBJECTS {
      svcName,
      svcNameId,
      svcNameRowStatus,
      svcNameLastChanged,
      svcNameTableLastChanged,
      svcNameType,
      svcEndPointStandbySigMaster,
      svcTlsPerSvcHashing,
      svcEpipePerSvcHashing,
      svcTlsBackboneForceQTagFwd,
      svcEpipeBackboneForceQTagFwd,
      svcEpipeBackboneLastChngd,  
      svcEpipeBackboneTableLastChanged,  
      svcEpipeLastChngd,  
      svcEpipeTableLastChanged, 
      svcHashLabel
    }
    STATUS     current 
    DESCRIPTION
        "The group of objects supporting management of Services
         capabilities on Nokia SROS series systems for release 8.0."
    ::= { tmnxSvcGroups 143 }

tmnxSvcMrpPolicyV8v0Group OBJECT-GROUP
    OBJECTS {
      svcMrpPlcyTableLastChgd,
      svcMrpPlcyParamsTblLastChgd,
      svcMrpPlcyParamsISIDTblLastChgd,
      svcMrpPolicyRowStatus,
      svcMrpPolicyLastChanged,
      svcMrpPolicyDescription,
      svcMrpPolicyScope,
      svcMrpPolicyDefaultAction,
      svcMrpPolicyParamsRowStatus,
      svcMrpPolicyParamsLastChanged,
      svcMrpPolicyParamsDescription,
      svcMrpPolicyParamsAction,
      svcMrpPolicyParamsISIDHigh,
      svcMrpPolicyParamsISIDRowStatus,
      svcMrpPolicyParamsISIDLastChgd
    }
    STATUS      current
    DESCRIPTION
        "The group of objects supporting mrp-policies on Nokia
         SROS series systems."
    ::= { tmnxSvcGroups 144 }    

tmnxSvcSiteV8v0Group OBJECT-GROUP
    OBJECTS {
     svcTlsSiteIdAdminStatus,  
     svcTlsSiteIdEncapValue,  
     svcTlsSiteIdLastChanged,  
     svcTlsSiteIdPortId,  
     svcTlsSiteIdRowStatus,  
     svcTlsSiteIdSdpBindId,  
     svcTlsSiteIdShgMeshSdp,  
     svcTlsSiteIdShgName,  
     svcTlsSiteIdSiteId,  
     svcTlsSiteIdFailedThresh,
     svcTlsSiteIdOperStatus,
     svcTlsSiteIdDesignatedFwdr,
     svcTlsSiteIdDfUpTime,
     svcTlsSiteIdDfChgCnt,
     svcTlsSiteIdTblLastChanged,
     svcBgpVplsVeId,  
     svcBgpVplsVeName,  
     svcBgpVplsMaxVeId,
     svcBgpVplsAdminStatus,
     svcBgpVplsLastChanged,
     svcBgpVplsRowStatus,
     svcBgpVplsTblLastChanged,
     svcTlsBgpExportRteTarget,  
     svcTlsBgpImportRteTarget,  
     svcTlsBgpLastChanged,  
     svcTlsBgpTableLastChanged,  
     svcTlsBgpVsiExportPolicy1,  
     svcTlsBgpVsiExportPolicy2,  
     svcTlsBgpVsiExportPolicy3,  
     svcTlsBgpVsiExportPolicy4,  
     svcTlsBgpVsiExportPolicy5,  
     svcTlsBgpVsiImportPolicy1,  
     svcTlsBgpVsiImportPolicy2,  
     svcTlsBgpVsiImportPolicy3,  
     svcTlsBgpVsiImportPolicy4,  
     svcTlsBgpVsiImportPolicy5,  
     svcTlsBgpVsiRD,
     tlsShgSiteName,
     svcTlsSiteIdBootTimer,
     svcTlsSiteIdSiteActTimer,
     svcTlsSiteIdTimerRemain
    }
    STATUS      current
    DESCRIPTION
        "The group of objects supporting sites on Nokia SROS
         series systems."
    ::= { tmnxSvcGroups 145 }    

-- This group is not in 7450
tmnxSvcRoutedCOV8v0Group OBJECT-GROUP
    OBJECTS {
        iesIfParentIf,
        iesIfFwdServId,
        iesIfFwdSubIf,
        iesGrpIfRedInterface,
        svcWholesalerNumStaticHosts,
        svcWholesalerNumDynamicHosts,
        iesIfPrivateRetailSubnets,
        svcWholesalerNumDhcpLeaseStates,
        svcWholesalerNumPppoeSessions,
        svcWholesalerNumArpHosts,
        iesIfDelegatedPrefixLen,
        iesIfLns,
        iesIfDefaultPrimaryDnsIPv4Addr,  
        iesIfDefaultSecondaryDnsIPv4Addr,
        iesIfDefaultPrimaryDnsIPv6Addr,  
        iesIfDefaultSecondaryDnsIPv6Addr,
        iesIfIPv6ConfigAllowed
    }
    STATUS      obsolete
    DESCRIPTION
        "The group of objects supporting routed CO Nokia SROS systems."
    ::= { tmnxSvcGroups 146 }
    
tmnxArpHostV8v0Group OBJECT-GROUP
    OBJECTS {
        svcArpHostTableLastChanged,
        svcArpHostLocale,
        svcArpHostSapPortId,
        svcArpHostSapEncapValue,
        svcArpHostSdpId,
        svcArpHostVcId,
        svcArpHostSessionTimeout,
        svcArpHostStart,
        svcArpHostLastAuth,
        svcArpHostRefresh,
        svcArpHostRemainingTime,
        svcArpHostShcvOperState,
        svcArpHostShcvChecks,
        svcArpHostShcvReplies,
        svcArpHostShcvReplyTime,
        svcArpHostSubscrIdent,
        svcArpHostSubProfString,
        svcArpHostSlaProfString,
        svcArpHostAppProfString,
        svcArpHostAncpString,
        svcArpHostInterDestId,
        svcArpHostRetailerSvcId,
        svcArpHostRetailerIf,
        svcArpHostMacAddr,
        svcArpHostPersistKey,
        svcArpHostCategoryMapName,
        svcArpHostRadiusClassAttr,
        svcArpHostRadiusUserName,
        svcArpHostOriginSubscrId,
        svcArpHostOriginStrings,
        svcArpHostIfTableLastMgmtChange,
        svcArpHostIfLastMgmtChange,
        svcArpHostIfAdminState,
        svcArpHostIfMaxNumHosts,
        svcArpHostIfMaxNumHostsSap,
        svcArpHostIfMinAuthInterval,
        svcArpHostIfNumHosts,
        svcArpHostDefaultSessionTimeout,
        svcArpHostMRtStatus
    }
    STATUS      obsolete
    DESCRIPTION
        "The group of objects supporting management of Services ARP hosts
         capabilities on Nokia SROS series systems in release 8.0."
    ::= { tmnxSvcGroups 147 }

tmnxSvcTlsBgpV8v0Group OBJECT-GROUP
    OBJECTS {
      svcTlsBgpADTableLastChanged,
      svcTlsBgpADRowStatus,
      svcTlsBgpADLastChanged,
      svcTlsBgpADVplsId,
      svcTlsBgpADVsiPrefix,
      svcTlsBgpADAdminStatus,
      svcL2MhRteDf, 
      svcL2MhRteState
    }
    STATUS      current
    DESCRIPTION
        "The group of objects supporting management of Services BGP AD
         capabilities on Nokia SROS series systems."
    ::= { tmnxSvcGroups 148 }
      
tmnxSvcDhcpV8v0Group OBJECT-GROUP
    OBJECTS {
      svcDhcpLeaseChAddr,
      svcDhcpLeaseLocale,
      svcDhcpLeasePortId,
      svcDhcpLeaseEncapValue,
      svcDhcpLeaseSdpId,
      svcDhcpLeaseVcId,
      svcDhcpLeaseRemainLseTime,
      svcDhcpLeaseOption82,
      svcDhcpLeasePersistKey,
      svcDhcpLeaseSubscrIdent,
      svcDhcpLeaseSubProfString,
      svcDhcpLeaseSlaProfString,
      svcDhcpLeaseShcvOperState,
      svcDhcpLeaseShcvChecks,
      svcDhcpLeaseShcvReplies,
      svcDhcpLeaseShcvReplyTime,
      svcDhcpLeaseClientId,
      svcDhcpLeaseIAID,
      svcDhcpLeaseIAIDType,
      svcDhcpLeaseCiAddrMaskLen,
      svcDhcpLeaseRetailerSvcId,
      svcDhcpLeaseRetailerIf,
      svcDhcpLeaseAncpString,
      svcDhcpLeaseFramedIpNetMaskTp,
      svcDhcpLeaseFramedIpNetMask,
      svcDhcpLeaseBCastIpAddrType,
      svcDhcpLeaseBCastIpAddr,
      svcDhcpLeaseDefaultRouterTp,
      svcDhcpLeaseDefaultRouter,
      svcDhcpLeasePrimaryDnsType,
      svcDhcpLeasePrimaryDns,
      svcDhcpLeaseSecondaryDnsType,
      svcDhcpLeaseSecondaryDns,
      svcDhcpLeaseSessionTimeout,
      svcDhcpLeaseServerLeaseStart,
      svcDhcpLeaseServerLastRenew,
      svcDhcpLeaseServerLeaseEnd,
      svcDhcpLeaseDhcpServerAddrType,
      svcDhcpLeaseDhcpServerAddr,
      svcDhcpLeaseOriginSubscrId,
      svcDhcpLeaseOriginStrings,
      svcDhcpLeaseOriginLeaseInfo,
      svcDhcpLeaseDhcpClientAddrType,
      svcDhcpLeaseDhcpClientAddr,
      svcDhcpLeaseLeaseSplitActive,
      svcDhcpLeaseInterDestId,
      svcDhcpLeasePrimaryNbnsType,
      svcDhcpLeasePrimaryNbns,
      svcDhcpLeaseSecondaryNbnsType,
      svcDhcpLeaseSecondaryNbns,
      svcDhcpLeaseCategoryMapName,
      svcDhcpLeaseNakNextRenew,
      svcDhcpLeaseRadiusClassAttr,
      svcDhcpLeaseRadiusUserName,
      svcDhcpManagedRouteStatus,
      svcDhcpLeaseModifySubIndent,
      svcDhcpLeaseModifySubIndent, 
      svcDhcpLeaseModifySubProfile,
      svcDhcpLeaseModifySlaProfile,
      svcDhcpLeaseEvaluateState,   
      svcDhcpLeaseModInterDestId,  
      svcDhcpLeaseModifyAncpString,
      svcDhcpLeaseForceRenew,
      svcDhcpLeaseBgpPrngPlcyName, 
      svcDhcpLeaseBgpAuthKeyChain, 
      svcDhcpLeaseBgpMD5AuthKey,   
      svcDhcpLeaseBgpImportPolicy, 
      svcDhcpLeaseBgpExportPolicy, 
      svcDhcpLeaseBgpPeerAS,       
      svcDhcpLeaseBgpPeeringStatus
    }
    STATUS      obsolete
    DESCRIPTION
        "The group of objects supporting management of Services DHCP Lease
         capabilities on Nokia SROS series systems."
    ::= { tmnxSvcGroups 150 }

-- This group is not in 7710
tmnxSvcBsxV8v0Group OBJECT-GROUP
    OBJECTS {
      svcDhcpLeaseAppProfString,
      svcDhcpLeaseModifyAppProfile
    }
    STATUS      current
    DESCRIPTION
        "The group of objects supporting management of BSX (Application
         Assurance) capabilities on Nokia SROS series systems."
    ::= { tmnxSvcGroups 151 }

tmnxSvcRoutedVplsV8v0Group OBJECT-GROUP
    OBJECTS {
     svcTlsAllowIpIfBinding,
     iesIfVplsName,
     iesIfVplsStatus,
     iesIfVplsFailedReason,
     iesIfSapEgressQosId
    }
    STATUS      current
    DESCRIPTION
        "The group of objects supporting management of Services Routed VPLS
         capabilities on Nokia SROS series systems."
    ::= { tmnxSvcGroups 154 }

tmnxSvcMvrpV8v0Group OBJECT-GROUP
    OBJECTS {
       svcTmplLastChanged, 
       svcTmplMtu, 
       svcTmplRowStatus, 
       svcTmplTblLastChanged, 
       svcTmplType,
       svcTmplTlsTblLastChanged, 
       svcTmplTlsLastChanged, 
       svcTlsGroupAdminStatus, 
       svcTlsGroupEnd, 
       svcTlsGroupLastChanged, 
       svcTlsGroupRowStatus, 
       svcTlsGroupSapTmplName, 
       svcTlsGroupStart, 
       svcTlsGroupSvcTmplName, 
       svcTlsGroupTblLastChanged, 
       svcTlsGroupMvrpControl,
       svcTlsGroupStartVlanTag,
       svcTlsTempFloodTime,
       svcTlsTempFloodActive,  
       svcTlsTempFloodChangeCount,
       svcTmplSvcCount,
       svcTmplUsed,
       svcCtrlSvcId,
       svcTlsExtMvrpAttributeCount,
       svcTlsExtMmrpAdminStatus,
       svcTlsExtMmrpOperStatus,
       svcTmplUserCreationOrigin,
       svcTmplUserCreatorSvcId,
       svcTmplTlsDiscardUnknownDest,
       svcTmplTlsFdbLocalAgeTime,
       svcTmplTlsFdbRemoteAgeTime,
       svcTmplTlsFdbTableFullHighWMark,
       svcTmplTlsFdbTableFullLowWMark,
       svcTmplTlsFdbTableSize,
       svcTmplTlsMacAgeing,
       svcTmplTlsMacLearning,
       svcTmplTlsMacMoveAdminStatus,
       svcTmplTlsMacMoveMaxRate,
       svcTmplTlsMacMoveNumRetries,
       svcTmplTlsMacMoveRetryTimeout,
       svcTmplTlsPerSvcHashing,
       svcTmplTlsPriPortsCumFactor,
       svcTmplTlsSecPortsCumFactor,
       svcTmplTlsStpAdminStatus,
       svcTmplTlsStpBridgeForwardDelay,
       svcTmplTlsStpBridgeHelloTime,
       svcTmplTlsStpBridgeMaxAge,
       svcTmplTlsStpHoldCount,
       svcTmplTlsStpPriority,
       svcTmplTlsStpVersion,
       svcTmplTlsTempFloodTime,
       svcTlsExtMvrpAttrTblHighWM, 
       svcTlsExtMvrpAttrTblLowWM, 
       svcTlsExtMvrpHoldTime, 
       svcTlsExtMvrpMaxAttributes, 
       svcTlsExtMvrpAdminStatus,
       svcTlsExtMvrpOperStatus,
       svcTlsGroupOperStatus,
       svcTlsGroupLastError,
       svcTlsExtMmrpDeclaredAttrCnt, 
       svcTlsExtMmrpFailedRegCnt, 
       svcTlsExtMmrpRegAttrCnt, 
       svcTlsExtMvrpDeclaredAttrCnt, 
       svcTlsExtMvrpFailedRegCnt, 
       svcTlsExtMvrpRegAttrCnt,
       svcTmplCustId
    }
    STATUS     current 
    DESCRIPTION
        "The group of objects supporting management of MVRP
         capabilities on Nokia SROS series systems."
    ::= { tmnxSvcGroups 155 }

tmnxSvcIpipeV8v0Group OBJECT-GROUP
    OBJECTS {
      svcIpipeInfoLastMgmtChange,
      svcIpipeCeAddressDiscovery,
      svcIpipeInfoTableLastMgmtChange,
      svcIpipeIpv6CeAddressDiscovery,
      svcIpipeStackCapabilitySignaling
    }
    STATUS      current
    DESCRIPTION
        "The group of objects supporting management of IPIPE Service
         on Nokia SROS series systems for Release 8.0."
    ::= { tmnxSvcGroups 156 }

tmnxSvcInterAsV8v0Group OBJECT-GROUP
    OBJECTS {
      svcInterASMvpn
    }
    STATUS      current
    DESCRIPTION
        "The group of objects supporting management of inter-AS Service
         on Nokia SROS series systems for Release 8.0."
    ::= { tmnxSvcGroups 157 }

tmnxSvcPwV8v0Group OBJECT-GROUP
    OBJECTS {
      svcEndPointStandbySigSlave
    }
    STATUS      current
    DESCRIPTION
        "The group of objects supporting management of services specific
         psuedo-wire capabilities on Nokia SROS series systems for
         release 8.0."
    ::= { tmnxSvcGroups 158 }

tmnxSvcTlsPipV8v0Group OBJECT-GROUP
    OBJECTS {
      tlsPipInTcBitBpdus,
      tlsPipOutTcBitBpdus
    }
    STATUS      current
    DESCRIPTION
        "The group of objects supporting management of Services TLS PIP
         capabilities on Nokia SROS series systems
         added in release 8.0."
    ::= { tmnxSvcGroups 159 }

tmnxSvcIesIfV8v0Group OBJECT-GROUP
    OBJECTS {
      iesGrpIfPolicyControl
    }
    STATUS      current
    DESCRIPTION
        "The group of objects supporting management of Services IES
         interface capabilities on Nokia SROS series systems
         added in release 8.0."
    ::= { tmnxSvcGroups 160 }


tmnxSvcV9v0Group OBJECT-GROUP
    OBJECTS {
      svcCreationOrigin,
      svcMacFdbRecords
    }
    STATUS      current
    DESCRIPTION
        "The group of objects supporting management of Services
         capabilities on Nokia SROS series systems for release 9.0."
    ::= { tmnxSvcGroups 161 }

tmnxSvcMSPwPeV9v0Group OBJECT-GROUP
    OBJECTS {
       svcMSPwPeAdminStatus, 
       svcMSPwPeLastChange,
       svcMSPwPeRowStatus, 
       svcMSPwPeTblLastChanged,
       svcMSPwPeFecType,
       svcMSPwPeAiiType,
       svcMSPwPeAgi, 
       svcMSPwPeAutoConfig, 
       svcMSPwPeEndPoint, 
       svcMSPwPeStandbySigSlave, 
       svcMSPwPeIsICB, 
       svcMSPwPePathName, 
       svcMSPwPePolicyId, 
       svcMSPwPePrecedence, 
       svcMSPwPeRetryCount, 
       svcMSPwPeRetryTimer, 
       svcMSPwPeSaiiAcId, 
       svcMSPwPeSaiiGlobalId, 
       svcMSPwPeSaiiPrefix, 
       svcMSPwPeSignaling, 
       svcMSPwPeTaiiAcId, 
       svcMSPwPeTaiiGlobalId, 
       svcMSPwPeTaiiPrefix,
       svcPwRtPathAdminStatus, 
       svcPwRtPathHopAddr, 
       svcPwRtPathHopAddrType, 
       svcPwRtPathHopLastChange, 
       svcPwRtPathHopRowStatus, 
       svcPwRtPathHopTblLastChgd, 
       svcPwRtPathLastChange, 
       svcPwRtPathRowStatus, 
       svcPwRtPathTblLastChanged, 
       svcPwRtLclPrefixLastChange, 
       svcPwRtLclPrefixRowStatus, 
       svcPwRtLclPrefixTblLastChanged, 
       svcPwRtStaticRtLastChange, 
       svcPwRtStaticRtRowStatus, 
       svcPwRtStaticRtTblLastChgd,
       svcPwSpeTaiiOperSdpBind1, 
       svcPwSpeTaiiOperSdpBind2, 
       svcPwSpeTaiiSvcId, 
       svcPwSpeTaiiSaiiAcId, 
       svcPwSpeTaiiSaiiGlobalId, 
       svcPwSpeTaiiSaiiPrefix, 
       svcPwSpeSaiiOperSdpBind1, 
       svcPwSpeSaiiOperSdpBind2, 
       svcPwSpeSaiiSvcId, 
       svcPwSpeSaiiTaiiAcId, 
       svcPwSpeSaiiTaiiGlobalId, 
       svcPwSpeSaiiTaiiPrefix, 
       svcMSPwPeRetryRemain, 
       svcMSPwPeTimeRemain,
       svcMSPwPeOperSdpBind,
       svcEndPointTxActiveSdpFec,
       svcPwRtSpeAddrGlobalId,
       svcPwRtSpeAddrPrefix,
       svcEndPointForceSwitchOvrSdpFec,
       svcMSPwPeRetryExpired, 
       svcMSPwPeLastError, 
       svcPwRtBgpRoutes, 
       svcPwRtBootTimer, 
       svcPwRtHostRoutes, 
       svcPwRtLocalRoutes, 
       svcPwRtRetryCount, 
       svcPwRtRetryTimer, 
       svcPwRtStaticRoutes, 
       svcPwRtLclPfxRDCommunity, 
       svcPwRtLclPfxRDLastChange, 
       svcPwRtLclPfxRDRowStatus, 
       svcPwRtLclPfxRDTblLastChanged,
       svcPwRtBootTimerRemain
    }
    STATUS      current
    DESCRIPTION
        "The group of objects supporting management of Services
         capabilities on Nokia SROS series systems for release 9.0."
    ::= { tmnxSvcGroups 162 }

tmnxSvcOperGrpV9v0Group OBJECT-GROUP
    OBJECTS {
       svcTlsSiteIdMonitorOperGrp,
       svcOperGrpCreationOrigin,
       svcOperGrpHoldUpTime, 
       svcOperGrpHoldDownTime, 
       svcOperGrpNumMembers, 
       svcOperGrpNumMonitoring, 
       svcOperGrpLastChange, 
       svcOperGrpOperStatus, 
       svcOperGrpRowStatus, 
       svcOperGrpTblLastChanged,
       svcOperGrpHoldUpTimeRemain,
       svcOperGrpHoldDownTimeRemain
    }
    STATUS      current
    DESCRIPTION
        "The group of objects supporting management of Services
         capabilities on Nokia SROS series systems for release 9.0."
    ::= { tmnxSvcGroups 163 }

tmnxSvcDhcpV9v0Group OBJECT-GROUP
    OBJECTS {
        svcDhcpLeaseAleDatalink,
        svcDhcpLeaseAleEncaps1,
        svcDhcpLeaseAleEncaps2,
        svcDhcpLeaseOvrPIR,      
        svcDhcpLeaseOvrCIR,      
        svcDhcpLeaseOvrCBS,      
        svcDhcpLeaseOvrMBS,      
        svcDhcpLeaseOvrWrrWeight
    }
    STATUS      obsolete
    DESCRIPTION
        "The group of objects supporting management of Services DHCP Lease
         capabilities on Nokia SROS series systems
         that were added in release 9.0."
    ::= { tmnxSvcGroups 164 }

-- This group is not in 7450
tmnxSvcRoutedCOV9v0Group OBJECT-GROUP
    OBJECTS {
        iesIfParentIf,
        iesIfFwdServId,
        iesIfFwdSubIf,
        iesGrpIfRedInterface,
        svcWholesalerNumStaticHosts,
        svcWholesalerNumDynamicHosts,
        iesIfPrivateRetailSubnets,
        svcWholesalerNumDhcpLeaseStates,
        svcWholesalerNumPppoeSessions,
        svcWholesalerNumArpHosts,
        iesIfDelegatedPrefixLen,
        iesIfLns,
        iesIfDefaultPrimaryDnsIPv4Addr,  
        iesIfDefaultSecondaryDnsIPv4Addr,
        iesIfDefaultPrimaryDnsIPv6Addr,  
        iesIfDefaultSecondaryDnsIPv6Addr,
        iesIfIPv6ConfigAllowed,
        iesIfSrrpRoutingEnabled,
        iesIfSrrpRoutingHoldTime,
        iesIfAllowUnmatchingSubnets
    }
    STATUS      current
    DESCRIPTION
       "The group of objects supporting routed CO on R9.0 Nokia SROS 
        systems."
    ::= { tmnxSvcGroups 165 }
        
tmnxSvcV9v0R4Group OBJECT-GROUP
    OBJECTS {
      iesIfMonitorOperGrp,
      svcTlsExtMmrpEndStationOnly
    }
    STATUS      current
    DESCRIPTION
        "The group of objects supporting management of Services
         capabilities on Nokia SROS series systems for release 9.0 R4."
    ::= { tmnxSvcGroups 166 }

tmnxSvcMacReNotifyGroup OBJECT-GROUP
    OBJECTS {
      svcTlsExtMacReNotifInterval
    }
    STATUS      current
    DESCRIPTION
        "The group of objects supporting management of mac-notification
         capabilities on Nokia SROS series systems."
    ::= { tmnxSvcGroups 167 }

tmnxSvcDhcpV10v0Group OBJECT-GROUP
    OBJECTS {
        svcDhcpLeaseWppState,
        svcDhcpLeaseWppPortalRouter,
        svcDhcpLeaseWppPortalName,
        svcDhcpLeasePoolName,
        svcDhcpLeaseServerId,
        svcDhcpLeaseInterfaceId,
        svcDhcpLeaseRemoteId,
        svcDhcpLeaseOption60,
        svcDhcpLeaseRadCalledStationId
    }
    STATUS      obsolete
    DESCRIPTION
        "The group of objects supporting management of Services DHCP Lease
         capabilities on Nokia SROS series systems
         that were added in release 10.0."
    ::= { tmnxSvcGroups 170 }

tmnxSvcRoutedCOV10v0Group OBJECT-GROUP
    OBJECTS {
        iesIfGroupInterfaceType,
        svcIfSapCfgTableLastChanged,
        svcIfSapCfgLastMgmtChange,
        svcIfSapCfgDescription,
        svcIfSapCfgDefSubProfile,
        svcIfSapCfgDefSlaProfile,
        svcIfSapCfgDefAppProfile,
        svcIfSapCfgSubIdentPolicy,
        svcIfSapCfgDefSubIdent,
        svcIfSapCfgDefSubIdentString,
        svcIfSapCfgDefFilterProfile
    }
    STATUS      current
    DESCRIPTION
       "The group of objects supporting routed CO on R10.0 Nokia SROS 
        systems."
    ::= { tmnxSvcGroups 171 }
            
tmnxSvcV10v0Group OBJECT-GROUP
    OBJECTS {
        svcEndPointRestProtSrcMac,
        svcEndPointRestProtSrcMacAction,
        svcEndPointAutoLearnMacProtect,
        tlsShgAutoLearnMacProtect,
        custMssIngQosArbitStatsFwdPkts,
        custMssIngQosArbitStatsFwdPktsLo,
        custMssIngQosArbitStatsFwdPktsHi,
        custMssIngQosArbitStatsFwdOcts,
        custMssIngQosArbitStatsFwdOctsLo,
        custMssIngQosArbitStatsFwdOctsHi,
        custMssEgrQosArbitStatsFwdPkts,
        custMssEgrQosArbitStatsFwdPktsLo,
        custMssEgrQosArbitStatsFwdPktsHi,
        custMssEgrQosArbitStatsFwdOcts,
        custMssEgrQosArbitStatsFwdOctsLo,
        custMssEgrQosArbitStatsFwdOctsHi,
        custIngQosPortIdArbitFwdPkts,
        custIngQosPortIdArbitFwdPktsLo,
        custIngQosPortIdArbitFwdPktsHi,
        custIngQosPortIdArbitFwdOcts,
        custIngQosPortIdArbitFwdOctsLo,
        custIngQosPortIdArbitFwdOctsHi,
        custEgrQosPortIdArbitFwdPkts,
        custEgrQosPortIdArbitFwdPktsLo,
        custEgrQosPortIdArbitFwdPktsHi,
        custEgrQosPortIdArbitFwdOcts,
        custEgrQosPortIdArbitFwdOctsLo,
        custEgrQosPortIdArbitFwdOctsHi
    }
    STATUS      current
    DESCRIPTION
       "The group of objects supporting generic services on R10.0
       Nokia SROS systems."
    ::= { tmnxSvcGroups 172 }

tmnxSvcIesIfV10v0Group OBJECT-GROUP
    OBJECTS {
        iesIfShcvFamily,
        iesIfIPv6IpoeBridgedModeEnabled
    }
    STATUS      current
    DESCRIPTION
        "The group of objects supporting management of Services IES
         interface capabilities on Nokia SROS series systems."
    ::= { tmnxSvcGroups 173 }

tmnxArpHostV10v0Group OBJECT-GROUP
    OBJECTS {
        svcArpHostTableLastChanged,
        svcArpHostLocale,
        svcArpHostSapPortId,
        svcArpHostSapEncapValue,
        svcArpHostSdpId,
        svcArpHostVcId,
        svcArpHostSessionTimeout,
        svcArpHostStart,
        svcArpHostLastAuth,
        svcArpHostRefresh,
        svcArpHostRemainingTime,
        svcArpHostShcvOperState,
        svcArpHostShcvChecks,
        svcArpHostShcvReplies,
        svcArpHostShcvReplyTime,
        svcArpHostSubscrIdent,
        svcArpHostSubProfString,
        svcArpHostSlaProfString,
        svcArpHostAppProfString,
        svcArpHostAncpString,
        svcArpHostInterDestId,
        svcArpHostRetailerSvcId,
        svcArpHostRetailerIf,
        svcArpHostMacAddr,
        svcArpHostPersistKey,
        svcArpHostCategoryMapName,
        svcArpHostRadiusClassAttr,
        svcArpHostRadiusUserName,
        svcArpHostOriginSubscrId,
        svcArpHostOriginStrings,
        svcArpHostIfTableLastMgmtChange,
        svcArpHostIfLastMgmtChange,
        svcArpHostIfAdminState,
        svcArpHostIfMaxNumHosts,
        svcArpHostIfMaxNumHostsSap,
        svcArpHostIfMinAuthInterval,
        svcArpHostIfNumHosts,
        svcArpHostDefaultSessionTimeout,
        svcArpHostMRtStatus,
        svcArpHostOvrPIR,
        svcArpHostOvrCIR,
        svcArpHostOvrCBS,
        svcArpHostOvrMBS,
        svcArpHostOvrWrrWeight
    }
    STATUS      obsolete
    DESCRIPTION
        "The group of objects supporting management of Services ARP hosts
         capabilities on Nokia SROS series systems in release 10.0."
    ::= { tmnxSvcGroups 174 }

tmnxSvcIesIfV11v0Group OBJECT-GROUP
    OBJECTS {
        iesIfIPv6AllowUnmatchingPfxs,
        iesIfMcastNetDomainEgrIfCon
    }
    STATUS      current
    DESCRIPTION
        "The group of objects supporting management of Services IES
         interface capabilities on Nokia SROS series systems
         in release 11.0."
    ::= { tmnxSvcGroups 175 }

tmnxSvcIesIfNHV10v0Group OBJECT-GROUP
    OBJECTS {
        iesIfIsaTnlNHTableLastChanged,
        iesIfIsaTnlNHLastChanged,
        iesIfIsaTnlNHStaticAddrType,
        iesIfIsaTnlNHStaticAddr,
        iesIfIsaTnlNHDynAddrType,
        iesIfIsaTnlNHDynAddr
    }
    STATUS      current
    DESCRIPTION
        "The group of objects supporting management of Services IES
         interface capabilities on Nokia SROS series systems
         in release 11.0."
    ::= { tmnxSvcGroups 176 }

tmnxArpHostV11v0Group OBJECT-GROUP
    OBJECTS {
        svcArpHostTableLastChanged,
        svcArpHostLocale,
        svcArpHostSapPortId,
        svcArpHostSapEncapValue,
        svcArpHostSdpId,
        svcArpHostVcId,
        svcArpHostSessionTimeout,
        svcArpHostStart,
        svcArpHostLastAuth,
        svcArpHostRefresh,
        svcArpHostRemainingTime,
        svcArpHostShcvOperState,
        svcArpHostShcvChecks,
        svcArpHostShcvReplies,
        svcArpHostShcvReplyTime,
        svcArpHostSubscrIdent,
        svcArpHostSubProfString,
        svcArpHostSlaProfString,
        svcArpHostAppProfString,
        svcArpHostAncpString,
        svcArpHostInterDestId,
        svcArpHostRetailerSvcId,
        svcArpHostRetailerIf,
        svcArpHostMacAddr,
        svcArpHostPersistKey,
        svcArpHostCategoryMapName,
        svcArpHostRadiusClassAttr,
        svcArpHostRadiusUserName,
        svcArpHostIfTableLastMgmtChange,
        svcArpHostIfLastMgmtChange,
        svcArpHostIfAdminState,
        svcArpHostIfMaxNumHosts,
        svcArpHostIfMaxNumHostsSap,
        svcArpHostIfMinAuthInterval,
        svcArpHostIfNumHosts,
        svcArpHostDefaultSessionTimeout,
        svcArpHostMRtStatus,
        svcArpHostMRtMetric,
        svcArpHostMRtPreference,
        svcArpHostMRtTag,
        svcArpHostOvrPIR,
        svcArpHostOvrCIR,
        svcArpHostOvrCBS,
        svcArpHostOvrMBS,
        svcArpHostOvrWrrWeight
    }
    STATUS      current
    DESCRIPTION
        "The group of objects supporting management of Services ARP hosts
         capabilities on Nokia SROS series systems in release 11.0."
    ::= { tmnxSvcGroups 177 }

tmnxSvcDhcpV11v0Group OBJECT-GROUP
    OBJECTS {
      svcDhcpLeaseChAddr,
      svcDhcpLeaseLocale,
      svcDhcpLeasePortId,
      svcDhcpLeaseEncapValue,
      svcDhcpLeaseSdpId,
      svcDhcpLeaseVcId,
      svcDhcpLeaseRemainLseTime,
      svcDhcpLeaseOption82,
      svcDhcpLeasePersistKey,
      svcDhcpLeaseSubscrIdent,
      svcDhcpLeaseSubProfString,
      svcDhcpLeaseSlaProfString,
      svcDhcpLeaseShcvOperState,
      svcDhcpLeaseShcvChecks,
      svcDhcpLeaseShcvReplies,
      svcDhcpLeaseShcvReplyTime,
      svcDhcpLeaseClientId,
      svcDhcpLeaseIAID,
      svcDhcpLeaseIAIDType,
      svcDhcpLeaseCiAddrMaskLen,
      svcDhcpLeaseRetailerSvcId,
      svcDhcpLeaseRetailerIf,
      svcDhcpLeaseAncpString,
      svcDhcpLeaseFramedIpNetMaskTp,
      svcDhcpLeaseFramedIpNetMask,
      svcDhcpLeaseBCastIpAddrType,
      svcDhcpLeaseBCastIpAddr,
      svcDhcpLeaseDefaultRouterTp,
      svcDhcpLeaseDefaultRouter,
      svcDhcpLeasePrimaryDnsType,
      svcDhcpLeasePrimaryDns,
      svcDhcpLeaseSecondaryDnsType,
      svcDhcpLeaseSecondaryDns,
      svcDhcpLeaseServerLeaseStart,
      svcDhcpLeaseServerLastRenew,
      svcDhcpLeaseServerLeaseEnd,
      svcDhcpLeaseDhcpServerAddrType,
      svcDhcpLeaseDhcpServerAddr,
      svcDhcpLeaseOriginLeaseInfo,
      svcDhcpLeaseDhcpClientAddrType,
      svcDhcpLeaseDhcpClientAddr,
      svcDhcpLeaseLeaseSplitActive,
      svcDhcpLeaseInterDestId,
      svcDhcpLeasePrimaryNbnsType,
      svcDhcpLeasePrimaryNbns,
      svcDhcpLeaseSecondaryNbnsType,
      svcDhcpLeaseSecondaryNbns,
      svcDhcpLeaseCategoryMapName,
      svcDhcpLeaseNakNextRenew,
      svcDhcpLeaseRadiusClassAttr,
      svcDhcpLeaseRadiusUserName,
      svcDhcpManagedRouteStatus,
      svcDhcpManagedRouteMetric,
      svcDhcpManagedRoutePreference,
      svcDhcpManagedRouteTag,
      svcDhcpLeaseModifySubIndent,
      svcDhcpLeaseModifySubIndent, 
      svcDhcpLeaseModifySubProfile,
      svcDhcpLeaseModifySlaProfile,
      svcDhcpLeaseEvaluateState,   
      svcDhcpLeaseModInterDestId,  
      svcDhcpLeaseModifyAncpString,
      svcDhcpLeaseForceRenew,
      svcDhcpLeaseBgpPrngPlcyName, 
      svcDhcpLeaseBgpAuthKeyChain, 
      svcDhcpLeaseBgpMD5AuthKey,   
      svcDhcpLeaseBgpImportPolicy, 
      svcDhcpLeaseBgpExportPolicy, 
      svcDhcpLeaseBgpPeerAS,       
      svcDhcpLeaseBgpPeeringStatus,
      svcDhcpLeaseAleDatalink,
      svcDhcpLeaseAleEncaps1,
      svcDhcpLeaseAleEncaps2,
      svcDhcpLeaseOvrPIR,      
      svcDhcpLeaseOvrCIR,      
      svcDhcpLeaseOvrCBS,      
      svcDhcpLeaseOvrMBS,      
      svcDhcpLeaseOvrWrrWeight,
      svcDhcpLeaseWppState,
      svcDhcpLeaseWppPortalRouter,
      svcDhcpLeaseWppPortalName,
      svcDhcpLeasePoolName,
      svcDhcpLeaseServerId,
      svcDhcpLeaseInterfaceId,
      svcDhcpLeaseRemoteId,
      svcDhcpLeaseOption60,
      svcDhcpLeaseRadCalledStationId,
      svcDhcpLeaseLeaseTime,
      svcDhcpLeaseSessTimeout,
      svcDhcpLeaseUptime,
      svcDhcpLeaseRemainingSessTime
    }
    STATUS      current
    DESCRIPTION
        "The group of objects supporting management of Services DHCP Lease
         capabilities on Nokia SROS series systems in release 11.0."
    ::= { tmnxSvcGroups 178 }
    
tmnxSvcRoutedCOV13v0Group OBJECT-GROUP
    OBJECTS {
        svcWholesalerNumDhcp6LeaseStates,
        svcWholesalerNumSlaacHosts,
        svcWholesalerNumStatic6Hosts,
        svcWholesalerNumIpoeSessions,
        svcWholesalerNumIpcpHosts
     }
    STATUS      current
    DESCRIPTION
       "The group of objects supporting routed CO on R13.0 Nokia SROS 
        systems."
    ::= { tmnxSvcGroups 179 }
                
-- Notification objects group 

tmnxSvcNotifyObjsV6v0Group OBJECT-GROUP
    OBJECTS {
      svcDhcpRestoreLseStateCiAddr,
      svcDhcpRestoreLseStateProblem,
      svcDhcpLseStateOldCiAddr,
      svcDhcpLseStateOldChAddr,
      svcDhcpLseStateNewCiAddr,
      svcDhcpLseStateNewChAddr,
      svcDhcpClientLease,
      svcDhcpPacketProblem,
      svcDhcpLseStatePopulateError,
      hostConnectivityCiAddrType,
      hostConnectivityCiAddr,
      hostConnectivityChAddr,
      protectedMacForNotify,
      staticHostDynamicMacIpAddress,
      staticHostDynamicMacConflict,
      tmnxSvcObjRow,
      tmnxSvcObjRowDescr,
      tmnxSvcObjTodSuite,
      tmnxFailureDescription,
      svcDhcpProxyError,
      svcDhcpCoAError,
      svcDhcpSubAuthError,
      svcTlsMrpAttrRegFailedReason,
      svcTlsMrpAttrType,
      svcTlsMrpAttrValue,
      svcMstiInstanceId,
      tmnxCustomerBridgeId,
      tmnxCustomerRootBridgeId,
      tmnxOtherBridgeId,
      tmnxOldSdpBindTlsStpPortState,
      tmnxVcpState,
      macPinningMacAddress,
      macPinningPinnedRow,
      macPinningPinnedRowDescr,
      macPinningViolatingRow,
      macPinningViolatingRowDescr
    }
    STATUS      obsolete
    DESCRIPTION
        "The group of objects supporting management of Services
         notification objects on Nokia SROS series systems."
    ::= { tmnxSvcGroups 200 }

-- V7v0 feature, not in V6v1 :
tmnxArpHostNotifyObjsGroup OBJECT-GROUP
    OBJECTS {
      svcNotifSapPortId,
      svcNotifSapEncapValue,
      svcArpHostPopulateError
    }
    STATUS      current
    DESCRIPTION
        "The group of objects supporting management of Services
         notification objects on Nokia SROS series systems."
    ::= { tmnxSvcGroups 201 }

tmnxSvcNotifyObjsV7v0Group OBJECT-GROUP
    OBJECTS {
      svcDhcpRestoreLseStateCiAddr,
      svcDhcpRestoreLseStateProblem,
      svcDhcpLseStateOldCiAddr,
      svcDhcpLseStateOldChAddr,
      svcDhcpLseStateNewCiAddr,
      svcDhcpLseStateNewChAddr,
      svcDhcpClientLease,
      svcDhcpPacketProblem,
      svcDhcpLseStatePopulateError,
      hostConnectivityCiAddrType,
      hostConnectivityCiAddr,
      hostConnectivityChAddr,
      protectedMacForNotify,
      staticHostDynamicMacIpAddress,
      staticHostDynamicMacConflict,
      tmnxSvcObjRow,
      tmnxSvcObjRowDescr,
      tmnxSvcObjTodSuite,
      tmnxFailureDescription,
      svcDhcpProxyError,
      svcDhcpCoAError,
      svcDhcpSubAuthError,
      svcTlsMrpAttrRegFailedReason,
      svcTlsMrpAttrType,
      svcTlsMrpAttrValue,
      svcMstiInstanceId,
      tmnxCustomerBridgeId,
      tmnxCustomerRootBridgeId,
      tmnxOtherBridgeId,
      tmnxOldSdpBindTlsStpPortState,
      tmnxVcpState,
      macPinningMacAddress,
      macPinningPinnedRow,
      macPinningPinnedRowDescr,
      macPinningViolatingRow,
      macPinningViolatingRowDescr,
      svcHostAddrType,
      svcHostAddr
    }
    STATUS      current
    DESCRIPTION
        "The group of objects supporting management of Services
         notification objects on Nokia SROS series systems."
    ::= { tmnxSvcGroups 202 }

-- Obsoleted (300)

tmnxSvcObsoletedV6v0Group OBJECT-GROUP
    OBJECTS {
      svcTlsStpHoldTime,
      tlsMFibInfoFwdOrBlk,
      tlsMFibInfoSvcId,
      tlsMFibGrpSrcStatsForwardedPkts,
      tlsMFibGrpSrcStatsForwardedOctets,
      tlsDHCPClientLease,
      tlsDhcpLseStateOldCiAddr,
      tlsDhcpLseStateOldChAddr,
      tlsDhcpLseStateNewCiAddr,
      tlsDhcpLseStateNewChAddr,
      tlsDhcpRestoreLseStateCiAddr,
      tlsDhcpRestoreLseStateSvcId,
      tlsDhcpRestoreLseStatePortId,
      tlsDhcpRestoreLseStateEncapVal,
      tlsDhcpRestoreLseStateProblem,
      tlsDhcpPacketProblem,
      tlsDhcpLseStatePopulateError
    }
    STATUS      current
    DESCRIPTION
        "The group of obsolete objects for the services feature
         on Nokia SROS series systems."
    ::= { tmnxSvcGroups 300 }

tmnxSvcObsoletedV8v0Group OBJECT-GROUP
    OBJECTS {
      svcTlsBgpADVsiRD,
      svcTlsBgpADExportRteTarget,
      svcTlsBgpADVsiExportPolicy1,
      svcTlsBgpADVsiExportPolicy2,
      svcTlsBgpADVsiExportPolicy3,
      svcTlsBgpADVsiExportPolicy4,
      svcTlsBgpADVsiExportPolicy5,
      svcTlsBgpADImportRteTarget,
      svcTlsBgpADVsiImportPolicy1,
      svcTlsBgpADVsiImportPolicy2,
      svcTlsBgpADVsiImportPolicy3,
      svcTlsBgpADVsiImportPolicy4,
      svcTlsBgpADVsiImportPolicy5,
      svcDhcpLseStateLocale,
      svcDhcpLseStatePortId,
      svcDhcpLseStateEncapValue,
      svcDhcpLseStateSdpId,
      svcDhcpLseStateVcId,
      svcDhcpLseStateChAddr,
      svcDhcpLseStateRemainLseTime,
      svcDhcpLseStateOption82,
      svcDhcpLseStatePersistKey,
      svcDhcpLseStateSubscrIdent,
      svcDhcpLseStateSubProfString,
      svcDhcpLseStateSlaProfString,
      svcDhcpLseStateShcvOperState,
      svcDhcpLseStateShcvChecks,
      svcDhcpLseStateShcvReplies,
      svcDhcpLseStateShcvReplyTime,
      svcDhcpLseStateClientId,
      svcDhcpLseStateIAID,
      svcDhcpLseStateIAIDType,
      svcDhcpLseStateCiAddrMaskLen,
      svcDhcpLseStateRetailerSvcId,
      svcDhcpLseStateRetailerIf,
      svcDhcpLseStateAncpString,
      svcDhcpLseStateFramedIpNetMaskTp,
      svcDhcpLseStateFramedIpNetMask,
      svcDhcpLseStateBCastIpAddrType,
      svcDhcpLseStateBCastIpAddr,
      svcDhcpLseStateDefaultRouterTp,
      svcDhcpLseStateDefaultRouter,
      svcDhcpLseStatePrimaryDnsType,
      svcDhcpLseStatePrimaryDns,
      svcDhcpLseStateSecondaryDnsType,
      svcDhcpLseStateSecondaryDns,
      svcDhcpLseStateSessionTimeout,
      svcDhcpLseStateServerLeaseStart,
      svcDhcpLseStateServerLastRenew,
      svcDhcpLseStateServerLeaseEnd,
      svcDhcpLseStateDhcpServerAddrType,
      svcDhcpLseStateDhcpServerAddr,
      svcDhcpLseStateOriginSubscrId,
      svcDhcpLseStateOriginStrings,
      svcDhcpLseStateOriginLeaseInfo,
      svcDhcpLseStateDhcpClientAddrType,
      svcDhcpLseStateDhcpClientAddr,
      svcDhcpLseStateLeaseSplitActive,
      svcDhcpLseStateInterDestId,
      svcDhcpLseStatePrimaryNbnsType,
      svcDhcpLseStatePrimaryNbns,
      svcDhcpLseStateSecondaryNbnsType,
      svcDhcpLseStateSecondaryNbns,
      svcDhcpLseStateNextHopMacAddr,
      svcDhcpLseStateCategoryMapName,
      svcDhcpLseStateNakNextRenew,
      svcDhcpLseStateRadiusClassAttr,
      svcDhcpLseStateRadiusUserName,
      svcDhcpLseStateModifySubIndent,
      svcDhcpLseStateModifySubProfile,
      svcDhcpLseStateModifySlaProfile,
      svcDhcpLseStateEvaluateState,
      svcDhcpLseStateModInterDestId,
      svcDhcpLseStateModifyAncpString,
      svcDhcpLseStateForceRenew,
      svcDhcpLseStateAppProfString,
      svcDhcpLseStateModifyAppProfile,
      svcDhcpLseStateBgpPrngPlcyName,
      svcDhcpLseStateBgpAuthKeyChain,
      svcDhcpLseStateBgpMD5AuthKey,   
      svcDhcpLseStateBgpImportPolicy, 
      svcDhcpLseStateBgpExportPolicy, 
      svcDhcpLseStateBgpPeerAS,       
      svcDhcpLseStateBgpPeeringStatus
    }
    STATUS      current
    DESCRIPTION
        "The group services feature objects obsoleted in release 8.0 
         of Nokia SROS series systems."
    ::= { tmnxSvcGroups 301 }

tmnxSvcObsoletedV9v0Group OBJECT-GROUP
    OBJECTS {
        iesIfVpnId
    }
    STATUS      current
    DESCRIPTION
        "The group services feature objects obsoleted in release 9.0 
         of Nokia SROS SR series systems."
    ::= { tmnxSvcGroups 302 }

tmnxSvcObsoletedV11v0Group OBJECT-GROUP
    OBJECTS {
       svcDhcpLeaseOriginSubscrId,
       svcDhcpLeaseOriginStrings,
       svcDhcpLeaseSessionTimeout,
       svcArpHostOriginSubscrId,
       svcArpHostOriginStrings
    }
    STATUS      current
    DESCRIPTION
        "The group services feature objects obsoleted in release 11.0 
         of Nokia SROS SR series systems."
    ::= { tmnxSvcGroups 303 }
-- ----------------------------
-- NOTIFICATION group
-- ----------------------------
tmnxSvcNotifyV6v0Group NOTIFICATION-GROUP
    NOTIFICATIONS   {
      svcStatusChanged,
      svcTlsFdbTableFullAlarmRaised,
      svcTlsFdbTableFullAlarmCleared,
      iesIfStatusChanged,
      svcTlsMfibTableFullAlarmRaised,
      svcTlsMfibTableFullAlarmCleared,
      svcTlsMacPinningViolation,
      svcDHCPLseStateRestoreProblem,
      tmnxSvcObjTodSuiteApplicFailed,
      tmnxEndPointTxActiveChanged,
      tmnxSvcPEDiscPolServOperStatChg,
      svcEndPointMacLimitAlarmRaised,
      svcEndPointMacLimitAlarmCleared,
      svcTlsMrpAttrRegistrationFailed,
      svcTlsMrpAttrTblFullAlarmRaised,
      svcTlsMrpAttrTblFullAlarmCleared,
      svcEpipePbbOperStatusChanged,
      topologyChangeVcpState,
      newRootVcpState,
      newRootBridge,
      vcpActiveProtocolChange,
      tmnxNewCistRegionalRootBridge,
      tmnxNewMstiRegionalRootBridge,
      topologyChangePipMajorState,
      topologyChangePipState,
      tmnxPipStpExcepCondStateChng,
      pipActiveProtocolChange,
      svcFdbMimDestTblFullAlrm,
      svcFdbMimDestTblFullAlrmCleared,
      svcDHCPMiscellaneousProblem,
      svcPersistencyProblem
    }
    STATUS      obsolete
    DESCRIPTION
        "The group of notifications for the services feature
         on Nokia SROS series systems."
    ::= { tmnxSvcGroups 401 }

tmnxSvcNotifyObsoletedGroup NOTIFICATION-GROUP
    NOTIFICATIONS   {
      custCreated,
      custDeleted,
      custMultSvcSiteCreated,
      custMultSvcSiteDeleted,
      svcCreated,
      svcDeleted,
      iesIfCreated,
      iesIfDeleted,
      svcTlsDHCPLseStRestoreProblem,
      svcTlsDHCPLseStatePopulateErr
    }
    STATUS      current
    DESCRIPTION
        "The group of notifications for the services feature
         on Nokia SROS series systems."
    ::= { tmnxSvcGroups 402 }

tmnxArpHostNotifyGroup NOTIFICATION-GROUP
    NOTIFICATIONS   {
      svcArpHostPopulateErr
    }
    STATUS      current
    DESCRIPTION
        "The group of notifications for the Services ARP hosts
         feature on Nokia SROS series systems."
    ::= { tmnxSvcGroups 403 }

tmnxSvcMCEPNotifyGroup NOTIFICATION-GROUP
    NOTIFICATIONS   {
         svcEPMCEPConfigMismatch,  
         svcEPMCEPConfigMismatchResolved,  
         svcEPMCEPPassiveModeActive,  
         svcEPMCEPPassiveModePassive
    }
    STATUS      current
    DESCRIPTION
        "The group of notifications for the Services multi-chassis endpoint
         feature on Nokia SROS series systems."
    ::= { tmnxSvcGroups 404 }

tmnxSvcNotifyV7v0Group NOTIFICATION-GROUP
    NOTIFICATIONS   {
      svcStatusChanged,
      svcTlsFdbTableFullAlarmRaised,
      svcTlsFdbTableFullAlarmCleared,
      iesIfStatusChanged,
      svcTlsMfibTableFullAlarmRaised,
      svcTlsMfibTableFullAlarmCleared,
      svcTlsMacPinningViolation,
      svcDHCPLseStateRestoreProblem,
      tmnxSvcObjTodSuiteApplicFailed,
      tmnxEndPointTxActiveChanged,
      tmnxSvcPEDiscPolServOperStatChg,
      svcEndPointMacLimitAlarmRaised,
      svcEndPointMacLimitAlarmCleared,
      svcTlsMrpAttrRegistrationFailed,
      svcTlsMrpAttrTblFullAlarmRaised,
      svcTlsMrpAttrTblFullAlarmCleared,
      svcEpipePbbOperStatusChanged,
      topologyChangeVcpState,
      newRootVcpState,
      newRootBridge,
      vcpActiveProtocolChange,
      tmnxNewCistRegionalRootBridge,
      tmnxNewMstiRegionalRootBridge,
      topologyChangePipMajorState,
      topologyChangePipState,
      tmnxPipStpExcepCondStateChng,
      pipActiveProtocolChange,
      svcFdbMimDestTblFullAlrm,
      svcFdbMimDestTblFullAlrmCleared,
      svcDHCPMiscellaneousProblem,
      svcPersistencyProblem,
      svcRestoreHostProblem
    }
    STATUS      obsolete
    DESCRIPTION
        "The group of notifications for the services feature
         on Nokia SROS series systems for release 7.0."
    ::= { tmnxSvcGroups 405 }

tmnxSvcNotifyV8v0Group NOTIFICATION-GROUP
    NOTIFICATIONS   {
       svcTlsSiteDesigFwdrChg,
       svcTlsGroupOperStatusChanged
    }
    STATUS      current
    DESCRIPTION
        "The group of notifications for the services feature
         on Nokia SROS series systems for release 8.0."
    ::= { tmnxSvcGroups 406 }

tmnxSvcEthCfmGroup     OBJECT-GROUP
    OBJECTS {
        svcEthCfmTblLastChanged,
        svcEthCfmTunnelFaultNotification,
        svcEthCfmVMepExtensions
    }
    STATUS      current
    DESCRIPTION
        "The group of objects supporting Ethernet Connectivity
         Fault Management (CFM) for the services feature on
         Nokia SROS series systems for release 9.0."
    ::= { tmnxSvcGroups 407 }

tmnxSvcNotifyV9v0Group NOTIFICATION-GROUP
    NOTIFICATIONS   {
       svcMSPwRtMisconfig,
       svcMSPwRetryExpiredNotif,
       svcMacFdbTblFullAlarm,
       svcMacFdbTblFullAlarmCleared,
       svcOperGrpOperStatusChanged
    }
    STATUS      current
    DESCRIPTION
        "The group of notifications for the services feature
         on Nokia SROS series systems for release 9.0."
    ::= { tmnxSvcGroups 408 }

tmnxSvcApipeInfoV9v0Group     OBJECT-GROUP
    OBJECTS {
        svcApipeSignaledVllTypeOverride
    }
    STATUS      current
    DESCRIPTION
        "The group of objects supporting management of APIPE services on
         Nokia SROS series systems for release 9.0."
    ::= { tmnxSvcGroups 409 }

tmnxSvcSpbGroup     OBJECT-GROUP
    OBJECTS {
       svcSpbIfEncapValue, 
       svcSpbIfLocale, 
       svcSpbIfPortId, 
       svcSpbIfSdpId, 
       svcSpbIfVcId, 
       svcSpbIfSvcId, 
       svcSpbIfIsisInstance, 
       tlsSpbFdbMEncapValue, 
       tlsSpbFdbMLocale, 
       tlsSpbFdbMPortId, 
       tlsSpbFdbMSdpId, 
       tlsSpbFdbMState, 
       tlsSpbFdbMVcId, 
       tlsSpbFidFdbMEncapValue, 
       tlsSpbFidFdbMLocale, 
       tlsSpbFidFdbMPortId, 
       tlsSpbFidFdbMSdpId, 
       tlsSpbFidFdbMVcId, 
       tlsSpbFidMFibIsid, 
       tlsSpbMFibState, 
       tlsSpbMFibIsid,
       tlsSpbFdbEncapValue, 
       tlsSpbFdbLocale,
       tlsSpbFdbPortId, 
       tlsSpbFdbSdpId, 
       tlsSpbFdbState, 
       tlsSpbFdbVcId, 
       tlsSpbFidFdbEncapValue, 
       tlsSpbFidFdbLocale, 
       tlsSpbFidFdbPortId, 
       tlsSpbFidFdbSdpId, 
       tlsSpbFidFdbVcId, 
       tlsSpbFidFdbLastUpdate,
       tlsSpbFidFdbMLastUpdate,
       tlsSpbFidMFibLastUpdate,
       svcTlsSpbUserSvcLastUpdate,
       svcTlsExtSpbmCtrlVpls, 
       svcTlsExtSpbmFid, 
       svcTlsSpbFid, 
       svcTlsSpbIsisInstance, 
       svcTlsSpbLastChanged, 
       svcTlsSpbRowStatus, 
       svcTlsSpbTableLastChanged,
       svcTlsSpbL1BridgePriority,
       svcTlsSpbL1FwdTreeTopoUcast,
       svcTlsSpbL1FwdTreeTopoMcast,
       svcTlsSpbL1BridgeId,
       svcTlsSpbL1McastDesigBridgeId,
       svcTlsSpbAdminState
    }
    STATUS      current
    DESCRIPTION
        "The group of objects supporting management of Shortest Path Bridging
         feature on Nokia SROS series systems."
    ::= { tmnxSvcGroups 410 }

tmnxSvcVllBgpGroup     OBJECT-GROUP
    OBJECTS {
       svcVllBgpExportRteTarget, 
       svcVllBgpImportRteTarget, 
       svcVllBgpLastChanged, 
       svcVllBgpTableLastChanged, 
       svcVllBgpVsiRD, 
       svcVllSiteIdAdminStatus, 
       svcVllSiteIdBootTimer, 
       svcVllSiteIdDesignatedFwdr, 
       svcVllSiteIdDfChgCnt, 
       svcVllSiteIdDfUpTime, 
       svcVllSiteIdEncapValue, 
       svcVllSiteIdLastChanged, 
       svcVllSiteIdOperStatus, 
       svcVllSiteIdPortId, 
       svcVllSiteIdRowStatus, 
       svcVllSiteIdSiteActTimer, 
       svcVllSiteIdSiteId, 
       svcVllSiteIdTblLastChanged, 
       svcVllSiteIdTimerRemain,
       svcVllBgpRowStatus,
       svcTlsBgpRowStatus
    }
    STATUS      current
    DESCRIPTION
        "The group of objects supporting management of Epipe BGP multi-homing
         feature on Nokia SROS series systems."
    ::= { tmnxSvcGroups 411 }

tmnxSvcP2mpGroup     OBJECT-GROUP
    OBJECTS {
       svcTlsIPmsiAdminState, 
       svcTlsIPmsiDataDelayIntvl, 
       svcTlsIPmsiRemainDataDelayIntvl, 
       svcTlsIPmsiType, 
       svcTlsIPmsiRootAndLeaf, 
       svcTlsIPmsiLspTmpl, 
       svcTlsIPmsiLspName, 
       svcTlsPmsiLastChanged, 
       svcTlsPmsiRowStatus, 
       svcTlsPmsiTableLastChanged
    }
    STATUS      current
    DESCRIPTION
        "The group of objects supporting management of P2MP for vpls
         feature on Nokia SROS series systems."
    ::= { tmnxSvcGroups 412 }

tmnxSvcNotifyV10v0Group NOTIFICATION-GROUP
    NOTIFICATIONS   {
       svcVllSiteDesigFwdrChg
    }
    STATUS      current
    DESCRIPTION
        "The group of notifications for the services feature
         on Nokia SROS series systems for release 8.0."
    ::= { tmnxSvcGroups 413 }

tmnxSvcV11v0Group OBJECT-GROUP
    OBJECTS {
      custCreationOrigin,
      svcNumEntries,
      svcId,
      svcRowStatus,
      svcType,
      svcCustId,
      svcIpRouting,
      svcDescription,
      svcMtu,
      svcAdminStatus,
      svcOperStatus,
      svcNumSaps,
      svcNumSdps,
      svcLastMgmtChange,
      svcDefMeshVcId,
      svcVpnId,
      svcVRouterId,
      svcAutoBind,
      svcLastStatusChange,
      svcVllType,
      svcMgmtVpls,
      svcRadiusDiscovery,
      svcRadiusUserName,
      svcRadiusUserNameType,
      svcVcSwitching,
      svcVplsType,
      svcTotalFdbMimDestIdxEntries
    }
    STATUS      obsolete
    DESCRIPTION
        "The group of objects supporting management of Services 
         general capabilities on Nokia SROS series systems
         that were added in release 11.0."
    ::= { tmnxSvcGroups 415 }

tmnxSvcPEObsoletedGroup OBJECT-GROUP
    OBJECTS {
      svcRadiusPEDiscPolicy,
      svcRadiusDiscoveryShutdown,
      svcPEDiscoveryPolicyRowStatus,
      svcPEDiscoveryPolicyPassword,
      svcPEDiscoveryPolicyInterval,
      svcPEDiscoveryPolicyTimeout,
      svcPEDiscPolServerRowStatus,
      svcPEDiscPolServerAddressType,
      svcPEDiscPolServerAddress,
      svcPEDiscPolServerSecret,
      svcPEDiscPolServerOperStatus,
      svcPEDiscPolServerPort
    }
    STATUS      current
    DESCRIPTION
        "The group of objects supporting management of Services PE Discovery
         capabilities on Nokia SROS series systems."
    ::= { tmnxSvcGroups 416 }

tmnxSvcNotifyObsoletedV11v0Group NOTIFICATION-GROUP
    NOTIFICATIONS   {
        tmnxSvcPEDiscPolServOperStatChg
    }
    STATUS      current
    DESCRIPTION
        "The group of notifications for the services feature
         on Nokia SROS series systems."
    ::= { tmnxSvcGroups 417 }

tmnxSvcNotifyV11v0Group NOTIFICATION-GROUP
    NOTIFICATIONS   {
      svcStatusChanged,
      svcTlsFdbTableFullAlarmRaised,
      svcTlsFdbTableFullAlarmCleared,
      iesIfStatusChanged,
      svcTlsMfibTableFullAlarmRaised,
      svcTlsMfibTableFullAlarmCleared,
      svcTlsMacPinningViolation,
      svcDHCPLseStateRestoreProblem,
      tmnxSvcObjTodSuiteApplicFailed,
      tmnxEndPointTxActiveChanged,
      svcEndPointMacLimitAlarmRaised,
      svcEndPointMacLimitAlarmCleared,
      svcTlsMrpAttrRegistrationFailed,
      svcTlsMrpAttrTblFullAlarmRaised,
      svcTlsMrpAttrTblFullAlarmCleared,
      svcEpipePbbOperStatusChanged,
      topologyChangeVcpState,
      newRootVcpState,
      newRootBridge,
      vcpActiveProtocolChange,
      tmnxNewCistRegionalRootBridge,
      tmnxNewMstiRegionalRootBridge,
      topologyChangePipMajorState,
      topologyChangePipState,
      tmnxPipStpExcepCondStateChng,
      pipActiveProtocolChange,
      svcFdbMimDestTblFullAlrm,
      svcFdbMimDestTblFullAlrmCleared,
      svcDHCPMiscellaneousProblem,
      svcPersistencyProblem,
      svcRestoreHostProblem
    }
    STATUS      current
    DESCRIPTION
        "The group of notifications for the services feature
         on Nokia SROS series systems for release 11.0."
    ::= { tmnxSvcGroups 418 }

svcBgpVpwsGroup OBJECT-GROUP
    OBJECTS {
        svcEndPointCreationOrigin,
        svcBgpVplsPwTemplateId,
        svcBgpVpwsPwTemplateId,
        svcL2MhRteVplsPreference,
        svcVllSiteIdPreference,
        svcBgpVpwsAdminStatus, 
        svcBgpVpwsLastChanged, 
        svcBgpVpwsRemoteVeId, 
        svcBgpVpwsRemoteVeLastChanged, 
        svcBgpVpwsRemoteVeRowStatus, 
        svcBgpVpwsRemoteVeTblLastChanged, 
        svcBgpVpwsRowStatus, 
        svcBgpVpwsTblLastChanged, 
        svcBgpVpwsVeId, 
        svcBgpVpwsVeName
    }
    STATUS      current
    DESCRIPTION
        "The group of objects supporting management of Services PE Discovery
         capabilities on Nokia SROS series systems."
    ::= { tmnxSvcGroups 419 }

tmnxSvcSchedulerRateV11v0Group OBJECT-GROUP
    OBJECTS {
        custMssIngQosSPIRHi,
        custMssIngQosSPIRLo,
        custMssIngQosSCIRHi,
        custMssIngQosSCIRLo,
        custMssEgrQosSPIRHi,
        custMssEgrQosSPIRLo,
        custMssEgrQosSCIRHi,
        custMssEgrQosSCIRLo
    }
    STATUS      current
    DESCRIPTION
        "The group of objects supporting management of Scheduler policies
         on Nokia SROS series systems release 11.0."
    ::= { tmnxSvcGroups 420 } 

tmnxSvcSpbV11v0Group OBJECT-GROUP
    OBJECTS {
        svcTlsIsidPlcyRangeRowStatus,
        svcTlsIsidPlcyRangeLastChanged,
        svcTlsIsidPlcyRangeLow,
        svcTlsIsidPlcyRangeHigh,
        svcTlsIsidPlcyRangeUseDefMCTree,
        svcTlsIsidPlcyRangeAdvLocal
    }
    STATUS      current
    DESCRIPTION
        "The group of objects supporting management of SPB feature
         on Nokia SROS series systems release 11.0."
    ::= { tmnxSvcGroups 421 } 

tmnxCustV11v0Group OBJECT-GROUP
    OBJECTS {
      custNumEntries,
      custNextFreeId,
      custId,
      custRowStatus,
      custDescription,
      custContact,
      custPhone,
      custLastMgmtChange,
      custMultSvcSiteName,
      custMultSvcSiteRowStatus,
      custMultSvcSiteDescription,
      custMultSvcSiteScope,
      custMultSvcSiteAssignment,
      custMultSvcSiteIngressSchedulerPolicy,
      custMultSvcSiteEgressSchedulerPolicy,
      custMultSvcSiteLastMgmtChange,
      custMultSvcSiteTodSuite,
      custMultSvcSiteCurrentIngrSchedPlcy,
      custMultSvcSiteCurrentEgrSchedPlcy,
      custMultSvcSiteEgressAggRateLimit,
      custMultSvcSiteIntendedIngrSchedPlcy,
      custMultSvcSiteIntendedEgrSchedPlcy,
      custMultSvcSiteFrameBasedAccnt,
      custIngQosSchedStatsForwardedPackets,
      custIngQosSchedStatsForwardedOctets,
      custEgrQosSchedStatsForwardedPackets,
      custEgrQosSchedStatsForwardedOctets,
      custIngQosPortSchedFwdPkts,
      custIngQosPortSchedFwdOctets,
      custEgrQosPortSchedFwdPkts,
      custEgrQosPortSchedFwdOctets,
      custMssIngQosSRowStatus,
      custMssIngQosSLastMgmtChange,
      custMssIngQosSOverrideFlags,
      custMssIngQosSSummedCIR,
      custMssEgrQosSRowStatus,
      custMssEgrQosSLastMgmtChange,
      custMssEgrQosSOverrideFlags,
      custMssEgrQosSSummedCIR,
      custIngSchedPlcyStatsFwdPkt,
      custIngSchedPlcyStatsFwdOct,
      custEgrSchedPlcyStatsFwdPkt,
      custEgrSchedPlcyStatsFwdOct,
      custIngSchedPlcyPortStatsFwdPkt,
      custIngSchedPlcyPortStatsFwdOct,
      custEgrSchedPlcyPortStatsFwdPkt,
      custEgrSchedPlcyPortStatsFwdOct,
      custMultSvcSiteFrameBasedAccnt,
      custMultSvcSiteSubscriberMss
    }
    STATUS      obsolete
    DESCRIPTION
        "The group of objects supporting management of Services customers
         general capabilities on Nokia SROS series systems."
    ::= { tmnxCustGroups 104 }

tmnxCustObsoletedV11v0Group OBJECT-GROUP
    OBJECTS {     
        custMssIngQosSPIR,
        custMssIngQosSCIR,
        custMssEgrQosSPIR,
        custMssEgrQosSCIR
   }
    STATUS      current
    DESCRIPTION
        "The group of objects obsoleted supporting management of Services 
         customers on Nokia SROS series systems release 11.0."
    ::= { tmnxCustGroups 105 }

tmnxSvcV12v0Group OBJECT-GROUP
    OBJECTS {
        svcNumMHStandbySaps,
        svcDhcpLeaseWppRestoreOnDiscon,
        svcDhcpLeaseWppIsTriggered,
        svcDhcpLeaseWppInitialSubProfile,
        svcDhcpLeaseWppInitialSLAProfile,
        svcDhcpLeaseWppInitialAppProfile,
        svcDhcpLeaseWppLocalUserDb,
        svcDhcpLeaseWppAuthPolicy,
        iesIfIPv6Dhcp6PDManagedRoute,
        svcDhcpLeaseMngdRtStatus
    }
    STATUS      current
    DESCRIPTION
        "The group of objects supporting management of services feature
         on Nokia SROS series systems release 12.0."
    ::= { tmnxSvcGroups 423 } 

tmnxSvcMHGroup     OBJECT-GROUP
    OBJECTS {
      svcTlsSiteIdActTimerRemain,
      svcVllSiteIdActTimerRemain
    }
    STATUS      current
    DESCRIPTION
        "The group of objects supporting management of multi-homing for vpls
         and epipe feature on Nokia SROS series systems."
    ::= { tmnxSvcGroups 424 }

tmnxSvcCondStaticMacGroup     OBJECT-GROUP
    OBJECTS {
        tlsCondStaticMacLastChanged,
        tlsCondStaticMacTblLastChanged,
        tlsCondStaticMacAddr,
        tlsCondStaticMacPreference,
        tlsCondStaticMacRowStatus,
        tlsCondStaticMacLocale,
        tlsCondStaticMacPortId,
        tlsCondStaticMacEncapValue,
        tlsCondStaticMacSdpId,
        tlsCondStaticMacVcId,
        tlsCondStaticMacMonitor
    }
    STATUS      current
    DESCRIPTION
        "The group of objects supporting management of multi-homing for vpls
         and epipe feature on Nokia SROS series systems."
    ::= { tmnxSvcGroups 425 }

svcTlsFdbMacStatsGroup OBJECT-GROUP
    OBJECTS {
        svcTlsFdbMacStatsNumEntries
    }
    STATUS      current
    DESCRIPTION
        "The group of objects supporting management of services feature
         on Nokia SROS series systems release 12.0."
    ::= { tmnxSvcGroups 426 } 

svcOperGrpBfdGroup OBJECT-GROUP
    OBJECTS {
        svcOperGrpBfdTblLastChgd,
        svcOperGrpBfdRowStatus,
        svcOperGrpBfdLastChgd,
        svcOperGrpBfdSvcId,
        svcOperGrpBfdIfName,
        svcOperGrpBfdDestIpType,
        svcOperGrpBfdDestIp,
        svcOperGrpBfdSrcIpType,
        svcOperGrpBfdSrcIp,
        svcOperGrpBfdSessOperState
    }
    STATUS      current
    DESCRIPTION
        "The group of objects supporting management of operational-group BFD
         feature on Nokia SROS series systems release 12.0."
    ::= { tmnxSvcGroups 427 } 

svcTlsEtreeGroup OBJECT-GROUP
    OBJECTS {
        svcTlsModeEtree
    }
    STATUS current
    DESCRIPTION
        "The group objects supporting service E-Tree feature on
         Nokia SROS series systems release 12.0."
    ::={ tmnxSvcGroups 428 } 


svcVxlanGroup OBJECT-GROUP
    OBJECTS {
        tlsFdbVTEPAddrType,
        tlsFdbVTEPAddr,
        tlsFdbVNI,
        svcTlsVxlanRowStatus,
        svcTlsVxlanLastChgd,
        svcTlsVxlanTblLastChgd,
        svcTlsVxlanCreationOrigin,
        svcVTEPAddrType,
        svcVTEPAddress,
        svcVTEPNumEgrVNIs,
        svcVTEPOperState,
        svcTlsVTEPEgrVNIVTEPAddrType,
        svcTlsVTEPEgrVNIVTEPAddress,
        svcTlsVTEPEgrVNIEgrVNI,
        svcTlsVTEPEgrVNINumMACs,
        svcTlsVTEPEgrVNIInMcastList,
        svcTlsVTEPEgrVNIOperState,
        svcVTEPEgrVNIVTEPAddrType,
        svcVTEPEgrVNIVTEPAddress,
        svcVTEPEgrVNIEgrVNI,
        svcVTEPEgrVNISvcId,
        svcTlsVTEPEgrVNIL2EsPbr
    }
    STATUS current
    DESCRIPTION
        "The group objects supporting service VXLAN (virtual extensible LAN)
         feature on Nokia SROS series systems release 12.0."
    ::={ tmnxSvcGroups 429 }


svcBgpEvpnGroup OBJECT-GROUP
    OBJECTS {
        svcBgpEvpnTableLastChanged,
        svcBgpEvpnRowStatus,
        svcBgpEvpnLastChanged,
        svcBgpEvpnMacAdvertisement,
        svcBgpEvpnMacAdvDefaultRoute,
        svcBgpEvpnVxlanAdminStatus,
        svcBgpEvpnCreationOrigin,
        svcTlsProxyArpTblLastChngd,
        svcTlsProxyArpMacAddr,
        svcBgpEvpnMacDupDetNumMoves,
        svcBgpEvpnMacDupDetWindow,
        svcBgpEvpnMacDupDetRetry,
        svcBgpEvpnMacDupDetNumDups,
        svcBgpEvpnDetDupMacAddress,
        svcBgpEvpnDetDupMacTime
    }
    STATUS current
    DESCRIPTION
        "The group objects supporting service EVPN (Ethernet - VPN)
         feature on Nokia SROS series systems release 12.0."
    ::={ tmnxSvcGroups 430 } 

tmnxSvcV11v4Group OBJECT-GROUP
    OBJECTS {
      custCreationOrigin,
      svcNumEntries,
      svcId,
      svcRowStatus,
      svcType,
      svcCustId,
      svcIpRouting,
      svcDescription,
      svcMtu,
      svcAdminStatus,
      svcOperStatus,
      svcNumSaps,
      svcNumSdps,
      svcLastMgmtChange,
      svcDefMeshVcId,
      svcVpnId,
      svcVRouterId,
      svcAutoBind,
      svcLastStatusChange,
      svcVllType,
      svcMgmtVpls,
      svcRadiusDiscovery,
      svcVcSwitching,
      svcVplsType,
      svcTotalFdbMimDestIdxEntries
    }
    STATUS      obsolete
    DESCRIPTION
        "The group of objects supporting management of Services 
         general capabilities on Nokia SROS series systems
         that were added in release R11.4."
    ::= { tmnxSvcGroups 431 }

svcBaseInfoObsoletedGroup OBJECT-GROUP
    OBJECTS {
       svcRadiusUserName,
       svcRadiusUserNameType
    }
    STATUS      current
    DESCRIPTION
        "The group of objects supporting management of services feature
         on Nokia SROS series systems release R11.4."
    ::= { tmnxSvcGroups 432 }

tmnxIesIfRtrSolicitGroup OBJECT-GROUP
    OBJECTS {
        tmnxIesIfRtrSolTableLastChanged,
        tmnxIesIfRtrSolLastMgmtChange,
        tmnxIesIfRtrSolAdminStatus,
        tmnxIesIfRtrSolUserDb,
        tmnxIesIfRtrSolMinAuthInterval,
        tmnxIesIfRtrSolInactivityTimer,
        iesIfIPv6AllowMultiWanAddr,
        iesIfIPv6Dhcp6OverrideSlaac
    }
    STATUS current
    DESCRIPTION
        "The group objects supporting router solicit
         feature on Nokia SROS series systems release 12.0."
    ::={ tmnxSvcGroups 433 }

svcVsdGroup OBJECT-GROUP
    OBJECTS {
         svcVsdDomainName,
         svcVsdDomainTblLastChngd,
         svcVsdDomainAdminState,
         svcVsdDomainDescription,
         svcVsdDomainRowStatus,
         svcVsdDomainType,
         svcVsdDomainCreationOrigin,
         svcVsdDomainToSvcTblLastChngd,
         svcVsdDomainToSvcRowStatus,
         svcVsdDomainToSvcCreationOrigin,
         svcVsdDomainLastErrStr,
         svcVsdDomainVsdLastErrStr,
         svcVsdDomainStatCfgChgEvtRcvd,
         svcVsdDomainStatLastCfgChgEvt,
         svcVsdDomainStatCfgUpdRcvd,
         svcVsdDomainStatLastCfgUpdRcvd,
         svcVsdDomainStatLastCfgUpdDone,
         svcVsdDomainStatCfgSuccess,
         svcVsdDomainStatCfgFailed,
         svcVsdDomainRecParams,
         svcVsdDomainExecParams
    }
    STATUS current
    DESCRIPTION
        "The group objects supporting service VSD (Virtualized Services Directory)
         domain configuration on Nokia SROS series systems R12.4."
    ::={ tmnxSvcGroups 434 }

tmnxSvcQosV12v0Group  OBJECT-GROUP
    OBJECTS {
        custMultSvcSiteEgressAggRateLUB
    }
    STATUS current
    DESCRIPTION
        "The group of objects supporting management of services QoS capabilities
         for release 12.0 on Nokia SROS series systems."
    ::= { tmnxSvcGroups 435 }

tmnxSvcCreation12v0Group OBJECT-GROUP
    OBJECTS {
        svcNameCreationOrigin,
        svcTlsBgpADCreationOrigin,
        svcTlsBgpCreationOrigin,
        iesIfCreationOrigin
    }
     STATUS current
      DESCRIPTION
        "The group of objects supporting management of service creation entities
         for release 12.0 on Nokia SROS series systems."
    ::= { tmnxSvcGroups 436 }

svcBgpEvpnNotifGroup NOTIFICATION-GROUP
    NOTIFICATIONS {
        svcBgpEvpnDupMacAddrsDetected,
        svcBgpEvpnDupMacAddrsCleared,
        svcTlsEvpnTunnNHopHiUsgAlarmSet,
        svcTlsEvpnTunnNHopHiUsgAlarmClr
    }
    STATUS current
    DESCRIPTION
        "The group notifications supporting notifications for the service EVPN
        (Ethernet - VPN) feature on Nokia SROS series systems
        release 12.0."
    ::={ tmnxSvcGroups 437 }

svcVxlanNotifGroup NOTIFICATION-GROUP
    NOTIFICATIONS {
        svcTlsDupVTEPEgrVNIDetected,
        svcTlsDupVTEPEgrVNICleared,
        svcTlsVTEPHiUsageAlarmRaised,
        svcTlsVTEPHiUsageAlarmCleared,
        svcTlsVTEPEgrVniSysHiUsgAlarmSet,
        svcTlsVTEPEgrVniSysHiUsgAlarmClr,
        svcTlsVTEPEgrVniSvcHiUsgAlarmSet,
        svcTlsVTEPEgrVniSvcHiUsgAlarmClr,
        svcBindSysHiUsageAlarmRaised,
        svcBindSysHiUsageAlarmCleared,
        svcTlsRvplsEgrVniSysHiUsgAlrmSet,
        svcTlsRvplsEgrVniSysHiUsgAlrmClr
    }
    STATUS current
    DESCRIPTION
       "The group notifications supporting service VXLAN (virtual extensible
       LAN) feature on Nokia SROS series systems release 12.0."
    ::={ tmnxSvcGroups 438 }

tmnxSvcPbbMacV12v0Group OBJECT-GROUP
    OBJECTS {
     svcTlsPbbMldSnpgMRtrRowStatus,
     svcTlsPbbMldSnpgMRtrLastCh
    }
    STATUS      current
    DESCRIPTION
        "The group of objects supporting management of Services PBB MAC
         capabilities on Nokia SROS series systems release 12.0."
    ::= { tmnxSvcGroups 439 }

  
tmnxSvcTestGroup OBJECT-GROUP
    OBJECTS {
        svcIsTestSvc
    }
     STATUS current
      DESCRIPTION
        "The group of objects supporting management of test service entities
         for release 12.0 on Nokia SROS series systems."
    ::= { tmnxSvcGroups 440 }

svcBgpEvpnIPRouteGroup OBJECT-GROUP
    OBJECTS {
        iesIfVplsEvpnTunnel,
        svcBgpEvpnIpRouteAdvertisement,
        svcBgpEvpnIpRouteAdverInclHost
    }
    STATUS current
    DESCRIPTION
        "The group objects supporting service EVPN (Ethernet - VPN)
         feature on Nokia SROS series systems release 12.0."
    ::={ tmnxSvcGroups 441 } 

tmnxSvcIesIfIpoeV13v0Group OBJECT-GROUP
    OBJECTS {
        tmnxSvcIesIfIpoeTableLastChanged,
        tmnxSvcIesIfIpoeLastChange,
        tmnxSvcIesIfIpoeAdminState,
        tmnxSvcIesIfIpoeDescription,
        tmnxSvcIesIfIpoePolicy,
        tmnxSvcIesIfIpoeUserDb,
        tmnxSvcIesIfIpoeSessionLimit,
        tmnxSvcIesIfIpoeSapSessionLimit,
        tmnxSvcIesIfIpoeMinAuthInterval,
        tmnxSvcIesIfIpoeForceAuth
    }
    STATUS      current
    DESCRIPTION
        "The group of objects supporting management of Services IES interface 
         IPoE session on  Nokia SROS series systems in release 13.0."
    ::= { tmnxSvcGroups 442 }

tmnxSvcIesIfV12v0Group OBJECT-GROUP
    OBJECTS {
        iesIfExportHostRoutes
    }
    STATUS      current
    DESCRIPTION
        "The group of objects supporting management of Services IES
         interface capabilities on Nokia SROS series systems
         in release 12.0."
    ::= { tmnxSvcGroups 443 }

tmnxSvcIpipeFaultPropGroup OBJECT-GROUP
    OBJECTS {
        svcIpipeCeAddressDiscoveryKeep,
        svcIpipeEthFaultNotifRecTimer,
        svcIpipeEthFaultNotifAdminState
    }
    STATUS      current
    DESCRIPTION
        "The group of objects supporting management of IPIPE fault propagation
         capabilities on Nokia SROS series systems."
    ::= { tmnxSvcGroups 444 }

tmnxSvcQosSchedV13v0Group OBJECT-GROUP
    OBJECTS {
        custMssIngQosSParentWeight,
        custMssIngQosSParentCIRWeight,
        custMssEgrQosSParentWeight,
        custMssEgrQosSParentCIRWeight
    }
    STATUS current
    DESCRIPTION
        "The group of objects supporting management of Qos scheduler overrides
         for release 13.0 on Nokia SROS series systems."
    ::= { tmnxSvcGroups 445 }

tmnxSvcTlsProxyArpGroup OBJECT-GROUP
    OBJECTS {
        svcTlsProxyArpCfgTblLastChngd,
        svcTlsProxyArpCfgRowStatus,
        svcTlsProxyArpCfgLastChgd,
        svcTlsProxyArpCfgAdminState
    }
    STATUS      current
    DESCRIPTION
        "The group of objects supporting management of proxy ARP
         capabilities on Nokia SROS series systems."
    ::= { tmnxSvcGroups 446 }

tmnxSvcVprnV13v0Group OBJECT-GROUP
    OBJECTS {
        svcVprnInfoTableLastChanged,
        svcVprnInfoEntryLastChanged,
        svcNetIngQosPolicyId,
        svcNetIngQosFPQGrp,
        svcNetIngQosFPQGrpInstanceId,
        svcNetIngIPFilterId,
        svcNetIngIPv6FilterId
    }
    STATUS      current
    DESCRIPTION
        "The group of objects supporting management of VPRN network
         capabilities on Nokia SROS series systems for release 13.0."
    ::= { tmnxSvcGroups 447 }


tmnxSvcTlsProxyArpEnhGroup OBJECT-GROUP
    OBJECTS {
        svcTlsProxyArpDynPopulate,
        svcTlsProxyArpAgeTime,
        svcTlsProxyArpSendRefresh,
        svcTlsProxyArpAntiSpoofingMac,
        svcTlsProxyArpAntiSpoofHoldDown,
        svcTlsProxyArpDupDetectWindow,
        svcTlsProxyArpAntiSpoofNumMoves,
        svcTlsProxyArpUnknReqFloodEvpn,
        svcTlsProxyArpStaticTblLastChngd,
        svcTlsProxyArpStaticRowStatus,
        svcTlsProxyArpStaticLastChgd,
        svcTlsProxyArpStaticMac,
        svcTlsProxyArpTableSize,
        svcTlsProxyArpGarpFloodEvpn
    }
    STATUS      current
    DESCRIPTION
        "The group of objects supporting management of enhanced proxy ARP 
         capabilities on Nokia SROS series systems."
    ::= { tmnxSvcGroups 448 }

tmnxSvcTlsEvpnProxyArpGroup OBJECT-GROUP
    OBJECTS {
        svcTlsProxyArpType,
        svcTlsProxyArpLastChgd,
        svcTlsProxyArpStatus,
        svcTlsProxyArpCount
    }
    STATUS      current
    DESCRIPTION
        "The group of objects supporting management of BGP EVPN and enhanced
         proxy ARP capabilities on Nokia SROS series systems."
    ::= { tmnxSvcGroups 449 }

tmnxSvcIesIfV13v0Group OBJECT-GROUP
    OBJECTS {
        iesIfSuppressAaSub,
        iesGrpIfDiameterAuthPolicy,         
        tmnxIesIfIpv6IpoeDhcp6Hosts,
        tmnxIesIfIpv6PppDhcp6Hosts,
        tmnxIesIfIpv6PppSLAACHosts, 
        tmnxIesIfIpv6IpoeSLAACHosts,
        tmnxIesIfIpv6StaticHostsUp,       
        iesIfIpv6Dhcp6UserIdent,
        iesGrpIfIpv6AutoReply,
        svcIfSapCfgAntiSpoof,
        iesIfIPv6Dhcp6PDManagedRouteNH
    }
    STATUS      current
    DESCRIPTION
        "The group of objects supporting management of Services IES
         interface capabilities on Nokia SROS series systems
         in release 13.0."
    ::= { tmnxSvcGroups 450 }

svcTlsProxyArpNotifGroup NOTIFICATION-GROUP
    NOTIFICATIONS {
        svcTlsProxyArpDupDetect, 
        svcTlsProxyArpDupClear,
        svcTlsProxyArpSysHiUsgSet,
        svcTlsProxyArpSysHiUsgClr,
        svcTlsProxyArpSvcHiUsgSet,
        svcTlsProxyArpSvcHiUsgClr
    }
    STATUS      current
    DESCRIPTION
        "The group of objects supporting management of VPLS proxy ARP/ND feature
         in release 13.0."
    ::= { tmnxSvcGroups 452 }


svcBgpEvpnMplsGroup OBJECT-GROUP
    OBJECTS {
        svcBgpEvpnMplsTableLastChanged,
        svcBgpEvpnEvi,
        svcBgpEvpnMplsLastChanged,
        svcBgpEvpnMplsForceVlanVcFwding,
        svcBgpEvpnMplsControlWord,
        svcBgpEvpnMplsShgName,
        tlsFdbEvpnMplsTEPAddrType,
        tlsFdbEvpnMplsTEPAddr,
        tlsFdbEvpnMplsLabel,
        svcEvpnMplsTEPAddrType,
        svcEvpnMplsTEPAddress,
        svcEvpnMplsTEPNumEvpnMplsDest,
        svcEvpnMplsTEPNumESDest,
        svcEvpnMplsTEPNumESBMacDest,
        svcTlsBgpEvpnABTnlTblLastChanged,
        svcTlsBgpEvpnAutoBindTnlLastChg,
        svcTlsBgpEvpnAutoBindTnlLdp,
        svcTlsBgpEvpnAutoBindTnlBgp,
        svcTlsBgpEvpnAutoBindTnlRsvpTe,
        svcTlsBgpEvpnAutoBindTnlSrIsis,
        svcTlsBgpEvpnAutoBindTnlSrOspf,
        svcTlsBgpEvpnAutoBndTnlStatus,
        svcEvpnMplsTEPEgrLblTEPAddrType,
        svcEvpnMplsTEPEgrLblTEPAddress,
        svcEvpnMplsTEPEgrLblTEPLabel,
        svcEvpnMplsTEPEgrLblNumMACs,
        svcEvpnMplsTEPEgrLblInMcastList,
        svcTlsBgpOperImportRteTgtOrigin,
        svcTlsBgpOperImportRteTarget,
        svcTlsBgpOperExportRteTgtOrigin,
        svcTlsBgpOperExportRteTarget,
        svcBgpEvpnMplsIngressLabel,
        svcBgpEvpnMplsIngressBumLabel,
        svcEvpnMplsTEPEgrLblLastChanged,
        svcEvpnMplsTEPEgrLblTunnelType,
        svcBgpEvpnMplsAdminState
    }
    STATUS current
    DESCRIPTION
        "The group of objects supporting service BGP EVPN (Ethernet - VPN)
         MPLS feature on Nokia SROS series systems release 13.0."
    ::={ tmnxSvcGroups 454 } 

svcBgpEvpnMplsMhGroup OBJECT-GROUP
    OBJECTS {
        svcBgpEvpnMplsIngressRepBumLabel,
        svcBgpEvpnMplsMaxEcmpRoutes,
        tmnxSvcSysBgpEvpnRD,
        tmnxSvcSysEthSegRowStatus,
        tmnxSvcSysEthSegLastChg,
        tmnxSvcSysEthSegAdminState,
        tmnxSvcSysEthSegEsi,
        tmnxSvcSysEthSegMultiHoming,
        tmnxSvcSysEthSegSvcCarving,
        tmnxSvcSysEthSegLagId,
        tmnxSvcSysEthSegPortId,
        tmnxSvcSysEthSegSdpId,
        tmnxSvcSysEthSegSourceBMacLSB,
        tmnxSvcSysEthSegBMacTblSize,
        tmnxSvcSysEthSegBMacTblEntries,
        tmnxSvcSysEthSegOperMultiHoming,
        tmnxSvcSysEthSegTblLastChanged,
        svcEthSegCarvEviRngTblLastChgd,
        svcEthSegCarvIsidRngTblLastChgd,
        svcEthSegCarvEviRngRowStatus,
        svcEthSegCarvEviRngLastChg,
        svcEthSegCarvEviRngTo,
        svcEthSegCarvIsidRngRowStatus,
        svcEthSegCarvIsidRngLastChg,
        svcEthSegCarvIsidRngTo,
        tmnxSvcSysEthSegEsActTimer,
        svcEvpnMHEthSegEviIsDF,
        svcEvpnMHEthSegIsidIsDF,
        svcEvpnMHEthSegEviActTimRem,
        svcEvpnMHEthSegIsidActTimRem,
        svcEvpnMHEthSegEviSvcId,
        svcEvpnMHEthSegIsidSvcId,
        svcEvpnMHEthSegEviDFLastChanged,
        svcEvpnMHEthSegIsidDFLastChanged,
        tlsFdbEvpnMplsEthSegId,
        svcEvpnMplsESDestTEPLabel,
        svcEvpnMplsPbbESDestTEPLabel,
        svcSysEthSegBMacAddress,
        tmnxSvcSysEthSegOperState,
        tmnxSvcSysEthSegSHGLabel,
        svcEvpnMplsESDestTEPLastChanged,
        svcEvpnMplsPbbESDestTEPLstChg,
        svcEvpnMHEthSegEviDFCndtAdded,
        svcEvpnMHEthSegIsidDFCndtAdded,
        svcEvpnMplsESDestTEPTunnelType,
        svcEvpnMplsPbbESDestTEPTnlType,
        svcEvpnMplsESDestNumMacs,
        svcEvpnMplsPbbESegDestNumMacs,
        svcNumEvpnMHStandbySaps,
        svcEvpnMplsESDestLastChanged,
        svcEvpnMplsPbbESegDestLstChg
    }
    STATUS current
    DESCRIPTION
        "The group of objects supporting service BGP EVPN (Ethernet - VPN)
         MPLS Multi Home feature on Nokia SROS series systems
         release 13.0."
    ::={ tmnxSvcGroups 455 }


svcEvpnMplsNotifGroup NOTIFICATION-GROUP
    NOTIFICATIONS {
        svcEvpnMplsTEPHiUsageRaised,
        svcEvpnMplsTEPHiUsageCleared,
        svcEvpnMplsTEPEgrBndSysHiUsgSet,
        svcEvpnMplsTEPEgrBndSysHiUsgClr,
        svcEvpnMplsTEPEgrBndSvcHiUsgSet,
        svcEvpnMplsTEPEgrBndSvcHiUsgClr
    }
    STATUS current
    DESCRIPTION
       "The group notifications supporting service BGP EVPN MPLS 
       feature on Nokia SROS series systems release 13.0."
    ::={ tmnxSvcGroups 457 }

tmnxSvcTlsMFibV13v0Group OBJECT-GROUP
    OBJECTS {
      tlsMFibNgFwdOrBlk,
      tlsMFibNgSvcId
    }
    STATUS      current
    DESCRIPTION
        "The group of objects supporting management of Services TLS MFib
         capabilities on Nokia SROS 13.0 series systems."
    ::= { tmnxSvcGroups 458 }

svcSpiLoadBalGroup OBJECT-GROUP
    OBJECTS {
        svcTlsExtSpiLoadBalancing,
        svcTmplTlsSpiLoadBalancing
    }
    STATUS      current
    DESCRIPTION
        "The group of objects supporting management of SPI load-balancing
         feature capabilities on Nokia SROS 13.0 series systems."
    ::= { tmnxSvcGroups 459 }

svcRipListenerGroup  OBJECT-GROUP
    OBJECTS {
        svcDhcpLeaseRipPlcyName,
        svcDhcpLeaseRipListenerStatus,
        svcArpHostRipPlcyName,
        svcArpHostRipListenerStatus
    }
    STATUS      current
    DESCRIPTION
        "The group of objects supporting management of RIP listener feature
         in Nokia SROS 13.0 series systems."
    ::= { tmnxSvcGroups 461 }

tmnxSvcQosRateV13v0Group OBJECT-GROUP
    OBJECTS {
        custMultSvcSiteEgrAggRateLimit
  }
    STATUS      current
    DESCRIPTION
        "The group of objects supporting management of services QoS capabilities
         for release 13.0 on Nokia SROS series systems."
    ::= { tmnxSvcGroups 462 }

tmnxSvcGrpIfGroup  OBJECT-GROUP
    OBJECTS {
        tmnxSvcGrpIfVRouterId
  }
    STATUS      current
    DESCRIPTION
        "The group of objects supporting the tmnxSvcGrpIfTable
         on Nokia SROS series systems."
    ::= { tmnxSvcGroups 463 }


svcTeidLoadBalGroup OBJECT-GROUP
    OBJECTS {
        svcTlsExtTeidLoadBalancing,
        svcTmplTlsTeidLoadBalancing
    }
    STATUS      current
    DESCRIPTION
        "The group of objects supporting management of TE-ID load-balancing
         feature capabilities on Nokia SROS 13.0 series systems."
    ::= { tmnxSvcGroups 464 }

svcBgpMHSiteGroup OBJECT-GROUP
    OBJECTS {
       svcTlsSiteIdMinDnTimer,
       svcTlsSiteIdMinDnTimerRemain,
       svcVllSiteIdMinDnTimer,
       svcVllSiteIdMinDnTimerRemain
    }
    STATUS        current
    DESCRIPTION
        "A group of objects supporting service BGP multi-homing site feature
         on Nokia SROS series systems."
    ::= { tmnxSvcGroups 465 }

svcSiteMinDnTimerNotifyObjsGroup OBJECT-GROUP
    OBJECTS {
       svcNotifSiteName,
       svcNotifSiteMinDnTimer,
       svcNotifSiteMinDnTimerRemain,
       svcNotifSiteMinDnTimerState
    }
    STATUS        current
    DESCRIPTION
        "A group of notification objects supporting service site
         minimum-down-timer feature on Nokia SROS series systems."
    ::= { tmnxSvcGroups 466 }

svcSiteMinDnTimerNotifGroup NOTIFICATION-GROUP
    NOTIFICATIONS {
        svcSiteMinDnTimerStateChg
    }
    STATUS current
    DESCRIPTION
       "The group of notifications supporting service site
        minimum-down-timer feature on Nokia SROS series systems."
    ::={ tmnxSvcGroups 467 }
    
tmnxSvcShcvPolicyGroup OBJECT-GROUP
    OBJECTS {
        iesIfShcvPolicy,
        iesIfShcvPolicyIpv4,
        iesIfShcvPolicyIpv6,
        svcTlsShcvPolicyIpv4
    }
    STATUS      current
    DESCRIPTION
        "The group of objects supporting management of 
         references to Subscriber Host Connectivity Verification (SHCV) policies
         in Nokia SROS series systems."
    ::= { tmnxSvcGroups 468 }


tmnxSvcV13v0Group OBJECT-GROUP
    OBJECTS {
      custCreationOrigin,
      svcNumEntries,
      svcId,
      svcRowStatus,
      svcType,
      svcCustId,
      svcIpRouting,
      svcDescription,
      svcMtu,
      svcAdminStatus,
      svcOperStatus,
      svcNumSaps,
      svcNumSdps,
      svcLastMgmtChange,
      svcDefMeshVcId,
      svcVpnId,
      svcVRouterId,
      -- svcAutoBind,
      svcLastStatusChange,
      svcVllType,
      svcMgmtVpls,
      svcRadiusDiscovery,
      svcVcSwitching,
      svcVplsType,
      svcTotalFdbMimDestIdxEntries,
      svcDhcpLeaseTerminationType,
      tmnxSvcDhcpMRtStatus,
      tmnxSvcDhcpMRtMetric,
      tmnxSvcDhcpMRtPreference,
      tmnxSvcDhcpMRtTag,
      svcBgpEvpnCfmMacAdvertisement,
      svcDhcpLeaseIpoeSessionHost,
      svcDhcpLeasePppSession
    }
    STATUS      current
    DESCRIPTION
        "The group of objects supporting management of Services 
         general capabilities on Nokia SROS series systems
         that were added in release R13.0."
    ::= { tmnxSvcGroups 469 }

tmnxSvcObsoletedV13v0Group OBJECT-GROUP
    OBJECTS {
        svcAutoBind
    }
    STATUS      current
    DESCRIPTION
        "The group of objects supporting management of services feature
         on Nokia SROS series systems release R13.0."
    ::= { tmnxSvcGroups 470 }

svcTlsProxyArpNotifyObjsGroup OBJECT-GROUP
    OBJECTS {
       svcNotifTlsProxyMacAddr
    }
    STATUS        current
    DESCRIPTION
        "A group of notification objects supporting service proxy ARP/ND 
         feature on Nokia SROS series systems."
    ::= { tmnxSvcGroups 471 }

tmnxCustV13v0Group OBJECT-GROUP
    OBJECTS {
      custNumEntries,
      custNextFreeId,
      custId,
      custRowStatus,
      custDescription,
      custContact,
      custPhone,
      custLastMgmtChange,
      custMultSvcSiteName,
      custMultSvcSiteRowStatus,
      custMultSvcSiteDescription,
      custMultSvcSiteScope,
      custMultSvcSiteAssignment,
      custMultSvcSiteIngressSchedulerPolicy,
      custMultSvcSiteEgressSchedulerPolicy,
      custMultSvcSiteLastMgmtChange,
      custMultSvcSiteTodSuite,
      custMultSvcSiteCurrentIngrSchedPlcy,
      custMultSvcSiteCurrentEgrSchedPlcy,
      custMultSvcSiteIntendedIngrSchedPlcy,
      custMultSvcSiteIntendedEgrSchedPlcy,
      custMultSvcSiteFrameBasedAccnt,
      custIngQosSchedStatsForwardedPackets,
      custIngQosSchedStatsForwardedOctets,
      custEgrQosSchedStatsForwardedPackets,
      custEgrQosSchedStatsForwardedOctets,
      custIngQosPortSchedFwdPkts,
      custIngQosPortSchedFwdOctets,
      custEgrQosPortSchedFwdPkts,
      custEgrQosPortSchedFwdOctets,
      custMssIngQosSRowStatus,
      custMssIngQosSLastMgmtChange,
      custMssIngQosSOverrideFlags,
      custMssIngQosSSummedCIR,
      custMssEgrQosSRowStatus,
      custMssEgrQosSLastMgmtChange,
      custMssEgrQosSOverrideFlags,
      custMssEgrQosSSummedCIR,
      custIngSchedPlcyStatsFwdPkt,
      custIngSchedPlcyStatsFwdOct,
      custEgrSchedPlcyStatsFwdPkt,
      custEgrSchedPlcyStatsFwdOct,
      custIngSchedPlcyPortStatsFwdPkt,
      custIngSchedPlcyPortStatsFwdOct,
      custEgrSchedPlcyPortStatsFwdPkt,
      custEgrSchedPlcyPortStatsFwdOct,
      custMultSvcSiteFrameBasedAccnt,
      custMultSvcSiteSubscriberMss
    }
    STATUS      current
    DESCRIPTION
        "The group of objects supporting management of Services customers
         general capabilities on Nokia SROS 13.0 series systems."
    ::= { tmnxCustGroups 472 }


tmnxCustObsoletedV13v0Group OBJECT-GROUP
    OBJECTS {
      custMultSvcSiteEgressAggRateLimit
    }
    STATUS      current
    DESCRIPTION
        "The group of obsoleted objects supporting management of Services
         customers general capabilities on Nokia SROS
         13.0 series systems."
    ::= { tmnxCustGroups 473 }

svcAutoBindTunnelGroup OBJECT-GROUP
    OBJECTS {
        svcVprnBgpAutoBindLastChg,
        svcVprnBgpAutoBindLdp,
        svcVprnBgpAutoBindRsvpTe,
        svcVprnBgpAutoBindSrIsis,
        svcVprnBgpAutoBindSrOspf,
        svcVprnBgpAutoBindGre,
        svcVprnBgpAutoBindTblLastChgd,
        svcVprnBgpAutoBindTnlStatus
    }
    STATUS current
    DESCRIPTION
        "The group of objects supporting service BGP EVPN (Ethernet - VPN)
         MPLS feature on Nokia SROS series systems release 13.0."
    ::={ tmnxSvcGroups 474 } 


tmnxSvcTlsProxyNdGroup OBJECT-GROUP
    OBJECTS {
        svcTlsProxyNdDynPopulate,
        svcTlsProxyNdAgeTime,
        svcTlsProxyNdSendRefresh,
        svcTlsProxyNdAntiSpoofingMac,
        svcTlsProxyNdAntiSpoofHoldDown,
        svcTlsProxyNdDupDetectWindow,
        svcTlsProxyNdAntiSpoofNumMoves,
        svcTlsProxyNdUnknSolFloodEvpn,
        svcTlsProxyNdStaticTblLastChngd,
        svcTlsProxyNdStaticRowStatus,
        svcTlsProxyNdStaticLastChgd,
        svcTlsProxyNdStaticMac,
        svcTlsProxyNdCfgTblLastChngd,
        svcTlsProxyNdCfgRowStatus,
        svcTlsProxyNdCfgLastChgd,
        svcTlsProxyNdCfgAdminState,
        svcTlsProxyNdTblLastChngd,
        svcTlsProxyNdMacAddr,
        svcTlsProxyNdType,
        svcTlsProxyNdLastChgd,
        svcTlsProxyNdStatus,
        svcTlsProxyNdTableSize,
        svcTlsProxyNdRtrUnSolNAFloodEvpn,
        svcTlsProxyNdHstUnSolNAFloodEvpn,
        svcTlsProxyNdEvpnNdAdvRouter,
        svcTlsProxyNdStaticIsRouter,
        svcTlsProxyNdIsRouter,
        svcTlsProxyNdCount
    }
    STATUS      current
    DESCRIPTION
        "The group of objects supporting management of enhanced proxy ND
         capabilities on Nokia SROS series systems."
    ::= { tmnxSvcGroups 475 }

svcTlsProxyNdNotifGroup NOTIFICATION-GROUP
    NOTIFICATIONS {
        svcTlsProxyNdDupDetect,
        svcTlsProxyNdDupClear,
        svcTlsProxyNdSysHiUsgSet,
        svcTlsProxyNdSysHiUsgClr,
        svcTlsProxyNdSvcHiUsgSet,
        svcTlsProxyNdSvcHiUsgClr
    }
    STATUS      current
    DESCRIPTION
        "The group of objects supporting management of VPLS proxy ND feature
         in release 13.0."
    ::= { tmnxSvcGroups 476 }

svcV13v0NotifyObjsGroup OBJECT-GROUP
    OBJECTS {
       svcNotifyMacAddress,
       svcNotifyText
    }
    STATUS        current
    DESCRIPTION
        "A group of notification objects added in release 13.0
         of Nokia SROS series systems."
    ::= { tmnxSvcGroups 477 }
    
svcArpHostNotifGroup NOTIFICATION-GROUP
    NOTIFICATIONS {
        svcArpHostOverride
    }
    STATUS      current
    DESCRIPTION
        "The group of notifications supporting Subscriber Host Connectivity Verification (SHCV) policies."
    ::= { tmnxSvcGroups 478 }


svcEvpnDestNotifGroup NOTIFICATION-GROUP
    NOTIFICATIONS {
        svcEvpnDestSysHiUsgSet,
        svcEvpnDestSysHiUsgClr
    }
    STATUS  current
    DESCRIPTION
        "The group notifications supporting service BGP EVPN MPLS and VXLAN
        feature on Nokia SROS series systems release 13.0. "
        ::={tmnxSvcGroups 480 }


tmnxSvcDhcpV13v0Group OBJECT-GROUP
    OBJECTS {
        svcDhcpLeaseOvrSummedCIR
    }
    STATUS      current
    DESCRIPTION
        "The group of objects supporting management of Services DHCP Lease
         capabilities on Nokia SROS series systems added in
         release 13.0."
    ::= { tmnxSvcGroups 484 }

tmnxArpHostV13v0Group OBJECT-GROUP
    OBJECTS {
        svcArpHostOvrSummedCIR
    }
    STATUS      current
    DESCRIPTION
        "The group of objects supporting management of Services ARP hosts
         capabilities on Nokia SROS series systems added in
         release 13.0."
    ::= { tmnxSvcGroups 485 }

svcEvpnMhEsDFNotifGroup NOTIFICATION-GROUP
    NOTIFICATIONS {
       svcEvpnMHEsEviDFStateChgd,
       svcEvpnMHEsIsidDFStateChgd
    }
    STATUS current
    DESCRIPTION
        "The group notification supporting service EVPN MH feature on
        Nokia SROS series systems release 13.0."
    ::= { tmnxSvcGroups 486 } 

END
