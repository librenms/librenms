DOCS-CABLE-DEVICE-TRAP-MIB DEFINITIONS ::= BEGIN
IMPORTS
MODULE-IDENTITY,
NOTIFICATION-TYPE
FROM SNMPv2-SMI
MODULE-COMPLIANCE,
NOTIFICATION-GROUP
FROM SNMPv2-CONF
docsDev,
--docsDevBase,
docsDevEvLevel,
docsDevEvId,
docsDevEvText,
docsDevSwFilename,
docsDevSwServer,
docsDevServerDhcp,
docsDevServerTime,
docsDevNotification
FROM DOCS-CABLE-DEVICE-MIB --RFC2669
docsIfCmCmtsAddress,
docsIfCmtsCmStatusMacAddress,
docsIfDocsisBaseCapability,
docsIfCmStatusDocsisOperMode,
docsIfCmStatusModulationType,docsIfCmtsCmStatusDocsisRegMode,
docsIfCmtsCmStatusModulationType
FROM DOCS-IF-MIB -- draft-ietf-ipcdn-docs-rfmibv2-02
docsIfDocsisCapability, -- deprecated
docsIfDocsisOperMode, -- deprecated
docsIfCmtsCmStatusDocsisMode -- deprecated
FROM DOCS-IF-EXT-MIB -- deprecated
ifPhysAddress
FROM IF-MIB;
docsDevTrapMIB MODULE-IDENTITY
LAST-UPDATED "0202250000Z"
ORGANIZATION "Cisco Systems, Inc."
CONTACT-INFO "
Junming Gao
Cisco Systems Inc
<jgao@ cisco. com>
"
DESCRIPTION
"Modified by David Raftus (david.raftus@imedia.com) to deprecate
trap definition objects originating from the docsIfExt MIB.
Corresponding objects from the Docsis 2.0 RF MIB draft were added
to the trap definitions."
REVISION "000926000000Z"
DESCRIPTION
"The CABLE DEVICE TRAP MIB is an extension of the
CABLE DEVICE MIB defined in RFC2669.
It defines various trap objects for both cable
modem and cable modem termination systems.
Two groups of SNMP notification objects are defined.
One group is for notifying cable modem events and one group
for notifying cable modem termination system events.
Common to all CM notification objects (traps) is that
their OBJECTS statements contain information
about the event priority, the event Id, the event message
body, the CM DOCSIS capability, the CM DOCSIS QOS level, the CM
DOCSIS upstream modulation type, the cable interface MAC address
of the cable modem and the cable card MAC address of the CMTS to
which the modem is connectede.
These objects are docsDevEvLevel, docsDevId, docsDevEvText,
docsIfDocsisBaseCapability, docsIfCmStatusDocsisOperMode,
docsIfCmStatusModulationType,ifPhysAddress and
docsIfCmCmtsAddress. The values of docsDevEvLevel, docsDevId, and
docsDevEvText are from the entry which logs this event in the
docsDevEventTable, which is defined in
DOCS-CABLE-DEVICE-MIB of RFC2669. The docsIfDocsisBaseCapability,
docsIfCmStatusDocsisOperMode, and docsIfCmStatusModulationType
are defined in the DOCS-IF-MIB.
The ifPhysAddress value is the MAC address of the cable
interface of this cable modem. The docsIfCmCmtsAddress
specifies the MAC address of the CMTS (if there is a cable.card/ interface in the CMTS, then it is actually the
cable interface interface MAC address to which the CM is
connected).
Individual CM trap may contain additional objects to
provide necessary information.
Common to all CMTS notification objects (traps) is that their
OBJECTS statements contain information about the event priority,
the event Id, the event message body, the connected CM DOCSIS QOS
status, the connected CM DOCSIS modulation type, the CM cable
interface MAC address, the CMTS DOCSIS capability, and
the CMTS MAC address.
These objects are docsDevEvLevel, docsDevId, docsDevEvText,
docsIfCmtsCmStatusDocsisRegMode,
docsIfCmtsCmStatusModulationType, docsIfCmtsCmStatusMacAddress,
docsIfDocsisBaseCapability, and ifPhysAddress. The values of
docsDevEvLevel, docsDevId, and docsDevEvText are
similar to those in CM traps. The values of
docsIfCmtsCmStatusDocsisRegMode,
docsIfCmtsCmStatusModulationType, and
docsIfCmtsCmStatusMacAddress are from the
docsIfCmtsCmStatusEntry (defined in DOCS-IF-MIB)
corresponding to a connected CM. The docsIfDocsisBaseCapability
indicates the CMTS DOCSIS capability.
The ifPhysAddress value is the CMTS MAC address (if there is a
cable
card/ interface in the CMTS, then it is actually the MAC address
of the cable
interface which connected to the CM).
"
::= { docsDev 10 }
--
--docsDevNotification OBJECT IDENTIFIER ::= { docsDev 2 }
--
docsDevTraps OBJECT IDENTIFIER ::= { docsDevNotification 1 }
docsDevTrapControl OBJECT IDENTIFIER ::= { docsDevTraps 1}
docsDevCmTraps OBJECT IDENTIFIER ::= { docsDevTraps 2 0 }
docsDevCmtsTraps OBJECT IDENTIFIER ::= { docsDevTraps 3 0 }
docsDevCmTrapControl OBJECT-TYPE
SYNTAX BITS {
cmInitTLVUnknownTrap( 0),
cmDynServReqFailTrap( 1),
cmDynServRspFailTrap( 2),
cmDynServAckFailTrap( 3),
cmBpiInitTrap( 4),
cmBPKMTrap( 5),
cmDynamicSATrap( 6),
cmDHCPFailTrap( 7),
cmSwUpgradeInitTrap( 8),
cmSwUpgradeFailTrap( 9),
cmSwUpgradeSuccessTrap( 10),
cmSwUpgradeCVCTrap( 11),
cmTODFailTrap( 12),
cmDCCReqFailTrap( 13),
cmDCCRspFailTrap( 14),
cmDCCAckFailTrap( 15)
}
MAX-ACCESS read-write
STATUS current
DESCRIPTION
"The object is used to enable CM traps. From left to right,
the set bit indicates the corresponding CM trap is enabled.
For example, if the first bit is set, then
docsDevCmInitTLVUnknownTrap is enabled. If it is zero,
the trap is disabled.
"
DEFVAL { '00'h }
::= { docsDevTrapControl 1 }
docsDevCmtsTrapControl OBJECT-TYPE
SYNTAX BITS {
cmtsInitRegReqFailTrap( 0),
cmtsInitRegRspFailTrap( 1),
cmtsInitRegAckFailTrap( 2),
cmtsDynServReqFailTrap( 3),
cmtsDynServRspFailTrap( 4),
cmtsDynServAckFailTrap( 5),
cmtsBpiInitTrap( 6),
cmtsBPKMTrap( 7),
cmtsDynamicSATrap( 8),
cmtsDCCReqFailTrap( 9),
cmtsDCCRspFailTrap( 10),
cmtsDCCAckFailTrap( 11)
}
MAX-ACCESS read-write
STATUS current
DESCRIPTION
"The object is used to enable CMTS traps. From left to right,
the set bit indicates the corresponding CMTS trap is enabled.
For example, if the first bit is set, then
docsDevCmtsInitRegRspFailTrap is enabled. If it is zero,
the trap is disabled.
"
DEFVAL { '00'h }
::= { docsDevTrapControl 2 }
docsDevCmInitTLVUnknownTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"Event due to detection of unknown TLV during
the TLV parsing process.
The values of docsDevEvLevel, docsDevId, and
docsDevEvText are from the entry which logs this event
in the docsDevEventTable. The docsIfDocsisBaseCapability
indicates the DOCSIS version information. The
docsIfCmStatusDocsisOperMode indicates the QOS level of the CM,
while the docsIfCmStatusModulationType indicates the upstream
modulation methodology used by the CM.
The ifPhysAddress value is the MAC address of the cable interface
of this cable modem.
The docsIfCmCmtsAddress specifies the MAC address
of the CMTS to which the CM is connected (if there is a cable
card/ interface in the CMTS, then it is actually the MAC address
of the cable
interface which connected to the CM).
This part of information is uniformed across all CM traps.
"
::= { docsDevCmTraps 1 }
docsDevCmDynServReqFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic service
request happened during the dynamic services process.
"
::= { docsDevCmTraps 2 }
docsDevCmDynServRspFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic service
response happened during the dynamic services process.
"
::= { docsDevCmTraps 3}
docsDevCmDynServAckFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic service
acknowledgement happened during the dynamic services process.
"
::= { docsDevCmTraps 4}
docsDevCmBpiInitTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a BPI initialization
attempt happened during the registration process.
"
::= { docsDevCmTraps 5 }
docsDevCmBPKMTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a BPKM operation.
"
::= { docsDevCmTraps 6 }
docsDevCmDynamicSATrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic security
association operation.
"
::= { docsDevCmTraps 7 }
docsDevCmDHCPFailTrap NOTIFICATION-TYPE
OBJECTS { docsDevEvLevel,
docsDevEvId,
docsDevEvText,
docsIfDocsisCapability, -- deprecated
docsIfDocsisOperMode, -- deprecated
ifPhysAddress,
docsIfCmCmtsAddress,
docsDevServerDhcp,
docsIfDocsisBaseCapability,
docsIfCmStatusDocsisOperMode,
docsIfCmStatusModulationType }
STATUS current
DESCRIPTION
"An event to report the failure of a DHCP server.
The value of docsDevServerDhcp is the IP address
of the DHCP server.
"
::= { docsDevCmTraps 8 }
docsDevCmSwUpgradeInitTrap NOTIFICATION-TYPE
OBJECTS { docsDevEvLevel,
docsDevEvId,
docsDevEvText,
docsIfDocsisCapability, -- deprecated
docsIfDocsisOperMode, -- deprecated
ifPhysAddress,
docsIfCmCmtsAddress,
docsDevSwFilename,
docsDevSwServer,
docsIfDocsisBaseCapability,
docsIfCmStatusDocsisOperMode,
docsIfCmStatusModulationType }
STATUS current
DESCRIPTION
"An event to report a software upgrade initiated
event. The values of docsDevSwFilename, and
docsDevSwServer indicate the software image name
and the server IP address the image is from.
"
::= { docsDevCmTraps 9 }
docsDevCmSwUpgradeFailTrap NOTIFICATION-TYPE
OBJECTS { docsDevEvLevel,
docsDevEvId,
docsDevEvText,
docsIfDocsisCapability, -- deprecated
docsIfDocsisOperMode, -- deprecated
ifPhysAddress,
docsIfCmCmtsAddress,
docsDevSwFilename,
docsDevSwServer,
docsIfDocsisBaseCapability,
docsIfCmStatusDocsisOperMode,
docsIfCmStatusModulationType }
STATUS current
DESCRIPTION
"An event to report the failure of a software upgrade
attempt. The values of docsDevSwFilename, and
docsDevSwServer indicate the software image name.and the server IP address the image is from.
"
::= { docsDevCmTraps 10 }
docsDevCmSwUpgradeSuccessTrap NOTIFICATION-TYPE
OBJECTS { docsDevEvLevel,
docsDevEvId,
docsDevEvText,
docsIfDocsisCapability, -- deprecated
docsIfDocsisOperMode, -- deprecated
ifPhysAddress,
docsIfCmCmtsAddress,
docsDevSwFilename,
docsDevSwServer,
docsIfDocsisBaseCapability,
docsIfCmStatusDocsisOperMode,
docsIfCmStatusModulationType }
STATUS current
DESCRIPTION
"An event to report the Software upgrade success event.
The values of docsDevSwFilename, and
docsDevSwServer indicate the software image name
and the server IP address the image is from.
"
::= { docsDevCmTraps 11 }
docsDevCmSwUpgradeCVCFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of the verification
of code file happened during a secure software upgrade
attempt.
"
::= { docsDevCmTraps 12 }
docsDevCmTODFailTrap NOTIFICATION-TYPE
OBJECTS { docsDevEvLevel,
docsDevEvId,
docsDevEvText,
docsIfDocsisCapability, -- deprecated
docsIfDocsisOperMode, -- deprecated
ifPhysAddress,
docsIfCmCmtsAddress,
docsDevServerTime,
docsIfDocsisBaseCapability,
docsIfCmStatusDocsisOperMode,
docsIfCmStatusModulationType }
STATUS current
DESCRIPTION
"An event to report the failure of a time of day server.
The value of docsDevServerTime indicates the server IP
address.
"
::= { docsDevCmTraps 13 }
docsDevCmDCCReqFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic channel
change request happened during the dynamic channel
change process in the CM side.
"
::= { docsDevCmTraps 14 }
docsDevCmDCCRspFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic channel
change response happened during the dynamic channel
change process in the CM side.
"
::= { docsDevCmTraps 15 }
docsDevCmDCCAckFailTrap NOTIFICATION-TYPE
OBJECTS { docsDevEvLevel,
docsDevEvId,
docsDevEvText,
docsIfDocsisCapability, -- deprecated
docsIfDocsisOperMode, -- deprecated
ifPhysAddress,
docsIfCmCmtsAddress,
docsIfDocsisBaseCapability,
docsIfCmStatusDocsisOperMode,
docsIfCmStatusModulationType }
STATUS current
DESCRIPTION
"An event to report the failure of a dynamic channel
change acknowledgement happened during the dynamic channel
change process in the CM side.
"
::= { docsDevCmTraps 16}
docsDevCmtsInitRegReqFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a registration
request from CM happening during the CM initialization
process and detected on the CMTS side.
The values of docsDevEvLevel, docsDevId, and
docsDevEvText are from the entry which logs this event
in the docsDevEventTable. The docsIfCmtsCmStatusDocsisRegMode
and docsIfCmtsCmStatusMacAddress indicate the docsis.QOS version and the MAC address of the requesting CM. The
docsIfCmtsCmModulationType indicates the upstream modulation
methodology used by the connected CM.
The docsIfDocsisBaseCapability and ifPhysAddress
indicate the docsis version of the CMTS and the MAC
address of the CMTS (if there is a cable
card/ interface in the CMTS, then it is actually the MAC address
of the cable interface which connected to the CM) cable card
connected to the CM.
This part of information is uniformed across all CMTS traps.
"
::= { docsDevCmtsTraps 1 }
docsDevCmtsInitRegRspFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a registration
response happened during the CM initialization
process and detected in the CMTS side.
"
::= { docsDevCmtsTraps 2 }
docsDevCmtsInitRegAckFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a registration
acknowledgement from CM happened during the CM
initialization process and detected in the CMTS side.
"
::= { docsDevCmtsTraps 3 }
docsDevCmtsDynServReqFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic service
request happened during the dynamic services process
and detected in the CMTS side.
"
::= { docsDevCmtsTraps 4 }
docsDevCmtsDynServRspFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic service
response happened during the dynamic services process
and detected in the CMTS side.
"
::= { docsDevCmtsTraps 5 }
docsDevCmtsDynServAckFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic service
acknowledgement happened during the dynamic services
process and detected in the CMTS side.
"
::= { docsDevCmtsTraps 6 }
docsDevCmtsBpiInitTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a BPI initialization
attempt happened during the CM registration process
and detected in the CMTS side.
"
::= { docsDevCmtsTraps 7 }
docsDevCmtsBPKMTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a BPKM operation
which is detected in the CMTS side.
"
::= { docsDevCmtsTraps 8 }
docsDevCmtsDynamicSATrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic security
association operation which is detected in the CMTS side.
"
::= { docsDevCmtsTraps 9 }
docsDevCmtsDCCReqFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic channel
change request happened during the dynamic channel
change process in the CM side and detected in the
CMTS side.
"
::= { docsDevCmtsTraps 10 }
docsDevCmtsDCCRspFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic channel
change response happened during the dynamic channel
change process in the CMTS side.
"
::= { docsDevCmtsTraps 11 }
docsDevCmtsDCCAckFailTrap NOTIFICATION-TYPE
OBJECTS { docsDevEvLevel,
docsDevEvId,
docsDevEvText,
docsIfCmtsCmStatusDocsisMode, -- deprecated
docsIfCmtsCmStatusMacAddress,
docsIfDocsisCapability, -- deprecated
ifPhysAddress,
docsIfCmtsCmStatusDocsisRegMode,
docsIfDocsisBaseCapability,
docsIfCmtsCmStatusModulationType }
STATUS current
DESCRIPTION
"An event to report the failure of a dynamic channel
change acknowledgement happened during the dynamic channel
change process in the CMTS side.
"
::= { docsDevCmtsTraps 12}
--
--Conformance definitions
--
docsDevTrapConformance OBJECT IDENTIFIER ::= { docsDevTraps 4 }
docsDevTrapGroups OBJECT IDENTIFIER ::= { docsDevTrapConformance
1 }
docsDevTrapCompliances OBJECT IDENTIFIER ::= {
docsDevTrapConformance 2 }
docsDevCmTrapCompliance MODULE-COMPLIANCE
STATUS current
DESCRIPTION
"The compliance statement for Cable Modem Traps and Control"
MODULE --docsDevTrap
--mandatory groups
GROUP docsDevCmTrapControlGroup
DESCRIPTION
"Mandatory in CM."
GROUP docsDevCmNotificationGroup
DESCRIPTION
"Mandatory in Cable Modem."
::= { docsDevTrapCompliances 1 }
docsDevCmTrapControlGroup OBJECT-GROUP
OBJECTS {
docsDevCmTrapControl
}
STATUS current
DESCRIPTION
"CM must support docsDevCmTrapControl."
::= { docsDevTrapGroups 1 }
docsDevCmNotificationGroup NOTIFICATION-GROUP
NOTIFICATIONS {
docsDevCmInitTLVUnknownTrap,
docsDevCmDynServReqFailTrap,
docsDevCmDynServRspFailTrap,
docsDevCmDynServAckFailTrap,
docsDevCmBpiInitTrap,
docsDevCmBPKMTrap,
docsDevCmDynamicSATrap,
docsDevCmDHCPFailTrap,
docsDevCmSwUpgradeInitTrap,
docsDevCmSwUpgradeFailTrap,
docsDevCmSwUpgradeSuccessTrap,
docsDevCmSwUpgradeCVCFailTrap,
docsDevCmTODFailTrap,
docsDevCmDCCReqFailTrap,
docsDevCmDCCRspFailTrap,
docsDevCmDCCAckFailTrap
}
STATUS current
DESCRIPTION
"A collection of CM notifications providing device status and
control."
::= { docsDevTrapGroups 2 }
docsDevCmtsTrapCompliance MODULE-COMPLIANCE
STATUS current
DESCRIPTION
"The compliance statement for MCNS Cable Modems and
Cable Modem Termination Systems."
MODULE --docsDevTrap
--mandatory groups
GROUP docsDevCmtsTrapControlGroup
DESCRIPTION
"Mandatory in CMTS."
GROUP docsDevCmtsNotificationGroup
DESCRIPTION
"Mandatory in Cable Modem Termination Systems."
::= { docsDevTrapCompliances 2 }
docsDevCmtsTrapControlGroup OBJECT-GROUP
OBJECTS {
docsDevCmtsTrapControl
}
STATUS current
DESCRIPTION
"CMTS must support docsDevCmtsTrapControl."
::= { docsDevTrapGroups 3 }
docsDevCmtsNotificationGroup NOTIFICATION-GROUP
NOTIFICATIONS {
docsDevCmtsInitRegReqFailTrap,
docsDevCmtsInitRegRspFailTrap,
docsDevCmtsInitRegAckFailTrap ,
docsDevCmtsDynServReqFailTrap,
docsDevCmtsDynServRspFailTrap,
docsDevCmtsDynServAckFailTrap,
docsDevCmtsBpiInitTrap,
docsDevCmtsBPKMTrap,
docsDevCmtsDynamicSATrap,
docsDevCmtsDCCReqFailTrap,
docsDevCmtsDCCRspFailTrap,
docsDevCmtsDCCAckFailTrap
}
STATUS current
DESCRIPTION
"A collection of CMTS notifications providing device status and
control."
::= { docsDevTrapGroups 4 }
END
