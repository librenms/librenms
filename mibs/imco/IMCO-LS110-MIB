IMCO-LS110-MIB DEFINITIONS ::= BEGIN

IMPORTS
     MODULE-IDENTITY, OBJECT-TYPE,
     Counter32, Integer32, Gauge32,
     TimeTicks, IpAddress,
     enterprises
    FROM SNMPv2-SMI
    TRAP-TYPE FROM RFC-1215;
 

mib-AN-Dcz-SDS MODULE-IDENTITY
    LAST-UPDATED "201702090000Z"
    ORGANIZATION "ViaNet.sk"
    CONTACT-INFO
            "   Ivan Mochnac
                ViaNet
                -
                -
                SK EUROPE

                -
                vianet@vianet.sk"
    DESCRIPTION
            "The MIB module to describe PSMSmicro version of SDS."


    REVISION      "201702090000Z"
    DESCRIPTION
            "PSMSmicro, by ViaNet.sk."
    ::= { enterprises 33283 }


--
-- MIB file definition for device: PSMSmicro
--

sdsxpublic OBJECT IDENTIFIER ::= { mib-AN-Dcz-SDS 1 }

sdsBIGandSTSW   OBJECT IDENTIFIER ::= { sdsxpublic 30 }

-- ****************************************************************************

sdsOptoInput OBJECT IDENTIFIER ::= { sdsBIGandSTSW 2 }

opto1 OBJECT-TYPE
    SYNTAX  INTEGER {
                activeSignalPresent(0),
                noSignal(32768)
            }
    MAX-ACCESS  read-only
    STATUS      current
    DESCRIPTION
            "Current OPTO1 binary input status."
    ::= { sdsOptoInput 1 }

opto2 OBJECT-TYPE
    SYNTAX  INTEGER {
                activeSignalPresent(0),
                noSignal(1)
            }
    MAX-ACCESS  read-only
    STATUS      current
    DESCRIPTION
            "Current OPTO2 binary input status."
    ::= { sdsOptoInput 2 }

opto3 OBJECT-TYPE
    SYNTAX  INTEGER {
                activeSignalPresent(0),
                noSignal(2)
            }
    MAX-ACCESS  read-only
    STATUS      current
    DESCRIPTION
            "Current Mains (OPTO3) binary input status."
    ::= { sdsOptoInput 3 }

-- ****************************************************************************

sdsOutputRelays OBJECT IDENTIFIER ::= { sdsBIGandSTSW 3 }

sdsOutputRelay1 OBJECT IDENTIFIER ::= { sdsOutputRelays 1 }

sdsRE1state OBJECT-TYPE
    SYNTAX  INTEGER {
                off(0),
                activated(255)
            }
    MAX-ACCESS  read-write
    STATUS      current
    DESCRIPTION
            "Current RELAY 1 output status."
    ::= { sdsOutputRelay1 1 }

sdsOutputRelay2 OBJECT IDENTIFIER ::= { sdsOutputRelays 2 }

sdsRE2state OBJECT-TYPE
    SYNTAX  INTEGER {
                off(0),
                activated(255)
            }
    MAX-ACCESS  read-write
    STATUS      current
    DESCRIPTION
            "Current RELAY 2 output status."
    ::= { sdsOutputRelay2 1 }

sdsOutputRelay3 OBJECT IDENTIFIER ::= { sdsOutputRelays 3 }

sdsRE3state OBJECT-TYPE
    SYNTAX  INTEGER {
                off(0),
                activated(255)
            }
    MAX-ACCESS  read-write
    STATUS      current
    DESCRIPTION
            "Current RELAY 3 output status."
    ::= { sdsOutputRelay3 1 }    

-- ****************************************************************************

sdsADCinputs OBJECT IDENTIFIER ::= { sdsBIGandSTSW 5 }

sdsADCitem0 OBJECT IDENTIFIER ::= { sdsADCinputs 1 }

sdsTempSensValue OBJECT-TYPE
    SYNTAX      Gauge32
    MAX-ACCESS  read-only
    STATUS      current
    DESCRIPTION
            "Temperature Sensor (C) multiplied by 100."
    ::= { sdsADCitem0 3 }

sdsTempSensName OBJECT-TYPE
    SYNTAX      OCTET STRING
    MAX-ACCESS  read-only
    STATUS      current
    DESCRIPTION
            "User name for the analog temperature sensor."
    ::= { sdsADCitem0 4 }
 
-- ****************************************************************************

sdsADCvalues OBJECT IDENTIFIER ::= { sdsBIGandSTSW 7 }

sdsMaximumLoad OBJECT-TYPE
    SYNTAX    Integer32
    MAX-ACCESS  read-only
    STATUS      current
    DESCRIPTION
            "Maximum Load (W) multiplied by 10."
    ::= { sdsADCvalues 2 }

sdsAlarmText OBJECT-TYPE
    SYNTAX    OCTET STRING
    MAX-ACCESS  read-only
    STATUS      current
    DESCRIPTION
            "SDS Alarm Text."
    ::= { sdsADCvalues 3 }

sdsOutputVoltage1 OBJECT-TYPE
    SYNTAX    Integer32
    MAX-ACCESS  read-only
    STATUS      current
    DESCRIPTION
            "Output voltage U1 (V) multiplied by 100."
    ::= { sdsADCvalues 4 }

sdsOutputVoltage2 OBJECT-TYPE
    SYNTAX    Integer32
    MAX-ACCESS  read-only
    STATUS      current
    DESCRIPTION
            "Output voltage U2 (V) multiplied by 100."
    ::= { sdsADCvalues 5 }

sdsOutputCurrent OBJECT-TYPE
    SYNTAX    Integer32
    MAX-ACCESS  read-only
    STATUS      current
    DESCRIPTION
            "Output current I (A) multiplied by 10."
    ::= { sdsADCvalues 6 }

sdsBatteryCapacity OBJECT-TYPE
    SYNTAX    Integer32
    MAX-ACCESS  read-only
    STATUS      current
    DESCRIPTION
            "Battery Capacity (%) multiplied by 10."
    ::= { sdsADCvalues 7 }
    
sdsLoad OBJECT-TYPE
    SYNTAX    Integer32
    MAX-ACCESS  read-only
    STATUS      current
    DESCRIPTION
            "Load (%) multiplied by 10."
    ::= { sdsADCvalues 8 }
    
sdsCapTestTime OBJECT-TYPE
    SYNTAX    Integer32
    MAX-ACCESS  read-only
    STATUS      current
    DESCRIPTION
            "Time (min) of last Capacity Test."
    ::= { sdsADCvalues 9 }    

-- ****************************************************************************

sdsGeneralInfoEntry OBJECT IDENTIFIER ::= { sdsBIGandSTSW 8 }

sdsManufacturer OBJECT-TYPE
    SYNTAX    OCTET STRING
    MAX-ACCESS  read-only
    STATUS      current
    DESCRIPTION
            "Manufacturer of the device."
    ::= { sdsGeneralInfoEntry 80 }

sdsModel OBJECT-TYPE
    SYNTAX    OCTET STRING
    MAX-ACCESS  read-only
    STATUS      current
    DESCRIPTION
            "Model (type) of the device."
    ::= { sdsGeneralInfoEntry 81 }

sdsName OBJECT-TYPE
    SYNTAX    OCTET STRING
    MAX-ACCESS  read-only
    STATUS      current
    DESCRIPTION
            "Name/Location of the device."
    ::= { sdsGeneralInfoEntry 82 }

sdsSerialNumber OBJECT-TYPE
    SYNTAX    OCTET STRING
    MAX-ACCESS  read-only
    STATUS      current
    DESCRIPTION
            "Serial number of the device."
    ::= { sdsGeneralInfoEntry 83 }

sdsSoftware OBJECT-TYPE
    SYNTAX    OCTET STRING
    MAX-ACCESS  read-only
    STATUS      current
    DESCRIPTION
            "Software version of the device."
    ::= { sdsGeneralInfoEntry 84 }

-- ****************************************************************************

-- ****************************************************************************
-- TRAP-SDS-MICRO-MIB DEFINITIONS 
-- ****************************************************************************

opto1-trap TRAP-TYPE
	-- STATUS current
	ENTERPRISE mib-AN-Dcz-SDS
	VARIABLES { opto1 }
	DESCRIPTION "TRAP: optical input 1 status."
	::= 100

opto2-trap TRAP-TYPE
	-- STATUS current
	ENTERPRISE mib-AN-Dcz-SDS
	VARIABLES { opto2 }
	DESCRIPTION "TRAP: optical input 2 status."
	::= 101

opto3-trap TRAP-TYPE
	-- STATUS current
	ENTERPRISE mib-AN-Dcz-SDS
	VARIABLES { opto3 }
	DESCRIPTION "TRAP: optical input 3 status."
	::= 102

-- next

sdsRE1state-trap TRAP-TYPE
	-- STATUS current
	ENTERPRISE mib-AN-Dcz-SDS
	VARIABLES { sdsRE1state }
	DESCRIPTION "TRAP: Current RELAY 1 output status."
    ::= 150

sdsRE2state-trap TRAP-TYPE
	-- STATUS current
	ENTERPRISE mib-AN-Dcz-SDS
	VARIABLES { sdsRE2state }
	DESCRIPTION "TRAP: Current RELAY 2 output status."
    ::= 153

-- next

sdsTempSensValue-trap TRAP-TYPE
	-- STATUS current
	ENTERPRISE mib-AN-Dcz-SDS
	VARIABLES { sdsTempSensValue }
	DESCRIPTION "TRAP: Temperature Sensor (C) multiplied by 100."
    ::= 222

sdsTempSensName-trap TRAP-TYPE
	-- STATUS current
	ENTERPRISE mib-AN-Dcz-SDS
	VARIABLES { sdsTempSensName }
	DESCRIPTION "TRAP: User name for analog temperature sensor."
    ::= 223

-- next

sdsMaximumLoad-trap TRAP-TYPE
	-- STATUS current
	ENTERPRISE mib-AN-Dcz-SDS
	VARIABLES { sdsMaximumLoad }
        DESCRIPTION "TRAP: SDS Maximum Load-trap."
    ::= 401

sdsAlarmText-trap TRAP-TYPE
	-- STATUS current
	ENTERPRISE mib-AN-Dcz-SDS
	VARIABLES { sdsAlarmText }
        DESCRIPTION "TRAP: SDS Alarm Text."
    ::= 402

sdsOutputVoltage1-trap TRAP-TYPE
	-- STATUS current
	ENTERPRISE mib-AN-Dcz-SDS
	VARIABLES { sdsOutputVoltage1 }
        DESCRIPTION "TRAP: SDS Output Voltage1-trap."
    ::= 403

sdsOutputVoltage2-trap TRAP-TYPE
	-- STATUS current
	ENTERPRISE mib-AN-Dcz-SDS
	VARIABLES { sdsOutputVoltage2 }
        DESCRIPTION "TRAP: SDS Outpur Voltage2-trap."
    ::= 404

sdsOutputCurrent-trap TRAP-TYPE
	-- STATUS current
	ENTERPRISE mib-AN-Dcz-SDS
	VARIABLES { sdsOutputCurrent }
        DESCRIPTION "TRAP: SDS Output current-trap."
    ::= 405

sdsBatteryCapacity-trap TRAP-TYPE
	-- STATUS current
	ENTERPRISE mib-AN-Dcz-SDS
	VARIABLES { sdsBatteryCapacity }
        DESCRIPTION "TRAP: SDS Battery Capacity-trap."
    ::= 406
    
sdsLoad-trap TRAP-TYPE
	-- STATUS current
	ENTERPRISE mib-AN-Dcz-SDS
	VARIABLES { sdsLoad }
        DESCRIPTION "TRAP: SDS Load-trap."
    ::= 407

sdsCapTestTime-trap TRAP-TYPE
	-- STATUS current
	ENTERPRISE mib-AN-Dcz-SDS
	VARIABLES { sdsCapTestTime }
        DESCRIPTION "TRAP: SDS CapTestTime-trap."
    ::= 408

-- end

END
