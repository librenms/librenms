-- **********************************************************
-- OPENWRT-MIB
--
-- Base registration module for OpenWrt metrics exported by the
-- LibreNMS OpenWrt SNMP agent (a single net-snmp pass_persist handler).
--
-- This module only establishes the OpenWrt OID structure. The metrics
-- themselves live in per-subsystem modules that register beneath
-- openwrtObjects, for example OPENWRT-WIRELESS-MIB at { openwrtObjects 10 }.
--
-- Enterprise Number: 60652 (LibreNMS, IANA PEN)
-- OID Base: .1.3.6.1.4.1.60652.102
--
-- NOTE: the sub-arc { enterprises 60652 102 } is PROVISIONAL, following the
-- LibreNMS agent-MIB convention where OS/agent MIBs occupy the 100-block
-- (XCP-NG-VMINFO-MIB uses { enterprises 60652 100 }). openwrtMIB is rooted
-- directly under the enterprise number, with no intermediate node, so a future
-- enterprise-number reassignment is a single-line change.
-- Pending final assignment by a LibreNMS maintainer.
--
-- Device metadata scalars (e.g. openwrtMIBversion, openwrtOSversion) are
-- reserved for a future revision and are intentionally not defined yet, so
-- that this MIB stays in lockstep with what the agent currently serves.
-- Temperature/thermal data is exported separately via LM-SENSORS-MIB.
-- **********************************************************

OPENWRT-MIB DEFINITIONS ::= BEGIN

IMPORTS
    MODULE-IDENTITY, enterprises
        FROM SNMPv2-SMI;

openwrtMIB MODULE-IDENTITY
    LAST-UPDATED "202607030000Z"
    ORGANIZATION "LibreNMS"
    CONTACT-INFO
        "       LibreNMS Community
                https://www.librenms.org
                https://github.com/librenms/librenms
        "
    DESCRIPTION
        "Base module describing the OpenWrt OID structure used by the
         LibreNMS OpenWrt SNMP agent. Per-subsystem metrics register under
         openwrtObjects (wireless at { openwrtObjects 10 }); conformance
         registers under openwrtConformance."
    REVISION "202607030000Z"
    DESCRIPTION
        "Initial version: base registration nodes for the OpenWrt subtree."
    ::= { enterprises 60652 102 }

-- **********************************************************
-- Structure
-- **********************************************************

openwrtObjects     OBJECT IDENTIFIER ::= { openwrtMIB 1 }
openwrtConformance OBJECT IDENTIFIER ::= { openwrtMIB 2 }

END
