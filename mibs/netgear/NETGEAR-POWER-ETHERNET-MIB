NETGEAR-POWER-ETHERNET-MIB DEFINITIONS ::= BEGIN

-- Copyright Netgear Inc (2003-2015)  All rights reserved.

-- This SNMP Management Information Specification
-- embodies Netgear Inc's confidential and proprietary
-- intellectual property.  Netgear Inc retains all title
-- and ownership in the Specification including any revisions.

-- This Specification is supplied "AS IS", Netgear Inc
-- makes no warranty, either expressed or implied,
-- as to the use, operation, condition, or performance of the
-- Specification.
    
    IMPORTS
      MODULE-IDENTITY, OBJECT-TYPE, Integer32, Gauge32       FROM SNMPv2-SMI
      TruthValue                                             FROM SNMPv2-TC
      ng7000managedswitch                                               FROM NETGEAR-REF-MIB
      DisplayString                                          FROM RFC1213-MIB
      pethPsePortEntry, pethMainPseEntry                     FROM POWER-ETHERNET-MIB;
    

    fastPathpowerEthernetMIB MODULE-IDENTITY
    LAST-UPDATED "201803020000Z" -- 02 Mar 2018 12:00:00 GMT
    ORGANIZATION "Netgear Inc"
    CONTACT-INFO ""

    DESCRIPTION
        "This MIB Augments the POWER-ETHERNET-MIB created by the IETF Ethernet 
         Interfaces and Hub MIB Working Group for managing Power Source 
         Equipment (PSE).  The objects in this MIB are intended to provide 
         additional objects for reporting information available to the hardware 
         on this platform which are not represented in the draft MIB."
         
      -- Revision history.
   REVISION
        "201803020000Z" -- 02 Mar 2018 12:00:00 GMT
   DESCRIPTION
        "Deprecated agentPethPoeMainPseThresholdPower and 
         agentPethPoeMainPseUsageThreshold objects from 
         agentPethPoeMainPseObjects group as threshold 
         should be maintained for unit (system) instead of per slot. 
         Threshold Power is not present in agentPethPseTable, hence 
         added agentPethPseThresholdPower in agentPethPseTable."
   REVISION
        "201801250000Z" -- 25 Jan 2018 12:00:00 GMT
   DESCRIPTION
        "agentPethPoeMainPseObjects Group is added to get/set the 
         PoE System Data for all slots in a unit."
   REVISION
        "201503130000Z" -- 13 Mar 2015 12:00:00 GMT
   DESCRIPTION
        "agentPethPsePowerManagementMode object description is updated."
   REVISION
        "201404160000Z" -- 16 Apr 2014 12:00:00 GMT
   DESCRIPTION
        "Upoe support added in new object agentPethHighPowerMode."
   REVISION
        "201101260000Z" -- 26 Jan 2011 12:00:00 GMT
   DESCRIPTION
        "Postal address updated."
   REVISION
        "200708191200Z" -- 17 Aug 2007 12:00:00 GMT
   DESCRIPTION
        "PoE support for BCM59101 added."
   REVISION
        "200705230000Z" -- 23 May 2007 12:00:00 GMT
   DESCRIPTION
        "Netgear branding related changes."
   REVISION
        "200311101200Z" -- 10 Nov 2003 12:00:00 GMT
   DESCRIPTION
        "Initial revision."
    ::= {  ng7000managedswitch 15 }

    agentPethObjects       OBJECT IDENTIFIER ::= { fastPathpowerEthernetMIB 1 }

    agentPethPsePortTable OBJECT-TYPE
          SYNTAX      SEQUENCE OF AgentPethPsePortEntry
          MAX-ACCESS  not-accessible
          STATUS      current
          DESCRIPTION
              "A table of per-port information and configuration objects relating 
              to the power status of each port."
          ::= { agentPethObjects 1 }

    agentPethPsePortEntry OBJECT-TYPE
          SYNTAX      AgentPethPsePortEntry
          MAX-ACCESS  not-accessible
          STATUS      current
          DESCRIPTION
              "A collection of objects providing additional power information 
              and control parameters for the specified port."
          AUGMENTS    { pethPsePortEntry }
          ::= { agentPethPsePortTable 1 }

    AgentPethPsePortEntry ::= SEQUENCE {
          agentPethPowerLimit
             Gauge32,
          agentPethOutputPower
             Gauge32,
          agentPethOutputCurrent
             Gauge32,
          agentPethOutputVolts
             Gauge32,
          agentPethTemperature
             Gauge32,
          agentPethPowerLimitType
             INTEGER,
          agentPethHighPowerEnable
             TruthValue,
          agentPethPowerDetectionType
             INTEGER,
          agentPethFaultStatus
             INTEGER,  
          agentPethPortReset
             INTEGER,
          agentPethPowerLimitMin
             Gauge32,
          agentPethPowerLimitMax
             Gauge32
          }
             
    agentPethPowerLimit OBJECT-TYPE
          SYNTAX      Gauge32
          UNITS       "Milliwatts"
          MAX-ACCESS  read-write
          STATUS      current
          DESCRIPTION
             "The configured maximum power this port can provide to an 
             attached device measured in Milliwatts."
          ::= { agentPethPsePortEntry 1 }
    
    agentPethOutputPower OBJECT-TYPE
          SYNTAX      Gauge32
          UNITS       "Milliwatts"
          MAX-ACCESS  read-only
          STATUS      current
          DESCRIPTION
             "The power this port is supplying to an attached device measured 
             in Milliwatts."
          ::= { agentPethPsePortEntry 2 }
    
    agentPethOutputCurrent OBJECT-TYPE
          SYNTAX      Gauge32
          UNITS       "Milliamps"
          MAX-ACCESS  read-only
          STATUS      current
          DESCRIPTION
             "The current this port is supplying to an attached device measured 
             in Milliamps."
          ::= { agentPethPsePortEntry 3 }
    
    agentPethOutputVolts OBJECT-TYPE
          SYNTAX      Gauge32
          UNITS       "Volts"
          MAX-ACCESS  read-only
          STATUS      current
          DESCRIPTION
             "The voltage this port is supplying to an attached device measured 
             in Volts."
          ::= { agentPethPsePortEntry 4 }

    agentPethTemperature OBJECT-TYPE
          SYNTAX      Gauge32
          UNITS       "DEGREES"
          MAX-ACCESS  read-only
          STATUS      obsolete
          DESCRIPTION
             "The temperature measured at this port of the PoE Controller. It is
              measured in degree celcius."
          ::= { agentPethPsePortEntry 5 }

    agentPethPowerLimitType OBJECT-TYPE
    SYNTAX INTEGER   {
               dot3af(1),
               user(2),
               none(3)
     }
    MAX-ACCESS read-write
    STATUS current
    DESCRIPTION
        "Describes or controls the maximum power that a port can deliver.
         A value of dot3af(1) means that the port power limit is as per
         the dot3af class of the PD attached.
         A value of user(2) means that the port power limit is equal to the value 
         specified by agentPethPowerLimit"
    REFERENCE
      "Broadcom 5910X programmers guide, IEEE Std 802.3af Section 30.9.1.1.6"
    ::= { agentPethPsePortEntry 6 }

    agentPethHighPowerEnable OBJECT-TYPE
    SYNTAX TruthValue
    MAX-ACCESS read-write
    STATUS current
    DESCRIPTION
        "true (1) The PSE port can deliver power up to 32Watts.
         false(2) The PSE port can deliver power up to 18Watts"
    REFERENCE
      "Broadcom 5910X programmers guide"

    ::= { agentPethPsePortEntry 7 }

    agentPethPowerDetectionType OBJECT-TYPE
    SYNTAX INTEGER   {
               none(0),
               legacy(1),
               fourPtdot3afonly(2),
               fourPtdot3afandlegacy(3),
               twoPtdot3afonly(4),
               twoPtdot3afandlegacy(5)
     }
    MAX-ACCESS read-write
    STATUS current
    DESCRIPTION
        "Describes PD detection mechanism performed by the PSE port.
         A value of none(0) means no detection is done.
         A value of legacy(1) means only legacy capacitive detection scheme is
         used.
         A value of 4ptdot3afonly(2) means that IEEE 802.3af 4point detection scheme
         is used.
         A value of 4ptdot3afandlegacy(3) means that IEEE 802.3af 4point detection scheme
         is used and when that fails to detect a connected PD, legacity capacitive detection
         is used.
         A value of 2ptdot3afonly(4) means that IEEE 802.3af 2point detection scheme
         is used.
         A value of 2ptdot3afandlegacy(5)means that IEEE 802.3af 2point detection scheme
         is used and when that fails to detect a connected PD, legacity capacitive detection
         is used.          
         The value 'none' can not be forcibly set by the administrator."
    REFERENCE
      "Broadcom 5910X programmers guide, IEEE Std 802.3af Section 30.9.1.1.6"
    ::= { agentPethPsePortEntry 8 }

    agentPethFaultStatus OBJECT-TYPE
    SYNTAX INTEGER   {
               none(0),
               mpsAbsent(1),
               short(2),
               overload(3),
               powerDenied(4),
               thermalShutdown(5),
               startupFailure(6)
     }
    MAX-ACCESS read-only
    STATUS current
    DESCRIPTION
        "Describes the error description when the pse port is in fault status.
         A value of none(0) specifies that the pse port is not in any error state.
         A value of mpsAbsent(1) specifies that the pse port has detected and absence
         of main power supply.
         A value of short(2) specifies that the pse port has detected a short circuit
         condition.
         A value of overload(3) specifies that the pd connected to the pse port had tried
         to draw more power than permissible by the hardware. 
         A value of powerDenied(4) specifies that the pse port has been denied power
         because of shortage of power or due to administrative action.
         A value of thermalShutdown(5) specifies that the thermal threshold has exceeded 
         for the pse port.
         A value of startupFailure(6) as fault status indicates that the port does not have
         sufficient voltage."
    REFERENCE
      "Broadcom 5910X programmers guide, IEEE Std 802.3af"

    ::= { agentPethPsePortEntry 9 }

   agentPethPortReset OBJECT-TYPE
    SYNTAX INTEGER   {
               none(0),
               reset(1)
     }
    MAX-ACCESS read-write
    STATUS current
    DESCRIPTION
        "A value of reset(1) is used to move the pse port dot3af state to idle. A
         read on this object will always return the value none(0). The value none(0)
         can not be forcibly set by the administrtor."
    REFERENCE
      "Broadcom 5910X programmers guide, IEEE Std 802.3af"
    ::= { agentPethPsePortEntry 10 }
 
    agentPethPowerLimitMin OBJECT-TYPE
          SYNTAX      Gauge32
          UNITS       "Milliwatts"
          MAX-ACCESS  read-only
          STATUS      current
          DESCRIPTION
             "The minimum power this port can be configured to provide, measured in Milliwatts."
    ::= { agentPethPsePortEntry 11 }
    
    agentPethPowerLimitMax OBJECT-TYPE
          SYNTAX      Gauge32
          UNITS       "Milliwatts"
          MAX-ACCESS  read-only
          STATUS      current
          DESCRIPTION
             "The maximum power this port can be configured to provide, measured in Milliwatts."
    ::= { agentPethPsePortEntry 12 }
    

-- Main objects
    agentPethMainPseObjects       OBJECT IDENTIFIER ::= { agentPethObjects 2 }

    agentPethMainPseTable OBJECT-TYPE
          SYNTAX      SEQUENCE OF AgentPethMainPseEntry
          MAX-ACCESS  not-accessible
          STATUS      current
          DESCRIPTION
              "A table of objects that display and control attributes
               of the main power source in a PSE  device. Ethernet
               switches are one example of boxes that would support
               these objects.
               Values of all read-write objects in this table are
               persistent at restart/reboot."
          ::= { agentPethMainPseObjects 1 }

        agentPethMainPseEntry OBJECT-TYPE
            SYNTAX      AgentPethMainPseEntry
            MAX-ACCESS  not-accessible
            STATUS      current
            DESCRIPTION
               "A set of objects that display and control the Main
                power of a PSE. "
            AUGMENTS    { pethMainPseEntry }
            ::= { agentPethMainPseTable 1 }      

        AgentPethMainPseEntry ::= SEQUENCE {
            agentPethMainPseLegacy
                TruthValue
        }
             
        agentPethMainPseLegacy OBJECT-TYPE
          SYNTAX      TruthValue
          MAX-ACCESS  read-write
          STATUS      current
          DESCRIPTION
                  "Enable/Disable Legacy device detection. The
                value true(1) means legacy devices are detected; the
                value false(2) means legacy devices are not detected."
          ::= { agentPethMainPseEntry 1 }
          
    agentPethPseTable OBJECT-TYPE
          SYNTAX      SEQUENCE OF AgentPethPseEntry
          MAX-ACCESS  not-accessible
          STATUS      current
          DESCRIPTION
              "A table of per-unit information and configuration objects relating 
              to the power configurtion for the entire pse unit."
          ::= { agentPethObjects 3 }

    agentPethPseEntry OBJECT-TYPE
          SYNTAX      AgentPethPseEntry
          MAX-ACCESS  not-accessible
          STATUS      current
          DESCRIPTION
              "A collection of objects providing additional power information 
              and control parameters for the specified pse unit."
          AUGMENTS    { pethMainPseEntry }
          ::= { agentPethPseTable 1 }

    AgentPethPseEntry ::= SEQUENCE {
          agentPethPsePowerManagementMode

            INTEGER
          ,
          agentPethPseThresholdPower
            Gauge32
          }

    agentPethPsePowerManagementMode OBJECT-TYPE
    SYNTAX INTEGER   {
               none(0),
               dynamic(1),
               static(2)
     }
    MAX-ACCESS read-write
    STATUS current
    DESCRIPTION
        "Describes or controls the power management algorithm used by the pse 
         to deliver power to the requesting PDsthat a pds.
         A value of dynamic(1) means that power consumption of each port 
         is measured and calculated in real-time.
         A value of static(2) means that power allocated for each port depends 
         on the type of power threshold configured on the port."
    REFERENCE
      "Broadcom 5910X programmers guide"

    ::= { agentPethPseEntry 1 }

    agentPethPseThresholdPower OBJECT-TYPE
      SYNTAX      Gauge32
      UNITS       "Watts"
      MAX-ACCESS  read-only
      STATUS      current
      DESCRIPTION
          "Measured usage power expressed in Watts."
    ::= { agentPethPseEntry 6 }         

   agentPethPoeMainPseObjects       OBJECT IDENTIFIER ::= { agentPethObjects 4 }
   agentPethPoeMainPseTable OBJECT-TYPE
       SYNTAX      SEQUENCE OF AgentPethPoeMainPseEntry 
       MAX-ACCESS  not-accessible
       STATUS      current
       DESCRIPTION
           "A table of objects that display and control attributes
            of the main power source in a PSE  device.  Ethernet
            switches are one example of boxes that would support
            these objects.
            Values of all read-write objects in this table are
            persistent at restart/reboot."
       ::= { agentPethPoeMainPseObjects 1 }

   agentPethPoeMainPseEntry OBJECT-TYPE
       SYNTAX      AgentPethPoeMainPseEntry
       MAX-ACCESS  not-accessible
       STATUS      current
       DESCRIPTION
            "A set of objects that display and control the Main
             power of a PSE. "
       INDEX    { agentPethPoeMainPseGroupIndex, agentPethPoeMainPseSlotIndex }
       ::= { agentPethPoeMainPseTable 1 }

   AgentPethPoeMainPseEntry ::= SEQUENCE {
       agentPethPoeMainPseGroupIndex
           Integer32,
       agentPethPoeMainPseSlotIndex
           Integer32,
       agentPethPoeMainPsePower
           Gauge32,
       agentPethPoeMainPseOperStatus
           INTEGER,
       agentPethPoeMainPseThresholdPower
           Gauge32,
       agentPethPoeMainPseConsumptionPower
           Gauge32,
       agentPethPoeMainPseUsageThreshold
           Integer32,
       agentPethPoeMainPseFWImageVersion
           OCTET STRING,
       agentPethPoePsePowerManagementMode
           INTEGER,
       agentPethPoePseCardModel
           DisplayString,
       agentPethPoePseCardHost
           DisplayString,
       agentPethPoePseCardStatus
           INTEGER
   }
   agentPethPoeMainPseGroupIndex OBJECT-TYPE
       SYNTAX       Integer32 (1..2147483647)
       MAX-ACCESS   not-accessible
       STATUS       current
       DESCRIPTION
           "This variable uniquely identifies the group to which
           power Ethernet PSE is connected.  Group means (box in
           the stack, module in a rack) and the value 1 MUST be
           used for non-modular devices.  Furthermore, the same
           value MUST be used in this variable, pethPsePortGroupIndex,
           and pethNotificationControlGroupIndex to refer to a
           given box in a stack or module in a rack."
       ::= { agentPethPoeMainPseEntry 1 }

   agentPethPoeMainPseSlotIndex OBJECT-TYPE
       SYNTAX       Integer32 (1..2147483647)
       MAX-ACCESS   not-accessible
       STATUS       current
       DESCRIPTION
           "This variable uniquely identifies the slot in an unit."
       ::= { agentPethPoeMainPseEntry 2 }

   agentPethPoeMainPsePower OBJECT-TYPE
       SYNTAX      Gauge32  (1..65535)
       UNITS       "Watts"
       MAX-ACCESS  read-only
       STATUS      current
       DESCRIPTION
           "The nominal power of the PSE expressed in Watts."
       ::= { agentPethPoeMainPseEntry 3 }

   agentPethPoeMainPseOperStatus OBJECT-TYPE
       SYNTAX      INTEGER   {
                   on(1),
                   off(2),
                   faulty(3)
                   }
       MAX-ACCESS  read-only
       STATUS      current
       DESCRIPTION
           "The operational status of the main PSE."
       ::= { agentPethPoeMainPseEntry 4 }

   agentPethPoeMainPseThresholdPower OBJECT-TYPE
       SYNTAX      Gauge32
       UNITS       "Watts"
       MAX-ACCESS  read-only
       STATUS      deprecated 
       DESCRIPTION
           "Measured usage power expressed in Watts. This object is deprecated as 
            per slot Threshold is no longer supported"
       ::= { agentPethPoeMainPseEntry 5 }

   agentPethPoeMainPseConsumptionPower OBJECT-TYPE
       SYNTAX      Gauge32
       UNITS       "Milliwatts"
       MAX-ACCESS  read-only
       STATUS      current
       DESCRIPTION
           "Measured usage power expressed in Watts."
       ::= { agentPethPoeMainPseEntry 6 }

   agentPethPoeMainPseUsageThreshold OBJECT-TYPE
       SYNTAX      Integer32  (1..99)
       UNITS       "%"
       MAX-ACCESS  read-write
       STATUS      deprecated 
       DESCRIPTION
           "The usage threshold expressed in percents for
            comparing the measured power and initiating
            an alarm if the threshold is exceeded. This 
            object is deprecated as per slot Usage Threshold 
            is no longer supported."
       ::= { agentPethPoeMainPseEntry 7 }

   agentPethPoeMainPseFWImageVersion OBJECT-TYPE
       SYNTAX      OCTET STRING (SIZE(256))
       MAX-ACCESS  read-only
       STATUS      current
       DESCRIPTION
           "Version of the PoE controller's FW image."
       ::= { agentPethPoeMainPseEntry 8 }

   agentPethPoePsePowerManagementMode OBJECT-TYPE
       SYNTAX      INTEGER   {
                   none(0),
                   dynamic(1),
                   static(2)
                   }
       MAX-ACCESS  read-write
       STATUS      current
       DESCRIPTION
           "Describes or controls the power management algorithm used by the pse 
            to deliver power to the requesting PDs. A value of dynamic(1) 
            means that power consumption of each port is measured and calculated in 
            real-time. A value of static(2) means that power allocated for each port 
            depends on the type of power threshold configured on the port."
       REFERENCE
           "Broadcom 5910X programmers guide"
       ::= { agentPethPoeMainPseEntry 9 }

   agentPethPoePseCardModel OBJECT-TYPE
       SYNTAX      DisplayString (SIZE(1..32))
       MAX-ACCESS  read-only
       STATUS      current
       DESCRIPTION
           "Displays the PoE daughther card model at PSE side."
       ::= { agentPethPoeMainPseEntry 10 }         

   agentPethPoePseCardHost OBJECT-TYPE
       SYNTAX      DisplayString (SIZE(1..32))
       MAX-ACCESS  read-only
       STATUS      current
       DESCRIPTION
           "Displays the board which hosts the PoE daughther card at PSE side."
       ::= { agentPethPoeMainPseEntry 11 }         

   agentPethPoePseCardStatus OBJECT-TYPE
       SYNTAX      INTEGER   {
                   absent-or-failed(0),
                   running(1)
                   }
       MAX-ACCESS  read-only
       STATUS      current
       DESCRIPTION
           "Displays running status of the PoE daughther card at PSE side. The value 
            absent-or-failed(0) means that the card is either not present or some error 
            has occurred. The value running(1) means that card is present and working fine."
       ::= { agentPethPoeMainPseEntry 12 }         

END
