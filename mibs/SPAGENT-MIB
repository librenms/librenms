--/***************************************************************************/
--/**                                                                        */
--/**               AKCP, Ltd                                                */
--/**               Proprietary and Confidential Information                 */
--/**                                                                        */
--/** This material contains, and is part of a computer software program     */
--/** which is, proprietary and confidential information owned by AKCP,Ltd   */
--/** The program, including this material,                                  */
--/** may not be duplicated, disclosed or reproduced in whole or in part for */
--/** any purpose without the express written authorization of AKCP, Ltd     */
--/** All authorized reproductions must be marked with this legend.          */
--/**                                                                        */
--/**                                                                        */
--/**                         Copyright (c) 1994-2007                        */
--/**                         AKCP, Ltd                                      */
--/**                         All rights reserved                            */
--/**                                                                        */
--/***************************************************************************/

--/***************************************************************************/
--/**                                                                        */
--/** This MIB is a superset which includes all of the features in the       */
--/** sensorProbe family. Some features may not be implemented in certain    */
--/** models.                                                                */
--/**                                                                        */
--/***************************************************************************/
--
--/*
-- * Change Log
-- *
-- * 24/12/2009 Ji          : bug:1657 -  Separate the email and traps in sensor filter and send Trap/Email for sensor on port
-- * 29/12/2009 Ji          : bug:1801 -  New OID for detect sensor status
-- * 03/03/2010 Ji          : bug:1992 -  degreeRaw of sensorTemperatureTable return sensorIndex
-- * 05/03/2010 Ji          : bug:1994 -  new OID for sensorPort sensorsubPort and sensorDeviceIndex
-- * 04/05/2010 Ek          : bug:2078 -  new OID for sensor type name
-- * 04/05/2010 chaiylee    : bug:2078 -  new OID for hostname
-- * 03/06/2010 chaiylee    : bug:2078 -  Add sensor setting default for DC and 4-20ma
-- * 03/06/2010 bom         : bug:2142 -  Add gauge to analog sensor web interface
-- * 22/06/2010 bom         : bug:2201 -  validation akcp.mib at http://www.simpleweb.org/ietf/mibs/validate/ 
-- * 02/11/2010 Chaiylee    : bug:2463 - Add the new Tank Sender sensor
-- * 16/11/2010 Ji          : bug:2493 - Some OID do not update in MIB file
-- *
-- */

SPAGENT-MIB DEFINITIONS ::= BEGIN

IMPORTS
        enterprises, IpAddress, Gauge
                FROM RFC1155-SMI
        OBJECT-TYPE
                FROM RFC-1212
        DisplayString
                FROM RFC1213-MIB
        TRAP-TYPE
                FROM RFC-1215;


   akcp  OBJECT IDENTIFIER ::= { enterprises 3854 }
   sensorProbe OBJECT IDENTIFIER ::= { akcp 1 }


      spSummary OBJECT IDENTIFIER  ::=  {  sensorProbe 1   }

         spStatus OBJECT-TYPE
            SYNTAX  INTEGER {
               noStatus(1),
               normal(2),
               warning(3),
               critical(4),
               sensorError(5)
            }
            ACCESS  read-only
            STATUS  mandatory
            DESCRIPTION
            "The current status of this sensorProbe. The status of the sensorProbe is the worst status of all the sensors under the control of this sensorProbe."
            ::=  {  spSummary 2   }

         spManufName OBJECT-TYPE
            SYNTAX  DisplayString
            ACCESS  read-only
            STATUS  mandatory
            DESCRIPTION
            "The manufacturers name"
            ::=  {  spSummary 6   }

         spHelpUrl OBJECT-TYPE
            SYNTAX  DisplayString
            ACCESS  read-only
            STATUS  mandatory
            DESCRIPTION
            "The URL of the web based help"
            ::=  {  spSummary 7   }

         spProductName OBJECT-TYPE
            SYNTAX  DisplayString
            ACCESS  read-only
            STATUS  mandatory
            DESCRIPTION
            "The product name"
            ::=  {  spSummary 8   }

         spHostName OBJECT-TYPE
            SYNTAX  DisplayString
            ACCESS  read-only
            STATUS  mandatory
            DESCRIPTION
            "The hostname"
            ::=  {  spSummary 9   }

      spSensor OBJECT IDENTIFIER  ::=  {  sensorProbe 2 }

         sensorProbeDetail OBJECT IDENTIFIER ::= { spSensor 2  }

            sensorProbeEntry OBJECT IDENTIFIER ::= { sensorProbeDetail 1  }

               sensorProbeHost OBJECT-TYPE
                  SYNTAX  IpAddress
                  ACCESS  read-write
                  STATUS  mandatory
                  DESCRIPTION
                  "The Host of this sensor, this is the IP address"
                  ::=  {  sensorProbeEntry 1   }

               sensorProbeUseDHCP OBJECT-TYPE
                  SYNTAX  INTEGER {
                     yes(1),
                     no(2)
                  }
                  ACCESS  read-write
                  STATUS  mandatory
                  DESCRIPTION
                  "To use DHCP enter a 1, to use a static IP address enter a 2"
                  ::=  {  sensorProbeEntry 2   }

               sensorProbeMAC OBJECT-TYPE
                  SYNTAX  DisplayString
                  ACCESS  read-only
                  STATUS  mandatory
                  DESCRIPTION
                  "The MAC address of this system"
                  ::=  {  sensorProbeEntry 3   }

               sensorProbeSetCommunity OBJECT-TYPE
                  SYNTAX  DisplayString
                  ACCESS  read-write
                  STATUS  mandatory
                  DESCRIPTION
                  "The sensorProbe community string used for snmp Sets"
                  ::=  {  sensorProbeEntry 4   }

               sensorProbeGetCommunity OBJECT-TYPE
                  SYNTAX  DisplayString
                  ACCESS  read-write
                  STATUS  mandatory
                  DESCRIPTION
                  "The sensorProbe community string used for snmp Gets"
                  ::=  {  sensorProbeEntry 5   }

               sensorProbeTempTable OBJECT-TYPE
                  SYNTAX  SEQUENCE OF SensorProbeTempEntry
                  ACCESS  not-accessible
                  STATUS  mandatory
                  DESCRIPTION
                  "This table contains the data for every Temperature Sensor in the SensorArray. Each row in the table contains data for a different Temperature Sensor."
                  ::=  {  sensorProbeEntry 16   }

               sensorProbeTempEntry OBJECT-TYPE
                  SYNTAX  SensorProbeTempEntry
                  ACCESS  not-accessible
                  STATUS  mandatory
                  DESCRIPTION
                  "This is an entry in the sensorProbeTempEntry Table"
                  INDEX         { sensorProbeTempIndex }
                  ::=  {  sensorProbeTempTable 1 }

                  SensorProbeTempEntry ::= SEQUENCE {
                     sensorProbeTempDescription
                        DisplayString,
                     sensorProbeTempLocation
                        DisplayString,
                     sensorProbeTempDegree
                        INTEGER,
                     sensorProbeTempStatus
                        INTEGER,
                     sensorProbeTempOnline
                        INTEGER,
                     sensorProbeTempGoOnline
                        INTEGER,
                     sensorProbeTempHighWarning
                        INTEGER,
                     sensorProbeTempHighCritical
                        INTEGER,
                     sensorProbeTempLowWarning
                        INTEGER,
                     sensorProbeTempLowCritical
                        INTEGER,
                     sensorProbeTempRearm
                        INTEGER,
                     sensorProbeTempDegreeType
                        INTEGER,
                     sensorProbeTempSensorType
                        INTEGER,
                     sensorProbeTempDegreeRaw
                        INTEGER,
                     sensorProbeTempEmailTrapLimit
                        INTEGER,
                     sensorProbeTempEmailTrapSchedule
                        DisplayString,
                     sensorProbeTempEmailTrapInterval
                        INTEGER,
                     sensorProbeTempSendNormalTrap
                        INTEGER,
                     sensorProbeTempDelayError
                        INTEGER,
                     sensorProbeTempDelayNormal
                        INTEGER,
                     sensorProbeTempIndex
                        INTEGER,
                     sensorProbeTempRelayCycleTime
                        INTEGER,
                     sensorProbeTempRelayOnPort
                        INTEGER,
                     sensorProbeTempRelayActiveStatus
                        INTEGER,
                     sensorProbeTempRelayAction
                        INTEGER,
                     sensorProbeTempEmailInterval
                        INTEGER,
                     sensorProbeTempIndexCount
                        INTEGER,
                     sensorProbeTempOffset
                        INTEGER,
                     sensorProbeTempSirenCycleTime
                        INTEGER,
                     sensorProbeTempSirenOnPort
                        INTEGER,
                     sensorProbeTempSirenActiveStatus
                        INTEGER,
                     sensorProbeTempSirenAction
                        INTEGER,
                     sensorProbeTempAcknowledgement
                        INTEGER,
                     sensorProbeTempSirenDelayAlarm
                        INTEGER,
                     sensorProbeTempURL
                        DisplayString,
                     sensorProbeTempOpenURL
                        INTEGER,
                     sensorProbeTempDatacollectType
                        INTEGER,
                     sensorProbeTempContTimeHighCritical
                        INTEGER,
                     sensorProbeTempContTimeHighWarning
                        INTEGER,
                     sensorProbeTempContTimeNormal
                        INTEGER,
                     sensorProbeTempContTimeLowWarning
                        INTEGER,
                     sensorProbeTempContTimeLowCritical
                        INTEGER,
                     sensorProbeTempContTimeSensorError
                        INTEGER,
                     sensorProbeTempCalendar
                        INTEGER,
                     sensorProbeThermostatIndex
                        INTEGER,
                     sensorProbeThermostatDescription
                        DisplayString,
                     sensorProbeThermostatValue
                        INTEGER,
                     sensorProbeThermostatOnline
                        INTEGER,
                     sensorProbeThermostatGoOnline
                        INTEGER,
                     sensorProbeThermostatMode
                        INTEGER,
                     sensorProbeThermostatRelayControlPort
                        INTEGER,
                     sensorProbeThermostatNormalAction1
                        INTEGER,
                     sensorProbeThermostatHighLimit1
                        INTEGER,
                     sensorProbeThermostatHighLimitAction1
                        INTEGER,
                     sensorProbeThermostatLowLimit1
                        INTEGER,
                     sensorProbeThermostatLowLimitAction1
                        INTEGER,
                     sensorProbeThermostatNormalAction2
                        INTEGER,
                     sensorProbeThermostatHighLimit2
                        INTEGER,
                     sensorProbeThermostatHighLimitAction2
                        INTEGER,
                     sensorProbeThermostatLowLimit2
                        INTEGER,
                     sensorProbeThermostatLowLimitAction2
                        INTEGER,
                     sensorProbeThermostatEnableTime
                        DisplayString,
                     sensorProbeTempSendNormalMail
                        INTEGER,
                     sensorProbeTempSendTrap
                        INTEGER,
                     sensorProbeTempSendMail
                        INTEGER
                  }
                  sensorProbeTempDescription OBJECT-TYPE
                     SYNTAX  DisplayString
                     ACCESS  read-write
                     STATUS  mandatory
                     DESCRIPTION
                     "A Description of this sensor"
                     ::=  {  sensorProbeTempEntry 1   }

                  sensorProbeTempLocation OBJECT-TYPE
                       SYNTAX  DisplayString
                       ACCESS  read-write
                       STATUS  mandatory
                       DESCRIPTION
                       "The physical location of this sensor"
                       ::=  {  sensorProbeTempEntry 2   }

                  sensorProbeTempDegree OBJECT-TYPE
                     SYNTAX  INTEGER
                     ACCESS  read-only
                     STATUS  mandatory
                     DESCRIPTION
                     "The degrees in this sensor"
                     ::=  {  sensorProbeTempEntry 3   }

                  sensorProbeTempStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  sensorProbeTempEntry 4   }
      
                  sensorProbeTempOnline OBJECT-TYPE
                     SYNTAX  INTEGER {
                        online(1),
                        offline(2)
                     }
                     ACCESS  read-only
                     STATUS  mandatory
                     DESCRIPTION
                     "If this Sensor is currently online"
                     ::=  {  sensorProbeTempEntry 5   }
   
                  sensorProbeTempGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeTempEntry 6   }
         
                  sensorProbeTempHighWarning OBJECT-TYPE
                     SYNTAX  INTEGER
                     ACCESS  read-write
                     STATUS  mandatory
                     DESCRIPTION
                     "How hot this sensor gets before it sends a warning"
                     ::=  {  sensorProbeTempEntry 7   }
      
                  sensorProbeTempHighCritical OBJECT-TYPE
                     SYNTAX  INTEGER
                     ACCESS  read-write
                     STATUS  mandatory
                     DESCRIPTION
                     "How hot this sensor gets before it sends a critical event"
                     ::=  {  sensorProbeTempEntry 8   }
   
                  sensorProbeTempLowWarning OBJECT-TYPE
                     SYNTAX  INTEGER
                     ACCESS  read-write
                     STATUS  mandatory
                     DESCRIPTION
                     "How cold this sensor gets before it sends a warning"
                     ::=  {  sensorProbeTempEntry 9   }
   
                  sensorProbeTempLowCritical OBJECT-TYPE
                     SYNTAX  INTEGER
                     ACCESS  read-write
                     STATUS  mandatory
                     DESCRIPTION
                     "How cold this sensor gets before it sends a critical event"
                     ::=  {  sensorProbeTempEntry 10   }
      
                  sensorProbeTempRearm OBJECT-TYPE
                     SYNTAX  INTEGER
                     ACCESS  read-write
                     STATUS  mandatory
                     DESCRIPTION
                     "The number of degrees to rearm the status. For example if status goes from normal to warning, the temp must go down spTempRearm degrees below warning before the status goes to normal"
                     ::=  {  sensorProbeTempEntry 11   }
   
                  sensorProbeTempDegreeType OBJECT-TYPE
                     SYNTAX  INTEGER {
                        fahr(0),
                        celsius(1)
                     }
                     ACCESS  read-write
                     STATUS  mandatory
                     DESCRIPTION
                     "The degrees are in fahrenheit(0) or in celsius(1)"
                     ::=  {  sensorProbeTempEntry 12   }
      
                  sensorProbeTempSensorType OBJECT-TYPE
                       SYNTAX  INTEGER {
                          type1(0),
                          type2(1)
                       }
                       ACCESS  read-write
                       STATUS  mandatory
                       DESCRIPTION
                       "The type of temperture sensor"
                       ::=  {  sensorProbeTempEntry 13   }
         
                  sensorProbeTempDegreeRaw OBJECT-TYPE
                     SYNTAX  INTEGER 
                     ACCESS  read-only
                     STATUS  mandatory
                     DESCRIPTION
                     "SP Only: The raw degree data from the temperature sensor, slightly higher resolution"
                     ::=  {  sensorProbeTempEntry 14   }

                  sensorProbeTempEmailTrapLimit OBJECT-TYPE
                     SYNTAX  INTEGER {
                        disable(0),
                        enable(1)
                     }
                     ACCESS  read-write
                     STATUS  mandatory
                     DESCRIPTION
                     "Enable email/trap limit feature"
                     ::=  {  sensorProbeTempEntry 16   }

                  sensorProbeTempEmailTrapSchedule OBJECT-TYPE
                     SYNTAX  DisplayString
                     ACCESS  read-write
                     STATUS  mandatory
                     DESCRIPTION
                     "SP Only: Email/trap limit schedule for this sensor"
                     ::=  {  sensorProbeTempEntry 17   }

                  sensorProbeTempEmailTrapInterval OBJECT-TYPE
                     SYNTAX  INTEGER (0..60)
                     ACCESS  read-write
                     STATUS  mandatory
                     DESCRIPTION
                     "Minimum time between each [email/trap:SP, only trap:CP8] (can be from 0 to 60 minutes)."
                     ::=  {  sensorProbeTempEntry 18   }

                  sensorProbeTempSendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeTempEntry 19   }

                  sensorProbeTempDelayError OBJECT-TYPE
                     SYNTAX  INTEGER (0..65534)
                     ACCESS  read-write
                     STATUS  mandatory
                     DESCRIPTION
                     "Time in seconds after the sensor has been in error status before report as an error"
                     ::=  {  sensorProbeTempEntry 20   }

                  sensorProbeTempDelayNormal OBJECT-TYPE
                     SYNTAX  INTEGER (0..65534)
                     ACCESS  read-write
                     STATUS  mandatory
                     DESCRIPTION
                     "Time in seconds after the sensor change from error to normal before report as normal"
                     ::=  {  sensorProbeTempEntry 21   }

                  sensorProbeTempIndex OBJECT-TYPE
                     SYNTAX  INTEGER (0..7)
                     ACCESS  read-only
                     STATUS  mandatory
                     DESCRIPTION
                     "The index into the temperature sensor table"
                     ::=  {  sensorProbeTempEntry 22   }
                     
                  sensorProbeTempRelayCycleTime OBJECT-TYPE
                     SYNTAX INTEGER (1..255)
                     ACCESS read-write
                     STATUS mandatory
                     DESCRIPTION
                     "Relay toggle period in seconds for Cycle action."
                     ::= {  sensorProbeTempEntry 23 }

                  sensorProbeTempRelayOnPort OBJECT-TYPE
                     SYNTAX INTEGER (0..255)
                     ACCESS read-write
                     STATUS mandatory
                     DESCRIPTION
                     "The sensor port that the relay will listen to. If this is set to 255, then the relay will not listen to any sensor ports"
                     ::= {  sensorProbeTempEntry 24 }

                  sensorProbeTempRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::= {  sensorProbeTempEntry 25 }

                  sensorProbeTempRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::= {  sensorProbeTempEntry 26 }

                  sensorProbeTempEmailInterval OBJECT-TYPE
                     SYNTAX  INTEGER (0..60)
                     ACCESS  read-write
                     STATUS  mandatory
                     DESCRIPTION
                     "CP8 Only: Minimum time between each email (can be from 0 to 60 minutes)"
                     ::=  {  sensorProbeTempEntry 27   }

                  sensorProbeTempIndexCount OBJECT-TYPE
                     SYNTAX  INTEGER
                     ACCESS  read-only
                     STATUS  mandatory
                     DESCRIPTION
                     "Number of Temperature sensor online"
                     ::=  {  sensorProbeTempEntry 28   }

                  sensorProbeTempOffset OBJECT-TYPE
                     SYNTAX  INTEGER
                     ACCESS  read-write
                     STATUS  mandatory
                     DESCRIPTION
                     "Temperature Offset reading"
                     ::=  {  sensorProbeTempEntry 29   }

                  sensorProbeTempSirenCycleTime OBJECT-TYPE
                     SYNTAX INTEGER (1..255)
                     ACCESS read-write
                     STATUS mandatory
                     DESCRIPTION
                     "Siren toggle period in seconds for Cycle action."
                     ::= {  sensorProbeTempEntry 30 }

                  sensorProbeTempSirenOnPort OBJECT-TYPE
                     SYNTAX INTEGER (0..255)
                     ACCESS read-write
                     STATUS mandatory
                     DESCRIPTION
                     "The sensor port that the siren will listen to. If this is set to 255, then the siren will not listen to any sensor ports"
                     ::= {  sensorProbeTempEntry 31 }

                  sensorProbeTempSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::= {  sensorProbeTempEntry 32 }

                  sensorProbeTempSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::= {  sensorProbeTempEntry 33 }

                  sensorProbeTempAcknowledgement OBJECT-TYPE
                     SYNTAX INTEGER {
                        ack(1)
                     }
                     ACCESS read-write
                     STATUS mandatory
                     DESCRIPTION
                     "Acknowledged sensor error and stop notification"
                     ::= {  sensorProbeTempEntry 34 }

                  sensorProbeTempSirenDelayAlarm OBJECT-TYPE
                     SYNTAX INTEGER (1..255)
                     ACCESS read-write
                     STATUS mandatory
                     DESCRIPTION
                     "Siren delay in seconds before start Alarm."
                     ::= {  sensorProbeTempEntry 35 }

                  sensorProbeTempURL OBJECT-TYPE
                     SYNTAX  DisplayString
                     ACCESS  read-write
                     STATUS  mandatory
                     DESCRIPTION
                     "Sensor URL link."
                     ::= {  sensorProbeTempEntry 36 }

                  sensorProbeTempOpenURL OBJECT-TYPE
                     SYNTAX INTEGER {
                        cur-window(0),
                        new-window(2)
                     }
                     ACCESS read-write
                     STATUS mandatory
                     DESCRIPTION
                     "Open URL in this browser or open in a new window."
                     ::= {  sensorProbeTempEntry 37 }

                  sensorProbeTempDatacollectType OBJECT-TYPE
                     SYNTAX INTEGER {
                        average(1),
                        highest(2),
                        lowest(3)
                     }
                     ACCESS read-write
                     STATUS mandatory
                     DESCRIPTION
                     "Type of datacollect to collect."
                     ::= {  sensorProbeTempEntry 38 }

                  sensorProbeTempContTimeHighCritical OBJECT-TYPE
                     SYNTAX INTEGER (0..65535)
                     ACCESS read-write
                     STATUS mandatory
                     DESCRIPTION
                     "Continuous time for this sensor to be in High Critical before accepting new Status."
                     ::= {  sensorProbeTempEntry 39 }

                  sensorProbeTempContTimeHighWarning OBJECT-TYPE
                     SYNTAX INTEGER (0..65535)
                     ACCESS read-write
                     STATUS mandatory
                     DESCRIPTION
                     "Continuous time for this sensor to be in High Warning before accepting new Status."
                     ::= {  sensorProbeTempEntry 40 }

                  sensorProbeTempContTimeNormal OBJECT-TYPE
                     SYNTAX INTEGER (0..65535)
                     ACCESS read-write
                     STATUS mandatory
                     DESCRIPTION
                     "Continuous time for this sensor to be in Normal before accepting new Status."
                     ::= {  sensorProbeTempEntry 41 }

                  sensorProbeTempContTimeLowWarning OBJECT-TYPE
                     SYNTAX INTEGER (0..65535)
                     ACCESS read-write
                     STATUS mandatory
                     DESCRIPTION
                     "Continuous time for this sensor to be in Low Warning before accepting new Status."
                     ::= {  sensorProbeTempEntry 42 }

                  sensorProbeTempContTimeLowCritical OBJECT-TYPE
                     SYNTAX INTEGER (0..65535)
                     ACCESS read-write
                     STATUS mandatory
                     DESCRIPTION
                     "Continuous time for this sensor to be in Low Critical before accepting new Status."
                     ::= {  sensorProbeTempEntry 43 }

                  sensorProbeTempContTimeSensorError OBJECT-TYPE
                     SYNTAX INTEGER (0..65535)
                     ACCESS read-write
                     STATUS mandatory
                     DESCRIPTION
                     "Continuous time for this sensor to be in Sensor Error before accepting new Status."
                     ::= {  sensorProbeTempEntry 44 }

                  sensorProbeTempCalendar OBJECT-TYPE
                     SYNTAX INTEGER {
                        disable(0),
                        enable(1)
                     }
                     ACCESS read-write
                     STATUS mandatory
                     DESCRIPTION
                     "Enable or disable the calendar filtering working hours of sensor."
                     ::= {  sensorProbeTempEntry 45 }

                  sensorProbeThermostatIndex OBJECT-TYPE
                     SYNTAX  INTEGER
                     ACCESS  read-only
                     STATUS  mandatory
                     DESCRIPTION
                     "A unique value for each sensor thermostat port."
                     ::= {  sensorProbeTempEntry 46 }

                  sensorProbeThermostatDescription OBJECT-TYPE
                     SYNTAX  DisplayString
                     ACCESS  read-write
                     STATUS  mandatory
                     DESCRIPTION
                     "A Description of this sensor thermostat"
                     ::= {  sensorProbeTempEntry 47 }

                  sensorProbeThermostatValue OBJECT-TYPE
                     SYNTAX  INTEGER
                     ACCESS  read-only
                     STATUS  mandatory
                     DESCRIPTION
                     "The value in this sensor"
                     ::= {  sensorProbeTempEntry 48 }

                  sensorProbeThermostatOnline OBJECT-TYPE
                     SYNTAX  INTEGER {
                        online(1),
                        offline(2)
                     }
                     ACCESS  read-only
                     STATUS  mandatory
                     DESCRIPTION
                     "If this Sensor is currently online"
                     ::= {  sensorProbeTempEntry 49 }

                  sensorProbeThermostatGoOnline OBJECT-TYPE
                     SYNTAX  INTEGER {
                        goOnline(1),
                        goOffline(2)
                     }
                     ACCESS  read-write
                     STATUS  mandatory
                     DESCRIPTION
                     "To put online enter a 1, to take offline enter a 2"
                     ::= {  sensorProbeTempEntry 50 }

                  sensorProbeThermostatMode OBJECT-TYPE
                     SYNTAX INTEGER {
                        normal(0),
                        time-bases(1)
                     }
                     ACCESS read-write
                     STATUS mandatory
                     DESCRIPTION
                     "To select the thermostat mode for working on time-bases(1) or normal(0)."
                     ::= {  sensorProbeTempEntry 51 }

                  sensorProbeThermostatRelayControlPort OBJECT-TYPE
                     SYNTAX INTEGER
                     ACCESS read-write
                     STATUS mandatory
                     DESCRIPTION
                     "To select a relay port to be controled by this thermostat sensor."
                     ::= {  sensorProbeTempEntry 52 }

                  sensorProbeThermostatNormalAction1 OBJECT-TYPE
                     SYNTAX INTEGER {
                        turn-on(0),
                        turn-off(1),
                        no-change(2)
                     }
                     ACCESS read-write
                     STATUS mandatory
                     DESCRIPTION
                     "Profile1: Thermostat normal action for controlling a relay sensor."
                     ::= {  sensorProbeTempEntry 53 }

                  sensorProbeThermostatHighLimit1 OBJECT-TYPE
                     SYNTAX INTEGER (-40..167)
                     ACCESS read-write
                     STATUS mandatory
                     DESCRIPTION
                     "Profile1: When this sersor higher than thermostat high limit, it will take a high limit action."
                     ::= {  sensorProbeTempEntry 54 }

                  sensorProbeThermostatHighLimitAction1 OBJECT-TYPE
                     SYNTAX INTEGER {
                        turn-on(0),
                        turn-off(1),
                        no-change(2)
                     }
                     ACCESS read-write
                     STATUS mandatory
                     DESCRIPTION
                     "Profile1: Thermostat high limit action for controlling a relay sensor."
                     ::= {  sensorProbeTempEntry 55 }

                  sensorProbeThermostatLowLimit1 OBJECT-TYPE
                     SYNTAX INTEGER (-40..167)
                     ACCESS read-write
                     STATUS mandatory
                     DESCRIPTION
                     "Profile1: When this sersor higher than thermostat low limit, it will take a normal limit action."
                     ::= {  sensorProbeTempEntry 56 }

                  sensorProbeThermostatLowLimitAction1 OBJECT-TYPE
                     SYNTAX INTEGER {
                        turn-on(0),
                        turn-off(1),
                        no-change(2)
                     }
                     ACCESS read-write
                     STATUS mandatory
                     DESCRIPTION
                     "Profile1: Thermostat low limit action for controlling a relay sensor."
                     ::= {  sensorProbeTempEntry 57 }

                  sensorProbeThermostatNormalAction2 OBJECT-TYPE
                     SYNTAX INTEGER {
                        turn-on(0),
                        turn-off(1),
                        no-change(2)
                     }
                     ACCESS read-write
                     STATUS mandatory
                     DESCRIPTION
                     "Profile2: Thermostat normal action for controlling a relay sensor."
                     ::= {  sensorProbeTempEntry 58 }

                  sensorProbeThermostatHighLimit2 OBJECT-TYPE
                     SYNTAX INTEGER (-40..167)
                     ACCESS read-write
                     STATUS mandatory
                     DESCRIPTION
                     "Profile2: When this sersor higher than thermostat high limit, it will take a high limit action."
                     ::= {  sensorProbeTempEntry 59 }

                  sensorProbeThermostatHighLimitAction2 OBJECT-TYPE
                     SYNTAX INTEGER {
                        turn-on(0),
                        turn-off(1),
                        no-change(2)
                     }
                     ACCESS read-write
                     STATUS mandatory
                     DESCRIPTION
                     "Profile2: Thermostat high limit action for controlling a relay sensor."
                     ::= {  sensorProbeTempEntry 60 }

                  sensorProbeThermostatLowLimit2 OBJECT-TYPE
                     SYNTAX INTEGER (-40..167)
                     ACCESS read-write
                     STATUS mandatory
                     DESCRIPTION
                     "Profile2: When this sersor higher than thermostat low limit, it will take a normal limit action."
                     ::= {  sensorProbeTempEntry 61 }

                  sensorProbeThermostatLowLimitAction2 OBJECT-TYPE
                     SYNTAX INTEGER {
                        turn-on(0),
                        turn-off(1),
                        no-change(2)
                     }
                     ACCESS read-write
                     STATUS mandatory
                     DESCRIPTION
                     "Profile2: Thermostat low limit action for controlling a relay sensor."
                     ::= {  sensorProbeTempEntry 62 }

                  sensorProbeThermostatEnableTime OBJECT-TYPE
                     SYNTAX  DisplayString
                     ACCESS  read-write
                     STATUS  mandatory
                     DESCRIPTION
                     "Time to enable on Thermostat"
                     ::=  {  sensorProbeTempEntry 63 }

                  sensorProbeTempSendNormalMail OBJECT-TYPE
                     SYNTAX  INTEGER {
                        disable(0),
                        enable(1)
                     }
                     ACCESS  read-write
                     STATUS  mandatory
                     DESCRIPTION
                     "Enable sending email when sensor goes to normal"
                     ::=  {  sensorProbeTempEntry 64 }

                  sensorProbeTempSendTrap OBJECT-TYPE
                     SYNTAX  INTEGER {
                        disable(0),
                        enable(1)
                     }
                     ACCESS  read-write
                     STATUS  mandatory
                     DESCRIPTION
                     "Enable sending trap when sensor change status"
                     ::=  {  sensorProbeTempEntry 65 }

                  sensorProbeTempSendMail OBJECT-TYPE
                     SYNTAX  INTEGER {
                        disable(0),
                        enable(1)
                     }
                     ACCESS  read-write
                     STATUS  mandatory
                     DESCRIPTION
                     "Enable sending email when sensor change status"
                     ::=  {  sensorProbeTempEntry 66 }

               sensorProbeHumidityTable OBJECT-TYPE
                  SYNTAX  SEQUENCE OF SensorProbeHumidityEntry
                  ACCESS  not-accessible
                  STATUS  mandatory
                  DESCRIPTION
                  "This table contains the data for every Humidity Sensor in the SensorArray. Each row in the table contains data for a different Humidity Sensor."
                  ::=  {  sensorProbeEntry 17   }

               sensorProbeHumidityEntry OBJECT-TYPE
                  SYNTAX  SensorProbeHumidityEntry
                  ACCESS  not-accessible
                  STATUS  mandatory
                  DESCRIPTION
                  "This is an entry in the sensorProbeHumidityEntry Table"
                  INDEX         { sensorProbeHumidityIndex }
                  ::=  { sensorProbeHumidityTable 1 }

                  SensorProbeHumidityEntry ::= SEQUENCE {
                     sensorProbeHumidityDescription
                        DisplayString,
                       sensorProbeHumidityLocation
                          DisplayString,
                     sensorProbeHumidityPercent
                        INTEGER,
                     sensorProbeHumidityStatus
                        INTEGER,
                     sensorProbeHumidityOnline
                        INTEGER,
                     sensorProbeHumidityGoOnline
                        INTEGER,
                     sensorProbeHumidityHighWarning
                        INTEGER,
                     sensorProbeHumidityHighCritical
                        INTEGER,
                     sensorProbeHumidityLowWarning
                        INTEGER,
                     sensorProbeHumidityLowCritical
                        INTEGER,
                     sensorProbeHumidityRearm
                        INTEGER,
                     sensorProbeHumidityRaw
                        INTEGER,
                     sensorProbeHumidityLowVoltage
                        INTEGER,
                     sensorProbeHumidityHighVoltage
                        INTEGER,
                     sensorProbeHumidityEmailTrapLimit
                        INTEGER,
                     sensorProbeHumidityEmailTrapSchedule
                        DisplayString,
                     sensorProbeHumidityEmailTrapInterval
                        INTEGER,
                     sensorProbeHumiditySendNormalTrap
                        INTEGER,
                     sensorProbeHumidityDelayError
                        INTEGER,
                     sensorProbeHumidityDelayNormal
                        INTEGER,
                     sensorProbeHumidityIndex
                        INTEGER,
                     sensorProbeHumidityAtoDAmountMaxVoltage
                        INTEGER,
                     sensorProbeHumidityAtoDAmountBaseVoltage
                        INTEGER,
                     sensorProbeHumidityAtoDTypeUnit
                        INTEGER,
                     sensorProbeHumidityDcUnit
                        DisplayString,
                     sensorProbeHumidityAtoDJumper
                        INTEGER,
                     sensorProbeHumidityRelayCycleTime
                        INTEGER,
                     sensorProbeHumidityRelayOnPort
                        INTEGER,
                     sensorProbeHumidityRelayActiveStatus
                        INTEGER,
                     sensorProbeHumidityRelayAction
                        INTEGER,
                     sensorProbeHumidityEmailInterval
                        INTEGER,
                     sensorProbeHumidity4to20mAUnit
                        DisplayString,
                     sensorProbeHumidityIndexCount
                        INTEGER,
                     sensorProbeHumidityOffset
                        INTEGER,
                     sensorProbeHumiditySirenCycleTime
                        INTEGER,
                     sensorProbeHumiditySirenOnPort
                        INTEGER,
                     sensorProbeHumiditySirenActiveStatus
                        INTEGER,
                     sensorProbeHumiditySirenAction
                        INTEGER,
                     sensorProbeHumidityAcknowledgement
                        INTEGER,
                     sensorProbeHumiditySirenDelayAlarm
                        INTEGER,
                     sensorProbeHumidityURL
                        DisplayString,
                     sensorProbeHumidityOpenURL
                        INTEGER,
                     sensorProbeHumidityDatacollectType
                        INTEGER,
                     sensorProbeHumidityContTimeHighCritical
                        INTEGER,
                     sensorProbeHumidityContTimeHighWarning
                        INTEGER,
                     sensorProbeHumidityContTimeNormal
                        INTEGER,
                     sensorProbeHumidityContTimeLowWarning
                        INTEGER,
                     sensorProbeHumidityContTimeLowCritical
                        INTEGER,
                     sensorProbeHumidityContTimeSensorError
                        INTEGER,
                     sensorProbeHumidityCalendar
                        INTEGER,
                     sensorProbeHumiditySendNormalMail
                        INTEGER,
                     sensorProbeHumiditySendTrap
                        INTEGER,
                     sensorProbeHumiditySendMail
                        INTEGER
                  }
                  sensorProbeHumidityDescription OBJECT-TYPE
                     SYNTAX  DisplayString
                     ACCESS  read-write
                     STATUS  mandatory
                     DESCRIPTION
                     "A Description of this sensor"
                     ::=  {  sensorProbeHumidityEntry 1   }

                  sensorProbeHumidityLocation OBJECT-TYPE
                       SYNTAX  DisplayString
                       ACCESS  read-write
                       STATUS  mandatory
                       DESCRIPTION
                       "The physical location of this sensor"
                       ::=  {  sensorProbeHumidityEntry 2   }

                  sensorProbeHumidityPercent OBJECT-TYPE
                     SYNTAX  INTEGER (-32768..32767)
                     ACCESS  read-only
                     STATUS  mandatory
                     DESCRIPTION
                     "The relative humidity percentage measured by this sensor"
                     ::=  {  sensorProbeHumidityEntry 3   }

                  sensorProbeHumidityStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  sensorProbeHumidityEntry 4   }

                  sensorProbeHumidityOnline OBJECT-TYPE
                     SYNTAX  INTEGER {
                        online(1),
                        offline(2)
                     }
                     ACCESS  read-only
                     STATUS  mandatory
                     DESCRIPTION
                     "If this Sensor is currently online"
                        ::=  {  sensorProbeHumidityEntry 5   }

                  sensorProbeHumidityGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeHumidityEntry 6   }

                  sensorProbeHumidityHighWarning OBJECT-TYPE
                     SYNTAX  INTEGER
                     ACCESS  read-write
                     STATUS  mandatory
                     DESCRIPTION
                     "How high the relative humidity this sensor measures before it sends a warning"
                     ::=  {  sensorProbeHumidityEntry 7   }

                  sensorProbeHumidityHighCritical OBJECT-TYPE
                     SYNTAX  INTEGER
                     ACCESS  read-write
                     STATUS  mandatory
                     DESCRIPTION
                     "How high the relative humidity this sensor measures before it becomes critical"
                     ::=  {  sensorProbeHumidityEntry 8   }

                  sensorProbeHumidityLowWarning OBJECT-TYPE
                     SYNTAX  INTEGER
                     ACCESS  read-write
                     STATUS  mandatory
                     DESCRIPTION
                     "How low the relative humidity this sensor measures before it sends a warning"
                     ::=  {  sensorProbeHumidityEntry 9   }

                  sensorProbeHumidityLowCritical OBJECT-TYPE
                     SYNTAX  INTEGER
                     ACCESS  read-write
                     STATUS  mandatory
                     DESCRIPTION
                     "How low the relative humidity this sensor measures before it becomes critical"
                     ::=  {  sensorProbeHumidityEntry 10   }

                  sensorProbeHumidityRearm OBJECT-TYPE
                     SYNTAX  INTEGER
                     ACCESS  read-write
                     STATUS  mandatory
                     DESCRIPTION
                     "The percent relative humidity to rearm the status. For example if status goes from normal to warning, the humidity must go down spAnalogueRearm below warning before the status goes to normal"
                     ::=  {  sensorProbeHumidityEntry 11   }

                  sensorProbeHumidityRaw OBJECT-TYPE
                     SYNTAX  INTEGER 
                     ACCESS  read-only
                     STATUS  mandatory
                     DESCRIPTION
                     "The unformatted, raw, A/D value in this sensor. Contains more resolution than the formated percentage. This number can go from 0 to 1023 depending on the input voltage"
                     ::=  {  sensorProbeHumidityEntry 13   }

                  sensorProbeHumidityLowVoltage OBJECT-TYPE
                     SYNTAX  INTEGER
                     ACCESS  read-write
                     STATUS  mandatory
                     DESCRIPTION
                     "SP Only: The low voltage range for use in AtoD conversion."
                     ::=  {  sensorProbeHumidityEntry 14   }

                  sensorProbeHumidityHighVoltage OBJECT-TYPE
                     SYNTAX  INTEGER
                     ACCESS  read-write
                     STATUS  mandatory
                     DESCRIPTION
                     "SP Only: The high voltage range for use in AtoD conversion."
                     ::=  {  sensorProbeHumidityEntry 15   }

                  sensorProbeHumidityEmailTrapLimit OBJECT-TYPE
                     SYNTAX  INTEGER {
                        disable(0),
                        enable(1)
                     }
                     ACCESS  read-write
                     STATUS  mandatory
                     DESCRIPTION
                     "Enable email/trap limit feature"
                     ::=  {  sensorProbeHumidityEntry 17   }

                  sensorProbeHumidityEmailTrapSchedule OBJECT-TYPE
                     SYNTAX  DisplayString
                     ACCESS  read-write
                     STATUS  mandatory
                     DESCRIPTION
                     "SP Only: Email/trap limit schedule for this sensor"
                     ::=  {  sensorProbeHumidityEntry 18   }

                  sensorProbeHumidityEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  sensorProbeHumidityEntry 19   }

                  sensorProbeHumiditySendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeHumidityEntry 20   }

                  sensorProbeHumidityDelayError OBJECT-TYPE
                     SYNTAX  INTEGER (0..65534)
                     ACCESS  read-write
                     STATUS  mandatory
                     DESCRIPTION
                     "Time in seconds after the sensor has been in error status before report as an error"
                     ::=  {  sensorProbeHumidityEntry 21   }

                  sensorProbeHumidityDelayNormal OBJECT-TYPE
                     SYNTAX  INTEGER (0..65534)
                     ACCESS  read-write
                     STATUS  mandatory
                     DESCRIPTION
                     "Time in seconds after the sensor change from error to normal before report as normal"
                     ::=  {  sensorProbeHumidityEntry 22   }

                  sensorProbeHumidityIndex OBJECT-TYPE
                     SYNTAX  INTEGER (0..7)
                     ACCESS  read-only
                     STATUS  mandatory
                     DESCRIPTION
                     "The index into the Humidity sensor table"
                     ::=  {  sensorProbeHumidityEntry 23   }

                  sensorProbeHumidityAtoDAmountMaxVoltage OBJECT-TYPE
                     SYNTAX  INTEGER
                     ACCESS  read-write
                     STATUS  mandatory
                     DESCRIPTION
                     "The maximum scale of DC voltage conversion."
                     ::=  {  sensorProbeHumidityEntry 24   }

                  sensorProbeHumidityAtoDAmountBaseVoltage OBJECT-TYPE
                     SYNTAX  INTEGER
                     ACCESS  read-write
                     STATUS  mandatory
                     DESCRIPTION
                     "The base scale of DC voltage conversion."
                     ::=  {  sensorProbeHumidityEntry 25   }

                  sensorProbeHumidityAtoDTypeUnit OBJECT-TYPE
                     SYNTAX  INTEGER {
                        absolute(1),
                        percent(2)
                     }
                     ACCESS  read-write
                     STATUS  mandatory
                     DESCRIPTION
                     "Type of scale for use in DC voltage conversion."
                     ::=  {  sensorProbeHumidityEntry 26   }
                
                  sensorProbeHumidityDcUnit OBJECT-TYPE
                     SYNTAX  DisplayString
                     ACCESS  read-write
                     STATUS  mandatory
                     DESCRIPTION
                     "Display unit in DC voltage conversion."
                     ::=  {  sensorProbeHumidityEntry 27   }

                  sensorProbeHumidityAtoDJumper OBJECT-TYPE
                     SYNTAX  INTEGER {                 
                        jumperAt-60(-600),
                        jumperAt-40(-400),
                        jumperAt-30(-300),
                        jumperAt-20(-200),
                        jumperAt-10(-100),                        
                        jumperAt10(100),
                        jumperAt20(200),
                        jumperAt30(300),
                        jumperAt40(400),
                        jumperAt60(600)
                     }
                     ACCESS  read-write
                     STATUS  mandatory
                     DESCRIPTION
                     "Selected voltage scale (jumper 0) in DC voltage conversion."
                     ::=  {  sensorProbeHumidityEntry 28   }

                  sensorProbeHumidityRelayCycleTime OBJECT-TYPE
                     SYNTAX INTEGER (1..255)
                     ACCESS read-write
                     STATUS mandatory
                     DESCRIPTION
                     "Relay toggle period in seconds for Cycle action."
                     ::=  {  sensorProbeHumidityEntry 29   }

                  sensorProbeHumidityRelayOnPort OBJECT-TYPE
                     SYNTAX INTEGER (0..255)
                     ACCESS read-write
                     STATUS mandatory
                     DESCRIPTION
                     "The sensor port that the relay will listen to. If this is set to 255, then the relay will not listen to any sensor ports"
                     ::=  {  sensorProbeHumidityEntry 30   }

                  sensorProbeHumidityRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  sensorProbeHumidityEntry 31   }

                  sensorProbeHumidityRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  sensorProbeHumidityEntry 32   }

                  sensorProbeHumidityEmailInterval OBJECT-TYPE
                     SYNTAX  INTEGER (0..60)
                     ACCESS  read-write
                     STATUS  mandatory
                     DESCRIPTION
                     "CP8 Only: Minimum time between each emial (can be from 0 to 60 minutes)"
                     ::=  {  sensorProbeHumidityEntry 33   }

                  sensorProbeHumidity4to20mAUnit OBJECT-TYPE
                     SYNTAX  DisplayString
                     ACCESS  read-write
                     STATUS  mandatory
                     DESCRIPTION
                     "Display unit in DC voltage conversion."
                     ::=  {  sensorProbeHumidityEntry 34   }

                  sensorProbeHumidityIndexCount OBJECT-TYPE
                     SYNTAX  INTEGER
                     ACCESS   read-only
                     STATUS  mandatory
                     DESCRIPTION
                     "Number of Humidity sensor online"
                     ::=  {  sensorProbeHumidityEntry 35   }

                  sensorProbeHumidityOffset OBJECT-TYPE
                     SYNTAX  INTEGER
                     ACCESS  read-write
                     STATUS  mandatory
                     DESCRIPTION
                     "Humidity Offset reading"
                     ::=  {  sensorProbeHumidityEntry 36   }

                  sensorProbeHumiditySirenCycleTime OBJECT-TYPE
                     SYNTAX INTEGER (1..255)
                     ACCESS read-write
                     STATUS mandatory
                     DESCRIPTION
                     "Siren toggle period in seconds for Cycle action."
                     ::=  {  sensorProbeHumidityEntry 37   }

                  sensorProbeHumiditySirenOnPort OBJECT-TYPE
                     SYNTAX INTEGER (0..255)
                     ACCESS read-write
                     STATUS mandatory
                     DESCRIPTION
                     "The sensor port that the siren will listen to. If this is set to 255, then the siren will not listen to any sensor ports"
                     ::=  {  sensorProbeHumidityEntry 38   }

                  sensorProbeHumiditySirenActiveStatus OBJECT-TYPE
                     SYNTAX INTEGER {
                        highWarning(3),
                        highCritical(4),
                        lowWarning(5),
                        lowCritical(6),                        
                        anyError(7)
                     }
                     ACCESS read-write
                     STATUS mandatory
                     DESCRIPTION
                     "Sensor status that will activate the siren"
                     ::=  {  sensorProbeHumidityEntry 39   }

                  sensorProbeHumiditySirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  sensorProbeHumidityEntry 40   }

                  sensorProbeHumidityAcknowledgement OBJECT-TYPE
                     SYNTAX INTEGER {
                        ack(1)
                     }
                     ACCESS read-write
                     STATUS mandatory
                     DESCRIPTION
                     "Acknowledged sensor error and stop notification"
                     ::= {  sensorProbeHumidityEntry 41 }

                  sensorProbeHumiditySirenDelayAlarm OBJECT-TYPE
                     SYNTAX INTEGER (1..255)
                     ACCESS read-write
                     STATUS mandatory
                     DESCRIPTION
                     "Siren delay in seconds before start Alarm."
                     ::=  {  sensorProbeHumidityEntry 42 }

                  sensorProbeHumidityURL OBJECT-TYPE
                     SYNTAX  DisplayString
                     ACCESS  read-write
                     STATUS  mandatory
                     DESCRIPTION
                     "Sensor URL link."
                     ::=  {  sensorProbeHumidityEntry 43 }

                  sensorProbeHumidityOpenURL OBJECT-TYPE
                     SYNTAX INTEGER {
                        cur-window(0),
                        new-window(2)
                     }
                     ACCESS  read-write
                     STATUS  mandatory
                     DESCRIPTION
                     "Open URL in this browser or open in a new window."
                     ::=  {  sensorProbeHumidityEntry 44 }

                  sensorProbeHumidityDatacollectType OBJECT-TYPE
                     SYNTAX INTEGER {
                        average(1),
                        highest(2),
                        lowest(3)
                     }
                     ACCESS  read-write
                     STATUS  mandatory
                     DESCRIPTION
                     "Type of datacollect to collect."
                     ::=  {  sensorProbeHumidityEntry 45 }

                  sensorProbeHumidityContTimeHighCritical OBJECT-TYPE
                     SYNTAX INTEGER (0..65535)
                     ACCESS read-write
                     STATUS mandatory
                     DESCRIPTION
                     "Continuous time for this sensor to be in High Critical before accepting new Status."
                     ::= {  sensorProbeHumidityEntry 46 }

                  sensorProbeHumidityContTimeHighWarning OBJECT-TYPE
                     SYNTAX INTEGER (0..65535)
                     ACCESS read-write
                     STATUS mandatory
                     DESCRIPTION
                     "Continuous time for this sensor to be in High Warning before accepting new Status."
                     ::= {  sensorProbeHumidityEntry 47 }

                  sensorProbeHumidityContTimeNormal OBJECT-TYPE
                     SYNTAX INTEGER (0..65535)
                     ACCESS read-write
                     STATUS mandatory
                     DESCRIPTION
                     "Continuous time for this sensor to be in Normal before accepting new Status."
                     ::= {  sensorProbeHumidityEntry 48 }

                  sensorProbeHumidityContTimeLowWarning OBJECT-TYPE
                     SYNTAX INTEGER (0..65535)
                     ACCESS read-write
                     STATUS mandatory
                     DESCRIPTION
                     "Continuous time for this sensor to be in Low Warning before accepting new Status."
                     ::= {  sensorProbeHumidityEntry 49 }

                  sensorProbeHumidityContTimeLowCritical OBJECT-TYPE
                     SYNTAX INTEGER (0..65535)
                     ACCESS read-write
                     STATUS mandatory
                     DESCRIPTION
                     "Continuous time for this sensor to be in Low Critical before accepting new Status."
                     ::= {  sensorProbeHumidityEntry 50 }

                  sensorProbeHumidityContTimeSensorError OBJECT-TYPE
                     SYNTAX INTEGER (0..65535)
                     ACCESS read-write
                     STATUS mandatory
                     DESCRIPTION
                     "Continuous time for this sensor to be in Sensor Error before accepting new Status."
                     ::= {  sensorProbeHumidityEntry 51 }

                  sensorProbeHumidityCalendar OBJECT-TYPE
                     SYNTAX INTEGER {
                        disable(0),
                        enable(1)
                     }
                     ACCESS read-write
                     STATUS mandatory
                     DESCRIPTION
                     "Enable or disable the calendar filtering working hours of sensor."
                     ::= {  sensorProbeHumidityEntry 52 }

                  sensorProbeHumiditySendNormalMail OBJECT-TYPE
                     SYNTAX  INTEGER {
                        disable(0),
                        enable(1)
                     }
                     ACCESS  read-write
                     STATUS  mandatory
                     DESCRIPTION
                     "Enable sending email when sensor goes to normal"
                     ::=  {  sensorProbeHumidityEntry 53 }

                  sensorProbeHumiditySendTrap OBJECT-TYPE
                     SYNTAX  INTEGER {
                        disable(0),
                        enable(1)
                     }
                     ACCESS  read-write
                     STATUS  mandatory
                     DESCRIPTION
                     "Enable sending trap when sensor change status"
                     ::=  {  sensorProbeHumidityEntry 54 }

                  sensorProbeHumiditySendMail OBJECT-TYPE
                     SYNTAX  INTEGER {
                        disable(0),
                        enable(1)
                     }
                     ACCESS  read-write
                     STATUS  mandatory
                     DESCRIPTION
                     "Enable sending email when sensor change status"
                     ::=  {  sensorProbeHumidityEntry 55 }

               sensorProbeSwitchTable OBJECT-TYPE
                  SYNTAX  SEQUENCE OF SensorProbeSwitchEntry
                  ACCESS  not-accessible
                  STATUS  mandatory
                  DESCRIPTION
                  "This table contains the data for every Switch Sensor in the SensorArray. Each row in the table contains data for a different Switch Sensor."
                  ::=  {  sensorProbeEntry 18   }

               sensorProbeSwitchEntry OBJECT-TYPE
                  SYNTAX  SensorProbeSwitchEntry
                  ACCESS  not-accessible
                  STATUS  mandatory
                  DESCRIPTION
                  "This is an entry in the sensorProbeSwitchEntry Table"
                  INDEX         { sensorProbeSwitchIndex }
                  ::=  { sensorProbeSwitchTable 1 }

                  SensorProbeSwitchEntry ::= SEQUENCE {
                     sensorProbeSwitchDescription
                        DisplayString,
                     sensorProbeSwitchLocation
                        DisplayString,
                     sensorProbeSwitchStatus
                        INTEGER,
                     sensorProbeSwitchOnline
                        INTEGER,
                     sensorProbeSwitchGoOnline
                        INTEGER,
                     sensorProbeSwitchDirection
                        INTEGER,
                     sensorProbeSwitchNormalState
                        INTEGER,
                     sensorProbeSwitchOutputLevel
                        INTEGER,
                     sensorProbeSensorType
                        INTEGER,
                     sensorProbeSwitchEmailTrapLimit
                        INTEGER,
                     sensorProbeSwitchEmailTrapSchedule
                        DisplayString,
                     sensorProbeSwitchEmailTrapInterval
                        INTEGER,
                     sensorProbeSwitchSendNormalTrap
                        INTEGER,
                     sensorProbeSwitchDelayError
                        INTEGER,
                     sensorProbeSwitchDelayNormal
                        INTEGER,
                     sensorProbeSwitchIndex
                        INTEGER,
                     sensorProbeSwitchRelayCycleTime
                        INTEGER,
                     sensorProbeSwitchRelayOnPort
                        INTEGER,
                     sensorProbeSwitchRelayActiveStatus
                        INTEGER,
                     sensorProbeSwitchRelayAction
                        INTEGER,
                     sensorProbeSwitchEmailInterval
                        INTEGER,
                     sensorProbeSwitchRelayOutputVoltStatus
                        INTEGER,
                     sensorProbeSwitchManualRelayCycleTime
                        INTEGER,
                     sensorProbeSwitchManualRelayAction
                        INTEGER,
                     sensorProbeSwitchRelayDescOn
                        DisplayString,
                     sensorProbeSwitchRelayDescOff
                        DisplayString,
                     sensorProbeSwitchIndexCount
                        INTEGER,
                     sensorProbeSwitchSirenCycleTime
                        INTEGER,
                     sensorProbeSwitchSirenOnPort
                        INTEGER,
                     sensorProbeSwitchSirenActiveStatus
                        INTEGER,
                     sensorProbeSwitchSirenAction
                        INTEGER,
                     sensorProbeSwitchAcknowledgement
                        INTEGER,
                     sensorProbeSwitchSirenDelayAlarm
                        INTEGER,
                     sensorProbeSwitchURL
                        DisplayString,
                     sensorProbeSwitchOpenURL
                        INTEGER,
                     sensorProbeSwitchContTimeHighCritical
                        INTEGER,
                     sensorProbeSwitchContTimeNormal
                        INTEGER,
                     sensorProbeSwitchCalendar
                        INTEGER,
                     sensorProbeSwitchRelayControlMode
                        INTEGER,
                     sensorProbeSwitchSirenControlMode
                        INTEGER,
                     sensorProbeSwitchSendNormalMail
                        INTEGER,
                     sensorProbeSwitchSendTrap
                        INTEGER,
                     sensorProbeSwitchSendMail
                        INTEGER,
                     sensorProbeSwitchWaterRopeLeakLocation
                        INTEGER,
                     sensorProbeSwitchWaterRopeLength
                        INTEGER,
                     sensorProbeSwitchWaterRopeUnit
                        INTEGER,
                     sensorProbeSwitchWaterRopeImpedance
                        INTEGER,
                     sensorProbeSwitchWaterRopeRaw
                        INTEGER,
                     sensorProbeSwitchWaterRopeType
                        INTEGER
                  }
                  sensorProbeSwitchDescription OBJECT-TYPE
                     SYNTAX  DisplayString
                     ACCESS  read-write
                     STATUS  mandatory
                     DESCRIPTION
                     "A Description of this sensor Switch"
                     ::=  {  sensorProbeSwitchEntry 1   }

                    sensorProbeSwitchLocation OBJECT-TYPE
                       SYNTAX  DisplayString
                       ACCESS  read-write
                       STATUS  mandatory
                       DESCRIPTION
                       "The physical location of this sensor Switch"
                       ::=  {  sensorProbeSwitchEntry 2   }

                  sensorProbeSwitchStatus OBJECT-TYPE
                     SYNTAX  INTEGER {
                        noStatus(1),
                        normal(2),
                        highCritical(4),
                        lowCritical(6),
                        sensorError(7),
                        relayOn(8),
                        relayOff(9)
                     }
                     ACCESS  read-only
                     STATUS  mandatory
                     DESCRIPTION
                     "The current status of this Sensor, only input switches have a status"
                     ::=  {  sensorProbeSwitchEntry 3  }

                  sensorProbeSwitchOnline OBJECT-TYPE
                     SYNTAX  INTEGER {
                        online(1),
                        offline(2)
                     }
                     ACCESS  read-only
                     STATUS  mandatory
                     DESCRIPTION
                     "If this Sensor is currently online"
                        ::=  {  sensorProbeSwitchEntry 4  }

                  sensorProbeSwitchGoOnline OBJECT-TYPE
                     SYNTAX  INTEGER {
                        goOnline(1),
                        goOffline(2)
                     }
                     ACCESS  read-write
                     STATUS  mandatory
                     DESCRIPTION
                     "To put online enter a 1, to take offline enter a 2"
                     ::=  {  sensorProbeSwitchEntry 5  }

                  sensorProbeSwitchDirection OBJECT-TYPE
                     SYNTAX  INTEGER {
                        input(0),
                        output(1)
                     }
                     ACCESS  read-write
                     STATUS  mandatory
                     DESCRIPTION
                     "To set a switch to input enter 0. To set a switch to output enter 1"
                     ::=  {  sensorProbeSwitchEntry 6  }

                  sensorProbeSwitchNormalState OBJECT-TYPE
                     SYNTAX  INTEGER {
                        closed(0),
                        open(1)
                     }
                     ACCESS  read-write
                     STATUS  mandatory
                     DESCRIPTION
                     "The normal state of an input switch. If an input switch is in this state it is normal, else it is critical. An open switch senses +5 volts. A closed switch senses 0 volts."
                     ::=  {  sensorProbeSwitchEntry 7  }
                     
                  sensorProbeSwitchOutputLevel OBJECT-TYPE
                     SYNTAX  INTEGER {
                        low(0),
                        high(1)
                     }
                     ACCESS  read-write
                     STATUS  mandatory
                     DESCRIPTION
                     "An output swith can be set to this level"
                     ::=  {  sensorProbeSwitchEntry 8  }
                     
                  sensorProbeSensorType OBJECT-TYPE
                     SYNTAX  INTEGER {
                        temperature(1),
                        fourTo20mA(2),
                        humidity(3),
                        water(4),
                        atod(5),
                        security(6),
                        airflow(8),
                        siren(9),
                        dryContact(10),
                        voltage(12),
                        relay(13),
                        motion(14)
                     }

                     ACCESS  read-write
                     STATUS  mandatory
                     DESCRIPTION
                     "Enter the type of this Sensor"
                     ::=  {  sensorProbeSwitchEntry 9  }

                  sensorProbeSwitchEmailTrapLimit OBJECT-TYPE
                     SYNTAX  INTEGER {
                        disable(0),
                        enable(1)
                     }
                     ACCESS  read-write
                     STATUS  mandatory
                     DESCRIPTION
                     "Enable email/trap limit feature"
                     ::=  {  sensorProbeSwitchEntry 11   }

                  sensorProbeSwitchEmailTrapSchedule OBJECT-TYPE
                     SYNTAX  DisplayString
                     ACCESS  read-write
                     STATUS  mandatory
                     DESCRIPTION
                     "SP Only: Email/trap limit schedule for this sensor"
                     ::=  {  sensorProbeSwitchEntry 12   }

                  sensorProbeSwitchEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  sensorProbeSwitchEntry 13   }

                  sensorProbeSwitchSendNormalTrap OBJECT-TYPE
                     SYNTAX  INTEGER {
                        disable(0),
                        enable(1)
                     }
                     ACCESS  read-write
                     STATUS  mandatory
                     DESCRIPTION
                     "Enable sending email/trap when sensor goes to normal"
                     ::=  {  sensorProbeSwitchEntry 14   }

                  sensorProbeSwitchDelayError OBJECT-TYPE
                     SYNTAX  INTEGER (0..65534)
                     ACCESS  read-write
                     STATUS  mandatory
                     DESCRIPTION
                     "Time in seconds after the sensor has been in error status before report as an error"
                     ::=  {  sensorProbeSwitchEntry 15   }

                  sensorProbeSwitchDelayNormal OBJECT-TYPE
                     SYNTAX  INTEGER (0..65534)
                     ACCESS  read-write
                     STATUS  mandatory
                     DESCRIPTION
                     "Time in seconds after the sensor change from error to normal before report as normal"
                     ::=  {  sensorProbeSwitchEntry 16   }

                  sensorProbeSwitchIndex OBJECT-TYPE
                     SYNTAX  INTEGER (0..67)
                     ACCESS  read-only
                     STATUS  mandatory
                     DESCRIPTION
                     "The index into the Switch sensor table"
                     ::=  {  sensorProbeSwitchEntry 17   }

                  sensorProbeSwitchRelayCycleTime OBJECT-TYPE
                     SYNTAX INTEGER (1..255)
                     ACCESS read-write
                     STATUS mandatory
                     DESCRIPTION
                     "Relay toggle period in seconds for Cycle action."
                     ::=  {  sensorProbeSwitchEntry 18   }

                  sensorProbeSwitchRelayOnPort OBJECT-TYPE
                     SYNTAX INTEGER (0..255)
                     ACCESS read-write
                     STATUS mandatory
                     DESCRIPTION
                     "The sensor port that the relay will listen to. If this is set to 255, then the relay will not listen to any sensor ports"
                     ::=  {  sensorProbeSwitchEntry 19   }

                  sensorProbeSwitchRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  sensorProbeSwitchEntry 20   }

                  sensorProbeSwitchRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  sensorProbeSwitchEntry 21   }

                  sensorProbeSwitchEmailInterval OBJECT-TYPE
                     SYNTAX  INTEGER (0..60)
                     ACCESS  read-write
                     STATUS  mandatory
                     DESCRIPTION
                     "CP8 Only: Minimum time between each email (can be from 0 to 60 minutes)"
                     ::=  {  sensorProbeSwitchEntry 22   }

                  sensorProbeSwitchRelayOutputVoltStatus OBJECT-TYPE
                     SYNTAX  INTEGER {
                        sensorError(7),
                        noVoltagePresent(10),
                        voltagePresent(11)
                     }
                     ACCESS  read-only
                     STATUS  mandatory
                     DESCRIPTION
                     "SP Only: The current voltage status of the relay"
                        ::=  {  sensorProbeSwitchEntry 23  }

                  sensorProbeSwitchManualRelayCycleTime OBJECT-TYPE
                     SYNTAX INTEGER (1..255)
                     ACCESS read-write
                     STATUS mandatory
                     DESCRIPTION
                     "Relay toggle period in seconds for Manual Cycle action."
                     ::= { sensorProbeSwitchEntry 24 }

                  sensorProbeSwitchManualRelayAction OBJECT-TYPE
                     SYNTAX INTEGER {
                        allow-sensor-control(1),
                        turn-on(3),
                        turn-off(4),
                        cycle-Off-On-Off(7),                        
                        cycle-On-Off-On(8)
                     }
                     ACCESS read-write
                     STATUS mandatory
                     DESCRIPTION
                     "Control the relay manualy"
                     ::= { sensorProbeSwitchEntry 25 }

                  sensorProbeSwitchRelayDescOn OBJECT-TYPE
                     SYNTAX  DisplayString
                     ACCESS  read-write
                     STATUS  mandatory
                     DESCRIPTION
                     "Description of relay On"
                     ::=  {  sensorProbeSwitchEntry 26   }

                  sensorProbeSwitchRelayDescOff OBJECT-TYPE
                     SYNTAX  DisplayString
                     ACCESS  read-write
                     STATUS  mandatory
                     DESCRIPTION
                     "Description of relay Off"
                     ::=  {  sensorProbeSwitchEntry 27   }

                  sensorProbeSwitchIndexCount OBJECT-TYPE
                     SYNTAX  INTEGER
                     ACCESS  read-only
                     STATUS  mandatory
                     DESCRIPTION
                     "Number of Switch sensor online"
                     ::=  {  sensorProbeSwitchEntry 28   }

                  sensorProbeSwitchSirenCycleTime OBJECT-TYPE
                     SYNTAX INTEGER (1..255)
                     ACCESS read-write
                     STATUS mandatory
                     DESCRIPTION
                     "Siren toggle period in seconds for Cycle action."
                     ::=  {  sensorProbeSwitchEntry 29   }

                  sensorProbeSwitchSirenOnPort OBJECT-TYPE
                     SYNTAX INTEGER (0..255)
                     ACCESS read-write
                     STATUS mandatory
                     DESCRIPTION
                     "The sensor port that the siren will listen to. If this is set to 255, then the siren will not listen to any sensor ports"
                     ::=  {  sensorProbeSwitchEntry 30   }

                  sensorProbeSwitchSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::=  {  sensorProbeSwitchEntry 31   }

                  sensorProbeSwitchSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  sensorProbeSwitchEntry 32   }

                  sensorProbeSwitchAcknowledgement OBJECT-TYPE
                     SYNTAX INTEGER {
                        ack(1)
                     }
                     ACCESS read-write
                     STATUS mandatory
                     DESCRIPTION
                     "Acknowledged sensor error and stop notification"
                     ::= {  sensorProbeSwitchEntry 33 }

                  sensorProbeSwitchSirenDelayAlarm OBJECT-TYPE
                     SYNTAX INTEGER (1..255)
                     ACCESS read-write
                     STATUS mandatory
                     DESCRIPTION
                     "Siren delay in seconds before start Alarm."
                     ::=  {  sensorProbeSwitchEntry 34   }

                  sensorProbeSwitchURL OBJECT-TYPE
                     SYNTAX  DisplayString
                     ACCESS  read-write
                     STATUS  mandatory
                     DESCRIPTION
                     "Sensor URL link."
                     ::=  {  sensorProbeSwitchEntry 35 }

                  sensorProbeSwitchOpenURL OBJECT-TYPE
                     SYNTAX  INTEGER {
                        cur-window(0),
                        new-window(2)
                     }
                     ACCESS  read-write
                     STATUS  mandatory
                     DESCRIPTION
                     "Open URL in this browser or open in a new window."
                     ::=  {  sensorProbeSwitchEntry 36 }

                  sensorProbeSwitchContTimeHighCritical OBJECT-TYPE
                     SYNTAX INTEGER (0..65535)
                     ACCESS read-write
                     STATUS mandatory
                     DESCRIPTION
                     "Continuous time for this sensor to be in High Critical before accepting new Status."
                     ::= {  sensorProbeSwitchEntry 37 }

                  sensorProbeSwitchContTimeNormal OBJECT-TYPE
                     SYNTAX INTEGER (0..65535)
                     ACCESS read-write
                     STATUS mandatory
                     DESCRIPTION
                     "Continuous time for this sensor to be in Normal before accepting new Status."
                     ::= {  sensorProbeSwitchEntry 39 }

                  sensorProbeSwitchCalendar OBJECT-TYPE
                     SYNTAX INTEGER {
                        disable(0),
                        enable(1)
                     }
                     ACCESS read-write
                     STATUS mandatory
                     DESCRIPTION
                     "Enable or disable the calendar filtering working hours of sensor."
                     ::= {  sensorProbeSwitchEntry 43 }

                  sensorProbeSwitchRelayControlMode OBJECT-TYPE
                     SYNTAX  INTEGER {
                        manual-control(0),
                        notification-control(1),
                        time-control(2),
                        thermostat-control(3)
                     }
                     ACCESS  read-write
                     STATUS  mandatory
                     DESCRIPTION
                     "Relay Control Mode used for selecting the mode to control a relay."
                     ::=  {  sensorProbeSwitchEntry 44  }

                  sensorProbeSwitchSirenControlMode OBJECT-TYPE
                     SYNTAX  INTEGER {
                        manual-control(0),
                        notification-control(1),
                        time-control(2)
                     }
                     ACCESS  read-write
                     STATUS  mandatory
                     DESCRIPTION
                     "Siren Control Mode used for selecting the mode to control a siren."
                     ::=  {  sensorProbeSwitchEntry 45  }

                  sensorProbeSwitchSendNormalMail OBJECT-TYPE
                     SYNTAX  INTEGER {
                        disable(0),
                        enable(1)
                     }
                     ACCESS  read-write
                     STATUS  mandatory
                     DESCRIPTION
                     "Enable sending email when sensor goes to normal"
                     ::=  {  sensorProbeSwitchEntry 46 }

                  sensorProbeSwitchSendTrap OBJECT-TYPE
                     SYNTAX  INTEGER {
                        disable(0),
                        enable(1)
                     }
                     ACCESS  read-write
                     STATUS  mandatory
                     DESCRIPTION
                     "Enable sending trap when sensor change status"
                     ::=  {  sensorProbeSwitchEntry 47 }

                  sensorProbeSwitchSendMail OBJECT-TYPE
                     SYNTAX  INTEGER {
                        disable(0),
                        enable(1)
                     }
                     ACCESS  read-write
                     STATUS  mandatory
                     DESCRIPTION
                     "Enable sending email when sensor change status"
                     ::=  {  sensorProbeSwitchEntry 48 }

                  sensorProbeSwitchWaterRopeLeakLocation OBJECT-TYPE
                     SYNTAX INTEGER
                     ACCESS read-only
                     STATUS mandatory
                     DESCRIPTION
                     "Location of leakage of water rope sensor."
                     ::= {  sensorProbeSwitchEntry 49 }

                  sensorProbeSwitchWaterRopeLength OBJECT-TYPE
                     SYNTAX INTEGER
                     ACCESS read-only
                     STATUS mandatory
                     DESCRIPTION
                     "Length of water rope sensor."
                     ::= {  sensorProbeSwitchEntry 50 }

                  sensorProbeSwitchWaterRopeUnit OBJECT-TYPE
                     SYNTAX  INTEGER {
                        meters(0),
                        feet(1)
                     }
                     ACCESS  read-write
                     STATUS  mandatory
                     DESCRIPTION
                     "Display unit of water rope sensor."
                     ::=  {  sensorProbeSwitchEntry 51   }

                  sensorProbeSwitchWaterRopeImpedance OBJECT-TYPE
                     SYNTAX INTEGER (0..65535)
                     ACCESS read-write
                     STATUS mandatory
                     DESCRIPTION
                     "Sensing wire impedance per meter value times 100"
                     ::= {  sensorProbeSwitchEntry 52 }

                  sensorProbeSwitchWaterRopeRaw OBJECT-TYPE
                     SYNTAX INTEGER
                     ACCESS read-only
                     STATUS mandatory
                     DESCRIPTION
                     "Raw value of location or length in ohms"
                     ::= {  sensorProbeSwitchEntry 53 }

                  sensorProbeSwitchWaterRopeType OBJECT-TYPE
                     SYNTAX  INTEGER {
                        custom(0),
                        water(1),
                        fuel(2)
                     }
                     ACCESS  read-write
                     STATUS  mandatory
                     DESCRIPTION
                     "Water rope sensing cable type"
                     ::=  {  sensorProbeSwitchEntry 55   }

               sensorProbeOtherSensor OBJECT IDENTIFIER ::= { sensorProbeEntry 19  }

                  sensorProbeIRMSSensor OBJECT IDENTIFIER ::= { sensorProbeOtherSensor 26  }

                     sensorProbeIRMSSensorNumber OBJECT-TYPE
                        SYNTAX INTEGER
                        ACCESS read-only
                        STATUS mandatory
                        DESCRIPTION
                        "The total number of RMS current Sensor port."
                        ::= {  sensorProbeIRMSSensor 1 }

                     sensorProbeIRMSSensorTable OBJECT-TYPE
                        SYNTAX  SEQUENCE OF SensorProbeIRMSSensorEntry
                        ACCESS  not-accessible
                        STATUS  mandatory
                        DESCRIPTION
                        "This table contains the data for every RMS current Sensor in the SensorArray. Each row in the table contains data for a different RMS current Sensor."
                        ::=  {  sensorProbeIRMSSensor 2   }

                        sensorProbeIRMSSensorEntry OBJECT-TYPE
                           SYNTAX  SensorProbeIRMSSensorEntry
                           ACCESS  not-accessible
                           STATUS  mandatory
                           DESCRIPTION
                           "This is an entry in the sensorProbeIRMSSensorEntry Table"
                           INDEX         { sensorProbeIRMSSensorIndex }
                           ::=  { sensorProbeIRMSSensorTable 1 }

                        SensorProbeIRMSSensorEntry ::= SEQUENCE {
                           sensorProbeIRMSSensorIndex
                              INTEGER,
                           sensorProbeIRMSDescription
                              DisplayString,
                           sensorProbeIRMSPercent
                              INTEGER,
                           sensorProbeIRMSStatus
                              INTEGER,
                           sensorProbeIRMSOnline
                              INTEGER,
                           sensorProbeIRMSGoOnline
                              INTEGER,
                           sensorProbeIRMSHighWarning
                              INTEGER,
                           sensorProbeIRMSHighCritical
                              INTEGER,
                           sensorProbeIRMSLowWarning
                              INTEGER,
                           sensorProbeIRMSLowCritical
                              INTEGER,
                           sensorProbeIRMSRearm
                              INTEGER,
                           sensorProbeIRMSRaw
                              INTEGER,
                           sensorProbeIRMSEmailTrapLimit
                              INTEGER,
                           sensorProbeIRMSDelayError
                              INTEGER,
                           sensorProbeIRMSDelayNormal
                              INTEGER,
                           sensorProbeIRMSRelayCycleTime
                              INTEGER,
                           sensorProbeIRMSRelayOnPort
                              INTEGER,
                           sensorProbeIRMSRelayActiveStatus
                              INTEGER,
                           sensorProbeIRMSRelayAction
                              INTEGER,
                           sensorProbeIRMSSirenCycleTime
                              INTEGER,
                           sensorProbeIRMSSirenOnPort
                              INTEGER,
                           sensorProbeIRMSSirenActiveStatus
                              INTEGER,
                           sensorProbeIRMSSirenAction
                              INTEGER,
                           sensorProbeIRMSAcknowledgement
                              INTEGER,
                           sensorProbeIRMSSirenDelayAlarm
                              INTEGER,
                           sensorProbeIRMSURL
                              DisplayString,
                           sensorProbeIRMSOpenURL
                              INTEGER,
                           sensorProbeIRMSDatacollectType
                              INTEGER,
                           sensorProbeIRMSContTimeHighCritical
                              INTEGER,
                           sensorProbeIRMSContTimeHighWarning
                              INTEGER,
                           sensorProbeIRMSContTimeNormal
                              INTEGER,
                           sensorProbeIRMSContTimeLowWarning
                              INTEGER,
                           sensorProbeIRMSContTimeLowCritical
                              INTEGER,
                           sensorProbeIRMSContTimeSensorError
                              INTEGER,
                           sensorProbeIRMSCalendar
                              INTEGER
                        }

                          sensorProbeIRMSSensorIndex OBJECT-TYPE
                              SYNTAX  INTEGER (0..7)
                              ACCESS  read-only
                              STATUS  mandatory
                              DESCRIPTION
                              "A unique value for each IRMS sensor port."
                              ::=  {  sensorProbeIRMSSensorEntry 1   }

                          sensorProbeIRMSDescription OBJECT-TYPE
                              SYNTAX  DisplayString
                              ACCESS  read-write
                              STATUS  mandatory
                              DESCRIPTION
                              "A Description of this sensor IRMS"
                              ::=  {  sensorProbeIRMSSensorEntry 2   }

                          sensorProbeIRMSPercent OBJECT-TYPE
                              SYNTAX  INTEGER (-32768..32767)
                              ACCESS  read-only
                              STATUS  mandatory
                              DESCRIPTION
                              "The relative IRMS percentage measured by this sensor"
                              ::=  {  sensorProbeIRMSSensorEntry 3   }

                           sensorProbeIRMSStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeIRMSSensorEntry 4   }

                           sensorProbeIRMSOnline OBJECT-TYPE
                              SYNTAX  INTEGER {
                                 online(1),
                                 offline(2)
                              }
                              ACCESS  read-only
                              STATUS  mandatory
                              DESCRIPTION
                              "If this Sensor is currently online"
                                 ::=  {  sensorProbeIRMSSensorEntry 5   }

                           sensorProbeIRMSGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeIRMSSensorEntry 6   }

                           sensorProbeIRMSHighWarning OBJECT-TYPE
                              SYNTAX  INTEGER
                              ACCESS  read-write
                              STATUS  mandatory
                              DESCRIPTION
                              "How high the relative IRMS this sensor measures before it sends a warning"
                              ::=  {  sensorProbeIRMSSensorEntry 7   }

                           sensorProbeIRMSHighCritical OBJECT-TYPE
                              SYNTAX  INTEGER
                              ACCESS  read-write
                              STATUS  mandatory
                              DESCRIPTION
                              "How high the relative IRMS this sensor measures before it becomes critical"
                              ::=  {  sensorProbeIRMSSensorEntry 8   }

                           sensorProbeIRMSLowWarning OBJECT-TYPE
                              SYNTAX  INTEGER
                              ACCESS  read-write
                              STATUS  mandatory
                              DESCRIPTION
                              "How low the relative IRMS this sensor measures before it sends a warning"
                              ::=  {  sensorProbeIRMSSensorEntry 9   }

                           sensorProbeIRMSLowCritical OBJECT-TYPE
                              SYNTAX  INTEGER
                              ACCESS  read-write
                              STATUS  mandatory
                              DESCRIPTION
                              "How low the relative IRMS this sensor measures before it becomes critical"
                              ::=  {  sensorProbeIRMSSensorEntry 10   }

                           sensorProbeIRMSRearm OBJECT-TYPE
                              SYNTAX  INTEGER
                              ACCESS  read-write
                              STATUS  mandatory
                              DESCRIPTION
                              "The percent relative IRMS to rearm the status. For example if status goes from normal to warning, the IRMS must go down spAnalogueRearm below warning before the status goes to normal"
                              ::=  {  sensorProbeIRMSSensorEntry 11   }

                           sensorProbeIRMSRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeIRMSSensorEntry 13   }

                           sensorProbeIRMSEmailTrapLimit OBJECT-TYPE
                              SYNTAX  INTEGER {
                                 disable(0),
                                 enable(1)
                              }
                              ACCESS  read-write
                              STATUS  mandatory
                              DESCRIPTION
                              "Enable email/trap limit feature"
                              ::=  {  sensorProbeIRMSSensorEntry 17   }

                           sensorProbeIRMSDelayError OBJECT-TYPE
                              SYNTAX  INTEGER (0..65534)
                              ACCESS  read-write
                              STATUS  mandatory
                              DESCRIPTION
                              "Time in seconds after the sensor has been in error status before report as an error"
                              ::=  {  sensorProbeIRMSSensorEntry 21   }

                           sensorProbeIRMSDelayNormal OBJECT-TYPE
                              SYNTAX  INTEGER (0..65534)
                              ACCESS  read-write
                              STATUS  mandatory
                              DESCRIPTION
                              "Time in seconds after the sensor change from error to normal before report as normal"
                              ::=  {  sensorProbeIRMSSensorEntry 22   }

                           sensorProbeIRMSRelayCycleTime OBJECT-TYPE
                              SYNTAX INTEGER (1..255)
                              ACCESS read-write
                              STATUS mandatory
                              DESCRIPTION
                              "Relay toggle period in seconds for Cycle action."
                              ::=  {  sensorProbeIRMSSensorEntry 29   }

                           sensorProbeIRMSRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeIRMSSensorEntry 30   }

                           sensorProbeIRMSRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeIRMSSensorEntry 31   }

                           sensorProbeIRMSRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeIRMSSensorEntry 32   }

                           sensorProbeIRMSSirenCycleTime OBJECT-TYPE
                              SYNTAX INTEGER (1..255)
                              ACCESS read-write
                              STATUS mandatory
                              DESCRIPTION
                              "Siren toggle period in seconds for Cycle action."
                              ::=  {  sensorProbeIRMSSensorEntry 37   }

                           sensorProbeIRMSSirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeIRMSSensorEntry 38   }

                           sensorProbeIRMSSirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeIRMSSensorEntry 39   }

                           sensorProbeIRMSSirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeIRMSSensorEntry 40   }

                           sensorProbeIRMSAcknowledgement OBJECT-TYPE
                              SYNTAX INTEGER {
                                 ack(1)
                              }
                              ACCESS read-write
                              STATUS mandatory
                              DESCRIPTION
                              "Acknowledged sensor error and stop notification"
                              ::= {  sensorProbeIRMSSensorEntry 41 }

                           sensorProbeIRMSSirenDelayAlarm OBJECT-TYPE
                              SYNTAX INTEGER (1..255)
                              ACCESS read-write
                              STATUS mandatory
                              DESCRIPTION
                              "Siren delay in seconds before start Alarm."
                              ::=  {  sensorProbeIRMSSensorEntry 42   }

                           sensorProbeIRMSURL OBJECT-TYPE
                              SYNTAX DisplayString
                              ACCESS read-write
                              STATUS mandatory
                              DESCRIPTION
                              "Sensor URL link."
                              ::=  {  sensorProbeIRMSSensorEntry 43   }

                           sensorProbeIRMSOpenURL OBJECT-TYPE
                              SYNTAX INTEGER {
                                 cur-window(0),
                                 new-window(2)
                              }
                              ACCESS read-write
                              STATUS mandatory
                              DESCRIPTION
                              "Open URL in this browser or open in a new window."
                              ::=  {  sensorProbeIRMSSensorEntry 44   }

                           sensorProbeIRMSDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeIRMSSensorEntry 45   }

                           sensorProbeIRMSContTimeHighCritical OBJECT-TYPE
                              SYNTAX INTEGER (0..65535)
                              ACCESS read-write
                              STATUS mandatory
                              DESCRIPTION
                              "Continuous time for this sensor to be in High Critical before accepting new Status."
                              ::= {  sensorProbeIRMSSensorEntry 46 }

                           sensorProbeIRMSContTimeHighWarning OBJECT-TYPE
                              SYNTAX INTEGER (0..65535)
                              ACCESS read-write
                              STATUS mandatory
                              DESCRIPTION
                              "Continuous time for this sensor to be in High Warning before accepting new Status."
                              ::= {  sensorProbeIRMSSensorEntry 47 }

                           sensorProbeIRMSContTimeNormal OBJECT-TYPE
                              SYNTAX INTEGER (0..65535)
                              ACCESS read-write
                              STATUS mandatory
                              DESCRIPTION
                              "Continuous time for this sensor to be in Normal before accepting new Status."
                              ::= {  sensorProbeIRMSSensorEntry 48 }

                           sensorProbeIRMSContTimeLowWarning OBJECT-TYPE
                              SYNTAX INTEGER (0..65535)
                              ACCESS read-write
                              STATUS mandatory
                              DESCRIPTION
                              "Continuous time for this sensor to be in Low Warning before accepting new Status."
                              ::= {  sensorProbeIRMSSensorEntry 49 }

                           sensorProbeIRMSContTimeLowCritical OBJECT-TYPE
                              SYNTAX INTEGER (0..65535)
                              ACCESS read-write
                              STATUS mandatory
                              DESCRIPTION
                              "Continuous time for this sensor to be in Low Critical before accepting new Status."
                              ::= {  sensorProbeIRMSSensorEntry 50 }

                           sensorProbeIRMSContTimeSensorError OBJECT-TYPE
                              SYNTAX INTEGER (0..65535)
                              ACCESS read-write
                              STATUS mandatory
                              DESCRIPTION
                              "Continuous time for this sensor to be in Sensor Error before accepting new Status."
                              ::= {  sensorProbeIRMSSensorEntry 51 }

                           sensorProbeIRMSCalendar OBJECT-TYPE
                              SYNTAX INTEGER {
                                 disable(0),
                                 enable(1)
                              }
                              ACCESS read-write
                              STATUS mandatory
                              DESCRIPTION
                              "Enable or disable the calendar filtering working hours of sensor."
                              ::= {  sensorProbeIRMSSensorEntry 52 }

                  sensorProbeVRMSSensor OBJECT IDENTIFIER ::= { sensorProbeOtherSensor 27  }

                     sensorProbeVRMSSensorNumber OBJECT-TYPE
                        SYNTAX INTEGER
                        ACCESS read-only
                        STATUS mandatory
                        DESCRIPTION
                        "The total number of RMS voltage Sensor port."
                        ::= {  sensorProbeVRMSSensor 1 }

                     sensorProbeVRMSSensorTable OBJECT-TYPE
                        SYNTAX  SEQUENCE OF SensorProbeVRMSSensorEntry
                        ACCESS  not-accessible
                        STATUS  mandatory
                        DESCRIPTION
                        "This table contains the data for every RMS voltage Sensor in the SensorArray. Each row in the table contains data for a different RMS voltage Sensor."
                        ::=  {  sensorProbeVRMSSensor 2   }

                        sensorProbeVRMSSensorEntry OBJECT-TYPE
                           SYNTAX  SensorProbeVRMSSensorEntry
                           ACCESS  not-accessible
                           STATUS  mandatory
                           DESCRIPTION
                           "This is an entry in the sensorProbeVRMSSensorEntry Table"
                           INDEX         { sensorProbeVRMSSensorIndex }
                           ::=  { sensorProbeVRMSSensorTable 1 }

                        SensorProbeVRMSSensorEntry ::= SEQUENCE {
                           sensorProbeVRMSSensorIndex
                              INTEGER,
                           sensorProbeVRMSDescription
                              DisplayString,
                           sensorProbeVRMSPercent
                              INTEGER,
                           sensorProbeVRMSStatus
                              INTEGER,
                           sensorProbeVRMSOnline
                              INTEGER,
                           sensorProbeVRMSGoOnline
                              INTEGER,
                           sensorProbeVRMSHighWarning
                              INTEGER,
                           sensorProbeVRMSHighCritical
                              INTEGER,
                           sensorProbeVRMSLowWarning
                              INTEGER,
                           sensorProbeVRMSLowCritical
                              INTEGER,
                           sensorProbeVRMSRearm
                              INTEGER,
                           sensorProbeVRMSRaw
                              INTEGER,
                           sensorProbeVRMSEmailTrapLimit
                              INTEGER,
                           sensorProbeVRMSDelayError
                              INTEGER,
                           sensorProbeVRMSDelayNormal
                              INTEGER,
                           sensorProbeVRMSRelayCycleTime
                              INTEGER,
                           sensorProbeVRMSRelayOnPort
                              INTEGER,
                           sensorProbeVRMSRelayActiveStatus
                              INTEGER,
                           sensorProbeVRMSRelayAction
                              INTEGER,
                           sensorProbeVRMSSirenCycleTime
                              INTEGER,
                           sensorProbeVRMSSirenOnPort
                              INTEGER,
                           sensorProbeVRMSSirenActiveStatus
                              INTEGER,
                           sensorProbeVRMSSirenAction
                              INTEGER,
                           sensorProbeVRMSAcknowledgement
                              INTEGER,
                           sensorProbeVRMSSirenDelayAlarm
                              INTEGER,
                           sensorProbeVRMSvoltageMode
                              INTEGER,
                           sensorProbeVRMSURL
                              DisplayString,
                           sensorProbeVRMSOpenURL
                              INTEGER,
                           sensorProbeVRMSDatacollectType
                              INTEGER,
                           sensorProbeVRMSContTimeHighCritical
                              INTEGER,
                           sensorProbeVRMSContTimeHighWarning
                              INTEGER,
                           sensorProbeVRMSContTimeNormal
                              INTEGER,
                           sensorProbeVRMSContTimeLowWarning
                              INTEGER,
                           sensorProbeVRMSContTimeLowCritical
                              INTEGER,
                           sensorProbeVRMSContTimeSensorError
                              INTEGER,
                           sensorProbeVRMSCalendar
                              INTEGER
                        }

                          sensorProbeVRMSSensorIndex OBJECT-TYPE
                              SYNTAX  INTEGER (0..7)
                              ACCESS  read-only
                              STATUS  mandatory
                              DESCRIPTION
                              "A unique value for each VRMS sensor port."
                              ::=  {  sensorProbeVRMSSensorEntry 1   }

                          sensorProbeVRMSDescription OBJECT-TYPE
                              SYNTAX  DisplayString
                              ACCESS  read-write
                              STATUS  mandatory
                              DESCRIPTION
                              "A Description of this sensor VRMS"
                              ::=  {  sensorProbeVRMSSensorEntry 2   }

                          sensorProbeVRMSPercent OBJECT-TYPE
                              SYNTAX  INTEGER (-32768..32767)
                              ACCESS  read-only
                              STATUS  mandatory
                              DESCRIPTION
                              "The relative VRMS percentage measured by this sensor"
                              ::=  {  sensorProbeVRMSSensorEntry 3   }

                           sensorProbeVRMSStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVRMSSensorEntry 4   }

                           sensorProbeVRMSOnline OBJECT-TYPE
                              SYNTAX  INTEGER {
                                 online(1),
                                 offline(2)
                              }
                              ACCESS  read-only
                              STATUS  mandatory
                              DESCRIPTION
                              "If this Sensor is currently online"
                                 ::=  {  sensorProbeVRMSSensorEntry 5   }

                           sensorProbeVRMSGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVRMSSensorEntry 6   }

                           sensorProbeVRMSHighWarning OBJECT-TYPE
                              SYNTAX  INTEGER
                              ACCESS  read-write
                              STATUS  mandatory
                              DESCRIPTION
                              "How high the relative VRMS this sensor measures before it sends a warning"
                              ::=  {  sensorProbeVRMSSensorEntry 7   }

                           sensorProbeVRMSHighCritical OBJECT-TYPE
                              SYNTAX  INTEGER
                              ACCESS  read-write
                              STATUS  mandatory
                              DESCRIPTION
                              "How high the relative VRMS this sensor measures before it becomes critical"
                              ::=  {  sensorProbeVRMSSensorEntry 8   }

                           sensorProbeVRMSLowWarning OBJECT-TYPE
                              SYNTAX  INTEGER
                              ACCESS  read-write
                              STATUS  mandatory
                              DESCRIPTION
                              "How low the relative VRMS this sensor measures before it sends a warning"
                              ::=  {  sensorProbeVRMSSensorEntry 9   }

                           sensorProbeVRMSLowCritical OBJECT-TYPE
                              SYNTAX  INTEGER
                              ACCESS  read-write
                              STATUS  mandatory
                              DESCRIPTION
                              "How low the relative VRMS this sensor measures before it becomes critical"
                              ::=  {  sensorProbeVRMSSensorEntry 10   }

                           sensorProbeVRMSRearm OBJECT-TYPE
                              SYNTAX  INTEGER
                              ACCESS  read-write
                              STATUS  mandatory
                              DESCRIPTION
                              "The percent relative VRMS to rearm the status. For example if status goes from normal to warning, the VRMS must go down spAnalogueRearm below warning before the status goes to normal"
                              ::=  {  sensorProbeVRMSSensorEntry 11   }

                           sensorProbeVRMSRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeVRMSSensorEntry 13   }

                           sensorProbeVRMSEmailTrapLimit OBJECT-TYPE
                              SYNTAX  INTEGER {
                                 disable(0),
                                 enable(1)
                              }
                              ACCESS  read-write
                              STATUS  mandatory
                              DESCRIPTION
                              "Enable email/trap limit feature"
                              ::=  {  sensorProbeVRMSSensorEntry 17   }

                           sensorProbeVRMSDelayError OBJECT-TYPE
                              SYNTAX  INTEGER (0..65534)
                              ACCESS  read-write
                              STATUS  mandatory
                              DESCRIPTION
                              "Time in seconds after the sensor has been in error status before report as an error"
                              ::=  {  sensorProbeVRMSSensorEntry 21   }

                           sensorProbeVRMSDelayNormal OBJECT-TYPE
                              SYNTAX  INTEGER (0..65534)
                              ACCESS  read-write
                              STATUS  mandatory
                              DESCRIPTION
                              "Time in seconds after the sensor change from error to normal before report as normal"
                              ::=  {  sensorProbeVRMSSensorEntry 22   }

                           sensorProbeVRMSRelayCycleTime OBJECT-TYPE
                              SYNTAX INTEGER (1..255)
                              ACCESS read-write
                              STATUS mandatory
                              DESCRIPTION
                              "Relay toggle period in seconds for Cycle action."
                              ::=  {  sensorProbeVRMSSensorEntry 29   }

                           sensorProbeVRMSRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeVRMSSensorEntry 30   }

                           sensorProbeVRMSRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeVRMSSensorEntry 31   }

                           sensorProbeVRMSRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeVRMSSensorEntry 32   }

                           sensorProbeVRMSSirenCycleTime OBJECT-TYPE
                              SYNTAX INTEGER (1..255)
                              ACCESS read-write
                              STATUS mandatory
                              DESCRIPTION
                              "Siren toggle period in seconds for Cycle action."
                              ::=  {  sensorProbeVRMSSensorEntry 37   }

                           sensorProbeVRMSSirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeVRMSSensorEntry 38   }

                           sensorProbeVRMSSirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeVRMSSensorEntry 39   }

                           sensorProbeVRMSSirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeVRMSSensorEntry 40   }

                           sensorProbeVRMSAcknowledgement OBJECT-TYPE
                              SYNTAX INTEGER {
                                 ack(1)
                              }
                              ACCESS read-write
                              STATUS mandatory
                              DESCRIPTION
                              "Acknowledged sensor error and stop notification"
                              ::= {  sensorProbeVRMSSensorEntry 41 }

                           sensorProbeVRMSSirenDelayAlarm OBJECT-TYPE
                              SYNTAX INTEGER (1..255)
                              ACCESS read-write
                              STATUS mandatory
                              DESCRIPTION
                              "Siren delay in seconds before start Alarm."
                              ::=  {  sensorProbeVRMSSensorEntry 42   }

                           sensorProbeVRMSvoltageMode OBJECT-TYPE
                              SYNTAX INTEGER {
                                 ac-110(110),
                                 ac-220(220)
                              }
                              ACCESS read-write
                              STATUS mandatory
                              DESCRIPTION
                              "VRMS Voltage Mode."
                              ::=  {  sensorProbeVRMSSensorEntry 43   }

                           sensorProbeVRMSURL OBJECT-TYPE
                              SYNTAX DisplayString
                              ACCESS read-write
                              STATUS mandatory
                              DESCRIPTION
                              "Sensor URL link."
                              ::=  {  sensorProbeVRMSSensorEntry 44   }

                           sensorProbeVRMSOpenURL OBJECT-TYPE
                              SYNTAX INTEGER {
                                 cur-window(0),
                                 new-window(2)
                              }
                              ACCESS read-write
                              STATUS mandatory
                              DESCRIPTION
                              "Open URL in this browser or open in a new window."
                              ::=  {  sensorProbeVRMSSensorEntry 45   }

                           sensorProbeVRMSDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeVRMSSensorEntry 46   }

                           sensorProbeVRMSContTimeHighCritical OBJECT-TYPE
                              SYNTAX INTEGER (0..65535)
                              ACCESS read-write
                              STATUS mandatory
                              DESCRIPTION
                              "Continuous time for this sensor to be in High Critical before accepting new Status."
                              ::= {  sensorProbeVRMSSensorEntry 47 }

                           sensorProbeVRMSContTimeHighWarning OBJECT-TYPE
                              SYNTAX INTEGER (0..65535)
                              ACCESS read-write
                              STATUS mandatory
                              DESCRIPTION
                              "Continuous time for this sensor to be in High Warning before accepting new Status."
                              ::= {  sensorProbeVRMSSensorEntry 48 }

                           sensorProbeVRMSContTimeNormal OBJECT-TYPE
                              SYNTAX INTEGER (0..65535)
                              ACCESS read-write
                              STATUS mandatory
                              DESCRIPTION
                              "Continuous time for this sensor to be in Normal before accepting new Status."
                              ::= {  sensorProbeVRMSSensorEntry 49 }

                           sensorProbeVRMSContTimeLowWarning OBJECT-TYPE
                              SYNTAX INTEGER (0..65535)
                              ACCESS read-write
                              STATUS mandatory
                              DESCRIPTION
                              "Continuous time for this sensor to be in Low Warning before accepting new Status."
                              ::= {  sensorProbeVRMSSensorEntry 50 }

                           sensorProbeVRMSContTimeLowCritical OBJECT-TYPE
                              SYNTAX INTEGER (0..65535)
                              ACCESS read-write
                              STATUS mandatory
                              DESCRIPTION
                              "Continuous time for this sensor to be in Low Critical before accepting new Status."
                              ::= {  sensorProbeVRMSSensorEntry 51 }

                           sensorProbeVRMSContTimeSensorError OBJECT-TYPE
                              SYNTAX INTEGER (0..65535)
                              ACCESS read-write
                              STATUS mandatory
                              DESCRIPTION
                              "Continuous time for this sensor to be in Sensor Error before accepting new Status."
                              ::= {  sensorProbeVRMSSensorEntry 52 }

                           sensorProbeVRMSCalendar OBJECT-TYPE
                              SYNTAX INTEGER {
                                 disable(0),
                                 enable(1)
                              }
                              ACCESS read-write
                              STATUS mandatory
                              DESCRIPTION
                              "Enable or disable the calendar filtering working hours of sensor."
                              ::= {  sensorProbeVRMSSensorEntry 53 }

                  sensorProbeEnergySensor OBJECT IDENTIFIER ::= { sensorProbeOtherSensor 28  }

                     sensorProbeEnergySensorNumber OBJECT-TYPE
                        SYNTAX INTEGER
                        ACCESS read-only
                        STATUS mandatory
                        DESCRIPTION
                        "The total number of Energy Sensor port."
                        ::= {  sensorProbeEnergySensor 1 }

                     sensorProbeEnergySensorTable OBJECT-TYPE
                        SYNTAX  SEQUENCE OF SensorProbeEnergySensorEntry
                        ACCESS  not-accessible
                        STATUS  mandatory
                        DESCRIPTION
                        "This table contains the data for every Energy Sensor in the SensorArray. Each row in the table contains data for a different Energy Sensor."
                        ::=  {  sensorProbeEnergySensor 2   }

                        sensorProbeEnergySensorEntry OBJECT-TYPE
                           SYNTAX  SensorProbeEnergySensorEntry
                           ACCESS  not-accessible
                           STATUS  mandatory
                           DESCRIPTION
                           "This is an entry in the sensorProbeEnergySensorEntry Table"
                           INDEX         { sensorProbeEnergySensorIndex }
                           ::=  { sensorProbeEnergySensorTable 1 }

                        SensorProbeEnergySensorEntry ::= SEQUENCE {
                           sensorProbeEnergySensorIndex
                              INTEGER,
                           sensorProbeEnergyDescription
                              DisplayString,
                           sensorProbeEnergyPercent
                              INTEGER,
                           sensorProbeEnergyStatus
                              INTEGER,
                           sensorProbeEnergyOnline
                              INTEGER,
                           sensorProbeEnergyGoOnline
                              INTEGER,
                           sensorProbeEnergyHighWarning
                              INTEGER,
                           sensorProbeEnergyHighCritical
                              INTEGER,
                           sensorProbeEnergyLowWarning
                              INTEGER,
                           sensorProbeEnergyLowCritical
                              INTEGER,
                           sensorProbeEnergyRearm
                              INTEGER,
                           sensorProbeEnergyRaw
                              INTEGER,
                           sensorProbeEnergyEmailTrapLimit
                              INTEGER,
                           sensorProbeEnergyDelayError
                              INTEGER,
                           sensorProbeEnergyDelayNormal
                              INTEGER,
                           sensorProbeEnergyRelayCycleTime
                              INTEGER,
                           sensorProbeEnergyRelayOnPort
                              INTEGER,
                           sensorProbeEnergyRelayActiveStatus
                              INTEGER,
                           sensorProbeEnergyRelayAction
                              INTEGER,
                           sensorProbeEnergySirenCycleTime
                              INTEGER,
                           sensorProbeEnergySirenOnPort
                              INTEGER,
                           sensorProbeEnergySirenActiveStatus
                              INTEGER,
                           sensorProbeEnergySirenAction
                              INTEGER,
                           sensorProbeEnergyAcknowledgement
                              INTEGER,
                           sensorProbeEnergySirenDelayAlarm
                              INTEGER,
                           sensorProbeEnergyReadingMode
                              INTEGER,
                           sensorProbeEnergyURL
                              DisplayString,
                           sensorProbeEnergyOpenURL
                              INTEGER,
                           sensorProbeEnergyDatacollectType
                              INTEGER,
                           sensorProbeEnergyContTimeHighCritical
                              INTEGER,
                           sensorProbeEnergyContTimeHighWarning
                              INTEGER,
                           sensorProbeEnergyContTimeNormal
                              INTEGER,
                           sensorProbeEnergyContTimeLowWarning
                              INTEGER,
                           sensorProbeEnergyContTimeLowCritical
                              INTEGER,
                           sensorProbeEnergyContTimeSensorError
                              INTEGER,
                           sensorProbeEnergyCalendar
                              INTEGER
                        }

                          sensorProbeEnergySensorIndex OBJECT-TYPE
                              SYNTAX  INTEGER (0..7)
                              ACCESS  read-only
                              STATUS  mandatory
                              DESCRIPTION
                              "A unique value for each Energy sensor port."
                              ::=  {  sensorProbeEnergySensorEntry 1   }

                          sensorProbeEnergyDescription OBJECT-TYPE
                              SYNTAX  DisplayString
                              ACCESS  read-write
                              STATUS  mandatory
                              DESCRIPTION
                              "A Description of this sensor Energy"
                              ::=  {  sensorProbeEnergySensorEntry 2   }

                          sensorProbeEnergyPercent OBJECT-TYPE
                              SYNTAX  INTEGER (-32768..32767)
                              ACCESS  read-only
                              STATUS  mandatory
                              DESCRIPTION
                              "The relative Energy percentage measured by this sensor"
                              ::=  {  sensorProbeEnergySensorEntry 3   }

                           sensorProbeEnergyStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeEnergySensorEntry 4   }

                           sensorProbeEnergyOnline OBJECT-TYPE
                              SYNTAX  INTEGER {
                                 online(1),
                                 offline(2)
                              }
                              ACCESS  read-only
                              STATUS  mandatory
                              DESCRIPTION
                              "If this Sensor is currently online"
                                 ::=  {  sensorProbeEnergySensorEntry 5   }

                           sensorProbeEnergyGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeEnergySensorEntry 6   }

                           sensorProbeEnergyHighWarning OBJECT-TYPE
                              SYNTAX  INTEGER
                              ACCESS  read-write
                              STATUS  mandatory
                              DESCRIPTION
                              "How high the relative Energy this sensor measures before it sends a warning"
                              ::=  {  sensorProbeEnergySensorEntry 7   }

                           sensorProbeEnergyHighCritical OBJECT-TYPE
                              SYNTAX  INTEGER
                              ACCESS  read-write
                              STATUS  mandatory
                              DESCRIPTION
                              "How high the relative Energy this sensor measures before it becomes critical"
                              ::=  {  sensorProbeEnergySensorEntry 8   }

                           sensorProbeEnergyLowWarning OBJECT-TYPE
                              SYNTAX  INTEGER
                              ACCESS  read-write
                              STATUS  mandatory
                              DESCRIPTION
                              "How low the relative Energy this sensor measures before it sends a warning"
                              ::=  {  sensorProbeEnergySensorEntry 9   }

                           sensorProbeEnergyLowCritical OBJECT-TYPE
                              SYNTAX  INTEGER
                              ACCESS  read-write
                              STATUS  mandatory
                              DESCRIPTION
                              "How low the relative Energy this sensor measures before it becomes critical"
                              ::=  {  sensorProbeEnergySensorEntry 10   }

                           sensorProbeEnergyRearm OBJECT-TYPE
                              SYNTAX  INTEGER
                              ACCESS  read-write
                              STATUS  mandatory
                              DESCRIPTION
                              "The percent relative Energy to rearm the status. For example if status goes from normal to warning, the Energy must go down spAnalogueRearm below warning before the status goes to normal"
                              ::=  {  sensorProbeEnergySensorEntry 11   }

                           sensorProbeEnergyRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeEnergySensorEntry 13   }

                           sensorProbeEnergyEmailTrapLimit OBJECT-TYPE
                              SYNTAX  INTEGER {
                                 disable(0),
                                 enable(1)
                              }
                              ACCESS  read-write
                              STATUS  mandatory
                              DESCRIPTION
                              "Enable email/trap limit feature"
                              ::=  {  sensorProbeEnergySensorEntry 17   }

                           sensorProbeEnergyDelayError OBJECT-TYPE
                              SYNTAX  INTEGER (0..65534)
                              ACCESS  read-write
                              STATUS  mandatory
                              DESCRIPTION
                              "Time in seconds after the sensor has been in error status before report as an error"
                              ::=  {  sensorProbeEnergySensorEntry 21   }

                           sensorProbeEnergyDelayNormal OBJECT-TYPE
                              SYNTAX  INTEGER (0..65534)
                              ACCESS  read-write
                              STATUS  mandatory
                              DESCRIPTION
                              "Time in seconds after the sensor change from error to normal before report as normal"
                              ::=  {  sensorProbeEnergySensorEntry 22   }

                           sensorProbeEnergyRelayCycleTime OBJECT-TYPE
                              SYNTAX INTEGER (1..255)
                              ACCESS read-write
                              STATUS mandatory
                              DESCRIPTION
                              "Relay toggle period in seconds for Cycle action."
                              ::=  {  sensorProbeEnergySensorEntry 29   }

                           sensorProbeEnergyRelayOnPort OBJECT-TYPE
                              SYNTAX INTEGER (0..255)
                              ACCESS read-write
                              STATUS mandatory
                              DESCRIPTION
                              "The sensor port that the relay will listen to. If this is set to 255, then the relay will not listen to any sensor ports"
                              ::=  {  sensorProbeEnergySensorEntry 30   }

                           sensorProbeEnergyRelayActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the relay"
                              ::=  {  sensorProbeEnergySensorEntry 31   }

                           sensorProbeEnergyRelayAction OBJECT-TYPE
                              SYNTAX INTEGER {
                                 cycle(2),
                                 turn-on(3),
                                 turn-off(4)
                              }
                              ACCESS read-write
                              STATUS mandatory
                              DESCRIPTION
                              "What the relay will do when the listened to port status turns to the specified active status."
                              ::=  {  sensorProbeEnergySensorEntry 32   }

                           sensorProbeEnergySirenCycleTime OBJECT-TYPE
                              SYNTAX INTEGER (1..255)
                              ACCESS read-write
                              STATUS mandatory
                              DESCRIPTION
                              "Siren toggle period in seconds for Cycle action."
                              ::=  {  sensorProbeEnergySensorEntry 37   }

                           sensorProbeEnergySirenOnPort OBJECT-TYPE
                              SYNTAX INTEGER (0..255)
                              ACCESS read-write
                              STATUS mandatory
                              DESCRIPTION
                              "The sensor port that the siren will listen to. If this is set to 255, then the siren will not listen to any sensor ports"
                              ::=  {  sensorProbeEnergySensorEntry 38   }

                           sensorProbeEnergySirenActiveStatus OBJECT-TYPE
                              SYNTAX INTEGER {
                                 highWarning(3),
                                 highCritical(4),
                                 lowWarning(5),
                                 lowCritical(6),
                                 anyError(7)
                              }
                              ACCESS read-write
                              STATUS mandatory
                              DESCRIPTION
                              "Sensor status that will activate the siren"
                              ::=  {  sensorProbeEnergySensorEntry 39   }

                           sensorProbeEnergySirenAction OBJECT-TYPE
                              SYNTAX INTEGER {
                                 cycle(2),
                                 turn-on(3),
                                 turn-off(4)
                              }
                              ACCESS read-write
                              STATUS mandatory
                              DESCRIPTION
                              "What the siren will do when the listened to port status turns to the specified active status."
                              ::=  {  sensorProbeEnergySensorEntry 40   }

                           sensorProbeEnergyAcknowledgement OBJECT-TYPE
                              SYNTAX INTEGER {
                                 ack(1)
                              }
                              ACCESS read-write
                              STATUS mandatory
                              DESCRIPTION
                              "Acknowledged sensor error and stop notification"
                              ::= {  sensorProbeEnergySensorEntry 41 }

                           sensorProbeEnergySirenDelayAlarm OBJECT-TYPE
                              SYNTAX INTEGER (1..255)
                              ACCESS read-write
                              STATUS mandatory
                              DESCRIPTION
                              "Siren delay in seconds before start Alarm."
                              ::=  {  sensorProbeEnergySensorEntry 42   }

                           sensorProbeEnergyReadingMode OBJECT-TYPE
                              SYNTAX INTEGER {
                                 active(0),
                                 apparent(1)
                              }
                              ACCESS read-write
                              STATUS mandatory
                              DESCRIPTION
                              "Energy Meter Reading Mode."
                              ::=  {  sensorProbeEnergySensorEntry 43   }

                           sensorProbeEnergyURL OBJECT-TYPE
                              SYNTAX DisplayString
                              ACCESS read-write
                              STATUS mandatory
                              DESCRIPTION
                              "Sensor URL link."
                              ::=  {  sensorProbeEnergySensorEntry 44   }

                           sensorProbeEnergyOpenURL OBJECT-TYPE
                              SYNTAX INTEGER {
                                 cur-window(0),
                                 new-window(2)
                              }
                              ACCESS read-write
                              STATUS mandatory
                              DESCRIPTION
                              "Open URL in this browser or open in a new window."
                              ::=  {  sensorProbeEnergySensorEntry 45   }

                           sensorProbeEnergyDatacollectType OBJECT-TYPE
                              SYNTAX INTEGER {
                                 average(1),
                                 highest(2),
                                 lowest(3)
                              }
                              ACCESS read-write
                              STATUS mandatory
                              DESCRIPTION
                              "Type of datacollect to collect."
                              ::=  {  sensorProbeEnergySensorEntry 46   }

                           sensorProbeEnergyContTimeHighCritical OBJECT-TYPE
                              SYNTAX INTEGER (0..65535)
                              ACCESS read-write
                              STATUS mandatory
                              DESCRIPTION
                              "Continuous time for this sensor to be in High Critical before accepting new Status."
                              ::= {  sensorProbeEnergySensorEntry 47 }

                           sensorProbeEnergyContTimeHighWarning OBJECT-TYPE
                              SYNTAX INTEGER (0..65535)
                              ACCESS read-write
                              STATUS mandatory
                              DESCRIPTION
                              "Continuous time for this sensor to be in High Warning before accepting new Status."
                              ::= {  sensorProbeEnergySensorEntry 48 }

                           sensorProbeEnergyContTimeNormal OBJECT-TYPE
                              SYNTAX INTEGER (0..65535)
                              ACCESS read-write
                              STATUS mandatory
                              DESCRIPTION
                              "Continuous time for this sensor to be in Normal before accepting new Status."
                              ::= {  sensorProbeEnergySensorEntry 49 }

                           sensorProbeEnergyContTimeLowWarning OBJECT-TYPE
                              SYNTAX INTEGER (0..65535)
                              ACCESS read-write
                              STATUS mandatory
                              DESCRIPTION
                              "Continuous time for this sensor to be in Low Warning before accepting new Status."
                              ::= {  sensorProbeEnergySensorEntry 50 }

                           sensorProbeEnergyContTimeLowCritical OBJECT-TYPE
                              SYNTAX INTEGER (0..65535)
                              ACCESS read-write
                              STATUS mandatory
                              DESCRIPTION
                              "Continuous time for this sensor to be in Low Critical before accepting new Status."
                              ::= {  sensorProbeEnergySensorEntry 51 }

                           sensorProbeEnergyContTimeSensorError OBJECT-TYPE
                              SYNTAX INTEGER (0..65535)
                              ACCESS read-write
                              STATUS mandatory
                              DESCRIPTION
                              "Continuous time for this sensor to be in Sensor Error before accepting new Status."
                              ::= {  sensorProbeEnergySensorEntry 52 }

                           sensorProbeEnergyCalendar OBJECT-TYPE
                              SYNTAX INTEGER {
                                 disable(0),
                                 enable(1)
                              }
                              ACCESS read-write
                              STATUS mandatory
                              DESCRIPTION
                              "Enable or disable the calendar filtering working hours of sensor."
                              ::= {  sensorProbeEnergySensorEntry 53 }

                        sensorProbeRelayArraySensor OBJECT IDENTIFIER ::= { sensorProbeOtherSensor 29  }

                           sensorProbeRelayArrayPort1 OBJECT IDENTIFIER ::= { sensorProbeRelayArraySensor 1  }
                              sensorProbeRelayArrayPort1Number OBJECT-TYPE
                                 SYNTAX INTEGER
                                 ACCESS read-only
                                 STATUS mandatory
                                 DESCRIPTION
                                 "The total number of port on the RelayArray."
                                 ::=  {  sensorProbeRelayArrayPort1 1   }

                              sensorProbeRelayArrayPort1Table OBJECT-TYPE
                                 SYNTAX  SEQUENCE OF SensorProbeRelayArrayPort1Entry
                                 ACCESS  not-accessible
                                 STATUS  mandatory
                                 DESCRIPTION
                                 "This table contains the data for every Switch Sensor in the SensorArray. Each row in the table contains data for a different Switch Sensor."
                                 ::=  {  sensorProbeRelayArrayPort1 2   }

                                 sensorProbeRelayArrayPort1Entry OBJECT-TYPE
                                    SYNTAX  SensorProbeRelayArrayPort1Entry
                                    ACCESS  not-accessible
                                    STATUS  mandatory
                                    DESCRIPTION
                                    "This is an entry in the sensorProbeRelayArrayPort1 Table"
                                    INDEX         { sensorProbeRelayArrayPort1Index }
                                    ::=  { sensorProbeRelayArrayPort1Table 1 }

                                    SensorProbeRelayArrayPort1Entry ::= SEQUENCE {
                                       sensorProbeRelayArrayPort1Index
                                          INTEGER,
                                       sensorProbeRelayArrayPort1Description
                                          DisplayString,
                                       sensorProbeRelayArrayPort1Status
                                          INTEGER,
                                       sensorProbeRelayArrayPort1Online
                                          INTEGER,
                                       sensorProbeRelayArrayPort1GoOnline
                                          INTEGER,
                                       sensorProbeRelayArrayPort1NormalState
                                          INTEGER,
                                       sensorProbeRelayArrayPort1RelayCycleTime
                                          INTEGER,
                                       sensorProbeRelayArrayPort1RelayAction
                                          INTEGER,
                                       sensorProbeRelayArrayPort1ManualRelayCycleTime
                                          INTEGER,
                                       sensorProbeRelayArrayPort1ManualRelayAction
                                          INTEGER,
                                       sensorProbeRelayArrayPort1RelayDescOn
                                          DisplayString,
                                       sensorProbeRelayArrayPort1RelayDescOff
                                          DisplayString,
                                       sensorProbeRelayArrayPort1URL
                                          DisplayString,
                                       sensorProbeRelayArrayPort1OpenURL
                                          INTEGER,
                                       sensorProbeRelayArrayPort1ControlMode
                                          INTEGER
                                    }

                                    sensorProbeRelayArrayPort1Index OBJECT-TYPE
                                       SYNTAX  INTEGER (0..7)
                                       ACCESS  read-only
                                       STATUS  mandatory
                                       DESCRIPTION
                                       "A unique value for each sensor RelayArray port."
                                       ::=  {  sensorProbeRelayArrayPort1Entry 1   }

                                    sensorProbeRelayArrayPort1Description OBJECT-TYPE
                                       SYNTAX  DisplayString
                                       ACCESS  read-write
                                       STATUS  mandatory
                                       DESCRIPTION
                                       "A Description of this sensor RelayArray"
                                       ::=  {  sensorProbeRelayArrayPort1Entry 2   }

                                    sensorProbeRelayArrayPort1Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort1Entry 4  }

                                    sensorProbeRelayArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort1Entry 5  }

                                    sensorProbeRelayArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort1Entry 6  }

                                    sensorProbeRelayArrayPort1NormalState OBJECT-TYPE
                                       SYNTAX  INTEGER {
                                          closed(0),
                                          open(1)
                                       }
                                       ACCESS  read-write
                                       STATUS  mandatory
                                       DESCRIPTION
                                       "The normal state of RelayArray"
                                       ::=  {  sensorProbeRelayArrayPort1Entry 7  }

                                    sensorProbeRelayArrayPort1RelayCycleTime OBJECT-TYPE
                                       SYNTAX INTEGER (1..255)
                                       ACCESS read-write
                                       STATUS mandatory
                                       DESCRIPTION
                                       "Relay toggle period in seconds for Cycle action."
                                       ::=  {  sensorProbeRelayArrayPort1Entry 18   }

                                    sensorProbeRelayArrayPort1RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort1Entry 21   }

                                    sensorProbeRelayArrayPort1ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort1Entry 24 }

                                    sensorProbeRelayArrayPort1ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort1Entry 25 }

                                    sensorProbeRelayArrayPort1RelayDescOn OBJECT-TYPE
                                       SYNTAX  DisplayString
                                       ACCESS  read-write
                                       STATUS  mandatory
                                       DESCRIPTION
                                       "Description of relay On"
                                       ::=  {  sensorProbeRelayArrayPort1Entry 26   }

                                    sensorProbeRelayArrayPort1RelayDescOff OBJECT-TYPE
                                       SYNTAX  DisplayString
                                       ACCESS  read-write
                                       STATUS  mandatory
                                       DESCRIPTION
                                       "Description of relay Off"
                                       ::=  {  sensorProbeRelayArrayPort1Entry 27   }

                                    sensorProbeRelayArrayPort1URL OBJECT-TYPE
                                       SYNTAX  DisplayString
                                       ACCESS  read-write
                                       STATUS  mandatory
                                       DESCRIPTION
                                       "Sersor URL link."
                                       ::=  {  sensorProbeRelayArrayPort1Entry 28   }

                                    sensorProbeRelayArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort1Entry 29   }

                                    sensorProbeRelayArrayPort1ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort1Entry 30  }

                           sensorProbeRelayArrayPort2 OBJECT IDENTIFIER ::= { sensorProbeRelayArraySensor 2  }
                              sensorProbeRelayArrayPort2Number OBJECT-TYPE
                                 SYNTAX INTEGER
                                 ACCESS read-only
                                 STATUS mandatory
                                 DESCRIPTION
                                 "The total number of port on the RelayArray."
                                 ::=  {  sensorProbeRelayArrayPort2 1   }

                              sensorProbeRelayArrayPort2Table OBJECT-TYPE
                                 SYNTAX  SEQUENCE OF SensorProbeRelayArrayPort2Entry
                                 ACCESS  not-accessible
                                 STATUS  mandatory
                                 DESCRIPTION
                                 "This table contains the data for every Switch Sensor in the SensorArray. Each row in the table contains data for a different Switch Sensor."
                                 ::=  {  sensorProbeRelayArrayPort2 2   }

                                 sensorProbeRelayArrayPort2Entry OBJECT-TYPE
                                    SYNTAX  SensorProbeRelayArrayPort2Entry
                                    ACCESS  not-accessible
                                    STATUS  mandatory
                                    DESCRIPTION
                                    "This is an entry in the sensorProbeRelayArrayPort2 Table"
                                    INDEX         { sensorProbeRelayArrayPort2Index }
                                    ::=  { sensorProbeRelayArrayPort2Table 1 }

                                    SensorProbeRelayArrayPort2Entry ::= SEQUENCE {
                                       sensorProbeRelayArrayPort2Index
                                          INTEGER,
                                       sensorProbeRelayArrayPort2Description
                                          DisplayString,
                                       sensorProbeRelayArrayPort2Status
                                          INTEGER,
                                       sensorProbeRelayArrayPort2Online
                                          INTEGER,
                                       sensorProbeRelayArrayPort2GoOnline
                                          INTEGER,
                                       sensorProbeRelayArrayPort2NormalState
                                          INTEGER,
                                       sensorProbeRelayArrayPort2RelayCycleTime
                                          INTEGER,
                                       sensorProbeRelayArrayPort2RelayAction
                                          INTEGER,
                                       sensorProbeRelayArrayPort2ManualRelayCycleTime
                                          INTEGER,
                                       sensorProbeRelayArrayPort2ManualRelayAction
                                          INTEGER,
                                       sensorProbeRelayArrayPort2RelayDescOn
                                          DisplayString,
                                       sensorProbeRelayArrayPort2RelayDescOff
                                          DisplayString,
                                       sensorProbeRelayArrayPort2URL
                                          DisplayString,
                                       sensorProbeRelayArrayPort2OpenURL
                                          INTEGER,
                                       sensorProbeRelayArrayPort2ControlMode
                                          INTEGER
                                    }

                                    sensorProbeRelayArrayPort2Index OBJECT-TYPE
                                       SYNTAX  INTEGER (0..7)
                                       ACCESS  read-only
                                       STATUS  mandatory
                                       DESCRIPTION
                                       "A unique value for each sensor RelayArray port."
                                       ::=  {  sensorProbeRelayArrayPort2Entry 1   }

                                    sensorProbeRelayArrayPort2Description OBJECT-TYPE
                                       SYNTAX  DisplayString
                                       ACCESS  read-write
                                       STATUS  mandatory
                                       DESCRIPTION
                                       "A Description of this sensor RelayArray"
                                       ::=  {  sensorProbeRelayArrayPort2Entry 2   }

                                    sensorProbeRelayArrayPort2Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort2Entry 4  }

                                    sensorProbeRelayArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort2Entry 5  }

                                    sensorProbeRelayArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort2Entry 6  }

                                    sensorProbeRelayArrayPort2NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort2Entry 7  }

                                    sensorProbeRelayArrayPort2RelayCycleTime OBJECT-TYPE
                                       SYNTAX INTEGER (1..255)
                                       ACCESS read-write
                                       STATUS mandatory
                                       DESCRIPTION
                                       "Relay toggle period in seconds for Cycle action."
                                       ::=  {  sensorProbeRelayArrayPort2Entry 18   }

                                    sensorProbeRelayArrayPort2RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort2Entry 21   }

                                    sensorProbeRelayArrayPort2ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort2Entry 24 }

                                    sensorProbeRelayArrayPort2ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort2Entry 25 }

                                    sensorProbeRelayArrayPort2RelayDescOn OBJECT-TYPE
                                       SYNTAX  DisplayString
                                       ACCESS  read-write
                                       STATUS  mandatory
                                       DESCRIPTION
                                       "Description of relay On"
                                       ::=  {  sensorProbeRelayArrayPort2Entry 26   }

                                    sensorProbeRelayArrayPort2RelayDescOff OBJECT-TYPE
                                       SYNTAX  DisplayString
                                       ACCESS  read-write
                                       STATUS  mandatory
                                       DESCRIPTION
                                       "Description of relay Off"
                                       ::=  {  sensorProbeRelayArrayPort2Entry 27   }

                                    sensorProbeRelayArrayPort2URL OBJECT-TYPE
                                       SYNTAX  DisplayString
                                       ACCESS  read-write
                                       STATUS  mandatory
                                       DESCRIPTION
                                       "Sensor URL link"
                                       ::=  {  sensorProbeRelayArrayPort2Entry 28   }

                                    sensorProbeRelayArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort2Entry 29   }

                                    sensorProbeRelayArrayPort2ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort2Entry 30  }

                           sensorProbeRelayArrayPort3 OBJECT IDENTIFIER ::= { sensorProbeRelayArraySensor 3  }
                              sensorProbeRelayArrayPort3Number OBJECT-TYPE
                                 SYNTAX INTEGER
                                 ACCESS read-only
                                 STATUS mandatory
                                 DESCRIPTION
                                 "The total number of port on the RelayArray."
                                 ::=  {  sensorProbeRelayArrayPort3 1   }

                              sensorProbeRelayArrayPort3Table OBJECT-TYPE
                                 SYNTAX  SEQUENCE OF SensorProbeRelayArrayPort3Entry
                                 ACCESS  not-accessible
                                 STATUS  mandatory
                                 DESCRIPTION
                                 "This table contains the data for every Switch Sensor in the SensorArray. Each row in the table contains data for a different Switch Sensor."
                                 ::=  {  sensorProbeRelayArrayPort3 2   }

                                 sensorProbeRelayArrayPort3Entry OBJECT-TYPE
                                    SYNTAX  SensorProbeRelayArrayPort3Entry
                                    ACCESS  not-accessible
                                    STATUS  mandatory
                                    DESCRIPTION
                                    "This is an entry in the sensorProbeRelayArrayPort3 Table"
                                    INDEX         { sensorProbeRelayArrayPort3Index }
                                    ::=  { sensorProbeRelayArrayPort3Table 1 }

                                    SensorProbeRelayArrayPort3Entry ::= SEQUENCE {
                                       sensorProbeRelayArrayPort3Index
                                          INTEGER,
                                       sensorProbeRelayArrayPort3Description
                                          DisplayString,
                                       sensorProbeRelayArrayPort3Status
                                          INTEGER,
                                       sensorProbeRelayArrayPort3Online
                                          INTEGER,
                                       sensorProbeRelayArrayPort3GoOnline
                                          INTEGER,
                                       sensorProbeRelayArrayPort3NormalState
                                          INTEGER,
                                       sensorProbeRelayArrayPort3RelayCycleTime
                                          INTEGER,
                                       sensorProbeRelayArrayPort3RelayAction
                                          INTEGER,
                                       sensorProbeRelayArrayPort3ManualRelayCycleTime
                                          INTEGER,
                                       sensorProbeRelayArrayPort3ManualRelayAction
                                          INTEGER,
                                       sensorProbeRelayArrayPort3RelayDescOn
                                          DisplayString,
                                       sensorProbeRelayArrayPort3RelayDescOff
                                          DisplayString,
                                       sensorProbeRelayArrayPort3URL
                                          DisplayString,
                                       sensorProbeRelayArrayPort3OpenURL
                                          INTEGER,
                                       sensorProbeRelayArrayPort3ControlMode
                                          INTEGER
                                    }

                                    sensorProbeRelayArrayPort3Index OBJECT-TYPE
                                       SYNTAX  INTEGER (0..7)
                                       ACCESS  read-only
                                       STATUS  mandatory
                                       DESCRIPTION
                                       "A unique value for each sensor RelayArray port."
                                       ::=  {  sensorProbeRelayArrayPort3Entry 1   }

                                    sensorProbeRelayArrayPort3Description OBJECT-TYPE
                                       SYNTAX  DisplayString
                                       ACCESS  read-write
                                       STATUS  mandatory
                                       DESCRIPTION
                                       "A Description of this sensor RelayArray"
                                       ::=  {  sensorProbeRelayArrayPort3Entry 2   }

                                    sensorProbeRelayArrayPort3Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort3Entry 4  }

                                    sensorProbeRelayArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort3Entry 5  }

                                    sensorProbeRelayArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort3Entry 6  }

                                    sensorProbeRelayArrayPort3NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort3Entry 7  }

                                    sensorProbeRelayArrayPort3RelayCycleTime OBJECT-TYPE
                                       SYNTAX INTEGER (1..255)
                                       ACCESS read-write
                                       STATUS mandatory
                                       DESCRIPTION
                                       "Relay toggle period in seconds for Cycle action."
                                       ::=  {  sensorProbeRelayArrayPort3Entry 18   }

                                    sensorProbeRelayArrayPort3RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort3Entry 21   }

                                    sensorProbeRelayArrayPort3ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort3Entry 24 }

                                    sensorProbeRelayArrayPort3ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort3Entry 25 }

                                    sensorProbeRelayArrayPort3RelayDescOn OBJECT-TYPE
                                       SYNTAX  DisplayString
                                       ACCESS  read-write
                                       STATUS  mandatory
                                       DESCRIPTION
                                       "Description of relay On"
                                       ::=  {  sensorProbeRelayArrayPort3Entry 26   }

                                    sensorProbeRelayArrayPort3RelayDescOff OBJECT-TYPE
                                       SYNTAX  DisplayString
                                       ACCESS  read-write
                                       STATUS  mandatory
                                       DESCRIPTION
                                       "Description of relay Off"
                                       ::=  {  sensorProbeRelayArrayPort3Entry 27   }

                                    sensorProbeRelayArrayPort3URL OBJECT-TYPE
                                       SYNTAX  DisplayString
                                       ACCESS  read-write
                                       STATUS  mandatory
                                       DESCRIPTION
                                       "Sensor URL link."
                                       ::=  {  sensorProbeRelayArrayPort3Entry 28   }

                                    sensorProbeRelayArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort3Entry 29   }

                                    sensorProbeRelayArrayPort3ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort3Entry 30  }

                           sensorProbeRelayArrayPort4 OBJECT IDENTIFIER ::= { sensorProbeRelayArraySensor 4  }
                              sensorProbeRelayArrayPort4Number OBJECT-TYPE
                                 SYNTAX INTEGER
                                 ACCESS read-only
                                 STATUS mandatory
                                 DESCRIPTION
                                 "The total number of port on the RelayArray."
                                 ::=  {  sensorProbeRelayArrayPort4 1   }

                              sensorProbeRelayArrayPort4Table OBJECT-TYPE
                                 SYNTAX  SEQUENCE OF SensorProbeRelayArrayPort4Entry
                                 ACCESS  not-accessible
                                 STATUS  mandatory
                                 DESCRIPTION
                                 "This table contains the data for every Switch Sensor in the SensorArray. Each row in the table contains data for a different Switch Sensor."
                                 ::=  {  sensorProbeRelayArrayPort4 2   }

                                 sensorProbeRelayArrayPort4Entry OBJECT-TYPE
                                    SYNTAX  SensorProbeRelayArrayPort4Entry
                                    ACCESS  not-accessible
                                    STATUS  mandatory
                                    DESCRIPTION
                                    "This is an entry in the sensorProbeRelayArrayPort4 Table"
                                    INDEX         { sensorProbeRelayArrayPort4Index }
                                    ::=  { sensorProbeRelayArrayPort4Table 1 }

                                    SensorProbeRelayArrayPort4Entry ::= SEQUENCE {
                                       sensorProbeRelayArrayPort4Index
                                          INTEGER,
                                       sensorProbeRelayArrayPort4Description
                                          DisplayString,
                                       sensorProbeRelayArrayPort4Status
                                          INTEGER,
                                       sensorProbeRelayArrayPort4Online
                                          INTEGER,
                                       sensorProbeRelayArrayPort4GoOnline
                                          INTEGER,
                                       sensorProbeRelayArrayPort4NormalState
                                          INTEGER,
                                       sensorProbeRelayArrayPort4RelayCycleTime
                                          INTEGER,
                                       sensorProbeRelayArrayPort4RelayAction
                                          INTEGER,
                                       sensorProbeRelayArrayPort4ManualRelayCycleTime
                                          INTEGER,
                                       sensorProbeRelayArrayPort4ManualRelayAction
                                          INTEGER,
                                       sensorProbeRelayArrayPort4RelayDescOn
                                          DisplayString,
                                       sensorProbeRelayArrayPort4RelayDescOff
                                          DisplayString,
                                       sensorProbeRelayArrayPort4URL
                                          DisplayString,
                                       sensorProbeRelayArrayPort4OpenURL
                                          INTEGER,
                                       sensorProbeRelayArrayPort4ControlMode
                                          INTEGER
                                    }

                                    sensorProbeRelayArrayPort4Index OBJECT-TYPE
                                       SYNTAX  INTEGER (0..7)
                                       ACCESS  read-only
                                       STATUS  mandatory
                                       DESCRIPTION
                                       "A unique value for each sensor RelayArray port."
                                       ::=  {  sensorProbeRelayArrayPort4Entry 1   }

                                    sensorProbeRelayArrayPort4Description OBJECT-TYPE
                                       SYNTAX  DisplayString
                                       ACCESS  read-write
                                       STATUS  mandatory
                                       DESCRIPTION
                                       "A Description of this sensor RelayArray"
                                       ::=  {  sensorProbeRelayArrayPort4Entry 2   }

                                    sensorProbeRelayArrayPort4Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort4Entry 4  }

                                    sensorProbeRelayArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort4Entry 5  }

                                    sensorProbeRelayArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort4Entry 6  }

                                    sensorProbeRelayArrayPort4NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort4Entry 7  }

                                    sensorProbeRelayArrayPort4RelayCycleTime OBJECT-TYPE
                                       SYNTAX INTEGER (1..255)
                                       ACCESS read-write
                                       STATUS mandatory
                                       DESCRIPTION
                                       "Relay toggle period in seconds for Cycle action."
                                       ::=  {  sensorProbeRelayArrayPort4Entry 18   }

                                    sensorProbeRelayArrayPort4RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort4Entry 21   }

                                    sensorProbeRelayArrayPort4ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort4Entry 24 }

                                    sensorProbeRelayArrayPort4ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort4Entry 25 }

                                    sensorProbeRelayArrayPort4RelayDescOn OBJECT-TYPE
                                       SYNTAX  DisplayString
                                       ACCESS  read-write
                                       STATUS  mandatory
                                       DESCRIPTION
                                       "Description of relay On"
                                       ::=  {  sensorProbeRelayArrayPort4Entry 26   }

                                    sensorProbeRelayArrayPort4RelayDescOff OBJECT-TYPE
                                       SYNTAX  DisplayString
                                       ACCESS  read-write
                                       STATUS  mandatory
                                       DESCRIPTION
                                       "Description of relay Off"
                                       ::=  {  sensorProbeRelayArrayPort4Entry 27   }

                                    sensorProbeRelayArrayPort4URL OBJECT-TYPE
                                       SYNTAX  DisplayString
                                       ACCESS  read-write
                                       STATUS  mandatory
                                       DESCRIPTION
                                       "Sensor URL link."
                                       ::=  {  sensorProbeRelayArrayPort4Entry 28   }

                                    sensorProbeRelayArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort4Entry 29   }

                                    sensorProbeRelayArrayPort4ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort4Entry 30  }

                           sensorProbeRelayArrayPort5 OBJECT IDENTIFIER ::= { sensorProbeRelayArraySensor 5  }
                              sensorProbeRelayArrayPort5Number OBJECT-TYPE
                                 SYNTAX INTEGER
                                 ACCESS read-only
                                 STATUS mandatory
                                 DESCRIPTION
                                 "The total number of port on the RelayArray."
                                 ::=  {  sensorProbeRelayArrayPort5 1   }

                              sensorProbeRelayArrayPort5Table OBJECT-TYPE
                                 SYNTAX  SEQUENCE OF SensorProbeRelayArrayPort5Entry
                                 ACCESS  not-accessible
                                 STATUS  mandatory
                                 DESCRIPTION
                                 "This table contains the data for every Switch Sensor in the SensorArray. Each row in the table contains data for a different Switch Sensor."
                                 ::=  {  sensorProbeRelayArrayPort5 2   }

                                 sensorProbeRelayArrayPort5Entry OBJECT-TYPE
                                    SYNTAX  SensorProbeRelayArrayPort5Entry
                                    ACCESS  not-accessible
                                    STATUS  mandatory
                                    DESCRIPTION
                                    "This is an entry in the sensorProbeRelayArrayPort5 Table"
                                    INDEX         { sensorProbeRelayArrayPort5Index }
                                    ::=  { sensorProbeRelayArrayPort5Table 1 }

                                    SensorProbeRelayArrayPort5Entry ::= SEQUENCE {
                                       sensorProbeRelayArrayPort5Index
                                          INTEGER,
                                       sensorProbeRelayArrayPort5Description
                                          DisplayString,
                                       sensorProbeRelayArrayPort5Status
                                          INTEGER,
                                       sensorProbeRelayArrayPort5Online
                                          INTEGER,
                                       sensorProbeRelayArrayPort5GoOnline
                                          INTEGER,
                                       sensorProbeRelayArrayPort5NormalState
                                          INTEGER,
                                       sensorProbeRelayArrayPort5RelayCycleTime
                                          INTEGER,
                                       sensorProbeRelayArrayPort5RelayAction
                                          INTEGER,
                                       sensorProbeRelayArrayPort5ManualRelayCycleTime
                                          INTEGER,
                                       sensorProbeRelayArrayPort5ManualRelayAction
                                          INTEGER,
                                       sensorProbeRelayArrayPort5RelayDescOn
                                          DisplayString,
                                       sensorProbeRelayArrayPort5RelayDescOff
                                          DisplayString,
                                       sensorProbeRelayArrayPort5URL
                                          DisplayString,
                                       sensorProbeRelayArrayPort5OpenURL
                                          INTEGER,
                                       sensorProbeRelayArrayPort5ControlMode
                                          INTEGER
                                    }

                                    sensorProbeRelayArrayPort5Index OBJECT-TYPE
                                       SYNTAX  INTEGER (0..7)
                                       ACCESS  read-only
                                       STATUS  mandatory
                                       DESCRIPTION
                                       "A unique value for each sensor RelayArray port."
                                       ::=  {  sensorProbeRelayArrayPort5Entry 1   }

                                    sensorProbeRelayArrayPort5Description OBJECT-TYPE
                                       SYNTAX  DisplayString
                                       ACCESS  read-write
                                       STATUS  mandatory
                                       DESCRIPTION
                                       "A Description of this sensor RelayArray"
                                       ::=  {  sensorProbeRelayArrayPort5Entry 2   }

                                    sensorProbeRelayArrayPort5Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort5Entry 4  }

                                    sensorProbeRelayArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort5Entry 5  }

                                    sensorProbeRelayArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort5Entry 6  }

                                    sensorProbeRelayArrayPort5NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort5Entry 7  }

                                    sensorProbeRelayArrayPort5RelayCycleTime OBJECT-TYPE
                                       SYNTAX INTEGER (1..255)
                                       ACCESS read-write
                                       STATUS mandatory
                                       DESCRIPTION
                                       "Relay toggle period in seconds for Cycle action."
                                       ::=  {  sensorProbeRelayArrayPort5Entry 18   }

                                    sensorProbeRelayArrayPort5RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort5Entry 21   }

                                    sensorProbeRelayArrayPort5ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort5Entry 24 }

                                    sensorProbeRelayArrayPort5ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort5Entry 25 }

                                    sensorProbeRelayArrayPort5RelayDescOn OBJECT-TYPE
                                       SYNTAX  DisplayString
                                       ACCESS  read-write
                                       STATUS  mandatory
                                       DESCRIPTION
                                       "Description of relay On"
                                       ::=  {  sensorProbeRelayArrayPort5Entry 26   }

                                    sensorProbeRelayArrayPort5RelayDescOff OBJECT-TYPE
                                       SYNTAX  DisplayString
                                       ACCESS  read-write
                                       STATUS  mandatory
                                       DESCRIPTION
                                       "Description of relay Off"
                                       ::=  {  sensorProbeRelayArrayPort5Entry 27   }

                                    sensorProbeRelayArrayPort5URL OBJECT-TYPE
                                       SYNTAX  DisplayString
                                       ACCESS  read-write
                                       STATUS  mandatory
                                       DESCRIPTION
                                       "Sensor URL link."
                                       ::=  {  sensorProbeRelayArrayPort5Entry 28   }

                                    sensorProbeRelayArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort5Entry 29   }

                                    sensorProbeRelayArrayPort5ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort5Entry 30  }

                           sensorProbeRelayArrayPort6 OBJECT IDENTIFIER ::= { sensorProbeRelayArraySensor 6  }
                              sensorProbeRelayArrayPort6Number OBJECT-TYPE
                                 SYNTAX INTEGER
                                 ACCESS read-only
                                 STATUS mandatory
                                 DESCRIPTION
                                 "The total number of port on the RelayArray."
                                 ::=  {  sensorProbeRelayArrayPort6 1   }

                              sensorProbeRelayArrayPort6Table OBJECT-TYPE
                                 SYNTAX  SEQUENCE OF SensorProbeRelayArrayPort6Entry
                                 ACCESS  not-accessible
                                 STATUS  mandatory
                                 DESCRIPTION
                                 "This table contains the data for every Switch Sensor in the SensorArray. Each row in the table contains data for a different Switch Sensor."
                                 ::=  {  sensorProbeRelayArrayPort6 2   }

                                 sensorProbeRelayArrayPort6Entry OBJECT-TYPE
                                    SYNTAX  SensorProbeRelayArrayPort6Entry
                                    ACCESS  not-accessible
                                    STATUS  mandatory
                                    DESCRIPTION
                                    "This is an entry in the sensorProbeRelayArrayPort6 Table"
                                    INDEX         { sensorProbeRelayArrayPort6Index }
                                    ::=  { sensorProbeRelayArrayPort6Table 1 }

                                    SensorProbeRelayArrayPort6Entry ::= SEQUENCE {
                                       sensorProbeRelayArrayPort6Index
                                          INTEGER,
                                       sensorProbeRelayArrayPort6Description
                                          DisplayString,
                                       sensorProbeRelayArrayPort6Status
                                          INTEGER,
                                       sensorProbeRelayArrayPort6Online
                                          INTEGER,
                                       sensorProbeRelayArrayPort6GoOnline
                                          INTEGER,
                                       sensorProbeRelayArrayPort6NormalState
                                          INTEGER,
                                       sensorProbeRelayArrayPort6RelayCycleTime
                                          INTEGER,
                                       sensorProbeRelayArrayPort6RelayAction
                                          INTEGER,
                                       sensorProbeRelayArrayPort6ManualRelayCycleTime
                                          INTEGER,
                                       sensorProbeRelayArrayPort6ManualRelayAction
                                          INTEGER,
                                       sensorProbeRelayArrayPort6RelayDescOn
                                          DisplayString,
                                       sensorProbeRelayArrayPort6RelayDescOff
                                          DisplayString,
                                       sensorProbeRelayArrayPort6URL
                                          DisplayString,
                                       sensorProbeRelayArrayPort6OpenURL
                                          INTEGER,
                                       sensorProbeRelayArrayPort6ControlMode
                                          INTEGER
                                    }

                                    sensorProbeRelayArrayPort6Index OBJECT-TYPE
                                       SYNTAX  INTEGER (0..7)
                                       ACCESS  read-only
                                       STATUS  mandatory
                                       DESCRIPTION
                                       "A unique value for each sensor RelayArray port."
                                       ::=  {  sensorProbeRelayArrayPort6Entry 1   }

                                    sensorProbeRelayArrayPort6Description OBJECT-TYPE
                                       SYNTAX  DisplayString
                                       ACCESS  read-write
                                       STATUS  mandatory
                                       DESCRIPTION
                                       "A Description of this sensor RelayArray"
                                       ::=  {  sensorProbeRelayArrayPort6Entry 2   }

                                    sensorProbeRelayArrayPort6Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort6Entry 4  }

                                    sensorProbeRelayArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort6Entry 5  }

                                    sensorProbeRelayArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort6Entry 6  }

                                    sensorProbeRelayArrayPort6NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort6Entry 7  }

                                    sensorProbeRelayArrayPort6RelayCycleTime OBJECT-TYPE
                                       SYNTAX INTEGER (1..255)
                                       ACCESS read-write
                                       STATUS mandatory
                                       DESCRIPTION
                                       "Relay toggle period in seconds for Cycle action."
                                       ::=  {  sensorProbeRelayArrayPort6Entry 18   }

                                    sensorProbeRelayArrayPort6RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort6Entry 21   }

                                    sensorProbeRelayArrayPort6ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort6Entry 24 }

                                    sensorProbeRelayArrayPort6ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort6Entry 25 }

                                    sensorProbeRelayArrayPort6RelayDescOn OBJECT-TYPE
                                       SYNTAX  DisplayString
                                       ACCESS  read-write
                                       STATUS  mandatory
                                       DESCRIPTION
                                       "Description of relay On"
                                       ::=  {  sensorProbeRelayArrayPort6Entry 26   }

                                    sensorProbeRelayArrayPort6RelayDescOff OBJECT-TYPE
                                       SYNTAX  DisplayString
                                       ACCESS  read-write
                                       STATUS  mandatory
                                       DESCRIPTION
                                       "Description of relay Off"
                                       ::=  {  sensorProbeRelayArrayPort6Entry 27   }

                                    sensorProbeRelayArrayPort6URL OBJECT-TYPE
                                       SYNTAX  DisplayString
                                       ACCESS  read-write
                                       STATUS  mandatory
                                       DESCRIPTION
                                       "Sensor URL link."
                                       ::=  {  sensorProbeRelayArrayPort6Entry 28   }

                                    sensorProbeRelayArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort6Entry 29   }

                                    sensorProbeRelayArrayPort6ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort6Entry 30  }

                           sensorProbeRelayArrayPort7 OBJECT IDENTIFIER ::= { sensorProbeRelayArraySensor 7  }
                              sensorProbeRelayArrayPort7Number OBJECT-TYPE
                                 SYNTAX INTEGER
                                 ACCESS read-only
                                 STATUS mandatory
                                 DESCRIPTION
                                 "The total number of port on the RelayArray."
                                 ::=  {  sensorProbeRelayArrayPort7 1   }

                              sensorProbeRelayArrayPort7Table OBJECT-TYPE
                                 SYNTAX  SEQUENCE OF SensorProbeRelayArrayPort7Entry
                                 ACCESS  not-accessible
                                 STATUS  mandatory
                                 DESCRIPTION
                                 "This table contains the data for every Switch Sensor in the SensorArray. Each row in the table contains data for a different Switch Sensor."
                                 ::=  {  sensorProbeRelayArrayPort7 2   }

                                 sensorProbeRelayArrayPort7Entry OBJECT-TYPE
                                    SYNTAX  SensorProbeRelayArrayPort7Entry
                                    ACCESS  not-accessible
                                    STATUS  mandatory
                                    DESCRIPTION
                                    "This is an entry in the sensorProbeRelayArrayPort7 Table"
                                    INDEX         { sensorProbeRelayArrayPort7Index }
                                    ::=  { sensorProbeRelayArrayPort7Table 1 }

                                    SensorProbeRelayArrayPort7Entry ::= SEQUENCE {
                                       sensorProbeRelayArrayPort7Index
                                          INTEGER,
                                       sensorProbeRelayArrayPort7Description
                                          DisplayString,
                                       sensorProbeRelayArrayPort7Status
                                          INTEGER,
                                       sensorProbeRelayArrayPort7Online
                                          INTEGER,
                                       sensorProbeRelayArrayPort7GoOnline
                                          INTEGER,
                                       sensorProbeRelayArrayPort7NormalState
                                          INTEGER,
                                       sensorProbeRelayArrayPort7RelayCycleTime
                                          INTEGER,
                                       sensorProbeRelayArrayPort7RelayAction
                                          INTEGER,
                                       sensorProbeRelayArrayPort7ManualRelayCycleTime
                                          INTEGER,
                                       sensorProbeRelayArrayPort7ManualRelayAction
                                          INTEGER,
                                       sensorProbeRelayArrayPort7RelayDescOn
                                          DisplayString,
                                       sensorProbeRelayArrayPort7RelayDescOff
                                          DisplayString,
                                       sensorProbeRelayArrayPort7URL
                                          DisplayString,
                                       sensorProbeRelayArrayPort7OpenURL
                                          INTEGER,
                                       sensorProbeRelayArrayPort7ControlMode
                                          INTEGER
                                    }

                                    sensorProbeRelayArrayPort7Index OBJECT-TYPE
                                       SYNTAX  INTEGER (0..7)
                                       ACCESS  read-only
                                       STATUS  mandatory
                                       DESCRIPTION
                                       "A unique value for each sensor RelayArray port."
                                       ::=  {  sensorProbeRelayArrayPort7Entry 1   }

                                    sensorProbeRelayArrayPort7Description OBJECT-TYPE
                                       SYNTAX  DisplayString
                                       ACCESS  read-write
                                       STATUS  mandatory
                                       DESCRIPTION
                                       "A Description of this sensor RelayArray"
                                       ::=  {  sensorProbeRelayArrayPort7Entry 2   }

                                    sensorProbeRelayArrayPort7Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort7Entry 4  }

                                    sensorProbeRelayArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort7Entry 5  }

                                    sensorProbeRelayArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort7Entry 6  }

                                    sensorProbeRelayArrayPort7NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort7Entry 7  }

                                    sensorProbeRelayArrayPort7RelayCycleTime OBJECT-TYPE
                                       SYNTAX INTEGER (1..255)
                                       ACCESS read-write
                                       STATUS mandatory
                                       DESCRIPTION
                                       "Relay toggle period in seconds for Cycle action."
                                       ::=  {  sensorProbeRelayArrayPort7Entry 18   }

                                    sensorProbeRelayArrayPort7RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort7Entry 21   }

                                    sensorProbeRelayArrayPort7ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort7Entry 24 }

                                    sensorProbeRelayArrayPort7ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort7Entry 25 }

                                    sensorProbeRelayArrayPort7RelayDescOn OBJECT-TYPE
                                       SYNTAX  DisplayString
                                       ACCESS  read-write
                                       STATUS  mandatory
                                       DESCRIPTION
                                       "Description of relay On"
                                       ::=  {  sensorProbeRelayArrayPort7Entry 26   }

                                    sensorProbeRelayArrayPort7RelayDescOff OBJECT-TYPE
                                       SYNTAX  DisplayString
                                       ACCESS  read-write
                                       STATUS  mandatory
                                       DESCRIPTION
                                       "Description of relay Off"
                                       ::=  {  sensorProbeRelayArrayPort7Entry 27   }

                                    sensorProbeRelayArrayPort7URL OBJECT-TYPE
                                       SYNTAX  DisplayString
                                       ACCESS  read-write
                                       STATUS  mandatory
                                       DESCRIPTION
                                       "Sensor URL link."
                                       ::=  {  sensorProbeRelayArrayPort7Entry 28   }

                                    sensorProbeRelayArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort7Entry 29   }

                                    sensorProbeRelayArrayPort7ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort7Entry 30  }

                           sensorProbeRelayArrayPort8 OBJECT IDENTIFIER ::= { sensorProbeRelayArraySensor 8  }
                              sensorProbeRelayArrayPort8Number OBJECT-TYPE
                                 SYNTAX INTEGER
                                 ACCESS read-only
                                 STATUS mandatory
                                 DESCRIPTION
                                 "The total number of port on the RelayArray."
                                 ::=  {  sensorProbeRelayArrayPort8 1   }

                              sensorProbeRelayArrayPort8Table OBJECT-TYPE
                                 SYNTAX  SEQUENCE OF SensorProbeRelayArrayPort8Entry
                                 ACCESS  not-accessible
                                 STATUS  mandatory
                                 DESCRIPTION
                                 "This table contains the data for every Switch Sensor in the SensorArray. Each row in the table contains data for a different Switch Sensor."
                                 ::=  {  sensorProbeRelayArrayPort8 2   }

                                 sensorProbeRelayArrayPort8Entry OBJECT-TYPE
                                    SYNTAX  SensorProbeRelayArrayPort8Entry
                                    ACCESS  not-accessible
                                    STATUS  mandatory
                                    DESCRIPTION
                                    "This is an entry in the sensorProbeRelayArrayPort8 Table"
                                    INDEX         { sensorProbeRelayArrayPort8Index }
                                    ::=  { sensorProbeRelayArrayPort8Table 1 }

                                    SensorProbeRelayArrayPort8Entry ::= SEQUENCE {
                                       sensorProbeRelayArrayPort8Index
                                          INTEGER,
                                       sensorProbeRelayArrayPort8Description
                                          DisplayString,
                                       sensorProbeRelayArrayPort8Status
                                          INTEGER,
                                       sensorProbeRelayArrayPort8Online
                                          INTEGER,
                                       sensorProbeRelayArrayPort8GoOnline
                                          INTEGER,
                                       sensorProbeRelayArrayPort8NormalState
                                          INTEGER,
                                       sensorProbeRelayArrayPort8RelayCycleTime
                                          INTEGER,
                                       sensorProbeRelayArrayPort8RelayAction
                                          INTEGER,
                                       sensorProbeRelayArrayPort8ManualRelayCycleTime
                                          INTEGER,
                                       sensorProbeRelayArrayPort8ManualRelayAction
                                          INTEGER,
                                       sensorProbeRelayArrayPort8RelayDescOn
                                          DisplayString,
                                       sensorProbeRelayArrayPort8RelayDescOff
                                          DisplayString,
                                       sensorProbeRelayArrayPort8URL
                                          DisplayString,
                                       sensorProbeRelayArrayPort8OpenURL
                                          INTEGER,
                                       sensorProbeRelayArrayPort8ControlMode
                                          INTEGER
                                    }

                                    sensorProbeRelayArrayPort8Index OBJECT-TYPE
                                       SYNTAX  INTEGER (0..7)
                                       ACCESS  read-only
                                       STATUS  mandatory
                                       DESCRIPTION
                                       "A unique value for each sensor RelayArray port."
                                       ::=  {  sensorProbeRelayArrayPort8Entry 1   }

                                    sensorProbeRelayArrayPort8Description OBJECT-TYPE
                                       SYNTAX  DisplayString
                                       ACCESS  read-write
                                       STATUS  mandatory
                                       DESCRIPTION
                                       "A Description of this sensor RelayArray"
                                       ::=  {  sensorProbeRelayArrayPort8Entry 2   }

                                    sensorProbeRelayArrayPort8Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeRelayArrayPort8Entry 4  }

                                    sensorProbeRelayArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeRelayArrayPort8Entry 5  }

                                    sensorProbeRelayArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeRelayArrayPort8Entry 6  }

                                    sensorProbeRelayArrayPort8NormalState OBJECT-TYPE
                                       SYNTAX  INTEGER {
                                          closed(0),
                                          open(1)
                                       }
                                       ACCESS  read-write
                                       STATUS  mandatory
                                       DESCRIPTION
                                       "The normal state of RleayArray"
                                       ::=  {  sensorProbeRelayArrayPort8Entry 7  }

                                    sensorProbeRelayArrayPort8RelayCycleTime OBJECT-TYPE
                                       SYNTAX INTEGER (1..255)
                                       ACCESS read-write
                                       STATUS mandatory
                                       DESCRIPTION
                                       "Relay toggle period in seconds for Cycle action."
                                       ::=  {  sensorProbeRelayArrayPort8Entry 18   }

                                    sensorProbeRelayArrayPort8RelayAction OBJECT-TYPE
                                       SYNTAX INTEGER {
                                          cycle(2),
                                          turn-on(3),
                                          turn-off(4)
                                       }
                                       ACCESS read-write
                                       STATUS mandatory
                                       DESCRIPTION
                                       "What the relay will do when the listened to port status turns to the specified active status."
                                       ::=  {  sensorProbeRelayArrayPort8Entry 21   }

                                    sensorProbeRelayArrayPort8ManualRelayCycleTime OBJECT-TYPE
                                       SYNTAX INTEGER (1..255)
                                       ACCESS read-write
                                       STATUS mandatory
                                       DESCRIPTION
                                       "Relay toggle period in seconds for Manual Cycle action."
                                       ::= { sensorProbeRelayArrayPort8Entry 24 }

                                    sensorProbeRelayArrayPort8ManualRelayAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the relay manualy"
                                       ::= { sensorProbeRelayArrayPort8Entry 25 }

                                    sensorProbeRelayArrayPort8RelayDescOn OBJECT-TYPE
                                       SYNTAX  DisplayString
                                       ACCESS  read-write
                                       STATUS  mandatory
                                       DESCRIPTION
                                       "Description of relay On"
                                       ::=  {  sensorProbeRelayArrayPort8Entry 26   }

                                    sensorProbeRelayArrayPort8RelayDescOff OBJECT-TYPE
                                       SYNTAX  DisplayString
                                       ACCESS  read-write
                                       STATUS  mandatory
                                       DESCRIPTION
                                       "Description of relay Off"
                                       ::=  {  sensorProbeRelayArrayPort8Entry 27   }

                                    sensorProbeRelayArrayPort8URL OBJECT-TYPE
                                       SYNTAX  DisplayString
                                       ACCESS  read-write
                                       STATUS  mandatory
                                       DESCRIPTION
                                       "Sensor URL link."
                                       ::=  {  sensorProbeRelayArrayPort8Entry 28   }

                                    sensorProbeRelayArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeRelayArrayPort8Entry 29   }

                                    sensorProbeRelayArrayPort8ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Relay Control Mode used for selecting the mode to control a relay."
                                       ::=  {  sensorProbeRelayArrayPort8Entry 30  }

                  sensorProbeVirtualAnalogSensor OBJECT IDENTIFIER ::= { sensorProbeOtherSensor 30  }

                     sensorProbeVirtualAnalogSensorNumber OBJECT-TYPE
                        SYNTAX INTEGER
                        ACCESS read-only
                        STATUS mandatory
                        DESCRIPTION
                        "The total number of VirtualAnalog Sensor port."
                        ::= {  sensorProbeVirtualAnalogSensor 1 }

                     sensorProbeVirtualAnalogSensorTable OBJECT-TYPE
                        SYNTAX  SEQUENCE OF SensorProbeVirtualAnalogSensorEntry
                        ACCESS  not-accessible
                        STATUS  mandatory
                        DESCRIPTION
                        "This table contains the data for every VirtualAnalog Sensor in the SensorArray. Each row in the table contains data for a different VirtualAnalog Sensor."
                        ::=  {  sensorProbeVirtualAnalogSensor 2   }

                        sensorProbeVirtualAnalogSensorEntry OBJECT-TYPE
                           SYNTAX  SensorProbeVirtualAnalogSensorEntry
                           ACCESS  not-accessible
                           STATUS  mandatory
                           DESCRIPTION
                           "This is an entry in the sensorProbeVirtualAnalogSensorEntry Table"
                           INDEX         { sensorProbeVirtualAnalogSensorIndex }
                           ::=  { sensorProbeVirtualAnalogSensorTable 1 }

                        SensorProbeVirtualAnalogSensorEntry ::= SEQUENCE {
                           sensorProbeVirtualAnalogSensorIndex
                              INTEGER,
                           sensorProbeVirtualAnalogDescription
                              DisplayString,
                           sensorProbeVirtualAnalogStatus
                              INTEGER,
                           sensorProbeVirtualAnalogOnline
                              INTEGER,
                           sensorProbeVirtualAnalogGoOnline
                              INTEGER,
                           sensorProbeVirtualAnalogHighWarning
                              INTEGER,
                           sensorProbeVirtualAnalogHighCritical
                              INTEGER,
                           sensorProbeVirtualAnalogLowWarning
                              INTEGER,
                           sensorProbeVirtualAnalogLowCritical
                              INTEGER,
                           sensorProbeVirtualAnalogRearm
                              INTEGER,
                           sensorProbeVirtualAnalogRaw
                              INTEGER,
                           sensorProbeVirtualAnalogEmailTrapLimit
                              INTEGER,
                           sensorProbeVirtualAnalogDelayError
                              INTEGER,
                           sensorProbeVirtualAnalogDelayNormal
                              INTEGER,
                           sensorProbeVirtualAnalogUnit
                              DisplayString,
                           sensorProbeVirtualAnalogAcknowledgement
                              INTEGER,
                           sensorProbeVirtualAnalogURL
                              DisplayString,
                           sensorProbeVirtualAnalogOpenURL
                              INTEGER,
                           sensorProbeVirtualAnalogContTimeHighCritical
                              INTEGER,
                           sensorProbeVirtualAnalogContTimeHighWarning
                              INTEGER,
                           sensorProbeVirtualAnalogContTimeNormal
                              INTEGER,
                           sensorProbeVirtualAnalogContTimeLowWarning
                              INTEGER,
                           sensorProbeVirtualAnalogContTimeLowCritical
                              INTEGER,
                           sensorProbeVirtualAnalogContTimeSensorError
                              INTEGER,
                           sensorProbeVirtualAnalogCalendar
                              INTEGER,
                           sensorProbeVirtualAnalogValueFactor
                              INTEGER
                        }

                          sensorProbeVirtualAnalogSensorIndex OBJECT-TYPE
                              SYNTAX  INTEGER (0..67)
                              ACCESS  read-only
                              STATUS  mandatory
                              DESCRIPTION
                              "A unique value for each VirtualAnalog sensor port."
                              ::=  {  sensorProbeVirtualAnalogSensorEntry 1   }

                          sensorProbeVirtualAnalogDescription OBJECT-TYPE
                              SYNTAX  DisplayString
                              ACCESS  read-write
                              STATUS  mandatory
                              DESCRIPTION
                              "A Description of this sensor"
                              ::=  {  sensorProbeVirtualAnalogSensorEntry 2   }

                           sensorProbeVirtualAnalogStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVirtualAnalogSensorEntry 4   }

                           sensorProbeVirtualAnalogOnline OBJECT-TYPE
                              SYNTAX  INTEGER {
                                 online(1),
                                 offline(2)
                              }
                              ACCESS  read-only
                              STATUS  mandatory
                              DESCRIPTION
                              "If this Sensor is currently online"
                                 ::=  {  sensorProbeVirtualAnalogSensorEntry 5   }

                           sensorProbeVirtualAnalogGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVirtualAnalogSensorEntry 6   }

                           sensorProbeVirtualAnalogHighWarning OBJECT-TYPE
                              SYNTAX  INTEGER
                              ACCESS  read-write
                              STATUS  mandatory
                              DESCRIPTION
                              "How high the relative VirtualAnalog this sensor measures before it sends a warning"
                              ::=  {  sensorProbeVirtualAnalogSensorEntry 7   }

                           sensorProbeVirtualAnalogHighCritical OBJECT-TYPE
                              SYNTAX  INTEGER
                              ACCESS  read-write
                              STATUS  mandatory
                              DESCRIPTION
                              "How high the relative VirtualAnalog this sensor measures before it becomes critical"
                              ::=  {  sensorProbeVirtualAnalogSensorEntry 8   }

                           sensorProbeVirtualAnalogLowWarning OBJECT-TYPE
                              SYNTAX  INTEGER
                              ACCESS  read-write
                              STATUS  mandatory
                              DESCRIPTION
                              "How low the relative VirtualAnalog this sensor measures before it sends a warning"
                              ::=  {  sensorProbeVirtualAnalogSensorEntry 9   }

                           sensorProbeVirtualAnalogLowCritical OBJECT-TYPE
                              SYNTAX  INTEGER
                              ACCESS  read-write
                              STATUS  mandatory
                              DESCRIPTION
                              "How low the relative VirtualAnalog this sensor measures before it becomes critical"
                              ::=  {  sensorProbeVirtualAnalogSensorEntry 10   }

                           sensorProbeVirtualAnalogRearm OBJECT-TYPE
                              SYNTAX  INTEGER
                              ACCESS  read-write
                              STATUS  mandatory
                              DESCRIPTION
                              "The percent relative VirtualAnalog to rearm the status. For example if status goes from normal to warning, the VirtualAnalog must go down spAnalogueRearm below warning before the status goes to normal"
                              ::=  {  sensorProbeVirtualAnalogSensorEntry 11   }

                           sensorProbeVirtualAnalogRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  sensorProbeVirtualAnalogSensorEntry 13   }

                           sensorProbeVirtualAnalogEmailTrapLimit OBJECT-TYPE
                              SYNTAX  INTEGER {
                                 disable(0),
                                 enable(1)
                              }
                              ACCESS  read-write
                              STATUS  mandatory
                              DESCRIPTION
                              "Enable email/trap limit feature"
                              ::=  {  sensorProbeVirtualAnalogSensorEntry 17   }

                           sensorProbeVirtualAnalogDelayError OBJECT-TYPE
                              SYNTAX  INTEGER (0..65534)
                              ACCESS  read-write
                              STATUS  mandatory
                              DESCRIPTION
                              "Time in seconds after the sensor has been in error status before report as an error"
                              ::=  {  sensorProbeVirtualAnalogSensorEntry 21   }

                           sensorProbeVirtualAnalogDelayNormal OBJECT-TYPE
                              SYNTAX  INTEGER (0..65534)
                              ACCESS  read-write
                              STATUS  mandatory
                              DESCRIPTION
                              "Time in seconds after the sensor change from error to normal before report as normal"
                              ::=  {  sensorProbeVirtualAnalogSensorEntry 22   }

                           sensorProbeVirtualAnalogUnit OBJECT-TYPE
                              SYNTAX  DisplayString
                              ACCESS  read-write
                              STATUS  mandatory
                              DESCRIPTION
                              "Display unit in VirtualAnalog."
                              ::=  {  sensorProbeVirtualAnalogSensorEntry 27   }

                           sensorProbeVirtualAnalogAcknowledgement OBJECT-TYPE
                              SYNTAX INTEGER {
                                 ack(1)
                              }
                              ACCESS read-write
                              STATUS mandatory
                              DESCRIPTION
                              "Acknowledged sensor error and stop notification"
                              ::= {  sensorProbeVirtualAnalogSensorEntry 41 }

                           sensorProbeVirtualAnalogURL OBJECT-TYPE
                              SYNTAX DisplayString
                              ACCESS read-write
                              STATUS mandatory
                              DESCRIPTION
                              "Sensor URL link."
                              ::=  {  sensorProbeVirtualAnalogSensorEntry 43   }

                           sensorProbeVirtualAnalogOpenURL OBJECT-TYPE
                              SYNTAX INTEGER {
                                 cur-window(0),
                                 new-window(2)
                              }
                              ACCESS read-write
                              STATUS mandatory
                              DESCRIPTION
                              "Open URL in this browser or open in a new window."
                              ::=  {  sensorProbeVirtualAnalogSensorEntry 44   }

                           sensorProbeVirtualAnalogContTimeHighCritical OBJECT-TYPE
                              SYNTAX INTEGER (0..65535)
                              ACCESS read-write
                              STATUS mandatory
                              DESCRIPTION
                              "Continuous time for this sensor to be in High Critical before accepting new Status."
                              ::= {  sensorProbeVirtualAnalogSensorEntry 45 }

                           sensorProbeVirtualAnalogContTimeHighWarning OBJECT-TYPE
                              SYNTAX INTEGER (0..65535)
                              ACCESS read-write
                              STATUS mandatory
                              DESCRIPTION
                              "Continuous time for this sensor to be in High Warning before accepting new Status."
                              ::= {  sensorProbeVirtualAnalogSensorEntry 46 }

                           sensorProbeVirtualAnalogContTimeNormal OBJECT-TYPE
                              SYNTAX INTEGER (0..65535)
                              ACCESS read-write
                              STATUS mandatory
                              DESCRIPTION
                              "Continuous time for this sensor to be in Normal before accepting new Status."
                              ::= {  sensorProbeVirtualAnalogSensorEntry 47 }

                           sensorProbeVirtualAnalogContTimeLowWarning OBJECT-TYPE
                              SYNTAX INTEGER (0..65535)
                              ACCESS read-write
                              STATUS mandatory
                              DESCRIPTION
                              "Continuous time for this sensor to be in Low Warning before accepting new Status."
                              ::= {  sensorProbeVirtualAnalogSensorEntry 48 }

                           sensorProbeVirtualAnalogContTimeLowCritical OBJECT-TYPE
                              SYNTAX INTEGER (0..65535)
                              ACCESS read-write
                              STATUS mandatory
                              DESCRIPTION
                              "Continuous time for this sensor to be in Low Critical before accepting new Status."
                              ::= {  sensorProbeVirtualAnalogSensorEntry 49 }

                           sensorProbeVirtualAnalogContTimeSensorError OBJECT-TYPE
                              SYNTAX INTEGER (0..65535)
                              ACCESS read-write
                              STATUS mandatory
                              DESCRIPTION
                              "Continuous time for this sensor to be in Sensor Error before accepting new Status."
                              ::= {  sensorProbeVirtualAnalogSensorEntry 50 }

                           sensorProbeVirtualAnalogCalendar OBJECT-TYPE
                              SYNTAX INTEGER {
                                 disable(0),
                                 enable(1)
                              }
                              ACCESS read-write
                              STATUS mandatory
                              DESCRIPTION
                              "Enable or disable the calendar filtering working hours of sensor."
                              ::= {  sensorProbeVirtualAnalogSensorEntry 51 }

                           sensorProbeVirtualAnalogValueFactor OBJECT-TYPE
                              SYNTAX INTEGER {
                                 x1(1),
                                 x0-1(10),
                                 x0-01(100),
                                 x0-001(1000)
                              }
                              ACCESS read-write
                              STATUS mandatory
                              DESCRIPTION
                              "To change the ratio of value."
                              ::= {  sensorProbeVirtualAnalogSensorEntry 52 }

                  sensorProbeVirtualSwitchSensor OBJECT IDENTIFIER ::= { sensorProbeOtherSensor 31  }

                     sensorProbeVirtualSwitchSensorNumber OBJECT-TYPE
                        SYNTAX INTEGER
                        ACCESS read-only
                        STATUS mandatory
                        DESCRIPTION
                        "The total number of VirtualSwitch Sensor port."
                        ::= {  sensorProbeVirtualSwitchSensor 1 }

                     sensorProbeVirtualSwitchSensorTable OBJECT-TYPE
                        SYNTAX  SEQUENCE OF SensorProbeVirtualSwitchSensorEntry
                        ACCESS  not-accessible
                        STATUS  mandatory
                        DESCRIPTION
                        "This table contains the data for every VirtualSwitch Sensor in the SensorArray. Each row in the table contains data for a different VirtualSwitch Sensor."
                        ::=  {  sensorProbeVirtualSwitchSensor 2   }

                        sensorProbeVirtualSwitchSensorEntry OBJECT-TYPE
                           SYNTAX  SensorProbeVirtualSwitchSensorEntry
                           ACCESS  not-accessible
                           STATUS  mandatory
                           DESCRIPTION
                           "This is an entry in the sensorProbeVirtualSwitchSensorEntry Table"
                           INDEX         { sensorProbeVirtualSwitchSensorIndex }
                           ::=  { sensorProbeVirtualSwitchSensorTable 1 }

                        SensorProbeVirtualSwitchSensorEntry ::= SEQUENCE {
                           sensorProbeVirtualSwitchSensorIndex
                              INTEGER,
                           sensorProbeVirtualSwitchDescription
                              DisplayString,
                           sensorProbeVirtualSwitchStatus
                              INTEGER,
                           sensorProbeVirtualSwitchOnline
                              INTEGER,
                           sensorProbeVirtualSwitchGoOnline
                              INTEGER,
                           sensorProbeVirtualSwitchEmailTrapLimit
                              INTEGER,
                           sensorProbeVirtualSwitchContTimeHighCritical
                              INTEGER,
                           sensorProbeVirtualSwitchContTimeNormal
                              INTEGER,                         
                           sensorProbeVirtualSwitchDescriptionCritical
                              DisplayString,
                           sensorProbeVirtualSwitchDescriptionNormal
                              DisplayString,                           
                           sensorProbeVirtualSwitchAcknowledgement
                              INTEGER,                             
                           sensorProbeVirtualSwitchURL
                              DisplayString,
                           sensorProbeVirtualSwitchOpenURL
                              INTEGER,
                           sensorProbeVirtualSwitchCalendar
                              INTEGER,
                           sensorProbeVirtualSwitchNormalState
                              INTEGER
                        }

                          sensorProbeVirtualSwitchSensorIndex OBJECT-TYPE
                              SYNTAX  INTEGER (0..67)
                              ACCESS  read-only
                              STATUS  mandatory
                              DESCRIPTION
                              "A unique value for each VirtualSwitch sensor port."
                              ::=  {  sensorProbeVirtualSwitchSensorEntry 1   }

                          sensorProbeVirtualSwitchDescription OBJECT-TYPE
                              SYNTAX  DisplayString
                              ACCESS  read-write
                              STATUS  mandatory
                              DESCRIPTION
                              "A Description of this sensor"
                              ::=  {  sensorProbeVirtualSwitchSensorEntry 2   }

                           sensorProbeVirtualSwitchStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeVirtualSwitchSensorEntry 4   }

                           sensorProbeVirtualSwitchOnline OBJECT-TYPE
                              SYNTAX  INTEGER {
                                 online(1),
                                 offline(2)
                              }
                              ACCESS  read-only
                              STATUS  mandatory
                              DESCRIPTION
                              "If this Sensor is currently online"
                                 ::=  {  sensorProbeVirtualSwitchSensorEntry 5   }

                           sensorProbeVirtualSwitchGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeVirtualSwitchSensorEntry 6   }

                           sensorProbeVirtualSwitchEmailTrapLimit OBJECT-TYPE
                              SYNTAX  INTEGER {
                                 disable(0),
                                 enable(1)
                              }
                              ACCESS  read-write
                              STATUS  mandatory
                              DESCRIPTION
                              "Enable email/trap limit feature"
                              ::=  {  sensorProbeVirtualSwitchSensorEntry 17   }

                           sensorProbeVirtualSwitchContTimeHighCritical OBJECT-TYPE
                              SYNTAX  INTEGER (0..65534)
                              ACCESS  read-write
                              STATUS  mandatory
                              DESCRIPTION
                              "Continuous time for this sensor to be in High Critical before accepting new Status."
                              ::=  {  sensorProbeVirtualSwitchSensorEntry 21   }

                           sensorProbeVirtualSwitchContTimeNormal OBJECT-TYPE
                              SYNTAX INTEGER (0..65535)
                              ACCESS read-write
                              STATUS mandatory
                              DESCRIPTION
                              "Continuous time for this sensor to be in Normal before accepting new Status."
                              ::=  {  sensorProbeVirtualSwitchSensorEntry 22   }

                           sensorProbeVirtualSwitchDescriptionCritical OBJECT-TYPE
                              SYNTAX DisplayString
                              ACCESS read-write
                              STATUS mandatory
                              DESCRIPTION
                              "Description of status when the virsual switch is critical"
                              ::=  {  sensorProbeVirtualSwitchSensorEntry 26   }

                           sensorProbeVirtualSwitchDescriptionNormal OBJECT-TYPE
                              SYNTAX DisplayString
                              ACCESS read-write
                              STATUS mandatory
                              DESCRIPTION
                              "Description of status when the virsual switch is normal"
                              ::=  {  sensorProbeVirtualSwitchSensorEntry 27   }

                           sensorProbeVirtualSwitchAcknowledgement OBJECT-TYPE
                              SYNTAX INTEGER {
                                 ack(1)
                              }
                              ACCESS read-write
                              STATUS mandatory
                              DESCRIPTION
                              "Acknowledged sensor error and stop notification"
                              ::= {  sensorProbeVirtualSwitchSensorEntry 41 }

                           sensorProbeVirtualSwitchURL OBJECT-TYPE
                              SYNTAX DisplayString
                              ACCESS read-write
                              STATUS mandatory
                              DESCRIPTION
                              "Sensor URL link."
                              ::=  {  sensorProbeVirtualSwitchSensorEntry 43   }

                           sensorProbeVirtualSwitchOpenURL OBJECT-TYPE
                              SYNTAX INTEGER {
                                 cur-window(0),
                                 new-window(2)
                              }
                              ACCESS read-write
                              STATUS mandatory
                              DESCRIPTION
                              "Open URL in this browser or open in a new window."
                              ::=  {  sensorProbeVirtualSwitchSensorEntry 44   }

                           sensorProbeVirtualSwitchCalendar OBJECT-TYPE
                              SYNTAX INTEGER {
                                 disable(0),
                                 enable(1)
                              }
                              ACCESS read-write
                              STATUS mandatory
                              DESCRIPTION
                              "Enable or disable the calendar filtering working hours of sensor."
                              ::= {  sensorProbeVirtualSwitchSensorEntry 45 }

                           sensorProbeVirtualSwitchNormalState OBJECT-TYPE
                              SYNTAX INTEGER
                              ACCESS read-write
                              STATUS mandatory
                              DESCRIPTION
                              "The normal state of a return of the virsual switch. If a return of the virsual switch is equal this normal state value, it is normal. Otherwise, it is critical."
                              ::= {  sensorProbeVirtualSwitchSensorEntry 46 }

                  sensorProbeWattHoursSensor OBJECT IDENTIFIER ::= { sensorProbeOtherSensor 32  }

                     sensorProbeWattHoursSensorNumber OBJECT-TYPE
                        SYNTAX INTEGER
                        ACCESS read-only
                        STATUS mandatory
                        DESCRIPTION
                        "The total number of WattHours Sensor port."
                        ::= {  sensorProbeWattHoursSensor 1 }

                     sensorProbeWattHoursSensorTable OBJECT-TYPE
                        SYNTAX  SEQUENCE OF SensorProbeWattHoursSensorEntry
                        ACCESS  not-accessible
                        STATUS  mandatory
                        DESCRIPTION
                        "This table contains the data for every WattHours Sensor in the SensorArray. Each row in the table contains data for a different WattHours Sensor."
                        ::=  {  sensorProbeWattHoursSensor 2   }

                        sensorProbeWattHoursSensorEntry OBJECT-TYPE
                           SYNTAX  SensorProbeWattHoursSensorEntry
                           ACCESS  not-accessible
                           STATUS  mandatory
                           DESCRIPTION
                           "This is an entry in the sensorProbeWattHoursSensorEntry Table"
                           INDEX         { sensorProbeWattHoursSensorIndex }
                           ::=  { sensorProbeWattHoursSensorTable 1 }

                        SensorProbeWattHoursSensorEntry ::= SEQUENCE {
                           sensorProbeWattHoursSensorIndex
                              INTEGER,
                           sensorProbeWattHoursDescription
                              DisplayString,
                           sensorProbeWattHoursPercent
                              INTEGER,
                           sensorProbeWattHoursReset
                              INTEGER
                        }

                          sensorProbeWattHoursSensorIndex OBJECT-TYPE
                              SYNTAX  INTEGER (0..7)
                              ACCESS  read-only
                              STATUS  mandatory
                              DESCRIPTION
                              "A unique value for each WattHours sensor port."
                              ::=  {  sensorProbeWattHoursSensorEntry 1  }

                          sensorProbeWattHoursDescription OBJECT-TYPE
                              SYNTAX  DisplayString
                              ACCESS  read-write
                              STATUS  mandatory
                              DESCRIPTION
                              "A Description of this sensor"
                              ::=  {  sensorProbeWattHoursSensorEntry 2   }

                          sensorProbeWattHoursPercent OBJECT-TYPE
                              SYNTAX  INTEGER (-32768..32767)
                              ACCESS  read-only
                              STATUS  mandatory
                              DESCRIPTION
                              "The relative WattHours percentage measured by this sensor"
                              ::=  {  sensorProbeWattHoursSensorEntry 3   }

                          sensorProbeWattHoursReset OBJECT-TYPE
                              SYNTAX  INTEGER (1)
                              ACCESS  read-write
                              STATUS  mandatory
                              DESCRIPTION
                              "The relative WattHours percentage measured by this sensor"
                              ::=  {  sensorProbeWattHoursSensorEntry 43   }

                        sensorProbeTemperatureArraySensor OBJECT IDENTIFIER ::= { sensorProbeOtherSensor 33  }

                           sensorProbeTemperatureArrayPort1 OBJECT IDENTIFIER ::= { sensorProbeTemperatureArraySensor 1  }
                              sensorProbeTemperatureArrayPort1Number OBJECT-TYPE
                                 SYNTAX INTEGER
                                 ACCESS read-only
                                 STATUS mandatory
                                 DESCRIPTION
                                 "The total number of port on the TemperatureArray."
                                 ::=  {  sensorProbeTemperatureArrayPort1 1   }

                              sensorProbeTemperatureArrayPort1Table OBJECT-TYPE
                                 SYNTAX  SEQUENCE OF SensorProbeTemperatureArrayPort1Entry
                                 ACCESS  not-accessible
                                 STATUS  mandatory
                                 DESCRIPTION
                                 "This table contains the data for every Switch Sensor in the SensorArray. Each row in the table contains data for a different Switch Sensor."
                                 ::=  {  sensorProbeTemperatureArrayPort1 2   }

                                 sensorProbeTemperatureArrayPort1Entry OBJECT-TYPE
                                    SYNTAX  SensorProbeTemperatureArrayPort1Entry
                                    ACCESS  not-accessible
                                    STATUS  mandatory
                                    DESCRIPTION
                                    "This is an entry in the sensorProbeTemperatureArrayPort1 Table"
                                    INDEX         { sensorProbeTemperatureArrayPort1Index }
                                    ::=  { sensorProbeTemperatureArrayPort1Table 1 }

                                    SensorProbeTemperatureArrayPort1Entry ::= SEQUENCE {
                                       sensorProbeTemperatureArrayPort1Index
                                          INTEGER,
                                       sensorProbeTemperatureArrayPort1Description
                                          DisplayString,
                                       sensorProbeTemperatureArrayPort1Value
                                          INTEGER,
                                       sensorProbeTemperatureArrayPort1Status
                                          INTEGER,
                                       sensorProbeTemperatureArrayPort1Online
                                          INTEGER,
                                       sensorProbeTemperatureArrayPort1GoOnline
                                          INTEGER,
                                       sensorProbeTemperatureArrayPort1HighWarning
                                          INTEGER,
                                       sensorProbeTemperatureArrayPort1HighCritical
                                          INTEGER,
                                       sensorProbeTemperatureArrayPort1LowWarning
                                          INTEGER,
                                       sensorProbeTemperatureArrayPort1LowCritical
                                          INTEGER,
                                       sensorProbeTemperatureArrayPort1Rearm
                                          INTEGER,
                                       sensorProbeTemperatureArrayPort1DegreeType
                                          INTEGER,
                                       sensorProbeTemperatureArrayPort1DegreeRaw
                                          INTEGER,
                                       sensorProbeTemperatureArrayPort1Offset
                                          INTEGER,
                                       sensorProbeTemperatureArrayPort1URL
                                          DisplayString,
                                       sensorProbeTemperatureArrayPort1OpenURL
                                          INTEGER,
                                       sensorProbeTemperatureArrayPort1DatacollectType
                                          INTEGER,
                                       sensorProbeTemperatureArrayPort1ContTimeHighCritical
                                          INTEGER,
                                       sensorProbeTemperatureArrayPort1ContTimeHighWarning
                                          INTEGER,
                                       sensorProbeTemperatureArrayPort1ContTimeNormal
                                          INTEGER,
                                       sensorProbeTemperatureArrayPort1ContTimeLowWarning
                                          INTEGER,
                                       sensorProbeTemperatureArrayPort1ContTimeLowCritical
                                          INTEGER,
                                       sensorProbeTemperatureArrayPort1ContTimeSensorError
                                          INTEGER,
                                       sensorProbeTemperatureArrayPort1Calendar
                                          INTEGER,
                                       sensorProbeThermostatTemperatureArrayPort1Index
                                          INTEGER,
                                       sensorProbeThermostatTemperatureArrayPort1Description
                                          DisplayString,
                                       sensorProbeThermostatTemperatureArrayPort1Value
                                          INTEGER,
                                       sensorProbeThermostatTemperatureArrayPort1Online
                                          INTEGER,
                                       sensorProbeThermostatTemperatureArrayPort1GoOnline
                                          INTEGER,
                                       sensorProbeThermostatTemperatureArrayPort1Mode
                                          INTEGER,
                                       sensorProbeThermostatTemperatureArrayPort1RelayControlPort
                                          INTEGER,
                                       sensorProbeThermostatTemperatureArrayPort1NormalAction1
                                          INTEGER,
                                       sensorProbeThermostatTemperatureArrayPort1HighLimit1
                                          INTEGER,
                                       sensorProbeThermostatTemperatureArrayPort1HighLimitAction1
                                          INTEGER,
                                       sensorProbeThermostatTemperatureArrayPort1LowLimit1
                                          INTEGER,
                                       sensorProbeThermostatTemperatureArrayPort1LowLimitAction1
                                          INTEGER,
                                       sensorProbeThermostatTemperatureArrayPort1NormalAction2
                                          INTEGER,
                                       sensorProbeThermostatTemperatureArrayPort1HighLimit2
                                          INTEGER,
                                       sensorProbeThermostatTemperatureArrayPort1HighLimitAction2
                                          INTEGER,
                                       sensorProbeThermostatTemperatureArrayPort1LowLimit2
                                          INTEGER,
                                       sensorProbeThermostatTemperatureArrayPort1LowLimitAction2
                                          INTEGER,
                                       sensorProbeThermostatTemperatureArrayPort1EnableTime
                                          DisplayString
                                    }

                                    sensorProbeTemperatureArrayPort1Index OBJECT-TYPE
                                       SYNTAX  INTEGER (0..7)
                                       ACCESS  read-only
                                       STATUS  mandatory
                                       DESCRIPTION
                                       "A unique value for each sensor TemperatureArray port."
                                       ::=  {  sensorProbeTemperatureArrayPort1Entry 1   }

                                    sensorProbeTemperatureArrayPort1Description OBJECT-TYPE
                                       SYNTAX  DisplayString
                                       ACCESS  read-write
                                       STATUS  mandatory
                                       DESCRIPTION
                                       "A Description of this sensor TemperatureArray"
                                       ::=  {  sensorProbeTemperatureArrayPort1Entry 2   }

                                    sensorProbeTemperatureArrayPort1Value OBJECT-TYPE
                                       SYNTAX  INTEGER
                                       ACCESS  read-only
                                       STATUS  mandatory
                                       DESCRIPTION
                                       "The value in this sensor"
                                       ::=  {  sensorProbeTemperatureArrayPort1Entry 3   }

                                    sensorProbeTemperatureArrayPort1Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort1Entry 4   }

                                    sensorProbeTemperatureArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort1Entry 5   }

                                    sensorProbeTemperatureArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort1Entry 6   }

                                    sensorProbeTemperatureArrayPort1HighWarning OBJECT-TYPE
                                       SYNTAX  INTEGER
                                       ACCESS  read-write
                                       STATUS  mandatory
                                       DESCRIPTION
                                       "How hot this  sensor gets before it sends a warning"
                                       ::=  {  sensorProbeTemperatureArrayPort1Entry 7   }

                                    sensorProbeTemperatureArrayPort1HighCritical OBJECT-TYPE
                                       SYNTAX  INTEGER
                                       ACCESS  read-write
                                       STATUS  mandatory
                                       DESCRIPTION
                                       "How hot this sensor gets before it sends a critical event"
                                       ::=  {  sensorProbeTemperatureArrayPort1Entry 8   }

                                    sensorProbeTemperatureArrayPort1LowWarning OBJECT-TYPE
                                       SYNTAX  INTEGER
                                       ACCESS  read-write
                                       STATUS  mandatory
                                       DESCRIPTION
                                       "How cold this sensor gets before it sends a warning"
                                       ::=  {  sensorProbeTemperatureArrayPort1Entry 9   }

                                    sensorProbeTemperatureArrayPort1LowCritical OBJECT-TYPE
                                       SYNTAX  INTEGER
                                       ACCESS  read-write
                                       STATUS  mandatory
                                       DESCRIPTION
                                       "How cold this sensor gets before it sends a critical event"
                                       ::=  {  sensorProbeTemperatureArrayPort1Entry 10   }

                                    sensorProbeTemperatureArrayPort1Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort1Entry 11   }

                                    sensorProbeTemperatureArrayPort1DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort1Entry 12   }

                                    sensorProbeTemperatureArrayPort1DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort1Entry 14   }

                                    sensorProbeTemperatureArrayPort1Offset OBJECT-TYPE
                                       SYNTAX  INTEGER
                                       ACCESS  read-write
                                       STATUS  mandatory
                                       DESCRIPTION
                                       "Offset reading"
                                       ::=  {  sensorProbeTemperatureArrayPort1Entry 15   }

                                    sensorProbeTemperatureArrayPort1URL OBJECT-TYPE
                                       SYNTAX  DisplayString
                                       ACCESS  read-write
                                       STATUS  mandatory
                                       DESCRIPTION
                                       "Sensor URL link."
                                       ::=  {  sensorProbeTemperatureArrayPort1Entry 16   }

                                    sensorProbeTemperatureArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort1Entry 17   }

                                    sensorProbeTemperatureArrayPort1DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort1Entry 18   }

                                    sensorProbeTemperatureArrayPort1ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort1Entry 19 }

                                    sensorProbeTemperatureArrayPort1ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort1Entry 20 }

                                    sensorProbeTemperatureArrayPort1ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort1Entry 21 }

                                    sensorProbeTemperatureArrayPort1ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort1Entry 22 }

                                    sensorProbeTemperatureArrayPort1ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort1Entry 23 }

                                    sensorProbeTemperatureArrayPort1ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort1Entry 24 }

                                    sensorProbeTemperatureArrayPort1Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort1Entry 25 }

                                    sensorProbeThermostatTemperatureArrayPort1Index OBJECT-TYPE
                                       SYNTAX  INTEGER
                                       ACCESS  read-only
                                       STATUS  mandatory
                                       DESCRIPTION
                                       "A unique value for each sensor thermostat port."
                                       ::= {  sensorProbeTemperatureArrayPort1Entry 26 }

                                    sensorProbeThermostatTemperatureArrayPort1Description OBJECT-TYPE
                                       SYNTAX  DisplayString
                                       ACCESS  read-write
                                       STATUS  mandatory
                                       DESCRIPTION
                                       "A Description of this sensor thermostat"
                                       ::= {  sensorProbeTemperatureArrayPort1Entry 27 }

                                    sensorProbeThermostatTemperatureArrayPort1Value OBJECT-TYPE
                                       SYNTAX  INTEGER
                                       ACCESS  read-only
                                       STATUS  mandatory
                                       DESCRIPTION
                                       "The value in this sensor"
                                       ::= {  sensorProbeTemperatureArrayPort1Entry 28 }

                                    sensorProbeThermostatTemperatureArrayPort1Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort1Entry 29 }

                                    sensorProbeThermostatTemperatureArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort1Entry 30 }

                                    sensorProbeThermostatTemperatureArrayPort1Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort1Entry 31 }

                                    sensorProbeThermostatTemperatureArrayPort1RelayControlPort OBJECT-TYPE
                                       SYNTAX INTEGER
                                       ACCESS read-write
                                       STATUS mandatory
                                       DESCRIPTION
                                       "To select a relay port to be controled by this thermostat sensor."
                                       ::= {  sensorProbeTemperatureArrayPort1Entry 32 }

                                    sensorProbeThermostatTemperatureArrayPort1NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort1Entry 33 }

                                    sensorProbeThermostatTemperatureArrayPort1HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort1Entry 34 }

                                    sensorProbeThermostatTemperatureArrayPort1HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort1Entry 35 }

                                    sensorProbeThermostatTemperatureArrayPort1LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort1Entry 36 }

                                    sensorProbeThermostatTemperatureArrayPort1LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort1Entry 37 }

                                    sensorProbeThermostatTemperatureArrayPort1NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort1Entry 38 }

                                    sensorProbeThermostatTemperatureArrayPort1HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort1Entry 39 }

                                    sensorProbeThermostatTemperatureArrayPort1HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort1Entry 40 }

                                    sensorProbeThermostatTemperatureArrayPort1LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort1Entry 41 }

                                    sensorProbeThermostatTemperatureArrayPort1LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort1Entry 42 }

                                    sensorProbeThermostatTemperatureArrayPort1EnableTime OBJECT-TYPE
                                       SYNTAX  DisplayString
                                       ACCESS  read-write
                                       STATUS  mandatory
                                       DESCRIPTION
                                       "Time to enable on Thermostat"
                                       ::=  {  sensorProbeTemperatureArrayPort1Entry 43 }

                           sensorProbeTemperatureArrayPort2 OBJECT IDENTIFIER ::= { sensorProbeTemperatureArraySensor 2  }
                              sensorProbeTemperatureArrayPort2Number OBJECT-TYPE
                                 SYNTAX INTEGER
                                 ACCESS read-only
                                 STATUS mandatory
                                 DESCRIPTION
                                 "The total number of port on the TemperatureArray."
                                 ::=  {  sensorProbeTemperatureArrayPort2 1   }

                              sensorProbeTemperatureArrayPort2Table OBJECT-TYPE
                                 SYNTAX  SEQUENCE OF SensorProbeTemperatureArrayPort2Entry
                                 ACCESS  not-accessible
                                 STATUS  mandatory
                                 DESCRIPTION
                                 "This table contains the data for every Switch Sensor in the SensorArray. Each row in the table contains data for a different Switch Sensor."
                                 ::=  {  sensorProbeTemperatureArrayPort2 2   }

                                 sensorProbeTemperatureArrayPort2Entry OBJECT-TYPE
                                    SYNTAX  SensorProbeTemperatureArrayPort2Entry
                                    ACCESS  not-accessible
                                    STATUS  mandatory
                                    DESCRIPTION
                                    "This is an entry in the sensorProbeTemperatureArrayPort2 Table"
                                    INDEX         { sensorProbeTemperatureArrayPort2Index }
                                    ::=  { sensorProbeTemperatureArrayPort2Table 1 }

                                    SensorProbeTemperatureArrayPort2Entry ::= SEQUENCE {
                                       sensorProbeTemperatureArrayPort2Index
                                          INTEGER,
                                       sensorProbeTemperatureArrayPort2Description
                                          DisplayString,
                                       sensorProbeTemperatureArrayPort2Value
                                          INTEGER,
                                       sensorProbeTemperatureArrayPort2Status
                                          INTEGER,
                                       sensorProbeTemperatureArrayPort2Online
                                          INTEGER,
                                       sensorProbeTemperatureArrayPort2GoOnline
                                          INTEGER,
                                       sensorProbeTemperatureArrayPort2HighWarning
                                          INTEGER,
                                       sensorProbeTemperatureArrayPort2HighCritical
                                          INTEGER,
                                       sensorProbeTemperatureArrayPort2LowWarning
                                          INTEGER,
                                       sensorProbeTemperatureArrayPort2LowCritical
                                          INTEGER,
                                       sensorProbeTemperatureArrayPort2Rearm
                                          INTEGER,
                                       sensorProbeTemperatureArrayPort2DegreeType
                                          INTEGER,
                                       sensorProbeTemperatureArrayPort2DegreeRaw
                                          INTEGER,
                                       sensorProbeTemperatureArrayPort2Offset
                                          INTEGER,
                                       sensorProbeTemperatureArrayPort2URL
                                          DisplayString,
                                       sensorProbeTemperatureArrayPort2OpenURL
                                          INTEGER,
                                       sensorProbeTemperatureArrayPort2DatacollectType
                                          INTEGER,
                                       sensorProbeTemperatureArrayPort2ContTimeHighCritical
                                          INTEGER,
                                       sensorProbeTemperatureArrayPort2ContTimeHighWarning
                                          INTEGER,
                                       sensorProbeTemperatureArrayPort2ContTimeNormal
                                          INTEGER,
                                       sensorProbeTemperatureArrayPort2ContTimeLowWarning
                                          INTEGER,
                                       sensorProbeTemperatureArrayPort2ContTimeLowCritical
                                          INTEGER,
                                       sensorProbeTemperatureArrayPort2ContTimeSensorError
                                          INTEGER,
                                       sensorProbeTemperatureArrayPort2Calendar
                                          INTEGER,
                                       sensorProbeThermostatTemperatureArrayPort2Index
                                          INTEGER,
                                       sensorProbeThermostatTemperatureArrayPort2Description
                                          DisplayString,
                                       sensorProbeThermostatTemperatureArrayPort2Value
                                          INTEGER,
                                       sensorProbeThermostatTemperatureArrayPort2Online
                                          INTEGER,
                                       sensorProbeThermostatTemperatureArrayPort2GoOnline
                                          INTEGER,
                                       sensorProbeThermostatTemperatureArrayPort2Mode
                                          INTEGER,
                                       sensorProbeThermostatTemperatureArrayPort2RelayControlPort
                                          INTEGER,
                                       sensorProbeThermostatTemperatureArrayPort2NormalAction1
                                          INTEGER,
                                       sensorProbeThermostatTemperatureArrayPort2HighLimit1
                                          INTEGER,
                                       sensorProbeThermostatTemperatureArrayPort2HighLimitAction1
                                          INTEGER,
                                       sensorProbeThermostatTemperatureArrayPort2LowLimit1
                                          INTEGER,
                                       sensorProbeThermostatTemperatureArrayPort2LowLimitAction1
                                          INTEGER,
                                       sensorProbeThermostatTemperatureArrayPort2NormalAction2
                                          INTEGER,
                                       sensorProbeThermostatTemperatureArrayPort2HighLimit2
                                          INTEGER,
                                       sensorProbeThermostatTemperatureArrayPort2HighLimitAction2
                                          INTEGER,
                                       sensorProbeThermostatTemperatureArrayPort2LowLimit2
                                          INTEGER,
                                       sensorProbeThermostatTemperatureArrayPort2LowLimitAction2
                                          INTEGER,
                                       sensorProbeThermostatTemperatureArrayPort2EnableTime
                                          DisplayString
                                    }

                                    sensorProbeTemperatureArrayPort2Index OBJECT-TYPE
                                       SYNTAX  INTEGER (0..7)
                                       ACCESS  read-only
                                       STATUS  mandatory
                                       DESCRIPTION
                                       "A unique value for each sensor TemperatureArray port."
                                       ::=  {  sensorProbeTemperatureArrayPort2Entry 1   }

                                    sensorProbeTemperatureArrayPort2Description OBJECT-TYPE
                                       SYNTAX  DisplayString
                                       ACCESS  read-write
                                       STATUS  mandatory
                                       DESCRIPTION
                                       "A Description of this sensor TemperatureArray"
                                       ::=  {  sensorProbeTemperatureArrayPort2Entry 2   }

                                    sensorProbeTemperatureArrayPort2Value OBJECT-TYPE
                                       SYNTAX  INTEGER
                                       ACCESS  read-only
                                       STATUS  mandatory
                                       DESCRIPTION
                                       "The value in this sensor"
                                       ::=  {  sensorProbeTemperatureArrayPort2Entry 3   }

                                    sensorProbeTemperatureArrayPort2Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort2Entry 4   }

                                    sensorProbeTemperatureArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort2Entry 5   }

                                    sensorProbeTemperatureArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort2Entry 6   }

                                    sensorProbeTemperatureArrayPort2HighWarning OBJECT-TYPE
                                       SYNTAX  INTEGER
                                       ACCESS  read-write
                                       STATUS  mandatory
                                       DESCRIPTION
                                       "How hot this  sensor gets before it sends a warning"
                                       ::=  {  sensorProbeTemperatureArrayPort2Entry 7   }

                                    sensorProbeTemperatureArrayPort2HighCritical OBJECT-TYPE
                                       SYNTAX  INTEGER
                                       ACCESS  read-write
                                       STATUS  mandatory
                                       DESCRIPTION
                                       "How hot this sensor gets before it sends a critical event"
                                       ::=  {  sensorProbeTemperatureArrayPort2Entry 8   }

                                    sensorProbeTemperatureArrayPort2LowWarning OBJECT-TYPE
                                       SYNTAX  INTEGER
                                       ACCESS  read-write
                                       STATUS  mandatory
                                       DESCRIPTION
                                       "How cold this sensor gets before it sends a warning"
                                       ::=  {  sensorProbeTemperatureArrayPort2Entry 9   }

                                    sensorProbeTemperatureArrayPort2LowCritical OBJECT-TYPE
                                       SYNTAX  INTEGER
                                       ACCESS  read-write
                                       STATUS  mandatory
                                       DESCRIPTION
                                       "How cold this sensor gets before it sends a critical event"
                                       ::=  {  sensorProbeTemperatureArrayPort2Entry 10   }

                                    sensorProbeTemperatureArrayPort2Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort2Entry 11   }

                                    sensorProbeTemperatureArrayPort2DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort2Entry 12   }

                                    sensorProbeTemperatureArrayPort2DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort2Entry 14   }

                                    sensorProbeTemperatureArrayPort2Offset OBJECT-TYPE
                                       SYNTAX  INTEGER
                                       ACCESS  read-write
                                       STATUS  mandatory
                                       DESCRIPTION
                                       "Offset reading"
                                       ::=  {  sensorProbeTemperatureArrayPort2Entry 15   }

                                    sensorProbeTemperatureArrayPort2URL OBJECT-TYPE
                                       SYNTAX  DisplayString
                                       ACCESS  read-write
                                       STATUS  mandatory
                                       DESCRIPTION
                                       "Sensor URL link."
                                       ::=  {  sensorProbeTemperatureArrayPort2Entry 16   }

                                    sensorProbeTemperatureArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort2Entry 17   }

                                    sensorProbeTemperatureArrayPort2DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort2Entry 18   }

                                    sensorProbeTemperatureArrayPort2ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort2Entry 19 }

                                    sensorProbeTemperatureArrayPort2ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort2Entry 20 }

                                    sensorProbeTemperatureArrayPort2ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort2Entry 21 }

                                    sensorProbeTemperatureArrayPort2ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort2Entry 22 }

                                    sensorProbeTemperatureArrayPort2ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort2Entry 23 }

                                    sensorProbeTemperatureArrayPort2ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort2Entry 24 }

                                    sensorProbeTemperatureArrayPort2Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort2Entry 25 }

                                    sensorProbeThermostatTemperatureArrayPort2Index OBJECT-TYPE
                                       SYNTAX  INTEGER
                                       ACCESS  read-only
                                       STATUS  mandatory
                                       DESCRIPTION
                                       "A unique value for each sensor thermostat port."
                                       ::= {  sensorProbeTemperatureArrayPort2Entry 26 }

                                    sensorProbeThermostatTemperatureArrayPort2Description OBJECT-TYPE
                                       SYNTAX  DisplayString
                                       ACCESS  read-write
                                       STATUS  mandatory
                                       DESCRIPTION
                                       "A Description of this sensor thermostat"
                                       ::= {  sensorProbeTemperatureArrayPort2Entry 27 }

                                    sensorProbeThermostatTemperatureArrayPort2Value OBJECT-TYPE
                                       SYNTAX  INTEGER
                                       ACCESS  read-only
                                       STATUS  mandatory
                                       DESCRIPTION
                                       "The value in this sensor"
                                       ::= {  sensorProbeTemperatureArrayPort2Entry 28 }

                                    sensorProbeThermostatTemperatureArrayPort2Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort2Entry 29 }

                                    sensorProbeThermostatTemperatureArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort2Entry 30 }

                                    sensorProbeThermostatTemperatureArrayPort2Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort2Entry 31 }

                                    sensorProbeThermostatTemperatureArrayPort2RelayControlPort OBJECT-TYPE
                                       SYNTAX INTEGER
                                       ACCESS read-write
                                       STATUS mandatory
                                       DESCRIPTION
                                       "To select a relay port to be controled by this thermostat sensor."
                                       ::= {  sensorProbeTemperatureArrayPort2Entry 32 }

                                    sensorProbeThermostatTemperatureArrayPort2NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort2Entry 33 }

                                    sensorProbeThermostatTemperatureArrayPort2HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort2Entry 34 }

                                    sensorProbeThermostatTemperatureArrayPort2HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort2Entry 35 }

                                    sensorProbeThermostatTemperatureArrayPort2LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort2Entry 36 }

                                    sensorProbeThermostatTemperatureArrayPort2LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort2Entry 37 }

                                    sensorProbeThermostatTemperatureArrayPort2NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort2Entry 38 }

                                    sensorProbeThermostatTemperatureArrayPort2HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort2Entry 39 }

                                    sensorProbeThermostatTemperatureArrayPort2HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort2Entry 40 }

                                    sensorProbeThermostatTemperatureArrayPort2LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort2Entry 41 }

                                    sensorProbeThermostatTemperatureArrayPort2LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort2Entry 42 }

                                    sensorProbeThermostatTemperatureArrayPort2EnableTime OBJECT-TYPE
                                       SYNTAX  DisplayString
                                       ACCESS  read-write
                                       STATUS  mandatory
                                       DESCRIPTION
                                       "Time to enable on Thermostat"
                                       ::=  {  sensorProbeTemperatureArrayPort2Entry 43 }

                           sensorProbeTemperatureArrayPort3 OBJECT IDENTIFIER ::= { sensorProbeTemperatureArraySensor 3  }
                              sensorProbeTemperatureArrayPort3Number OBJECT-TYPE
                                 SYNTAX INTEGER
                                 ACCESS read-only
                                 STATUS mandatory
                                 DESCRIPTION
                                 "The total number of port on the TemperatureArray."
                                 ::=  {  sensorProbeTemperatureArrayPort3 1   }

                              sensorProbeTemperatureArrayPort3Table OBJECT-TYPE
                                 SYNTAX  SEQUENCE OF SensorProbeTemperatureArrayPort3Entry
                                 ACCESS  not-accessible
                                 STATUS  mandatory
                                 DESCRIPTION
                                 "This table contains the data for every Switch Sensor in the SensorArray. Each row in the table contains data for a different Switch Sensor."
                                 ::=  {  sensorProbeTemperatureArrayPort3 2   }

                                 sensorProbeTemperatureArrayPort3Entry OBJECT-TYPE
                                    SYNTAX  SensorProbeTemperatureArrayPort3Entry
                                    ACCESS  not-accessible
                                    STATUS  mandatory
                                    DESCRIPTION
                                    "This is an entry in the sensorProbeTemperatureArrayPort3 Table"
                                    INDEX         { sensorProbeTemperatureArrayPort3Index }
                                    ::=  { sensorProbeTemperatureArrayPort3Table 1 }

                                    SensorProbeTemperatureArrayPort3Entry ::= SEQUENCE {
                                       sensorProbeTemperatureArrayPort3Index
                                          INTEGER,
                                       sensorProbeTemperatureArrayPort3Description
                                          DisplayString,
                                       sensorProbeTemperatureArrayPort3Value
                                          INTEGER,
                                       sensorProbeTemperatureArrayPort3Status
                                          INTEGER,
                                       sensorProbeTemperatureArrayPort3Online
                                          INTEGER,
                                       sensorProbeTemperatureArrayPort3GoOnline
                                          INTEGER,
                                       sensorProbeTemperatureArrayPort3HighWarning
                                          INTEGER,
                                       sensorProbeTemperatureArrayPort3HighCritical
                                          INTEGER,
                                       sensorProbeTemperatureArrayPort3LowWarning
                                          INTEGER,
                                       sensorProbeTemperatureArrayPort3LowCritical
                                          INTEGER,
                                       sensorProbeTemperatureArrayPort3Rearm
                                          INTEGER,
                                       sensorProbeTemperatureArrayPort3DegreeType
                                          INTEGER,
                                       sensorProbeTemperatureArrayPort3DegreeRaw
                                          INTEGER,
                                       sensorProbeTemperatureArrayPort3Offset
                                          INTEGER,
                                       sensorProbeTemperatureArrayPort3URL
                                          DisplayString,
                                       sensorProbeTemperatureArrayPort3OpenURL
                                          INTEGER,
                                       sensorProbeTemperatureArrayPort3DatacollectType
                                          INTEGER,
                                       sensorProbeTemperatureArrayPort3ContTimeHighCritical
                                          INTEGER,
                                       sensorProbeTemperatureArrayPort3ContTimeHighWarning
                                          INTEGER,
                                       sensorProbeTemperatureArrayPort3ContTimeNormal
                                          INTEGER,
                                       sensorProbeTemperatureArrayPort3ContTimeLowWarning
                                          INTEGER,
                                       sensorProbeTemperatureArrayPort3ContTimeLowCritical
                                          INTEGER,
                                       sensorProbeTemperatureArrayPort3ContTimeSensorError
                                          INTEGER,
                                       sensorProbeTemperatureArrayPort3Calendar
                                          INTEGER,
                                       sensorProbeThermostatTemperatureArrayPort3Index
                                          INTEGER,
                                       sensorProbeThermostatTemperatureArrayPort3Description
                                          DisplayString,
                                       sensorProbeThermostatTemperatureArrayPort3Value
                                          INTEGER,
                                       sensorProbeThermostatTemperatureArrayPort3Online
                                          INTEGER,
                                       sensorProbeThermostatTemperatureArrayPort3GoOnline
                                          INTEGER,
                                       sensorProbeThermostatTemperatureArrayPort3Mode
                                          INTEGER,
                                       sensorProbeThermostatTemperatureArrayPort3RelayControlPort
                                          INTEGER,
                                       sensorProbeThermostatTemperatureArrayPort3NormalAction1
                                          INTEGER,
                                       sensorProbeThermostatTemperatureArrayPort3HighLimit1
                                          INTEGER,
                                       sensorProbeThermostatTemperatureArrayPort3HighLimitAction1
                                          INTEGER,
                                       sensorProbeThermostatTemperatureArrayPort3LowLimit1
                                          INTEGER,
                                       sensorProbeThermostatTemperatureArrayPort3LowLimitAction1
                                          INTEGER,
                                       sensorProbeThermostatTemperatureArrayPort3NormalAction2
                                          INTEGER,
                                       sensorProbeThermostatTemperatureArrayPort3HighLimit2
                                          INTEGER,
                                       sensorProbeThermostatTemperatureArrayPort3HighLimitAction2
                                          INTEGER,
                                       sensorProbeThermostatTemperatureArrayPort3LowLimit2
                                          INTEGER,
                                       sensorProbeThermostatTemperatureArrayPort3LowLimitAction2
                                          INTEGER,
                                       sensorProbeThermostatTemperatureArrayPort3EnableTime
                                          DisplayString
                                    }

                                    sensorProbeTemperatureArrayPort3Index OBJECT-TYPE
                                       SYNTAX  INTEGER (0..7)
                                       ACCESS  read-only
                                       STATUS  mandatory
                                       DESCRIPTION
                                       "A unique value for each sensor TemperatureArray port."
                                       ::=  {  sensorProbeTemperatureArrayPort3Entry 1   }

                                    sensorProbeTemperatureArrayPort3Description OBJECT-TYPE
                                       SYNTAX  DisplayString
                                       ACCESS  read-write
                                       STATUS  mandatory
                                       DESCRIPTION
                                       "A Description of this sensor TemperatureArray"
                                       ::=  {  sensorProbeTemperatureArrayPort3Entry 2   }

                                    sensorProbeTemperatureArrayPort3Value OBJECT-TYPE
                                       SYNTAX  INTEGER
                                       ACCESS  read-only
                                       STATUS  mandatory
                                       DESCRIPTION
                                       "The value in this sensor"
                                       ::=  {  sensorProbeTemperatureArrayPort3Entry 3   }

                                    sensorProbeTemperatureArrayPort3Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort3Entry 4   }

                                    sensorProbeTemperatureArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort3Entry 5   }

                                    sensorProbeTemperatureArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort3Entry 6   }

                                    sensorProbeTemperatureArrayPort3HighWarning OBJECT-TYPE
                                       SYNTAX  INTEGER
                                       ACCESS  read-write
                                       STATUS  mandatory
                                       DESCRIPTION
                                       "How hot this  sensor gets before it sends a warning"
                                       ::=  {  sensorProbeTemperatureArrayPort3Entry 7   }

                                    sensorProbeTemperatureArrayPort3HighCritical OBJECT-TYPE
                                       SYNTAX  INTEGER
                                       ACCESS  read-write
                                       STATUS  mandatory
                                       DESCRIPTION
                                       "How hot this sensor gets before it sends a critical event"
                                       ::=  {  sensorProbeTemperatureArrayPort3Entry 8   }

                                    sensorProbeTemperatureArrayPort3LowWarning OBJECT-TYPE
                                       SYNTAX  INTEGER
                                       ACCESS  read-write
                                       STATUS  mandatory
                                       DESCRIPTION
                                       "How cold this sensor gets before it sends a warning"
                                       ::=  {  sensorProbeTemperatureArrayPort3Entry 9   }

                                    sensorProbeTemperatureArrayPort3LowCritical OBJECT-TYPE
                                       SYNTAX  INTEGER
                                       ACCESS  read-write
                                       STATUS  mandatory
                                       DESCRIPTION
                                       "How cold this sensor gets before it sends a critical event"
                                       ::=  {  sensorProbeTemperatureArrayPort3Entry 10   }

                                    sensorProbeTemperatureArrayPort3Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort3Entry 11   }

                                    sensorProbeTemperatureArrayPort3DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort3Entry 12   }

                                    sensorProbeTemperatureArrayPort3DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort3Entry 14   }

                                    sensorProbeTemperatureArrayPort3Offset OBJECT-TYPE
                                       SYNTAX  INTEGER
                                       ACCESS  read-write
                                       STATUS  mandatory
                                       DESCRIPTION
                                       "Offset reading"
                                       ::=  {  sensorProbeTemperatureArrayPort3Entry 15   }

                                    sensorProbeTemperatureArrayPort3URL OBJECT-TYPE
                                       SYNTAX  DisplayString
                                       ACCESS  read-write
                                       STATUS  mandatory
                                       DESCRIPTION
                                       "Sensor URL link."
                                       ::=  {  sensorProbeTemperatureArrayPort3Entry 16   }

                                    sensorProbeTemperatureArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort3Entry 17   }

                                    sensorProbeTemperatureArrayPort3DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort3Entry 18   }

                                    sensorProbeTemperatureArrayPort3ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort3Entry 19 }

                                    sensorProbeTemperatureArrayPort3ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort3Entry 20 }

                                    sensorProbeTemperatureArrayPort3ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort3Entry 21 }

                                    sensorProbeTemperatureArrayPort3ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort3Entry 22 }

                                    sensorProbeTemperatureArrayPort3ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort3Entry 23 }

                                    sensorProbeTemperatureArrayPort3ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort3Entry 24 }

                                    sensorProbeTemperatureArrayPort3Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort3Entry 25 }

                                    sensorProbeThermostatTemperatureArrayPort3Index OBJECT-TYPE
                                       SYNTAX  INTEGER
                                       ACCESS  read-only
                                       STATUS  mandatory
                                       DESCRIPTION
                                       "A unique value for each sensor thermostat port."
                                       ::= {  sensorProbeTemperatureArrayPort3Entry 26 }

                                    sensorProbeThermostatTemperatureArrayPort3Description OBJECT-TYPE
                                       SYNTAX  DisplayString
                                       ACCESS  read-write
                                       STATUS  mandatory
                                       DESCRIPTION
                                       "A Description of this sensor thermostat"
                                       ::= {  sensorProbeTemperatureArrayPort3Entry 27 }

                                    sensorProbeThermostatTemperatureArrayPort3Value OBJECT-TYPE
                                       SYNTAX  INTEGER
                                       ACCESS  read-only
                                       STATUS  mandatory
                                       DESCRIPTION
                                       "The value in this sensor"
                                       ::= {  sensorProbeTemperatureArrayPort3Entry 28 }

                                    sensorProbeThermostatTemperatureArrayPort3Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort3Entry 29 }

                                    sensorProbeThermostatTemperatureArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort3Entry 30 }

                                    sensorProbeThermostatTemperatureArrayPort3Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort3Entry 31 }

                                    sensorProbeThermostatTemperatureArrayPort3RelayControlPort OBJECT-TYPE
                                       SYNTAX INTEGER
                                       ACCESS read-write
                                       STATUS mandatory
                                       DESCRIPTION
                                       "To select a relay port to be controled by this thermostat sensor."
                                       ::= {  sensorProbeTemperatureArrayPort3Entry 32 }

                                    sensorProbeThermostatTemperatureArrayPort3NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort3Entry 33 }

                                    sensorProbeThermostatTemperatureArrayPort3HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort3Entry 34 }

                                    sensorProbeThermostatTemperatureArrayPort3HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort3Entry 35 }

                                    sensorProbeThermostatTemperatureArrayPort3LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort3Entry 36 }

                                    sensorProbeThermostatTemperatureArrayPort3LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort3Entry 37 }

                                    sensorProbeThermostatTemperatureArrayPort3NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort3Entry 38 }

                                    sensorProbeThermostatTemperatureArrayPort3HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort3Entry 39 }

                                    sensorProbeThermostatTemperatureArrayPort3HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort3Entry 40 }

                                    sensorProbeThermostatTemperatureArrayPort3LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort3Entry 41 }

                                    sensorProbeThermostatTemperatureArrayPort3LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort3Entry 42 }

                                    sensorProbeThermostatTemperatureArrayPort3EnableTime OBJECT-TYPE
                                       SYNTAX  DisplayString
                                       ACCESS  read-write
                                       STATUS  mandatory
                                       DESCRIPTION
                                       "Time to enable on Thermostat"
                                       ::=  {  sensorProbeTemperatureArrayPort3Entry 43 }


                           sensorProbeTemperatureArrayPort4 OBJECT IDENTIFIER ::= { sensorProbeTemperatureArraySensor 4  }
                              sensorProbeTemperatureArrayPort4Number OBJECT-TYPE
                                 SYNTAX INTEGER
                                 ACCESS read-only
                                 STATUS mandatory
                                 DESCRIPTION
                                 "The total number of port on the TemperatureArray."
                                 ::=  {  sensorProbeTemperatureArrayPort4 1   }

                              sensorProbeTemperatureArrayPort4Table OBJECT-TYPE
                                 SYNTAX  SEQUENCE OF SensorProbeTemperatureArrayPort4Entry
                                 ACCESS  not-accessible
                                 STATUS  mandatory
                                 DESCRIPTION
                                 "This table contains the data for every Switch Sensor in the SensorArray. Each row in the table contains data for a different Switch Sensor."
                                 ::=  {  sensorProbeTemperatureArrayPort4 2   }

                                 sensorProbeTemperatureArrayPort4Entry OBJECT-TYPE
                                    SYNTAX  SensorProbeTemperatureArrayPort4Entry
                                    ACCESS  not-accessible
                                    STATUS  mandatory
                                    DESCRIPTION
                                    "This is an entry in the sensorProbeTemperatureArrayPort4 Table"
                                    INDEX         { sensorProbeTemperatureArrayPort4Index }
                                    ::=  { sensorProbeTemperatureArrayPort4Table 1 }

                                    SensorProbeTemperatureArrayPort4Entry ::= SEQUENCE {
                                       sensorProbeTemperatureArrayPort4Index
                                          INTEGER,
                                       sensorProbeTemperatureArrayPort4Description
                                          DisplayString,
                                       sensorProbeTemperatureArrayPort4Value
                                          INTEGER,
                                       sensorProbeTemperatureArrayPort4Status
                                          INTEGER,
                                       sensorProbeTemperatureArrayPort4Online
                                          INTEGER,
                                       sensorProbeTemperatureArrayPort4GoOnline
                                          INTEGER,
                                       sensorProbeTemperatureArrayPort4HighWarning
                                          INTEGER,
                                       sensorProbeTemperatureArrayPort4HighCritical
                                          INTEGER,
                                       sensorProbeTemperatureArrayPort4LowWarning
                                          INTEGER,
                                       sensorProbeTemperatureArrayPort4LowCritical
                                          INTEGER,
                                       sensorProbeTemperatureArrayPort4Rearm
                                          INTEGER,
                                       sensorProbeTemperatureArrayPort4DegreeType
                                          INTEGER,
                                       sensorProbeTemperatureArrayPort4DegreeRaw
                                          INTEGER,
                                       sensorProbeTemperatureArrayPort4Offset
                                          INTEGER,
                                       sensorProbeTemperatureArrayPort4URL
                                          DisplayString,
                                       sensorProbeTemperatureArrayPort4OpenURL
                                          INTEGER,
                                       sensorProbeTemperatureArrayPort4DatacollectType
                                          INTEGER,
                                       sensorProbeTemperatureArrayPort4ContTimeHighCritical
                                          INTEGER,
                                       sensorProbeTemperatureArrayPort4ContTimeHighWarning
                                          INTEGER,
                                       sensorProbeTemperatureArrayPort4ContTimeNormal
                                          INTEGER,
                                       sensorProbeTemperatureArrayPort4ContTimeLowWarning
                                          INTEGER,
                                       sensorProbeTemperatureArrayPort4ContTimeLowCritical
                                          INTEGER,
                                       sensorProbeTemperatureArrayPort4ContTimeSensorError
                                          INTEGER,
                                       sensorProbeTemperatureArrayPort4Calendar
                                          INTEGER,
                                       sensorProbeThermostatTemperatureArrayPort4Index
                                          INTEGER,
                                       sensorProbeThermostatTemperatureArrayPort4Description
                                          DisplayString,
                                       sensorProbeThermostatTemperatureArrayPort4Value
                                          INTEGER,
                                       sensorProbeThermostatTemperatureArrayPort4Online
                                          INTEGER,
                                       sensorProbeThermostatTemperatureArrayPort4GoOnline
                                          INTEGER,
                                       sensorProbeThermostatTemperatureArrayPort4Mode
                                          INTEGER,
                                       sensorProbeThermostatTemperatureArrayPort4RelayControlPort
                                          INTEGER,
                                       sensorProbeThermostatTemperatureArrayPort4NormalAction1
                                          INTEGER,
                                       sensorProbeThermostatTemperatureArrayPort4HighLimit1
                                          INTEGER,
                                       sensorProbeThermostatTemperatureArrayPort4HighLimitAction1
                                          INTEGER,
                                       sensorProbeThermostatTemperatureArrayPort4LowLimit1
                                          INTEGER,
                                       sensorProbeThermostatTemperatureArrayPort4LowLimitAction1
                                          INTEGER,
                                       sensorProbeThermostatTemperatureArrayPort4NormalAction2
                                          INTEGER,
                                       sensorProbeThermostatTemperatureArrayPort4HighLimit2
                                          INTEGER,
                                       sensorProbeThermostatTemperatureArrayPort4HighLimitAction2
                                          INTEGER,
                                       sensorProbeThermostatTemperatureArrayPort4LowLimit2
                                          INTEGER,
                                       sensorProbeThermostatTemperatureArrayPort4LowLimitAction2
                                          INTEGER,
                                       sensorProbeThermostatTemperatureArrayPort4EnableTime
                                          DisplayString
                                    }

                                    sensorProbeTemperatureArrayPort4Index OBJECT-TYPE
                                       SYNTAX  INTEGER (0..7)
                                       ACCESS  read-only
                                       STATUS  mandatory
                                       DESCRIPTION
                                       "A unique value for each sensor TemperatureArray port."
                                       ::=  {  sensorProbeTemperatureArrayPort4Entry 1   }

                                    sensorProbeTemperatureArrayPort4Description OBJECT-TYPE
                                       SYNTAX  DisplayString
                                       ACCESS  read-write
                                       STATUS  mandatory
                                       DESCRIPTION
                                       "A Description of this sensor TemperatureArray"
                                       ::=  {  sensorProbeTemperatureArrayPort4Entry 2   }

                                    sensorProbeTemperatureArrayPort4Value OBJECT-TYPE
                                       SYNTAX  INTEGER
                                       ACCESS  read-only
                                       STATUS  mandatory
                                       DESCRIPTION
                                       "The value in this sensor"
                                       ::=  {  sensorProbeTemperatureArrayPort4Entry 3   }

                                    sensorProbeTemperatureArrayPort4Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort4Entry 4   }

                                    sensorProbeTemperatureArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort4Entry 5   }

                                    sensorProbeTemperatureArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort4Entry 6   }

                                    sensorProbeTemperatureArrayPort4HighWarning OBJECT-TYPE
                                       SYNTAX  INTEGER
                                       ACCESS  read-write
                                       STATUS  mandatory
                                       DESCRIPTION
                                       "How hot this  sensor gets before it sends a warning"
                                       ::=  {  sensorProbeTemperatureArrayPort4Entry 7   }

                                    sensorProbeTemperatureArrayPort4HighCritical OBJECT-TYPE
                                       SYNTAX  INTEGER
                                       ACCESS  read-write
                                       STATUS  mandatory
                                       DESCRIPTION
                                       "How hot this sensor gets before it sends a critical event"
                                       ::=  {  sensorProbeTemperatureArrayPort4Entry 8   }

                                    sensorProbeTemperatureArrayPort4LowWarning OBJECT-TYPE
                                       SYNTAX  INTEGER
                                       ACCESS  read-write
                                       STATUS  mandatory
                                       DESCRIPTION
                                       "How cold this sensor gets before it sends a warning"
                                       ::=  {  sensorProbeTemperatureArrayPort4Entry 9   }

                                    sensorProbeTemperatureArrayPort4LowCritical OBJECT-TYPE
                                       SYNTAX  INTEGER
                                       ACCESS  read-write
                                       STATUS  mandatory
                                       DESCRIPTION
                                       "How cold this sensor gets before it sends a critical event"
                                       ::=  {  sensorProbeTemperatureArrayPort4Entry 10   }

                                    sensorProbeTemperatureArrayPort4Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort4Entry 11   }

                                    sensorProbeTemperatureArrayPort4DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort4Entry 12   }

                                    sensorProbeTemperatureArrayPort4DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort4Entry 14   }

                                    sensorProbeTemperatureArrayPort4Offset OBJECT-TYPE
                                       SYNTAX  INTEGER
                                       ACCESS  read-write
                                       STATUS  mandatory
                                       DESCRIPTION
                                       "Offset reading"
                                       ::=  {  sensorProbeTemperatureArrayPort4Entry 15   }

                                    sensorProbeTemperatureArrayPort4URL OBJECT-TYPE
                                       SYNTAX  DisplayString
                                       ACCESS  read-write
                                       STATUS  mandatory
                                       DESCRIPTION
                                       "Sensor URL link."
                                       ::=  {  sensorProbeTemperatureArrayPort4Entry 16   }

                                    sensorProbeTemperatureArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort4Entry 17   }

                                    sensorProbeTemperatureArrayPort4DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort4Entry 18   }

                                    sensorProbeTemperatureArrayPort4ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort4Entry 19 }

                                    sensorProbeTemperatureArrayPort4ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort4Entry 20 }

                                    sensorProbeTemperatureArrayPort4ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort4Entry 21 }

                                    sensorProbeTemperatureArrayPort4ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort4Entry 22 }

                                    sensorProbeTemperatureArrayPort4ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort4Entry 23 }

                                    sensorProbeTemperatureArrayPort4ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort4Entry 24 }

                                    sensorProbeTemperatureArrayPort4Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort4Entry 25 }

                                    sensorProbeThermostatTemperatureArrayPort4Index OBJECT-TYPE
                                       SYNTAX  INTEGER
                                       ACCESS  read-only
                                       STATUS  mandatory
                                       DESCRIPTION
                                       "A unique value for each sensor thermostat port."
                                       ::= {  sensorProbeTemperatureArrayPort4Entry 26 }

                                    sensorProbeThermostatTemperatureArrayPort4Description OBJECT-TYPE
                                       SYNTAX  DisplayString
                                       ACCESS  read-write
                                       STATUS  mandatory
                                       DESCRIPTION
                                       "A Description of this sensor thermostat"
                                       ::= {  sensorProbeTemperatureArrayPort4Entry 27 }

                                    sensorProbeThermostatTemperatureArrayPort4Value OBJECT-TYPE
                                       SYNTAX  INTEGER
                                       ACCESS  read-only
                                       STATUS  mandatory
                                       DESCRIPTION
                                       "The value in this sensor"
                                       ::= {  sensorProbeTemperatureArrayPort4Entry 28 }

                                    sensorProbeThermostatTemperatureArrayPort4Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort4Entry 29 }

                                    sensorProbeThermostatTemperatureArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort4Entry 30 }

                                    sensorProbeThermostatTemperatureArrayPort4Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort4Entry 31 }

                                    sensorProbeThermostatTemperatureArrayPort4RelayControlPort OBJECT-TYPE
                                       SYNTAX INTEGER
                                       ACCESS read-write
                                       STATUS mandatory
                                       DESCRIPTION
                                       "To select a relay port to be controled by this thermostat sensor."
                                       ::= {  sensorProbeTemperatureArrayPort4Entry 32 }

                                    sensorProbeThermostatTemperatureArrayPort4NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort4Entry 33 }

                                    sensorProbeThermostatTemperatureArrayPort4HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort4Entry 34 }

                                    sensorProbeThermostatTemperatureArrayPort4HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort4Entry 35 }

                                    sensorProbeThermostatTemperatureArrayPort4LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort4Entry 36 }

                                    sensorProbeThermostatTemperatureArrayPort4LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort4Entry 37 }

                                    sensorProbeThermostatTemperatureArrayPort4NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort4Entry 38 }

                                    sensorProbeThermostatTemperatureArrayPort4HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort4Entry 39 }

                                    sensorProbeThermostatTemperatureArrayPort4HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort4Entry 40 }

                                    sensorProbeThermostatTemperatureArrayPort4LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort4Entry 41 }

                                    sensorProbeThermostatTemperatureArrayPort4LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort4Entry 42 }

                                    sensorProbeThermostatTemperatureArrayPort4EnableTime OBJECT-TYPE
                                       SYNTAX  DisplayString
                                       ACCESS  read-write
                                       STATUS  mandatory
                                       DESCRIPTION
                                       "Time to enable on Thermostat"
                                       ::=  {  sensorProbeTemperatureArrayPort4Entry 43 }

                           sensorProbeTemperatureArrayPort5 OBJECT IDENTIFIER ::= { sensorProbeTemperatureArraySensor 5  }
                              sensorProbeTemperatureArrayPort5Number OBJECT-TYPE
                                 SYNTAX INTEGER
                                 ACCESS read-only
                                 STATUS mandatory
                                 DESCRIPTION
                                 "The total number of port on the TemperatureArray."
                                 ::=  {  sensorProbeTemperatureArrayPort5 1   }

                              sensorProbeTemperatureArrayPort5Table OBJECT-TYPE
                                 SYNTAX  SEQUENCE OF SensorProbeTemperatureArrayPort5Entry
                                 ACCESS  not-accessible
                                 STATUS  mandatory
                                 DESCRIPTION
                                 "This table contains the data for every Switch Sensor in the SensorArray. Each row in the table contains data for a different Switch Sensor."
                                 ::=  {  sensorProbeTemperatureArrayPort5 2   }

                                 sensorProbeTemperatureArrayPort5Entry OBJECT-TYPE
                                    SYNTAX  SensorProbeTemperatureArrayPort5Entry
                                    ACCESS  not-accessible
                                    STATUS  mandatory
                                    DESCRIPTION
                                    "This is an entry in the sensorProbeTemperatureArrayPort5 Table"
                                    INDEX         { sensorProbeTemperatureArrayPort5Index }
                                    ::=  { sensorProbeTemperatureArrayPort5Table 1 }

                                    SensorProbeTemperatureArrayPort5Entry ::= SEQUENCE {
                                       sensorProbeTemperatureArrayPort5Index
                                          INTEGER,
                                       sensorProbeTemperatureArrayPort5Description
                                          DisplayString,
                                       sensorProbeTemperatureArrayPort5Value
                                          INTEGER,
                                       sensorProbeTemperatureArrayPort5Status
                                          INTEGER,
                                       sensorProbeTemperatureArrayPort5Online
                                          INTEGER,
                                       sensorProbeTemperatureArrayPort5GoOnline
                                          INTEGER,
                                       sensorProbeTemperatureArrayPort5HighWarning
                                          INTEGER,
                                       sensorProbeTemperatureArrayPort5HighCritical
                                          INTEGER,
                                       sensorProbeTemperatureArrayPort5LowWarning
                                          INTEGER,
                                       sensorProbeTemperatureArrayPort5LowCritical
                                          INTEGER,
                                       sensorProbeTemperatureArrayPort5Rearm
                                          INTEGER,
                                       sensorProbeTemperatureArrayPort5DegreeType
                                          INTEGER,
                                       sensorProbeTemperatureArrayPort5DegreeRaw
                                          INTEGER,
                                       sensorProbeTemperatureArrayPort5Offset
                                          INTEGER,
                                       sensorProbeTemperatureArrayPort5URL
                                          DisplayString,
                                       sensorProbeTemperatureArrayPort5OpenURL
                                          INTEGER,
                                       sensorProbeTemperatureArrayPort5DatacollectType
                                          INTEGER,
                                       sensorProbeTemperatureArrayPort5ContTimeHighCritical
                                          INTEGER,
                                       sensorProbeTemperatureArrayPort5ContTimeHighWarning
                                          INTEGER,
                                       sensorProbeTemperatureArrayPort5ContTimeNormal
                                          INTEGER,
                                       sensorProbeTemperatureArrayPort5ContTimeLowWarning
                                          INTEGER,
                                       sensorProbeTemperatureArrayPort5ContTimeLowCritical
                                          INTEGER,
                                       sensorProbeTemperatureArrayPort5ContTimeSensorError
                                          INTEGER,
                                       sensorProbeTemperatureArrayPort5Calendar
                                          INTEGER,
                                       sensorProbeThermostatTemperatureArrayPort5Index
                                          INTEGER,
                                       sensorProbeThermostatTemperatureArrayPort5Description
                                          DisplayString,
                                       sensorProbeThermostatTemperatureArrayPort5Value
                                          INTEGER,
                                       sensorProbeThermostatTemperatureArrayPort5Online
                                          INTEGER,
                                       sensorProbeThermostatTemperatureArrayPort5GoOnline
                                          INTEGER,
                                       sensorProbeThermostatTemperatureArrayPort5Mode
                                          INTEGER,
                                       sensorProbeThermostatTemperatureArrayPort5RelayControlPort
                                          INTEGER,
                                       sensorProbeThermostatTemperatureArrayPort5NormalAction1
                                          INTEGER,
                                       sensorProbeThermostatTemperatureArrayPort5HighLimit1
                                          INTEGER,
                                       sensorProbeThermostatTemperatureArrayPort5HighLimitAction1
                                          INTEGER,
                                       sensorProbeThermostatTemperatureArrayPort5LowLimit1
                                          INTEGER,
                                       sensorProbeThermostatTemperatureArrayPort5LowLimitAction1
                                          INTEGER,
                                       sensorProbeThermostatTemperatureArrayPort5NormalAction2
                                          INTEGER,
                                       sensorProbeThermostatTemperatureArrayPort5HighLimit2
                                          INTEGER,
                                       sensorProbeThermostatTemperatureArrayPort5HighLimitAction2
                                          INTEGER,
                                       sensorProbeThermostatTemperatureArrayPort5LowLimit2
                                          INTEGER,
                                       sensorProbeThermostatTemperatureArrayPort5LowLimitAction2
                                          INTEGER,
                                       sensorProbeThermostatTemperatureArrayPort5EnableTime
                                          DisplayString
                                    }

                                    sensorProbeTemperatureArrayPort5Index OBJECT-TYPE
                                       SYNTAX  INTEGER (0..7)
                                       ACCESS  read-only
                                       STATUS  mandatory
                                       DESCRIPTION
                                       "A unique value for each sensor TemperatureArray port."
                                       ::=  {  sensorProbeTemperatureArrayPort5Entry 1   }

                                    sensorProbeTemperatureArrayPort5Description OBJECT-TYPE
                                       SYNTAX  DisplayString
                                       ACCESS  read-write
                                       STATUS  mandatory
                                       DESCRIPTION
                                       "A Description of this sensor TemperatureArray"
                                       ::=  {  sensorProbeTemperatureArrayPort5Entry 2   }

                                    sensorProbeTemperatureArrayPort5Value OBJECT-TYPE
                                       SYNTAX  INTEGER
                                       ACCESS  read-only
                                       STATUS  mandatory
                                       DESCRIPTION
                                       "The value in this sensor"
                                       ::=  {  sensorProbeTemperatureArrayPort5Entry 3   }

                                    sensorProbeTemperatureArrayPort5Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort5Entry 4   }

                                    sensorProbeTemperatureArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort5Entry 5   }

                                    sensorProbeTemperatureArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort5Entry 6   }

                                    sensorProbeTemperatureArrayPort5HighWarning OBJECT-TYPE
                                       SYNTAX  INTEGER
                                       ACCESS  read-write
                                       STATUS  mandatory
                                       DESCRIPTION
                                       "How hot this  sensor gets before it sends a warning"
                                       ::=  {  sensorProbeTemperatureArrayPort5Entry 7   }

                                    sensorProbeTemperatureArrayPort5HighCritical OBJECT-TYPE
                                       SYNTAX  INTEGER
                                       ACCESS  read-write
                                       STATUS  mandatory
                                       DESCRIPTION
                                       "How hot this sensor gets before it sends a critical event"
                                       ::=  {  sensorProbeTemperatureArrayPort5Entry 8   }

                                    sensorProbeTemperatureArrayPort5LowWarning OBJECT-TYPE
                                       SYNTAX  INTEGER
                                       ACCESS  read-write
                                       STATUS  mandatory
                                       DESCRIPTION
                                       "How cold this sensor gets before it sends a warning"
                                       ::=  {  sensorProbeTemperatureArrayPort5Entry 9   }

                                    sensorProbeTemperatureArrayPort5LowCritical OBJECT-TYPE
                                       SYNTAX  INTEGER
                                       ACCESS  read-write
                                       STATUS  mandatory
                                       DESCRIPTION
                                       "How cold this sensor gets before it sends a critical event"
                                       ::=  {  sensorProbeTemperatureArrayPort5Entry 10   }

                                    sensorProbeTemperatureArrayPort5Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort5Entry 11   }

                                    sensorProbeTemperatureArrayPort5DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort5Entry 12   }

                                    sensorProbeTemperatureArrayPort5DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort5Entry 14   }

                                    sensorProbeTemperatureArrayPort5Offset OBJECT-TYPE
                                       SYNTAX  INTEGER
                                       ACCESS  read-write
                                       STATUS  mandatory
                                       DESCRIPTION
                                       "Offset reading"
                                       ::=  {  sensorProbeTemperatureArrayPort5Entry 15   }

                                    sensorProbeTemperatureArrayPort5URL OBJECT-TYPE
                                       SYNTAX  DisplayString
                                       ACCESS  read-write
                                       STATUS  mandatory
                                       DESCRIPTION
                                       "Sensor URL link."
                                       ::=  {  sensorProbeTemperatureArrayPort5Entry 16   }

                                    sensorProbeTemperatureArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort5Entry 17   }

                                    sensorProbeTemperatureArrayPort5DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort5Entry 18   }

                                    sensorProbeTemperatureArrayPort5ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort5Entry 19 }

                                    sensorProbeTemperatureArrayPort5ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort5Entry 20 }

                                    sensorProbeTemperatureArrayPort5ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort5Entry 21 }

                                    sensorProbeTemperatureArrayPort5ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort5Entry 22 }

                                    sensorProbeTemperatureArrayPort5ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort5Entry 23 }

                                    sensorProbeTemperatureArrayPort5ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort5Entry 24 }

                                    sensorProbeTemperatureArrayPort5Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort5Entry 25 }

                                    sensorProbeThermostatTemperatureArrayPort5Index OBJECT-TYPE
                                       SYNTAX  INTEGER
                                       ACCESS  read-only
                                       STATUS  mandatory
                                       DESCRIPTION
                                       "A unique value for each sensor thermostat port."
                                       ::= {  sensorProbeTemperatureArrayPort5Entry 26 }

                                    sensorProbeThermostatTemperatureArrayPort5Description OBJECT-TYPE
                                       SYNTAX  DisplayString
                                       ACCESS  read-write
                                       STATUS  mandatory
                                       DESCRIPTION
                                       "A Description of this sensor thermostat"
                                       ::= {  sensorProbeTemperatureArrayPort5Entry 27 }

                                    sensorProbeThermostatTemperatureArrayPort5Value OBJECT-TYPE
                                       SYNTAX  INTEGER
                                       ACCESS  read-only
                                       STATUS  mandatory
                                       DESCRIPTION
                                       "The value in this sensor"
                                       ::= {  sensorProbeTemperatureArrayPort5Entry 28 }

                                    sensorProbeThermostatTemperatureArrayPort5Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort5Entry 29 }

                                    sensorProbeThermostatTemperatureArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort5Entry 30 }

                                    sensorProbeThermostatTemperatureArrayPort5Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort5Entry 31 }

                                    sensorProbeThermostatTemperatureArrayPort5RelayControlPort OBJECT-TYPE
                                       SYNTAX INTEGER
                                       ACCESS read-write
                                       STATUS mandatory
                                       DESCRIPTION
                                       "To select a relay port to be controled by this thermostat sensor."
                                       ::= {  sensorProbeTemperatureArrayPort5Entry 32 }

                                    sensorProbeThermostatTemperatureArrayPort5NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort5Entry 33 }

                                    sensorProbeThermostatTemperatureArrayPort5HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort5Entry 34 }

                                    sensorProbeThermostatTemperatureArrayPort5HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort5Entry 35 }

                                    sensorProbeThermostatTemperatureArrayPort5LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort5Entry 36 }

                                    sensorProbeThermostatTemperatureArrayPort5LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort5Entry 37 }

                                    sensorProbeThermostatTemperatureArrayPort5NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort5Entry 38 }

                                    sensorProbeThermostatTemperatureArrayPort5HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort5Entry 39 }

                                    sensorProbeThermostatTemperatureArrayPort5HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort5Entry 40 }

                                    sensorProbeThermostatTemperatureArrayPort5LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort5Entry 41 }

                                    sensorProbeThermostatTemperatureArrayPort5LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort5Entry 42 }

                                    sensorProbeThermostatTemperatureArrayPort5EnableTime OBJECT-TYPE
                                       SYNTAX  DisplayString
                                       ACCESS  read-write
                                       STATUS  mandatory
                                       DESCRIPTION
                                       "Time to enable on Thermostat"
                                       ::=  {  sensorProbeTemperatureArrayPort5Entry 43 }

                           sensorProbeTemperatureArrayPort6 OBJECT IDENTIFIER ::= { sensorProbeTemperatureArraySensor 6  }
                              sensorProbeTemperatureArrayPort6Number OBJECT-TYPE
                                 SYNTAX INTEGER
                                 ACCESS read-only
                                 STATUS mandatory
                                 DESCRIPTION
                                 "The total number of port on the TemperatureArray."
                                 ::=  {  sensorProbeTemperatureArrayPort6 1   }

                              sensorProbeTemperatureArrayPort6Table OBJECT-TYPE
                                 SYNTAX  SEQUENCE OF SensorProbeTemperatureArrayPort6Entry
                                 ACCESS  not-accessible
                                 STATUS  mandatory
                                 DESCRIPTION
                                 "This table contains the data for every Switch Sensor in the SensorArray. Each row in the table contains data for a different Switch Sensor."
                                 ::=  {  sensorProbeTemperatureArrayPort6 2   }

                                 sensorProbeTemperatureArrayPort6Entry OBJECT-TYPE
                                    SYNTAX  SensorProbeTemperatureArrayPort6Entry
                                    ACCESS  not-accessible
                                    STATUS  mandatory
                                    DESCRIPTION
                                    "This is an entry in the sensorProbeTemperatureArrayPort6 Table"
                                    INDEX         { sensorProbeTemperatureArrayPort6Index }
                                    ::=  { sensorProbeTemperatureArrayPort6Table 1 }

                                    SensorProbeTemperatureArrayPort6Entry ::= SEQUENCE {
                                       sensorProbeTemperatureArrayPort6Index
                                          INTEGER,
                                       sensorProbeTemperatureArrayPort6Description
                                          DisplayString,
                                       sensorProbeTemperatureArrayPort6Value
                                          INTEGER,
                                       sensorProbeTemperatureArrayPort6Status
                                          INTEGER,
                                       sensorProbeTemperatureArrayPort6Online
                                          INTEGER,
                                       sensorProbeTemperatureArrayPort6GoOnline
                                          INTEGER,
                                       sensorProbeTemperatureArrayPort6HighWarning
                                          INTEGER,
                                       sensorProbeTemperatureArrayPort6HighCritical
                                          INTEGER,
                                       sensorProbeTemperatureArrayPort6LowWarning
                                          INTEGER,
                                       sensorProbeTemperatureArrayPort6LowCritical
                                          INTEGER,
                                       sensorProbeTemperatureArrayPort6Rearm
                                          INTEGER,
                                       sensorProbeTemperatureArrayPort6DegreeType
                                          INTEGER,
                                       sensorProbeTemperatureArrayPort6DegreeRaw
                                          INTEGER,
                                       sensorProbeTemperatureArrayPort6Offset
                                          INTEGER,
                                       sensorProbeTemperatureArrayPort6URL
                                          DisplayString,
                                       sensorProbeTemperatureArrayPort6OpenURL
                                          INTEGER,
                                       sensorProbeTemperatureArrayPort6DatacollectType
                                          INTEGER,
                                       sensorProbeTemperatureArrayPort6ContTimeHighCritical
                                          INTEGER,
                                       sensorProbeTemperatureArrayPort6ContTimeHighWarning
                                          INTEGER,
                                       sensorProbeTemperatureArrayPort6ContTimeNormal
                                          INTEGER,
                                       sensorProbeTemperatureArrayPort6ContTimeLowWarning
                                          INTEGER,
                                       sensorProbeTemperatureArrayPort6ContTimeLowCritical
                                          INTEGER,
                                       sensorProbeTemperatureArrayPort6ContTimeSensorError
                                          INTEGER,
                                       sensorProbeTemperatureArrayPort6Calendar
                                          INTEGER,
                                       sensorProbeThermostatTemperatureArrayPort6Index
                                          INTEGER,
                                       sensorProbeThermostatTemperatureArrayPort6Description
                                          DisplayString,
                                       sensorProbeThermostatTemperatureArrayPort6Value
                                          INTEGER,
                                       sensorProbeThermostatTemperatureArrayPort6Online
                                          INTEGER,
                                       sensorProbeThermostatTemperatureArrayPort6GoOnline
                                          INTEGER,
                                       sensorProbeThermostatTemperatureArrayPort6Mode
                                          INTEGER,
                                       sensorProbeThermostatTemperatureArrayPort6RelayControlPort
                                          INTEGER,
                                       sensorProbeThermostatTemperatureArrayPort6NormalAction1
                                          INTEGER,
                                       sensorProbeThermostatTemperatureArrayPort6HighLimit1
                                          INTEGER,
                                       sensorProbeThermostatTemperatureArrayPort6HighLimitAction1
                                          INTEGER,
                                       sensorProbeThermostatTemperatureArrayPort6LowLimit1
                                          INTEGER,
                                       sensorProbeThermostatTemperatureArrayPort6LowLimitAction1
                                          INTEGER,
                                       sensorProbeThermostatTemperatureArrayPort6NormalAction2
                                          INTEGER,
                                       sensorProbeThermostatTemperatureArrayPort6HighLimit2
                                          INTEGER,
                                       sensorProbeThermostatTemperatureArrayPort6HighLimitAction2
                                          INTEGER,
                                       sensorProbeThermostatTemperatureArrayPort6LowLimit2
                                          INTEGER,
                                       sensorProbeThermostatTemperatureArrayPort6LowLimitAction2
                                          INTEGER,
                                       sensorProbeThermostatTemperatureArrayPort6EnableTime
                                          DisplayString
                                    }

                                    sensorProbeTemperatureArrayPort6Index OBJECT-TYPE
                                       SYNTAX  INTEGER (0..7)
                                       ACCESS  read-only
                                       STATUS  mandatory
                                       DESCRIPTION
                                       "A unique value for each sensor TemperatureArray port."
                                       ::=  {  sensorProbeTemperatureArrayPort6Entry 1   }

                                    sensorProbeTemperatureArrayPort6Description OBJECT-TYPE
                                       SYNTAX  DisplayString
                                       ACCESS  read-write
                                       STATUS  mandatory
                                       DESCRIPTION
                                       "A Description of this sensor TemperatureArray"
                                       ::=  {  sensorProbeTemperatureArrayPort6Entry 2   }

                                    sensorProbeTemperatureArrayPort6Value OBJECT-TYPE
                                       SYNTAX  INTEGER
                                       ACCESS  read-only
                                       STATUS  mandatory
                                       DESCRIPTION
                                       "The value in this sensor"
                                       ::=  {  sensorProbeTemperatureArrayPort6Entry 3   }

                                    sensorProbeTemperatureArrayPort6Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort6Entry 4   }

                                    sensorProbeTemperatureArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort6Entry 5   }

                                    sensorProbeTemperatureArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort6Entry 6   }

                                    sensorProbeTemperatureArrayPort6HighWarning OBJECT-TYPE
                                       SYNTAX  INTEGER
                                       ACCESS  read-write
                                       STATUS  mandatory
                                       DESCRIPTION
                                       "How hot this  sensor gets before it sends a warning"
                                       ::=  {  sensorProbeTemperatureArrayPort6Entry 7   }

                                    sensorProbeTemperatureArrayPort6HighCritical OBJECT-TYPE
                                       SYNTAX  INTEGER
                                       ACCESS  read-write
                                       STATUS  mandatory
                                       DESCRIPTION
                                       "How hot this sensor gets before it sends a critical event"
                                       ::=  {  sensorProbeTemperatureArrayPort6Entry 8   }

                                    sensorProbeTemperatureArrayPort6LowWarning OBJECT-TYPE
                                       SYNTAX  INTEGER
                                       ACCESS  read-write
                                       STATUS  mandatory
                                       DESCRIPTION
                                       "How cold this sensor gets before it sends a warning"
                                       ::=  {  sensorProbeTemperatureArrayPort6Entry 9   }

                                    sensorProbeTemperatureArrayPort6LowCritical OBJECT-TYPE
                                       SYNTAX  INTEGER
                                       ACCESS  read-write
                                       STATUS  mandatory
                                       DESCRIPTION
                                       "How cold this sensor gets before it sends a critical event"
                                       ::=  {  sensorProbeTemperatureArrayPort6Entry 10   }

                                    sensorProbeTemperatureArrayPort6Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort6Entry 11   }

                                    sensorProbeTemperatureArrayPort6DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort6Entry 12   }

                                    sensorProbeTemperatureArrayPort6DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort6Entry 14   }

                                    sensorProbeTemperatureArrayPort6Offset OBJECT-TYPE
                                       SYNTAX  INTEGER
                                       ACCESS  read-write
                                       STATUS  mandatory
                                       DESCRIPTION
                                       "Offset reading"
                                       ::=  {  sensorProbeTemperatureArrayPort6Entry 15   }

                                    sensorProbeTemperatureArrayPort6URL OBJECT-TYPE
                                       SYNTAX  DisplayString
                                       ACCESS  read-write
                                       STATUS  mandatory
                                       DESCRIPTION
                                       "Sensor URL link."
                                       ::=  {  sensorProbeTemperatureArrayPort6Entry 16   }

                                    sensorProbeTemperatureArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort6Entry 17   }

                                    sensorProbeTemperatureArrayPort6DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort6Entry 18   }

                                    sensorProbeTemperatureArrayPort6ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort6Entry 19 }

                                    sensorProbeTemperatureArrayPort6ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort6Entry 20 }

                                    sensorProbeTemperatureArrayPort6ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort6Entry 21 }

                                    sensorProbeTemperatureArrayPort6ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort6Entry 22 }

                                    sensorProbeTemperatureArrayPort6ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort6Entry 23 }

                                    sensorProbeTemperatureArrayPort6ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort6Entry 24 }

                                    sensorProbeTemperatureArrayPort6Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort6Entry 25 }

                                    sensorProbeThermostatTemperatureArrayPort6Index OBJECT-TYPE
                                       SYNTAX  INTEGER
                                       ACCESS  read-only
                                       STATUS  mandatory
                                       DESCRIPTION
                                       "A unique value for each sensor thermostat port."
                                       ::= {  sensorProbeTemperatureArrayPort6Entry 26 }

                                    sensorProbeThermostatTemperatureArrayPort6Description OBJECT-TYPE
                                       SYNTAX  DisplayString
                                       ACCESS  read-write
                                       STATUS  mandatory
                                       DESCRIPTION
                                       "A Description of this sensor thermostat"
                                       ::= {  sensorProbeTemperatureArrayPort6Entry 27 }

                                    sensorProbeThermostatTemperatureArrayPort6Value OBJECT-TYPE
                                       SYNTAX  INTEGER
                                       ACCESS  read-only
                                       STATUS  mandatory
                                       DESCRIPTION
                                       "The value in this sensor"
                                       ::= {  sensorProbeTemperatureArrayPort6Entry 28 }

                                    sensorProbeThermostatTemperatureArrayPort6Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort6Entry 29 }

                                    sensorProbeThermostatTemperatureArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort6Entry 30 }

                                    sensorProbeThermostatTemperatureArrayPort6Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort6Entry 31 }

                                    sensorProbeThermostatTemperatureArrayPort6RelayControlPort OBJECT-TYPE
                                       SYNTAX INTEGER
                                       ACCESS read-write
                                       STATUS mandatory
                                       DESCRIPTION
                                       "To select a relay port to be controled by this thermostat sensor."
                                       ::= {  sensorProbeTemperatureArrayPort6Entry 32 }

                                    sensorProbeThermostatTemperatureArrayPort6NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort6Entry 33 }

                                    sensorProbeThermostatTemperatureArrayPort6HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort6Entry 34 }

                                    sensorProbeThermostatTemperatureArrayPort6HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort6Entry 35 }

                                    sensorProbeThermostatTemperatureArrayPort6LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort6Entry 36 }

                                    sensorProbeThermostatTemperatureArrayPort6LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort6Entry 37 }

                                    sensorProbeThermostatTemperatureArrayPort6NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort6Entry 38 }

                                    sensorProbeThermostatTemperatureArrayPort6HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort6Entry 39 }

                                    sensorProbeThermostatTemperatureArrayPort6HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort6Entry 40 }

                                    sensorProbeThermostatTemperatureArrayPort6LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort6Entry 41 }

                                    sensorProbeThermostatTemperatureArrayPort6LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort6Entry 42 }

                                    sensorProbeThermostatTemperatureArrayPort6EnableTime OBJECT-TYPE
                                       SYNTAX  DisplayString
                                       ACCESS  read-write
                                       STATUS  mandatory
                                       DESCRIPTION
                                       "Time to enable on Thermostat"
                                       ::=  {  sensorProbeTemperatureArrayPort6Entry 43 }

                           sensorProbeTemperatureArrayPort7 OBJECT IDENTIFIER ::= { sensorProbeTemperatureArraySensor 7  }
                              sensorProbeTemperatureArrayPort7Number OBJECT-TYPE
                                 SYNTAX INTEGER
                                 ACCESS read-only
                                 STATUS mandatory
                                 DESCRIPTION
                                 "The total number of port on the TemperatureArray."
                                 ::=  {  sensorProbeTemperatureArrayPort7 1   }

                              sensorProbeTemperatureArrayPort7Table OBJECT-TYPE
                                 SYNTAX  SEQUENCE OF SensorProbeTemperatureArrayPort7Entry
                                 ACCESS  not-accessible
                                 STATUS  mandatory
                                 DESCRIPTION
                                 "This table contains the data for every Switch Sensor in the SensorArray. Each row in the table contains data for a different Switch Sensor."
                                 ::=  {  sensorProbeTemperatureArrayPort7 2   }

                                 sensorProbeTemperatureArrayPort7Entry OBJECT-TYPE
                                    SYNTAX  SensorProbeTemperatureArrayPort7Entry
                                    ACCESS  not-accessible
                                    STATUS  mandatory
                                    DESCRIPTION
                                    "This is an entry in the sensorProbeTemperatureArrayPort7 Table"
                                    INDEX         { sensorProbeTemperatureArrayPort7Index }
                                    ::=  { sensorProbeTemperatureArrayPort7Table 1 }

                                    SensorProbeTemperatureArrayPort7Entry ::= SEQUENCE {
                                       sensorProbeTemperatureArrayPort7Index
                                          INTEGER,
                                       sensorProbeTemperatureArrayPort7Description
                                          DisplayString,
                                       sensorProbeTemperatureArrayPort7Value
                                          INTEGER,
                                       sensorProbeTemperatureArrayPort7Status
                                          INTEGER,
                                       sensorProbeTemperatureArrayPort7Online
                                          INTEGER,
                                       sensorProbeTemperatureArrayPort7GoOnline
                                          INTEGER,
                                       sensorProbeTemperatureArrayPort7HighWarning
                                          INTEGER,
                                       sensorProbeTemperatureArrayPort7HighCritical
                                          INTEGER,
                                       sensorProbeTemperatureArrayPort7LowWarning
                                          INTEGER,
                                       sensorProbeTemperatureArrayPort7LowCritical
                                          INTEGER,
                                       sensorProbeTemperatureArrayPort7Rearm
                                          INTEGER,
                                       sensorProbeTemperatureArrayPort7DegreeType
                                          INTEGER,
                                       sensorProbeTemperatureArrayPort7DegreeRaw
                                          INTEGER,
                                       sensorProbeTemperatureArrayPort7Offset
                                          INTEGER,
                                       sensorProbeTemperatureArrayPort7URL
                                          DisplayString,
                                       sensorProbeTemperatureArrayPort7OpenURL
                                          INTEGER,
                                       sensorProbeTemperatureArrayPort7DatacollectType
                                          INTEGER,
                                       sensorProbeTemperatureArrayPort7ContTimeHighCritical
                                          INTEGER,
                                       sensorProbeTemperatureArrayPort7ContTimeHighWarning
                                          INTEGER,
                                       sensorProbeTemperatureArrayPort7ContTimeNormal
                                          INTEGER,
                                       sensorProbeTemperatureArrayPort7ContTimeLowWarning
                                          INTEGER,
                                       sensorProbeTemperatureArrayPort7ContTimeLowCritical
                                          INTEGER,
                                       sensorProbeTemperatureArrayPort7ContTimeSensorError
                                          INTEGER,
                                       sensorProbeTemperatureArrayPort7Calendar
                                          INTEGER,
                                       sensorProbeThermostatTemperatureArrayPort7Index
                                          INTEGER,
                                       sensorProbeThermostatTemperatureArrayPort7Description
                                          DisplayString,
                                       sensorProbeThermostatTemperatureArrayPort7Value
                                          INTEGER,
                                       sensorProbeThermostatTemperatureArrayPort7Online
                                          INTEGER,
                                       sensorProbeThermostatTemperatureArrayPort7GoOnline
                                          INTEGER,
                                       sensorProbeThermostatTemperatureArrayPort7Mode
                                          INTEGER,
                                       sensorProbeThermostatTemperatureArrayPort7RelayControlPort
                                          INTEGER,
                                       sensorProbeThermostatTemperatureArrayPort7NormalAction1
                                          INTEGER,
                                       sensorProbeThermostatTemperatureArrayPort7HighLimit1
                                          INTEGER,
                                       sensorProbeThermostatTemperatureArrayPort7HighLimitAction1
                                          INTEGER,
                                       sensorProbeThermostatTemperatureArrayPort7LowLimit1
                                          INTEGER,
                                       sensorProbeThermostatTemperatureArrayPort7LowLimitAction1
                                          INTEGER,
                                       sensorProbeThermostatTemperatureArrayPort7NormalAction2
                                          INTEGER,
                                       sensorProbeThermostatTemperatureArrayPort7HighLimit2
                                          INTEGER,
                                       sensorProbeThermostatTemperatureArrayPort7HighLimitAction2
                                          INTEGER,
                                       sensorProbeThermostatTemperatureArrayPort7LowLimit2
                                          INTEGER,
                                       sensorProbeThermostatTemperatureArrayPort7LowLimitAction2
                                          INTEGER,
                                       sensorProbeThermostatTemperatureArrayPort7EnableTime
                                          DisplayString
                                    }

                                    sensorProbeTemperatureArrayPort7Index OBJECT-TYPE
                                       SYNTAX  INTEGER (0..7)
                                       ACCESS  read-only
                                       STATUS  mandatory
                                       DESCRIPTION
                                       "A unique value for each sensor TemperatureArray port."
                                       ::=  {  sensorProbeTemperatureArrayPort7Entry 1   }

                                    sensorProbeTemperatureArrayPort7Description OBJECT-TYPE
                                       SYNTAX  DisplayString
                                       ACCESS  read-write
                                       STATUS  mandatory
                                       DESCRIPTION
                                       "A Description of this sensor TemperatureArray"
                                       ::=  {  sensorProbeTemperatureArrayPort7Entry 2   }

                                    sensorProbeTemperatureArrayPort7Value OBJECT-TYPE
                                       SYNTAX  INTEGER
                                       ACCESS  read-only
                                       STATUS  mandatory
                                       DESCRIPTION
                                       "The value in this sensor"
                                       ::=  {  sensorProbeTemperatureArrayPort7Entry 3   }

                                    sensorProbeTemperatureArrayPort7Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort7Entry 4   }

                                    sensorProbeTemperatureArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort7Entry 5   }

                                    sensorProbeTemperatureArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort7Entry 6   }

                                    sensorProbeTemperatureArrayPort7HighWarning OBJECT-TYPE
                                       SYNTAX  INTEGER
                                       ACCESS  read-write
                                       STATUS  mandatory
                                       DESCRIPTION
                                       "How hot this  sensor gets before it sends a warning"
                                       ::=  {  sensorProbeTemperatureArrayPort7Entry 7   }

                                    sensorProbeTemperatureArrayPort7HighCritical OBJECT-TYPE
                                       SYNTAX  INTEGER
                                       ACCESS  read-write
                                       STATUS  mandatory
                                       DESCRIPTION
                                       "How hot this sensor gets before it sends a critical event"
                                       ::=  {  sensorProbeTemperatureArrayPort7Entry 8   }

                                    sensorProbeTemperatureArrayPort7LowWarning OBJECT-TYPE
                                       SYNTAX  INTEGER
                                       ACCESS  read-write
                                       STATUS  mandatory
                                       DESCRIPTION
                                       "How cold this sensor gets before it sends a warning"
                                       ::=  {  sensorProbeTemperatureArrayPort7Entry 9   }

                                    sensorProbeTemperatureArrayPort7LowCritical OBJECT-TYPE
                                       SYNTAX  INTEGER
                                       ACCESS  read-write
                                       STATUS  mandatory
                                       DESCRIPTION
                                       "How cold this sensor gets before it sends a critical event"
                                       ::=  {  sensorProbeTemperatureArrayPort7Entry 10   }

                                    sensorProbeTemperatureArrayPort7Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort7Entry 11   }

                                    sensorProbeTemperatureArrayPort7DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort7Entry 12   }

                                    sensorProbeTemperatureArrayPort7DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort7Entry 14   }

                                    sensorProbeTemperatureArrayPort7Offset OBJECT-TYPE
                                       SYNTAX  INTEGER
                                       ACCESS  read-write
                                       STATUS  mandatory
                                       DESCRIPTION
                                       "Offset reading"
                                       ::=  {  sensorProbeTemperatureArrayPort7Entry 15   }

                                    sensorProbeTemperatureArrayPort7URL OBJECT-TYPE
                                       SYNTAX  DisplayString
                                       ACCESS  read-write
                                       STATUS  mandatory
                                       DESCRIPTION
                                       "Sensor URL link."
                                       ::=  {  sensorProbeTemperatureArrayPort7Entry 16   }

                                    sensorProbeTemperatureArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort7Entry 17   }

                                    sensorProbeTemperatureArrayPort7DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort7Entry 18   }

                                    sensorProbeTemperatureArrayPort7ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort7Entry 19 }

                                    sensorProbeTemperatureArrayPort7ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort7Entry 20 }

                                    sensorProbeTemperatureArrayPort7ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort7Entry 21 }

                                    sensorProbeTemperatureArrayPort7ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort7Entry 22 }

                                    sensorProbeTemperatureArrayPort7ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort7Entry 23 }

                                    sensorProbeTemperatureArrayPort7ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort7Entry 24 }

                                    sensorProbeTemperatureArrayPort7Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort7Entry 25 }

                                    sensorProbeThermostatTemperatureArrayPort7Index OBJECT-TYPE
                                       SYNTAX  INTEGER
                                       ACCESS  read-only
                                       STATUS  mandatory
                                       DESCRIPTION
                                       "A unique value for each sensor thermostat port."
                                       ::= {  sensorProbeTemperatureArrayPort7Entry 26 }

                                    sensorProbeThermostatTemperatureArrayPort7Description OBJECT-TYPE
                                       SYNTAX  DisplayString
                                       ACCESS  read-write
                                       STATUS  mandatory
                                       DESCRIPTION
                                       "A Description of this sensor thermostat"
                                       ::= {  sensorProbeTemperatureArrayPort7Entry 27 }

                                    sensorProbeThermostatTemperatureArrayPort7Value OBJECT-TYPE
                                       SYNTAX  INTEGER
                                       ACCESS  read-only
                                       STATUS  mandatory
                                       DESCRIPTION
                                       "The value in this sensor"
                                       ::= {  sensorProbeTemperatureArrayPort7Entry 28 }

                                    sensorProbeThermostatTemperatureArrayPort7Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort7Entry 29 }

                                    sensorProbeThermostatTemperatureArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort7Entry 30 }

                                    sensorProbeThermostatTemperatureArrayPort7Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort7Entry 31 }

                                    sensorProbeThermostatTemperatureArrayPort7RelayControlPort OBJECT-TYPE
                                       SYNTAX INTEGER
                                       ACCESS read-write
                                       STATUS mandatory
                                       DESCRIPTION
                                       "To select a relay port to be controled by this thermostat sensor."
                                       ::= {  sensorProbeTemperatureArrayPort7Entry 32 }

                                    sensorProbeThermostatTemperatureArrayPort7NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort7Entry 33 }

                                    sensorProbeThermostatTemperatureArrayPort7HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort7Entry 34 }

                                    sensorProbeThermostatTemperatureArrayPort7HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort7Entry 35 }

                                    sensorProbeThermostatTemperatureArrayPort7LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort7Entry 36 }

                                    sensorProbeThermostatTemperatureArrayPort7LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort7Entry 37 }

                                    sensorProbeThermostatTemperatureArrayPort7NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort7Entry 38 }

                                    sensorProbeThermostatTemperatureArrayPort7HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort7Entry 39 }

                                    sensorProbeThermostatTemperatureArrayPort7HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort7Entry 40 }

                                    sensorProbeThermostatTemperatureArrayPort7LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort7Entry 41 }

                                    sensorProbeThermostatTemperatureArrayPort7LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort7Entry 42 }

                                    sensorProbeThermostatTemperatureArrayPort7EnableTime OBJECT-TYPE
                                       SYNTAX  DisplayString
                                       ACCESS  read-write
                                       STATUS  mandatory
                                       DESCRIPTION
                                       "Time to enable on Thermostat"
                                       ::=  {  sensorProbeTemperatureArrayPort7Entry 43 }

                           sensorProbeTemperatureArrayPort8 OBJECT IDENTIFIER ::= { sensorProbeTemperatureArraySensor 8  }
                              sensorProbeTemperatureArrayPort8Number OBJECT-TYPE
                                 SYNTAX INTEGER
                                 ACCESS read-only
                                 STATUS mandatory
                                 DESCRIPTION
                                 "The total number of port on the TemperatureArray."
                                 ::=  {  sensorProbeTemperatureArrayPort8 1   }

                              sensorProbeTemperatureArrayPort8Table OBJECT-TYPE
                                 SYNTAX  SEQUENCE OF SensorProbeTemperatureArrayPort8Entry
                                 ACCESS  not-accessible
                                 STATUS  mandatory
                                 DESCRIPTION
                                 "This table contains the data for every Switch Sensor in the SensorArray. Each row in the table contains data for a different Switch Sensor."
                                 ::=  {  sensorProbeTemperatureArrayPort8 2   }

                                 sensorProbeTemperatureArrayPort8Entry OBJECT-TYPE
                                    SYNTAX  SensorProbeTemperatureArrayPort8Entry
                                    ACCESS  not-accessible
                                    STATUS  mandatory
                                    DESCRIPTION
                                    "This is an entry in the sensorProbeTemperatureArrayPort8 Table"
                                    INDEX         { sensorProbeTemperatureArrayPort8Index }
                                    ::=  { sensorProbeTemperatureArrayPort8Table 1 }

                                    SensorProbeTemperatureArrayPort8Entry ::= SEQUENCE {
                                       sensorProbeTemperatureArrayPort8Index
                                          INTEGER,
                                       sensorProbeTemperatureArrayPort8Description
                                          DisplayString,
                                       sensorProbeTemperatureArrayPort8Value
                                          INTEGER,
                                       sensorProbeTemperatureArrayPort8Status
                                          INTEGER,
                                       sensorProbeTemperatureArrayPort8Online
                                          INTEGER,
                                       sensorProbeTemperatureArrayPort8GoOnline
                                          INTEGER,
                                       sensorProbeTemperatureArrayPort8HighWarning
                                          INTEGER,
                                       sensorProbeTemperatureArrayPort8HighCritical
                                          INTEGER,
                                       sensorProbeTemperatureArrayPort8LowWarning
                                          INTEGER,
                                       sensorProbeTemperatureArrayPort8LowCritical
                                          INTEGER,
                                       sensorProbeTemperatureArrayPort8Rearm
                                          INTEGER,
                                       sensorProbeTemperatureArrayPort8DegreeType
                                          INTEGER,
                                       sensorProbeTemperatureArrayPort8DegreeRaw
                                          INTEGER,
                                       sensorProbeTemperatureArrayPort8Offset
                                          INTEGER,
                                       sensorProbeTemperatureArrayPort8URL
                                          DisplayString,
                                       sensorProbeTemperatureArrayPort8OpenURL
                                          INTEGER,
                                       sensorProbeTemperatureArrayPort8DatacollectType
                                          INTEGER,
                                       sensorProbeTemperatureArrayPort8ContTimeHighCritical
                                          INTEGER,
                                       sensorProbeTemperatureArrayPort8ContTimeHighWarning
                                          INTEGER,
                                       sensorProbeTemperatureArrayPort8ContTimeNormal
                                          INTEGER,
                                       sensorProbeTemperatureArrayPort8ContTimeLowWarning
                                          INTEGER,
                                       sensorProbeTemperatureArrayPort8ContTimeLowCritical
                                          INTEGER,
                                       sensorProbeTemperatureArrayPort8ContTimeSensorError
                                          INTEGER,
                                       sensorProbeTemperatureArrayPort8Calendar
                                          INTEGER,
                                       sensorProbeThermostatTemperatureArrayPort8Index
                                          INTEGER,
                                       sensorProbeThermostatTemperatureArrayPort8Description
                                          DisplayString,
                                       sensorProbeThermostatTemperatureArrayPort8Value
                                          INTEGER,
                                       sensorProbeThermostatTemperatureArrayPort8Online
                                          INTEGER,
                                       sensorProbeThermostatTemperatureArrayPort8GoOnline
                                          INTEGER,
                                       sensorProbeThermostatTemperatureArrayPort8Mode
                                          INTEGER,
                                       sensorProbeThermostatTemperatureArrayPort8RelayControlPort
                                          INTEGER,
                                       sensorProbeThermostatTemperatureArrayPort8NormalAction1
                                          INTEGER,
                                       sensorProbeThermostatTemperatureArrayPort8HighLimit1
                                          INTEGER,
                                       sensorProbeThermostatTemperatureArrayPort8HighLimitAction1
                                          INTEGER,
                                       sensorProbeThermostatTemperatureArrayPort8LowLimit1
                                          INTEGER,
                                       sensorProbeThermostatTemperatureArrayPort8LowLimitAction1
                                          INTEGER,
                                       sensorProbeThermostatTemperatureArrayPort8NormalAction2
                                          INTEGER,
                                       sensorProbeThermostatTemperatureArrayPort8HighLimit2
                                          INTEGER,
                                       sensorProbeThermostatTemperatureArrayPort8HighLimitAction2
                                          INTEGER,
                                       sensorProbeThermostatTemperatureArrayPort8LowLimit2
                                          INTEGER,
                                       sensorProbeThermostatTemperatureArrayPort8LowLimitAction2
                                          INTEGER,
                                       sensorProbeThermostatTemperatureArrayPort8EnableTime
                                          DisplayString
                                    }

                                    sensorProbeTemperatureArrayPort8Index OBJECT-TYPE
                                       SYNTAX  INTEGER (0..7)
                                       ACCESS  read-only
                                       STATUS  mandatory
                                       DESCRIPTION
                                       "A unique value for each sensor TemperatureArray port."
                                       ::=  {  sensorProbeTemperatureArrayPort8Entry 1   }

                                    sensorProbeTemperatureArrayPort8Description OBJECT-TYPE
                                       SYNTAX  DisplayString
                                       ACCESS  read-write
                                       STATUS  mandatory
                                       DESCRIPTION
                                       "A Description of this sensor TemperatureArray"
                                       ::=  {  sensorProbeTemperatureArrayPort8Entry 2   }

                                    sensorProbeTemperatureArrayPort8Value OBJECT-TYPE
                                       SYNTAX  INTEGER
                                       ACCESS  read-only
                                       STATUS  mandatory
                                       DESCRIPTION
                                       "The value in this sensor"
                                       ::=  {  sensorProbeTemperatureArrayPort8Entry 3   }

                                    sensorProbeTemperatureArrayPort8Status OBJECT-TYPE
                                       SYNTAX  INTEGER {
                                          noStatus(1),
                                          normal(2),
                                          highWarning(3),
                                          highCritical(4),
                                          lowWarning(5),
                                          lowCritical(6),
                                          sensorError(7)
                                       }
                                       ACCESS  read-only
                                       STATUS  mandatory
                                       DESCRIPTION
                                       "The current status of this Sensor"
                                       ::=  {  sensorProbeTemperatureArrayPort8Entry 4   }

                                    sensorProbeTemperatureArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeTemperatureArrayPort8Entry 5   }

                                    sensorProbeTemperatureArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeTemperatureArrayPort8Entry 6   }

                                    sensorProbeTemperatureArrayPort8HighWarning OBJECT-TYPE
                                       SYNTAX  INTEGER
                                       ACCESS  read-write
                                       STATUS  mandatory
                                       DESCRIPTION
                                       "How hot this  sensor gets before it sends a warning"
                                       ::=  {  sensorProbeTemperatureArrayPort8Entry 7   }

                                    sensorProbeTemperatureArrayPort8HighCritical OBJECT-TYPE
                                       SYNTAX  INTEGER
                                       ACCESS  read-write
                                       STATUS  mandatory
                                       DESCRIPTION
                                       "How hot this sensor gets before it sends a critical event"
                                       ::=  {  sensorProbeTemperatureArrayPort8Entry 8   }

                                    sensorProbeTemperatureArrayPort8LowWarning OBJECT-TYPE
                                       SYNTAX  INTEGER
                                       ACCESS  read-write
                                       STATUS  mandatory
                                       DESCRIPTION
                                       "How cold this sensor gets before it sends a warning"
                                       ::=  {  sensorProbeTemperatureArrayPort8Entry 9   }

                                    sensorProbeTemperatureArrayPort8LowCritical OBJECT-TYPE
                                       SYNTAX  INTEGER
                                       ACCESS  read-write
                                       STATUS  mandatory
                                       DESCRIPTION
                                       "How cold this sensor gets before it sends a critical event"
                                       ::=  {  sensorProbeTemperatureArrayPort8Entry 10   }

                                    sensorProbeTemperatureArrayPort8Rearm OBJECT-TYPE
                                       SYNTAX  INTEGER
                                       ACCESS  read-write
                                       STATUS  mandatory
                                       DESCRIPTION
                                       "The number of degrees to rearm the status. For example if status goes from normal to warning, the temp must go down spTempRearm degrees below warning before the status goes to normal"
                                       ::=  {  sensorProbeTemperatureArrayPort8Entry 11   }

                                    sensorProbeTemperatureArrayPort8DegreeType OBJECT-TYPE
                                       SYNTAX  INTEGER {
                                          fahr(0),
                                          celsius(1)
                                       }
                                       ACCESS  read-write
                                       STATUS  mandatory
                                       DESCRIPTION
                                       "The degrees are in fahrenheit(0) or in celsius(1)"
                                       ::=  {  sensorProbeTemperatureArrayPort8Entry 12   }

                                    sensorProbeTemperatureArrayPort8DegreeRaw OBJECT-TYPE
                                       SYNTAX  INTEGER 
                                       ACCESS  read-only
                                       STATUS  mandatory
                                       DESCRIPTION
                                       "The raw degree data from the temperature sensor, slightly higher resolution"
                                       ::=  {  sensorProbeTemperatureArrayPort8Entry 14   }

                                    sensorProbeTemperatureArrayPort8Offset OBJECT-TYPE
                                       SYNTAX  INTEGER
                                       ACCESS  read-write
                                       STATUS  mandatory
                                       DESCRIPTION
                                       "Offset reading"
                                       ::=  {  sensorProbeTemperatureArrayPort8Entry 15   }

                                    sensorProbeTemperatureArrayPort8URL OBJECT-TYPE
                                       SYNTAX  DisplayString
                                       ACCESS  read-write
                                       STATUS  mandatory
                                       DESCRIPTION
                                       "Sensor URL link."
                                       ::=  {  sensorProbeTemperatureArrayPort8Entry 16   }

                                    sensorProbeTemperatureArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeTemperatureArrayPort8Entry 17   }

                                    sensorProbeTemperatureArrayPort8DatacollectType OBJECT-TYPE
                                       SYNTAX  INTEGER {
                                          average(1),
                                          highest(2),
                                          lowest(3)
                                       }
                                       ACCESS  read-write
                                       STATUS  mandatory
                                       DESCRIPTION
                                       "Type of datacollect to collect."
                                       ::=  {  sensorProbeTemperatureArrayPort8Entry 18   }

                                    sensorProbeTemperatureArrayPort8ContTimeHighCritical OBJECT-TYPE
                                       SYNTAX INTEGER (0..65535)
                                       ACCESS read-write
                                       STATUS mandatory
                                       DESCRIPTION
                                       "Continuous time for this sensor to be in High Critical before accepting new Status."
                                       ::= {  sensorProbeTemperatureArrayPort8Entry 19 }

                                    sensorProbeTemperatureArrayPort8ContTimeHighWarning OBJECT-TYPE
                                       SYNTAX INTEGER (0..65535)
                                       ACCESS read-write
                                       STATUS mandatory
                                       DESCRIPTION
                                       "Continuous time for this sensor to be in High Warning before accepting new Status."
                                       ::= {  sensorProbeTemperatureArrayPort8Entry 20 }

                                    sensorProbeTemperatureArrayPort8ContTimeNormal OBJECT-TYPE
                                       SYNTAX INTEGER (0..65535)
                                       ACCESS read-write
                                       STATUS mandatory
                                       DESCRIPTION
                                       "Continuous time for this sensor to be in Normal before accepting new Status."
                                       ::= {  sensorProbeTemperatureArrayPort8Entry 21 }

                                    sensorProbeTemperatureArrayPort8ContTimeLowWarning OBJECT-TYPE
                                       SYNTAX INTEGER (0..65535)
                                       ACCESS read-write
                                       STATUS mandatory
                                       DESCRIPTION
                                       "Continuous time for this sensor to be in Low Warning before accepting new Status."
                                       ::= {  sensorProbeTemperatureArrayPort8Entry 22 }

                                    sensorProbeTemperatureArrayPort8ContTimeLowCritical OBJECT-TYPE
                                       SYNTAX INTEGER (0..65535)
                                       ACCESS read-write
                                       STATUS mandatory
                                       DESCRIPTION
                                       "Continuous time for this sensor to be in Low Critical before accepting new Status."
                                       ::= {  sensorProbeTemperatureArrayPort8Entry 23 }

                                    sensorProbeTemperatureArrayPort8ContTimeSensorError OBJECT-TYPE
                                       SYNTAX INTEGER (0..65535)
                                       ACCESS read-write
                                       STATUS mandatory
                                       DESCRIPTION
                                       "Continuous time for this sensor to be in Sensor Error before accepting new Status."
                                       ::= {  sensorProbeTemperatureArrayPort8Entry 24 }

                                    sensorProbeTemperatureArrayPort8Calendar OBJECT-TYPE
                                       SYNTAX INTEGER {
                                          disable(0),
                                          enable(1)
                                       }
                                       ACCESS read-write
                                       STATUS mandatory
                                       DESCRIPTION
                                       "Enable or disable the calendar filtering working hours of sensor."
                                       ::= {  sensorProbeTemperatureArrayPort8Entry 25 }

                                    sensorProbeThermostatTemperatureArrayPort8Index OBJECT-TYPE
                                       SYNTAX  INTEGER
                                       ACCESS  read-only
                                       STATUS  mandatory
                                       DESCRIPTION
                                       "A unique value for each sensor thermostat port."
                                       ::= {  sensorProbeTemperatureArrayPort8Entry 26 }

                                    sensorProbeThermostatTemperatureArrayPort8Description OBJECT-TYPE
                                       SYNTAX  DisplayString
                                       ACCESS  read-write
                                       STATUS  mandatory
                                       DESCRIPTION
                                       "A Description of this sensor thermostat"
                                       ::= {  sensorProbeTemperatureArrayPort8Entry 27 }

                                    sensorProbeThermostatTemperatureArrayPort8Value OBJECT-TYPE
                                       SYNTAX  INTEGER
                                       ACCESS  read-only
                                       STATUS  mandatory
                                       DESCRIPTION
                                       "The value in this sensor"
                                       ::= {  sensorProbeTemperatureArrayPort8Entry 28 }

                                    sensorProbeThermostatTemperatureArrayPort8Online OBJECT-TYPE
                                       SYNTAX  INTEGER {
                                          online(1),
                                          offline(2)
                                       }
                                       ACCESS  read-only
                                       STATUS  mandatory
                                       DESCRIPTION
                                       "If this Sensor is currently online"
                                       ::= {  sensorProbeTemperatureArrayPort8Entry 29 }

                                    sensorProbeThermostatTemperatureArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::= {  sensorProbeTemperatureArrayPort8Entry 30 }

                                    sensorProbeThermostatTemperatureArrayPort8Mode OBJECT-TYPE
                                       SYNTAX INTEGER {
                                          normal(0),
                                          time-bases(1)
                                       }
                                       ACCESS read-write
                                       STATUS mandatory
                                       DESCRIPTION
                                       "To select the thermostat mode for working on time-bases(1) or normal(0)."
                                       ::= {  sensorProbeTemperatureArrayPort8Entry 31 }

                                    sensorProbeThermostatTemperatureArrayPort8RelayControlPort OBJECT-TYPE
                                       SYNTAX INTEGER
                                       ACCESS read-write
                                       STATUS mandatory
                                       DESCRIPTION
                                       "To select a relay port to be controled by this thermostat sensor."
                                       ::= {  sensorProbeTemperatureArrayPort8Entry 32 }

                                    sensorProbeThermostatTemperatureArrayPort8NormalAction1 OBJECT-TYPE
                                       SYNTAX INTEGER {
                                          turn-on(0),
                                          turn-off(1),
                                          no-change(2)
                                       }
                                       ACCESS read-write
                                       STATUS mandatory
                                       DESCRIPTION
                                       "Profile1: Thermostat normal action for controlling a relay sensor."
                                       ::= {  sensorProbeTemperatureArrayPort8Entry 33 }

                                    sensorProbeThermostatTemperatureArrayPort8HighLimit1 OBJECT-TYPE
                                       SYNTAX INTEGER (-40..167)
                                       ACCESS read-write
                                       STATUS mandatory
                                       DESCRIPTION
                                       "Profile1: When this sersor higher than thermostat high limit, it will take a high limit action."
                                       ::= {  sensorProbeTemperatureArrayPort8Entry 34 }

                                    sensorProbeThermostatTemperatureArrayPort8HighLimitAction1 OBJECT-TYPE
                                       SYNTAX INTEGER {
                                          turn-on(0),
                                          turn-off(1),
                                          no-change(2)
                                       }
                                       ACCESS read-write
                                       STATUS mandatory
                                       DESCRIPTION
                                       "Profile1: Thermostat high limit action for controlling a relay sensor."
                                       ::= {  sensorProbeTemperatureArrayPort8Entry 35 }

                                    sensorProbeThermostatTemperatureArrayPort8LowLimit1 OBJECT-TYPE
                                       SYNTAX INTEGER (-40..167)
                                       ACCESS read-write
                                       STATUS mandatory
                                       DESCRIPTION
                                       "Profile1: When this sersor higher than thermostat low limit, it will take a normal limit action."
                                       ::= {  sensorProbeTemperatureArrayPort8Entry 36 }

                                    sensorProbeThermostatTemperatureArrayPort8LowLimitAction1 OBJECT-TYPE
                                       SYNTAX INTEGER {
                                          turn-on(0),
                                          turn-off(1),
                                          no-change(2)
                                       }
                                       ACCESS read-write
                                       STATUS mandatory
                                       DESCRIPTION
                                       "Profile1: Thermostat low limit action for controlling a relay sensor."
                                       ::= {  sensorProbeTemperatureArrayPort8Entry 37 }

                                    sensorProbeThermostatTemperatureArrayPort8NormalAction2 OBJECT-TYPE
                                       SYNTAX INTEGER {
                                          turn-on(0),
                                          turn-off(1),
                                          no-change(2)
                                       }
                                       ACCESS read-write
                                       STATUS mandatory
                                       DESCRIPTION
                                       "Profile2: Thermostat normal action for controlling a relay sensor."
                                       ::= {  sensorProbeTemperatureArrayPort8Entry 38 }

                                    sensorProbeThermostatTemperatureArrayPort8HighLimit2 OBJECT-TYPE
                                       SYNTAX INTEGER (-40..167)
                                       ACCESS read-write
                                       STATUS mandatory
                                       DESCRIPTION
                                       "Profile2: When this sersor higher than thermostat high limit, it will take a high limit action."
                                       ::= {  sensorProbeTemperatureArrayPort8Entry 39 }

                                    sensorProbeThermostatTemperatureArrayPort8HighLimitAction2 OBJECT-TYPE
                                       SYNTAX INTEGER {
                                          turn-on(0),
                                          turn-off(1),
                                          no-change(2)
                                       }
                                       ACCESS read-write
                                       STATUS mandatory
                                       DESCRIPTION
                                       "Profile2: Thermostat high limit action for controlling a relay sensor."
                                       ::= {  sensorProbeTemperatureArrayPort8Entry 40 }

                                    sensorProbeThermostatTemperatureArrayPort8LowLimit2 OBJECT-TYPE
                                       SYNTAX INTEGER (-40..167)
                                       ACCESS read-write
                                       STATUS mandatory
                                       DESCRIPTION
                                       "Profile2: When this sersor higher than thermostat low limit, it will take a normal limit action."
                                       ::= {  sensorProbeTemperatureArrayPort8Entry 41 }

                                    sensorProbeThermostatTemperatureArrayPort8LowLimitAction2 OBJECT-TYPE
                                       SYNTAX INTEGER {
                                          turn-on(0),
                                          turn-off(1),
                                          no-change(2)
                                       }
                                       ACCESS read-write
                                       STATUS mandatory
                                       DESCRIPTION
                                       "Profile2: Thermostat low limit action for controlling a relay sensor."
                                       ::= {  sensorProbeTemperatureArrayPort8Entry 42 }

                                    sensorProbeThermostatTemperatureArrayPort8EnableTime OBJECT-TYPE
                                       SYNTAX  DisplayString
                                       ACCESS  read-write
                                       STATUS  mandatory
                                       DESCRIPTION
                                       "Time to enable on Thermostat"
                                       ::=  {  sensorProbeTemperatureArrayPort8Entry 43 }

                  sensorProbeNoCameraSensor OBJECT IDENTIFIER ::= { sensorProbeOtherSensor 34  }

                     sensorProbeNoCameraSensorNumber OBJECT-TYPE
                        SYNTAX INTEGER
                        ACCESS read-only
                        STATUS mandatory
                        DESCRIPTION
                        "The total number of no camera sensor port."
                        ::= {  sensorProbeNoCameraSensor 1 }

                     sensorProbeNoCameraSensorTable OBJECT-TYPE
                        SYNTAX  SEQUENCE OF SensorProbeNoCameraSensorEntry
                        ACCESS  not-accessible
                        STATUS  mandatory
                        DESCRIPTION
                        "This table contains the data for every no camera Sensor. Each row in the table contains data for a different NoCamera Sensor."
                        ::=  {  sensorProbeNoCameraSensor 2   }

                        sensorProbeNoCameraSensorEntry OBJECT-TYPE
                           SYNTAX  SensorProbeNoCameraSensorEntry
                           ACCESS  not-accessible
                           STATUS  mandatory
                           DESCRIPTION
                           "This is an entry in the sensorProbeNoCameraSensorEntry Table"
                           INDEX         { sensorProbeNoCameraSensorIndex }
                           ::=  { sensorProbeNoCameraSensorTable 1 }

                        SensorProbeNoCameraSensorEntry ::= SEQUENCE {
                           sensorProbeNoCameraSensorIndex
                              INTEGER,
                           sensorProbeNoCameraDescription
                              DisplayString,
                           sensorProbeNoCameraStatus
                              INTEGER,
                           sensorProbeNoCameraOnline
                              INTEGER,
                           sensorProbeNoCameraGoOnline
                              INTEGER,
                           sensorProbeNoCameraContTimeHighCritical
                              INTEGER,
                           sensorProbeNoCameraContTimeNormal
                              INTEGER,
                           sensorProbeNoCameraCalendar
                              INTEGER
                        }

                           sensorProbeNoCameraSensorIndex OBJECT-TYPE
                              SYNTAX  INTEGER (0..3)
                              ACCESS  read-only
                              STATUS  mandatory
                              DESCRIPTION
                              "A unique value for each no camera sensor port."
                              ::=  {  sensorProbeNoCameraSensorEntry 1  }

                           sensorProbeNoCameraDescription OBJECT-TYPE
                              SYNTAX  DisplayString
                              ACCESS  read-write
                              STATUS  mandatory
                              DESCRIPTION
                              "A Description of this sensor"
                              ::=  {  sensorProbeNoCameraSensorEntry 2   }

                           sensorProbeNoCameraStatus OBJECT-TYPE
                              SYNTAX  INTEGER {
                                 noStatus(1),
                                 normal(2),
                                 highCritical(4),
                                 lowCritical(6),
                                 sensorError(7),
                                 relayOn(8),
                                 relayOff(9)
                              }
                              ACCESS  read-only
                              STATUS  mandatory
                              DESCRIPTION
                              "The current status of this Sensor."
                              ::=  {  sensorProbeNoCameraSensorEntry 4  }

                           sensorProbeNoCameraOnline OBJECT-TYPE
                              SYNTAX  INTEGER {
                                 online(1),
                                 offline(2)
                              }
                              ACCESS  read-only
                              STATUS  mandatory
                              DESCRIPTION
                              "If this Sensor is currently online"
                                 ::=  {  sensorProbeNoCameraSensorEntry 5  }

                           sensorProbeNoCameraGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeNoCameraSensorEntry 6  }

                           sensorProbeNoCameraContTimeHighCritical OBJECT-TYPE
                              SYNTAX INTEGER (0..65535)
                              ACCESS read-write
                              STATUS mandatory
                              DESCRIPTION
                              "Continuous time for this sensor to be in High Critical before accepting new Status."
                              ::= {  sensorProbeNoCameraSensorEntry 7 }

                           sensorProbeNoCameraContTimeNormal OBJECT-TYPE
                              SYNTAX INTEGER (0..65535)
                              ACCESS read-write
                              STATUS mandatory
                              DESCRIPTION
                              "Continuous time for this sensor to be in Normal before accepting new Status."
                              ::= {  sensorProbeNoCameraSensorEntry 8 }

                           sensorProbeNoCameraCalendar OBJECT-TYPE
                              SYNTAX INTEGER {
                                 disable(0),
                                 enable(1)
                              }
                              ACCESS read-write
                              STATUS mandatory
                              DESCRIPTION
                              "Enable or disable the calendar filtering working hours of sensor."
                              ::= {  sensorProbeNoCameraSensorEntry 9 }

                  sensorProbeSoftMotionSensor OBJECT IDENTIFIER ::= { sensorProbeOtherSensor 35  }

                     sensorProbeSoftMotionSensorNumber OBJECT-TYPE
                        SYNTAX INTEGER
                        ACCESS read-only
                        STATUS mandatory
                        DESCRIPTION
                        "The total number of SoftMotionSensor port."
                        ::= {  sensorProbeSoftMotionSensor 1 }

                     sensorProbeSoftMotionSensorTable OBJECT-TYPE
                        SYNTAX  SEQUENCE OF SensorProbeSoftMotionSensorEntry
                        ACCESS  not-accessible
                        STATUS  mandatory
                        DESCRIPTION
                        "This table contains the data for every SoftMotion Sensor. Each row in the table contains data for a different SoftMotion Sensor."
                        ::=  {  sensorProbeSoftMotionSensor 2   }

                        sensorProbeSoftMotionSensorEntry OBJECT-TYPE
                           SYNTAX  SensorProbeSoftMotionSensorEntry
                           ACCESS  not-accessible
                           STATUS  mandatory
                           DESCRIPTION
                           "This is an entry in the sensorProbeSoftMotionSensorEntry Table"
                           INDEX         { sensorProbeSoftMotionSensorIndex }
                           ::=  { sensorProbeSoftMotionSensorTable 1 }

                        SensorProbeSoftMotionSensorEntry ::= SEQUENCE {
                           sensorProbeSoftMotionSensorIndex
                              INTEGER,
                           sensorProbeSoftMotionDescription
                              DisplayString,
                           sensorProbeSoftMotionStatus
                              INTEGER,
                           sensorProbeSoftMotionOnline
                              INTEGER,
                           sensorProbeSoftMotionGoOnline
                              INTEGER,
                           sensorProbeSoftMotionPercentSensitivity
                              INTEGER,
                           sensorProbeSoftMotionURL
                              DisplayString,
                           sensorProbeSoftMotionOpenURL
                              INTEGER,
                           sensorProbeSoftMotionContTimeHighCritical
                              INTEGER,
                           sensorProbeSoftMotionContTimeNormal
                              INTEGER,
                           sensorProbeSoftMotionCalendar
                              INTEGER,
                           sensorProbeSoftMotionMask
                              INTEGER
                        }

                           sensorProbeSoftMotionSensorIndex OBJECT-TYPE
                              SYNTAX  INTEGER (0..3)
                              ACCESS  read-only
                              STATUS  mandatory
                              DESCRIPTION
                              "A unique value for each soft motion sensor port."
                              ::=  {  sensorProbeSoftMotionSensorEntry 1  }

                           sensorProbeSoftMotionDescription OBJECT-TYPE
                              SYNTAX  DisplayString
                              ACCESS  read-write
                              STATUS  mandatory
                              DESCRIPTION
                              "A Description of this sensor"
                              ::=  {  sensorProbeSoftMotionSensorEntry 2   }

                           sensorProbeSoftMotionStatus OBJECT-TYPE
                              SYNTAX  INTEGER {
                                 noStatus(1),
                                 normal(2),
                                 highCritical(4),
                                 lowCritical(6),
                                 sensorError(7),
                                 relayOn(8),
                                 relayOff(9)
                              }
                              ACCESS  read-only
                              STATUS  mandatory
                              DESCRIPTION
                              "The current status of this Sensor."
                              ::=  {  sensorProbeSoftMotionSensorEntry 4  }

                           sensorProbeSoftMotionOnline OBJECT-TYPE
                              SYNTAX  INTEGER {
                                 online(1),
                                 offline(2)
                              }
                              ACCESS  read-only
                              STATUS  mandatory
                              DESCRIPTION
                              "If this Sensor is currently online"
                                 ::=  {  sensorProbeSoftMotionSensorEntry 5  }

                           sensorProbeSoftMotionGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeSoftMotionSensorEntry 6  }

                           sensorProbeSoftMotionPercentSensitivity OBJECT-TYPE
                              SYNTAX INTEGER (0..100)
                              ACCESS read-write
                              STATUS mandatory
                              DESCRIPTION
                              "The percent of sensitivity uses for setting the sentisitivity of motion detector."
                              ::= {  sensorProbeSoftMotionSensorEntry 7 }

                           sensorProbeSoftMotionURL OBJECT-TYPE
                              SYNTAX  DisplayString
                              ACCESS  read-write
                              STATUS  mandatory
                              DESCRIPTION
                              "Sensor URL link."
                              ::=  {  sensorProbeSoftMotionSensorEntry 8   }

                           sensorProbeSoftMotionOpenURL OBJECT-TYPE
                              SYNTAX  INTEGER {
                                 cur-window(0),
                                 new-window(2)
                              }
                              ACCESS  read-write
                              STATUS  mandatory
                              DESCRIPTION
                              "Open URL in this browser or open in a new window."
                              ::=  {  sensorProbeSoftMotionSensorEntry 9   }

                           sensorProbeSoftMotionContTimeHighCritical OBJECT-TYPE
                              SYNTAX INTEGER (0..65535)
                              ACCESS read-write
                              STATUS mandatory
                              DESCRIPTION
                              "Continuous time for this sensor to be in High Critical before accepting new Status."
                              ::= {  sensorProbeSoftMotionSensorEntry 10 }

                           sensorProbeSoftMotionContTimeNormal OBJECT-TYPE
                              SYNTAX INTEGER (0..65535)
                              ACCESS read-write
                              STATUS mandatory
                              DESCRIPTION
                              "Continuous time for this sensor to be in Normal before accepting new Status."
                              ::= {  sensorProbeSoftMotionSensorEntry 11 }

                           sensorProbeSoftMotionCalendar OBJECT-TYPE
                              SYNTAX INTEGER {
                                 disable(0),
                                 enable(1)
                              }
                              ACCESS read-write
                              STATUS mandatory
                              DESCRIPTION
                              "Enable or disable the calendar filtering working hours of sensor."
                              ::= {  sensorProbeSoftMotionSensorEntry 12 }

                           sensorProbeSoftMotionMask OBJECT-TYPE
                              SYNTAX INTEGER (0..33554431)
                              ACCESS read-write
                              STATUS mandatory
                              DESCRIPTION
                              "Mask of enable or disable of SoftMotion."
                              ::= {  sensorProbeSoftMotionSensorEntry 13 }

                  sensorProbeSoundDetectorSensor OBJECT IDENTIFIER ::= { sensorProbeOtherSensor 36  }

                     sensorProbeSoundDetectorSensorNumber OBJECT-TYPE
                        SYNTAX INTEGER
                        ACCESS read-only
                        STATUS mandatory
                        DESCRIPTION
                        "The total number of SoundDetectorSensor port."
                        ::= {  sensorProbeSoundDetectorSensor 1 }

                     sensorProbeSoundDetectorSensorTable OBJECT-TYPE
                        SYNTAX  SEQUENCE OF SensorProbeSoundDetectorSensorEntry
                        ACCESS  not-accessible
                        STATUS  mandatory
                        DESCRIPTION
                        "This table contains the data for every SoundDetectorSensor Sensor. Each row in the table contains data for a different SoundDetectorSensor Sensor."
                        ::=  {  sensorProbeSoundDetectorSensor 2   }

                        sensorProbeSoundDetectorSensorEntry OBJECT-TYPE
                           SYNTAX  SensorProbeSoundDetectorSensorEntry
                           ACCESS  not-accessible
                           STATUS  mandatory
                           DESCRIPTION
                           "This is an entry in the sensorProbeSoundDetectorSensorEntry Table"
                           INDEX         { sensorProbeSoundDetectorIndex }
                           ::=  { sensorProbeSoundDetectorSensorTable 1 }

                        SensorProbeSoundDetectorSensorEntry ::= SEQUENCE {
                           sensorProbeSoundDetectorIndex
                              INTEGER,
                           sensorProbeSoundDetectorDescription
                              DisplayString,
                           sensorProbeSoundDetectorValue
                              INTEGER,
                           sensorProbeSoundDetectorStatus
                              INTEGER,
                           sensorProbeSoundDetectorOnline
                              INTEGER,
                           sensorProbeSoundDetectorGoOnline
                              INTEGER,
                           sensorProbeSoundDetectorHighWarning
                              INTEGER,
                           sensorProbeSoundDetectorHighCritical
                              INTEGER,
                           sensorProbeSoundDetectorLowWarning
                              INTEGER,
                           sensorProbeSoundDetectorLowCritical
                              INTEGER,
                           sensorProbeSoundDetectorRearm
                              INTEGER,
                           sensorProbeSoundDetectorRecordingSource
                              INTEGER,
                           sensorProbeSoundDetectorMicBoost
                              INTEGER,
                           sensorProbeSoundDetectorMicSensitivity
                              INTEGER,
                           sensorProbeSoundDetectorPulseLength
                              INTEGER,
                           sensorProbeSoundDetectorURL
                              DisplayString,
                           sensorProbeSoundDetectorOpenURL
                              INTEGER,
                           sensorProbeSoundDetectorDatacollectType
                              INTEGER,
                           sensorProbeSoundDetectorContTimeHighCritical
                              INTEGER,
                           sensorProbeSoundDetectorContTimeHighWarning
                              INTEGER,
                           sensorProbeSoundDetectorContTimeNormal
                              INTEGER,
                           sensorProbeSoundDetectorContTimeLowWarning
                              INTEGER,
                           sensorProbeSoundDetectorContTimeLowCritical
                              INTEGER,
                           sensorProbeSoundDetectorContTimeSensorError
                              INTEGER,
                           sensorProbeSoundDetectorCalendar
                              INTEGER
                        }

                           sensorProbeSoundDetectorIndex OBJECT-TYPE
                              SYNTAX  INTEGER (0)
                              ACCESS  read-only
                              STATUS  mandatory
                              DESCRIPTION
                              "A unique value for each sound detector sensor port."
                              ::=  {  sensorProbeSoundDetectorSensorEntry 1  }

                           sensorProbeSoundDetectorDescription OBJECT-TYPE
                              SYNTAX  DisplayString
                              ACCESS  read-write
                              STATUS  mandatory
                              DESCRIPTION
                              "A Description of this sensor"
                              ::=  {  sensorProbeSoundDetectorSensorEntry 2   }

                           sensorProbeSoundDetectorValue OBJECT-TYPE
                              SYNTAX  INTEGER
                              ACCESS  read-only
                              STATUS  mandatory
                              DESCRIPTION
                              "The value in this sensor"
                              ::=  {  sensorProbeSoundDetectorSensorEntry 3   }

                           sensorProbeSoundDetectorStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  sensorProbeSoundDetectorSensorEntry 4   }

                           sensorProbeSoundDetectorOnline OBJECT-TYPE
                              SYNTAX  INTEGER {
                                 online(1),
                                 offline(2)
                              }
                              ACCESS  read-only
                              STATUS  mandatory
                              DESCRIPTION
                              "If this Sensor is currently online"
                              ::=  {  sensorProbeSoundDetectorSensorEntry 5   }

                           sensorProbeSoundDetectorGoOnline OBJECT-TYPE
                              SYNTAX  INTEGER {
                                 goOnline(1),
                                 goOffline(2)
                              }
                              ACCESS  read-write
                              STATUS  mandatory
                              DESCRIPTION
                              "To put online enter a 1, to take offline enter a 2"
                              ::=  {  sensorProbeSoundDetectorSensorEntry 6   }

                           sensorProbeSoundDetectorHighWarning OBJECT-TYPE
                              SYNTAX  INTEGER
                              ACCESS  read-write
                              STATUS  mandatory
                              DESCRIPTION
                              "How hot this  sensor gets before it sends a warning"
                              ::=  {  sensorProbeSoundDetectorSensorEntry 7   }

                           sensorProbeSoundDetectorHighCritical OBJECT-TYPE
                              SYNTAX  INTEGER
                              ACCESS  read-write
                              STATUS  mandatory
                              DESCRIPTION
                              "How hot this sensor gets before it sends a critical event"
                              ::=  {  sensorProbeSoundDetectorSensorEntry 8   }

                           sensorProbeSoundDetectorLowWarning OBJECT-TYPE
                              SYNTAX  INTEGER
                              ACCESS  read-write
                              STATUS  mandatory
                              DESCRIPTION
                              "How cold this sensor gets before it sends a warning"
                              ::=  {  sensorProbeSoundDetectorSensorEntry 9   }

                           sensorProbeSoundDetectorLowCritical OBJECT-TYPE
                              SYNTAX  INTEGER
                              ACCESS  read-write
                              STATUS  mandatory
                              DESCRIPTION
                              "How cold this sensor gets before it sends a critical event"
                              ::=  {  sensorProbeSoundDetectorSensorEntry 10   }

                           sensorProbeSoundDetectorRearm OBJECT-TYPE
                              SYNTAX  INTEGER
                              ACCESS  read-write
                              STATUS  mandatory
                              DESCRIPTION
                              "The number of degrees to rearm the status. For example if status goes from normal to warning, the temp must go down Rearm degrees below warning before the status goes to normal"
                              ::=  {  sensorProbeSoundDetectorSensorEntry 11   }

                           sensorProbeSoundDetectorRecordingSource OBJECT-TYPE
                              SYNTAX  INTEGER {
                                 internal-mic(0),
                                 line-in(1)
                              }
                              ACCESS  read-write
                              STATUS  mandatory
                              DESCRIPTION
                              "To select a recording source being in internal microphone(0) or in line-in(1)."
                              ::=  {  sensorProbeSoundDetectorSensorEntry 12   }

                           sensorProbeSoundDetectorMicBoost OBJECT-TYPE
                              SYNTAX  INTEGER {
                                 off(0),
                                 on(1)
                              }
                              ACCESS  read-write
                              STATUS  mandatory
                              DESCRIPTION
                              "Enable or disable a microphone boost(+20 db)."
                              ::=  {  sensorProbeSoundDetectorSensorEntry 13   }

                           sensorProbeSoundDetectorMicSensitivity OBJECT-TYPE
                              SYNTAX  INTEGER {
                                 i0(0),
                                 i20(20),
                                 i40(40),
                                 i60(60),
                                 i80(80),
                                 i100(100)
                              }
                              ACCESS  read-write
                              STATUS  mandatory
                              DESCRIPTION
                              "The sensitivity of microphone to detect sound."
                              ::=  {  sensorProbeSoundDetectorSensorEntry 14   }

                           sensorProbeSoundDetectorPulseLength OBJECT-TYPE
                              SYNTAX  INTEGER
                              ACCESS  read-write
                              STATUS  mandatory
                              DESCRIPTION
                              "Continuous time for detecting before changing status."
                              ::=  {  sensorProbeSoundDetectorSensorEntry 15   }

                           sensorProbeSoundDetectorURL OBJECT-TYPE
                              SYNTAX  DisplayString
                              ACCESS  read-write
                              STATUS  mandatory
                              DESCRIPTION
                              "Sensor URL link."
                              ::=  {  sensorProbeSoundDetectorSensorEntry 16   }

                           sensorProbeSoundDetectorOpenURL OBJECT-TYPE
                              SYNTAX  INTEGER {
                                 cur-window(0),
                                 new-window(2)
                              }
                              ACCESS  read-write
                              STATUS  mandatory
                              DESCRIPTION
                              "Open URL in this browser or open in a new window."
                              ::=  {  sensorProbeSoundDetectorSensorEntry 17   }

                           sensorProbeSoundDetectorDatacollectType OBJECT-TYPE
                              SYNTAX  INTEGER {
                                 average(1),
                                 highest(2),
                                 lowest(3)
                              }
                              ACCESS  read-write
                              STATUS  mandatory
                              DESCRIPTION
                              "Type of datacollect to collect."
                              ::=  {  sensorProbeSoundDetectorSensorEntry 18   }

                           sensorProbeSoundDetectorContTimeHighCritical OBJECT-TYPE
                              SYNTAX INTEGER (0..65535)
                              ACCESS read-write
                              STATUS mandatory
                              DESCRIPTION
                              "Continuous time for this sensor to be in High Critical before accepting new Status."
                              ::= {  sensorProbeSoundDetectorSensorEntry 19 }

                           sensorProbeSoundDetectorContTimeHighWarning OBJECT-TYPE
                              SYNTAX INTEGER (0..65535)
                              ACCESS read-write
                              STATUS mandatory
                              DESCRIPTION
                              "Continuous time for this sensor to be in High Warning before accepting new Status."
                              ::= {  sensorProbeSoundDetectorSensorEntry 20 }

                           sensorProbeSoundDetectorContTimeNormal OBJECT-TYPE
                              SYNTAX INTEGER (0..65535)
                              ACCESS read-write
                              STATUS mandatory
                              DESCRIPTION
                              "Continuous time for this sensor to be in Normal before accepting new Status."
                              ::= {  sensorProbeSoundDetectorSensorEntry 21 }

                           sensorProbeSoundDetectorContTimeLowWarning OBJECT-TYPE
                              SYNTAX INTEGER (0..65535)
                              ACCESS read-write
                              STATUS mandatory
                              DESCRIPTION
                              "Continuous time for this sensor to be in Low Warning before accepting new Status."
                              ::= {  sensorProbeSoundDetectorSensorEntry 22 }

                           sensorProbeSoundDetectorContTimeLowCritical OBJECT-TYPE
                              SYNTAX INTEGER (0..65535)
                              ACCESS read-write
                              STATUS mandatory
                              DESCRIPTION
                              "Continuous time for this sensor to be in Low Critical before accepting new Status."
                              ::= {  sensorProbeSoundDetectorSensorEntry 23 }

                           sensorProbeSoundDetectorContTimeSensorError OBJECT-TYPE
                              SYNTAX INTEGER (0..65535)
                              ACCESS read-write
                              STATUS mandatory
                              DESCRIPTION
                              "Continuous time for this sensor to be in Sensor Error before accepting new Status."
                              ::= {  sensorProbeSoundDetectorSensorEntry 24 }

                           sensorProbeSoundDetectorCalendar OBJECT-TYPE
                              SYNTAX INTEGER {
                                 disable(0),
                                 enable(1)
                              }
                              ACCESS read-write
                              STATUS mandatory
                              DESCRIPTION
                              "Enable or disable the calendar filtering working hours of sensor."
                              ::= {  sensorProbeSoundDetectorSensorEntry 25 }

                        sensorProbeDrycontactArraySensor OBJECT IDENTIFIER ::= { sensorProbeOtherSensor 37  }

                           sensorProbeDrycontactArrayPort1 OBJECT IDENTIFIER ::= { sensorProbeDrycontactArraySensor 1  }
                              sensorProbeDrycontactArrayPort1Number OBJECT-TYPE
                                 SYNTAX INTEGER
                                 ACCESS read-only
                                 STATUS mandatory
                                 DESCRIPTION
                                 "The total number of port on the DrycontactArray."
                                 ::=  {  sensorProbeDrycontactArrayPort1 1   }

                              sensorProbeDrycontactArrayPort1Table OBJECT-TYPE
                                 SYNTAX  SEQUENCE OF SensorProbeDrycontactArrayPort1Entry
                                 ACCESS  not-accessible
                                 STATUS  mandatory
                                 DESCRIPTION
                                 "This table contains the data for every Drycontact Sensor in the SensorArray. Each row in the table contains data for a different Drycontact Sensor."
                                 ::=  {  sensorProbeDrycontactArrayPort1 2   }

                                 sensorProbeDrycontactArrayPort1Entry OBJECT-TYPE
                                    SYNTAX  SensorProbeDrycontactArrayPort1Entry
                                    ACCESS  not-accessible
                                    STATUS  mandatory
                                    DESCRIPTION
                                    "This is an entry in the sensorProbeDrycontactArrayPort1 Table"
                                    INDEX         { sensorProbeDrycontactArrayPort1Index }
                                    ::=  { sensorProbeDrycontactArrayPort1Table 1 }

                                    SensorProbeDrycontactArrayPort1Entry ::= SEQUENCE {
                                       sensorProbeDrycontactArrayPort1Index
                                          INTEGER,
                                       sensorProbeDrycontactArrayPort1Description
                                          DisplayString,
                                       sensorProbeDrycontactArrayPort1Status
                                          INTEGER,
                                       sensorProbeDrycontactArrayPort1Online
                                          INTEGER,
                                       sensorProbeDrycontactArrayPort1GoOnline
                                          INTEGER,
                                       sensorProbeDrycontactArrayPort1NormalState
                                          INTEGER,
                                       sensorProbeDrycontactArrayPort1Direction
                                          INTEGER,
                                       sensorProbeDrycontactArrayPort1ContTimeCritical
                                          INTEGER,
                                       sensorProbeDrycontactArrayPort1ContTimeNormal
                                          INTEGER,
                                       sensorProbeDrycontactArrayPort1ManualOutputCycleTime
                                          INTEGER,
                                       sensorProbeDrycontactArrayPort1ManualOutputAction
                                          INTEGER,
                                       sensorProbeDrycontactArrayPort1OutputDescOn
                                          DisplayString,
                                       sensorProbeDrycontactArrayPort1OutputDescOff
                                          DisplayString,
                                       sensorProbeDrycontactArrayPort1URL
                                          DisplayString,
                                       sensorProbeDrycontactArrayPort1OpenURL
                                          INTEGER,
                                       sensorProbeDrycontactArrayPort1ControlMode
                                          INTEGER
                                    }

                                    sensorProbeDrycontactArrayPort1Index OBJECT-TYPE
                                       SYNTAX  INTEGER (0..7)
                                       ACCESS  read-only
                                       STATUS  mandatory
                                       DESCRIPTION
                                       "A unique value for each sensor DrycontactArray port."
                                       ::=  {  sensorProbeDrycontactArrayPort1Entry 1   }

                                    sensorProbeDrycontactArrayPort1Description OBJECT-TYPE
                                       SYNTAX  DisplayString
                                       ACCESS  read-write
                                       STATUS  mandatory
                                       DESCRIPTION
                                       "A Description of this sensor DrycontactArray"
                                       ::=  {  sensorProbeDrycontactArrayPort1Entry 2   }

                                    sensorProbeDrycontactArrayPort1Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort1Entry 4  }

                                    sensorProbeDrycontactArrayPort1Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort1Entry 5  }

                                    sensorProbeDrycontactArrayPort1GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort1Entry 6  }

                                    sensorProbeDrycontactArrayPort1NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort1Entry 7  }

                                    sensorProbeDrycontactArrayPort1Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort1Entry 8  }

                                    sensorProbeDrycontactArrayPort1ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort1Entry 9   }

                                    sensorProbeDrycontactArrayPort1ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort1Entry 10   }

                                    sensorProbeDrycontactArrayPort1ManualOutputCycleTime OBJECT-TYPE
                                       SYNTAX INTEGER (1..255)
                                       ACCESS read-write
                                       STATUS mandatory
                                       DESCRIPTION
                                       "Drycontact output toggle period in seconds for Manual Cycle action."
                                       ::= { sensorProbeDrycontactArrayPort1Entry 24 }

                                    sensorProbeDrycontactArrayPort1ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the drycontact output manualy"
                                       ::=  {  sensorProbeDrycontactArrayPort1Entry 25 }

                                    sensorProbeDrycontactArrayPort1OutputDescOn OBJECT-TYPE
                                       SYNTAX  DisplayString
                                       ACCESS  read-write
                                       STATUS  mandatory
                                       DESCRIPTION
                                       "Description of Drycontact output On"
                                       ::=  {  sensorProbeDrycontactArrayPort1Entry 26   }

                                    sensorProbeDrycontactArrayPort1OutputDescOff OBJECT-TYPE
                                       SYNTAX  DisplayString
                                       ACCESS  read-write
                                       STATUS  mandatory
                                       DESCRIPTION
                                       "Description of Drycontact output Off"
                                       ::=  {  sensorProbeDrycontactArrayPort1Entry 27   }

                                    sensorProbeDrycontactArrayPort1URL OBJECT-TYPE
                                       SYNTAX  DisplayString
                                       ACCESS  read-write
                                       STATUS  mandatory
                                       DESCRIPTION
                                       "Sersor URL link."
                                       ::=  {  sensorProbeDrycontactArrayPort1Entry 28   }

                                    sensorProbeDrycontactArrayPort1OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort1Entry 29   }

                                    sensorProbeDrycontactArrayPort1ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a drycontact output."
                                       ::=  {  sensorProbeDrycontactArrayPort1Entry 30  }

                           sensorProbeDrycontactArrayPort2 OBJECT IDENTIFIER ::= { sensorProbeDrycontactArraySensor 2  }
                              sensorProbeDrycontactArrayPort2Number OBJECT-TYPE
                                 SYNTAX INTEGER
                                 ACCESS read-only
                                 STATUS mandatory
                                 DESCRIPTION
                                 "The total number of port on the DrycontactArray."
                                 ::=  {  sensorProbeDrycontactArrayPort2 1   }

                              sensorProbeDrycontactArrayPort2Table OBJECT-TYPE
                                 SYNTAX  SEQUENCE OF SensorProbeDrycontactArrayPort2Entry
                                 ACCESS  not-accessible
                                 STATUS  mandatory
                                 DESCRIPTION
                                 "This table contains the data for every Drycontact Sensor in the SensorArray. Each row in the table contains data for a different Drycontact Sensor."
                                 ::=  {  sensorProbeDrycontactArrayPort2 2   }

                                 sensorProbeDrycontactArrayPort2Entry OBJECT-TYPE
                                    SYNTAX  SensorProbeDrycontactArrayPort2Entry
                                    ACCESS  not-accessible
                                    STATUS  mandatory
                                    DESCRIPTION
                                    "This is an entry in the sensorProbeDrycontactArrayPort2 Table"
                                    INDEX         { sensorProbeDrycontactArrayPort2Index }
                                    ::=  { sensorProbeDrycontactArrayPort2Table 1 }

                                    SensorProbeDrycontactArrayPort2Entry ::= SEQUENCE {
                                       sensorProbeDrycontactArrayPort2Index
                                          INTEGER,
                                       sensorProbeDrycontactArrayPort2Description
                                          DisplayString,
                                       sensorProbeDrycontactArrayPort2Status
                                          INTEGER,
                                       sensorProbeDrycontactArrayPort2Online
                                          INTEGER,
                                       sensorProbeDrycontactArrayPort2GoOnline
                                          INTEGER,
                                       sensorProbeDrycontactArrayPort2NormalState
                                          INTEGER,
                                       sensorProbeDrycontactArrayPort2Direction
                                          INTEGER,
                                       sensorProbeDrycontactArrayPort2ContTimeCritical
                                          INTEGER,
                                       sensorProbeDrycontactArrayPort2ContTimeNormal
                                          INTEGER,
                                       sensorProbeDrycontactArrayPort2ManualOutputCycleTime
                                          INTEGER,
                                       sensorProbeDrycontactArrayPort2ManualOutputAction
                                          INTEGER,
                                       sensorProbeDrycontactArrayPort2OutputDescOn
                                          DisplayString,
                                       sensorProbeDrycontactArrayPort2OutputDescOff
                                          DisplayString,
                                       sensorProbeDrycontactArrayPort2URL
                                          DisplayString,
                                       sensorProbeDrycontactArrayPort2OpenURL
                                          INTEGER,
                                       sensorProbeDrycontactArrayPort2ControlMode
                                          INTEGER
                                    }

                                    sensorProbeDrycontactArrayPort2Index OBJECT-TYPE
                                       SYNTAX  INTEGER (0..7)
                                       ACCESS  read-only
                                       STATUS  mandatory
                                       DESCRIPTION
                                       "A unique value for each sensor DrycontactArray port."
                                       ::=  {  sensorProbeDrycontactArrayPort2Entry 1   }

                                    sensorProbeDrycontactArrayPort2Description OBJECT-TYPE
                                       SYNTAX  DisplayString
                                       ACCESS  read-write
                                       STATUS  mandatory
                                       DESCRIPTION
                                       "A Description of this sensor DrycontactArray"
                                       ::=  {  sensorProbeDrycontactArrayPort2Entry 2   }

                                    sensorProbeDrycontactArrayPort2Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort2Entry 4  }

                                    sensorProbeDrycontactArrayPort2Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort2Entry 5  }

                                    sensorProbeDrycontactArrayPort2GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort2Entry 6  }

                                    sensorProbeDrycontactArrayPort2NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort2Entry 7  }

                                    sensorProbeDrycontactArrayPort2Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort2Entry 8  }

                                    sensorProbeDrycontactArrayPort2ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort2Entry 9   }

                                    sensorProbeDrycontactArrayPort2ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort2Entry 10   }

                                    sensorProbeDrycontactArrayPort2ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort2Entry 24 }

                                    sensorProbeDrycontactArrayPort2ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort2Entry 25 }

                                    sensorProbeDrycontactArrayPort2OutputDescOn OBJECT-TYPE
                                       SYNTAX  DisplayString
                                       ACCESS  read-write
                                       STATUS  mandatory
                                       DESCRIPTION
                                       "Description of Drycontact output On"
                                       ::=  {  sensorProbeDrycontactArrayPort2Entry 26   }

                                    sensorProbeDrycontactArrayPort2OutputDescOff OBJECT-TYPE
                                       SYNTAX  DisplayString
                                       ACCESS  read-write
                                       STATUS  mandatory
                                       DESCRIPTION
                                       "Description of Drycontact output Off"
                                       ::=  {  sensorProbeDrycontactArrayPort2Entry 27   }

                                    sensorProbeDrycontactArrayPort2URL OBJECT-TYPE
                                       SYNTAX  DisplayString
                                       ACCESS  read-write
                                       STATUS  mandatory
                                       DESCRIPTION
                                       "Sensor URL link"
                                       ::=  {  sensorProbeDrycontactArrayPort2Entry 28   }

                                    sensorProbeDrycontactArrayPort2OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort2Entry 29   }

                                    sensorProbeDrycontactArrayPort2ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort2Entry 30  }

                           sensorProbeDrycontactArrayPort3 OBJECT IDENTIFIER ::= { sensorProbeDrycontactArraySensor 3  }
                              sensorProbeDrycontactArrayPort3Number OBJECT-TYPE
                                 SYNTAX INTEGER
                                 ACCESS read-only
                                 STATUS mandatory
                                 DESCRIPTION
                                 "The total number of port on the DrycontactArray."
                                 ::=  {  sensorProbeDrycontactArrayPort3 1   }

                              sensorProbeDrycontactArrayPort3Table OBJECT-TYPE
                                 SYNTAX  SEQUENCE OF SensorProbeDrycontactArrayPort3Entry
                                 ACCESS  not-accessible
                                 STATUS  mandatory
                                 DESCRIPTION
                                 "This table contains the data for every Drycontact Sensor in the SensorArray. Each row in the table contains data for a different Drycontact Sensor."
                                 ::=  {  sensorProbeDrycontactArrayPort3 2   }

                                 sensorProbeDrycontactArrayPort3Entry OBJECT-TYPE
                                    SYNTAX  SensorProbeDrycontactArrayPort3Entry
                                    ACCESS  not-accessible
                                    STATUS  mandatory
                                    DESCRIPTION
                                    "This is an entry in the sensorProbeDrycontactArrayPort3 Table"
                                    INDEX         { sensorProbeDrycontactArrayPort3Index }
                                    ::=  { sensorProbeDrycontactArrayPort3Table 1 }

                                    SensorProbeDrycontactArrayPort3Entry ::= SEQUENCE {
                                       sensorProbeDrycontactArrayPort3Index
                                          INTEGER,
                                       sensorProbeDrycontactArrayPort3Description
                                          DisplayString,
                                       sensorProbeDrycontactArrayPort3Status
                                          INTEGER,
                                       sensorProbeDrycontactArrayPort3Online
                                          INTEGER,
                                       sensorProbeDrycontactArrayPort3GoOnline
                                          INTEGER,
                                       sensorProbeDrycontactArrayPort3NormalState
                                          INTEGER,
                                       sensorProbeDrycontactArrayPort3Direction
                                          INTEGER,
                                       sensorProbeDrycontactArrayPort3ContTimeCritical
                                          INTEGER,
                                       sensorProbeDrycontactArrayPort3ContTimeNormal
                                          INTEGER,
                                       sensorProbeDrycontactArrayPort3ManualOutputCycleTime
                                          INTEGER,
                                       sensorProbeDrycontactArrayPort3ManualOutputAction
                                          INTEGER,
                                       sensorProbeDrycontactArrayPort3OutputDescOn
                                          DisplayString,
                                       sensorProbeDrycontactArrayPort3OutputDescOff
                                          DisplayString,
                                       sensorProbeDrycontactArrayPort3URL
                                          DisplayString,
                                       sensorProbeDrycontactArrayPort3OpenURL
                                          INTEGER,
                                       sensorProbeDrycontactArrayPort3ControlMode
                                          INTEGER
                                    }

                                    sensorProbeDrycontactArrayPort3Index OBJECT-TYPE
                                       SYNTAX  INTEGER (0..7)
                                       ACCESS  read-only
                                       STATUS  mandatory
                                       DESCRIPTION
                                       "A unique value for each sensor DrycontactArray port."
                                       ::=  {  sensorProbeDrycontactArrayPort3Entry 1   }

                                    sensorProbeDrycontactArrayPort3Description OBJECT-TYPE
                                       SYNTAX  DisplayString
                                       ACCESS  read-write
                                       STATUS  mandatory
                                       DESCRIPTION
                                       "A Description of this sensor DrycontactArray"
                                       ::=  {  sensorProbeDrycontactArrayPort3Entry 2   }

                                    sensorProbeDrycontactArrayPort3Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort3Entry 4  }

                                    sensorProbeDrycontactArrayPort3Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort3Entry 5  }

                                    sensorProbeDrycontactArrayPort3GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort3Entry 6  }

                                    sensorProbeDrycontactArrayPort3NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort3Entry 7  }

                                    sensorProbeDrycontactArrayPort3Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort3Entry 8  }

                                    sensorProbeDrycontactArrayPort3ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort3Entry 9   }

                                    sensorProbeDrycontactArrayPort3ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort3Entry 10   }

                                    sensorProbeDrycontactArrayPort3ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort3Entry 24 }

                                    sensorProbeDrycontactArrayPort3ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort3Entry 25 }

                                    sensorProbeDrycontactArrayPort3OutputDescOn OBJECT-TYPE
                                       SYNTAX  DisplayString
                                       ACCESS  read-write
                                       STATUS  mandatory
                                       DESCRIPTION
                                       "Description of Drycontact output On"
                                       ::=  {  sensorProbeDrycontactArrayPort3Entry 26   }

                                    sensorProbeDrycontactArrayPort3OutputDescOff OBJECT-TYPE
                                       SYNTAX  DisplayString
                                       ACCESS  read-write
                                       STATUS  mandatory
                                       DESCRIPTION
                                       "Description of Drycontact output Off"
                                       ::=  {  sensorProbeDrycontactArrayPort3Entry 27   }

                                    sensorProbeDrycontactArrayPort3URL OBJECT-TYPE
                                       SYNTAX  DisplayString
                                       ACCESS  read-write
                                       STATUS  mandatory
                                       DESCRIPTION
                                       "Sensor URL link."
                                       ::=  {  sensorProbeDrycontactArrayPort3Entry 28   }

                                    sensorProbeDrycontactArrayPort3OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort3Entry 29   }

                                    sensorProbeDrycontactArrayPort3ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort3Entry 30  }

                           sensorProbeDrycontactArrayPort4 OBJECT IDENTIFIER ::= { sensorProbeDrycontactArraySensor 4  }
                              sensorProbeDrycontactArrayPort4Number OBJECT-TYPE
                                 SYNTAX INTEGER
                                 ACCESS read-only
                                 STATUS mandatory
                                 DESCRIPTION
                                 "The total number of port on the DrycontactArray."
                                 ::=  {  sensorProbeDrycontactArrayPort4 1   }

                              sensorProbeDrycontactArrayPort4Table OBJECT-TYPE
                                 SYNTAX  SEQUENCE OF SensorProbeDrycontactArrayPort4Entry
                                 ACCESS  not-accessible
                                 STATUS  mandatory
                                 DESCRIPTION
                                 "This table contains the data for every Drycontact Sensor in the SensorArray. Each row in the table contains data for a different Drycontact Sensor."
                                 ::=  {  sensorProbeDrycontactArrayPort4 2   }

                                 sensorProbeDrycontactArrayPort4Entry OBJECT-TYPE
                                    SYNTAX  SensorProbeDrycontactArrayPort4Entry
                                    ACCESS  not-accessible
                                    STATUS  mandatory
                                    DESCRIPTION
                                    "This is an entry in the sensorProbeDrycontactArrayPort4 Table"
                                    INDEX         { sensorProbeDrycontactArrayPort4Index }
                                    ::=  { sensorProbeDrycontactArrayPort4Table 1 }

                                    SensorProbeDrycontactArrayPort4Entry ::= SEQUENCE {
                                       sensorProbeDrycontactArrayPort4Index
                                          INTEGER,
                                       sensorProbeDrycontactArrayPort4Description
                                          DisplayString,
                                       sensorProbeDrycontactArrayPort4Status
                                          INTEGER,
                                       sensorProbeDrycontactArrayPort4Online
                                          INTEGER,
                                       sensorProbeDrycontactArrayPort4GoOnline
                                          INTEGER,
                                       sensorProbeDrycontactArrayPort4NormalState
                                          INTEGER,
                                       sensorProbeDrycontactArrayPort4Direction
                                          INTEGER,
                                       sensorProbeDrycontactArrayPort4ContTimeCritical
                                          INTEGER,
                                       sensorProbeDrycontactArrayPort4ContTimeNormal
                                          INTEGER,
                                       sensorProbeDrycontactArrayPort4ManualOutputCycleTime
                                          INTEGER,
                                       sensorProbeDrycontactArrayPort4ManualOutputAction
                                          INTEGER,
                                       sensorProbeDrycontactArrayPort4OutputDescOn
                                          DisplayString,
                                       sensorProbeDrycontactArrayPort4OutputDescOff
                                          DisplayString,
                                       sensorProbeDrycontactArrayPort4URL
                                          DisplayString,
                                       sensorProbeDrycontactArrayPort4OpenURL
                                          INTEGER,
                                       sensorProbeDrycontactArrayPort4ControlMode
                                          INTEGER
                                    }

                                    sensorProbeDrycontactArrayPort4Index OBJECT-TYPE
                                       SYNTAX  INTEGER (0..7)
                                       ACCESS  read-only
                                       STATUS  mandatory
                                       DESCRIPTION
                                       "A unique value for each sensor DrycontactArray port."
                                       ::=  {  sensorProbeDrycontactArrayPort4Entry 1   }

                                    sensorProbeDrycontactArrayPort4Description OBJECT-TYPE
                                       SYNTAX  DisplayString
                                       ACCESS  read-write
                                       STATUS  mandatory
                                       DESCRIPTION
                                       "A Description of this sensor DrycontactArray"
                                       ::=  {  sensorProbeDrycontactArrayPort4Entry 2   }

                                    sensorProbeDrycontactArrayPort4Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort4Entry 4  }

                                    sensorProbeDrycontactArrayPort4Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort4Entry 5  }

                                    sensorProbeDrycontactArrayPort4GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort4Entry 6  }

                                    sensorProbeDrycontactArrayPort4NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort4Entry 7  }

                                    sensorProbeDrycontactArrayPort4Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort4Entry 8  }

                                    sensorProbeDrycontactArrayPort4ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort4Entry 9   }

                                    sensorProbeDrycontactArrayPort4ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort4Entry 10   }

                                    sensorProbeDrycontactArrayPort4ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort4Entry 24 }

                                    sensorProbeDrycontactArrayPort4ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort4Entry 25 }

                                    sensorProbeDrycontactArrayPort4OutputDescOn OBJECT-TYPE
                                       SYNTAX  DisplayString
                                       ACCESS  read-write
                                       STATUS  mandatory
                                       DESCRIPTION
                                       "Description of Drycontact output On"
                                       ::=  {  sensorProbeDrycontactArrayPort4Entry 26   }

                                    sensorProbeDrycontactArrayPort4OutputDescOff OBJECT-TYPE
                                       SYNTAX  DisplayString
                                       ACCESS  read-write
                                       STATUS  mandatory
                                       DESCRIPTION
                                       "Description of Drycontact output Off"
                                       ::=  {  sensorProbeDrycontactArrayPort4Entry 27   }

                                    sensorProbeDrycontactArrayPort4URL OBJECT-TYPE
                                       SYNTAX  DisplayString
                                       ACCESS  read-write
                                       STATUS  mandatory
                                       DESCRIPTION
                                       "Sensor URL link."
                                       ::=  {  sensorProbeDrycontactArrayPort4Entry 28   }

                                    sensorProbeDrycontactArrayPort4OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort4Entry 29   }

                                    sensorProbeDrycontactArrayPort4ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort4Entry 30  }

                           sensorProbeDrycontactArrayPort5 OBJECT IDENTIFIER ::= { sensorProbeDrycontactArraySensor 5  }
                              sensorProbeDrycontactArrayPort5Number OBJECT-TYPE
                                 SYNTAX INTEGER
                                 ACCESS read-only
                                 STATUS mandatory
                                 DESCRIPTION
                                 "The total number of port on the DrycontactArray."
                                 ::=  {  sensorProbeDrycontactArrayPort5 1   }

                              sensorProbeDrycontactArrayPort5Table OBJECT-TYPE
                                 SYNTAX  SEQUENCE OF SensorProbeDrycontactArrayPort5Entry
                                 ACCESS  not-accessible
                                 STATUS  mandatory
                                 DESCRIPTION
                                 "This table contains the data for every Drycontact Sensor in the SensorArray. Each row in the table contains data for a different Drycontact Sensor."
                                 ::=  {  sensorProbeDrycontactArrayPort5 2   }

                                 sensorProbeDrycontactArrayPort5Entry OBJECT-TYPE
                                    SYNTAX  SensorProbeDrycontactArrayPort5Entry
                                    ACCESS  not-accessible
                                    STATUS  mandatory
                                    DESCRIPTION
                                    "This is an entry in the sensorProbeDrycontactArrayPort5 Table"
                                    INDEX         { sensorProbeDrycontactArrayPort5Index }
                                    ::=  { sensorProbeDrycontactArrayPort5Table 1 }

                                    SensorProbeDrycontactArrayPort5Entry ::= SEQUENCE {
                                       sensorProbeDrycontactArrayPort5Index
                                          INTEGER,
                                       sensorProbeDrycontactArrayPort5Description
                                          DisplayString,
                                       sensorProbeDrycontactArrayPort5Status
                                          INTEGER,
                                       sensorProbeDrycontactArrayPort5Online
                                          INTEGER,
                                       sensorProbeDrycontactArrayPort5GoOnline
                                          INTEGER,
                                       sensorProbeDrycontactArrayPort5NormalState
                                          INTEGER,
                                       sensorProbeDrycontactArrayPort5Direction
                                          INTEGER,
                                       sensorProbeDrycontactArrayPort5ContTimeCritical
                                          INTEGER,
                                       sensorProbeDrycontactArrayPort5ContTimeNormal
                                          INTEGER,
                                       sensorProbeDrycontactArrayPort5ManualOutputCycleTime
                                          INTEGER,
                                       sensorProbeDrycontactArrayPort5ManualOutputAction
                                          INTEGER,
                                       sensorProbeDrycontactArrayPort5OutputDescOn
                                          DisplayString,
                                       sensorProbeDrycontactArrayPort5OutputDescOff
                                          DisplayString,
                                       sensorProbeDrycontactArrayPort5URL
                                          DisplayString,
                                       sensorProbeDrycontactArrayPort5OpenURL
                                          INTEGER,
                                       sensorProbeDrycontactArrayPort5ControlMode
                                          INTEGER
                                    }

                                    sensorProbeDrycontactArrayPort5Index OBJECT-TYPE
                                       SYNTAX  INTEGER (0..7)
                                       ACCESS  read-only
                                       STATUS  mandatory
                                       DESCRIPTION
                                       "A unique value for each sensor DrycontactArray port."
                                       ::=  {  sensorProbeDrycontactArrayPort5Entry 1   }

                                    sensorProbeDrycontactArrayPort5Description OBJECT-TYPE
                                       SYNTAX  DisplayString
                                       ACCESS  read-write
                                       STATUS  mandatory
                                       DESCRIPTION
                                       "A Description of this sensor DrycontactArray"
                                       ::=  {  sensorProbeDrycontactArrayPort5Entry 2   }

                                    sensorProbeDrycontactArrayPort5Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort5Entry 4  }

                                    sensorProbeDrycontactArrayPort5Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort5Entry 5  }

                                    sensorProbeDrycontactArrayPort5GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort5Entry 6  }

                                    sensorProbeDrycontactArrayPort5NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort5Entry 7  }

                                    sensorProbeDrycontactArrayPort5Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort5Entry 8  }

                                    sensorProbeDrycontactArrayPort5ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort5Entry 9   }

                                    sensorProbeDrycontactArrayPort5ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort5Entry 10   }

                                    sensorProbeDrycontactArrayPort5ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort5Entry 24 }

                                    sensorProbeDrycontactArrayPort5ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort5Entry 25 }

                                    sensorProbeDrycontactArrayPort5OutputDescOn OBJECT-TYPE
                                       SYNTAX  DisplayString
                                       ACCESS  read-write
                                       STATUS  mandatory
                                       DESCRIPTION
                                       "Description of Drycontact output On"
                                       ::=  {  sensorProbeDrycontactArrayPort5Entry 26   }

                                    sensorProbeDrycontactArrayPort5OutputDescOff OBJECT-TYPE
                                       SYNTAX  DisplayString
                                       ACCESS  read-write
                                       STATUS  mandatory
                                       DESCRIPTION
                                       "Description of Drycontact output Off"
                                       ::=  {  sensorProbeDrycontactArrayPort5Entry 27   }

                                    sensorProbeDrycontactArrayPort5URL OBJECT-TYPE
                                       SYNTAX  DisplayString
                                       ACCESS  read-write
                                       STATUS  mandatory
                                       DESCRIPTION
                                       "Sensor URL link."
                                       ::=  {  sensorProbeDrycontactArrayPort5Entry 28   }

                                    sensorProbeDrycontactArrayPort5OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort5Entry 29   }

                                    sensorProbeDrycontactArrayPort5ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort5Entry 30  }

                           sensorProbeDrycontactArrayPort6 OBJECT IDENTIFIER ::= { sensorProbeDrycontactArraySensor 6  }
                              sensorProbeDrycontactArrayPort6Number OBJECT-TYPE
                                 SYNTAX INTEGER
                                 ACCESS read-only
                                 STATUS mandatory
                                 DESCRIPTION
                                 "The total number of port on the DrycontactArray."
                                 ::=  {  sensorProbeDrycontactArrayPort6 1   }

                              sensorProbeDrycontactArrayPort6Table OBJECT-TYPE
                                 SYNTAX  SEQUENCE OF SensorProbeDrycontactArrayPort6Entry
                                 ACCESS  not-accessible
                                 STATUS  mandatory
                                 DESCRIPTION
                                 "This table contains the data for every Drycontact Sensor in the SensorArray. Each row in the table contains data for a different Drycontact Sensor."
                                 ::=  {  sensorProbeDrycontactArrayPort6 2   }

                                 sensorProbeDrycontactArrayPort6Entry OBJECT-TYPE
                                    SYNTAX  SensorProbeDrycontactArrayPort6Entry
                                    ACCESS  not-accessible
                                    STATUS  mandatory
                                    DESCRIPTION
                                    "This is an entry in the sensorProbeDrycontactArrayPort6 Table"
                                    INDEX         { sensorProbeDrycontactArrayPort6Index }
                                    ::=  { sensorProbeDrycontactArrayPort6Table 1 }

                                    SensorProbeDrycontactArrayPort6Entry ::= SEQUENCE {
                                       sensorProbeDrycontactArrayPort6Index
                                          INTEGER,
                                       sensorProbeDrycontactArrayPort6Description
                                          DisplayString,
                                       sensorProbeDrycontactArrayPort6Status
                                          INTEGER,
                                       sensorProbeDrycontactArrayPort6Online
                                          INTEGER,
                                       sensorProbeDrycontactArrayPort6GoOnline
                                          INTEGER,
                                       sensorProbeDrycontactArrayPort6NormalState
                                          INTEGER,
                                       sensorProbeDrycontactArrayPort6Direction
                                          INTEGER,
                                       sensorProbeDrycontactArrayPort6ContTimeCritical
                                          INTEGER,
                                       sensorProbeDrycontactArrayPort6ContTimeNormal
                                          INTEGER,
                                       sensorProbeDrycontactArrayPort6ManualOutputCycleTime
                                          INTEGER,
                                       sensorProbeDrycontactArrayPort6ManualOutputAction
                                          INTEGER,
                                       sensorProbeDrycontactArrayPort6OutputDescOn
                                          DisplayString,
                                       sensorProbeDrycontactArrayPort6OutputDescOff
                                          DisplayString,
                                       sensorProbeDrycontactArrayPort6URL
                                          DisplayString,
                                       sensorProbeDrycontactArrayPort6OpenURL
                                          INTEGER,
                                       sensorProbeDrycontactArrayPort6ControlMode
                                          INTEGER
                                    }

                                    sensorProbeDrycontactArrayPort6Index OBJECT-TYPE
                                       SYNTAX  INTEGER (0..7)
                                       ACCESS  read-only
                                       STATUS  mandatory
                                       DESCRIPTION
                                       "A unique value for each sensor DrycontactArray port."
                                       ::=  {  sensorProbeDrycontactArrayPort6Entry 1   }

                                    sensorProbeDrycontactArrayPort6Description OBJECT-TYPE
                                       SYNTAX  DisplayString
                                       ACCESS  read-write
                                       STATUS  mandatory
                                       DESCRIPTION
                                       "A Description of this sensor DrycontactArray"
                                       ::=  {  sensorProbeDrycontactArrayPort6Entry 2   }

                                    sensorProbeDrycontactArrayPort6Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort6Entry 4  }

                                    sensorProbeDrycontactArrayPort6Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort6Entry 5  }

                                    sensorProbeDrycontactArrayPort6GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort6Entry 6  }

                                    sensorProbeDrycontactArrayPort6NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort6Entry 7  }

                                    sensorProbeDrycontactArrayPort6Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort6Entry 8  }

                                    sensorProbeDrycontactArrayPort6ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort6Entry 9   }

                                    sensorProbeDrycontactArrayPort6ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort6Entry 10   }

                                    sensorProbeDrycontactArrayPort6ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort6Entry 24 }

                                    sensorProbeDrycontactArrayPort6ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort6Entry 25 }

                                    sensorProbeDrycontactArrayPort6OutputDescOn OBJECT-TYPE
                                       SYNTAX  DisplayString
                                       ACCESS  read-write
                                       STATUS  mandatory
                                       DESCRIPTION
                                       "Description of Drycontact output On"
                                       ::=  {  sensorProbeDrycontactArrayPort6Entry 26   }

                                    sensorProbeDrycontactArrayPort6OutputDescOff OBJECT-TYPE
                                       SYNTAX  DisplayString
                                       ACCESS  read-write
                                       STATUS  mandatory
                                       DESCRIPTION
                                       "Description of Drycontact output Off"
                                       ::=  {  sensorProbeDrycontactArrayPort6Entry 27   }

                                    sensorProbeDrycontactArrayPort6URL OBJECT-TYPE
                                       SYNTAX  DisplayString
                                       ACCESS  read-write
                                       STATUS  mandatory
                                       DESCRIPTION
                                       "Sensor URL link."
                                       ::=  {  sensorProbeDrycontactArrayPort6Entry 28   }

                                    sensorProbeDrycontactArrayPort6OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort6Entry 29   }

                                    sensorProbeDrycontactArrayPort6ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort6Entry 30  }

                           sensorProbeDrycontactArrayPort7 OBJECT IDENTIFIER ::= { sensorProbeDrycontactArraySensor 7  }
                              sensorProbeDrycontactArrayPort7Number OBJECT-TYPE
                                 SYNTAX INTEGER
                                 ACCESS read-only
                                 STATUS mandatory
                                 DESCRIPTION
                                 "The total number of port on the DrycontactArray."
                                 ::=  {  sensorProbeDrycontactArrayPort7 1   }

                              sensorProbeDrycontactArrayPort7Table OBJECT-TYPE
                                 SYNTAX  SEQUENCE OF SensorProbeDrycontactArrayPort7Entry
                                 ACCESS  not-accessible
                                 STATUS  mandatory
                                 DESCRIPTION
                                 "This table contains the data for every Drycontact Sensor in the SensorArray. Each row in the table contains data for a different Drycontact Sensor."
                                 ::=  {  sensorProbeDrycontactArrayPort7 2   }

                                 sensorProbeDrycontactArrayPort7Entry OBJECT-TYPE
                                    SYNTAX  SensorProbeDrycontactArrayPort7Entry
                                    ACCESS  not-accessible
                                    STATUS  mandatory
                                    DESCRIPTION
                                    "This is an entry in the sensorProbeDrycontactArrayPort7 Table"
                                    INDEX         { sensorProbeDrycontactArrayPort7Index }
                                    ::=  { sensorProbeDrycontactArrayPort7Table 1 }

                                    SensorProbeDrycontactArrayPort7Entry ::= SEQUENCE {
                                       sensorProbeDrycontactArrayPort7Index
                                          INTEGER,
                                       sensorProbeDrycontactArrayPort7Description
                                          DisplayString,
                                       sensorProbeDrycontactArrayPort7Status
                                          INTEGER,
                                       sensorProbeDrycontactArrayPort7Online
                                          INTEGER,
                                       sensorProbeDrycontactArrayPort7GoOnline
                                          INTEGER,
                                       sensorProbeDrycontactArrayPort7NormalState
                                          INTEGER,
                                       sensorProbeDrycontactArrayPort7Direction
                                          INTEGER,
                                       sensorProbeDrycontactArrayPort7ContTimeCritical
                                          INTEGER,
                                       sensorProbeDrycontactArrayPort7ContTimeNormal
                                          INTEGER,
                                       sensorProbeDrycontactArrayPort7ManualOutputCycleTime
                                          INTEGER,
                                       sensorProbeDrycontactArrayPort7ManualOutputAction
                                          INTEGER,
                                       sensorProbeDrycontactArrayPort7OutputDescOn
                                          DisplayString,
                                       sensorProbeDrycontactArrayPort7OutputDescOff
                                          DisplayString,
                                       sensorProbeDrycontactArrayPort7URL
                                          DisplayString,
                                       sensorProbeDrycontactArrayPort7OpenURL
                                          INTEGER,
                                       sensorProbeDrycontactArrayPort7ControlMode
                                          INTEGER
                                    }

                                    sensorProbeDrycontactArrayPort7Index OBJECT-TYPE
                                       SYNTAX  INTEGER (0..7)
                                       ACCESS  read-only
                                       STATUS  mandatory
                                       DESCRIPTION
                                       "A unique value for each sensor DrycontactArray port."
                                       ::=  {  sensorProbeDrycontactArrayPort7Entry 1   }

                                    sensorProbeDrycontactArrayPort7Description OBJECT-TYPE
                                       SYNTAX  DisplayString
                                       ACCESS  read-write
                                       STATUS  mandatory
                                       DESCRIPTION
                                       "A Description of this sensor DrycontactArray"
                                       ::=  {  sensorProbeDrycontactArrayPort7Entry 2   }

                                    sensorProbeDrycontactArrayPort7Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort7Entry 4  }

                                    sensorProbeDrycontactArrayPort7Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort7Entry 5  }

                                    sensorProbeDrycontactArrayPort7GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort7Entry 6  }

                                    sensorProbeDrycontactArrayPort7NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort7Entry 7  }

                                    sensorProbeDrycontactArrayPort7Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort7Entry 8  }

                                    sensorProbeDrycontactArrayPort7ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort7Entry 9   }

                                    sensorProbeDrycontactArrayPort7ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort7Entry 10   }

                                    sensorProbeDrycontactArrayPort7ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort7Entry 24 }

                                    sensorProbeDrycontactArrayPort7ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort7Entry 25 }

                                    sensorProbeDrycontactArrayPort7OutputDescOn OBJECT-TYPE
                                       SYNTAX  DisplayString
                                       ACCESS  read-write
                                       STATUS  mandatory
                                       DESCRIPTION
                                       "Description of Drycontact output On"
                                       ::=  {  sensorProbeDrycontactArrayPort7Entry 26   }

                                    sensorProbeDrycontactArrayPort7OutputDescOff OBJECT-TYPE
                                       SYNTAX  DisplayString
                                       ACCESS  read-write
                                       STATUS  mandatory
                                       DESCRIPTION
                                       "Description of Drycontact output Off"
                                       ::=  {  sensorProbeDrycontactArrayPort7Entry 27   }

                                    sensorProbeDrycontactArrayPort7URL OBJECT-TYPE
                                       SYNTAX  DisplayString
                                       ACCESS  read-write
                                       STATUS  mandatory
                                       DESCRIPTION
                                       "Sensor URL link."
                                       ::=  {  sensorProbeDrycontactArrayPort7Entry 28   }

                                    sensorProbeDrycontactArrayPort7OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort7Entry 29   }

                                    sensorProbeDrycontactArrayPort7ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort7Entry 30  }

                           sensorProbeDrycontactArrayPort8 OBJECT IDENTIFIER ::= { sensorProbeDrycontactArraySensor 8  }
                              sensorProbeDrycontactArrayPort8Number OBJECT-TYPE
                                 SYNTAX INTEGER
                                 ACCESS read-only
                                 STATUS mandatory
                                 DESCRIPTION
                                 "The total number of port on the DrycontactArray."
                                 ::=  {  sensorProbeDrycontactArrayPort8 1   }

                              sensorProbeDrycontactArrayPort8Table OBJECT-TYPE
                                 SYNTAX  SEQUENCE OF SensorProbeDrycontactArrayPort8Entry
                                 ACCESS  not-accessible
                                 STATUS  mandatory
                                 DESCRIPTION
                                 "This table contains the data for every Drycontact Sensor in the SensorArray. Each row in the table contains data for a different Drycontact Sensor."
                                 ::=  {  sensorProbeDrycontactArrayPort8 2   }

                                 sensorProbeDrycontactArrayPort8Entry OBJECT-TYPE
                                    SYNTAX  SensorProbeDrycontactArrayPort8Entry
                                    ACCESS  not-accessible
                                    STATUS  mandatory
                                    DESCRIPTION
                                    "This is an entry in the sensorProbeDrycontactArrayPort8 Table"
                                    INDEX         { sensorProbeDrycontactArrayPort8Index }
                                    ::=  { sensorProbeDrycontactArrayPort8Table 1 }

                                    SensorProbeDrycontactArrayPort8Entry ::= SEQUENCE {
                                       sensorProbeDrycontactArrayPort8Index
                                          INTEGER,
                                       sensorProbeDrycontactArrayPort8Description
                                          DisplayString,
                                       sensorProbeDrycontactArrayPort8Status
                                          INTEGER,
                                       sensorProbeDrycontactArrayPort8Online
                                          INTEGER,
                                       sensorProbeDrycontactArrayPort8GoOnline
                                          INTEGER,
                                       sensorProbeDrycontactArrayPort8NormalState
                                          INTEGER,
                                       sensorProbeDrycontactArrayPort8Direction
                                          INTEGER,
                                       sensorProbeDrycontactArrayPort8ContTimeCritical
                                          INTEGER,
                                       sensorProbeDrycontactArrayPort8ContTimeNormal
                                          INTEGER,
                                       sensorProbeDrycontactArrayPort8ManualOutputCycleTime
                                          INTEGER,
                                       sensorProbeDrycontactArrayPort8ManualOutputAction
                                          INTEGER,
                                       sensorProbeDrycontactArrayPort8OutputDescOn
                                          DisplayString,
                                       sensorProbeDrycontactArrayPort8OutputDescOff
                                          DisplayString,
                                       sensorProbeDrycontactArrayPort8URL
                                          DisplayString,
                                       sensorProbeDrycontactArrayPort8OpenURL
                                          INTEGER,
                                       sensorProbeDrycontactArrayPort8ControlMode
                                          INTEGER
                                    }

                                    sensorProbeDrycontactArrayPort8Index OBJECT-TYPE
                                       SYNTAX  INTEGER (0..7)
                                       ACCESS  read-only
                                       STATUS  mandatory
                                       DESCRIPTION
                                       "A unique value for each sensor DrycontactArray port."
                                       ::=  {  sensorProbeDrycontactArrayPort8Entry 1   }

                                    sensorProbeDrycontactArrayPort8Description OBJECT-TYPE
                                       SYNTAX  DisplayString
                                       ACCESS  read-write
                                       STATUS  mandatory
                                       DESCRIPTION
                                       "A Description of this sensor DrycontactArray"
                                       ::=  {  sensorProbeDrycontactArrayPort8Entry 2   }

                                    sensorProbeDrycontactArrayPort8Status OBJECT-TYPE
                                       SYNTAX  INTEGER {
                                          noStatus(1),
                                          normal(2),
                                          highCritical(4),
                                          lowCritical(6),
                                          sensorError(7),
                                          relayOn(8),
                                          relayOff(9)
                                       }
                                       ACCESS  read-only
                                       STATUS  mandatory
                                       DESCRIPTION
                                       "The current status of this Sensor"
                                       ::=  {  sensorProbeDrycontactArrayPort8Entry 4  }

                                    sensorProbeDrycontactArrayPort8Online OBJECT-TYPE
                                       SYNTAX  INTEGER {
                                          online(1),
                                          offline(2)
                                       }
                                       ACCESS  read-only
                                       STATUS  mandatory
                                       DESCRIPTION
                                       "If this Sensor is currently online"
                                       ::=  {  sensorProbeDrycontactArrayPort8Entry 5  }

                                    sensorProbeDrycontactArrayPort8GoOnline OBJECT-TYPE
                                       SYNTAX  INTEGER {
                                          goOnline(1),
                                          goOffline(2)
                                       }
                                       ACCESS  read-write
                                       STATUS  mandatory
                                       DESCRIPTION
                                       "To put online enter a 1, to take offline enter a 2"
                                       ::=  {  sensorProbeDrycontactArrayPort8Entry 6  }

                                    sensorProbeDrycontactArrayPort8NormalState OBJECT-TYPE
                                       SYNTAX  INTEGER {
                                          closed(0),
                                          open(1)
                                       }
                                       ACCESS  read-write
                                       STATUS  mandatory
                                       DESCRIPTION
                                       "The normal state of DrycontactArray"
                                       ::=  {  sensorProbeDrycontactArrayPort8Entry 7  }

                                    sensorProbeDrycontactArrayPort8Direction OBJECT-TYPE
                                       SYNTAX  INTEGER {
                                          input(0),
                                          output(1)
                                       }
                                       ACCESS  read-write
                                       STATUS  mandatory
                                       DESCRIPTION
                                       "To set a drycontact to input enter 0. To set a switch to output enter 1"
                                       ::=  {  sensorProbeDrycontactArrayPort8Entry 8  }

                                    sensorProbeDrycontactArrayPort8ContTimeCritical OBJECT-TYPE
                                       SYNTAX  INTEGER (0..65534)
                                       ACCESS  read-write
                                       STATUS  mandatory
                                       DESCRIPTION
                                       "Continuous time for this sensor to be in Critical before accepting new Status."
                                       ::=  {  sensorProbeDrycontactArrayPort8Entry 9   }

                                    sensorProbeDrycontactArrayPort8ContTimeNormal OBJECT-TYPE
                                       SYNTAX INTEGER (0..65535)
                                       ACCESS read-write
                                       STATUS mandatory
                                       DESCRIPTION
                                       "Continuous time for this sensor to be in Normal before accepting new Status."
                                       ::=  {  sensorProbeDrycontactArrayPort8Entry 10   }

                                    sensorProbeDrycontactArrayPort8ManualOutputCycleTime OBJECT-TYPE
                                       SYNTAX INTEGER (1..255)
                                       ACCESS read-write
                                       STATUS mandatory
                                       DESCRIPTION
                                       "Drycontact toggle period in seconds for Manual Cycle action."
                                       ::= { sensorProbeDrycontactArrayPort8Entry 24 }

                                    sensorProbeDrycontactArrayPort8ManualOutputAction OBJECT-TYPE
                                       SYNTAX INTEGER {
                                          allow-sensor-control(1),
                                          turn-on(3),
                                          turn-off(4),
                                          cycle-Off-On-Off(7),
                                          cycle-On-Off-On(8)
                                       }
                                       ACCESS read-write
                                       STATUS mandatory
                                       DESCRIPTION
                                       "Control the Drycontact output manualy"
                                       ::= { sensorProbeDrycontactArrayPort8Entry 25 }

                                    sensorProbeDrycontactArrayPort8OutputDescOn OBJECT-TYPE
                                       SYNTAX  DisplayString
                                       ACCESS  read-write
                                       STATUS  mandatory
                                       DESCRIPTION
                                       "Description of Drycontact output On"
                                       ::=  {  sensorProbeDrycontactArrayPort8Entry 26   }

                                    sensorProbeDrycontactArrayPort8OutputDescOff OBJECT-TYPE
                                       SYNTAX  DisplayString
                                       ACCESS  read-write
                                       STATUS  mandatory
                                       DESCRIPTION
                                       "Description of Drycontact output Off"
                                       ::=  {  sensorProbeDrycontactArrayPort8Entry 27   }

                                    sensorProbeDrycontactArrayPort8URL OBJECT-TYPE
                                       SYNTAX  DisplayString
                                       ACCESS  read-write
                                       STATUS  mandatory
                                       DESCRIPTION
                                       "Sensor URL link."
                                       ::=  {  sensorProbeDrycontactArrayPort8Entry 28   }

                                    sensorProbeDrycontactArrayPort8OpenURL OBJECT-TYPE
                                       SYNTAX  INTEGER {
                                          cur-window(0),
                                          new-window(2)
                                       }
                                       ACCESS  read-write
                                       STATUS  mandatory
                                       DESCRIPTION
                                       "Open URL in this browser or open in a new window."
                                       ::=  {  sensorProbeDrycontactArrayPort8Entry 29   }

                                    sensorProbeDrycontactArrayPort8ControlMode OBJECT-TYPE
                                       SYNTAX  INTEGER {
                                          manual-control(0),
                                          notification-control(1),
                                          time-control(2),
                                          thermostat-control(3)
                                       }
                                       ACCESS  read-write
                                       STATUS  mandatory
                                       DESCRIPTION
                                       "Control Mode used for selecting the mode to control a Drycontact output."
                                       ::=  {  sensorProbeDrycontactArrayPort8Entry 30  }

               sensorProbeDebug OBJECT-TYPE
                  SYNTAX  INTEGER {
                     off(0),
                     on(1)
                  }
                  ACCESS  read-write
                  STATUS  mandatory
                  DESCRIPTION
                  "SP only: Turn on or off debug messages"
                  ::=  {  sensorProbeEntry 20  }

               sensorProbeTrapResend OBJECT-TYPE
                  SYNTAX  INTEGER {
                     off(0),
                     on(1)
                  }
                  ACCESS  read-write
                  STATUS  mandatory
                  DESCRIPTION
                  "If traps for Warning or Error should be resent. Traps for Normal status are sent once"
                  ::=  {  sensorProbeEntry 22  }

               sensorProbeTrapResendInterval OBJECT-TYPE
                  SYNTAX  INTEGER
                  ACCESS  read-write
                  STATUS  mandatory
                  DESCRIPTION
                  "How often to resend mail or Traps. Enter the number of seconds from 15 to 65535. Mail for WARNING and ERROR are resent at this interval. Traps for Normal status are sent once"
                  ::=  {  sensorProbeEntry 23  }

               sensorProbeSendTraps OBJECT-TYPE
                  SYNTAX  INTEGER {
                     on(1),
                     off(2)
                  }
                  ACCESS  read-write
                  STATUS  mandatory
                  DESCRIPTION
                  "Turn on or off the sending of traps"
                  ::=  {  sensorProbeEntry 24  }

               sensorProbeTrapDestination OBJECT-TYPE
                  SYNTAX  IpAddress
                  ACCESS  read-write
                  STATUS  mandatory
                  DESCRIPTION
                  "The IP address of the trap destination"
                  ::=  {  sensorProbeEntry 25  }

               sensorProbeTrapCommunity OBJECT-TYPE
                  SYNTAX  DisplayString
                  ACCESS  read-write
                  STATUS  mandatory
                  DESCRIPTION
                  "The community string of the trap destination"
                  ::=  {  sensorProbeEntry 26  }

               sensorProbeDefaultGateway OBJECT-TYPE
                  SYNTAX  IpAddress
                  ACCESS  read-write
                  STATUS  mandatory
                  DESCRIPTION
                  "If the destination is on another network, enter the IP address of the router"
                  ::=  {  sensorProbeEntry 27  }

               sensorProbeSubnetMask OBJECT-TYPE
                  SYNTAX  IpAddress
                  ACCESS  read-write
                  STATUS  mandatory
                  DESCRIPTION
                  "If the trap destination uses the default gateway"
                  ::=  {  sensorProbeEntry 28  }

               sensorProbeRouteAdd OBJECT-TYPE
                  SYNTAX  DisplayString
                  ACCESS  read-write
                  STATUS  mandatory
                  DESCRIPTION
                  "SP only: Up to 4, Manual additions to the routing table in the form, Network IP Address, Netmask, Gateway IP address"
                  ::=  {  sensorProbeEntry 29  }


               sensorProbeSendMail OBJECT-TYPE
                  SYNTAX  INTEGER {
                     on(1),
                     off(2)
                  }
                  ACCESS  read-write
                  STATUS  mandatory
                  DESCRIPTION
                  "Turn on or off the sending of Mail"
                  ::=  {  sensorProbeEntry 30  }

               sensorProbeMailRecpt OBJECT-TYPE
                  SYNTAX  DisplayString
                  ACCESS  read-write
                  STATUS  mandatory
                  DESCRIPTION
                  "The email address of the Recipient"
                  ::=  {  sensorProbeEntry 31  }

               sensorProbeMailFrom OBJECT-TYPE
                  SYNTAX  DisplayString
                  ACCESS  read-write
                  STATUS  mandatory
                  DESCRIPTION
                  "The email address of the Sender"
                  ::=  {  sensorProbeEntry 32  }

               sensorProbeMailSMTP OBJECT-TYPE
                  SYNTAX  DisplayString
                  ACCESS  read-write
                  STATUS  mandatory
                  DESCRIPTION
                  "The Address of the SMTP server"
                  ::=  {  sensorProbeEntry 33  }

               sensorProbeMailJpgInline OBJECT-TYPE
                  SYNTAX  INTEGER {
                     inline(1),
                     link(2)
                  }
                  ACCESS  read-write
                  STATUS  mandatory
                  DESCRIPTION
                  "If the jpg for this event is sent as an http link or is included with mail as an attachment"
                  ::=  {  sensorProbeEntry 34  }

               sensorProbeMailResendInterval OBJECT-TYPE
                  SYNTAX  INTEGER
                  ACCESS  read-write
                  STATUS  mandatory
                  DESCRIPTION
                  "How often to resend mail or Traps. Enter the number of seconds from 10 to 60. Mail for WARNING and ERROR are resent at this interval. Mail for Normal status are sent once"
                  ::=  {  sensorProbeEntry 36  }

               sensorProbeMailMaxResend OBJECT-TYPE
                  SYNTAX  INTEGER
                  ACCESS  read-write
                  STATUS  mandatory
                  DESCRIPTION
                  "The maximum number of times to resend mail. If set to 0 only send once. The maximum value is 5"
                  ::=  {  sensorProbeEntry 37  }

               sensorProbeMailLastStatus OBJECT-TYPE
                  SYNTAX  DisplayString
                  ACCESS  read-only
                  STATUS  mandatory
                  DESCRIPTION
                  "The status of the most recent attempt to send an email"
                  ::=  {  sensorProbeEntry 39  }

               sensorProbeSupportMailRcpt OBJECT-TYPE
                  SYNTAX  DisplayString
                  ACCESS  read-write
                  STATUS  mandatory
                  DESCRIPTION
                  "SP8L only: E-Mail address of support"
                  ::=  {  sensorProbeEntry 40  }

               sensorProbeCameraServerTable OBJECT-TYPE
                  SYNTAX  SEQUENCE OF SensorProbeCameraServerEntry
                  ACCESS  not-accessible
                  STATUS  mandatory
                  DESCRIPTION
                  "CP8 Only: This table contains the Camera Server features, This allows the sensorProbe to connect to a sensorProbe"
                  ::=  {  sensorProbeEntry 42   }

               sensorProbeCameraServerEntry OBJECT-TYPE
                  SYNTAX  SensorProbeCameraServerEntry
                  ACCESS  not-accessible
                  STATUS  mandatory
                  DESCRIPTION
                  "This is an entry in the sensorProbeCameraServerEntry Table"
                  INDEX         { sensorProbeCameraServerIndex }
                  ::=  { sensorProbeCameraServerTable 1 }

                  SensorProbeCameraServerEntry ::= SEQUENCE {
                     sensorProbeCameraServerClientOnline
                        INTEGER,
                     sensorProbeCameraServerClientGoOnline
                        INTEGER,
                     sensorProbeCameraServerClientIP
                        IpAddress,
                     sensorProbeCameraServerClientSetPassword
                        DisplayString,
                     sensorProbeCameraServerIndex
                          INTEGER,
                     sensorProbeJavaTimeOut
                          INTEGER,
                     sensorProbeJpegQualityFactor
                          INTEGER,
                     sensorProbeCameraDescription
                          DisplayString,
                     sensorProbeCameraRotate
                          INTEGER,
                     sensorProbeCameraResolution
                          INTEGER,
                     sensorProbePTZRotateRelative
                          DisplayString,
                     sensorProbePTZRotateAbsolute
                          DisplayString,
                     sensorProbeAudioAttachChannel
                          INTEGER,
                     sensorProbePTZEnable
                          INTEGER,
                     sensorProbePTZBrand
                          INTEGER,
                     sensorProbePTZPanTiltUntilEnd
                          INTEGER
                  }


                  sensorProbeCameraServerClientOnline OBJECT-TYPE
                     SYNTAX  INTEGER {
                        online(1),
                        offline(2)
                     }
                     ACCESS  read-only
                     STATUS  mandatory
                     DESCRIPTION
                     "If this Client is currently online"
                     ::=  {  sensorProbeCameraServerEntry 1  }

                  sensorProbeCameraServerClientGoOnline OBJECT-TYPE
                     SYNTAX  INTEGER {
                        goOnline(1),
                        goOffline(2)
                     }
                     ACCESS  read-write
                     STATUS  mandatory
                     DESCRIPTION
                     "To put this Client online enter a 1, to take offline enter a 2"
                     ::=  {  sensorProbeCameraServerEntry 2  }

                  sensorProbeCameraServerClientIP OBJECT-TYPE
                     SYNTAX  IpAddress
                     ACCESS  read-write
                     STATUS  mandatory
                     DESCRIPTION
                     "The IP address of the sensorProbe, used to send snmp keep alive messages"
                     ::=  {  sensorProbeCameraServerEntry 3  }

                  sensorProbeCameraServerClientSetPassword OBJECT-TYPE
                     SYNTAX  DisplayString
                     ACCESS  read-write
                     STATUS  mandatory
                     DESCRIPTION
                     "SP Only: The Set Password for the snmp keep alive messages sent to the sensorProbes"
                     ::=  {  sensorProbeCameraServerEntry 4  }

                    sensorProbeCameraServerIndex OBJECT-TYPE
                       SYNTAX  INTEGER (0..9)
                       ACCESS  read-only
                       STATUS  mandatory
                       DESCRIPTION
                       "The index into the Camera table"
                       ::=  {  sensorProbeCameraServerEntry 5  }

                  sensorProbeJavaTimeOut OBJECT-TYPE
                     SYNTAX  INTEGER
                     ACCESS  read-write
                     STATUS  mandatory
                     DESCRIPTION
                     "Timeout in minutes for Java client"
                     ::=  {  sensorProbeCameraServerEntry 6  }

                  sensorProbeJpegQualityFactor OBJECT-TYPE
                     SYNTAX  INTEGER (5..95)
                     ACCESS  read-write
                     STATUS  mandatory
                     DESCRIPTION
                     "Quality factor of jpeg image"
                     ::=  {  sensorProbeCameraServerEntry 7  }

                  sensorProbeCameraDescription OBJECT-TYPE
                     SYNTAX  DisplayString
                     ACCESS  read-write
                     STATUS  mandatory
                     DESCRIPTION
                     "A description of camera"
                     ::=  {  sensorProbeCameraServerEntry 8 }

                  sensorProbeCameraRotate OBJECT-TYPE
                     SYNTAX  INTEGER {
                        nonRotate(0),
                        rotate(1)
                     }
                     ACCESS  read-write
                     STATUS  mandatory
                     DESCRIPTION
                     "A Rotate of this camera"
                     ::=  {  sensorProbeCameraServerEntry 9 }

                  sensorProbeCameraResolution OBJECT-TYPE
                     SYNTAX  INTEGER {
                        resolution320x240(0),
                        resolution640x480(1)
                     }
                     ACCESS  read-write
                     STATUS  mandatory
                     DESCRIPTION
                     "Resolution of camera"
                     ::=  {  sensorProbeCameraServerEntry 10 }

                  sensorProbePTZRotateRelative OBJECT-TYPE
                     SYNTAX  DisplayString
                     ACCESS  read-write
                     STATUS  mandatory
                     DESCRIPTION
                     "Control PTZ by put Direction and step 'DIR STEP' when direction 0 or 1 is LEFT or RIGH and 2 or 3 is UP or DOWN "
                     ::=  {  sensorProbeCameraServerEntry 11 }

                  sensorProbePTZRotateAbsolute OBJECT-TYPE
                     SYNTAX  DisplayString
                     ACCESS  read-write
                     STATUS  mandatory
                     DESCRIPTION
                     "Control PTZ by put position of x and y 'POS_X POS_Y' value of position is 0 to 100"
                     ::=  {  sensorProbeCameraServerEntry 12 }

                  sensorProbeAudioAttachChannel OBJECT-TYPE
                     SYNTAX  INTEGER {
                        notAttachAudio(0),
                        attachAudio(1)
                     }
                     ACCESS  read-write
                     STATUS  mandatory
                     DESCRIPTION
                     "Disable/Enable audio attachment"
                     ::=  {  sensorProbeCameraServerEntry 13 }

                  sensorProbePTZEnable OBJECT-TYPE
                     SYNTAX  INTEGER {
                        disable(0),
                        enableInternal(1),
                        enableExternal(2)
                     }
                     ACCESS  read-write
                     STATUS  mandatory
                     DESCRIPTION
                     "Disable/Enable Ptz controller"
                     ::=  {  sensorProbeCameraServerEntry 14 }

                  sensorProbePTZBrand OBJECT-TYPE
                     SYNTAX  INTEGER {
                        generalBrand(0),
                        akcpBrand(1)
                     }
                     ACCESS  read-write
                     STATUS  mandatory
                     DESCRIPTION
                     "PTZ Brand"
                     ::=  {  sensorProbeCameraServerEntry 15 }

                  sensorProbePTZPanTiltUntilEnd OBJECT-TYPE
                     SYNTAX  INTEGER {
                        stop(0),
                        right(1),
                        left(2),
                        up(3),
                        down(4),
                        right-up(5),
                        right-down(6),
                        left-up(7),
                        left-down(8)
                     }
                     ACCESS  read-write
                     STATUS  mandatory
                     DESCRIPTION
                     "Pan or Tilt PTZ until endpoint"
                     ::=  {  sensorProbeCameraServerEntry 16 }


               sensorProbeTrapMailPollInterval OBJECT-TYPE
                  SYNTAX  INTEGER
                  ACCESS  read-write
                  STATUS  mandatory
                  DESCRIPTION
                  "SP Only: How often the sensor thresholds are tested before sending traps or mail. This can vary from 3 to 15 seconds"
                  ::=  {  sensorProbeEntry 50  }

               sensorProbeSendTestMail OBJECT-TYPE
                  SYNTAX  INTEGER
                  ACCESS  read-write
                  STATUS  mandatory
                  DESCRIPTION
                  "Send out an email test message"
                  ::=  {  sensorProbeEntry 51  }

               sensorProbeLastSystemError OBJECT-TYPE
                  SYNTAX  DisplayString
                  ACCESS  read-only
                  STATUS  mandatory
                  DESCRIPTION
                  "A text string containing the description of the last system error"
                  ::=  {  sensorProbeEntry 52  }

               sensorProbeDataCollectionPeriod OBJECT-TYPE
                  SYNTAX  INTEGER
                  ACCESS  read-write
                  STATUS  mandatory
                  DESCRIPTION
                  "The number of minutes between collections of the data logger. This can vary from 1 to 60 minutes"
                  ::=  {  sensorProbeEntry 53  }

               sensorProbeMailTimeout OBJECT-TYPE
                  SYNTAX  INTEGER
                  ACCESS  read-write
                  STATUS  mandatory
                  DESCRIPTION
                  "The number of seconds to wait for a timeout while sending email This can vary from 10 to 30 seconds"
                  ::=  {  sensorProbeEntry 54  }

               sensorProbeAutoSense OBJECT-TYPE
                  SYNTAX  INTEGER {
                     disable(0),
                     enable(1)
                  }                  
                  ACCESS  read-write
                  STATUS  mandatory
                  DESCRIPTION
                  "Enable Auto-sense feature"
                  ::=  {  sensorProbeEntry 55  }

               sensorProbeChecksum OBJECT-TYPE
                  SYNTAX  INTEGER
                  ACCESS  read-only
                  STATUS  mandatory
                  DESCRIPTION
                  "SP Only: The Flash Checksum, computed dynamically whenever this object is read"
                  ::=  {  sensorProbeEntry 56  }

               sensorProbeUsePassword OBJECT-TYPE
                  SYNTAX  INTEGER {
                     usePassword(0),
                     doNotUsePassword(1)
                  }
                  ACCESS  read-write
                  STATUS  mandatory
                  DESCRIPTION
                  "Determines whether or not the set and get community are used to check for access rights"
                  ::=  {  sensorProbeEntry 57  }

               sensorProbeDisplayLogo OBJECT-TYPE
                  SYNTAX  INTEGER {
                     disable(0),
                     enable(1)
                  }                  
                  ACCESS  read-write
                  STATUS  mandatory
                  DESCRIPTION
                  "Enable or Disable the display of the logo"
                  ::=  {  sensorProbeEntry 59  }

               sensorProbeTrapType OBJECT-TYPE
                  SYNTAX  INTEGER {
                     specificTypeTrap(1),
                     generalTypeTrap(2),
                     bothTypeTraps(3),
                     statusTypeTraps(4)
                  }                  
                  ACCESS  read-write
                  STATUS  mandatory
                  DESCRIPTION
                  "Whether to generate a trap that covers all sensors, a specific trap for each sensor, or both types of traps"
                  ::=  {  sensorProbeEntry 60  }

               sensorProbeMailCC OBJECT-TYPE
                  SYNTAX  DisplayString
                  ACCESS  read-write
                  STATUS  mandatory
                  DESCRIPTION
                  "The email address of the CC"
                  ::=  {  sensorProbeEntry 61  }

               sensorProbeAllowIPChange OBJECT-TYPE
                SYNTAX  INTEGER {
                    enable(1),
                    disable(2)
                  }
                  ACCESS  read-write
                  STATUS  mandatory
                  DESCRIPTION
                  "This disables the changing of the IP address. The default is to enable changing the IP address"
                  ::=  {  sensorProbeEntry 62  }

               sensorProbeTimeOfDay OBJECT-TYPE
                  SYNTAX  DisplayString
                  ACCESS  read-write
                  STATUS  mandatory
                  DESCRIPTION
                  "The time of day in the format day/month/year hour(1-24):minutes:seconds for example 23/10/02 12:45:06"
                  ::=  {  sensorProbeEntry 65  }

               sensorProbeEnableSysLog OBJECT-TYPE
                SYNTAX  INTEGER {
                     enableLogToFlash(1),
                     enableLogToNetAndFlash(2),
                     disable(3)
                  }                  
                  ACCESS  read-write
                  STATUS  mandatory
                  DESCRIPTION
                  "This enables sysLog Messages,including logging to the Net. The Destination IP of the net messages is the same as the source IP of the sender of this command"
                  ::=  {  sensorProbeEntry 66  }

               sensorProbeReadSysLog OBJECT-TYPE
                  SYNTAX  INTEGER {
                     lastMessage(1),
                     allMessages(2)
                  }                  
                  ACCESS  read-write
                  STATUS  mandatory
                  DESCRIPTION
                  "Return the sysLog Message in the snmp PDU and if enableLogToNetAndFlash in sensorProbeEnableSysLog, also send in debug message format, A Write of a 2 will return all of the messages in debug format"
                  ::=  {  sensorProbeEntry 67  }

               sensorProbeClearSysLog OBJECT-TYPE
                  SYNTAX  INTEGER {
                     allMessages(2)
                  }                  
                  ACCESS  read-write
                  STATUS  mandatory
                  DESCRIPTION
                  "Delete all entries in the sys log"
                  ::=  {  sensorProbeEntry 68  }

               sensorProbeSyslogDestIP OBJECT-TYPE
                  SYNTAX  IpAddress
                  ACCESS  read-write
                  STATUS  mandatory
                  DESCRIPTION
                  "The IP Address of the Syslog server. Note: This must be in dotted decimal form"
                  ::=  {  sensorProbeEntry 69  }

               sensorProbeSyslogPort OBJECT-TYPE
                  SYNTAX  Gauge 
                  ACCESS  read-write
                  STATUS  mandatory
                  DESCRIPTION
                  "The Port Number of the Syslog server."
                  ::=  {  sensorProbeEntry 70  }

               sensorProbeSetSyslogMsgPrefix OBJECT-TYPE
                  SYNTAX  DisplayString
                  ACCESS  read-write
                  STATUS  mandatory
                  DESCRIPTION
                  "SP Only: The Prefix message of the Syslog message"
                  ::=  {  sensorProbeEntry 71  }

--
-- sensorProbeEntry 72 is reserved for sensorProbeLanFullDuplex ( SP Only )
--

--
-- sensorProbeEntry 73 is reserved for sensorProbeExpectedMicrocodeCRC ( SP Only )
--

--
-- sensorProbeEntry 74 is reserved for sensorProbeExpectedMicrocodeLength ( SP Only )
--

--
-- sensorProbeEntry 75 is reserved for sensorProbeActualMicrocodeCRC ( SP Only )
--

--
-- sensorProbeEntry 76 is reserved for sensorProbeExpectedBootCRC ( SP Only )
--

--
-- sensorProbeEntry 77 is reserved for sensorProbeActualBootCRC ( SP Only )
--

--
-- sensorProbeEntry 78 is reserved for sensorProbeBootVersion ( SP Only )
--

--
-- sensorProbeEntry 80 is reserved for sensorProbeAdcCalibrate
--

               sensorProbeTimeZone OBJECT-TYPE
                  SYNTAX  INTEGER  
                  ACCESS  read-write
                  STATUS  mandatory
                  DESCRIPTION
                  "System time zone" 
                  ::=  {  sensorProbeEntry 81  }

--
-- sensorProbeEntry 82 is reserved for sensorProbeExtraDryContactEnable ( SP Only )
--

               sensorProbeMegaVersion OBJECT-TYPE
                  SYNTAX  INTEGER
                  ACCESS  read-only
                  STATUS  mandatory
                  DESCRIPTION
                  "Version number of mega board"
                  ::=  {  sensorProbeEntry 83  }

               sensorProbeNtpMode OBJECT-TYPE
                  SYNTAX  INTEGER {
                     notUse(0),
                     oneTime(1),
                     onSystemStartUp(2),
                     onceAMounth(3),
                     onceAWeek(4),
                     onceADay(5),
                     onceAnHour(6),
                     continuous(7)
                  }
                  ACCESS  read-write
                  STATUS  mandatory
                  DESCRIPTION
                  "Mode to synchronous with ntp server" 
                  ::=  {  sensorProbeEntry 84  }

               sensorProbeNtpServer OBJECT-TYPE
                  SYNTAX  DisplayString
                  ACCESS  read-write
                  STATUS  mandatory
                  DESCRIPTION
                  "NTP server which this machine synchronous with"
                  ::=  {  sensorProbeEntry 85  }

--
-- sensorProbeEntry 86 is reserved for SensorProbeModel string which is used internaly (AKCP).
--

               sensorProbeSMTPAuth OBJECT-TYPE
                  SYNTAX  INTEGER {
                     enable(1),
                     disable(2)
                  }                  
                  ACCESS  read-write
                  STATUS  mandatory
                  DESCRIPTION
                  "This enables the SMTP authentication"
                  ::=  {  sensorProbeEntry 87  }

               sensorProbeSMTPLogin OBJECT-TYPE
                  SYNTAX  DisplayString
                  ACCESS  read-write
                  STATUS  mandatory
                  DESCRIPTION
                  "The username used to login into SMTP server"
                  ::=  {  sensorProbeEntry 88  }

               sensorProbeSMTPPassword OBJECT-TYPE
                  SYNTAX  DisplayString
                  ACCESS  read-write
                  STATUS  mandatory
                  DESCRIPTION
                  "The password used to login into SMTP server"
                  ::=  {  sensorProbeEntry 89  }

               sensorProbeDNSServer OBJECT-TYPE
                  SYNTAX  IpAddress
                  ACCESS  read-write
                  STATUS  mandatory
                  DESCRIPTION
                  "IP address of the DNS server"
                  ::=  {  sensorProbeEntry 90  }

               sensorProbeAltWebPort OBJECT-TYPE
                  SYNTAX  Gauge
                  ACCESS  read-write
                  STATUS  mandatory
                  DESCRIPTION
                  "The alternative for a port number 80 used to access the web interface"
                  ::=  {  sensorProbeEntry 91  }

               sensorProbeNumberOfSensorPort OBJECT-TYPE
                  SYNTAX  INTEGER
                  ACCESS  read-only
                  STATUS  mandatory
                  DESCRIPTION
                  "The number of sensor ports(regardless of their current state)"
                  ::=  {  sensorProbeEntry 92  }
               
               sensorProbeSendTrapsAlive OBJECT-TYPE
                  SYNTAX  INTEGER {
                     on(1),
                     off(2)
                  }
                  ACCESS  read-write
                  STATUS  mandatory
                  DESCRIPTION
                  "On or off send keep alive traps."
                  ::=  {  sensorProbeEntry 93  }
               
               sensorProbeTrapReIntervalAlive OBJECT-TYPE
                  SYNTAX  INTEGER
                  ACCESS  read-write
                  STATUS  mandatory
                  DESCRIPTION
                  "Time between each keep alive trap."
                  ::=  {  sensorProbeEntry 94  }
               
               sensorProbeUseCamera OBJECT-TYPE
                  SYNTAX  INTEGER {
                     off(0),
                     on(1)
                  }
                  ACCESS  read-write
                  STATUS  mandatory
                  DESCRIPTION
                  "On or off camera."
                  ::=  {  sensorProbeEntry 95  }
                                 
               sensorProbeAdcCalibratePort OBJECT-TYPE
                  SYNTAX  INTEGER
                  ACCESS  read-write
                  STATUS  mandatory
                  DESCRIPTION
                  "Calibrate value for analog sensor."
                  ::=  {  sensorProbeEntry 96  }

--
-- sensorProbeEntry 97 is reseverd for future using with Linux version (AKCP).
--

               sensorProbeMailSubject OBJECT-TYPE
                  SYNTAX  DisplayString
                  ACCESS  read-write
                  STATUS  mandatory
                  DESCRIPTION
                  "Email Subject."
                  ::=  {  sensorProbeEntry 98  }

          sensorProbeSnmpPort OBJECT-TYPE
                  SYNTAX  Gauge 
                  ACCESS  read-write
                  STATUS  mandatory
                  DESCRIPTION
                  "SP Only: Port number used to access snmp"
                  ::=  {  sensorProbeEntry 99  }

          sensorProbeSnmpTrapPort OBJECT-TYPE
                  SYNTAX  Gauge 
                  ACCESS  read-write
                  STATUS  mandatory
                  DESCRIPTION
                  "SP Only: Port number used to access trap snmp"
                  ::=  {  sensorProbeEntry 100  }

          sensorProbeSnmpIndexingMode OBJECT-TYPE
                  SYNTAX  INTEGER {
                     index0(0),
                     index1(1)
                  }
                  ACCESS  read-write
                  STATUS  mandatory
                  DESCRIPTION
                  "CP8 Only: Snmp table index starting from 0 or 1 "
                  ::=  {  sensorProbeEntry 101  }

--
-- sensorProbeEntry 102 is reserved for sensorProbeSensorSummary
--
               sensorProbeNotifyBoot OBJECT-TYPE
                  SYNTAX  INTEGER
                  ACCESS  read-write
                  STATUS  mandatory
                  DESCRIPTION
                  "SP2 Only: Enable Notify on boot up"
                  ::=  {  sensorProbeEntry 103  }

               sensorProbeDelayNotifyBoot OBJECT-TYPE
                  SYNTAX  INTEGER
                  ACCESS  read-write
                  STATUS  mandatory
                  DESCRIPTION
                  "SP2 Only: Delay time for boot up notify"
                  ::=  {  sensorProbeEntry 104  }

               sensorProbeSmtpPort OBJECT-TYPE
                  SYNTAX  INTEGER
                  ACCESS  read-write
                  STATUS  mandatory
                  DESCRIPTION
                  "SMTP Port number used to send email"
                  ::=  {  sensorProbeEntry 105  }

               sensorProbeReboot OBJECT-TYPE
                  SYNTAX  INTEGER
                  ACCESS  read-write
                  STATUS  mandatory
                  DESCRIPTION
                  "Reboot SP2/SP8 set to 1"
                  ::=  {  sensorProbeEntry 106  }

          sensorProbeServerEnable OBJECT-TYPE
                  SYNTAX  INTEGER {
                     disable(0),
                     enable(1)
                  }
                  ACCESS  read-write
                  STATUS  mandatory
                  DESCRIPTION
                  "Enable database changed notify feature"
                  ::=  {  sensorProbeEntry 107  }

          sensorProbeFirmwareVersion OBJECT-TYPE
                  SYNTAX  DisplayString
                  ACCESS  read-only
                  STATUS  mandatory
                  DESCRIPTION
                  "Current firmware version"
                  ::=  {  sensorProbeEntry 108  }

          sensorProbeProductType OBJECT-TYPE
                  SYNTAX  INTEGER {
                     sensorProbe2(1),
                     sensorProbe8(2),
                     sensorProbeLinuxWithoutUSB(3),
                     sensorProbeLinuxWithUSB(4),
                     securityProbe(5)
                  }
                  ACCESS  read-only
                  STATUS  mandatory
                  DESCRIPTION
                  "Product type"
                  ::=  {  sensorProbeEntry 109  }

               sensorProbeRequestResendTrap OBJECT-TYPE
                  SYNTAX  INTEGER
                  ACCESS  read-write
                  STATUS  mandatory
                  DESCRIPTION
                  "SP only: Send immediately all traps by set to 1"
                  ::=  {  sensorProbeEntry 110  }

--
-- sensorProbeEntry 111 is reserved for Server Project
--

               sensorProbeSeparateEmail OBJECT-TYPE
                  SYNTAX  INTEGER {
                     notSeparate(0),
                     separate(1)
                  }
                  ACCESS  read-write
                  STATUS  mandatory
                  DESCRIPTION
                  "SP only: Separate Email by set 1 for not Separate Email set 0"
                  ::=  {  sensorProbeEntry 112  }

               sensorProbeMailCustom OBJECT-TYPE
                  SYNTAX  INTEGER {
                     normal(0),
                     custom(1)
                  }
                  ACCESS  read-write
                  STATUS  mandatory
                  DESCRIPTION
                  "SP only: Custom mail is removed 'http://' in the mail footer"
                  ::=  {  sensorProbeEntry 113  }

          sensorProbeUntidePassword OBJECT-TYPE
                  SYNTAX  INTEGER {
                     tidePassword(0),
                     untidePassword(1)
                  }
                  ACCESS  read-write
                  STATUS  mandatory
                  DESCRIPTION
                  "Use web password as SNMP password"
                  ::=  {  sensorProbeEntry 114  }

          sensorProbeWebPassword OBJECT IDENTIFIER ::= { sensorProbeEntry 115  }
              sensorProbeWebAdminPassword OBJECT-TYPE
                  SYNTAX DisplayString
                  ACCESS read-write
                  STATUS mandatory
                  DESCRIPTION
                  "Password Admin for login web and other connections"
                  ::= {  sensorProbeWebPassword 1 }

              sensorProbeWebUserPassword OBJECT-TYPE
                  SYNTAX DisplayString
                  ACCESS read-write
                  STATUS mandatory
                  DESCRIPTION
                  "Password User for login web and other connections"
                  ::= {  sensorProbeWebPassword 2 }

          sensorProbeReloadNetwork OBJECT-TYPE
                  SYNTAX  INTEGER {
                     reload(1)
                  }
                  ACCESS  read-write
                  STATUS  mandatory
                  DESCRIPTION
                  "Set 1 for reload network seting"
                  ::=  {  sensorProbeEntry 116  }

          sensorProbeStatusNumber OBJECT IDENTIFIER ::= { sensorProbeEntry 117  }
              sensorProbeStatusNumberNotNormal OBJECT-TYPE
                  SYNTAX INTEGER
                  ACCESS read-only
                  STATUS mandatory
                  DESCRIPTION
                  "Number of sensor status is Warning, Critical and Sensor Error"
                  ::= {  sensorProbeStatusNumber 1 }

              sensorProbeStatusNumberCriticalAndError OBJECT-TYPE
                  SYNTAX INTEGER
                  ACCESS read-only
                  STATUS mandatory
                  DESCRIPTION
                  "Number of sensor status is Critical and Sensor Error"
                  ::= {  sensorProbeStatusNumber 2 }

              sensorProbeStatusNumberError OBJECT-TYPE
                  SYNTAX INTEGER
                  ACCESS read-only
                  STATUS mandatory
                  DESCRIPTION
                  "Number of sensor status is Sensor Error"
                  ::= {  sensorProbeStatusNumber 3 }

          sensorProbeTypeName OBJECT IDENTIFIER ::= { sensorProbeEntry 118  }
              sensorProbeTypeTemperatureName OBJECT-TYPE
                  SYNTAX DisplayString
                  ACCESS read-write
                  STATUS mandatory
                  DESCRIPTION
                  "A Description of Sensor Type Name on web interface"
                  ::= {  sensorProbeTypeName 1 }

              sensorProbeTypeSHT11HumidityName OBJECT-TYPE
                  SYNTAX DisplayString
                  ACCESS read-write
                  STATUS mandatory
                  DESCRIPTION
                  "A Description of Sensor Type Name on web interface"
                  ::= {  sensorProbeTypeName 2 }
                  
              sensorProbeTypeSHT11TempName OBJECT-TYPE
                  SYNTAX DisplayString
                  ACCESS read-write
                  STATUS mandatory
                  DESCRIPTION
                  "A Description of Sensor Type Name on web interface"
                  ::= {  sensorProbeTypeName 3 }
           
              sensorProbeType4to20MAName OBJECT-TYPE
                  SYNTAX DisplayString
                  ACCESS read-write
                  STATUS mandatory
                  DESCRIPTION
                  "A Description of Sensor Type Name on web interface"
                  ::= {  sensorProbeTypeName 4 }

              sensorProbeTypeDCvoltageName OBJECT-TYPE
                  SYNTAX DisplayString
                  ACCESS read-write
                  STATUS mandatory
                  DESCRIPTION
                  "A Description of Sensor Type Name on web interface"
                  ::= {  sensorProbeTypeName 5 }
                  
              sensorProbeTypeAirflowName OBJECT-TYPE
                  SYNTAX DisplayString
                  ACCESS read-write
                  STATUS mandatory
                  DESCRIPTION
                  "A Description of Sensor Type Name on web interface"
                  ::= {  sensorProbeTypeName 6 }
                  
              sensorProbeTypeDrycontactInoutName OBJECT-TYPE
                  SYNTAX DisplayString
                  ACCESS read-write
                  STATUS mandatory
                  DESCRIPTION
                  "A Description of Sensor Type Name on web interface"
                  ::= {  sensorProbeTypeName 7 }

              sensorProbeTypeDrycontactInputName OBJECT-TYPE
                  SYNTAX DisplayString
                  ACCESS read-write
                  STATUS mandatory
                  DESCRIPTION
                  "A Description of Sensor Type Name on web interface"
                  ::= {  sensorProbeTypeName 8 }
                  
              sensorProbeTypeMotionName OBJECT-TYPE
                  SYNTAX DisplayString
                  ACCESS read-write
                  STATUS mandatory
                  DESCRIPTION
                  "A Description of Sensor Type Name on web interface"
                  ::= {  sensorProbeTypeName 9 }
                  
              sensorProbeTypeWaterName OBJECT-TYPE
                  SYNTAX DisplayString
                  ACCESS read-write
                  STATUS mandatory
                  DESCRIPTION
                  "A Description of Sensor Type Name on web interface"
                  ::= {  sensorProbeTypeName 10 }

              sensorProbeTypeSecurityName OBJECT-TYPE
                  SYNTAX DisplayString
                  ACCESS read-write
                  STATUS mandatory
                  DESCRIPTION
                  "A Description of Sensor Type Name on web interface"
                  ::= {  sensorProbeTypeName 11 }
                  
              sensorProbeTypeSirenName OBJECT-TYPE
                  SYNTAX DisplayString
                  ACCESS read-write
                  STATUS mandatory
                  DESCRIPTION
                  "A Description of Sensor Type Name on web interface"
                  ::= {  sensorProbeTypeName 12 }
                  
              sensorProbeTypeRelayName OBJECT-TYPE
                  SYNTAX DisplayString
                  ACCESS read-write
                  STATUS mandatory
                  DESCRIPTION
                  "A Description of Sensor Type Name on web interface"
                  ::= {  sensorProbeTypeName 13 }

              sensorProbeTypeACvoltageName OBJECT-TYPE
                  SYNTAX DisplayString
                  ACCESS read-write
                  STATUS mandatory
                  DESCRIPTION
                  "A Description of Sensor Type Name on web interface"
                  ::= {  sensorProbeTypeName 14 }
                  
              sensorProbeTypeADE7763VRMSName OBJECT-TYPE
                  SYNTAX DisplayString
                  ACCESS read-write
                  STATUS mandatory
                  DESCRIPTION
                  "A Description of Sensor Type Name on web interface"
                  ::= {  sensorProbeTypeName 15 }

              sensorProbeTypeADE7763IRMSName OBJECT-TYPE
                  SYNTAX DisplayString
                  ACCESS read-write
                  STATUS mandatory
                  DESCRIPTION
                  "A Description of Sensor Type Name on web interface"
                  ::= {  sensorProbeTypeName  16 }
                  
              sensorProbeTypeADE7763WattName OBJECT-TYPE
                  SYNTAX DisplayString
                  ACCESS read-write
                  STATUS mandatory
                  DESCRIPTION
                  "A Description of Sensor Type Name on web interface"
                  ::= {  sensorProbeTypeName  17 }
                  
              sensorProbeTypeADE7763WatthourName OBJECT-TYPE
                  SYNTAX DisplayString
                  ACCESS read-write
                  STATUS mandatory
                  DESCRIPTION
                  "A Description of Sensor Type Name on web interface"
                  ::= {  sensorProbeTypeName  18 }
                  
              sensorProbeTypePCF8574XRelayName OBJECT-TYPE
                  SYNTAX DisplayString
                  ACCESS read-write
                  STATUS mandatory
                  DESCRIPTION
                  "A Description of Sensor Type Name on web interface"
                  ::= {  sensorProbeTypeName  19 }
                  
              sensorProbeTypeThermocoupleName OBJECT-TYPE
                  SYNTAX DisplayString
                  ACCESS read-write
                  STATUS mandatory
                  DESCRIPTION
                  "A Description of Sensor Type Name on web interface"
                  ::= {  sensorProbeTypeName  20 }
                  
              sensorProbeTypeSmokeName OBJECT-TYPE
                  SYNTAX DisplayString
                  ACCESS read-write
                  STATUS mandatory
                  DESCRIPTION
                  "A Description of Sensor Type Name on web interface"
                  ::= {  sensorProbeTypeName  21 }
                  
              sensorProbeTypeXDryName OBJECT-TYPE
                  SYNTAX DisplayString
                  ACCESS read-write
                  STATUS mandatory
                  DESCRIPTION
                  "A Description of Sensor Type Name on web interface"
                  ::= {  sensorProbeTypeName  22 }
                  
              sensorProbeTypeTemperatureArrayName OBJECT-TYPE
                  SYNTAX DisplayString
                  ACCESS read-write
                  STATUS mandatory
                  DESCRIPTION
                  "A Description of Sensor Type Name on web interface"
                  ::= {  sensorProbeTypeName  23 }

              sensorProbeTypeWaterRopeName OBJECT-TYPE
                  SYNTAX DisplayString
                  ACCESS read-write
                  STATUS mandatory
                  DESCRIPTION
                  "A Description of Sensor Type Name on web interface"
                  ::= {  sensorProbeTypeName  24 }

              sensorProbeTypeFuelLevelName OBJECT-TYPE
                  SYNTAX DisplayString
                  ACCESS read-write
                  STATUS mandatory
                  DESCRIPTION
                  "A Description of Sensor Type Name on web interface"
                  ::= {  sensorProbeTypeName  25 }

              sensorProbeTypeTankSenderName OBJECT-TYPE
                  SYNTAX DisplayString
                  ACCESS read-write
                  STATUS mandatory
                  DESCRIPTION
                  "A Description of Sensor Type Name on web interface"
                  ::= {  sensorProbeTypeName  26 }
				  
              sensorProbeTypeThurmostatName OBJECT-TYPE
                  SYNTAX DisplayString
                  ACCESS read-write
                  STATUS mandatory
                  DESCRIPTION
                  "A Description of Sensor Type Name on web interface"
                  ::= {  sensorProbeTypeName  128 }

              sensorProbeTypeVirtualName OBJECT-TYPE
                  SYNTAX DisplayString
                  ACCESS read-write
                  STATUS mandatory
                  DESCRIPTION
                  "A Description of Sensor Type Name on web interface"
                  ::= {  sensorProbeTypeName  129 }

              sensorProbeTypeSoundName OBJECT-TYPE
                  SYNTAX DisplayString
                  ACCESS read-write
                  STATUS mandatory
                  DESCRIPTION
                  "A Description of Sensor Type Name on web interface"
                  ::= {  sensorProbeTypeName  130 }

              sensorProbeTypeSoftMotionName OBJECT-TYPE
                  SYNTAX DisplayString
                  ACCESS read-write
                  STATUS mandatory
                  DESCRIPTION
                  "A Description of Sensor Type Name on web interface"
                  ::= {  sensorProbeTypeName  131 }

              sensorProbeTypeNoSignalName OBJECT-TYPE
                  SYNTAX DisplayString
                  ACCESS read-write
                  STATUS mandatory
                  DESCRIPTION
                  "A Description of Sensor Type Name on web interface"
                  ::= {  sensorProbeTypeName  132 }

              sensorProbeTypePowerMeterName OBJECT-TYPE
                  SYNTAX DisplayString
                  ACCESS read-write
                  STATUS mandatory
                  DESCRIPTION
                  "A Description of Sensor Type Name on web interface"
                  ::= {  sensorProbeTypeName  134 }

              sensorProbeTypeSHT11Name OBJECT-TYPE
                  SYNTAX DisplayString
                  ACCESS read-write
                  STATUS mandatory
                  DESCRIPTION
                  "A Description of Sensor Type Name on web interface"
                  ::= {  sensorProbeTypeName 135 }

              sensorProbeTypeADE7763Name OBJECT-TYPE
                  SYNTAX DisplayString
                  ACCESS read-write
                  STATUS mandatory
                  DESCRIPTION
                  "A Description of Sensor Type Name on web interface"
                  ::= {  sensorProbeTypeName 136 }

          sensorProbeProductRevision OBJECT-TYPE
                  SYNTAX  INTEGER
                  ACCESS  read-only
                  STATUS  mandatory
                  DESCRIPTION
                  "SP only: Revision number"
                  ::=  {  sensorProbeEntry 119  }

   securityProbe OBJECT IDENTIFIER ::= { akcp 2 }

      secSummary OBJECT IDENTIFIER  ::=  {  securityProbe 1 }

      secDevice OBJECT IDENTIFIER  ::=  {  securityProbe 2 }

         deviceTable OBJECT-TYPE
            SYNTAX  SEQUENCE OF DeviceEntry
            ACCESS  not-accessible
            STATUS  mandatory
            DESCRIPTION
            "This table contains the property for every plugged-in device."
            ::=  {  secDevice 1   }

         deviceEntry OBJECT-TYPE
            SYNTAX  DeviceEntry
            ACCESS  not-accessible
            STATUS  mandatory
            DESCRIPTION
            "This is an entry in the deviceEntry Table"
            INDEX         { deviceIndex }
            ::=  {  deviceTable 1 }

         DeviceEntry ::= SEQUENCE {
               deviceIndex
                  INTEGER,
               deviceDescription
                  DisplayString,
               deviceType
                  INTEGER,
               deviceInfo
                  DisplayString,
               deviceStatus
                  INTEGER
         }

            deviceIndex OBJECT-TYPE
               SYNTAX  INTEGER (1..184549375)
               ACCESS  read-only
               STATUS  mandatory
               DESCRIPTION
               "The index into the device table"
               ::=  {  deviceEntry 1   }

            deviceDescription OBJECT-TYPE
               SYNTAX  DisplayString
               ACCESS  read-write
               STATUS  mandatory
               DESCRIPTION
               "A Description of this device"
               ::=  {  deviceEntry 2   }

            deviceType OBJECT-TYPE
               SYNTAX  INTEGER
               ACCESS  read-only
               STATUS  mandatory
               DESCRIPTION
               "..."
               ::=  {  deviceEntry 3   }

            deviceInfo OBJECT-TYPE
               SYNTAX  DisplayString
               ACCESS  read-only
               STATUS  mandatory
               DESCRIPTION
               "A information of this device"
               ::=  {  deviceEntry 4   }

            deviceStatus OBJECT-TYPE
               SYNTAX  INTEGER
               ACCESS  read-only
               STATUS  mandatory
               DESCRIPTION
               "..."
               ::=  {  deviceEntry 5   }

         deviceIntelligentTable OBJECT-TYPE
            SYNTAX  SEQUENCE OF DeviceIntelligentEntry
            ACCESS  not-accessible
            STATUS  mandatory
            DESCRIPTION
            "This table contains the property for every plugged-in device."
            ::=  {  secDevice 2  }

         deviceIntelligentEntry OBJECT-TYPE
            SYNTAX  DeviceIntelligentEntry
            ACCESS  not-accessible
            STATUS  mandatory
            DESCRIPTION
            "This is an entry in the deviceEntry Table"
            INDEX         { deviceIntelligentIndex }
            ::=  {  deviceIntelligentTable 1 }

         DeviceIntelligentEntry ::= SEQUENCE {
               deviceIntelligentIndex
                  INTEGER,
               deviceIntelligentDescription
                  DisplayString,
               deviceIntelligentInfo
                  DisplayString,
               deviceIntelligentStatus
                  INTEGER,
               sensorIntelligentTypeSelected
                  INTEGER,
               sensorIntelligentPort1GoOnline
                  INTEGER,
               sensorIntelligentPort2GoOnline
                  INTEGER,
               sensorIntelligentPort3GoOnline
                  INTEGER,
               sensorIntelligentPort4GoOnline
                  INTEGER,
               sensorIntelligentPort5GoOnline
                  INTEGER,
               sensorIntelligentPort6GoOnline
                  INTEGER,
               sensorIntelligentPort7GoOnline
                  INTEGER,
               sensorIntelligentPort8GoOnline
                  INTEGER
         }
            deviceIntelligentIndex OBJECT-TYPE
               SYNTAX  INTEGER (1..65535)
               ACCESS  read-only
               STATUS  mandatory
               DESCRIPTION
               "The index into the deviceIntelligent table"
               ::=  {  deviceIntelligentEntry 1   }

            deviceIntelligentDescription OBJECT-TYPE
               SYNTAX  DisplayString
               ACCESS  read-write
               STATUS  mandatory
               DESCRIPTION
               "A Description of this device"
               ::=  {  deviceIntelligentEntry 2   }

            deviceIntelligentInfo OBJECT-TYPE
               SYNTAX  DisplayString
               ACCESS  read-only
               STATUS  mandatory
               DESCRIPTION
               "A information of this device"
               ::=  {  deviceIntelligentEntry 4   }

            deviceIntelligentStatus OBJECT-TYPE
               SYNTAX  INTEGER
               ACCESS  read-only
               STATUS  mandatory
               DESCRIPTION
               "..."
               ::=  {  deviceIntelligentEntry 5   }

            sensorIntelligentTypeSelected OBJECT-TYPE
               SYNTAX  INTEGER
               ACCESS  read-write
               STATUS  mandatory
               DESCRIPTION
               "..."
               ::=  {  deviceIntelligentEntry 6   }

            sensorIntelligentPort1GoOnline OBJECT-TYPE
               SYNTAX  INTEGER {
               goOnline(1),
               goOffline(2)
               }
               ACCESS  read-write
               STATUS  mandatory
               DESCRIPTION
               "..."
               ::=  {  deviceIntelligentEntry 100   }

            sensorIntelligentPort2GoOnline OBJECT-TYPE
               SYNTAX  INTEGER {
               goOnline(1),
               goOffline(2)
               }
               ACCESS  read-write
               STATUS  mandatory
               DESCRIPTION
               "..."
               ::=  {  deviceIntelligentEntry 101   }

            sensorIntelligentPort3GoOnline OBJECT-TYPE
               SYNTAX  INTEGER {
               goOnline(1),
               goOffline(2)
               }
               ACCESS  read-write
               STATUS  mandatory
               DESCRIPTION
               "..."
               ::=  {  deviceIntelligentEntry 102   }

            sensorIntelligentPort4GoOnline OBJECT-TYPE
               SYNTAX  INTEGER {
               goOnline(1),
               goOffline(2)
               }
               ACCESS  read-write
               STATUS  mandatory
               DESCRIPTION
               "..."
               ::=  {  deviceIntelligentEntry 103   }

            sensorIntelligentPort5GoOnline OBJECT-TYPE
               SYNTAX  INTEGER {
               goOnline(1),
               goOffline(2)
               }
               ACCESS  read-write
               STATUS  mandatory
               DESCRIPTION
               "..."
               ::=  {  deviceIntelligentEntry 104   }

            sensorIntelligentPort6GoOnline OBJECT-TYPE
               SYNTAX  INTEGER {
               goOnline(1),
               goOffline(2)
               }
               ACCESS  read-write
               STATUS  mandatory
               DESCRIPTION
               "..."
               ::=  {  deviceIntelligentEntry 105   }

            sensorIntelligentPort7GoOnline OBJECT-TYPE
               SYNTAX  INTEGER {
               goOnline(1),
               goOffline(2)
               }
               ACCESS  read-write
               STATUS  mandatory
               DESCRIPTION
               "..."
               ::=  {  deviceIntelligentEntry 106   }

            sensorIntelligentPort8GoOnline OBJECT-TYPE
               SYNTAX  INTEGER {
               goOnline(1),
               goOffline(2)
               }
               ACCESS  read-write
               STATUS  mandatory
               DESCRIPTION
               "..."
               ::=  {  deviceIntelligentEntry 107   }

         deviceDryContactTable OBJECT-TYPE
            SYNTAX  SEQUENCE OF DeviceDryContactEntry
            ACCESS  not-accessible
            STATUS  mandatory
            DESCRIPTION
            "This table contains the property for every plugged-in device."
            ::=  {  secDevice 3  }

         deviceDryContactEntry OBJECT-TYPE
            SYNTAX  DeviceDryContactEntry
            ACCESS  not-accessible
            STATUS  mandatory
            DESCRIPTION
            "This is an entry in the deviceEntry Table"
            INDEX         { deviceDryContactIndex }
            ::=  {  deviceDryContactTable 1 }

         DeviceDryContactEntry ::= SEQUENCE {
               deviceDryContactIndex
                  INTEGER,
               deviceDryContactDescription
                  DisplayString,
               deviceDryContactInfo
                  DisplayString,
               deviceDryContactStatus
                  INTEGER,
               sensorDryContactPort1GoOnline
                  INTEGER,
               sensorDryContactPort2GoOnline
                  INTEGER,
               sensorDryContactPort3GoOnline
                  INTEGER,
               sensorDryContactPort4GoOnline
                  INTEGER,
               sensorDryContactPort5GoOnline
                  INTEGER,
               sensorDryContactPort6GoOnline
                  INTEGER,
               sensorDryContactPort7GoOnline
                  INTEGER,
               sensorDryContactPort8GoOnline
                  INTEGER,
               sensorDryContactPort9GoOnline
                  INTEGER,
               sensorDryContactPort10GoOnline
                  INTEGER,
               sensorDryContactPort11GoOnline
                  INTEGER,
               sensorDryContactPort12GoOnline
                  INTEGER,
               sensorDryContactPort13GoOnline
                  INTEGER,
               sensorDryContactPort14GoOnline
                  INTEGER,
               sensorDryContactPort15GoOnline
                  INTEGER,
               sensorDryContactPort16GoOnline
                  INTEGER
         }

            deviceDryContactIndex OBJECT-TYPE
               SYNTAX  INTEGER (1..65535)
               ACCESS  read-only
               STATUS  mandatory
               DESCRIPTION
               "The index into the deviceDryContact table"
               ::=  {  deviceDryContactEntry 1   }

            deviceDryContactDescription OBJECT-TYPE
               SYNTAX  DisplayString
               ACCESS  read-write
               STATUS  mandatory
               DESCRIPTION
               "A Description of this device"
               ::=  {  deviceDryContactEntry 2   }

            deviceDryContactInfo OBJECT-TYPE
               SYNTAX  DisplayString
               ACCESS  read-only
               STATUS  mandatory
               DESCRIPTION
               "A information of this device"
               ::=  {  deviceDryContactEntry 4   }

            deviceDryContactStatus OBJECT-TYPE
               SYNTAX  INTEGER
               ACCESS  read-only
               STATUS  mandatory
               DESCRIPTION
               "..."
               ::=  {  deviceDryContactEntry 5   }

            sensorDryContactPort1GoOnline OBJECT-TYPE
               SYNTAX  INTEGER {
               goOnline(1),
               goOffline(2)
               }
               ACCESS  read-write
               STATUS  mandatory
               DESCRIPTION
               "..."
               ::=  {  deviceDryContactEntry 100   }

            sensorDryContactPort2GoOnline OBJECT-TYPE
               SYNTAX  INTEGER {
               goOnline(1),
               goOffline(2)
               }
               ACCESS  read-write
               STATUS  mandatory
               DESCRIPTION
               "..."
               ::=  {  deviceDryContactEntry 101   }

            sensorDryContactPort3GoOnline OBJECT-TYPE
               SYNTAX  INTEGER {
               goOnline(1),
               goOffline(2)
               }
               ACCESS  read-write
               STATUS  mandatory
               DESCRIPTION
               "..."
               ::=  {  deviceDryContactEntry 102   }

            sensorDryContactPort4GoOnline OBJECT-TYPE
               SYNTAX  INTEGER {
               goOnline(1),
               goOffline(2)
               }
               ACCESS  read-write
               STATUS  mandatory
               DESCRIPTION
               "..."
               ::=  {  deviceDryContactEntry 103   }

            sensorDryContactPort5GoOnline OBJECT-TYPE
               SYNTAX  INTEGER {
               goOnline(1),
               goOffline(2)
               }
               ACCESS  read-write
               STATUS  mandatory
               DESCRIPTION
               "..."
               ::=  {  deviceDryContactEntry 104   }

            sensorDryContactPort6GoOnline OBJECT-TYPE
               SYNTAX  INTEGER {
               goOnline(1),
               goOffline(2)
               }
               ACCESS  read-write
               STATUS  mandatory
               DESCRIPTION
               "..."
               ::=  {  deviceDryContactEntry 105   }

            sensorDryContactPort7GoOnline OBJECT-TYPE
               SYNTAX  INTEGER {
               goOnline(1),
               goOffline(2)
               }
               ACCESS  read-write
               STATUS  mandatory
               DESCRIPTION
               "..."
               ::=  {  deviceDryContactEntry 106   }

            sensorDryContactPort8GoOnline OBJECT-TYPE
               SYNTAX  INTEGER {
               goOnline(1),
               goOffline(2)
               }
               ACCESS  read-write
               STATUS  mandatory
               DESCRIPTION
               "..."
               ::=  {  deviceDryContactEntry 107   }

            sensorDryContactPort9GoOnline OBJECT-TYPE
               SYNTAX  INTEGER {
               goOnline(1),
               goOffline(2)
               }
               ACCESS  read-write
               STATUS  mandatory
               DESCRIPTION
               "..."
               ::=  {  deviceDryContactEntry 108   }

            sensorDryContactPort10GoOnline OBJECT-TYPE
               SYNTAX  INTEGER {
               goOnline(1),
               goOffline(2)
               }
               ACCESS  read-write
               STATUS  mandatory
               DESCRIPTION
               "..."
               ::=  {  deviceDryContactEntry 109   }

            sensorDryContactPort11GoOnline OBJECT-TYPE
               SYNTAX  INTEGER {
               goOnline(1),
               goOffline(2)
               }
               ACCESS  read-write
               STATUS  mandatory
               DESCRIPTION
               "..."
               ::=  {  deviceDryContactEntry 110   }

            sensorDryContactPort12GoOnline OBJECT-TYPE
               SYNTAX  INTEGER {
               goOnline(1),
               goOffline(2)
               }
               ACCESS  read-write
               STATUS  mandatory
               DESCRIPTION
               "..."
               ::=  {  deviceDryContactEntry 111   }

            sensorDryContactPort13GoOnline OBJECT-TYPE
               SYNTAX  INTEGER {
               goOnline(1),
               goOffline(2)
               }
               ACCESS  read-write
               STATUS  mandatory
               DESCRIPTION
               "..."
               ::=  {  deviceDryContactEntry 112   }

            sensorDryContactPort14GoOnline OBJECT-TYPE
               SYNTAX  INTEGER {
               goOnline(1),
               goOffline(2)
               }
               ACCESS  read-write
               STATUS  mandatory
               DESCRIPTION
               "..."
               ::=  {  deviceDryContactEntry 113   }

            sensorDryContactPort15GoOnline OBJECT-TYPE
               SYNTAX  INTEGER {
               goOnline(1),
               goOffline(2)
               }
               ACCESS  read-write
               STATUS  mandatory
               DESCRIPTION
               "..."
               ::=  {  deviceDryContactEntry 114   }

            sensorDryContactPort16GoOnline OBJECT-TYPE
               SYNTAX  INTEGER {
               goOnline(1),
               goOffline(2)
               }
               ACCESS  read-write
               STATUS  mandatory
               DESCRIPTION
               "..."
               ::=  {  deviceDryContactEntry 115   }


      secSensor OBJECT IDENTIFIER  ::=  {  securityProbe 3 }

         sensorTable OBJECT-TYPE
            SYNTAX  SEQUENCE OF SensorEntry
            ACCESS  not-accessible
            STATUS  mandatory
            DESCRIPTION
            "This table contains the property and reading value for every sensor."
            ::=  {  secSensor 1   }

--/* Begin of sensorEntry */

         sensorEntry OBJECT-TYPE
            SYNTAX  SensorEntry
            ACCESS  not-accessible
            STATUS  mandatory
            DESCRIPTION
            "This is an entry in the sensorTable Table"
            INDEX         { sensorIndex }
            ::=  {  sensorTable 1 }

         SensorEntry ::= SEQUENCE {
               sensorIndex
                  INTEGER,
               sensorDescription
                  DisplayString,
               sensorType
                  INTEGER,
               sensorValue
                  INTEGER,
               sensorUnit
                  DisplayString,
               sensorStatus
                  INTEGER,
               sensorGoOffline
                  INTEGER,
               sensorPort
                  INTEGER,
               sensorSubPort
                  INTEGER,
               sensorDeviceIndex
                  INTEGER,
               sensorDisplayStyle
                  INTEGER,
               sensorHighCriticalDescription
                  DisplayString,
               sensorLowCriticalDescription
                  DisplayString,
               sensorNormalDescription
                  DisplayString,
               sensorLowWarningDescription
                  DisplayString,
               sensorHighWarningDescription
                  DisplayString,
               sensorErrorDescription
                  DisplayString,
               sensorOnDescription
                  DisplayString,
               sensorOffDescription
                  DisplayString,
               sensorHighCriticalColor
                  INTEGER,
               sensorLowCriticalColor
                  INTEGER,
               sensorNormalColor
                  INTEGER,
               sensorLowWarningColor
                  INTEGER,
               sensorHighWarningColor
                  INTEGER,
               sensorErrorColor
                  INTEGER,
               sensorOnColor
                  INTEGER,
               sensorOffColor
                  INTEGER
         }

            sensorIndex OBJECT-TYPE
               SYNTAX  INTEGER (1..65535)
               ACCESS  read-only
               STATUS  mandatory
               DESCRIPTION
               "The index into the sensor table"
               ::=  {  sensorEntry 1   }

            sensorDescription OBJECT-TYPE
               SYNTAX  DisplayString
               ACCESS  read-write
               STATUS  mandatory
               DESCRIPTION
               "A Description of this sensor"
               ::=  {  sensorEntry 2   }

            sensorType OBJECT-TYPE
               SYNTAX  INTEGER {
                  temperature(1),
                  humidity(2),
                  temperature2(3),
                  four-20mA(4),
                  dcvoltage(5),
                  airflow(6),
                  io(7),
                  drycontact(8),
                  motion(9),
                  water(10),
                  security(11),
                  siren(12),
                  relay(13),
                  acvoltage(14),
                  vrms(15),
                  irms(16),
                  watt(17),
                  watthour(18),
                  xrelay(19),
                  thermocouple(20),
                  smoke(21),
                  drycontact-array(22),
                  temperature-array(23),
                  thermostat(128),
                  virtual(129),
                  sound(130),
                  softmotion(131),
                  camera-dummy(132),
                  board-state(133),
                  nosignal(224),
                  test(255)
               }
               ACCESS  read-only
               STATUS  mandatory
               DESCRIPTION
               "Enter the type of this Sensor"
               ::=  {  sensorEntry 3  }

            sensorValue OBJECT-TYPE
               SYNTAX  INTEGER
               ACCESS  read-only
               STATUS  mandatory
               DESCRIPTION
               "The value in this sensor"
               ::=  {  sensorEntry 4   }

            sensorUnit OBJECT-TYPE
               SYNTAX  DisplayString
               ACCESS  read-only
               STATUS  mandatory
               DESCRIPTION
               "The unit string"
               ::=  {  sensorEntry 5  }

            sensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this sensor"
               ::=  {  sensorEntry 6   }

            sensorGoOffline OBJECT-TYPE
               SYNTAX  INTEGER {
                  online(1),
                  goOffline(2)
               }
               ACCESS  read-write
               STATUS  mandatory
               DESCRIPTION
               "To take offline enter a 2"
               ::=  {  sensorEntry 8   }

            sensorPort OBJECT-TYPE
               SYNTAX  INTEGER (0..65534)
               ACCESS  read-only
               STATUS  mandatory
               DESCRIPTION
               "Sensor port"
               ::=  {  sensorEntry 35 }

            sensorSubPort OBJECT-TYPE
               SYNTAX  INTEGER (0..65534)
               ACCESS  read-only
               STATUS  mandatory
               DESCRIPTION
               "Sensor sub port"
               ::=  {  sensorEntry 36 }

            sensorDeviceIndex OBJECT-TYPE
               SYNTAX  INTEGER (0..65534)
               ACCESS  read-only
               STATUS  mandatory
               DESCRIPTION
               "Device Index of sensor"
               ::=  {  sensorEntry 37 }

            sensorDisplayStyle OBJECT-TYPE
               SYNTAX  INTEGER {
                  basic(0),
                  gauge(1)
               }
               ACCESS  read-write
               STATUS  mandatory
               DESCRIPTION
               "Temperature display style"
               ::=  {  sensorEntry 45 }   

            sensorHighCriticalDescription OBJECT-TYPE
               SYNTAX  DisplayString
               ACCESS  read-write
               STATUS  mandatory
               DESCRIPTION
               "A HighCritical Description of this sensor"
               ::=  {  sensorEntry  46  }

            sensorLowCriticalDescription OBJECT-TYPE
               SYNTAX  DisplayString
               ACCESS  read-write
               STATUS  mandatory
               DESCRIPTION
               "A LowCritical Description of this sensor"
               ::=  {  sensorEntry  47  }

            sensorNormalDescription OBJECT-TYPE
               SYNTAX  DisplayString
               ACCESS  read-write
               STATUS  mandatory
               DESCRIPTION
               "A Normal Description of this sensor"
               ::=  {  sensorEntry  48  }
               
            sensorLowWarningDescription OBJECT-TYPE
               SYNTAX  DisplayString
               ACCESS  read-write
               STATUS  mandatory
               DESCRIPTION
               "A LowWarning Description of this sensor"
               ::=  {  sensorEntry  49  }
               
            sensorHighWarningDescription OBJECT-TYPE
               SYNTAX  DisplayString
               ACCESS  read-write
               STATUS  mandatory
               DESCRIPTION
               "A HighWarning Description of this sensor"
               ::=  {  sensorEntry  50  }
               
            sensorErrorDescription OBJECT-TYPE
               SYNTAX  DisplayString
               ACCESS  read-write
               STATUS  mandatory
               DESCRIPTION
               "A SensorError Description of this sensor"
               ::=  {  sensorEntry  51  }
               
            sensorOnDescription OBJECT-TYPE
               SYNTAX  DisplayString
               ACCESS  read-write
               STATUS  mandatory
               DESCRIPTION
               "A On Description of this sensor"
               ::=  {  sensorEntry  52  }     

            sensorOffDescription OBJECT-TYPE
               SYNTAX  DisplayString
               ACCESS  read-write
               STATUS  mandatory
               DESCRIPTION
               "A Off Description of this sensor"
               ::=  {  sensorEntry  53  }

            sensorHighCriticalColor OBJECT-TYPE
               SYNTAX  INTEGER
               ACCESS  read-write
               STATUS  mandatory
               DESCRIPTION
               "A HighCritical Color of this sensor"
               ::=  {  sensorEntry  54  }

            sensorLowCriticalColor OBJECT-TYPE
               SYNTAX  INTEGER
               ACCESS  read-write
               STATUS  mandatory
               DESCRIPTION
               "A LowCritical Color of this sensor"
               ::=  {  sensorEntry  55  }

            sensorNormalColor OBJECT-TYPE
               SYNTAX  INTEGER
               ACCESS  read-write
               STATUS  mandatory
               DESCRIPTION
               "A Normal Color of this sensor"
               ::=  {  sensorEntry  56  }
               
            sensorLowWarningColor OBJECT-TYPE
               SYNTAX  INTEGER
               ACCESS  read-write
               STATUS  mandatory
               DESCRIPTION
               "A LowWarning Color of this sensor"
               ::=  {  sensorEntry  57  }
               
            sensorHighWarningColor OBJECT-TYPE
               SYNTAX  INTEGER
               ACCESS  read-write
               STATUS  mandatory
               DESCRIPTION
               "A HighWarning Color of this sensor"
               ::=  {  sensorEntry  58  }
               
            sensorErrorColor OBJECT-TYPE
               SYNTAX  INTEGER
               ACCESS  read-write
               STATUS  mandatory
               DESCRIPTION
               "A SensorError Color of this sensor"
               ::=  {  sensorEntry  59  }
               
            sensorOnColor OBJECT-TYPE
               SYNTAX  INTEGER
               ACCESS  read-write
               STATUS  mandatory
               DESCRIPTION
               "A On Color of this sensor"
               ::=  {  sensorEntry  60  }

            sensorOffColor OBJECT-TYPE
               SYNTAX  INTEGER
               ACCESS  read-write
               STATUS  mandatory
               DESCRIPTION
               "A Off Color of this sensor"
               ::=  {  sensorEntry  61  }
--/* End of sensorEntry */

--/* Begin of sensorTemperatureEntry */
         sensorTemperatureTable OBJECT-TYPE
            SYNTAX  SEQUENCE OF SensorTemperatureEntry
            ACCESS  not-accessible
            STATUS  mandatory
            DESCRIPTION
            "This table contains the property and reading value for every Temperature sensor."
            ::=  {  secSensor 2   }

         sensorTemperatureEntry OBJECT-TYPE
            SYNTAX  SensorTemperatureEntry
            ACCESS  not-accessible
            STATUS  mandatory
            DESCRIPTION
            "This is an entry in the sensorTemperatureEntry Table"
            INDEX         { sensorTemperatureIndex }
            ::=  {  sensorTemperatureTable 1 }

         SensorTemperatureEntry ::= SEQUENCE {
               sensorTemperatureIndex
                  INTEGER,
               sensorTemperatureDescription
                  DisplayString,
               sensorTemperatureType
                  INTEGER,
               sensorTemperatureDegree
                  INTEGER,
               sensorTemperatureUnit
                  DisplayString,               
               sensorTemperatureStatus
                  INTEGER,
               sensorTemperatureGoOffline
                  INTEGER,
               sensorTemperatureLowCritical
                  INTEGER,
               sensorTemperatureLowWarning
                  INTEGER,
               sensorTemperatureHighWarning
                  INTEGER,
               sensorTemperatureHighCritical
                  INTEGER,
               sensorTemperatureRearm
                  INTEGER,
               sensorTemperatureDelayError
                  INTEGER,
               sensorTemperatureDelayNormal
                  INTEGER,
               sensorTemperatureDelayLowCritical
                  INTEGER,
               sensorTemperatureDelayLowWarning
                  INTEGER,
               sensorTemperatureDelayHighWarning
                  INTEGER,
               sensorTemperatureDelayHighCritical
                  INTEGER,
               sensorTemperatureRaw
                  INTEGER,
               sensorTemperatureOffset
                  INTEGER,
               sensorTemperaturePort
                  INTEGER,
               sensorTemperatureSubPort
                  INTEGER,
               sensorTemperatureDeviceIndex
                  INTEGER,
               sensorTemperatureDisplayStyle
                  INTEGER,
               sensorTemperatureHighCriticalDesc 
                  DisplayString,
               sensorTemperatureLowCriticalDesc 
                  DisplayString,
               sensorTemperatureNormalDesc 
                  DisplayString,
               sensorTemperatureLowWarningDesc 
                  DisplayString,   
               sensorTemperatureHighWarningDesc 
                  DisplayString,
               sensorTemperatureSensorErrorDesc 
                  DisplayString,
               sensorTemperatureHighCriticalColor 
                  INTEGER,
               sensorTemperatureLowCriticalColor 
                  INTEGER,
               sensorTemperatureNormalColor 
                  INTEGER,
               sensorTemperatureLowWarningColor 
                  INTEGER,   
               sensorTemperatureHighWarningColor 
                  INTEGER,
               sensorTemperatureSensorErrorColor 
                  INTEGER                 
            }

            sensorTemperatureIndex OBJECT-TYPE
               SYNTAX  INTEGER (1..65535)
               ACCESS  read-only
               STATUS  mandatory
               DESCRIPTION
               "The index into the sensor table"
               ::=  {  sensorTemperatureEntry 1   }

            sensorTemperatureDescription OBJECT-TYPE
               SYNTAX  DisplayString
               ACCESS  read-write
               STATUS  mandatory
               DESCRIPTION
               "A Description of this sensor"
               ::=  {  sensorTemperatureEntry 2   }

            sensorTemperatureType OBJECT-TYPE
               SYNTAX  INTEGER {
                  temperature(1),
                  dualsensor(3),
                  thermocouple(20)
               }
               ACCESS  read-only
               STATUS  mandatory
               DESCRIPTION
               "Enter the type of this Sensor"
               ::=  {  sensorTemperatureEntry 3  }

            sensorTemperatureDegree OBJECT-TYPE
               SYNTAX  INTEGER
               ACCESS  read-only
               STATUS  mandatory
               DESCRIPTION
               "The degrees in this sensor"
               ::=  {  sensorTemperatureEntry 4   }

            sensorTemperatureUnit OBJECT-TYPE
               SYNTAX  DisplayString
               ACCESS  read-only
               STATUS  mandatory
               DESCRIPTION
               "The unit string"
               ::=  {  sensorTemperatureEntry 5  }

            sensorTemperatureStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTemperatureEntry 6   }
   
            sensorTemperatureGoOffline OBJECT-TYPE
               SYNTAX  INTEGER {
                  online(1),
                  goOffline(2)
               }
               ACCESS  read-write
               STATUS  mandatory
               DESCRIPTION
               "To take offline enter a 2"
               ::=  {  sensorTemperatureEntry 8   }

            sensorTemperatureLowCritical OBJECT-TYPE
               SYNTAX  INTEGER
               ACCESS  read-write
               STATUS  mandatory
               DESCRIPTION
               "How cold this sensor gets before it sends a critical event"
               ::=  {  sensorTemperatureEntry 9   }

            sensorTemperatureLowWarning OBJECT-TYPE
               SYNTAX  INTEGER
               ACCESS  read-write
               STATUS  mandatory
               DESCRIPTION
               "How cold this sensor gets before it sends a warning"
               ::=  {  sensorTemperatureEntry 10   }
   
            sensorTemperatureHighWarning OBJECT-TYPE
               SYNTAX  INTEGER
               ACCESS  read-write
               STATUS  mandatory
               DESCRIPTION
               "How hot this sensor gets before it sends a warning"
               ::=  {  sensorTemperatureEntry 11   }  

            sensorTemperatureHighCritical OBJECT-TYPE
               SYNTAX  INTEGER
               ACCESS  read-write
               STATUS  mandatory
               DESCRIPTION
               "How hot this sensor gets before it sends a critical event"
               ::=  {  sensorTemperatureEntry 12   }   

            sensorTemperatureRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorTemperatureEntry 13   }

            sensorTemperatureDelayError OBJECT-TYPE
               SYNTAX  INTEGER (0..65534)
               ACCESS  read-write
               STATUS  mandatory
               DESCRIPTION
               "Time in seconds after the sensor has been in error status before report as an error"
               ::=  {  sensorTemperatureEntry 14   }

            sensorTemperatureDelayNormal OBJECT-TYPE
               SYNTAX  INTEGER (0..65534)
               ACCESS  read-write
               STATUS  mandatory
               DESCRIPTION
               "Time in seconds after the sensor change from error to normal before report as normal"
               ::=  {  sensorTemperatureEntry 15   }

            sensorTemperatureDelayLowCritical OBJECT-TYPE
               SYNTAX INTEGER (0..65535)
               ACCESS read-write
               STATUS mandatory
               DESCRIPTION
               "Continuous time for this sensor to be in Low Critical before accepting new Status."
               ::= {  sensorTemperatureEntry 16 }
               
            sensorTemperatureDelayLowWarning OBJECT-TYPE
               SYNTAX INTEGER (0..65535)
               ACCESS read-write
               STATUS mandatory
               DESCRIPTION
               "Continuous time for this sensor to be in Low Warning before accepting new Status."
               ::= {  sensorTemperatureEntry 17 }

            sensorTemperatureDelayHighWarning OBJECT-TYPE
               SYNTAX INTEGER (0..65535)
               ACCESS read-write
               STATUS mandatory
               DESCRIPTION
               "Continuous time for this sensor to be in High Warning before accepting new Status."
               ::= {  sensorTemperatureEntry 18 }

            sensorTemperatureDelayHighCritical OBJECT-TYPE
               SYNTAX INTEGER (0..65535)
               ACCESS read-write
               STATUS mandatory
               DESCRIPTION
               "Continuous time for this sensor to be in High Critical before accepting new Status."
               ::= {  sensorTemperatureEntry 19 }

            sensorTemperatureRaw OBJECT-TYPE
               SYNTAX  INTEGER 
               ACCESS  read-only
               STATUS  mandatory
               DESCRIPTION
               "The raw degree data from the temperature sensor, slightly higher resolution"
               ::=  {  sensorTemperatureEntry 20 }

            sensorTemperatureOffset OBJECT-TYPE
               SYNTAX  INTEGER
               ACCESS  read-write
               STATUS  mandatory
               DESCRIPTION
               "Temperature Offset reading"
               ::=  {  sensorTemperatureEntry 21 }

            sensorTemperaturePort OBJECT-TYPE
               SYNTAX  INTEGER (0..65534)
               ACCESS  read-only
               STATUS  mandatory
               DESCRIPTION
               "Sensor port"
               ::=  {  sensorTemperatureEntry 35 }

            sensorTemperatureSubPort OBJECT-TYPE
               SYNTAX  INTEGER (0..65534)
               ACCESS  read-only
               STATUS  mandatory
               DESCRIPTION
               "Sensor sub port"
               ::=  {  sensorTemperatureEntry 36 }

            sensorTemperatureDeviceIndex OBJECT-TYPE
               SYNTAX  INTEGER (0..65534)
               ACCESS  read-only
               STATUS  mandatory
               DESCRIPTION
               "Device Index of sensor"
               ::=  {  sensorTemperatureEntry 37 }
               
            sensorTemperatureDisplayStyle OBJECT-TYPE
               SYNTAX  INTEGER {
                  basic(0),
                  gauge(1)
               }
               ACCESS  read-write
               STATUS  mandatory
               DESCRIPTION
               "Temperature display style"
               ::=  {  sensorTemperatureEntry 45 }   

            sensorTemperatureHighCriticalDesc OBJECT-TYPE
               SYNTAX  DisplayString
               ACCESS  read-write
               STATUS  mandatory
               DESCRIPTION
               "A HighCritical Description of this sensor"
               ::=  {  sensorTemperatureEntry  46  }               

            sensorTemperatureLowCriticalDesc OBJECT-TYPE
               SYNTAX  DisplayString
               ACCESS  read-write
               STATUS  mandatory
               DESCRIPTION
               "A LowCritical Description of this sensor"
               ::=  {  sensorTemperatureEntry  47  }

            sensorTemperatureNormalDesc OBJECT-TYPE
               SYNTAX  DisplayString
               ACCESS  read-write
               STATUS  mandatory
               DESCRIPTION
               "A Normal Description of this sensor"
               ::=  {  sensorTemperatureEntry  48  }
               
            sensorTemperatureLowWarningDesc OBJECT-TYPE
               SYNTAX  DisplayString
               ACCESS  read-write
               STATUS  mandatory
               DESCRIPTION
               "A LowWarning Description of this sensor"
               ::=  {  sensorTemperatureEntry  49  }
               
            sensorTemperatureHighWarningDesc OBJECT-TYPE
               SYNTAX  DisplayString
               ACCESS  read-write
               STATUS  mandatory
               DESCRIPTION
               "A HighWarning Description of this sensor"
               ::=  {  sensorTemperatureEntry  50  }
               
            sensorTemperatureSensorErrorDesc OBJECT-TYPE
               SYNTAX  DisplayString
               ACCESS  read-write
               STATUS  mandatory
               DESCRIPTION
               "A SensorError Description of this sensor"
               ::=  {  sensorTemperatureEntry  51  }

            sensorTemperatureHighCriticalColor OBJECT-TYPE
               SYNTAX  INTEGER
               ACCESS  read-write
               STATUS  mandatory
               DESCRIPTION
               "A HighCritical Color of this sensor"
               ::=  {  sensorTemperatureEntry  54  }               

            sensorTemperatureLowCriticalColor OBJECT-TYPE
               SYNTAX  INTEGER
               ACCESS  read-write
               STATUS  mandatory
               DESCRIPTION
               "A LowCritical Color of this sensor"
               ::=  {  sensorTemperatureEntry  55  }

            sensorTemperatureNormalColor OBJECT-TYPE
               SYNTAX  INTEGER
               ACCESS  read-write
               STATUS  mandatory
               DESCRIPTION
               "A Normal Color of this sensor"
               ::=  {  sensorTemperatureEntry  56  }
               
            sensorTemperatureLowWarningColor OBJECT-TYPE
               SYNTAX  INTEGER
               ACCESS  read-write
               STATUS  mandatory
               DESCRIPTION
               "A LowWarning Color of this sensor"
               ::=  {  sensorTemperatureEntry  57  }
               
            sensorTemperatureHighWarningColor OBJECT-TYPE
               SYNTAX  INTEGER
               ACCESS  read-write
               STATUS  mandatory
               DESCRIPTION
               "A HighWarning Color of this sensor"
               ::=  {  sensorTemperatureEntry  58  }
               
            sensorTemperatureSensorErrorColor OBJECT-TYPE
               SYNTAX  INTEGER
               ACCESS  read-write
               STATUS  mandatory
               DESCRIPTION
               "A SensorError Color of this sensor"
               ::=  {  sensorTemperatureEntry  59  }                 
               
--/* End of sensorTemperatureEntry */

--/* Begin of sensorHumidityEntry */
         sensorHumidityTable OBJECT-TYPE
            SYNTAX  SEQUENCE OF SensorHumidityEntry
            ACCESS  not-accessible
            STATUS  mandatory
            DESCRIPTION
            "This table contains the property and reading value for every sensor."
            ::=  {  secSensor 3   }

         sensorHumidityEntry OBJECT-TYPE
            SYNTAX  SensorHumidityEntry
            ACCESS  not-accessible
            STATUS  mandatory
            DESCRIPTION
            "This is an entry in the sensorTemperatureEntry Table"
            INDEX         { sensorHumidityIndex }
            ::=  {  sensorHumidityTable 1 }

         SensorHumidityEntry ::= SEQUENCE {
               sensorHumidityIndex
                  INTEGER,
               sensorHumidityDescription
                  DisplayString,
               sensorHumidityPercent
                  INTEGER,
               sensorHumidityUnit
                  DisplayString,
               sensorHumidityStatus
                  INTEGER,
               sensorHumidityGoOffline
                  INTEGER,
               sensorHumidityLowCritical
                  INTEGER,
               sensorHumidityLowWarning
                  INTEGER,
               sensorHumidityHighWarning
                  INTEGER,
               sensorHumidityHighCritical
                  INTEGER,
               sensorHumidityRearm
                  INTEGER,
               sensorHumidityDelayError
                  INTEGER,
               sensorHumidityDelayNormal
                  INTEGER,
               sensorHumidityDelayLowCritical
                  INTEGER,
               sensorHumidityDelayLowWarning
                  INTEGER,
               sensorHumidityDelayHighWarning
                  INTEGER,
               sensorHumidityDelayHighCritical
                  INTEGER,
               sensorHumidityRaw
                  INTEGER,
               sensorHumidityOffset
                  INTEGER,
               sensorHumidityPort
                  INTEGER,
               sensorHumiditySubPort
                  INTEGER,
               sensorHumidityDeviceIndex
                  INTEGER,
               sensorHumidityDisplayStyle
                  INTEGER,
               sensorHumidityHighCriticalDesc 
                  DisplayString,
               sensorHumidityLowCriticalDesc 
                  DisplayString,
               sensorHumidityNormalDesc 
                  DisplayString,
               sensorHumidityLowWarningDesc 
                  DisplayString,   
               sensorHumidityHighWarningDesc 
                  DisplayString,
               sensorHumiditySensorErrorDesc 
                  DisplayString,
               sensorHumidityHighCriticalColor 
                  INTEGER,
               sensorHumidityLowCriticalColor 
                  INTEGER,
               sensorHumidityNormalColor 
                  INTEGER,
               sensorHumidityLowWarningColor 
                  INTEGER,   
               sensorHumidityHighWarningColor 
                  INTEGER,
               sensorHumiditySensorErrorColor 
                  INTEGER                
            }

            sensorHumidityIndex OBJECT-TYPE
               SYNTAX  INTEGER (1..65535)
               ACCESS  read-only
               STATUS  mandatory
               DESCRIPTION
               "The index into the sensor table"
               ::=  {  sensorHumidityEntry 1   }

            sensorHumidityDescription OBJECT-TYPE
               SYNTAX  DisplayString
               ACCESS  read-write
               STATUS  mandatory
               DESCRIPTION
               "A Description of this sensor"
               ::=  {  sensorHumidityEntry 2   }

            sensorHumidityPercent OBJECT-TYPE
               SYNTAX  INTEGER
               ACCESS  read-only
               STATUS  mandatory
               DESCRIPTION
               "The relative humidity percentage measured by this sensor"
               ::=  {  sensorHumidityEntry 4   }

            sensorHumidityUnit OBJECT-TYPE
               SYNTAX  DisplayString
               ACCESS  read-write
               STATUS  mandatory
               DESCRIPTION
               "The unit string"
               ::=  {  sensorHumidityEntry 5  }

            sensorHumidityStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorHumidityEntry 6   }

            sensorHumidityGoOffline OBJECT-TYPE
               SYNTAX  INTEGER {
                  online(1),
                  goOffline(2)
               }
               ACCESS  read-write
               STATUS  mandatory
               DESCRIPTION
               "To take offline enter a 2"
               ::=  {  sensorHumidityEntry 8   }

            sensorHumidityLowCritical OBJECT-TYPE
               SYNTAX  INTEGER
               ACCESS  read-write
               STATUS  mandatory
               DESCRIPTION
               "How cold this sensor gets before it sends a critical event"
               ::=  {  sensorHumidityEntry 9   }

            sensorHumidityLowWarning OBJECT-TYPE
               SYNTAX  INTEGER
               ACCESS  read-write
               STATUS  mandatory
               DESCRIPTION
               "How cold this sensor gets before it sends a warning"
               ::=  {  sensorHumidityEntry 10   }
   
            sensorHumidityHighWarning OBJECT-TYPE
               SYNTAX  INTEGER
               ACCESS  read-write
               STATUS  mandatory
               DESCRIPTION
               "How hot this sensor gets before it sends a warning"
               ::=  {  sensorHumidityEntry 11   }  

            sensorHumidityHighCritical OBJECT-TYPE
               SYNTAX  INTEGER
               ACCESS  read-write
               STATUS  mandatory
               DESCRIPTION
               "How hot this sensor gets before it sends a critical event"
               ::=  {  sensorHumidityEntry 12   }   

            sensorHumidityRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorHumidityEntry 13   }

            sensorHumidityDelayError OBJECT-TYPE
               SYNTAX  INTEGER (0..65534)
               ACCESS  read-write
               STATUS  mandatory
               DESCRIPTION
               "Time in seconds after the sensor has been in error status before report as an error"
               ::=  {  sensorHumidityEntry 14   }

            sensorHumidityDelayNormal OBJECT-TYPE
               SYNTAX  INTEGER (0..65534)
               ACCESS  read-write
               STATUS  mandatory
               DESCRIPTION
               "Time in seconds after the sensor change from error to normal before report as normal"
               ::=  {  sensorHumidityEntry 15   }

            sensorHumidityDelayLowCritical OBJECT-TYPE
               SYNTAX INTEGER (0..65535)
               ACCESS read-write
               STATUS mandatory
               DESCRIPTION
               "Continuous time for this sensor to be in Low Critical before accepting new Status."
               ::= {  sensorHumidityEntry 16 }
               
            sensorHumidityDelayLowWarning OBJECT-TYPE
               SYNTAX INTEGER (0..65535)
               ACCESS read-write
               STATUS mandatory
               DESCRIPTION
               "Continuous time for this sensor to be in Low Warning before accepting new Status."
               ::= {  sensorHumidityEntry 17 }

            sensorHumidityDelayHighWarning OBJECT-TYPE
               SYNTAX INTEGER (0..65535)
               ACCESS read-write
               STATUS mandatory
               DESCRIPTION
               "Continuous time for this sensor to be in High Warning before accepting new Status."
               ::= {  sensorHumidityEntry 18 }

            sensorHumidityDelayHighCritical OBJECT-TYPE
               SYNTAX INTEGER (0..65535)
               ACCESS read-write
               STATUS mandatory
               DESCRIPTION
               "Continuous time for this sensor to be in High Critical before accepting new Status."
               ::= {  sensorHumidityEntry 19 }

            sensorHumidityRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorHumidityEntry 20   }

            sensorHumidityOffset OBJECT-TYPE
               SYNTAX  INTEGER
               ACCESS  read-write
               STATUS  mandatory
               DESCRIPTION
               "Humidity Offset reading"
               ::=  {  sensorHumidityEntry 21   }

            sensorHumidityPort OBJECT-TYPE
               SYNTAX  INTEGER (0..65534)
               ACCESS  read-only
               STATUS  mandatory
               DESCRIPTION
               "Sensor port"
               ::=  {  sensorHumidityEntry 35 }

            sensorHumiditySubPort OBJECT-TYPE
               SYNTAX  INTEGER (0..65534)
               ACCESS  read-only
               STATUS  mandatory
               DESCRIPTION
               "Sensor sub port"
               ::=  {  sensorHumidityEntry 36 }

            sensorHumidityDeviceIndex OBJECT-TYPE
               SYNTAX  INTEGER (0..65534)
               ACCESS  read-only
               STATUS  mandatory
               DESCRIPTION
               "Device Index of sensor"
               ::=  {  sensorHumidityEntry 37 }
               
            sensorHumidityDisplayStyle OBJECT-TYPE
               SYNTAX  INTEGER {
                  basic(0),
                  gauge(1)
               }
               ACCESS  read-write
               STATUS  mandatory
               DESCRIPTION
               "Humidity display style"
               ::=  {  sensorHumidityEntry 45 }           
               
            sensorHumidityHighCriticalDesc OBJECT-TYPE
               SYNTAX  DisplayString
               ACCESS  read-write
               STATUS  mandatory
               DESCRIPTION
               "A HighCritical Description of this sensor"
               ::=  {  sensorHumidityEntry  46  }               

            sensorHumidityLowCriticalDesc OBJECT-TYPE
               SYNTAX  DisplayString
               ACCESS  read-write
               STATUS  mandatory
               DESCRIPTION
               "A LowCritical Description of this sensor"
               ::=  {  sensorHumidityEntry  47  }

            sensorHumidityNormalDesc OBJECT-TYPE
               SYNTAX  DisplayString
               ACCESS  read-write
               STATUS  mandatory
               DESCRIPTION
               "A Normal Description of this sensor"
               ::=  {  sensorHumidityEntry  48  }
               
            sensorHumidityLowWarningDesc OBJECT-TYPE
               SYNTAX  DisplayString
               ACCESS  read-write
               STATUS  mandatory
               DESCRIPTION
               "A LowWarning Description of this sensor"
               ::=  {  sensorHumidityEntry  49  }
               
            sensorHumidityHighWarningDesc OBJECT-TYPE
               SYNTAX  DisplayString
               ACCESS  read-write
               STATUS  mandatory
               DESCRIPTION
               "A HighWarning Description of this sensor"
               ::=  {  sensorHumidityEntry  50  }
               
            sensorHumiditySensorErrorDesc OBJECT-TYPE
               SYNTAX  DisplayString
               ACCESS  read-write
               STATUS  mandatory
               DESCRIPTION
               "A SensorError Description of this sensor"
               ::=  {  sensorHumidityEntry  51  }  

            sensorHumidityHighCriticalColor OBJECT-TYPE
               SYNTAX  INTEGER
               ACCESS  read-write
               STATUS  mandatory
               DESCRIPTION
               "A HighCritical Color of this sensor"
               ::=  {  sensorHumidityEntry  54  }               

            sensorHumidityLowCriticalColor OBJECT-TYPE
               SYNTAX  INTEGER
               ACCESS  read-write
               STATUS  mandatory
               DESCRIPTION
               "A LowCritical Color of this sensor"
               ::=  {  sensorHumidityEntry  55  }

            sensorHumidityNormalColor OBJECT-TYPE
               SYNTAX  INTEGER
               ACCESS  read-write
               STATUS  mandatory
               DESCRIPTION
               "A Normal Color of this sensor"
               ::=  {  sensorHumidityEntry  56  }
               
            sensorHumidityLowWarningColor OBJECT-TYPE
               SYNTAX  INTEGER
               ACCESS  read-write
               STATUS  mandatory
               DESCRIPTION
               "A LowWarning Color of this sensor"
               ::=  {  sensorHumidityEntry  57  }
               
            sensorHumidityHighWarningColor OBJECT-TYPE
               SYNTAX  INTEGER
               ACCESS  read-write
               STATUS  mandatory
               DESCRIPTION
               "A HighWarning Color of this sensor"
               ::=  {  sensorHumidityEntry  58  }
               
            sensorHumiditySensorErrorColor OBJECT-TYPE
               SYNTAX  INTEGER
               ACCESS  read-write
               STATUS  mandatory
               DESCRIPTION
               "A SensorError Color of this sensor"
               ::=  {  sensorHumidityEntry  59  }           

--/* End of sensorHumidityEntry */

--/* Begin of sensorDryContactEntry */
         sensorDryContactTable OBJECT-TYPE
            SYNTAX  SEQUENCE OF SensorDryContactEntry
            ACCESS  not-accessible
            STATUS  mandatory
            DESCRIPTION
            "This table contains the property and reading value for every sensor."
            ::=  {  secSensor 4   }

         sensorDryContactEntry OBJECT-TYPE
            SYNTAX  SensorDryContactEntry
            ACCESS  not-accessible
            STATUS  mandatory
            DESCRIPTION
            "This is an entry in the sensorTemperatureEntry Table"
            INDEX         { sensorDryContactIndex }
            ::=  {  sensorDryContactTable 1 }

         SensorDryContactEntry ::= SEQUENCE {
               sensorDryContactIndex
                  INTEGER,
               sensorDryContactDescription
                  DisplayString,
               sensorDryContactType
                  INTEGER,
               sensorDryContactStatus
                  INTEGER,
               sensorDryContactGoOffline
                  INTEGER,
               sensorDryContactDirection
                  INTEGER,
               sensorDryContactNormalState
                  INTEGER,
               sensorDryContactControlMode
                  INTEGER,
               sensorDryContactOutputManualCycleTime
                  INTEGER,
               sensorDryContactOutputManualAction
                  INTEGER,
               sensorDryContactPort
                  INTEGER,
               sensorDryContactSubPort
                  INTEGER,
               sensorDryContactDeviceIndex
                  INTEGER,
               sensorDryContactCriticalDesc 
                  DisplayString,
               sensorDryContactNormalDesc 
                  DisplayString,
               sensorDryContactOnDesc
                  DisplayString,
               sensorDryContactOffDesc
                  DisplayString,
               sensorDryContactCriticalColor 
                  INTEGER,
               sensorDryContactNormalColor 
                  INTEGER,
               sensorDryContactOnColor
                  INTEGER,
               sensorDryContactOffColor
                  INTEGER                 
            }

            sensorDryContactIndex OBJECT-TYPE
               SYNTAX  INTEGER (1..65535)
               ACCESS  read-only
               STATUS  mandatory
               DESCRIPTION
               "The index into the Switch sensor table"
               ::=  {  sensorDryContactEntry 1   }

            sensorDryContactDescription OBJECT-TYPE
               SYNTAX  DisplayString
               ACCESS  read-write
               STATUS  mandatory
               DESCRIPTION
               "A Description of this sensor Switch"
               ::=  {  sensorDryContactEntry 2   }

            sensorDryContactType OBJECT-TYPE
               SYNTAX  INTEGER {
                  drycontact-inout(7),
                  drycontact-input(8),
                  drycontact-array(22)
               }
               ACCESS  read-only
               STATUS  mandatory
               DESCRIPTION
               "Enter the type of this Sensor"
               ::=  {  sensorDryContactEntry 3  }

            sensorDryContactStatus OBJECT-TYPE
               SYNTAX  INTEGER {
                  noStatus(1),
                  normal(2),
                  highCritical(4),
                  lowCritical(6),
                  sensorError(7),
                  outputLow(8),
                  outputHigh(9)
               }
               ACCESS  read-only
               STATUS  mandatory
               DESCRIPTION
               "The current status of this Sensor, only input switches have a status"
               ::=  {  sensorDryContactEntry 6  }

            sensorDryContactGoOffline OBJECT-TYPE
               SYNTAX  INTEGER {
                  online(1),
                  goOffline(2)
               }
               ACCESS  read-write
               STATUS  mandatory
               DESCRIPTION
               "To take offline enter a 2"
               ::=  {  sensorDryContactEntry 8  }

            sensorDryContactDirection OBJECT-TYPE
               SYNTAX  INTEGER {
                  input(0),
                  output(1)
               }
               ACCESS  read-write
               STATUS  mandatory
               DESCRIPTION
               "To set a switch to input enter 0. To set a switch to output enter 1"
               ::=  {  sensorDryContactEntry 22  }

            sensorDryContactNormalState OBJECT-TYPE
               SYNTAX  INTEGER {
                  closed(0),
                  open(1)
               }
               ACCESS  read-write
               STATUS  mandatory
               DESCRIPTION
               "The normal state of an input switch. If an input switch is in this state it is normal, else it is critical. An open switch senses +5 volts. A closed switch senses 0 volts."
               ::=  {  sensorDryContactEntry 23  }
               
            sensorDryContactControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a sensor output."
               ::=  {  sensorDryContactEntry 24  }
               
            sensorDryContactOutputManualCycleTime OBJECT-TYPE
               SYNTAX  INTEGER (1..255)
               ACCESS  read-write
               STATUS  mandatory
               DESCRIPTION
               "Toggle period in seconds for Manual Cycle action."
               ::=  {  sensorDryContactEntry 25  }
               
            sensorDryContactOutputManualAction OBJECT-TYPE
               SYNTAX  INTEGER {
                  low(0),
                  high(1),
                  cycle-Low-High-Low(2),
                  cycle-High-Low-High(3)
               }
               ACCESS  read-write
               STATUS  mandatory
               DESCRIPTION
               "Control the sensor output manualy"
               ::=  {  sensorDryContactEntry 26  }

            sensorDryContactPort OBJECT-TYPE
               SYNTAX  INTEGER (0..65534)
               ACCESS  read-only
               STATUS  mandatory
               DESCRIPTION
               "Sensor port"
               ::=  {  sensorDryContactEntry 35 }

            sensorDryContactSubPort OBJECT-TYPE
               SYNTAX  INTEGER (0..65534)
               ACCESS  read-only
               STATUS  mandatory
               DESCRIPTION
               "Sensor sub port"
               ::=  {  sensorDryContactEntry 36 }

            sensorDryContactDeviceIndex OBJECT-TYPE
               SYNTAX  INTEGER (0..65534)
               ACCESS  read-only
               STATUS  mandatory
               DESCRIPTION
               "Device Index of sensor"
               ::=  {  sensorDryContactEntry 37 }
               
            sensorDryContactCriticalDesc OBJECT-TYPE
               SYNTAX  DisplayString
               ACCESS  read-write
               STATUS  mandatory
               DESCRIPTION
               "A Critical Description of this sensor"
               ::=  {  sensorDryContactEntry  46 } 

            sensorDryContactNormalDesc OBJECT-TYPE
               SYNTAX  DisplayString
               ACCESS  read-write
               STATUS  mandatory
               DESCRIPTION
               "A Normal Description of this sensor"
               ::=  {  sensorDryContactEntry  48  }

            sensorDryContactOnDesc OBJECT-TYPE
               SYNTAX  DisplayString
               ACCESS  read-write
               STATUS  mandatory
               DESCRIPTION
               "A On Description of this sensor"
               ::=  {  sensorDryContactEntry  52  }     

            sensorDryContactOffDesc OBJECT-TYPE
               SYNTAX  DisplayString
               ACCESS  read-write
               STATUS  mandatory
               DESCRIPTION
               "A Off Description of this sensor"
               ::=  {  sensorDryContactEntry  53  }                   

            sensorDryContactCriticalColor OBJECT-TYPE
               SYNTAX  INTEGER
               ACCESS  read-write
               STATUS  mandatory
               DESCRIPTION
               "A Critical Color of this sensor"
               ::=  {  sensorDryContactEntry  54  }               

            sensorDryContactNormalColor OBJECT-TYPE
               SYNTAX  INTEGER
               ACCESS  read-write
               STATUS  mandatory
               DESCRIPTION
               "A Normal Color of this sensor"
               ::=  {  sensorDryContactEntry  56  }

            sensorDryContactOnColor OBJECT-TYPE
               SYNTAX  INTEGER
               ACCESS  read-write
               STATUS  mandatory
               DESCRIPTION
               "A On Color of this sensor"
               ::=  {  sensorDryContactEntry  60  }    

            sensorDryContactOffColor OBJECT-TYPE
               SYNTAX  INTEGER
               ACCESS  read-write
               STATUS  mandatory
               DESCRIPTION
               "A Off Color of this sensor"
               ::=  {  sensorDryContactEntry  61  }                 
               
--/* End of sensorDryContactEntry */

--/* Begin of sensor4to20mAEntry */
         sensor4to20mATable OBJECT-TYPE
            SYNTAX  SEQUENCE OF Sensor4to20mAEntry
            ACCESS  not-accessible
            STATUS  mandatory
            DESCRIPTION
            "This table contains the property and reading value for every sensor."
            ::=  {  secSensor 5   }

         sensor4to20mAEntry OBJECT-TYPE
            SYNTAX  Sensor4to20mAEntry
            ACCESS  not-accessible
            STATUS  mandatory
            DESCRIPTION
            "This is an entry in the sensorTemperatureEntry Table"
            INDEX         { sensor4to20mAIndex }
            ::=  {  sensor4to20mATable 1 }

         Sensor4to20mAEntry ::= SEQUENCE {
               sensor4to20mAIndex
                  INTEGER,
               sensor4to20mADescription
                  DisplayString,
               sensor4to20mAValue
                  INTEGER,
               sensor4to20mAUnit
                  DisplayString,
               sensor4to20mAStatus
                  INTEGER,
               sensor4to20mAGoOffline
                  INTEGER,
               sensor4to20mALowCritical
                  INTEGER,
               sensor4to20mALowWarning
                  INTEGER,
               sensor4to20mAHighWarning
                  INTEGER,
               sensor4to20mAHighCritical
                  INTEGER,
               sensor4to20mARearm
                  INTEGER,
               sensor4to20mADelayError
                  INTEGER,
               sensor4to20mADelayNormal
                  INTEGER,
               sensor4to20mADelayLowCritical
                  INTEGER,
               sensor4to20mADelayLowWarning
                  INTEGER,
               sensor4to20mADelayHighWarning
                  INTEGER,
               sensor4to20mADelayHighCritical
                  INTEGER,
               sensor4to20mARaw
                  INTEGER,
               sensor4to20mAOffset
                  INTEGER,
               sensor4to20mAAmountMaxVoltage
                  INTEGER,
               sensor4to20mAAmountBaseVoltage
                  INTEGER,
               sensor4to20mAPort
                  INTEGER,
               sensor4to20mASubPort
                  INTEGER,
               sensor4to20mADeviceIndex
                  INTEGER,
               sensor4to20mAMaxVoltage
                  INTEGER,
               sensor4to20mABaseVoltage
                  INTEGER,
               sensor4to20mADisplayStyle
                  INTEGER,
               sensor4to20mAHighCriticalDesc 
                  DisplayString,
               sensor4to20mALowCriticalDesc 
                  DisplayString,
               sensor4to20mANormalDesc 
                  DisplayString,
               sensor4to20mALowWarningDesc 
                  DisplayString,   
               sensor4to20mAHighWarningDesc 
                  DisplayString,
               sensor4to20mASensorErrorDesc 
                  DisplayString,
               sensor4to20mAHighCriticalColor 
                  INTEGER,
               sensor4to20mALowCriticalColor 
                  INTEGER,
               sensor4to20mANormalColor 
                  INTEGER,
               sensor4to20mALowWarningColor 
                  INTEGER,   
               sensor4to20mAHighWarningColor 
                  INTEGER,
               sensor4to20mASensorErrorColor 
                  INTEGER                   
            }

            sensor4to20mAIndex OBJECT-TYPE
               SYNTAX  INTEGER (1..65535)
               ACCESS  read-only
               STATUS  mandatory
               DESCRIPTION
               "The index into the sensor table"
               ::=  {  sensor4to20mAEntry 1   }

            sensor4to20mADescription OBJECT-TYPE
               SYNTAX  DisplayString
               ACCESS  read-write
               STATUS  mandatory
               DESCRIPTION
               "A Description of this sensor"
               ::=  {  sensor4to20mAEntry 2   }

            sensor4to20mAValue OBJECT-TYPE
               SYNTAX  INTEGER
               ACCESS  read-only
               STATUS  mandatory
               DESCRIPTION
               "The reading value in this sensor"
               ::=  {  sensor4to20mAEntry 4   }

            sensor4to20mAUnit OBJECT-TYPE
               SYNTAX  DisplayString
               ACCESS  read-write
               STATUS  mandatory
               DESCRIPTION
               "The unit string"
               ::=  {  sensor4to20mAEntry 5  }

            sensor4to20mAStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensor4to20mAEntry 6   }

            sensor4to20mAGoOffline OBJECT-TYPE
               SYNTAX  INTEGER {
                  online(1),
                  goOffline(2)
               }
               ACCESS  read-write
               STATUS  mandatory
               DESCRIPTION
               "To take offline enter a 2"
               ::=  {  sensor4to20mAEntry 8   }

            sensor4to20mALowCritical OBJECT-TYPE
               SYNTAX  INTEGER
               ACCESS  read-write
               STATUS  mandatory
               DESCRIPTION
               "How cold this sensor gets before it sends a critical event"
               ::=  {  sensor4to20mAEntry 9   }

            sensor4to20mALowWarning OBJECT-TYPE
               SYNTAX  INTEGER
               ACCESS  read-write
               STATUS  mandatory
               DESCRIPTION
               "How cold this sensor gets before it sends a warning"
               ::=  {  sensor4to20mAEntry 10   }
   
            sensor4to20mAHighWarning OBJECT-TYPE
               SYNTAX  INTEGER
               ACCESS  read-write
               STATUS  mandatory
               DESCRIPTION
               "How hot this sensor gets before it sends a warning"
               ::=  {  sensor4to20mAEntry 11   }  

            sensor4to20mAHighCritical OBJECT-TYPE
               SYNTAX  INTEGER
               ACCESS  read-write
               STATUS  mandatory
               DESCRIPTION
               "How hot this sensor gets before it sends a critical event"
               ::=  {  sensor4to20mAEntry 12   }   

            sensor4to20mARearm OBJECT-TYPE
               SYNTAX  INTEGER
               ACCESS  read-write
               STATUS  mandatory
               DESCRIPTION
               "The number of degrees to rearm the status. For example if status goes from normal to warning, the temp must go down spTempRearm degrees below warning before the status goes to normal"
               ::=  {  sensor4to20mAEntry 13   }

            sensor4to20mADelayError OBJECT-TYPE
               SYNTAX  INTEGER (0..65534)
               ACCESS  read-write
               STATUS  mandatory
               DESCRIPTION
               "Time in seconds after the sensor has been in error status before report as an error"
               ::=  {  sensor4to20mAEntry 14   }

            sensor4to20mADelayNormal OBJECT-TYPE
               SYNTAX  INTEGER (0..65534)
               ACCESS  read-write
               STATUS  mandatory
               DESCRIPTION
               "Time in seconds after the sensor change from error to normal before report as normal"
               ::=  {  sensor4to20mAEntry 15   }

            sensor4to20mADelayLowCritical OBJECT-TYPE
               SYNTAX INTEGER (0..65535)
               ACCESS read-write
               STATUS mandatory
               DESCRIPTION
               "Continuous time for this sensor to be in Low Critical before accepting new Status."
               ::= {  sensor4to20mAEntry 16 }
               
            sensor4to20mADelayLowWarning OBJECT-TYPE
               SYNTAX INTEGER (0..65535)
               ACCESS read-write
               STATUS mandatory
               DESCRIPTION
               "Continuous time for this sensor to be in Low Warning before accepting new Status."
               ::= {  sensor4to20mAEntry 17 }

            sensor4to20mADelayHighWarning OBJECT-TYPE
               SYNTAX INTEGER (0..65535)
               ACCESS read-write
               STATUS mandatory
               DESCRIPTION
               "Continuous time for this sensor to be in High Warning before accepting new Status."
               ::= {  sensor4to20mAEntry 18 }

            sensor4to20mADelayHighCritical OBJECT-TYPE
               SYNTAX INTEGER (0..65535)
               ACCESS read-write
               STATUS mandatory
               DESCRIPTION
               "Continuous time for this sensor to be in High Critical before accepting new Status."
               ::= {  sensor4to20mAEntry 19 }

            sensor4to20mARaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensor4to20mAEntry 20   }

            sensor4to20mAOffset OBJECT-TYPE
               SYNTAX  INTEGER
               ACCESS  read-write
               STATUS  mandatory
               DESCRIPTION
               "4to20mA Offset reading"
               ::=  {  sensor4to20mAEntry 21   }

            sensor4to20mAAmountMaxVoltage OBJECT-TYPE
               SYNTAX  INTEGER
               ACCESS  read-write
               STATUS  mandatory
               DESCRIPTION
               "The maximum scale of 4to20mA conversion."
               ::=  {  sensor4to20mAEntry 33   }

            sensor4to20mAAmountBaseVoltage OBJECT-TYPE
               SYNTAX  INTEGER
               ACCESS  read-write
               STATUS  mandatory
               DESCRIPTION
               "The base scale of 4to20mA conversion."
               ::=  {  sensor4to20mAEntry 34   }

            sensor4to20mAPort OBJECT-TYPE
               SYNTAX  INTEGER (0..65534)
               ACCESS  read-only
               STATUS  mandatory
               DESCRIPTION
               "Sensor port"
               ::=  {  sensor4to20mAEntry 35 }

            sensor4to20mASubPort OBJECT-TYPE
               SYNTAX  INTEGER (0..65534)
               ACCESS  read-only
               STATUS  mandatory
               DESCRIPTION
               "Sensor sub port"
               ::=  {  sensor4to20mAEntry 36 }

            sensor4to20mADeviceIndex OBJECT-TYPE
               SYNTAX  INTEGER (0..65534)
               ACCESS  read-only
               STATUS  mandatory
               DESCRIPTION
               "Device Index of sensor"
               ::=  {  sensor4to20mAEntry 37 }
               
            sensor4to20mAMaxVoltage OBJECT-TYPE
               SYNTAX  INTEGER
               ACCESS  read-write
               STATUS  mandatory
               DESCRIPTION
               "The max range for use in conversion."
               ::=  {  sensor4to20mAEntry 43   }

            sensor4to20mABaseVoltage OBJECT-TYPE
               SYNTAX  INTEGER
               ACCESS  read-write
               STATUS  mandatory
               DESCRIPTION
               "The base range for use in conversion."
               ::=  {  sensor4to20mAEntry 44   }
               
            sensor4to20mADisplayStyle OBJECT-TYPE
               SYNTAX  INTEGER {
                  basic(0),
                  gauge(1)
               }
               ACCESS  read-write
               STATUS  mandatory
               DESCRIPTION
               "4to20mA display style"
               ::=  {  sensor4to20mAEntry 45 }  
               
            sensor4to20mAHighCriticalDesc OBJECT-TYPE
               SYNTAX  DisplayString
               ACCESS  read-write
               STATUS  mandatory
               DESCRIPTION
               "A HighCritical Description of this sensor"
               ::=  {  sensor4to20mAEntry  46  }               

            sensor4to20mALowCriticalDesc OBJECT-TYPE
               SYNTAX  DisplayString
               ACCESS  read-write
               STATUS  mandatory
               DESCRIPTION
               "A LowCritical Description of this sensor"
               ::=  {  sensor4to20mAEntry  47  }

            sensor4to20mANormalDesc OBJECT-TYPE
               SYNTAX  DisplayString
               ACCESS  read-write
               STATUS  mandatory
               DESCRIPTION
               "A Normal Description of this sensor"
               ::=  {  sensor4to20mAEntry  48  }
               
            sensor4to20mALowWarningDesc OBJECT-TYPE
               SYNTAX  DisplayString
               ACCESS  read-write
               STATUS  mandatory
               DESCRIPTION
               "A LowWarning Description of this sensor"
               ::=  {  sensor4to20mAEntry  49  }
               
            sensor4to20mAHighWarningDesc OBJECT-TYPE
               SYNTAX  DisplayString
               ACCESS  read-write
               STATUS  mandatory
               DESCRIPTION
               "A HighWarning Description of this sensor"
               ::=  {  sensor4to20mAEntry  50  }
               
            sensor4to20mASensorErrorDesc OBJECT-TYPE
               SYNTAX  DisplayString
               ACCESS  read-write
               STATUS  mandatory
               DESCRIPTION
               "A SensorError Description of this sensor"
               ::=  {  sensor4to20mAEntry  51  }    

            sensor4to20mAHighCriticalColor OBJECT-TYPE
               SYNTAX  INTEGER
               ACCESS  read-write
               STATUS  mandatory
               DESCRIPTION
               "A HighCritical Color of this sensor"
               ::=  {  sensor4to20mAEntry  54  }               

            sensor4to20mALowCriticalColor OBJECT-TYPE
               SYNTAX  INTEGER
               ACCESS  read-write
               STATUS  mandatory
               DESCRIPTION
               "A LowCritical Color of this sensor"
               ::=  {  sensor4to20mAEntry  55  }

            sensor4to20mANormalColor OBJECT-TYPE
               SYNTAX  INTEGER
               ACCESS  read-write
               STATUS  mandatory
               DESCRIPTION
               "A Normal Color of this sensor"
               ::=  {  sensor4to20mAEntry  56  }
               
            sensor4to20mALowWarningColor OBJECT-TYPE
               SYNTAX  INTEGER
               ACCESS  read-write
               STATUS  mandatory
               DESCRIPTION
               "A LowWarning Color of this sensor"
               ::=  {  sensor4to20mAEntry  57  }
               
            sensor4to20mAHighWarningColor OBJECT-TYPE
               SYNTAX  INTEGER
               ACCESS  read-write
               STATUS  mandatory
               DESCRIPTION
               "A HighWarning Color of this sensor"
               ::=  {  sensor4to20mAEntry  58  }
               
            sensor4to20mASensorErrorColor OBJECT-TYPE
               SYNTAX  INTEGER
               ACCESS  read-write
               STATUS  mandatory
               DESCRIPTION
               "A SensorError Color of this sensor"
               ::=  {  sensor4to20mAEntry  59  }  

--/* End of sensor4to20mAEntry */

--/* Begin of sensorDCvoltageEntry */
         sensorDCvoltageTable OBJECT-TYPE
            SYNTAX  SEQUENCE OF SensorDCvoltageEntry
            ACCESS  not-accessible
            STATUS  mandatory
            DESCRIPTION
            "This table contains the property and reading value for every sensor."
            ::=  {  secSensor 6   }

         sensorDCvoltageEntry OBJECT-TYPE
            SYNTAX  SensorDCvoltageEntry
            ACCESS  not-accessible
            STATUS  mandatory
            DESCRIPTION
            "This is an entry in the sensorTemperatureEntry Table"
            INDEX         { sensorDCvoltageIndex }
            ::=  {  sensorDCvoltageTable 1 }

         SensorDCvoltageEntry ::= SEQUENCE {
               sensorDCvoltageIndex
                  INTEGER,
               sensorDCvoltageDescription
                  DisplayString,
               sensorDCvoltageValue
                  INTEGER,
               sensorDCvoltageUnit
                  DisplayString,
               sensorDCvoltageStatus
                  INTEGER,
               sensorDCvoltageGoOffline
                  INTEGER,
               sensorDCvoltageLowCritical
                  INTEGER,
               sensorDCvoltageLowWarning
                  INTEGER,
               sensorDCvoltageHighWarning
                  INTEGER,
               sensorDCvoltageHighCritical
                  INTEGER,
               sensorDCvoltageRearm
                  INTEGER,
               sensorDCvoltageDelayError
                  INTEGER,
               sensorDCvoltageDelayNormal
                  INTEGER,
               sensorDCvoltageDelayLowCritical
                  INTEGER,
               sensorDCvoltageDelayLowWarning
                  INTEGER,
               sensorDCvoltageDelayHighWarning
                  INTEGER,
               sensorDCvoltageDelayHighCritical
                  INTEGER,
               sensorDCvoltageRaw
                  INTEGER,
               sensorDCvoltageOffset
                  INTEGER,
               sensorDCvoltageJumper
                  INTEGER,
               sensorDCvoltageAmountMaxVoltage
                  INTEGER,
               sensorDCvoltageAmountBaseVoltage
                  INTEGER,
               sensorDCvoltagePort
                  INTEGER,
               sensorDCvoltageSubPort
                  INTEGER,
               sensorDCvoltageDeviceIndex
                  INTEGER,
               sensorDCvoltageMaxVoltage
                  INTEGER,
               sensorDCvoltageBaseVoltage                  
                  INTEGER,
               sensorDCvoltageDisplayStyle
                  INTEGER,
               sensorDCvoltageHighCriticalDesc 
                  DisplayString,
               sensorDCvoltageLowCriticalDesc 
                  DisplayString,
               sensorDCvoltageNormalDesc 
                  DisplayString,
               sensorDCvoltageLowWarningDesc 
                  DisplayString,   
               sensorDCvoltageHighWarningDesc 
                  DisplayString,
               sensorDCvoltageSensorErrorDesc 
                  DisplayString,
               sensorDCvoltageHighCriticalColor 
                  INTEGER,
               sensorDCvoltageLowCriticalColor 
                  INTEGER,
               sensorDCvoltageNormalColor 
                  INTEGER,
               sensorDCvoltageLowWarningColor 
                  INTEGER,   
               sensorDCvoltageHighWarningColor 
                  INTEGER,
               sensorDCvoltageSensorErrorColor 
                  INTEGER                 
            }

            sensorDCvoltageIndex OBJECT-TYPE
               SYNTAX  INTEGER (1..65535)
               ACCESS  read-only
               STATUS  mandatory
               DESCRIPTION
               "The index into the sensor table"
               ::=  {  sensorDCvoltageEntry 1   }

            sensorDCvoltageDescription OBJECT-TYPE
               SYNTAX  DisplayString
               ACCESS  read-write
               STATUS  mandatory
               DESCRIPTION
               "A Description of this sensor"
               ::=  {  sensorDCvoltageEntry 2   }

            sensorDCvoltageValue OBJECT-TYPE
               SYNTAX  INTEGER
               ACCESS  read-only
               STATUS  mandatory
               DESCRIPTION
               "The reading value in this sensor"
               ::=  {  sensorDCvoltageEntry 4   }

            sensorDCvoltageUnit OBJECT-TYPE
               SYNTAX  DisplayString
               ACCESS  read-write
               STATUS  mandatory
               DESCRIPTION
               "The unit string"
               ::=  {  sensorDCvoltageEntry 5  }

            sensorDCvoltageStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorDCvoltageEntry 6   }

            sensorDCvoltageGoOffline OBJECT-TYPE
               SYNTAX  INTEGER {
                  online(1),
                  goOffline(2)
               }
               ACCESS  read-write
               STATUS  mandatory
               DESCRIPTION
               "To take offline enter a 2"
               ::=  {  sensorDCvoltageEntry 8   }

            sensorDCvoltageLowCritical OBJECT-TYPE
               SYNTAX  INTEGER
               ACCESS  read-write
               STATUS  mandatory
               DESCRIPTION
               "How cold this sensor gets before it sends a critical event"
               ::=  {  sensorDCvoltageEntry 9   }

            sensorDCvoltageLowWarning OBJECT-TYPE
               SYNTAX  INTEGER
               ACCESS  read-write
               STATUS  mandatory
               DESCRIPTION
               "How cold this sensor gets before it sends a warning"
               ::=  {  sensorDCvoltageEntry 10   }
   
            sensorDCvoltageHighWarning OBJECT-TYPE
               SYNTAX  INTEGER
               ACCESS  read-write
               STATUS  mandatory
               DESCRIPTION
               "How hot this sensor gets before it sends a warning"
               ::=  {  sensorDCvoltageEntry 11   }  

            sensorDCvoltageHighCritical OBJECT-TYPE
               SYNTAX  INTEGER
               ACCESS  read-write
               STATUS  mandatory
               DESCRIPTION
               "How hot this sensor gets before it sends a critical event"
               ::=  {  sensorDCvoltageEntry 12   }   

            sensorDCvoltageRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorDCvoltageEntry 13   }

            sensorDCvoltageDelayError OBJECT-TYPE
               SYNTAX  INTEGER (0..65534)
               ACCESS  read-write
               STATUS  mandatory
               DESCRIPTION
               "Time in seconds after the sensor has been in error status before report as an error"
               ::=  {  sensorDCvoltageEntry 14   }

            sensorDCvoltageDelayNormal OBJECT-TYPE
               SYNTAX  INTEGER (0..65534)
               ACCESS  read-write
               STATUS  mandatory
               DESCRIPTION
               "Time in seconds after the sensor change from error to normal before report as normal"
               ::=  {  sensorDCvoltageEntry 15   }

            sensorDCvoltageDelayLowCritical OBJECT-TYPE
               SYNTAX INTEGER (0..65535)
               ACCESS read-write
               STATUS mandatory
               DESCRIPTION
               "Continuous time for this sensor to be in Low Critical before accepting new Status."
               ::= {  sensorDCvoltageEntry 16 }
               
            sensorDCvoltageDelayLowWarning OBJECT-TYPE
               SYNTAX INTEGER (0..65535)
               ACCESS read-write
               STATUS mandatory
               DESCRIPTION
               "Continuous time for this sensor to be in Low Warning before accepting new Status."
               ::= {  sensorDCvoltageEntry 17 }

            sensorDCvoltageDelayHighWarning OBJECT-TYPE
               SYNTAX INTEGER (0..65535)
               ACCESS read-write
               STATUS mandatory
               DESCRIPTION
               "Continuous time for this sensor to be in High Warning before accepting new Status."
               ::= {  sensorDCvoltageEntry 18 }

            sensorDCvoltageDelayHighCritical OBJECT-TYPE
               SYNTAX INTEGER (0..65535)
               ACCESS read-write
               STATUS mandatory
               DESCRIPTION
               "Continuous time for this sensor to be in High Critical before accepting new Status."
               ::= {  sensorDCvoltageEntry 19 }

            sensorDCvoltageRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorDCvoltageEntry 20   }

            sensorDCvoltageOffset OBJECT-TYPE
               SYNTAX  INTEGER
               ACCESS  read-write
               STATUS  mandatory
               DESCRIPTION
               "DC voltage Offset reading"
               ::=  {  sensorDCvoltageEntry 21   }

            sensorDCvoltageJumper OBJECT-TYPE
               SYNTAX  INTEGER {
                  jumperAt-60(-600),
                  jumperAt-40(-400),
                  jumperAt-30(-300),
                  jumperAt-20(-200),
                  jumperAt-10(-100),                  
                  jumperAt10(100),
                  jumperAt20(200),
                  jumperAt30(300),
                  jumperAt40(400),
                  jumperAt60(600)                  
               }
               ACCESS  read-write
               STATUS  mandatory
               DESCRIPTION
               "Selected voltage scale (jumper 0) in DC voltage conversion."
               ::=  {  sensorDCvoltageEntry 32   }

            sensorDCvoltageAmountMaxVoltage OBJECT-TYPE
               SYNTAX  INTEGER
               ACCESS  read-write
               STATUS  mandatory
               DESCRIPTION
               "The maximum scale of DC voltage conversion."
               ::=  {  sensorDCvoltageEntry 33   }

            sensorDCvoltageAmountBaseVoltage OBJECT-TYPE
               SYNTAX  INTEGER
               ACCESS  read-write
               STATUS  mandatory
               DESCRIPTION
               "The base scale of DC voltage conversion."
               ::=  {  sensorDCvoltageEntry 34   }

            sensorDCvoltagePort OBJECT-TYPE
               SYNTAX  INTEGER (0..65534)
               ACCESS  read-only
               STATUS  mandatory
               DESCRIPTION
               "Sensor port"
               ::=  {  sensorDCvoltageEntry 35 }

            sensorDCvoltageSubPort OBJECT-TYPE
               SYNTAX  INTEGER (0..65534)
               ACCESS  read-only
               STATUS  mandatory
               DESCRIPTION
               "Sensor sub port"
               ::=  {  sensorDCvoltageEntry 36 }

            sensorDCvoltageDeviceIndex OBJECT-TYPE
               SYNTAX  INTEGER (0..65534)
               ACCESS  read-only
               STATUS  mandatory
               DESCRIPTION
               "Device Index of sensor"
               ::=  {  sensorDCvoltageEntry 37 }

            sensorDCvoltageMaxVoltage OBJECT-TYPE
               SYNTAX  INTEGER
               ACCESS  read-write
               STATUS  mandatory
               DESCRIPTION
               "The max voltage range for use in conversion."
               ::=  {  sensorDCvoltageEntry 43   }

            sensorDCvoltageBaseVoltage OBJECT-TYPE
               SYNTAX  INTEGER
               ACCESS  read-write
               STATUS  mandatory
               DESCRIPTION
               "The base voltage range for use in conversion."
               ::=  {  sensorDCvoltageEntry 44   }
               
            sensorDCvoltageDisplayStyle OBJECT-TYPE
               SYNTAX  INTEGER {
                  basic(0),
                  gauge(1)
               }
               ACCESS  read-write
               STATUS  mandatory
               DESCRIPTION
               "DCVoltage display style"
               ::=  {  sensorDCvoltageEntry 45 }
               
            sensorDCvoltageHighCriticalDesc OBJECT-TYPE
               SYNTAX  DisplayString
               ACCESS  read-write
               STATUS  mandatory
               DESCRIPTION
               "A HighCritical Description of this sensor"
               ::=  {  sensorDCvoltageEntry  46  }               

            sensorDCvoltageLowCriticalDesc OBJECT-TYPE
               SYNTAX  DisplayString
               ACCESS  read-write
               STATUS  mandatory
               DESCRIPTION
               "A LowCritical Description of this sensor"
               ::=  {  sensorDCvoltageEntry  47  }

            sensorDCvoltageNormalDesc OBJECT-TYPE
               SYNTAX  DisplayString
               ACCESS  read-write
               STATUS  mandatory
               DESCRIPTION
               "A Normal Description of this sensor"
               ::=  {  sensorDCvoltageEntry  48  }
               
            sensorDCvoltageLowWarningDesc OBJECT-TYPE
               SYNTAX  DisplayString
               ACCESS  read-write
               STATUS  mandatory
               DESCRIPTION
               "A LowWarning Description of this sensor"
               ::=  {  sensorDCvoltageEntry  49  }
               
            sensorDCvoltageHighWarningDesc OBJECT-TYPE
               SYNTAX  DisplayString
               ACCESS  read-write
               STATUS  mandatory
               DESCRIPTION
               "A HighWarning Description of this sensor"
               ::=  {  sensorDCvoltageEntry  50  }
               
            sensorDCvoltageSensorErrorDesc OBJECT-TYPE
               SYNTAX  DisplayString
               ACCESS  read-write
               STATUS  mandatory
               DESCRIPTION
               "A SensorError Description of this sensor"
               ::=  {  sensorDCvoltageEntry  51  }  

            sensorDCvoltageHighCriticalColor OBJECT-TYPE
               SYNTAX  INTEGER
               ACCESS  read-write
               STATUS  mandatory
               DESCRIPTION
               "A HighCritical Color of this sensor"
               ::=  {  sensorDCvoltageEntry  54  }               

            sensorDCvoltageLowCriticalColor OBJECT-TYPE
               SYNTAX  INTEGER
               ACCESS  read-write
               STATUS  mandatory
               DESCRIPTION
               "A LowCritical Color of this sensor"
               ::=  {  sensorDCvoltageEntry  55  }

            sensorDCvoltageNormalColor OBJECT-TYPE
               SYNTAX  INTEGER
               ACCESS  read-write
               STATUS  mandatory
               DESCRIPTION
               "A Normal Color of this sensor"
               ::=  {  sensorDCvoltageEntry  56  }
               
            sensorDCvoltageLowWarningColor OBJECT-TYPE
               SYNTAX  INTEGER
               ACCESS  read-write
               STATUS  mandatory
               DESCRIPTION
               "A LowWarning Color of this sensor"
               ::=  {  sensorDCvoltageEntry  57  }
               
            sensorDCvoltageHighWarningColor OBJECT-TYPE
               SYNTAX  INTEGER
               ACCESS  read-write
               STATUS  mandatory
               DESCRIPTION
               "A HighWarning Color of this sensor"
               ::=  {  sensorDCvoltageEntry  58  }
               
            sensorDCvoltageSensorErrorColor OBJECT-TYPE
               SYNTAX  INTEGER
               ACCESS  read-write
               STATUS  mandatory
               DESCRIPTION
               "A SensorError Color of this sensor"
               ::=  {  sensorDCvoltageEntry  59  }  

--/* End of sensorDCvoltageEntry */

--/* Begin of sensorAirflowEntry */
         sensorAirflowTable OBJECT-TYPE
            SYNTAX  SEQUENCE OF SensorAirflowEntry
            ACCESS  not-accessible
            STATUS  mandatory
            DESCRIPTION
            "This table contains the property and reading value for every sensor."
            ::=  {  secSensor 7   }

         sensorAirflowEntry OBJECT-TYPE
            SYNTAX  SensorAirflowEntry
            ACCESS  not-accessible
            STATUS  mandatory
            DESCRIPTION
            "This is an entry in the sensorTemperatureEntry Table"
            INDEX         { sensorAirflowIndex }
            ::=  {  sensorAirflowTable 1 }

         SensorAirflowEntry ::= SEQUENCE {
               sensorAirflowIndex
                  INTEGER,
               sensorAirflowDescription
                  DisplayString,
               sensorAirflowValue
                  INTEGER,
               sensorAirflowStatus
                  INTEGER,
               sensorAirflowGoOffline
                  INTEGER,
               sensorAirflowLowCritical
                  INTEGER,
               sensorAirflowLowWarning
                  INTEGER,
               sensorAirflowHighWarning
                  INTEGER,
               sensorAirflowHighCritical
                  INTEGER,
               sensorAirflowRearm
                  INTEGER,
               sensorAirflowDelayError
                  INTEGER,
               sensorAirflowDelayNormal
                  INTEGER,
               sensorAirflowDelayLowCritical
                  INTEGER,
               sensorAirflowDelayLowWarning
                  INTEGER,
               sensorAirflowDelayHighWarning
                  INTEGER,
               sensorAirflowDelayHighCritical
                  INTEGER,
               sensorAirflowRaw
                  INTEGER,
               sensorAirflowPort
                  INTEGER,
               sensorAirflowSubPort
                  INTEGER,
               sensorAirflowDeviceIndex
                  INTEGER,
               sensorAirflowDisplayStyle
                  INTEGER,
               sensorAirflowHighCriticalDesc 
                  DisplayString,
               sensorAirflowLowCriticalDesc 
                  DisplayString,
               sensorAirflowNormalDesc 
                  DisplayString,
               sensorAirflowLowWarningDesc 
                  DisplayString,   
               sensorAirflowHighWarningDesc 
                  DisplayString,
               sensorAirflowSensorErrorDesc 
                  DisplayString,
               sensorAirflowHighCriticalColor 
                  INTEGER,
               sensorAirflowLowCriticalColor 
                  INTEGER,
               sensorAirflowNormalColor 
                  INTEGER,
               sensorAirflowLowWarningColor 
                  INTEGER,   
               sensorAirflowHighWarningColor 
                  INTEGER,
               sensorAirflowSensorErrorColor 
                  INTEGER                  
            }

            sensorAirflowIndex OBJECT-TYPE
               SYNTAX  INTEGER (1..65535)
               ACCESS  read-only
               STATUS  mandatory
               DESCRIPTION
               "The index into the Switch sensor table"
               ::=  {  sensorAirflowEntry 1   }

            sensorAirflowDescription OBJECT-TYPE
               SYNTAX  DisplayString
               ACCESS  read-write
               STATUS  mandatory
               DESCRIPTION
               "A Description of this sensor Switch"
               ::=  {  sensorAirflowEntry 2   }

            sensorAirflowValue OBJECT-TYPE
               SYNTAX  INTEGER
               ACCESS  read-only
               STATUS  mandatory
               DESCRIPTION
               "The reading value in this sensor"
               ::=  {  sensorAirflowEntry 4   }

            sensorAirflowStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorAirflowEntry 6  }

            sensorAirflowGoOffline OBJECT-TYPE
               SYNTAX  INTEGER {
                  online(1),
                  goOffline(2)
               }
               ACCESS  read-write
               STATUS  mandatory
               DESCRIPTION
               "To take offline enter a 2"
               ::=  {  sensorAirflowEntry 8  }

            sensorAirflowLowCritical OBJECT-TYPE
               SYNTAX  INTEGER
               ACCESS  read-write
               STATUS  mandatory
               DESCRIPTION
               "How cold this sensor gets before it sends a critical event"
               ::=  {  sensorAirflowEntry 9   }

            sensorAirflowLowWarning OBJECT-TYPE
               SYNTAX  INTEGER
               ACCESS  read-write
               STATUS  mandatory
               DESCRIPTION
               "How cold this sensor gets before it sends a warning"
               ::=  {  sensorAirflowEntry 10   }
   
            sensorAirflowHighWarning OBJECT-TYPE
               SYNTAX  INTEGER
               ACCESS  read-write
               STATUS  mandatory
               DESCRIPTION
               "How hot this sensor gets before it sends a warning"
               ::=  {  sensorAirflowEntry 11   }  

            sensorAirflowHighCritical OBJECT-TYPE
               SYNTAX  INTEGER
               ACCESS  read-write
               STATUS  mandatory
               DESCRIPTION
               "How hot this sensor gets before it sends a critical event"
               ::=  {  sensorAirflowEntry 12   }   

            sensorAirflowRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorAirflowEntry 13   }

            sensorAirflowDelayError OBJECT-TYPE
               SYNTAX  INTEGER (0..65534)
               ACCESS  read-write
               STATUS  mandatory
               DESCRIPTION
               "Time in seconds after the sensor has been in error status before report as an error"
               ::=  {  sensorAirflowEntry 14   }

            sensorAirflowDelayNormal OBJECT-TYPE
               SYNTAX  INTEGER (0..65534)
               ACCESS  read-write
               STATUS  mandatory
               DESCRIPTION
               "Time in seconds after the sensor change from error to normal before report as normal"
               ::=  {  sensorAirflowEntry 15   }

            sensorAirflowDelayLowCritical OBJECT-TYPE
               SYNTAX INTEGER (0..65535)
               ACCESS read-write
               STATUS mandatory
               DESCRIPTION
               "Continuous time for this sensor to be in Low Critical before accepting new Status."
               ::= {  sensorAirflowEntry 16 }
               
            sensorAirflowDelayLowWarning OBJECT-TYPE
               SYNTAX INTEGER (0..65535)
               ACCESS read-write
               STATUS mandatory
               DESCRIPTION
               "Continuous time for this sensor to be in Low Warning before accepting new Status."
               ::= {  sensorAirflowEntry 17 }

            sensorAirflowDelayHighWarning OBJECT-TYPE
               SYNTAX INTEGER (0..65535)
               ACCESS read-write
               STATUS mandatory
               DESCRIPTION
               "Continuous time for this sensor to be in High Warning before accepting new Status."
               ::= {  sensorAirflowEntry 18 }

            sensorAirflowDelayHighCritical OBJECT-TYPE
               SYNTAX INTEGER (0..65535)
               ACCESS read-write
               STATUS mandatory
               DESCRIPTION
               "Continuous time for this sensor to be in High Critical before accepting new Status."
               ::= {  sensorAirflowEntry 19 }

            sensorAirflowRaw OBJECT-TYPE
               SYNTAX  INTEGER
               ACCESS  read-only
               STATUS  mandatory
               DESCRIPTION
               "The unformatted, raw, A/D value in this sensor. Contains more resolution than the formated percentage. This number can go from 0 to 1023 depending on the input voltage"
               ::=  {  sensorAirflowEntry 20   }

            sensorAirflowPort OBJECT-TYPE
               SYNTAX  INTEGER (0..65534)
               ACCESS  read-only
               STATUS  mandatory
               DESCRIPTION
               "Sensor port"
               ::=  {  sensorAirflowEntry 35 }

            sensorAirflowSubPort OBJECT-TYPE
               SYNTAX  INTEGER (0..65534)
               ACCESS  read-only
               STATUS  mandatory
               DESCRIPTION
               "Sensor sub port"
               ::=  {  sensorAirflowEntry 36 }

            sensorAirflowDeviceIndex OBJECT-TYPE
               SYNTAX  INTEGER (0..65534)
               ACCESS  read-only
               STATUS  mandatory
               DESCRIPTION
               "Device Index of sensor"
               ::=  {  sensorAirflowEntry 37 }

            sensorAirflowDisplayStyle OBJECT-TYPE
               SYNTAX  INTEGER {
                  basic(0),
                  gauge(1)
               }
               ACCESS  read-write
               STATUS  mandatory
               DESCRIPTION
               "Airflow display style"
               ::=  {  sensorAirflowEntry 45 }
               
            sensorAirflowHighCriticalDesc OBJECT-TYPE
               SYNTAX  DisplayString
               ACCESS  read-write
               STATUS  mandatory
               DESCRIPTION
               "A HighCritical Description of this sensor"
               ::=  {  sensorAirflowEntry  46  }               

            sensorAirflowLowCriticalDesc OBJECT-TYPE
               SYNTAX  DisplayString
               ACCESS  read-write
               STATUS  mandatory
               DESCRIPTION
               "A LowCritical Description of this sensor"
               ::=  {  sensorAirflowEntry  47  }

            sensorAirflowNormalDesc OBJECT-TYPE
               SYNTAX  DisplayString
               ACCESS  read-write
               STATUS  mandatory
               DESCRIPTION
               "A Normal Description of this sensor"
               ::=  {  sensorAirflowEntry  48  }
               
            sensorAirflowLowWarningDesc OBJECT-TYPE
               SYNTAX  DisplayString
               ACCESS  read-write
               STATUS  mandatory
               DESCRIPTION
               "A LowWarning Description of this sensor"
               ::=  {  sensorAirflowEntry  49  }
               
            sensorAirflowHighWarningDesc OBJECT-TYPE
               SYNTAX  DisplayString
               ACCESS  read-write
               STATUS  mandatory
               DESCRIPTION
               "A HighWarning Description of this sensor"
               ::=  {  sensorAirflowEntry  50  }
               
            sensorAirflowSensorErrorDesc OBJECT-TYPE
               SYNTAX  DisplayString
               ACCESS  read-write
               STATUS  mandatory
               DESCRIPTION
               "A SensorError Description of this sensor"
               ::=  {  sensorAirflowEntry  51  }  

            sensorAirflowHighCriticalColor OBJECT-TYPE
               SYNTAX  INTEGER
               ACCESS  read-write
               STATUS  mandatory
               DESCRIPTION
               "A HighCritical Color of this sensor"
               ::=  {  sensorAirflowEntry  54  }               

            sensorAirflowLowCriticalColor OBJECT-TYPE
               SYNTAX  INTEGER
               ACCESS  read-write
               STATUS  mandatory
               DESCRIPTION
               "A LowCritical Color of this sensor"
               ::=  {  sensorAirflowEntry  55  }

            sensorAirflowNormalColor OBJECT-TYPE
               SYNTAX  INTEGER
               ACCESS  read-write
               STATUS  mandatory
               DESCRIPTION
               "A Normal Color of this sensor"
               ::=  {  sensorAirflowEntry  56  }
               
            sensorAirflowLowWarningColor OBJECT-TYPE
               SYNTAX  INTEGER
               ACCESS  read-write
               STATUS  mandatory
               DESCRIPTION
               "A LowWarning Color of this sensor"
               ::=  {  sensorAirflowEntry  57  }
               
            sensorAirflowHighWarningColor OBJECT-TYPE
               SYNTAX  INTEGER
               ACCESS  read-write
               STATUS  mandatory
               DESCRIPTION
               "A HighWarning Color of this sensor"
               ::=  {  sensorAirflowEntry  58  }
               
            sensorAirflowSensorErrorColor OBJECT-TYPE
               SYNTAX  INTEGER
               ACCESS  read-write
               STATUS  mandatory
               DESCRIPTION
               "A SensorError Color of this sensor"
               ::=  {  sensorAirflowEntry  59  }                
               
--/* End of sensorAirflowEntry */

--/* Begin of sensorMotionEntry */
         sensorMotionTable OBJECT-TYPE
            SYNTAX  SEQUENCE OF SensorMotionEntry
            ACCESS  not-accessible
            STATUS  mandatory
            DESCRIPTION
            "This table contains the property and reading value for every sensor."
            ::=  {  secSensor 8   }

         sensorMotionEntry OBJECT-TYPE
            SYNTAX  SensorMotionEntry
            ACCESS  not-accessible
            STATUS  mandatory
            DESCRIPTION
            "This is an entry in the sensorTemperatureEntry Table"
            INDEX         { sensorMotionIndex }
            ::=  {  sensorMotionTable 1 }

         SensorMotionEntry ::= SEQUENCE {
               sensorMotionIndex
                  INTEGER,
               sensorMotionDescription
                  DisplayString,
               sensorMotionStatus
                  INTEGER,
               sensorMotionGoOffline
                  INTEGER,
               sensorMotionPort
                  INTEGER,
               sensorMotionSubPort
                  INTEGER,
               sensorMotionDeviceIndex
                  INTEGER,
               sensorMotionCriticalDesc 
                  DisplayString,
               sensorMotionNormalDesc 
                  DisplayString,
               sensorMotionCriticalColor 
                  INTEGER,
               sensorMotionNormalColor 
                  INTEGER           
            }

            sensorMotionIndex OBJECT-TYPE
               SYNTAX  INTEGER (1..65535)
               ACCESS  read-only
               STATUS  mandatory
               DESCRIPTION
               "The index into the Switch sensor table"
               ::=  {  sensorMotionEntry 1   }

            sensorMotionDescription OBJECT-TYPE
               SYNTAX  DisplayString
               ACCESS  read-write
               STATUS  mandatory
               DESCRIPTION
               "A Description of this sensor Switch"
               ::=  {  sensorMotionEntry 2   }

            sensorMotionStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorMotionEntry 6  }

            sensorMotionGoOffline OBJECT-TYPE
               SYNTAX  INTEGER {
                  online(1),
                  goOffline(2)
               }
               ACCESS  read-write
               STATUS  mandatory
               DESCRIPTION
               "To take offline enter a 2"
               ::=  {  sensorMotionEntry 8  }

            sensorMotionPort OBJECT-TYPE
               SYNTAX  INTEGER (0..65534)
               ACCESS  read-only
               STATUS  mandatory
               DESCRIPTION
               "Sensor port"
               ::=  {  sensorMotionEntry 35 }

            sensorMotionSubPort OBJECT-TYPE
               SYNTAX  INTEGER (0..65534)
               ACCESS  read-only
               STATUS  mandatory
               DESCRIPTION
               "Sensor sub port"
               ::=  {  sensorMotionEntry 36 }

            sensorMotionDeviceIndex OBJECT-TYPE
               SYNTAX  INTEGER (0..65534)
               ACCESS  read-only
               STATUS  mandatory
               DESCRIPTION
               "Device Index of sensor"
               ::=  {  sensorMotionEntry 37 }

            sensorMotionCriticalDesc OBJECT-TYPE
               SYNTAX  DisplayString
               ACCESS  read-write
               STATUS  mandatory
               DESCRIPTION
               "A Critical Description of this sensor"
               ::=  {  sensorMotionEntry  46  }           

            sensorMotionNormalDesc OBJECT-TYPE
               SYNTAX  DisplayString
               ACCESS  read-write
               STATUS  mandatory
               DESCRIPTION
               "A Normal Description of this sensor"
               ::=  {  sensorMotionEntry  48  }
               
            sensorMotionCriticalColor OBJECT-TYPE
               SYNTAX  INTEGER
               ACCESS  read-write
               STATUS  mandatory
               DESCRIPTION
               "A Critical Color of this sensor"
               ::=  {  sensorMotionEntry  54  }               
               
            sensorMotionNormalColor OBJECT-TYPE
               SYNTAX  INTEGER
               ACCESS  read-write
               STATUS  mandatory
               DESCRIPTION
               "A Normal Color of this sensor"
               ::=  {  sensorMotionEntry  56  }          
               
--/* End of sensorMotionEntry */

--/* Begin of sensorWaterEntry */
         sensorWaterTable OBJECT-TYPE
            SYNTAX  SEQUENCE OF SensorWaterEntry
            ACCESS  not-accessible
            STATUS  mandatory
            DESCRIPTION
            "This table contains the property and reading value for every sensor."
            ::=  {  secSensor 9   }

         sensorWaterEntry OBJECT-TYPE
            SYNTAX  SensorWaterEntry
            ACCESS  not-accessible
            STATUS  mandatory
            DESCRIPTION
            "This is an entry in the sensorTemperatureEntry Table"
            INDEX         { sensorWaterIndex }
            ::=  {  sensorWaterTable 1 }

         SensorWaterEntry ::= SEQUENCE {
               sensorWaterIndex
                  INTEGER,
               sensorWaterDescription
                  DisplayString,
               sensorWaterStatus
                  INTEGER,
               sensorWaterGoOffline
                  INTEGER,
               sensorWaterPort
                  INTEGER,
               sensorWaterSubPort
                  INTEGER,
               sensorWaterDeviceIndex
                  INTEGER,
               sensorWaterCriticalDesc 
                  DisplayString,
               sensorWaterNormalDesc 
                  DisplayString,
               sensorWaterCriticalColor 
                  INTEGER,
               sensorWaterNormalColor 
                  INTEGER                
            }

            sensorWaterIndex OBJECT-TYPE
               SYNTAX  INTEGER (1..65535)
               ACCESS  read-only
               STATUS  mandatory
               DESCRIPTION
               "The index into the Switch sensor table"
               ::=  {  sensorWaterEntry 1   }

            sensorWaterDescription OBJECT-TYPE
               SYNTAX  DisplayString
               ACCESS  read-write
               STATUS  mandatory
               DESCRIPTION
               "A Description of this sensor Switch"
               ::=  {  sensorWaterEntry 2   }

            sensorWaterStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorWaterEntry 6  }

            sensorWaterGoOffline OBJECT-TYPE
               SYNTAX  INTEGER {
                  online(1),
                  goOffline(2)
               }
               ACCESS  read-write
               STATUS  mandatory
               DESCRIPTION
               "To take offline enter a 2"
               ::=  {  sensorWaterEntry 8  }

            sensorWaterPort OBJECT-TYPE
               SYNTAX  INTEGER (0..65534)
               ACCESS  read-only
               STATUS  mandatory
               DESCRIPTION
               "Sensor port"
               ::=  {  sensorWaterEntry 35 }

            sensorWaterSubPort OBJECT-TYPE
               SYNTAX  INTEGER (0..65534)
               ACCESS  read-only
               STATUS  mandatory
               DESCRIPTION
               "Sensor sub port"
               ::=  {  sensorWaterEntry 36 }

            sensorWaterDeviceIndex OBJECT-TYPE
               SYNTAX  INTEGER (0..65534)
               ACCESS  read-only
               STATUS  mandatory
               DESCRIPTION
               "Device Index of sensor"
               ::=  {  sensorWaterEntry 37 }
           
            sensorWaterCriticalDesc OBJECT-TYPE
               SYNTAX  DisplayString
               ACCESS  read-write
               STATUS  mandatory
               DESCRIPTION
               "A Critical Description of this sensor"
               ::=  {  sensorWaterEntry  46  }               

            sensorWaterNormalDesc OBJECT-TYPE
               SYNTAX  DisplayString
               ACCESS  read-write
               STATUS  mandatory
               DESCRIPTION
               "A Normal Description of this sensor"
               ::=  {  sensorWaterEntry  48  }

            sensorWaterCriticalColor OBJECT-TYPE
               SYNTAX  INTEGER
               ACCESS  read-write
               STATUS  mandatory
               DESCRIPTION
               "A Critical Color of this sensor"
               ::=  {  sensorWaterEntry  54  }               

            sensorWaterNormalColor OBJECT-TYPE
               SYNTAX  INTEGER
               ACCESS  read-write
               STATUS  mandatory
               DESCRIPTION
               "A Normal Color of this sensor"
               ::=  {  sensorWaterEntry  56  }         
               
--/* End of sensorWaterEntry */

--/* Begin of sensorSecurityEntry */
         sensorSecurityTable OBJECT-TYPE
            SYNTAX  SEQUENCE OF SensorSecurityEntry
            ACCESS  not-accessible
            STATUS  mandatory
            DESCRIPTION
            "This table contains the property and reading value for every sensor."
            ::=  {  secSensor 10   }

         sensorSecurityEntry OBJECT-TYPE
            SYNTAX  SensorSecurityEntry
            ACCESS  not-accessible
            STATUS  mandatory
            DESCRIPTION
            "This is an entry in the sensorTemperatureEntry Table"
            INDEX         { sensorSecurityIndex }
            ::=  {  sensorSecurityTable 1 }

         SensorSecurityEntry ::= SEQUENCE {
               sensorSecurityIndex
                  INTEGER,
               sensorSecurityDescription
                  DisplayString,
               sensorSecurityStatus
                  INTEGER,
               sensorSecurityGoOffline
                  INTEGER,
               sensorSecurityPort
                  INTEGER,
               sensorSecuritySubPort
                  INTEGER,
               sensorSecurityDeviceIndex
                  INTEGER,
               sensorSecurityCriticalDesc 
                  DisplayString,
               sensorSecurityNormalDesc 
                  DisplayString,
               sensorSecurityCriticalColor 
                  INTEGER,
               sensorSecurityNormalColor 
                  INTEGER                
            }

            sensorSecurityIndex OBJECT-TYPE
               SYNTAX  INTEGER (1..65535)
               ACCESS  read-only
               STATUS  mandatory
               DESCRIPTION
               "The index into the Switch sensor table"
               ::=  {  sensorSecurityEntry 1   }

            sensorSecurityDescription OBJECT-TYPE
               SYNTAX  DisplayString
               ACCESS  read-write
               STATUS  mandatory
               DESCRIPTION
               "A Description of this sensor Switch"
               ::=  {  sensorSecurityEntry 2   }

            sensorSecurityStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSecurityEntry 6  }

            sensorSecurityGoOffline OBJECT-TYPE
               SYNTAX  INTEGER {
                  online(1),
                  goOffline(2)
               }
               ACCESS  read-write
               STATUS  mandatory
               DESCRIPTION
               "To take offline enter a 2"
               ::=  {  sensorSecurityEntry 8  }

            sensorSecurityPort OBJECT-TYPE
               SYNTAX  INTEGER (0..65534)
               ACCESS  read-only
               STATUS  mandatory
               DESCRIPTION
               "Sensor port"
               ::=  {  sensorSecurityEntry 35 }

            sensorSecuritySubPort OBJECT-TYPE
               SYNTAX  INTEGER (0..65534)
               ACCESS  read-only
               STATUS  mandatory
               DESCRIPTION
               "Sensor sub port"
               ::=  {  sensorSecurityEntry 36 }

            sensorSecurityDeviceIndex OBJECT-TYPE
               SYNTAX  INTEGER (0..65534)
               ACCESS  read-only
               STATUS  mandatory
               DESCRIPTION
               "Device Index of sensor"
               ::=  {  sensorSecurityEntry 37 }

            sensorSecurityCriticalDesc OBJECT-TYPE
               SYNTAX  DisplayString
               ACCESS  read-write
               STATUS  mandatory
               DESCRIPTION
               "A Critical Description of this sensor"
               ::=  {  sensorSecurityEntry  46  }               

            sensorSecurityNormalDesc OBJECT-TYPE
               SYNTAX  DisplayString
               ACCESS  read-write
               STATUS  mandatory
               DESCRIPTION
               "A Normal Description of this sensor"
               ::=  {  sensorSecurityEntry  48  }

            sensorSecurityCriticalColor OBJECT-TYPE
               SYNTAX  INTEGER
               ACCESS  read-write
               STATUS  mandatory
               DESCRIPTION
               "A Critical Color of this sensor"
               ::=  {  sensorSecurityEntry  54  }               

            sensorSecurityNormalColor OBJECT-TYPE
               SYNTAX  INTEGER
               ACCESS  read-write
               STATUS  mandatory
               DESCRIPTION
               "A Normal Color of this sensor"
               ::=  {  sensorSecurityEntry  56  }      
               
--/* End of sensorSecurityEntry */

--/* Begin of sensorSirenEntry */
         sensorSirenTable OBJECT-TYPE
            SYNTAX  SEQUENCE OF SensorSirenEntry
            ACCESS  not-accessible
            STATUS  mandatory
            DESCRIPTION
            "This table contains the property and reading value for every sensor."
            ::=  {  secSensor 11   }

         sensorSirenEntry OBJECT-TYPE
            SYNTAX  SensorSirenEntry
            ACCESS  not-accessible
            STATUS  mandatory
            DESCRIPTION
            "This is an entry in the sensorTemperatureEntry Table"
            INDEX         { sensorSirenIndex }
            ::=  {  sensorSirenTable 1 }

         SensorSirenEntry ::= SEQUENCE {
               sensorSirenIndex
                  INTEGER,
               sensorSirenDescription
                  DisplayString,
               sensorSirenStatus
                  INTEGER,
               sensorSirenGoOffline
                  INTEGER,
               sensorSirenControlMode
                  INTEGER,
               sensorSirenManualCycleTime
                  INTEGER,
               sensorSirenManualAction
                  INTEGER,
               sensorSirenPort
                  INTEGER,
               sensorSirenSubPort
                  INTEGER,
               sensorSirenDeviceIndex
                  INTEGER,
               sensorSirenOnDesc 
                  DisplayString,
               sensorSirenOffDesc 
                  DisplayString,
               sensorSirenOnColor 
                  INTEGER,
               sensorSirenOffColor 
                  INTEGER               
            }

            sensorSirenIndex OBJECT-TYPE
               SYNTAX  INTEGER (1..65535)
               ACCESS  read-only
               STATUS  mandatory
               DESCRIPTION
               "The index into the Switch sensor table"
               ::=  {  sensorSirenEntry 1   }

            sensorSirenDescription OBJECT-TYPE
               SYNTAX  DisplayString
               ACCESS  read-write
               STATUS  mandatory
               DESCRIPTION
               "A Description of this sensor Switch"
               ::=  {  sensorSirenEntry 2   }

            sensorSirenStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSirenEntry 6  }

            sensorSirenGoOffline OBJECT-TYPE
               SYNTAX  INTEGER {
                  online(1),
                  goOffline(2)
               }
               ACCESS  read-write
               STATUS  mandatory
               DESCRIPTION
               "To take offline enter a 2"
               ::=  {  sensorSirenEntry 8  }

            sensorSirenControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a siren."
               ::=  {  sensorSirenEntry 24  }
               
            sensorSirenManualCycleTime OBJECT-TYPE
               SYNTAX  INTEGER (1..255)
               ACCESS  read-write
               STATUS  mandatory
               DESCRIPTION
               "Toggle period in seconds for Manual Cycle action."
               ::=  {  sensorSirenEntry 25  }
               
            sensorSirenManualAction OBJECT-TYPE
               SYNTAX  INTEGER {
                  turn-On(0),
                  turn-Off(1),
                  cycle-On-Off-On(2),
                  cycle-Off-On-Off(3)
               }
               ACCESS  read-write
               STATUS  mandatory
               DESCRIPTION
               "Control the siren manualy"
               ::=  {  sensorSirenEntry 26  }

            sensorSirenPort OBJECT-TYPE
               SYNTAX  INTEGER (0..65534)
               ACCESS  read-only
               STATUS  mandatory
               DESCRIPTION
               "Sensor port"
               ::=  {  sensorSirenEntry 35 }

            sensorSirenSubPort OBJECT-TYPE
               SYNTAX  INTEGER (0..65534)
               ACCESS  read-only
               STATUS  mandatory
               DESCRIPTION
               "Sensor sub port"
               ::=  {  sensorSirenEntry 36 }

            sensorSirenDeviceIndex OBJECT-TYPE
               SYNTAX  INTEGER (0..65534)
               ACCESS  read-only
               STATUS  mandatory
               DESCRIPTION
               "Device Index of sensor"
               ::=  {  sensorSirenEntry 37 }
              
            sensorSirenOnDesc OBJECT-TYPE
               SYNTAX  DisplayString
               ACCESS  read-write
               STATUS  mandatory
               DESCRIPTION
               "A On Description of this sensor"
               ::=  {  sensorSirenEntry  52  }               

            sensorSirenOffDesc OBJECT-TYPE
               SYNTAX  DisplayString
               ACCESS  read-write
               STATUS  mandatory
               DESCRIPTION
               "A Off Description of this sensor"
               ::=  {  sensorSirenEntry  53  }

            sensorSirenOnColor OBJECT-TYPE
               SYNTAX  INTEGER
               ACCESS  read-write
               STATUS  mandatory
               DESCRIPTION
               "A On Color of this sensor"
               ::=  {  sensorSirenEntry  60  }               

            sensorSirenOffColor OBJECT-TYPE
               SYNTAX  INTEGER
               ACCESS  read-write
               STATUS  mandatory
               DESCRIPTION
               "A Off Color of this sensor"
               ::=  {  sensorSirenEntry  61  }       
               
--/* End of sensorSirenEntry */

--/* Begin of sensorRelayEntry */
         sensorRelayTable OBJECT-TYPE
            SYNTAX  SEQUENCE OF SensorRelayEntry
            ACCESS  not-accessible
            STATUS  mandatory
            DESCRIPTION
            "This table contains the property and reading value for every sensor."
            ::=  {  secSensor 12   }

         sensorRelayEntry OBJECT-TYPE
            SYNTAX  SensorRelayEntry
            ACCESS  not-accessible
            STATUS  mandatory
            DESCRIPTION
            "This is an entry in the sensorTemperatureEntry Table"
            INDEX         { sensorRelayIndex }
            ::=  {  sensorRelayTable 1 }

         SensorRelayEntry ::= SEQUENCE {
               sensorRelayIndex
                  INTEGER,
               sensorRelayDescription
                  DisplayString,
               sensorRelayType
                  INTEGER,
               sensorRelayStatus
                  INTEGER,
               sensorRelayGoOffline
                  INTEGER,
               sensorRelayControlMode
                  INTEGER,
               sensorRelayManualCycleTime
                  INTEGER,
               sensorRelayManualAction
                  INTEGER,
               sensorRelayPort
                  INTEGER,
               sensorRelaySubPort
                  INTEGER,
               sensorRelayDeviceIndex
                  INTEGER,
               sensorRelayOnDesc 
                  DisplayString,
               sensorRelayOffDesc 
                  DisplayString,
               sensorRelayOnColor 
                  INTEGER,
               sensorRelayOffColor 
                  INTEGER         
            }

            sensorRelayIndex OBJECT-TYPE
               SYNTAX  INTEGER (1..65535)
               ACCESS  read-only
               STATUS  mandatory
               DESCRIPTION
               "The index into the Switch sensor table"
               ::=  {  sensorRelayEntry 1   }

            sensorRelayDescription OBJECT-TYPE
               SYNTAX  DisplayString
               ACCESS  read-write
               STATUS  mandatory
               DESCRIPTION
               "A Description of this sensor Switch"
               ::=  {  sensorRelayEntry 2   }

            sensorRelayType OBJECT-TYPE
               SYNTAX  INTEGER {
                  relay(13),
                  xrelay(19)
               }
               ACCESS  read-only
               STATUS  mandatory
               DESCRIPTION
               "Enter the type of this Sensor"
               ::=  {  sensorRelayEntry 3  }

            sensorRelayStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorRelayEntry 6  }

            sensorRelayGoOffline OBJECT-TYPE
               SYNTAX  INTEGER {
                  online(1),
                  goOffline(2)
               }
               ACCESS  read-write
               STATUS  mandatory
               DESCRIPTION
               "To take offline enter a 2"
               ::=  {  sensorRelayEntry 8  }

            sensorRelayControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a relay."
               ::=  {  sensorRelayEntry 24  }
               
            sensorRelayManualCycleTime OBJECT-TYPE
               SYNTAX  INTEGER (1..255)
               ACCESS  read-write
               STATUS  mandatory
               DESCRIPTION
               "Toggle period in seconds for Manual Cycle action."
               ::=  {  sensorRelayEntry 25  }
               
            sensorRelayManualAction OBJECT-TYPE
               SYNTAX  INTEGER {
                  turn-On(0),
                  turn-Off(1),
                  cycle-On-Off-On(2),
                  cycle-Off-On-Off(3)
               }
               ACCESS  read-write
               STATUS  mandatory
               DESCRIPTION
               "Control the relay manualy"
               ::=  {  sensorRelayEntry 26  }

            sensorRelayPort OBJECT-TYPE
               SYNTAX  INTEGER (0..65534)
               ACCESS  read-only
               STATUS  mandatory
               DESCRIPTION
               "Sensor port"
               ::=  {  sensorRelayEntry 35 }

            sensorRelaySubPort OBJECT-TYPE
               SYNTAX  INTEGER (0..65534)
               ACCESS  read-only
               STATUS  mandatory
               DESCRIPTION
               "Sensor sub port"
               ::=  {  sensorRelayEntry 36 }

            sensorRelayDeviceIndex OBJECT-TYPE
               SYNTAX  INTEGER (0..65534)
               ACCESS  read-only
               STATUS  mandatory
               DESCRIPTION
               "Device Index of sensor"
               ::=  {  sensorRelayEntry 37 }
               
            sensorRelayOnDesc OBJECT-TYPE
               SYNTAX  DisplayString
               ACCESS  read-write
               STATUS  mandatory
               DESCRIPTION
               "A On Description of this sensor"
               ::=  {  sensorRelayEntry  52  }               

            sensorRelayOffDesc OBJECT-TYPE
               SYNTAX  DisplayString
               ACCESS  read-write
               STATUS  mandatory
               DESCRIPTION
               "A Off Description of this sensor"
               ::=  {  sensorRelayEntry  53  }

            sensorRelayOnColor OBJECT-TYPE
               SYNTAX  INTEGER
               ACCESS  read-write
               STATUS  mandatory
               DESCRIPTION
               "A On Color of this sensor"
               ::=  {  sensorRelayEntry  60  }               

            sensorRelayOffColor OBJECT-TYPE
               SYNTAX  INTEGER
               ACCESS  read-write
               STATUS  mandatory
               DESCRIPTION
               "A Off Color of this sensor"
               ::=  {  sensorRelayEntry  61  }     

--/* End of sensorRelayEntry */

--/* Begin of sensorACvoltageEntry */
         sensorACvoltageTable OBJECT-TYPE
            SYNTAX  SEQUENCE OF SensorACvoltageEntry
            ACCESS  not-accessible
            STATUS  mandatory
            DESCRIPTION
            "This table contains the property and reading value for every sensor."
            ::=  {  secSensor 13   }

         sensorACvoltageEntry OBJECT-TYPE
            SYNTAX  SensorACvoltageEntry
            ACCESS  not-accessible
            STATUS  mandatory
            DESCRIPTION
            "This is an entry in the sensorTemperatureEntry Table"
            INDEX         { sensorACvoltageIndex }
            ::=  {  sensorACvoltageTable 1 }

         SensorACvoltageEntry ::= SEQUENCE {
               sensorACvoltageIndex
                  INTEGER,
               sensorACvoltageDescription
                  DisplayString,
               sensorACvoltageStatus
                  INTEGER,
               sensorACvoltageGoOffline
                  INTEGER,
               sensorACvoltagePort
                  INTEGER,
               sensorACvoltageSubPort
                  INTEGER,
               sensorACvoltageDeviceIndex
                  INTEGER,
               sensorACvoltageCriticalDesc 
                  DisplayString,
               sensorACvoltageNormalDesc 
                  DisplayString,
               sensorACvoltageCriticalColor 
                  INTEGER,
               sensorACvoltageNormalColor 
                  INTEGER                   
            }

            sensorACvoltageIndex OBJECT-TYPE
               SYNTAX  INTEGER (1..65535)
               ACCESS  read-only
               STATUS  mandatory
               DESCRIPTION
               "The index into the Switch sensor table"
               ::=  {  sensorACvoltageEntry 1   }

            sensorACvoltageDescription OBJECT-TYPE
               SYNTAX  DisplayString
               ACCESS  read-write
               STATUS  mandatory
               DESCRIPTION
               "A Description of this sensor Switch"
               ::=  {  sensorACvoltageEntry 2   }

            sensorACvoltageStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorACvoltageEntry 6  }

            sensorACvoltageGoOffline OBJECT-TYPE
               SYNTAX  INTEGER {
                  online(1),
                  goOffline(2)
               }
               ACCESS  read-write
               STATUS  mandatory
               DESCRIPTION
               "To put online enter a 1, to take offline enter a 2"
               ::=  {  sensorACvoltageEntry 8  }

            sensorACvoltagePort OBJECT-TYPE
               SYNTAX  INTEGER (0..65534)
               ACCESS  read-only
               STATUS  mandatory
               DESCRIPTION
               "Sensor port"
               ::=  {  sensorACvoltageEntry 35 }

            sensorACvoltageSubPort OBJECT-TYPE
               SYNTAX  INTEGER (0..65534)
               ACCESS  read-only
               STATUS  mandatory
               DESCRIPTION
               "Sensor sub port"
               ::=  {  sensorACvoltageEntry 36 }

            sensorACvoltageDeviceIndex OBJECT-TYPE
               SYNTAX  INTEGER (0..65534)
               ACCESS  read-only
               STATUS  mandatory
               DESCRIPTION
               "Device Index of sensor"
               ::=  {  sensorACvoltageEntry 37 }
               
            sensorACvoltageCriticalDesc OBJECT-TYPE
               SYNTAX  DisplayString
               ACCESS  read-write
               STATUS  mandatory
               DESCRIPTION
               "A Critical Description of this sensor"
               ::=  {  sensorACvoltageEntry  46  }               

            sensorACvoltageNormalDesc OBJECT-TYPE
               SYNTAX  DisplayString
               ACCESS  read-write
               STATUS  mandatory
               DESCRIPTION
               "A Normal Description of this sensor"
               ::=  {  sensorACvoltageEntry  48  }
               
            sensorACvoltageCriticalColor OBJECT-TYPE
               SYNTAX  INTEGER
               ACCESS  read-write
               STATUS  mandatory
               DESCRIPTION
               "A Critical Color of this sensor"
               ::=  {  sensorACvoltageEntry  54  }               

            sensorACvoltageNormalColor OBJECT-TYPE
               SYNTAX  INTEGER
               ACCESS  read-write
               STATUS  mandatory
               DESCRIPTION
               "A Normal Color of this sensor"
               ::=  {  sensorACvoltageEntry  56  }                 

--/* End of sensorACvoltageEntry */

--/* Begin of sensorSmokeEntry */
         sensorSmokeTable OBJECT-TYPE
            SYNTAX  SEQUENCE OF SensorSmokeEntry
            ACCESS  not-accessible
            STATUS  mandatory
            DESCRIPTION
            "This table contains the property and reading value for every sensor."
            ::=  {  secSensor 14   }

         sensorSmokeEntry OBJECT-TYPE
            SYNTAX  SensorSmokeEntry
            ACCESS  not-accessible
            STATUS  mandatory
            DESCRIPTION
            "This is an entry in the sensorTemperatureEntry Table"
            INDEX         { sensorSmokeIndex }
            ::=  {  sensorSmokeTable 1 }

         SensorSmokeEntry ::= SEQUENCE {
               sensorSmokeIndex
                  INTEGER,
               sensorSmokeDescription
                  DisplayString,
               sensorSmokeStatus
                  INTEGER,
               sensorSmokeGoOffline
                  INTEGER,
               sensorSmokePort
                  INTEGER,
               sensorSmokeSubPort
                  INTEGER,
               sensorSmokeDeviceIndex
                  INTEGER,
               sensorSmokeCriticalDesc 
                  DisplayString,
               sensorSmokeNormalDesc 
                  DisplayString,
               sensorSmokeCriticalColor 
                  INTEGER,
               sensorSmokeNormalColor 
                  INTEGER                   
            }

            sensorSmokeIndex OBJECT-TYPE
               SYNTAX  INTEGER (1..65535)
               ACCESS  read-only
               STATUS  mandatory
               DESCRIPTION
               "The index into the Switch sensor table"
               ::=  {  sensorSmokeEntry 1   }

            sensorSmokeDescription OBJECT-TYPE
               SYNTAX  DisplayString
               ACCESS  read-write
               STATUS  mandatory
               DESCRIPTION
               "A Description of this sensor Switch"
               ::=  {  sensorSmokeEntry 2   }

            sensorSmokeStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSmokeEntry 6  }

            sensorSmokeGoOffline OBJECT-TYPE
               SYNTAX  INTEGER {
                  online(1),
                  goOffline(2)
               }
               ACCESS  read-write
               STATUS  mandatory
               DESCRIPTION
               "To take offline enter a 2"
               ::=  {  sensorSmokeEntry 8  }

            sensorSmokePort OBJECT-TYPE
               SYNTAX  INTEGER (0..65534)
               ACCESS  read-only
               STATUS  mandatory
               DESCRIPTION
               "Sensor port"
               ::=  {  sensorSmokeEntry 35 }

            sensorSmokeSubPort OBJECT-TYPE
               SYNTAX  INTEGER (0..65534)
               ACCESS  read-only
               STATUS  mandatory
               DESCRIPTION
               "Sensor sub port"
               ::=  {  sensorSmokeEntry 36 }

            sensorSmokeDeviceIndex OBJECT-TYPE
               SYNTAX  INTEGER (0..65534)
               ACCESS  read-only
               STATUS  mandatory
               DESCRIPTION
               "Device Index of sensor"
               ::=  {  sensorSmokeEntry 37 }

            sensorSmokeCriticalDesc OBJECT-TYPE
               SYNTAX  DisplayString
               ACCESS  read-write
               STATUS  mandatory
               DESCRIPTION
               "A Critical Description of this sensor"
               ::=  {  sensorSmokeEntry  46  }               

            sensorSmokeNormalDesc OBJECT-TYPE
               SYNTAX  DisplayString
               ACCESS  read-write
               STATUS  mandatory
               DESCRIPTION
               "A Normal Description of this sensor"
               ::=  {  sensorSmokeEntry  48  }
        
            sensorSmokeCriticalColor OBJECT-TYPE
               SYNTAX  INTEGER
               ACCESS  read-write
               STATUS  mandatory
               DESCRIPTION
               "A Critical Color of this sensor"
               ::=  {  sensorSmokeEntry  54  }               

            sensorSmokeNormalColor OBJECT-TYPE
               SYNTAX  INTEGER
               ACCESS  read-write
               STATUS  mandatory
               DESCRIPTION
               "A Normal Color of this sensor"
               ::=  {  sensorSmokeEntry  56  }              

--/* End of sensorSmokeEntry */

--/* Begin of sensorThermostatEntry */
         sensorThermostatTable OBJECT-TYPE
            SYNTAX  SEQUENCE OF SensorThermostatEntry
            ACCESS  not-accessible
            STATUS  mandatory
            DESCRIPTION
            "This table contains the property and reading value for every sensor."
            ::=  {  secSensor 20   }

         sensorThermostatEntry OBJECT-TYPE
            SYNTAX  SensorThermostatEntry
            ACCESS  not-accessible
            STATUS  mandatory
            DESCRIPTION
            "This is an entry in the sensorTemperatureEntry Table"
            INDEX         { sensorThermostatIndex }
            ::=  {  sensorThermostatTable 1 }

         SensorThermostatEntry ::= SEQUENCE {
               sensorThermostatIndex
                  INTEGER,
               sensorThermostatDescription
                  DisplayString,
               sensorThermostatDegree
                  INTEGER,
               sensorThermostatStatus
                  INTEGER,
               sensorThermostatGoOffline
                  INTEGER,
               sensorThermostatLowCritical
                  INTEGER,
               sensorThermostatLowWarning
                  INTEGER,
               sensorThermostatHighWarning
                  INTEGER,
               sensorThermostatHighCritical
                  INTEGER,
               sensorThermostatRearm
                  INTEGER,
               sensorThermostatDelayError
                  INTEGER,
               sensorThermostatDelayNormal
                  INTEGER,
               sensorThermostatDelayLowCritical
                  INTEGER,
               sensorThermostatDelayLowWarning
                  INTEGER,
               sensorThermostatDelayHighWarning
                  INTEGER,
               sensorThermostatDelayHighCritical
                  INTEGER,
               sensorThermostatPort
                  INTEGER,
               sensorThermostatSubPort
                  INTEGER,
               sensorThermostatDeviceIndex
                  INTEGER,
               sensorThermostatDisplayStyle
                  INTEGER,
               sensorThermostatHighCriticalDesc 
                  DisplayString,
               sensorThermostatLowCriticalDesc 
                  DisplayString,
               sensorThermostatNormalDesc 
                  DisplayString,
               sensorThermostatLowWarningDesc 
                  DisplayString,   
               sensorThermostatHighWarningDesc 
                  DisplayString,
               sensorThermostatSensorErrorDesc 
                  DisplayString,
               sensorThermostatHighCriticalColor 
                  INTEGER,
               sensorThermostatLowCriticalColor 
                  INTEGER,
               sensorThermostatNormalColor 
                  INTEGER,
               sensorThermostatLowWarningColor 
                  INTEGER,   
               sensorThermostatHighWarningColor 
                  INTEGER,
               sensorThermostatSensorErrorColor 
                  INTEGER            
            }

            sensorThermostatIndex OBJECT-TYPE
               SYNTAX  INTEGER (1..65535)
               ACCESS  read-only
               STATUS  mandatory
               DESCRIPTION
               "The index into the sensor table"
               ::=  {  sensorThermostatEntry 1   }

            sensorThermostatDescription OBJECT-TYPE
               SYNTAX  DisplayString
               ACCESS  read-write
               STATUS  mandatory
               DESCRIPTION
               "A Description of this sensor"
               ::=  {  sensorThermostatEntry 2   }

            sensorThermostatDegree OBJECT-TYPE
               SYNTAX  INTEGER
               ACCESS  read-only
               STATUS  mandatory
               DESCRIPTION
               "The degrees in this sensor"
               ::=  {  sensorThermostatEntry 4   }

            sensorThermostatStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorThermostatEntry 6   }

            sensorThermostatGoOffline OBJECT-TYPE
               SYNTAX  INTEGER {
                  online(1),
                  goOffline(2)
               }
               ACCESS  read-write
               STATUS  mandatory
               DESCRIPTION
               "To take offline enter a 2"
               ::=  {  sensorThermostatEntry 8   }

            sensorThermostatLowCritical OBJECT-TYPE
               SYNTAX  INTEGER
               ACCESS  read-write
               STATUS  mandatory
               DESCRIPTION
               "How cold this sensor gets before it sends a critical event"
               ::=  {  sensorThermostatEntry 9   }

            sensorThermostatLowWarning OBJECT-TYPE
               SYNTAX  INTEGER
               ACCESS  read-write
               STATUS  mandatory
               DESCRIPTION
               "How cold this sensor gets before it sends a warning"
               ::=  {  sensorThermostatEntry 10   }
   
            sensorThermostatHighWarning OBJECT-TYPE
               SYNTAX  INTEGER
               ACCESS  read-write
               STATUS  mandatory
               DESCRIPTION
               "How hot this sensor gets before it sends a warning"
               ::=  {  sensorThermostatEntry 11   }  

            sensorThermostatHighCritical OBJECT-TYPE
               SYNTAX  INTEGER
               ACCESS  read-write
               STATUS  mandatory
               DESCRIPTION
               "How hot this sensor gets before it sends a critical event"
               ::=  {  sensorThermostatEntry 12   }   

            sensorThermostatRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorThermostatEntry 13   }

            sensorThermostatDelayError OBJECT-TYPE
               SYNTAX  INTEGER (0..65534)
               ACCESS  read-write
               STATUS  mandatory
               DESCRIPTION
               "Time in seconds after the sensor has been in error status before report as an error"
               ::=  {  sensorThermostatEntry 14   }

            sensorThermostatDelayNormal OBJECT-TYPE
               SYNTAX  INTEGER (0..65534)
               ACCESS  read-write
               STATUS  mandatory
               DESCRIPTION
               "Time in seconds after the sensor change from error to normal before report as normal"
               ::=  {  sensorThermostatEntry 15   }

            sensorThermostatDelayLowCritical OBJECT-TYPE
               SYNTAX INTEGER (0..65535)
               ACCESS read-write
               STATUS mandatory
               DESCRIPTION
               "Continuous time for this sensor to be in Low Critical before accepting new Status."
               ::= {  sensorThermostatEntry 16 }
               
            sensorThermostatDelayLowWarning OBJECT-TYPE
               SYNTAX INTEGER (0..65535)
               ACCESS read-write
               STATUS mandatory
               DESCRIPTION
               "Continuous time for this sensor to be in Low Warning before accepting new Status."
               ::= {  sensorThermostatEntry 17 }

            sensorThermostatDelayHighWarning OBJECT-TYPE
               SYNTAX INTEGER (0..65535)
               ACCESS read-write
               STATUS mandatory
               DESCRIPTION
               "Continuous time for this sensor to be in High Warning before accepting new Status."
               ::= {  sensorThermostatEntry 18 }

            sensorThermostatDelayHighCritical OBJECT-TYPE
               SYNTAX INTEGER (0..65535)
               ACCESS read-write
               STATUS mandatory
               DESCRIPTION
               "Continuous time for this sensor to be in High Critical before accepting new Status."
               ::= {  sensorThermostatEntry 19 }

            sensorThermostatPort OBJECT-TYPE
               SYNTAX  INTEGER (0..65534)
               ACCESS  read-only
               STATUS  mandatory
               DESCRIPTION
               "Sensor port"
               ::=  {  sensorThermostatEntry 35 }

            sensorThermostatSubPort OBJECT-TYPE
               SYNTAX  INTEGER (0..65534)
               ACCESS  read-only
               STATUS  mandatory
               DESCRIPTION
               "Sensor sub port"
               ::=  {  sensorThermostatEntry 36 }

            sensorThermostatDeviceIndex OBJECT-TYPE
               SYNTAX  INTEGER (0..65534)
               ACCESS  read-only
               STATUS  mandatory
               DESCRIPTION
               "Device Index of sensor"
               ::=  {  sensorThermostatEntry 37 }
               
            sensorThermostatDisplayStyle OBJECT-TYPE
               SYNTAX  INTEGER {
                  basic(0),
                  gauge(1)
               }
               ACCESS  read-write
               STATUS  mandatory
               DESCRIPTION
               "Thermostat display style"
               ::=  {  sensorThermostatEntry 45 } 

            sensorThermostatHighCriticalDesc OBJECT-TYPE
               SYNTAX  DisplayString
               ACCESS  read-write
               STATUS  mandatory
               DESCRIPTION
               "A HighCritical Description of this sensor"
               ::=  {  sensorThermostatEntry  46  }               

            sensorThermostatLowCriticalDesc OBJECT-TYPE
               SYNTAX  DisplayString
               ACCESS  read-write
               STATUS  mandatory
               DESCRIPTION
               "A LowCritical Description of this sensor"
               ::=  {  sensorThermostatEntry  47  }

            sensorThermostatNormalDesc OBJECT-TYPE
               SYNTAX  DisplayString
               ACCESS  read-write
               STATUS  mandatory
               DESCRIPTION
               "A Normal Description of this sensor"
               ::=  {  sensorThermostatEntry  48  }
               
            sensorThermostatLowWarningDesc OBJECT-TYPE
               SYNTAX  DisplayString
               ACCESS  read-write
               STATUS  mandatory
               DESCRIPTION
               "A LowWarning Description of this sensor"
               ::=  {  sensorThermostatEntry  49  }
               
            sensorThermostatHighWarningDesc OBJECT-TYPE
               SYNTAX  DisplayString
               ACCESS  read-write
               STATUS  mandatory
               DESCRIPTION
               "A HighWarning Description of this sensor"
               ::=  {  sensorThermostatEntry  50  }
               
            sensorThermostatSensorErrorDesc OBJECT-TYPE
               SYNTAX  DisplayString
               ACCESS  read-write
               STATUS  mandatory
               DESCRIPTION
               "A SensorError Description of this sensor"
               ::=  {  sensorThermostatEntry  51  }  

            sensorThermostatHighCriticalColor OBJECT-TYPE
               SYNTAX  INTEGER
               ACCESS  read-write
               STATUS  mandatory
               DESCRIPTION
               "A HighCritical Color of this sensor"
               ::=  {  sensorThermostatEntry  54  }               

            sensorThermostatLowCriticalColor OBJECT-TYPE
               SYNTAX  INTEGER
               ACCESS  read-write
               STATUS  mandatory
               DESCRIPTION
               "A LowCritical Color of this sensor"
               ::=  {  sensorThermostatEntry  55  }

            sensorThermostatNormalColor OBJECT-TYPE
               SYNTAX  INTEGER
               ACCESS  read-write
               STATUS  mandatory
               DESCRIPTION
               "A Normal Color of this sensor"
               ::=  {  sensorThermostatEntry  56  }
               
            sensorThermostatLowWarningColor OBJECT-TYPE
               SYNTAX  INTEGER
               ACCESS  read-write
               STATUS  mandatory
               DESCRIPTION
               "A LowWarning Color of this sensor"
               ::=  {  sensorThermostatEntry  57  }
               
            sensorThermostatHighWarningColor OBJECT-TYPE
               SYNTAX  INTEGER
               ACCESS  read-write
               STATUS  mandatory
               DESCRIPTION
               "A HighWarning Color of this sensor"
               ::=  {  sensorThermostatEntry  58  }
               
            sensorThermostatSensorErrorColor OBJECT-TYPE
               SYNTAX  INTEGER
               ACCESS  read-write
               STATUS  mandatory
               DESCRIPTION
               "A SensorError Color of this sensor"
               ::=  {  sensorThermostatEntry  59  }             

--/* End of sensorThermostatEntry */

--/* Begin of sensorWaterRopeEntry */
         sensorWaterRopeTable OBJECT-TYPE
            SYNTAX  SEQUENCE OF SensorWaterRopeEntry
            ACCESS  not-accessible
            STATUS  mandatory
            DESCRIPTION
            "This table contains the property and reading value for every sensor."
            ::=  {  secSensor 21   }

         sensorWaterRopeEntry OBJECT-TYPE
            SYNTAX  SensorWaterRopeEntry
            ACCESS  not-accessible
            STATUS  mandatory
            DESCRIPTION
            "This is an entry in the SensorWaterRopeEntry Table"
            INDEX         { sensorWaterRopeIndex }
            ::=  {  sensorWaterRopeTable 1 }

         SensorWaterRopeEntry ::= SEQUENCE {
               sensorWaterRopeIndex
                  INTEGER,
               sensorWaterRopeDescription
                  DisplayString,
               sensorWaterRopeLeakLocation
                  INTEGER,
               sensorWaterRopeUnit
                  DisplayString,
               sensorWaterRopeStatus
                  INTEGER,
               sensorWaterRopeGoOffline
                  INTEGER,
               sensorWaterRopeRaw
                  INTEGER,
               sensorWaterRopeDeviceIndex
                  INTEGER,               
               sensorWaterRopeCriticalDesc 
                  DisplayString,
               sensorWaterRopeNormalDesc 
                  DisplayString,
               sensorWaterRopeSensorErrorDesc 
                  DisplayString,
               sensorWaterRopeCriticalColor 
                  INTEGER,
               sensorWaterRopeNormalColor 
                  INTEGER,
               sensorWaterRopeSensorErrorColor 
                  INTEGER,
               sensorWaterRopeLength
                  INTEGER,
               sensorWaterRopeImpedance
                  INTEGER,
               sensorWaterRopeType
                  INTEGER
            }

            sensorWaterRopeIndex OBJECT-TYPE
               SYNTAX  INTEGER (1..65535)
               ACCESS  read-only
               STATUS  mandatory
               DESCRIPTION
               "The index into the sensor table"
               ::=  {  sensorWaterRopeEntry 1   }

            sensorWaterRopeDescription OBJECT-TYPE
               SYNTAX  DisplayString
               ACCESS  read-write
               STATUS  mandatory
               DESCRIPTION
               "A Description of this sensor"
               ::=  {  sensorWaterRopeEntry 2   }

            sensorWaterRopeLeakLocation OBJECT-TYPE
               SYNTAX INTEGER
               ACCESS read-only
               STATUS mandatory
               DESCRIPTION
               "Location of leakage of water rope sensor."
               ::= {  sensorWaterRopeEntry 4 }

            sensorWaterRopeUnit OBJECT-TYPE
               SYNTAX  DisplayString
               ACCESS  read-write
               STATUS  mandatory
               DESCRIPTION
               "Display unit of water rope sensor."
               ::=  {  sensorWaterRopeEntry 5   }

            sensorWaterRopeStatus OBJECT-TYPE
               SYNTAX  INTEGER {
                  noStatus(1),
                  normal(2),
                  highCritical(4),
                  sensorError(7)
               }
               ACCESS  read-only
               STATUS  mandatory
               DESCRIPTION
               "The current status of this Sensor"
               ::=  {  sensorWaterRopeEntry 6  }

            sensorWaterRopeGoOffline OBJECT-TYPE
               SYNTAX  INTEGER {
                  online(1),
                  goOffline(2)
               }
               ACCESS  read-write
               STATUS  mandatory
               DESCRIPTION
               "To take offline enter a 2"
               ::=  {  sensorWaterRopeEntry 8  }
               
            sensorWaterRopeRaw OBJECT-TYPE
               SYNTAX INTEGER
               ACCESS read-only
               STATUS mandatory
               DESCRIPTION
               "Raw value of location or length in ohms"
               ::= {  sensorWaterRopeEntry 20 }

            sensorWaterRopeDeviceIndex OBJECT-TYPE
               SYNTAX  INTEGER (0..65534)
               ACCESS  read-only
               STATUS  mandatory
               DESCRIPTION
               "Device Index of sensor"
               ::=  {  sensorWaterRopeEntry 37 }
               
            sensorWaterRopeCriticalDesc OBJECT-TYPE
               SYNTAX  DisplayString
               ACCESS  read-write
               STATUS  mandatory
               DESCRIPTION
               "A Critical Description of this sensor"
               ::=  {  sensorWaterRopeEntry  46  }  
               
            sensorWaterRopeNormalDesc OBJECT-TYPE
               SYNTAX  DisplayString
               ACCESS  read-write
               STATUS  mandatory
               DESCRIPTION
               "A Normal Description of this sensor"
               ::=  {  sensorWaterRopeEntry  48  }
               
            sensorWaterRopeSensorErrorDesc OBJECT-TYPE
               SYNTAX  DisplayString
               ACCESS  read-write
               STATUS  mandatory
               DESCRIPTION
               "A SensorError Description of this sensor"
               ::=  {  sensorWaterRopeEntry  51  }  
               
            sensorWaterRopeCriticalColor OBJECT-TYPE
               SYNTAX  INTEGER
               ACCESS  read-write
               STATUS  mandatory
               DESCRIPTION
               "A Critical Color of this sensor"
               ::=  {  sensorWaterRopeEntry  54  }               

            sensorWaterRopeNormalColor OBJECT-TYPE
               SYNTAX  INTEGER
               ACCESS  read-write
               STATUS  mandatory
               DESCRIPTION
               "A Normal Color of this sensor"
               ::=  {  sensorWaterRopeEntry  56  }
               
            sensorWaterRopeSensorErrorColor OBJECT-TYPE
               SYNTAX  INTEGER
               ACCESS  read-write
               STATUS  mandatory
               DESCRIPTION
               "A SensorError Color of this sensor"
               ::=  {  sensorWaterRopeEntry  59  }               
            
            sensorWaterRopeLength OBJECT-TYPE
               SYNTAX INTEGER
               ACCESS read-only
               STATUS mandatory
               DESCRIPTION
               "Length of water rope sensor."
               ::= {  sensorWaterRopeEntry 100 }

            sensorWaterRopeImpedance OBJECT-TYPE
               SYNTAX INTEGER (0..65535)
               ACCESS read-write
               STATUS mandatory
               DESCRIPTION
               "Sensing wire impedance per meter value times 100"
               ::= {  sensorWaterRopeEntry 101 }            
 
            sensorWaterRopeType OBJECT-TYPE
               SYNTAX  INTEGER {
                  custom(0),
                  water(1),
                  fuel(2)
               }
               ACCESS read-write
               STATUS mandatory
               DESCRIPTION
               "Water rope sensing cable type"
               ::= {  sensorWaterRopeEntry 103 }                
               
--/* End of sensorWaterRopeEntry */

--/* Begin of sensorPowerEntry */
         sensorPowerTable OBJECT-TYPE
            SYNTAX  SEQUENCE OF SensorPowerEntry
            ACCESS  not-accessible
            STATUS  mandatory
            DESCRIPTION
            "This table contains the property and reading value for every sensor."
            ::=  {  secSensor 22   }

         sensorPowerEntry OBJECT-TYPE
            SYNTAX  SensorPowerEntry
            ACCESS  not-accessible
            STATUS  mandatory
            DESCRIPTION
            "This is an entry in the sensorPowerEntry Table"
            INDEX         { sensorPowerIndex }
            ::=  {  sensorPowerTable 1 }

         SensorPowerEntry ::= SEQUENCE {
               sensorPowerIndex
                  INTEGER,
               sensorPowerDescription
                  DisplayString,
               sensorPowerValue
                  INTEGER,
               sensorPowerUnit
                  DisplayString,
               sensorPowerStatus
                  INTEGER,
               sensorPowerGoOffline
                  INTEGER,
               sensorPowerLowCritical
                  INTEGER,
               sensorPowerLowWarning
                  INTEGER,
               sensorPowerHighWarning
                  INTEGER,
               sensorPowerHighCritical
                  INTEGER,
               sensorPowerRearm
                  INTEGER,
               sensorPowerDelayError
                  INTEGER,
               sensorPowerDelayNormal
                  INTEGER,
               sensorPowerDelayLowCritical
                  INTEGER,
               sensorPowerDelayLowWarning
                  INTEGER,
               sensorPowerDelayHighWarning
                  INTEGER,
               sensorPowerDelayHighCritical
                  INTEGER,
               sensorPowerPort
                  INTEGER,
               sensorPowerSubPort
                  INTEGER,
               sensorPowerDeviceIndex
                  INTEGER,
               sensorPowerTimeOut
                  INTEGER,
               sensorPowerInterval
                  INTEGER,
               sensorPowerErrorRetryNum
                  INTEGER,
               sensorPowerMaxValue
                  INTEGER,
               sensorPowerMinValue
                  INTEGER,
               sensorPowerDisplayStyle
                  INTEGER,
               sensorPowerHighCriticalDesc 
                  DisplayString,
               sensorPowerLowCriticalDesc 
                  DisplayString,
               sensorPowerNormalDesc 
                  DisplayString,
               sensorPowerLowWarningDesc 
                  DisplayString,   
               sensorPowerHighWarningDesc 
                  DisplayString,
               sensorPowerSensorErrorDesc 
                  DisplayString,
               sensorPowerHighCriticalColor 
                  INTEGER,
               sensorPowerLowCriticalColor 
                  INTEGER,
               sensorPowerNormalColor 
                  INTEGER,
               sensorPowerLowWarningColor 
                  INTEGER,   
               sensorPowerHighWarningColor 
                  INTEGER,
               sensorPowerSensorErrorColor 
                  INTEGER         
            }

            sensorPowerIndex OBJECT-TYPE
               SYNTAX  INTEGER (1..65535)
               ACCESS  read-only
               STATUS  mandatory
               DESCRIPTION
               "The index into the Switch sensor table"
               ::=  {  sensorPowerEntry 1   }

            sensorPowerDescription OBJECT-TYPE
               SYNTAX  DisplayString
               ACCESS  read-write
               STATUS  mandatory
               DESCRIPTION
               "A Description of this sensor Switch"
               ::=  {  sensorPowerEntry 2   }

            sensorPowerValue OBJECT-TYPE
               SYNTAX  INTEGER
               ACCESS  read-only
               STATUS  mandatory
               DESCRIPTION
               "The reading value in this sensor"
               ::=  {  sensorPowerEntry 4   }

            sensorPowerUnit OBJECT-TYPE
               SYNTAX  DisplayString
               ACCESS  read-write
               STATUS  mandatory
               DESCRIPTION
               "The unit string"
               ::=  {  sensorPowerEntry 5  }

            sensorPowerStatus OBJECT-TYPE
               SYNTAX  INTEGER {
                  noStatus(1),
                  normal(2),
                  highCritical(4),
                  lowCritical(6),
                  sensorError(7)
               }
               ACCESS  read-only
               STATUS  mandatory
               DESCRIPTION
               "The current status of this Sensor, only input switches have a status"
               ::=  {  sensorPowerEntry 6  }

            sensorPowerGoOffline OBJECT-TYPE
               SYNTAX  INTEGER {
                  online(1),
                  goOffline(2)
               }
               ACCESS  read-write
               STATUS  mandatory
               DESCRIPTION
               "To take offline enter a 2"
               ::=  {  sensorPowerEntry 8  }

            sensorPowerLowCritical OBJECT-TYPE
               SYNTAX  INTEGER
               ACCESS  read-write
               STATUS  mandatory
               DESCRIPTION
               "How cold this sensor gets before it sends a critical event"
               ::=  {  sensorPowerEntry 9   }

            sensorPowerLowWarning OBJECT-TYPE
               SYNTAX  INTEGER
               ACCESS  read-write
               STATUS  mandatory
               DESCRIPTION
               "How cold this sensor gets before it sends a warning"
               ::=  {  sensorPowerEntry 10   }
   
            sensorPowerHighWarning OBJECT-TYPE
               SYNTAX  INTEGER
               ACCESS  read-write
               STATUS  mandatory
               DESCRIPTION
               "How hot this sensor gets before it sends a warning"
               ::=  {  sensorPowerEntry 11   }  

            sensorPowerHighCritical OBJECT-TYPE
               SYNTAX  INTEGER
               ACCESS  read-write
               STATUS  mandatory
               DESCRIPTION
               "How hot this sensor gets before it sends a critical event"
               ::=  {  sensorPowerEntry 12   }   

            sensorPowerRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorPowerEntry 13   }

            sensorPowerDelayError OBJECT-TYPE
               SYNTAX  INTEGER (0..65534)
               ACCESS  read-write
               STATUS  mandatory
               DESCRIPTION
               "Time in seconds after the sensor has been in error status before report as an error"
               ::=  {  sensorPowerEntry 14   }

            sensorPowerDelayNormal OBJECT-TYPE
               SYNTAX  INTEGER (0..65534)
               ACCESS  read-write
               STATUS  mandatory
               DESCRIPTION
               "Time in seconds after the sensor change from error to normal before report as normal"
               ::=  {  sensorPowerEntry 15   }

            sensorPowerDelayLowCritical OBJECT-TYPE
               SYNTAX INTEGER (0..65535)
               ACCESS read-write
               STATUS mandatory
               DESCRIPTION
               "Continuous time for this sensor to be in Low Critical before accepting new Status."
               ::= {  sensorPowerEntry 16 }
               
            sensorPowerDelayLowWarning OBJECT-TYPE
               SYNTAX INTEGER (0..65535)
               ACCESS read-write
               STATUS mandatory
               DESCRIPTION
               "Continuous time for this sensor to be in Low Warning before accepting new Status."
               ::= {  sensorPowerEntry 17 }

            sensorPowerDelayHighWarning OBJECT-TYPE
               SYNTAX INTEGER (0..65535)
               ACCESS read-write
               STATUS mandatory
               DESCRIPTION
               "Continuous time for this sensor to be in High Warning before accepting new Status."
               ::= {  sensorPowerEntry 18 }

            sensorPowerDelayHighCritical OBJECT-TYPE
               SYNTAX INTEGER (0..65535)
               ACCESS read-write
               STATUS mandatory
               DESCRIPTION
               "Continuous time for this sensor to be in High Critical before accepting new Status."
               ::= {  sensorPowerEntry 19 }

            sensorPowerPort OBJECT-TYPE
               SYNTAX  INTEGER (0..65534)
               ACCESS  read-only
               STATUS  mandatory
               DESCRIPTION
               "Sensor port"
               ::=  {  sensorPowerEntry 35 }

            sensorPowerSubPort OBJECT-TYPE
               SYNTAX  INTEGER (0..65534)
               ACCESS  read-only
               STATUS  mandatory
               DESCRIPTION
               "Sensor sub port"
               ::=  {  sensorPowerEntry 36 }

            sensorPowerDeviceIndex OBJECT-TYPE
               SYNTAX  INTEGER (0..65534)
               ACCESS  read-only
               STATUS  mandatory
               DESCRIPTION
               "Device Index of sensor"
               ::=  {  sensorPowerEntry 37 }

            sensorPowerTimeOut OBJECT-TYPE
               SYNTAX  INTEGER (5..30)
               ACCESS  read-write
               STATUS  mandatory
               DESCRIPTION
               "The polling timeout of Power Sensor."
               ::=  {  sensorPowerEntry 38 }

            sensorPowerInterval OBJECT-TYPE
               SYNTAX  INTEGER (5..720)
               ACCESS  read-write
               STATUS  mandatory
               DESCRIPTION
               "The polling interval of Power Sensor."
               ::=  {  sensorPowerEntry 39 }

            sensorPowerErrorRetryNum OBJECT-TYPE
               SYNTAX  INTEGER
               ACCESS  read-write
               STATUS  mandatory
               DESCRIPTION
               "Number of retry before error."
               ::=  {  sensorPowerEntry 40 }
               
            sensorPowerMaxValue OBJECT-TYPE
               SYNTAX  INTEGER
               ACCESS  read-write
               STATUS  mandatory
               DESCRIPTION
               "The maximum scale of Power value."
               ::=  {  sensorPowerEntry 41   }

            sensorPowerMinValue OBJECT-TYPE
               SYNTAX  INTEGER
               ACCESS  read-write
               STATUS  mandatory
               DESCRIPTION
               "The minimum scale of Power value."
               ::=  {  sensorPowerEntry 42   }
               
            sensorPowerDisplayStyle OBJECT-TYPE
               SYNTAX  INTEGER {
                  basic(0),
                  gauge(1)
               }
               ACCESS  read-write
               STATUS  mandatory
               DESCRIPTION
               "Power display style."
               ::=  {  sensorPowerEntry 45 } 
               
            sensorPowerHighCriticalDesc OBJECT-TYPE
               SYNTAX  DisplayString
               ACCESS  read-write
               STATUS  mandatory
               DESCRIPTION
               "A HighCritical Description of this sensor"
               ::=  {  sensorPowerEntry  46  }               

            sensorPowerLowCriticalDesc OBJECT-TYPE
               SYNTAX  DisplayString
               ACCESS  read-write
               STATUS  mandatory
               DESCRIPTION
               "A LowCritical Description of this sensor"
               ::=  {  sensorPowerEntry  47  }

            sensorPowerNormalDesc OBJECT-TYPE
               SYNTAX  DisplayString
               ACCESS  read-write
               STATUS  mandatory
               DESCRIPTION
               "A Normal Description of this sensor"
               ::=  {  sensorPowerEntry  48  }
               
            sensorPowerLowWarningDesc OBJECT-TYPE
               SYNTAX  DisplayString
               ACCESS  read-write
               STATUS  mandatory
               DESCRIPTION
               "A LowWarning Description of this sensor"
               ::=  {  sensorPowerEntry  49  }
               
            sensorPowerHighWarningDesc OBJECT-TYPE
               SYNTAX  DisplayString
               ACCESS  read-write
               STATUS  mandatory
               DESCRIPTION
               "A HighWarning Description of this sensor"
               ::=  {  sensorPowerEntry  50  }
               
            sensorPowerSensorErrorDesc OBJECT-TYPE
               SYNTAX  DisplayString
               ACCESS  read-write
               STATUS  mandatory
               DESCRIPTION
               "A SensorError Description of this sensor"
               ::=  {  sensorPowerEntry  51  }  

            sensorPowerHighCriticalColor OBJECT-TYPE
               SYNTAX  INTEGER
               ACCESS  read-write
               STATUS  mandatory
               DESCRIPTION
               "A HighCritical Color of this sensor"
               ::=  {  sensorPowerEntry   54 }               

            sensorPowerLowCriticalColor OBJECT-TYPE
               SYNTAX  INTEGER
               ACCESS  read-write
               STATUS  mandatory
               DESCRIPTION
               "A LowCritical Color of this sensor"
               ::=  {  sensorPowerEntry  55  }

            sensorPowerNormalColor OBJECT-TYPE
               SYNTAX  INTEGER
               ACCESS  read-write
               STATUS  mandatory
               DESCRIPTION
               "A Normal Color of this sensor"
               ::=  {  sensorPowerEntry  56  }
               
            sensorPowerLowWarningColor OBJECT-TYPE
               SYNTAX  INTEGER
               ACCESS  read-write
               STATUS  mandatory
               DESCRIPTION
               "A LowWarning Color of this sensor"
               ::=  {  sensorPowerEntry  57  }
               
            sensorPowerHighWarningColor OBJECT-TYPE
               SYNTAX  INTEGER
               ACCESS  read-write
               STATUS  mandatory
               DESCRIPTION
               "A HighWarning Color of this sensor"
               ::=  {  sensorPowerEntry  58  }
               
            sensorPowerSensorErrorColor OBJECT-TYPE
               SYNTAX  INTEGER
               ACCESS  read-write
               STATUS  mandatory
               DESCRIPTION
               "A SensorError Color of this sensor"
               ::=  {  sensorPowerEntry  59  }  

--/* End of sensorPowerEntry */

--/* Begin of sensorFuelEntry */
         sensorFuelTable OBJECT-TYPE
            SYNTAX  SEQUENCE OF SensorFuelEntry
            ACCESS  not-accessible
            STATUS  mandatory
            DESCRIPTION
            "This table contains the property and reading value for every sensor."
            ::=  {  secSensor 24   }

         sensorFuelEntry OBJECT-TYPE
            SYNTAX  SensorFuelEntry
            ACCESS  not-accessible
            STATUS  mandatory
            DESCRIPTION
            "This is an entry in the SensorFuelEntry Table"
            INDEX         { sensorFuelIndex }
            ::=  {  sensorFuelTable 1 }

         SensorFuelEntry ::= SEQUENCE {
               sensorFuelIndex
                  INTEGER,
               sensorFuelDescription
                  DisplayString,
               sensorFuelValue
                  INTEGER,
               sensorFuelUnit
                  DisplayString,
               sensorFuelStatus
                  INTEGER,
               sensorFuelGoOffline
                  INTEGER,
               sensorFuelLowCritical
                  INTEGER,
               sensorFuelLowWarning
                  INTEGER,
               sensorFuelHighWarning
                  INTEGER,
               sensorFuelHighCritical
                  INTEGER,
               sensorFuelRearm
                  INTEGER,
               sensorFuelDelayError
                  INTEGER,
               sensorFuelDelayNormal
                  INTEGER,
               sensorFuelDelayLowCritical
                  INTEGER,
               sensorFuelDelayLowWarning
                  INTEGER,
               sensorFuelDelayHighWarning
                  INTEGER,
               sensorFuelDelayHighCritical
                  INTEGER,
               sensorFuelRaw
                  INTEGER,
               sensorFuelAmountMaxValue
                  INTEGER,
               sensorFuelAmountBaseValue
                  INTEGER,
               sensorFuelDeviceIndex
                  INTEGER,
               sensorFuelDisplayStyle
                  INTEGER,
               sensorFuelHighCriticalDesc 
                  DisplayString,
               sensorFuelLowCriticalDesc 
                  DisplayString,
               sensorFuelNormalDesc 
                  DisplayString,
               sensorFuelLowWarningDesc 
                  DisplayString,   
               sensorFuelHighWarningDesc 
                  DisplayString,
               sensorFuelSensorErrorDesc 
                  DisplayString,
               sensorFuelHighCriticalColor 
                  INTEGER,
               sensorFuelLowCriticalColor 
                  INTEGER,
               sensorFuelNormalColor 
                  INTEGER,
               sensorFuelLowWarningColor 
                  INTEGER,   
               sensorFuelHighWarningColor 
                  INTEGER,
               sensorFuelSensorErrorColor 
                  INTEGER             
            }

            sensorFuelIndex OBJECT-TYPE
               SYNTAX  INTEGER (1..65535)
               ACCESS  read-only
               STATUS  mandatory
               DESCRIPTION
               "The index into the sensor table"
               ::=  {  sensorFuelEntry 1   }

            sensorFuelDescription OBJECT-TYPE
               SYNTAX  DisplayString
               ACCESS  read-write
               STATUS  mandatory
               DESCRIPTION
               "A Description of this sensor"
               ::=  {  sensorFuelEntry 2   }

            sensorFuelValue OBJECT-TYPE
               SYNTAX  INTEGER
               ACCESS  read-only
               STATUS  mandatory
               DESCRIPTION
               "The reading value in this sensor"
               ::=  {  sensorFuelEntry 4   }

            sensorFuelUnit OBJECT-TYPE
               SYNTAX  DisplayString
               ACCESS  read-write
               STATUS  mandatory
               DESCRIPTION
               "The unit string"
               ::=  {  sensorFuelEntry 5  }

            sensorFuelStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorFuelEntry 6   }

            sensorFuelGoOffline OBJECT-TYPE
               SYNTAX  INTEGER {
                  online(1),
                  goOffline(2)
               }
               ACCESS  read-write
               STATUS  mandatory
               DESCRIPTION
               "To take offline enter a 2"
               ::=  {  sensorFuelEntry 8   }

            sensorFuelLowCritical OBJECT-TYPE
               SYNTAX  INTEGER
               ACCESS  read-write
               STATUS  mandatory
               DESCRIPTION
               "Level value of this sensor gets before it sends a critical event"
               ::=  {  sensorFuelEntry 9   }

            sensorFuelLowWarning OBJECT-TYPE
               SYNTAX  INTEGER
               ACCESS  read-write
               STATUS  mandatory
               DESCRIPTION
               "Level value of this sensor gets before it sends a warning"
               ::=  {  sensorFuelEntry 10   }
   
            sensorFuelHighWarning OBJECT-TYPE
               SYNTAX  INTEGER
               ACCESS  read-write
               STATUS  mandatory
               DESCRIPTION
               "Level value of this sensor gets before it sends a warning"
               ::=  {  sensorFuelEntry 11   }  

            sensorFuelHighCritical OBJECT-TYPE
               SYNTAX  INTEGER
               ACCESS  read-write
               STATUS  mandatory
               DESCRIPTION
               "Level value of this sensor gets before it sends a critical event"
               ::=  {  sensorFuelEntry 12   }   

            sensorFuelRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorFuelEntry 13   }

            sensorFuelDelayError OBJECT-TYPE
               SYNTAX  INTEGER (0..65534)
               ACCESS  read-write
               STATUS  mandatory
               DESCRIPTION
               "Time in seconds after the sensor has been in error status before report as an error"
               ::=  {  sensorFuelEntry 14   }

            sensorFuelDelayNormal OBJECT-TYPE
               SYNTAX  INTEGER (0..65534)
               ACCESS  read-write
               STATUS  mandatory
               DESCRIPTION
               "Time in seconds after the sensor change from error to normal before report as normal"
               ::=  {  sensorFuelEntry 15   }

            sensorFuelDelayLowCritical OBJECT-TYPE
               SYNTAX INTEGER (0..65535)
               ACCESS read-write
               STATUS mandatory
               DESCRIPTION
               "Continuous time for this sensor to be in Low Critical before accepting new Status."
               ::= {  sensorFuelEntry 16 }
               
            sensorFuelDelayLowWarning OBJECT-TYPE
               SYNTAX INTEGER (0..65535)
               ACCESS read-write
               STATUS mandatory
               DESCRIPTION
               "Continuous time for this sensor to be in Low Warning before accepting new Status."
               ::= {  sensorFuelEntry 17 }

            sensorFuelDelayHighWarning OBJECT-TYPE
               SYNTAX INTEGER (0..65535)
               ACCESS read-write
               STATUS mandatory
               DESCRIPTION
               "Continuous time for this sensor to be in High Warning before accepting new Status."
               ::= {  sensorFuelEntry 18 }

            sensorFuelDelayHighCritical OBJECT-TYPE
               SYNTAX INTEGER (0..65535)
               ACCESS read-write
               STATUS mandatory
               DESCRIPTION
               "Continuous time for this sensor to be in High Critical before accepting new Status."
               ::= {  sensorFuelEntry 19 }

            sensorFuelRaw OBJECT-TYPE
               SYNTAX  INTEGER 
               ACCESS  read-only
               STATUS  mandatory
               DESCRIPTION
               "The unformatted, raw, A/D value in this sensor. Contains more resolution than the formated percentage."
               ::=  {  sensorFuelEntry 20   }

            sensorFuelAmountMaxValue OBJECT-TYPE
               SYNTAX  INTEGER
               ACCESS  read-write
               STATUS  mandatory
               DESCRIPTION
               "The maximum scale of value conversion."
               ::=  {  sensorFuelEntry 33   }

            sensorFuelAmountBaseValue OBJECT-TYPE
               SYNTAX  INTEGER
               ACCESS  read-write
               STATUS  mandatory
               DESCRIPTION
               "The base scale of value conversion."
               ::=  {  sensorFuelEntry 34   }

            sensorFuelDeviceIndex OBJECT-TYPE
               SYNTAX  INTEGER (0..65534)
               ACCESS  read-only
               STATUS  mandatory
               DESCRIPTION
               "Device Index of sensor"
               ::=  {  sensorFuelEntry 37 }
               
            sensorFuelDisplayStyle OBJECT-TYPE
               SYNTAX  INTEGER {
                  basic(0),
                  gauge(1)
               }
               ACCESS  read-write
               STATUS  mandatory
               DESCRIPTION
               "Fuel display style"
               ::=  {  sensorFuelEntry 45 }     

            sensorFuelHighCriticalDesc OBJECT-TYPE
               SYNTAX  DisplayString
               ACCESS  read-write
               STATUS  mandatory
               DESCRIPTION
               "A HighCritical Description of this sensor"
               ::=  {  sensorFuelEntry  46  }               

            sensorFuelLowCriticalDesc OBJECT-TYPE
               SYNTAX  DisplayString
               ACCESS  read-write
               STATUS  mandatory
               DESCRIPTION
               "A LowCritical Description of this sensor"
               ::=  {  sensorFuelEntry  47  }

            sensorFuelNormalDesc OBJECT-TYPE
               SYNTAX  DisplayString
               ACCESS  read-write
               STATUS  mandatory
               DESCRIPTION
               "A Normal Description of this sensor"
               ::=  {  sensorFuelEntry  48  }
               
            sensorFuelLowWarningDesc OBJECT-TYPE
               SYNTAX  DisplayString
               ACCESS  read-write
               STATUS  mandatory
               DESCRIPTION
               "A LowWarning Description of this sensor"
               ::=  {  sensorFuelEntry  49  }
               
            sensorFuelHighWarningDesc OBJECT-TYPE
               SYNTAX  DisplayString
               ACCESS  read-write
               STATUS  mandatory
               DESCRIPTION
               "A HighWarning Description of this sensor"
               ::=  {  sensorFuelEntry  50  }
               
            sensorFuelSensorErrorDesc OBJECT-TYPE
               SYNTAX  DisplayString
               ACCESS  read-write
               STATUS  mandatory
               DESCRIPTION
               "A SensorError Description of this sensor"
               ::=  {  sensorFuelEntry  51  }  

            sensorFuelHighCriticalColor OBJECT-TYPE
               SYNTAX  INTEGER
               ACCESS  read-write
               STATUS  mandatory
               DESCRIPTION
               "A HighCritical Color of this sensor"
               ::=  {  sensorFuelEntry  54  }               

            sensorFuelLowCriticalColor OBJECT-TYPE
               SYNTAX  INTEGER
               ACCESS  read-write
               STATUS  mandatory
               DESCRIPTION
               "A LowCritical Color of this sensor"
               ::=  {  sensorFuelEntry  55  }

            sensorFuelNormalColor OBJECT-TYPE
               SYNTAX  INTEGER
               ACCESS  read-write
               STATUS  mandatory
               DESCRIPTION
               "A Normal Color of this sensor"
               ::=  {  sensorFuelEntry  56  }
               
            sensorFuelLowWarningColor OBJECT-TYPE
               SYNTAX  INTEGER
               ACCESS  read-write
               STATUS  mandatory
               DESCRIPTION
               "A LowWarning Color of this sensor"
               ::=  {  sensorFuelEntry  57  }
               
            sensorFuelHighWarningColor OBJECT-TYPE
               SYNTAX  INTEGER
               ACCESS  read-write
               STATUS  mandatory
               DESCRIPTION
               "A HighWarning Color of this sensor"
               ::=  {  sensorFuelEntry  58  }
               
            sensorFuelSensorErrorColor OBJECT-TYPE
               SYNTAX  INTEGER
               ACCESS  read-write
               STATUS  mandatory
               DESCRIPTION
               "A SensorError Color of this sensor"
               ::=  {  sensorFuelEntry  59  }           

--/* End of sensorFuelEntry */

--/* Begin of sensorTankSenderEntry */
         sensorTankSenderTable OBJECT-TYPE
            SYNTAX  SEQUENCE OF SensorTankSenderEntry
            ACCESS  not-accessible
            STATUS  mandatory
            DESCRIPTION
            "This table contains the property and reading value for every sensor."
            ::=  {  secSensor 26   }

         sensorTankSenderEntry OBJECT-TYPE
            SYNTAX  SensorTankSenderEntry
            ACCESS  not-accessible
            STATUS  mandatory
            DESCRIPTION
            "This is an entry in the sensorTankSenderEntry Table"
            INDEX         { sensorTankSenderIndex }
            ::=  {  sensorTankSenderTable 1 }

         SensorTankSenderEntry ::= SEQUENCE {
               sensorTankSenderIndex
                  INTEGER,
               sensorTankSenderDescription
                  DisplayString,
               sensorTankSenderValue
                  INTEGER,
               sensorTankSenderUnit
                  DisplayString,
               sensorTankSenderStatus
                  INTEGER,
               sensorTankSenderGoOffline
                  INTEGER,
               sensorTankSenderLowCritical
                  INTEGER,
               sensorTankSenderLowWarning
                  INTEGER,
               sensorTankSenderHighWarning
                  INTEGER,
               sensorTankSenderHighCritical
                  INTEGER,
               sensorTankSenderRearm
                  INTEGER,
               sensorTankSenderDelayError
                  INTEGER,
               sensorTankSenderDelayNormal
                  INTEGER,
               sensorTankSenderDelayLowCritical
                  INTEGER,
               sensorTankSenderDelayLowWarning
                  INTEGER,
               sensorTankSenderDelayHighWarning
                  INTEGER,
               sensorTankSenderDelayHighCritical
                  INTEGER,
               sensorTankSenderRaw
                  INTEGER,
               sensorTankSenderDeviceIndex
                  INTEGER,
               sensorTankSenderDisplayStyle
                  INTEGER,
               sensorTankSenderHighCriticalDesc 
                  DisplayString,
               sensorTankSenderLowCriticalDesc 
                  DisplayString,
               sensorTankSenderNormalDesc 
                  DisplayString,
               sensorTankSenderLowWarningDesc 
                  DisplayString,   
               sensorTankSenderHighWarningDesc 
                  DisplayString,
               sensorTankSenderSensorErrorDesc 
                  DisplayString,
               sensorTankSenderHighCriticalColor 
                  INTEGER,
               sensorTankSenderLowCriticalColor 
                  INTEGER,
               sensorTankSenderNormalColor 
                  INTEGER,
               sensorTankSenderLowWarningColor 
                  INTEGER,   
               sensorTankSenderHighWarningColor 
                  INTEGER,
               sensorTankSenderSensorErrorColor 
                  INTEGER             
            }

            sensorTankSenderIndex OBJECT-TYPE
               SYNTAX  INTEGER (1..65535)
               ACCESS  read-only
               STATUS  mandatory
               DESCRIPTION
               "The index into the sensor table"
               ::=  {  sensorTankSenderEntry 1   }

            sensorTankSenderDescription OBJECT-TYPE
               SYNTAX  DisplayString
               ACCESS  read-write
               STATUS  mandatory
               DESCRIPTION
               "A Description of this sensor"
               ::=  {  sensorTankSenderEntry 2   }

            sensorTankSenderValue OBJECT-TYPE
               SYNTAX  INTEGER
               ACCESS  read-only
               STATUS  mandatory
               DESCRIPTION
               "The reading value in this sensor"
               ::=  {  sensorTankSenderEntry 4   }

            sensorTankSenderUnit OBJECT-TYPE
               SYNTAX  DisplayString
               ACCESS  read-write
               STATUS  mandatory
               DESCRIPTION
               "The unit string"
               ::=  {  sensorTankSenderEntry 5  }

            sensorTankSenderStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTankSenderEntry 6   }

            sensorTankSenderGoOffline OBJECT-TYPE
               SYNTAX  INTEGER {
                  online(1),
                  goOffline(2)
               }
               ACCESS  read-write
               STATUS  mandatory
               DESCRIPTION
               "To take offline enter a 2"
               ::=  {  sensorTankSenderEntry 8   }

            sensorTankSenderLowCritical OBJECT-TYPE
               SYNTAX  INTEGER
               ACCESS  read-write
               STATUS  mandatory
               DESCRIPTION
               "Level value of this sensor gets before it sends a critical event"
               ::=  {  sensorTankSenderEntry 9   }

            sensorTankSenderLowWarning OBJECT-TYPE
               SYNTAX  INTEGER
               ACCESS  read-write
               STATUS  mandatory
               DESCRIPTION
               "Level value of this sensor gets before it sends a warning"
               ::=  {  sensorTankSenderEntry 10   }
   
            sensorTankSenderHighWarning OBJECT-TYPE
               SYNTAX  INTEGER
               ACCESS  read-write
               STATUS  mandatory
               DESCRIPTION
               "Level value of this sensor gets before it sends a warning"
               ::=  {  sensorTankSenderEntry 11   }  

            sensorTankSenderHighCritical OBJECT-TYPE
               SYNTAX  INTEGER
               ACCESS  read-write
               STATUS  mandatory
               DESCRIPTION
               "Level value of this sensor gets before it sends a critical event"
               ::=  {  sensorTankSenderEntry 12   }   

            sensorTankSenderRearm OBJECT-TYPE
               SYNTAX  INTEGER
               ACCESS  read-write
               STATUS  mandatory
               DESCRIPTION
               "The number of degrees to rearm the status. For example if status goes from normal to warning, the temp must go down spTempRearm degrees below warning before the status goes to normal"
               ::=  {  sensorTankSenderEntry 13   }

            sensorTankSenderDelayError OBJECT-TYPE
               SYNTAX  INTEGER (0..65534)
               ACCESS  read-write
               STATUS  mandatory
               DESCRIPTION
               "Time in seconds after the sensor has been in error status before report as an error"
               ::=  {  sensorTankSenderEntry 14   }

            sensorTankSenderDelayNormal OBJECT-TYPE
               SYNTAX  INTEGER (0..65534)
               ACCESS  read-write
               STATUS  mandatory
               DESCRIPTION
               "Time in seconds after the sensor change from error to normal before report as normal"
               ::=  {  sensorTankSenderEntry 15   }

            sensorTankSenderDelayLowCritical OBJECT-TYPE
               SYNTAX INTEGER (0..65535)
               ACCESS read-write
               STATUS mandatory
               DESCRIPTION
               "Continuous time for this sensor to be in Low Critical before accepting new Status."
               ::= {  sensorTankSenderEntry 16 }
               
            sensorTankSenderDelayLowWarning OBJECT-TYPE
               SYNTAX INTEGER (0..65535)
               ACCESS read-write
               STATUS mandatory
               DESCRIPTION
               "Continuous time for this sensor to be in Low Warning before accepting new Status."
               ::= {  sensorTankSenderEntry 17 }

            sensorTankSenderDelayHighWarning OBJECT-TYPE
               SYNTAX INTEGER (0..65535)
               ACCESS read-write
               STATUS mandatory
               DESCRIPTION
               "Continuous time for this sensor to be in High Warning before accepting new Status."
               ::= {  sensorTankSenderEntry 18 }

            sensorTankSenderDelayHighCritical OBJECT-TYPE
               SYNTAX INTEGER (0..65535)
               ACCESS read-write
               STATUS mandatory
               DESCRIPTION
               "Continuous time for this sensor to be in High Critical before accepting new Status."
               ::= {  sensorTankSenderEntry 19 }

            sensorTankSenderRaw OBJECT-TYPE
               SYNTAX  INTEGER 
               ACCESS  read-only
               STATUS  mandatory
               DESCRIPTION
               "The unformatted, raw, A/D value in this sensor. Contains more resolution than the formated percentage."
               ::=  {  sensorTankSenderEntry 20   }

            sensorTankSenderDeviceIndex OBJECT-TYPE
               SYNTAX  INTEGER (0..65534)
               ACCESS  read-only
               STATUS  mandatory
               DESCRIPTION
               "Device Index of sensor"
               ::=  {  sensorTankSenderEntry 37 }
               
            sensorTankSenderDisplayStyle OBJECT-TYPE
               SYNTAX  INTEGER {
                  basic(0),
                  gauge(1)
               }
               ACCESS  read-write
               STATUS  mandatory
               DESCRIPTION
               "TankSender display style"
               ::=  {  sensorTankSenderEntry 45 }     

            sensorTankSenderHighCriticalDesc OBJECT-TYPE
               SYNTAX  DisplayString
               ACCESS  read-write
               STATUS  mandatory
               DESCRIPTION
               "A HighCritical Description of this sensor"
               ::=  {  sensorTankSenderEntry  46  }               

            sensorTankSenderLowCriticalDesc OBJECT-TYPE
               SYNTAX  DisplayString
               ACCESS  read-write
               STATUS  mandatory
               DESCRIPTION
               "A LowCritical Description of this sensor"
               ::=  {  sensorTankSenderEntry  47  }

            sensorTankSenderNormalDesc OBJECT-TYPE
               SYNTAX  DisplayString
               ACCESS  read-write
               STATUS  mandatory
               DESCRIPTION
               "A Normal Description of this sensor"
               ::=  {  sensorTankSenderEntry  48  }
               
            sensorTankSenderLowWarningDesc OBJECT-TYPE
               SYNTAX  DisplayString
               ACCESS  read-write
               STATUS  mandatory
               DESCRIPTION
               "A LowWarning Description of this sensor"
               ::=  {  sensorTankSenderEntry  49  }
               
            sensorTankSenderHighWarningDesc OBJECT-TYPE
               SYNTAX  DisplayString
               ACCESS  read-write
               STATUS  mandatory
               DESCRIPTION
               "A HighWarning Description of this sensor"
               ::=  {  sensorTankSenderEntry  50  }
               
            sensorTankSenderSensorErrorDesc OBJECT-TYPE
               SYNTAX  DisplayString
               ACCESS  read-write
               STATUS  mandatory
               DESCRIPTION
               "A SensorError Description of this sensor"
               ::=  {  sensorTankSenderEntry  51  }  

            sensorTankSenderHighCriticalColor OBJECT-TYPE
               SYNTAX  INTEGER
               ACCESS  read-write
               STATUS  mandatory
               DESCRIPTION
               "A HighCritical Color of this sensor"
               ::=  {  sensorTankSenderEntry  54  }               

            sensorTankSenderLowCriticalColor OBJECT-TYPE
               SYNTAX  INTEGER
               ACCESS  read-write
               STATUS  mandatory
               DESCRIPTION
               "A LowCritical Color of this sensor"
               ::=  {  sensorTankSenderEntry  55  }

            sensorTankSenderNormalColor OBJECT-TYPE
               SYNTAX  INTEGER
               ACCESS  read-write
               STATUS  mandatory
               DESCRIPTION
               "A Normal Color of this sensor"
               ::=  {  sensorTankSenderEntry  56  }
               
            sensorTankSenderLowWarningColor OBJECT-TYPE
               SYNTAX  INTEGER
               ACCESS  read-write
               STATUS  mandatory
               DESCRIPTION
               "A LowWarning Color of this sensor"
               ::=  {  sensorTankSenderEntry  57  }
               
            sensorTankSenderHighWarningColor OBJECT-TYPE
               SYNTAX  INTEGER
               ACCESS  read-write
               STATUS  mandatory
               DESCRIPTION
               "A HighWarning Color of this sensor"
               ::=  {  sensorTankSenderEntry  58  }
               
            sensorTankSenderSensorErrorColor OBJECT-TYPE
               SYNTAX  INTEGER
               ACCESS  read-write
               STATUS  mandatory
               DESCRIPTION
               "A SensorError Color of this sensor"
               ::=  {  sensorTankSenderEntry  59  }           

--/* End of sensorTankSenderEntry */

--
-- Varbinds used in TRAP Definitions
--

      sensorProbeTraps      OBJECT IDENTIFIER  ::=  {  sensorProbe 7   }

      spSensorStatus OBJECT-TYPE
            SYNTAX  INTEGER {
               noStatus(1),
               normal(2),
               highWarning(3),
               highCritical(4),
               lowWarning(5),
               lowCritical(6),
               sensorError(7),
               turnOn(8),
               turnOff(9)
            }
         ACCESS  read-only
         STATUS  mandatory
         DESCRIPTION
         "The current integer status of the sensor causing this trap to be sent"
         ::=  {  sensorProbeTraps 1  }
      
      spSensorValue OBJECT-TYPE
         SYNTAX  INTEGER
         ACCESS  read-only
         STATUS  mandatory
         DESCRIPTION
         "The current integer value of the sensor causing this trap to be sent"
         ::=  {  sensorProbeTraps 2  }
      
      spSensorLevelExceeded OBJECT-TYPE
         SYNTAX  INTEGER
         ACCESS  read-only
         STATUS  mandatory
         DESCRIPTION
         "The integer level that was exceeded causing this trap to be sent"
         ::=  {  sensorProbeTraps 3  }
      

      spSensorIndex OBJECT-TYPE
         SYNTAX  INTEGER
         ACCESS  read-only
         STATUS  mandatory
         DESCRIPTION
         "The integer index of the sensor causing this trap to be sent"
         ::=  {  sensorProbeTraps 4  }
      

      spSensorName OBJECT-TYPE
         SYNTAX  DisplayString
         ACCESS  read-only
         STATUS  mandatory
         DESCRIPTION
         "The name of the sensor causing this trap to be sent"
         ::=  {  sensorProbeTraps 5  }
      
      spSensorDescription OBJECT-TYPE
         SYNTAX  DisplayString
         ACCESS  read-only
         STATUS  mandatory
         DESCRIPTION
         "The description of the sensor causing this trap to be sent"
         ::=  {  sensorProbeTraps 6  }
      
      spSensorProbeKeepAlive OBJECT-TYPE
         SYNTAX  INTEGER
         ACCESS  read-only
         STATUS  mandatory
         DESCRIPTION
         "Keep alive trap to be sent"
         ::=  {  sensorProbeTraps 7  }
      
      spSensorType OBJECT-TYPE
         SYNTAX  INTEGER {
            temperature(1),
            fourTo20mA(2),
            humidity(3),
            water(4),
            atod(5),
            security(6),
            airflow(8),
            siren(9),
            dryContact(10),
            voltage(12),
            relay(13),
            motion(14),
            extradrycontact(16),
            thermostat(23),
            smoke(24),
            power(25),
            irms(26),
            vrms(27),
            watt(28),
            relayarray(29),
            virtual(30),
            watthour(32),
            temperaturearray(33),
            waterrope(34),
            fuellevel(35),
			tanksender(36),
            sound(128),
            softwaremotion(129),
            nosignal(132),
            powermeter(134)
         }
         ACCESS  read-only
         STATUS  mandatory
         DESCRIPTION
         "Type of this sensor"
         ::=  {  sensorProbeTraps 8  }
      
      spSensorStatusName OBJECT-TYPE
         SYNTAX  DisplayString
         ACCESS  read-only
         STATUS  mandatory
         DESCRIPTION
    "The current status of the sensor causing this trap to be sent"
         ::=  {  sensorProbeTraps 9  }
      
      spSensorSubIndex OBJECT-TYPE
         SYNTAX  INTEGER
         ACCESS  read-only
         STATUS  mandatory
         DESCRIPTION
    "The integer sub index of the sensor causing this trap to be sent. Only for temperaturearray and relayarray"
         ::=  {  sensorProbeTraps 10  }
      
      spBoardIndex OBJECT-TYPE
         SYNTAX  INTEGER
         ACCESS  read-only
         STATUS  mandatory
         DESCRIPTION
    "The integer index of the sensor board causing this trap to be sent."
         ::=  {  sensorProbeTraps 11  }

      spBoardDescription OBJECT-TYPE
         SYNTAX  DisplayString
         ACCESS  read-only
         STATUS  mandatory
         DESCRIPTION
    "The description of the sensor board causing this trap to be sent"
         ::=  {  sensorProbeTraps 12  }
      
      spEventTimeStamp OBJECT-TYPE
         SYNTAX  DisplayString
         ACCESS  read-only
         STATUS  mandatory
         DESCRIPTION
    "The time(MM/DD/YYYY HH:MM:SS) of an event causing this trap to be sent"
         ::=  {  sensorProbeTraps 13  }
   
      spEventClassNumber OBJECT-TYPE
         SYNTAX  INTEGER
         ACCESS  read-only
         STATUS  mandatory
         DESCRIPTION
    "The user-defined class number associated with this trap"
         ::=  {  sensorProbeTraps 14  }
   
      spEventClassName OBJECT-TYPE
         SYNTAX  DisplayString
         ACCESS  read-only
         STATUS  mandatory
         DESCRIPTION
    "The user-defined class Name associated with this trap"
         ::=  {  sensorProbeTraps 15  }
   
      spSensorDecimalValue OBJECT-TYPE
         SYNTAX  DisplayString
         ACCESS  read-only
         STATUS  mandatory
         DESCRIPTION
     "The current decimal value of the sensor causing this trap to be sent"
         ::=  {  sensorProbeTraps 16  }

      spSensorAliveHigh OBJECT-TYPE
         SYNTAX  INTEGER
         ACCESS  read-only
         STATUS  mandatory
         DESCRIPTION
         "The highest sensor value in the period"
         ::=  {  sensorProbeTraps 17  }

      spSensorAliveLow OBJECT-TYPE
         SYNTAX  INTEGER
         ACCESS  read-only
         STATUS  mandatory
         DESCRIPTION
         "The  lowset sensor value in the period"
         ::=  {  sensorProbeTraps 18  }

-- TRAP Definitions

   spNormalStatus TRAP-TYPE
      ENTERPRISE sensorProbe
      DESCRIPTION
         "sensorProbe status is Normal"
      --#TYPE "sensorProbe Normal Status"
      --#SEVERITY INFORMATIONAL
      ::= 1

   spWarningStatus TRAP-TYPE
      ENTERPRISE sensorProbe
      DESCRIPTION
         "sensorProbe status went to Warning"
      --#TYPE "sensorProbe Warning Status"
      --#SEVERITY MINOR
      ::= 2

   spCriticalStatus TRAP-TYPE
      ENTERPRISE sensorProbe
      DESCRIPTION
         "sensorProbe status went to Critical"
      --#TYPE "sensorProbe Critical Status"
      --#SEVERITY MAJOR
      ::= 3

   spDownStatus TRAP-TYPE
      ENTERPRISE sensorProbe
      DESCRIPTION
         "sensorProbe status went to Disabled"
      --#TYPE "sensorProbe Down Status"
      --#SEVERITY MINOR
      ::= 4

   spKeepAliveTrap TRAP-TYPE
      ENTERPRISE sensorProbe
      DESCRIPTION
         "sensorProbe send keep alive trap."
      --#SEVERITY  INFORMATIONAL
      ::= 5

   spUnknownStatus TRAP-TYPE
      ENTERPRISE sensorProbe
      DESCRIPTION
         "sensorProbe status went to Unknown"
      --#TYPE "sensorProbe Unknown Status"
      --#SEVERITY INFORMATIONAL
      ::= 7      

-- sensorProbeTrapType = generalTypeTrap(2)

   spTemperatureStatus TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 10

   spTemperatureArray1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 11

   spTemperatureArray2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 12

   spTemperatureArray3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 13

   spTemperatureArray4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 14

   spTemperatureArray5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 15

   spTemperatureArray6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 16

   spTemperatureArray7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 17

   spTemperatureArray8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 18

   spAnalogueStatus TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 20

   spSwitchStatus TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 30

   spIRMSStatus TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 40

   spVRMSStatus TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 50

   spWattStatus TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 60

   spRelayArray1Status TRAP-TYPE
      ENTERPRISE sensorProbe
      VARIABLES
         { spSensorStatus, spSensorValue, spSensorLevelExceeded, 
         spSensorIndex, spSensorName, spSensorDescription }
      DESCRIPTION
         "RelayArray1 sensor trap"
      --#SEVERITY  MAJOR
      ::= 71

   spRelayArray2Status TRAP-TYPE
      ENTERPRISE sensorProbe
      VARIABLES
         { spSensorStatus, spSensorValue, spSensorLevelExceeded, 
         spSensorIndex, spSensorName, spSensorDescription }
      DESCRIPTION
         "RelayArray2 sensor trap"
      --#SEVERITY  MAJOR
      ::= 72

   spRelayArray3Status TRAP-TYPE
      ENTERPRISE sensorProbe
      VARIABLES
         { spSensorStatus, spSensorValue, spSensorLevelExceeded, 
         spSensorIndex, spSensorName, spSensorDescription }
      DESCRIPTION
         "RelayArray3 sensor trap"
      --#SEVERITY  MAJOR
      ::= 73

   spRelayArray4Status TRAP-TYPE
      ENTERPRISE sensorProbe
      VARIABLES
         { spSensorStatus, spSensorValue, spSensorLevelExceeded, 
         spSensorIndex, spSensorName, spSensorDescription }
      DESCRIPTION
         "RelayArray4 sensor trap"
      --#SEVERITY  MAJOR
      ::= 74

   spRelayArray5Status TRAP-TYPE
      ENTERPRISE sensorProbe
      VARIABLES
         { spSensorStatus, spSensorValue, spSensorLevelExceeded, 
         spSensorIndex, spSensorName, spSensorDescription }
      DESCRIPTION
         "RelayArray5 sensor trap"
      --#SEVERITY  MAJOR
      ::= 75

   spRelayArray6Status TRAP-TYPE
      ENTERPRISE sensorProbe
      VARIABLES
         { spSensorStatus, spSensorValue, spSensorLevelExceeded, 
         spSensorIndex, spSensorName, spSensorDescription }
      DESCRIPTION
         "RelayArray6 sensor trap"
      --#SEVERITY  MAJOR
      ::= 77

   spRelayArray8Status TRAP-TYPE
      ENTERPRISE sensorProbe
      VARIABLES
         { spSensorStatus, spSensorValue, spSensorLevelExceeded, 
         spSensorIndex, spSensorName, spSensorDescription }
      DESCRIPTION
         "RelayArray8 sensor trap"
      --#SEVERITY  MAJOR
      ::= 78

   spVirtualStatus TRAP-TYPE
      ENTERPRISE sensorProbe
      VARIABLES
         { spSensorStatus, spSensorValue, spSensorLevelExceeded, 
         spSensorIndex, spSensorName, spSensorDescription }
      DESCRIPTION
         "Virtual sensor trap"
      --#SEVERITY  MAJOR
      ::= 80

-- sensorProbeTrapType = statusTypeTraps(4)

   spSenUnknownStatus TRAP-TYPE
      ENTERPRISE sensorProbe
      VARIABLES
         { spSensorStatus, spSensorValue, spSensorLevelExceeded, 
         spSensorIndex, spSensorName, spSensorDescription }
      DESCRIPTION
         "sensorProbe sensor status went to Unknown"
      --#TYPE "sensorProbe Unknown Status"
      --#SUMMARY "%s(%s) Status is now %d on port %d."
      --#ARGUMENTS {4,5,1,3}
      --#SEVERITY MAJOR
      --#TIMEINDEX 4
      ::= 51

   spSenNormalStatus TRAP-TYPE
      ENTERPRISE sensorProbe
      VARIABLES
         { spSensorStatus, spSensorValue, spSensorLevelExceeded, 
         spSensorIndex, spSensorName, spSensorDescription }
      DESCRIPTION
         "sensorProbe sensor status is Normal"
      --#TYPE "sensorProbe Normal Status"
      --#SUMMARY "%s(%s) Status is now %d on port %d."
      --#ARGUMENTS {4,5,1,3}
      --#SEVERITY INFORMATIONAL
      --#TIMEINDEX 4
      ::= 52

   spSenWarningStatus TRAP-TYPE
      ENTERPRISE sensorProbe
      VARIABLES
         { spSensorStatus, spSensorValue, spSensorLevelExceeded, 
         spSensorIndex, spSensorName, spSensorDescription }
      DESCRIPTION
         "sensorProbe sensor status went to Warning"
      --#TYPE "sensorProbe Warning Status"
      --#SUMMARY "%s(%s) Status is now %d on port %d."
      --#ARGUMENTS {4,5,1,3}
      --#SEVERITY MINOR
      --#TIMEINDEX 4
      ::= 53

   spSenCriticalStatus TRAP-TYPE
      ENTERPRISE sensorProbe
      VARIABLES
         { spSensorStatus, spSensorValue, spSensorLevelExceeded, 
         spSensorIndex, spSensorName, spSensorDescription }
      DESCRIPTION
         "sensorProbe sensor status went to Critical"
      --#TYPE "sensorProbe Critical Status"
      --#SUMMARY "%s(%s) Status is now %d on port %d."
      --#ARGUMENTS {4,5,1,3}
      --#SEVERITY MAJOR
      --#TIMEINDEX 4
      ::= 54

   spSenDownStatus TRAP-TYPE
      ENTERPRISE sensorProbe
      VARIABLES
         { spSensorStatus, spSensorValue, spSensorLevelExceeded, 
         spSensorIndex, spSensorName, spSensorDescription }
      DESCRIPTION
         "sensorProbe sensor status went to Disabled"
      --#TYPE "sensorProbe Down Status"
      --#SUMMARY "%s(%s) Status is now %d on port %d."
      --#ARGUMENTS {4,5,1,3}
      --#SEVERITY INFORMATIONAL
      --#TIMEINDEX 4
      ::= 55

-- sensorProbeTrapType = specificTypeTrap(1)

   spTemperature1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 101

   spTemperature2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 102

   spTemperature3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 103

   spTemperature4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 104

   spTemperature5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 105

   spTemperature6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 106

   spTemperature7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 107

   spTemperature8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 108



   spTemperatureArray1-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 111

   spTemperatureArray1-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 112

   spTemperatureArray1-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 113

   spTemperatureArray1-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 114

   spTemperatureArray1-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 115

   spTemperatureArray1-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 116

   spTemperatureArray1-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 117

   spTemperatureArray1-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 118



   spTemperatureArray2-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 121

   spTemperatureArray2-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 122

   spTemperatureArray2-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 123

   spTemperatureArray2-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 124

   spTemperatureArray2-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 125

   spTemperatureArray2-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 126

   spTemperatureArray2-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 127

   spTemperatureArray2-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 128



   spTemperatureArray3-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 131

   spTemperatureArray3-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 132

   spTemperatureArray3-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 133

   spTemperatureArray3-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 134

   spTemperatureArray3-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 135

   spTemperatureArray3-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 136

   spTemperatureArray3-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 137

   spTemperatureArray3-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 138



   spTemperatureArray4-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 141

   spTemperatureArray4-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 142

   spTemperatureArray4-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 143

   spTemperatureArray4-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 144

   spTemperatureArray4-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 145

   spTemperatureArray4-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 146

   spTemperatureArray4-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 147

   spTemperatureArray4-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 148



   spTemperatureArray5-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 151

   spTemperatureArray5-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 152

   spTemperatureArray5-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 153

   spTemperatureArray5-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 154

   spTemperatureArray5-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 155

   spTemperatureArray5-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 156

   spTemperatureArray5-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 157

   spTemperatureArray5-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 158



   spTemperatureArray6-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 161

   spTemperatureArray6-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 162

   spTemperatureArray6-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 163

   spTemperatureArray6-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 164

   spTemperatureArray6-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 165

   spTemperatureArray6-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 166

   spTemperatureArray6-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 167

   spTemperatureArray6-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 168



   spTemperatureArray7-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 171

   spTemperatureArray7-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 172

   spTemperatureArray7-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 173

   spTemperatureArray7-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 174

   spTemperatureArray7-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 175

   spTemperatureArray7-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 176

   spTemperatureArray7-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 177

   spTemperatureArray7-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 178



   spTemperatureArray8-1Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 181

   spTemperatureArray8-2Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 182

   spTemperatureArray8-3Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 183

   spTemperatureArray8-4Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 184

   spTemperatureArray8-5Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 185

   spTemperatureArray8-6Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 186

   spTemperatureArray8-7Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 187

   spTemperatureArray8-8Status TRAP-TYPE
      ENTERPRISE sensorProbe
      VARIABLES
         { spSensorStatus, spSensorValue, spSensorLevelExceeded, 
         spSensorIndex, spSensorName, spSensorDescription }
      DESCRIPTION
         "Temperature sensor trap"
      --#SEVERITY  MAJOR
      ::= 188



   spAnalogue1Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 201

   spAnalogue2Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 202

   spAnalogue3Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 203

   spAnalogue4Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 204

   spAnalogue5Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 205

   spAnalogue6Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 206

   spAnalogue7Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 207

   spAnalogue8Status TRAP-TYPE
      ENTERPRISE sensorProbe
      VARIABLES
         { spSensorStatus, spSensorValue, spSensorLevelExceeded, 
         spSensorIndex, spSensorName, spSensorDescription }
      DESCRIPTION
         "Analogue Sensor Type"
      --#SEVERITY  MAJOR
      ::= 208



   spSwitch1Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 301

   spSwitch2Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 302

   spSwitch3Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 303

   spSwitch4Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 304

   spSwitch5Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 305

   spSwitch6Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 306

   spSwitch7Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 307

   spSwitch8Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 308

   spSwitch9Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 309

   spSwitch10Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 310

   spSwitch11Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 311

   spSwitch12Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 312

   spSwitch13Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 313

   spSwitch14Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 314

   spSwitch15Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 315

   spSwitch16Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 316

   spSwitch17Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 317

   spSwitch18Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 318

   spSwitch19Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 319

   spSwitch20Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 320

   spSwitch21Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 321

   spSwitch22Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 322

   spSwitch23Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 323

   spSwitch24Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 324

   spSwitch25Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 325

   spSwitch26Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 326

   spSwitch27Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 327

   spSwitch28Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 328

   spSwitch29Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 329

   spSwitch30Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 330

   spSwitch31Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 331

   spSwitch32Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 332

   spSwitch33Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 333

   spSwitch34Status TRAP-TYPE
      ENTERPRISE sensorProbe
      VARIABLES
         { spSensorStatus, spSensorValue, spSensorLevelExceeded, 
         spSensorIndex, spSensorName, spSensorDescription }
      DESCRIPTION
         "Switch sensor trap"
      --#SEVERITY  MAJOR
      ::= 334

   spSwitch35Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 335

   spSwitch36Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 336

   spSwitch37Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 337

   spSwitch38Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 338

   spSwitch39Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 339

   spSwitch40Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 340

   spSwitch41Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 341

   spSwitch42Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 342

   spSwitch43Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 343

   spSwitch44Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 344

   spSwitch45Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 345

   spSwitch46Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 346

   spSwitch47Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 347

   spSwitch48Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 348

   spSwitch49Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 349

   spSwitch50Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 350

   spSwitch51Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 351

   spSwitch52Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 352

   spSwitch53Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 353

   spSwitch54Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 354

   spSwitch55Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 355

   spSwitch56Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 356

   spSwitch57Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 357

   spSwitch58Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 358

   spSwitch59Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 359

   spSwitch60Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 360

   spSwitch61Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 361

   spSwitch62Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 362

   spSwitch63Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 363

   spSwitch64Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 364

   spSwitch65Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 365

   spSwitch66Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 366

   spSwitch67Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 367

   spSwitch68Status TRAP-TYPE
      ENTERPRISE sensorProbe
      VARIABLES
         { spSensorStatus, spSensorValue, spSensorLevelExceeded,
         spSensorIndex, spSensorName, spSensorDescription }
      DESCRIPTION
         "Switch sensor trap"
      --#SEVERITY  MAJOR
      ::= 368

   spIRMS1Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 401

   spIRMS2Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 402

   spIRMS3Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 403

   spIRMS4Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 404

   spIRMS5Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 405

   spIRMS6Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 406

   spIRMS7Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 407

   spIRMS8Status TRAP-TYPE
      ENTERPRISE sensorProbe
      VARIABLES
         { spSensorStatus, spSensorValue, spSensorLevelExceeded, 
         spSensorIndex, spSensorName, spSensorDescription }
      DESCRIPTION
         "IRMS sensor trap"
      --#SEVERITY  MAJOR
      ::= 408

   spVRMS1Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 501

   spVRMS2Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 502

   spVRMS3Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 503

   spVRMS4Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 504

   spVRMS5Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 505

   spVRMS6Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 506

   spVRMS7Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 507

   spVRMS8Status TRAP-TYPE
      ENTERPRISE sensorProbe
      VARIABLES
         { spSensorStatus, spSensorValue, spSensorLevelExceeded, 
         spSensorIndex, spSensorName, spSensorDescription }
      DESCRIPTION
         "VRMS sensor trap"
      --#SEVERITY  MAJOR
      ::= 508

   spEnergy1Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 601

   spEnergy2Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 602

   spEnergy3Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 603

   spEnergy4Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 604

   spEnergy5Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 605

   spEnergy6Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 606

   spEnergy7Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 607

   spEnergy8Status TRAP-TYPE
      ENTERPRISE sensorProbe
      VARIABLES
         { spSensorStatus, spSensorValue, spSensorLevelExceeded, 
         spSensorIndex, spSensorName, spSensorDescription }
      DESCRIPTION
         "Energy sensor trap"
      --#SEVERITY  MAJOR
      ::= 608

   spRelayArray1-1Status TRAP-TYPE
      ENTERPRISE sensorProbe
      VARIABLES
         { spSensorStatus, spSensorValue, spSensorLevelExceeded, 
         spSensorIndex, spSensorName, spSensorDescription }
      DESCRIPTION
         "RelayArray1.1 sensor trap"
      --#SEVERITY  MAJOR
      ::= 711

   spRelayArray1-2Status TRAP-TYPE
      ENTERPRISE sensorProbe
      VARIABLES
         { spSensorStatus, spSensorValue, spSensorLevelExceeded, 
         spSensorIndex, spSensorName, spSensorDescription }
      DESCRIPTION
         "RelayArray1.2 sensor trap"
      --#SEVERITY  MAJOR
      ::= 712

   spRelayArray1-3Status TRAP-TYPE
      ENTERPRISE sensorProbe
      VARIABLES
         { spSensorStatus, spSensorValue, spSensorLevelExceeded, 
         spSensorIndex, spSensorName, spSensorDescription }
      DESCRIPTION
         "RelayArray1.3 sensor trap"
      --#SEVERITY  MAJOR
      ::= 713

   spRelayArray1-4Status TRAP-TYPE
      ENTERPRISE sensorProbe
      VARIABLES
         { spSensorStatus, spSensorValue, spSensorLevelExceeded, 
         spSensorIndex, spSensorName, spSensorDescription }
      DESCRIPTION
         "RelayArray1.4 sensor trap"
      --#SEVERITY  MAJOR
      ::= 714

   spRelayArray1-5Status TRAP-TYPE
      ENTERPRISE sensorProbe
      VARIABLES
         { spSensorStatus, spSensorValue, spSensorLevelExceeded, 
         spSensorIndex, spSensorName, spSensorDescription }
      DESCRIPTION
         "RelayArray1.5 sensor trap"
      --#SEVERITY  MAJOR
      ::= 715

   spRelayArray1-6Status TRAP-TYPE
      ENTERPRISE sensorProbe
      VARIABLES
         { spSensorStatus, spSensorValue, spSensorLevelExceeded, 
         spSensorIndex, spSensorName, spSensorDescription }
      DESCRIPTION
         "RelayArray1.6 sensor trap"
      --#SEVERITY  MAJOR
      ::= 716

   spRelayArray1-7Status TRAP-TYPE
      ENTERPRISE sensorProbe
      VARIABLES
         { spSensorStatus, spSensorValue, spSensorLevelExceeded, 
         spSensorIndex, spSensorName, spSensorDescription }
      DESCRIPTION
         "RelayArray1.7 sensor trap"
      --#SEVERITY  MAJOR
      ::= 717

   spRelayArray1-8Status TRAP-TYPE
      ENTERPRISE sensorProbe
      VARIABLES
         { spSensorStatus, spSensorValue, spSensorLevelExceeded, 
         spSensorIndex, spSensorName, spSensorDescription }
      DESCRIPTION
         "RelayArray1.8 sensor trap"
      --#SEVERITY  MAJOR
      ::= 718

   spRelayArray2-1Status TRAP-TYPE
      ENTERPRISE sensorProbe
      VARIABLES
         { spSensorStatus, spSensorValue, spSensorLevelExceeded, 
         spSensorIndex, spSensorName, spSensorDescription }
      DESCRIPTION
         "RelayArray2.1 sensor trap"
      --#SEVERITY  MAJOR
      ::= 721

   spRelayArray2-2Status TRAP-TYPE
      ENTERPRISE sensorProbe
      VARIABLES
         { spSensorStatus, spSensorValue, spSensorLevelExceeded, 
         spSensorIndex, spSensorName, spSensorDescription }
      DESCRIPTION
         "RelayArray2.2 sensor trap"
      --#SEVERITY  MAJOR
      ::= 722

   spRelayArray2-3Status TRAP-TYPE
      ENTERPRISE sensorProbe
      VARIABLES
         { spSensorStatus, spSensorValue, spSensorLevelExceeded, 
         spSensorIndex, spSensorName, spSensorDescription }
      DESCRIPTION
         "RelayArray2.3 sensor trap"
      --#SEVERITY  MAJOR
      ::= 723

   spRelayArray2-4Status TRAP-TYPE
      ENTERPRISE sensorProbe
      VARIABLES
         { spSensorStatus, spSensorValue, spSensorLevelExceeded, 
         spSensorIndex, spSensorName, spSensorDescription }
      DESCRIPTION
         "RelayArray2.4 sensor trap"
      --#SEVERITY  MAJOR
      ::= 724

   spRelayArray2-5Status TRAP-TYPE
      ENTERPRISE sensorProbe
      VARIABLES
         { spSensorStatus, spSensorValue, spSensorLevelExceeded, 
         spSensorIndex, spSensorName, spSensorDescription }
      DESCRIPTION
         "RelayArray2.5 sensor trap"
      --#SEVERITY  MAJOR
      ::= 725

   spRelayArray2-6Status TRAP-TYPE
      ENTERPRISE sensorProbe
      VARIABLES
         { spSensorStatus, spSensorValue, spSensorLevelExceeded, 
         spSensorIndex, spSensorName, spSensorDescription }
      DESCRIPTION
         "RelayArray2.6 sensor trap"
      --#SEVERITY  MAJOR
      ::= 726

   spRelayArray2-7Status TRAP-TYPE
      ENTERPRISE sensorProbe
      VARIABLES
         { spSensorStatus, spSensorValue, spSensorLevelExceeded, 
         spSensorIndex, spSensorName, spSensorDescription }
      DESCRIPTION
         "RelayArray2.7 sensor trap"
      --#SEVERITY  MAJOR
      ::= 727

   spRelayArray2-8Status TRAP-TYPE
      ENTERPRISE sensorProbe
      VARIABLES
         { spSensorStatus, spSensorValue, spSensorLevelExceeded, 
         spSensorIndex, spSensorName, spSensorDescription }
      DESCRIPTION
         "RelayArray2.8 sensor trap"
      --#SEVERITY  MAJOR
      ::= 728

   spRelayArray3-1Status TRAP-TYPE
      ENTERPRISE sensorProbe
      VARIABLES
         { spSensorStatus, spSensorValue, spSensorLevelExceeded, 
         spSensorIndex, spSensorName, spSensorDescription }
      DESCRIPTION
         "RelayArray3.1 sensor trap"
      --#SEVERITY  MAJOR
      ::= 731

   spRelayArray3-2Status TRAP-TYPE
      ENTERPRISE sensorProbe
      VARIABLES
         { spSensorStatus, spSensorValue, spSensorLevelExceeded, 
         spSensorIndex, spSensorName, spSensorDescription }
      DESCRIPTION
         "RelayArray3.2 sensor trap"
      --#SEVERITY  MAJOR
      ::= 732

   spRelayArray3-3Status TRAP-TYPE
      ENTERPRISE sensorProbe
      VARIABLES
         { spSensorStatus, spSensorValue, spSensorLevelExceeded, 
         spSensorIndex, spSensorName, spSensorDescription }
      DESCRIPTION
         "RelayArray3.3 sensor trap"
      --#SEVERITY  MAJOR
      ::= 733

   spRelayArray3-4Status TRAP-TYPE
      ENTERPRISE sensorProbe
      VARIABLES
         { spSensorStatus, spSensorValue, spSensorLevelExceeded, 
         spSensorIndex, spSensorName, spSensorDescription }
      DESCRIPTION
         "RelayArray3.4 sensor trap"
      --#SEVERITY  MAJOR
      ::= 734

   spRelayArray3-5Status TRAP-TYPE
      ENTERPRISE sensorProbe
      VARIABLES
         { spSensorStatus, spSensorValue, spSensorLevelExceeded, 
         spSensorIndex, spSensorName, spSensorDescription }
      DESCRIPTION
         "RelayArray3.5 sensor trap"
      --#SEVERITY  MAJOR
      ::= 735

   spRelayArray3-6Status TRAP-TYPE
      ENTERPRISE sensorProbe
      VARIABLES
         { spSensorStatus, spSensorValue, spSensorLevelExceeded, 
         spSensorIndex, spSensorName, spSensorDescription }
      DESCRIPTION
         "RelayArray3.6 sensor trap"
      --#SEVERITY  MAJOR
      ::= 736

   spRelayArray3-7Status TRAP-TYPE
      ENTERPRISE sensorProbe
      VARIABLES
         { spSensorStatus, spSensorValue, spSensorLevelExceeded, 
         spSensorIndex, spSensorName, spSensorDescription }
      DESCRIPTION
         "RelayArray3.7 sensor trap"
      --#SEVERITY  MAJOR
      ::= 737

   spRelayArray3-8Status TRAP-TYPE
      ENTERPRISE sensorProbe
      VARIABLES
         { spSensorStatus, spSensorValue, spSensorLevelExceeded, 
         spSensorIndex, spSensorName, spSensorDescription }
      DESCRIPTION
         "RelayArray3.8 sensor trap"
      --#SEVERITY  MAJOR
      ::= 738

   spRelayArray4-1Status TRAP-TYPE
      ENTERPRISE sensorProbe
      VARIABLES
         { spSensorStatus, spSensorValue, spSensorLevelExceeded, 
         spSensorIndex, spSensorName, spSensorDescription }
      DESCRIPTION
         "RelayArray4.1 sensor trap"
      --#SEVERITY  MAJOR
      ::= 741

   spRelayArray4-2Status TRAP-TYPE
      ENTERPRISE sensorProbe
      VARIABLES
         { spSensorStatus, spSensorValue, spSensorLevelExceeded, 
         spSensorIndex, spSensorName, spSensorDescription }
      DESCRIPTION
         "RelayArray4.2 sensor trap"
      --#SEVERITY  MAJOR
      ::= 742

   spRelayArray4-3Status TRAP-TYPE
      ENTERPRISE sensorProbe
      VARIABLES
         { spSensorStatus, spSensorValue, spSensorLevelExceeded, 
         spSensorIndex, spSensorName, spSensorDescription }
      DESCRIPTION
         "RelayArray4.3 sensor trap"
      --#SEVERITY  MAJOR
      ::= 743

   spRelayArray4-4Status TRAP-TYPE
      ENTERPRISE sensorProbe
      VARIABLES
         { spSensorStatus, spSensorValue, spSensorLevelExceeded, 
         spSensorIndex, spSensorName, spSensorDescription }
      DESCRIPTION
         "RelayArray4.4 sensor trap"
      --#SEVERITY  MAJOR
      ::= 744

   spRelayArray4-5Status TRAP-TYPE
      ENTERPRISE sensorProbe
      VARIABLES
         { spSensorStatus, spSensorValue, spSensorLevelExceeded, 
         spSensorIndex, spSensorName, spSensorDescription }
      DESCRIPTION
         "RelayArray4.5 sensor trap"
      --#SEVERITY  MAJOR
      ::= 745

   spRelayArray4-6Status TRAP-TYPE
      ENTERPRISE sensorProbe
      VARIABLES
         { spSensorStatus, spSensorValue, spSensorLevelExceeded, 
         spSensorIndex, spSensorName, spSensorDescription }
      DESCRIPTION
         "RelayArray4.6 sensor trap"
      --#SEVERITY  MAJOR
      ::= 746

   spRelayArray4-7Status TRAP-TYPE
      ENTERPRISE sensorProbe
      VARIABLES
         { spSensorStatus, spSensorValue, spSensorLevelExceeded, 
         spSensorIndex, spSensorName, spSensorDescription }
      DESCRIPTION
         "RelayArray4.7 sensor trap"
      --#SEVERITY  MAJOR
      ::= 747

   spRelayArray4-8Status TRAP-TYPE
      ENTERPRISE sensorProbe
      VARIABLES
         { spSensorStatus, spSensorValue, spSensorLevelExceeded, 
         spSensorIndex, spSensorName, spSensorDescription }
      DESCRIPTION
         "RelayArray4.8 sensor trap"
      --#SEVERITY  MAJOR
      ::= 748

   spRelayArray5-1Status TRAP-TYPE
      ENTERPRISE sensorProbe
      VARIABLES
         { spSensorStatus, spSensorValue, spSensorLevelExceeded, 
         spSensorIndex, spSensorName, spSensorDescription }
      DESCRIPTION
         "RelayArray5.1 sensor trap"
      --#SEVERITY  MAJOR
      ::= 751

   spRelayArray5-2Status TRAP-TYPE
      ENTERPRISE sensorProbe
      VARIABLES
         { spSensorStatus, spSensorValue, spSensorLevelExceeded, 
         spSensorIndex, spSensorName, spSensorDescription }
      DESCRIPTION
         "RelayArray5.2 sensor trap"
      --#SEVERITY  MAJOR
      ::= 752

   spRelayArray5-3Status TRAP-TYPE
      ENTERPRISE sensorProbe
      VARIABLES
         { spSensorStatus, spSensorValue, spSensorLevelExceeded, 
         spSensorIndex, spSensorName, spSensorDescription }
      DESCRIPTION
         "RelayArray5.3 sensor trap"
      --#SEVERITY  MAJOR
      ::= 753

   spRelayArray5-4Status TRAP-TYPE
      ENTERPRISE sensorProbe
      VARIABLES
         { spSensorStatus, spSensorValue, spSensorLevelExceeded, 
         spSensorIndex, spSensorName, spSensorDescription }
      DESCRIPTION
         "RelayArray5.4 sensor trap"
      --#SEVERITY  MAJOR
      ::= 754

   spRelayArray5-5Status TRAP-TYPE
      ENTERPRISE sensorProbe
      VARIABLES
         { spSensorStatus, spSensorValue, spSensorLevelExceeded, 
         spSensorIndex, spSensorName, spSensorDescription }
      DESCRIPTION
         "RelayArray5.5 sensor trap"
      --#SEVERITY  MAJOR
      ::= 755

   spRelayArray5-6Status TRAP-TYPE
      ENTERPRISE sensorProbe
      VARIABLES
         { spSensorStatus, spSensorValue, spSensorLevelExceeded, 
         spSensorIndex, spSensorName, spSensorDescription }
      DESCRIPTION
         "RelayArray5.6 sensor trap"
      --#SEVERITY  MAJOR
      ::= 756

   spRelayArray5-7Status TRAP-TYPE
      ENTERPRISE sensorProbe
      VARIABLES
         { spSensorStatus, spSensorValue, spSensorLevelExceeded, 
         spSensorIndex, spSensorName, spSensorDescription }
      DESCRIPTION
         "RelayArray5.7 sensor trap"
      --#SEVERITY  MAJOR
      ::= 757

   spRelayArray5-8Status TRAP-TYPE
      ENTERPRISE sensorProbe
      VARIABLES
         { spSensorStatus, spSensorValue, spSensorLevelExceeded, 
         spSensorIndex, spSensorName, spSensorDescription }
      DESCRIPTION
         "RelayArray5.8 sensor trap"
      --#SEVERITY  MAJOR
      ::= 758

   spRelayArray6-1Status TRAP-TYPE
      ENTERPRISE sensorProbe
      VARIABLES
         { spSensorStatus, spSensorValue, spSensorLevelExceeded, 
         spSensorIndex, spSensorName, spSensorDescription }
      DESCRIPTION
         "RelayArray6.1 sensor trap"
      --#SEVERITY  MAJOR
      ::= 761

   spRelayArray6-2Status TRAP-TYPE
      ENTERPRISE sensorProbe
      VARIABLES
         { spSensorStatus, spSensorValue, spSensorLevelExceeded, 
         spSensorIndex, spSensorName, spSensorDescription }
      DESCRIPTION
         "RelayArray6.2 sensor trap"
      --#SEVERITY  MAJOR
      ::= 762

   spRelayArray6-3Status TRAP-TYPE
      ENTERPRISE sensorProbe
      VARIABLES
         { spSensorStatus, spSensorValue, spSensorLevelExceeded, 
         spSensorIndex, spSensorName, spSensorDescription }
      DESCRIPTION
         "RelayArray6.3 sensor trap"
      --#SEVERITY  MAJOR
      ::= 763

   spRelayArray6-4Status TRAP-TYPE
      ENTERPRISE sensorProbe
      VARIABLES
         { spSensorStatus, spSensorValue, spSensorLevelExceeded, 
         spSensorIndex, spSensorName, spSensorDescription }
      DESCRIPTION
         "RelayArray6.4 sensor trap"
      --#SEVERITY  MAJOR
      ::= 764

   spRelayArray6-5Status TRAP-TYPE
      ENTERPRISE sensorProbe
      VARIABLES
         { spSensorStatus, spSensorValue, spSensorLevelExceeded, 
         spSensorIndex, spSensorName, spSensorDescription }
      DESCRIPTION
         "RelayArray6.5 sensor trap"
      --#SEVERITY  MAJOR
      ::= 765

   spRelayArray6-6Status TRAP-TYPE
      ENTERPRISE sensorProbe
      VARIABLES
         { spSensorStatus, spSensorValue, spSensorLevelExceeded, 
         spSensorIndex, spSensorName, spSensorDescription }
      DESCRIPTION
         "RelayArray6.6 sensor trap"
      --#SEVERITY  MAJOR
      ::= 766

   spRelayArray6-7Status TRAP-TYPE
      ENTERPRISE sensorProbe
      VARIABLES
         { spSensorStatus, spSensorValue, spSensorLevelExceeded, 
         spSensorIndex, spSensorName, spSensorDescription }
      DESCRIPTION
         "RelayArray6.7 sensor trap"
      --#SEVERITY  MAJOR
      ::= 767

   spRelayArray6-8Status TRAP-TYPE
      ENTERPRISE sensorProbe
      VARIABLES
         { spSensorStatus, spSensorValue, spSensorLevelExceeded, 
         spSensorIndex, spSensorName, spSensorDescription }
      DESCRIPTION
         "RelayArray6.8 sensor trap"
      --#SEVERITY  MAJOR
      ::= 768

   spRelayArray7-1Status TRAP-TYPE
      ENTERPRISE sensorProbe
      VARIABLES
         { spSensorStatus, spSensorValue, spSensorLevelExceeded, 
         spSensorIndex, spSensorName, spSensorDescription }
      DESCRIPTION
         "RelayArray7.1 sensor trap"
      --#SEVERITY  MAJOR
      ::= 771

   spRelayArray7-2Status TRAP-TYPE
      ENTERPRISE sensorProbe
      VARIABLES
         { spSensorStatus, spSensorValue, spSensorLevelExceeded, 
         spSensorIndex, spSensorName, spSensorDescription }
      DESCRIPTION
         "RelayArray7.2 sensor trap"
      --#SEVERITY  MAJOR
      ::= 772

   spRelayArray7-3Status TRAP-TYPE
      ENTERPRISE sensorProbe
      VARIABLES
         { spSensorStatus, spSensorValue, spSensorLevelExceeded, 
         spSensorIndex, spSensorName, spSensorDescription }
      DESCRIPTION
         "RelayArray7.3 sensor trap"
      --#SEVERITY  MAJOR
      ::= 773

   spRelayArray7-4Status TRAP-TYPE
      ENTERPRISE sensorProbe
      VARIABLES
         { spSensorStatus, spSensorValue, spSensorLevelExceeded, 
         spSensorIndex, spSensorName, spSensorDescription }
      DESCRIPTION
         "RelayArray7.4 sensor trap"
      --#SEVERITY  MAJOR
      ::= 774

   spRelayArray7-5Status TRAP-TYPE
      ENTERPRISE sensorProbe
      VARIABLES
         { spSensorStatus, spSensorValue, spSensorLevelExceeded, 
         spSensorIndex, spSensorName, spSensorDescription }
      DESCRIPTION
         "RelayArray7.5 sensor trap"
      --#SEVERITY  MAJOR
      ::= 775

   spRelayArray7-6Status TRAP-TYPE
      ENTERPRISE sensorProbe
      VARIABLES
         { spSensorStatus, spSensorValue, spSensorLevelExceeded, 
         spSensorIndex, spSensorName, spSensorDescription }
      DESCRIPTION
         "RelayArray7.6 sensor trap"
      --#SEVERITY  MAJOR
      ::= 776

   spRelayArray7-7Status TRAP-TYPE
      ENTERPRISE sensorProbe
      VARIABLES
         { spSensorStatus, spSensorValue, spSensorLevelExceeded, 
         spSensorIndex, spSensorName, spSensorDescription }
      DESCRIPTION
         "RelayArray7.7 sensor trap"
      --#SEVERITY  MAJOR
      ::= 777

   spRelayArray7-8Status TRAP-TYPE
      ENTERPRISE sensorProbe
      VARIABLES
         { spSensorStatus, spSensorValue, spSensorLevelExceeded, 
         spSensorIndex, spSensorName, spSensorDescription }
      DESCRIPTION
         "RelayArray7.8 sensor trap"
      --#SEVERITY  MAJOR
      ::= 778

   spRelayArray8-1Status TRAP-TYPE
      ENTERPRISE sensorProbe
      VARIABLES
         { spSensorStatus, spSensorValue, spSensorLevelExceeded, 
         spSensorIndex, spSensorName, spSensorDescription }
      DESCRIPTION
         "RelayArray8.1 sensor trap"
      --#SEVERITY  MAJOR
      ::= 781

   spRelayArray8-2Status TRAP-TYPE
      ENTERPRISE sensorProbe
      VARIABLES
         { spSensorStatus, spSensorValue, spSensorLevelExceeded, 
         spSensorIndex, spSensorName, spSensorDescription }
      DESCRIPTION
         "RelayArray8.2 sensor trap"
      --#SEVERITY  MAJOR
      ::= 782

   spRelayArray8-3Status TRAP-TYPE
      ENTERPRISE sensorProbe
      VARIABLES
         { spSensorStatus, spSensorValue, spSensorLevelExceeded, 
         spSensorIndex, spSensorName, spSensorDescription }
      DESCRIPTION
         "RelayArray8.3 sensor trap"
      --#SEVERITY  MAJOR
      ::= 783

   spRelayArray8-4Status TRAP-TYPE
      ENTERPRISE sensorProbe
      VARIABLES
         { spSensorStatus, spSensorValue, spSensorLevelExceeded, 
         spSensorIndex, spSensorName, spSensorDescription }
      DESCRIPTION
         "RelayArray8.4 sensor trap"
      --#SEVERITY  MAJOR
      ::= 784

   spRelayArray8-5Status TRAP-TYPE
      ENTERPRISE sensorProbe
      VARIABLES
         { spSensorStatus, spSensorValue, spSensorLevelExceeded, 
         spSensorIndex, spSensorName, spSensorDescription }
      DESCRIPTION
         "RelayArray8.5 sensor trap"
      --#SEVERITY  MAJOR
      ::= 785

   spRelayArray8-6Status TRAP-TYPE
      ENTERPRISE sensorProbe
      VARIABLES
         { spSensorStatus, spSensorValue, spSensorLevelExceeded, 
         spSensorIndex, spSensorName, spSensorDescription }
      DESCRIPTION
         "RelayArray8.6 sensor trap"
      --#SEVERITY  MAJOR
      ::= 786

   spRelayArray8-7Status TRAP-TYPE
      ENTERPRISE sensorProbe
      VARIABLES
         { spSensorStatus, spSensorValue, spSensorLevelExceeded, 
         spSensorIndex, spSensorName, spSensorDescription }
      DESCRIPTION
         "RelayArray8.7 sensor trap"
      --#SEVERITY  MAJOR
      ::= 787

   spRelayArray8-8Status TRAP-TYPE
      ENTERPRISE sensorProbe
      VARIABLES
         { spSensorStatus, spSensorValue, spSensorLevelExceeded, 
         spSensorIndex, spSensorName, spSensorDescription }
      DESCRIPTION
         "RelayArray8.8 sensor trap"
      --#SEVERITY  MAJOR
      ::= 788

   spVirtual1Status TRAP-TYPE
      ENTERPRISE sensorProbe
      VARIABLES
         { spSensorStatus, spSensorValue, spSensorLevelExceeded, 
         spSensorIndex, spSensorName, spSensorDescription }
      DESCRIPTION
         "Virtual1 sensor trap"
      --#SEVERITY  MAJOR
      ::= 801

   spVirtual2Status TRAP-TYPE
      ENTERPRISE sensorProbe
      VARIABLES
         { spSensorStatus, spSensorValue, spSensorLevelExceeded, 
         spSensorIndex, spSensorName, spSensorDescription }
      DESCRIPTION
         "Virtual2 sensor trap"
      --#SEVERITY  MAJOR
      ::= 802

   spVirtual3Status TRAP-TYPE
      ENTERPRISE sensorProbe
      VARIABLES
         { spSensorStatus, spSensorValue, spSensorLevelExceeded, 
         spSensorIndex, spSensorName, spSensorDescription }
      DESCRIPTION
         "Virtual3 sensor trap"
      --#SEVERITY  MAJOR
      ::= 803

   spVirtual4Status TRAP-TYPE
      ENTERPRISE sensorProbe
      VARIABLES
         { spSensorStatus, spSensorValue, spSensorLevelExceeded, 
         spSensorIndex, spSensorName, spSensorDescription }
      DESCRIPTION
         "Virtual4 sensor trap"
      --#SEVERITY  MAJOR
      ::= 804

   spVirtual5Status TRAP-TYPE
      ENTERPRISE sensorProbe
      VARIABLES
         { spSensorStatus, spSensorValue, spSensorLevelExceeded, 
         spSensorIndex, spSensorName, spSensorDescription }
      DESCRIPTION
         "Virtual5 sensor trap"
      --#SEVERITY  MAJOR
      ::= 805

   spVirtual6Status TRAP-TYPE
      ENTERPRISE sensorProbe
      VARIABLES
         { spSensorStatus, spSensorValue, spSensorLevelExceeded, 
         spSensorIndex, spSensorName, spSensorDescription }
      DESCRIPTION
         "Virtual6 sensor trap"
      --#SEVERITY  MAJOR
      ::= 806

   spVirtual7Status TRAP-TYPE
      ENTERPRISE sensorProbe
      VARIABLES
         { spSensorStatus, spSensorValue, spSensorLevelExceeded, 
         spSensorIndex, spSensorName, spSensorDescription }
      DESCRIPTION
         "Virtual7 sensor trap"
      --#SEVERITY  MAJOR
      ::= 807

   spVirtual8Status TRAP-TYPE
      ENTERPRISE sensorProbe
      VARIABLES
         { spSensorStatus, spSensorValue, spSensorLevelExceeded, 
         spSensorIndex, spSensorName, spSensorDescription }
      DESCRIPTION
         "Virtual8 sensor trap"
      --#SEVERITY  MAJOR
      ::= 808

   spVirtual9Status TRAP-TYPE
      ENTERPRISE sensorProbe
      VARIABLES
         { spSensorStatus, spSensorValue, spSensorLevelExceeded, 
         spSensorIndex, spSensorName, spSensorDescription }
      DESCRIPTION
         "Virtual9 sensor trap"
      --#SEVERITY  MAJOR
      ::= 809

   spVirtual10Status TRAP-TYPE
      ENTERPRISE sensorProbe
      VARIABLES
         { spSensorStatus, spSensorValue, spSensorLevelExceeded, 
         spSensorIndex, spSensorName, spSensorDescription }
      DESCRIPTION
         "Virtual10 sensor trap"
      --#SEVERITY  MAJOR
      ::= 810

   spVirtual11Status TRAP-TYPE
      ENTERPRISE sensorProbe
      VARIABLES
         { spSensorStatus, spSensorValue, spSensorLevelExceeded, 
         spSensorIndex, spSensorName, spSensorDescription }
      DESCRIPTION
         "Virtual11 sensor trap"
      --#SEVERITY  MAJOR
      ::= 811

   spVirtual12Status TRAP-TYPE
      ENTERPRISE sensorProbe
      VARIABLES
         { spSensorStatus, spSensorValue, spSensorLevelExceeded, 
         spSensorIndex, spSensorName, spSensorDescription }
      DESCRIPTION
         "Virtual12 sensor trap"
      --#SEVERITY  MAJOR
      ::= 812

   spVirtual13Status TRAP-TYPE
      ENTERPRISE sensorProbe
      VARIABLES
         { spSensorStatus, spSensorValue, spSensorLevelExceeded, 
         spSensorIndex, spSensorName, spSensorDescription }
      DESCRIPTION
         "Virtual13 sensor trap"
      --#SEVERITY  MAJOR
      ::= 813

   spVirtual14Status TRAP-TYPE
      ENTERPRISE sensorProbe
      VARIABLES
         { spSensorStatus, spSensorValue, spSensorLevelExceeded, 
         spSensorIndex, spSensorName, spSensorDescription }
      DESCRIPTION
         "Virtual14 sensor trap"
      --#SEVERITY  MAJOR
      ::= 814

   spVirtual15Status TRAP-TYPE
      ENTERPRISE sensorProbe
      VARIABLES
         { spSensorStatus, spSensorValue, spSensorLevelExceeded, 
         spSensorIndex, spSensorName, spSensorDescription }
      DESCRIPTION
         "Virtual15 sensor trap"
      --#SEVERITY  MAJOR
      ::= 815

   spVirtual16Status TRAP-TYPE
      ENTERPRISE sensorProbe
      VARIABLES
         { spSensorStatus, spSensorValue, spSensorLevelExceeded, 
         spSensorIndex, spSensorName, spSensorDescription }
      DESCRIPTION
         "Virtual16 sensor trap"
      --#SEVERITY  MAJOR
      ::= 816

   spVirtual17Status TRAP-TYPE
      ENTERPRISE sensorProbe
      VARIABLES
         { spSensorStatus, spSensorValue, spSensorLevelExceeded, 
         spSensorIndex, spSensorName, spSensorDescription }
      DESCRIPTION
         "Virtual17 sensor trap"
      --#SEVERITY  MAJOR
      ::= 817

   spVirtual18Status TRAP-TYPE
      ENTERPRISE sensorProbe
      VARIABLES
         { spSensorStatus, spSensorValue, spSensorLevelExceeded, 
         spSensorIndex, spSensorName, spSensorDescription }
      DESCRIPTION
         "Virtual18 sensor trap"
      --#SEVERITY  MAJOR
      ::= 818

   spVirtual19Status TRAP-TYPE
      ENTERPRISE sensorProbe
      VARIABLES
         { spSensorStatus, spSensorValue, spSensorLevelExceeded, 
         spSensorIndex, spSensorName, spSensorDescription }
      DESCRIPTION
         "Virtual19 sensor trap"
      --#SEVERITY  MAJOR
      ::= 819

   spVirtual20Status TRAP-TYPE
      ENTERPRISE sensorProbe
      VARIABLES
         { spSensorStatus, spSensorValue, spSensorLevelExceeded, 
         spSensorIndex, spSensorName, spSensorDescription }
      DESCRIPTION
         "Virtual20 sensor trap"
      --#SEVERITY  MAJOR
      ::= 820

   spCustomStatus TRAP-TYPE
      ENTERPRISE sensorProbe
      VARIABLES
         { spSensorStatus, spSensorValue, spSensorLevelExceeded, 
         spSensorIndex, spSensorName, spSensorDescription,
    spSensorType, spSensorStatusName, spSensorSubIndex,
    spBoardIndex, spBoardDescription, spEventTimeStamp,
    spEventClassNumber, spEventClassName }
      DESCRIPTION
         "Custom sensor trap"
      --#SEVERITY  MAJOR
      ::= 1000

END
