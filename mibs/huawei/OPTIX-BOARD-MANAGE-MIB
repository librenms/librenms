-- OPTIX-BOARD-MANAGE-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--

OPTIX-BOARD-MANAGE-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus,DateAndTime
            FROM SNMPv2-TC
        ;

    optixBoardMng MODULE-IDENTITY
        LAST-UPDATED "201204170000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the general configuration information of board"
        REVISION "201204170000Z"
        DESCRIPTION
            "The initial revision of this MIB module."
        REVISION "201204170000Z"
        DESCRIPTION
            "The initial revision of this MIB module."
        ::={ optixProvisionEqpt 14 }

    -- 1.3.6.1.4.1.2011.2.25.4.30.14.1
    optixBoardMngGroup OBJECT IDENTIFIER ::= { optixBoardMng 1 }

    -- 1.3.6.1.4.1.2011.2.25.4.30.14.1.1
    optixLogBoardTable OBJECT-TYPE
        SYNTAX SEQUENCE OF OptixLogBoardEntry
        MAX-ACCESS not-accessible
        STATUS current
        DESCRIPTION
            "This table describes the general logical configurations of boards."
        ::= { optixBoardMngGroup 1 }

    -- 1.3.6.1.4.1.2011.2.25.4.30.14.1.1.1
    optixLogBoardEntry OBJECT-TYPE
        SYNTAX OptixLogBoardEntry
        MAX-ACCESS not-accessible
        STATUS current
        DESCRIPTION
            "Thisentry describes the general logical configurations of boards."
        INDEX{ optixLogBoardId }
        ::= { optixLogBoardTable 1 }

    OptixLogBoardEntry ::=
        SEQUENCE {
            optixLogBoardId
                Unsigned32,
            optixLogBoardLogType
                OCTET STRING,
            optixLogBoardTempHighTh
                OCTET STRING,
            optixLogBoardTempLowTh
                OCTET STRING,
            optixLogBoardCurTemp
                OCTET STRING,
            optixLogBoardBusdetect
                INTEGER,
            optixLogSubCardId
                Unsigned32,
            optixLogBoardLowTempThMin
                OCTET STRING,
            optixLogBoardLowTempThMax
                OCTET STRING,
            optixLogBoardLowTempThDefault
                OCTET STRING,
            optixLogBoardHighTempThMin
                OCTET STRING,
            optixLogBoardHighTempThMax
                OCTET STRING,
            optixLogBoardHighTempThDefault
                OCTET STRING,
            optixLogBoardReplaceBdType
                OCTET STRING,
            optixLogBoardChangeBdType
                OCTET STRING,
            optixLogBoardRowStatus
                RowStatus
        }

    -- 1.3.6.1.4.1.2011.2.25.4.30.14.1.1.1.1
    optixLogBoardId OBJECT-TYPE
        SYNTAX Unsigned32
        MAX-ACCESS not-accessible
        STATUS current
        DESCRIPTION
            "This object indicates the logical slot ID of the board."
        ::= { optixLogBoardEntry 1 }

    -- 1.3.6.1.4.1.2011.2.25.4.30.14.1.1.1.2
    optixLogBoardLogType OBJECT-TYPE
        SYNTAX OCTET STRING
        MAX-ACCESS read-create
        STATUS current
        DESCRIPTION
            "This object indicates the logical board type of the board."
        ::= { optixLogBoardEntry 2 }

    -- 1.3.6.1.4.1.2011.2.25.4.30.14.1.1.1.3
    optixLogBoardTempHighTh OBJECT-TYPE
        SYNTAX OCTET STRING
        MAX-ACCESS read-create
        STATUS current
        DESCRIPTION
            "This object indicates the upper threshold of the board temperature."
        ::= { optixLogBoardEntry 3 }

    -- 1.3.6.1.4.1.2011.2.25.4.30.14.1.1.1.4
    optixLogBoardTempLowTh OBJECT-TYPE
        SYNTAX OCTET STRING
        MAX-ACCESS read-create
        STATUS current
        DESCRIPTION
            "This object indicates the lower threshold of the board temperature."
        ::= { optixLogBoardEntry 4 }

    -- 1.3.6.1.4.1.2011.2.25.4.30.14.1.1.1.5
    optixLogBoardCurTemp OBJECT-TYPE
        SYNTAX OCTET STRING
        MAX-ACCESS read-only
        STATUS current
        DESCRIPTION
            "This object indicates the current temperatureof theboard."
        ::= { optixLogBoardEntry 5 }

    -- 1.3.6.1.4.1.2011.2.25.4.30.14.1.1.1.6
    optixLogBoardBusdetect OBJECT-TYPE
        SYNTAX INTEGER
        {
            disable(0),
            enable(1)
        }
        MAX-ACCESS read-create
        STATUS current
        DESCRIPTION
            "This object indicates the detection status of the board bus. 0: disable, 1: enable"
        ::= { optixLogBoardEntry 6 }

    -- 1.3.6.1.4.1.2011.2.25.4.30.14.1.1.1.7
    optixLogSubCardId OBJECT-TYPE
        SYNTAX Unsigned32
        MAX-ACCESS read-only
        STATUS current
        DESCRIPTION
            "This object indicates thesubboard ID."
        ::= { optixLogBoardEntry 7 }

    -- 1.3.6.1.4.1.2011.2.25.4.30.14.1.1.1.8
    optixLogBoardLowTempThMin OBJECT-TYPE
        SYNTAX OCTET STRING
        MAX-ACCESS read-only
        STATUS current
        DESCRIPTION
            "This object indicates the minimal value of the low board temperature range"
        ::= { optixLogBoardEntry 8 }

    -- 1.3.6.1.4.1.2011.2.25.4.30.14.1.1.1.9
    optixLogBoardLowTempThMax OBJECT-TYPE
        SYNTAX OCTET STRING
        MAX-ACCESS read-only
        STATUS current
        DESCRIPTION
            "This object indicates the maximal value of the low board temperature range"
        ::= { optixLogBoardEntry 9 }

    -- 1.3.6.1.4.1.2011.2.25.4.30.14.1.1.1.10
    optixLogBoardLowTempThDefault OBJECT-TYPE
        SYNTAX OCTET STRING
        MAX-ACCESS read-only
        STATUS current
        DESCRIPTION
            "This object indicates the default value of the low board temperature range"
        ::= { optixLogBoardEntry 10 }

    -- 1.3.6.1.4.1.2011.2.25.4.30.14.1.1.1.11
    optixLogBoardHighTempThMin OBJECT-TYPE
        SYNTAX OCTET STRING
        MAX-ACCESS read-only
        STATUS current
        DESCRIPTION
            "This object indicates the minimal value of the high board temperature range"
        ::= { optixLogBoardEntry 11 }

    -- 1.3.6.1.4.1.2011.2.25.4.30.14.1.1.1.12
    optixLogBoardHighTempThMax OBJECT-TYPE
        SYNTAX OCTET STRING
        MAX-ACCESS read-only
        STATUS current
        DESCRIPTION
            "This object indicates the maximal value of the high board temperature range"
        ::= { optixLogBoardEntry 12 }

    -- 1.3.6.1.4.1.2011.2.25.4.30.14.1.1.1.13
    optixLogBoardHighTempThDefault OBJECT-TYPE
        SYNTAX OCTET STRING
        MAX-ACCESS read-only
        STATUS current
        DESCRIPTION
            "This object indicates the Default value of the high board temperature range."
        ::= { optixLogBoardEntry 13 }

    -- 1.3.6.1.4.1.2011.2.25.4.30.14.1.1.1.14
    optixLogBoardReplaceBdType OBJECT-TYPE
        SYNTAX OCTET STRING
        MAX-ACCESS read-only
        STATUS current
        DESCRIPTION
            "This entry describes the type of the replaceable board for a board."
        ::= { optixLogBoardEntry 14 }

    -- 1.3.6.1.4.1.2011.2.25.4.30.14.1.1.1.15
    optixLogBoardChangeBdType OBJECT-TYPE
        SYNTAX OCTET STRING
        MAX-ACCESS read-create
        STATUS current
        DESCRIPTION
            "This entry describes the board type that is manually changed. The board types include sp3s, sl1d, cd1, and mp1."
        ::= { optixLogBoardEntry 15 }

    -- 1.3.6.1.4.1.2011.2.25.4.30.14.1.1.1.255
    optixLogBoardRowStatus OBJECT-TYPE
        SYNTAX RowStatus
        MAX-ACCESS read-create
        STATUS current
        DESCRIPTION
            "This object indicates the row status."
        DEFVAL{ RowStatus }
        ::= { optixLogBoardEntry 255 }

    -- 1.3.6.1.4.1.2011.2.25.4.30.14.1.2
    optixPhyBoardTable OBJECT-TYPE
        SYNTAX SEQUENCE OF OptixPhyBoardEntry
        MAX-ACCESS not-accessible
        STATUS current
        DESCRIPTION
            "This table describes the generalphysical configurations of boards."
        ::= { optixBoardMngGroup 2 }

    -- 1.3.6.1.4.1.2011.2.25.4.30.14.1.2.1
    optixPhyBoardEntry OBJECT-TYPE
        SYNTAX OptixPhyBoardEntry
        MAX-ACCESS not-accessible
        STATUS current
        DESCRIPTION
            "This entry describes the generalphysical configurations of boards."
        INDEX{ optixPhyBoardId }
        ::= { optixPhyBoardTable 1 }

    OptixPhyBoardEntry ::=
        SEQUENCE {
            optixPhyBoardId
                Unsigned32,
            optixPhyBoardType
                OCTET STRING,
            optixPhyBoardState
                INTEGER,
            optixPhyBDRVer
                Unsigned32,
            optixPhyBDDVer
                Unsigned32,
            optixPhyBDHVer
                Unsigned32,
            optixPhyBDVerInfo
                OCTET STRING,
            optixPhyBDOnlineFlag
                INTEGER,
            optixPhyBoardReset
                INTEGER,
            optixPhybdCfgFlag
                INTEGER,
            optixPhybdCfgTimeinfo
                DateAndTime,
            optixPhybdtypelist
                OCTET STRING
        }

    -- 1.3.6.1.4.1.2011.2.25.4.30.14.1.2.1.1
    optixPhyBoardId OBJECT-TYPE
        SYNTAX Unsigned32
        MAX-ACCESS not-accessible
        STATUS current
        DESCRIPTION
            "This object indicates thephysical slot ID of the board."
        ::= { optixPhyBoardEntry 1 }

    -- 1.3.6.1.4.1.2011.2.25.4.30.14.1.2.1.2
    optixPhyBoardType OBJECT-TYPE
        SYNTAX OCTET STRING
        MAX-ACCESS read-only
        STATUS current
        DESCRIPTION
            "This object indicates thephysical board type of the board."
        ::= { optixPhyBoardEntry 2 }

    -- 1.3.6.1.4.1.2011.2.25.4.30.14.1.2.1.3
    optixPhyBoardState OBJECT-TYPE
        SYNTAX INTEGER
        {
            work(1),
            notWork(0)
        }
        MAX-ACCESS read-only
        STATUS current
        DESCRIPTION
            "This object indicates the working status of the board. 1: work, 0: not work"
        ::= { optixPhyBoardEntry 3 }

    -- 1.3.6.1.4.1.2011.2.25.4.30.14.1.2.1.4
    optixPhyBDRVer OBJECT-TYPE
        SYNTAX Unsigned32
        MAX-ACCESS read-only
        STATUS current
        DESCRIPTION
            "This object indicates the version number of the board."
        ::= { optixPhyBoardEntry 4 }

    -- 1.3.6.1.4.1.2011.2.25.4.30.14.1.2.1.5
    optixPhyBDDVer OBJECT-TYPE
        SYNTAX Unsigned32
        MAX-ACCESS read-only
        STATUS current
        DESCRIPTION
            "This object indicates the sub-version number of the board."
        ::= { optixPhyBoardEntry 5 }

    -- 1.3.6.1.4.1.2011.2.25.4.30.14.1.2.1.6
    optixPhyBDHVer OBJECT-TYPE
        SYNTAX Unsigned32
        MAX-ACCESS read-only
        STATUS current
        DESCRIPTION
            "This object indicates thePCB version number of the board."
        ::= { optixPhyBoardEntry 6 }

    -- 1.3.6.1.4.1.2011.2.25.4.30.14.1.2.1.7
    optixPhyBDVerInfo OBJECT-TYPE
        SYNTAX OCTET STRING
 (SIZE(0..200))
        MAX-ACCESS read-only
        STATUS current
        DESCRIPTION
            "This object indicates the version information of theboard."
        ::= { optixPhyBoardEntry 7 }

    -- 1.3.6.1.4.1.2011.2.25.4.30.14.1.2.1.8
    optixPhyBDOnlineFlag OBJECT-TYPE
        SYNTAX INTEGER
        {
            offline(0),
            online(1),
            notMatch(2)
        }
        MAX-ACCESS read-only
        STATUS current
        DESCRIPTION
            "This object indicates the board online flag. 0: offline, 1: oneline, 2: not match"
        ::= { optixPhyBoardEntry 8 }

    -- 1.3.6.1.4.1.2011.2.25.4.30.14.1.2.1.9
    optixPhyBoardReset OBJECT-TYPE
        SYNTAX INTEGER
        {
            hard(0),
            soft(1)
        }
        MAX-ACCESS read-write
        STATUS current
        DESCRIPTION
            "This object indicates the board reset status. 0: hard, 1: soft, 255: invalid"
        ::= { optixPhyBoardEntry 9 }

    -- 1.3.6.1.4.1.2011.2.25.4.30.14.1.2.1.10
    optixPhybdCfgFlag OBJECT-TYPE
        SYNTAX INTEGER
        {
            yes(1),
            no(0)
        }
        MAX-ACCESS read-only
        STATUS current
        DESCRIPTION
            "This object indicates the save flag for board configuration data."
        ::= { optixPhyBoardEntry 10 }

    -- 1.3.6.1.4.1.2011.2.25.4.30.14.1.2.1.11
    optixPhybdCfgTimeinfo OBJECT-TYPE
        SYNTAX DateAndTime
        MAX-ACCESS read-only
        STATUS current
        DESCRIPTION
            "This object indicates the time, which is precise to seconds. The year starts from 1990. When para[3] is 1, this object indicates the save time of the current configurations. When para[3] is 0, this object indicates the latest time when the configurations are cleared. The initial time is all zeros."
        ::= { optixPhyBoardEntry 11 }

    -- 1.3.6.1.4.1.2011.2.25.4.30.14.1.2.1.12
    optixPhybdtypelist OBJECT-TYPE
        SYNTAX OCTET STRING
        MAX-ACCESS read-only
        STATUS current
        DESCRIPTION
            "This object indicates the list of board types supported by the board."
        ::= { optixPhyBoardEntry 12 }

    -- 1.3.6.1.4.1.2011.2.25.4.30.14.1.3
    optixBoardMngMember OBJECT IDENTIFIER ::= { optixBoardMngGroup 3 }

    -- 1.3.6.1.4.1.2011.2.25.4.30.14.1.3.1
    optixBoardMngBid OBJECT-TYPE
        SYNTAX Unsigned32
        MAX-ACCESS accessible-for-notify
        STATUS current
        DESCRIPTION
            "This object indicates the physical slot ID of the board."
        ::= { optixBoardMngMember 1 }

    -- 1.3.6.1.4.1.2011.2.25.4.30.14.1.3.2
    optixBoardMngBoardType OBJECT-TYPE
        SYNTAX OCTET STRING
        MAX-ACCESS accessible-for-notify
        STATUS current
        DESCRIPTION
            "This object indicates the physical board type of the board."
        ::= { optixBoardMngMember 2 }

    -- 1.3.6.1.4.1.2011.2.25.4.30.14.1.4
    optixBoardMngEvent OBJECT IDENTIFIER ::= { optixBoardMngGroup 4 }

    -- 1.3.6.1.4.1.2011.2.25.4.30.14.1.4.1
    optixBoardMngNewBdTrap NOTIFICATION-TYPE
        OBJECTS{ optixBoardMngBid,optixBoardMngBoardType }
        STATUS current
        DESCRIPTION
            "This object indicates the event for the physical board online."
        ::= { optixBoardMngEvent 1 }

END
