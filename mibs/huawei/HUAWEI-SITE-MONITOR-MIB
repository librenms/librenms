--
-- HUAWEI-SITE-MONITOR-MIB.mib
-- MIB generated by MG-SOFT Visual MIB Builder Version 4.0 Build 347
-- Wednesday, March 30, 2011 at 11:17:42
--

--  HUAWEI-NGPOWER-MIB.mib
-- MIB generated by MG-SOFT Visual MIB Builder Version 3.0 Build 253
-- Sunday, June 14, 2009 at 11:04:12
-- 

	HUAWEI-SITE-MONITOR-MIB DEFINITIONS ::= BEGIN
 
		IMPORTS
			huaweiUtility			
				FROM HUAWEI-MIB			
			OBJECT-GROUP, NOTIFICATION-GROUP			
				FROM SNMPv2-CONF			
			Integer32, Unsigned32, OBJECT-TYPE, MODULE-IDENTITY, NOTIFICATION-TYPE			
				FROM SNMPv2-SMI			
			TEXTUAL-CONVENTION			
				FROM SNMPv2-TC;
	
	
--        September 15, 2010 at 11:00 GMT
		hwSiteMonitorMIB MODULE-IDENTITY 
			LAST-UPDATED "201103040000Z"		-- March 04, 2011 at 00:00 GMT
			ORGANIZATION 
				"Huawei Technologies Co.,Ltd."
			CONTACT-INFO 
				"Floor 5, Block 4, R&D Building,
				Huawei Longgang Production Base,
				Shenzhen,   P.R.C.
				http://www.huawei.com
				Zip: 518129."
			DESCRIPTION 
				"Site Monitor MIB defines MIB objects which provides load and backup management, patch management NMS interfaces.
				The current version is V1.01"
			REVISION "201103040000Z"		-- March 04, 2011 at 00:00 GMT
			DESCRIPTION 
				"Add hwAcOffLongTimeAlarmTraps, hwAcOffLongTimeAlarmResumeTraps"
			REVISION "201010310000Z"		-- October 31, 2010 at 00:00 GMT
			DESCRIPTION 
				"Huawei site monitor mib V1.00"
			::= { huaweiUtility 164 }

		
	
--
-- Textual conventions
--
	
		DisplayString ::= TEXTUAL-CONVENTION
			STATUS current
			DESCRIPTION 
				"Description."
			SYNTAX OCTET STRING (SIZE (1..64))
			
		RowStatus ::= TEXTUAL-CONVENTION
			STATUS current
			DESCRIPTION 
				"Description."
			SYNTAX INTEGER
				{
				active(1),
				notInService(2),
				notReady(3),
				createAndGo(4),
				createAndWait(5),
				destroy(6)
				}
			
--        Textual conventions
-- 
		DateAndTime ::= TEXTUAL-CONVENTION
			STATUS current
			DESCRIPTION 
				"Description."
			SYNTAX OCTET STRING (SIZE (8..11))

		RunStatus ::= TEXTUAL-CONVENTION
			STATUS current
			DESCRIPTION 
				"This integer value represents running status of the system. 
				Depending on situation there may be limits on allowed values.
				  Operational values:
					(1) unknown - status has not yet been defined
					(2) normal - there are no activated alarms
					(3) alarm - alarm status
				"
			SYNTAX INTEGER
				{
				unknow(1),
				normal(2),
				alarm(3)
				}

		MeasuresRange ::= TEXTUAL-CONVENTION
			STATUS current
			DESCRIPTION 
				"Description."
			SYNTAX Integer32

		TruthValue ::= TEXTUAL-CONVENTION
			STATUS current
			DESCRIPTION 
				"Description."
			SYNTAX INTEGER
				{
				true(1),
				flase(2)
				}

	
--
-- Node definitions
--
	
		-- 1.3.6.1.4.1.2011.6.164.1
		hwSiteMonitorMIBObjects OBJECT IDENTIFIER ::= { hwSiteMonitorMIB 1 }

		
		-- 1.3.6.1.4.1.2011.6.164.1.1
		hwSiteInfo OBJECT IDENTIFIER ::= { hwSiteMonitorMIBObjects 1 }
		
		-- 1.3.6.1.4.1.2011.6.164.1.1.1
		hwSiteSummary OBJECT IDENTIFIER ::= { hwSiteInfo 1 }
		
		-- 1.3.6.1.4.1.2011.6.164.1.1.1.1
		hwSiteId OBJECT-TYPE
			SYNTAX Unsigned32
			MAX-ACCESS read-only
			STATUS current
			DESCRIPTION
				"Site ID, default value: 000,000.
				Naming rule of the site device ID (six digits): The first three digits indicate the device name and the last three digits indicate the serial number (SN) of the device. If the last three digits are 000, it indicates a virtual device. "
			::= { hwSiteSummary 1 }
		
		-- 1.3.6.1.4.1.2011.6.164.1.1.1.2
		hwSiteName OBJECT-TYPE
			SYNTAX OCTET STRING (SIZE (0..63))
			MAX-ACCESS read-write
			STATUS current
			DESCRIPTION
				"Site name, which users can configure, is used to specify a site. 
				Otherwise, the configured character can not be any other languages except English."
			::= { hwSiteSummary 2 }
		
		-- 1.3.6.1.4.1.2011.6.164.1.1.1.3
		hwSiteAdminAddr OBJECT-TYPE
			SYNTAX Unsigned32 (0..65535)
			MAX-ACCESS read-write
			STATUS current
			DESCRIPTION
				"Site administrant address, which users can assigned, is the unique ID of a site. It is used for device management by NMS, and value range is 0 to 65535. "
			::= { hwSiteSummary 3 }
		
		-- 1.3.6.1.4.1.2011.6.164.1.1.1.4
		hwSiteDescription OBJECT-TYPE
			SYNTAX OCTET STRING (SIZE (0..127))
			MAX-ACCESS read-write
			STATUS current
			DESCRIPTION
				"Site description. It is of the character string type. It is used to describe the site information such as the site location, which users can configure. 
				Otherwise, the configured character can not be any other languages except English."
			::= { hwSiteSummary 4 }
		
		-- 1.3.6.1.4.1.2011.6.164.1.1.1.5
		hwNetIdentifier OBJECT-TYPE
			SYNTAX OCTET STRING (SIZE (0..63))
			MAX-ACCESS read-write
			STATUS current
			DESCRIPTION
				"NE ID. It is of the character string type. It is the unique ID of the site (an independent network element (NE)) on the network.
				Otherwise, the configured character can not be any other languages except English. "
			::= { hwSiteSummary 5 }
		
		-- 1.3.6.1.4.1.2011.6.164.1.1.1.6
		hwSiteIp OBJECT-TYPE
			SYNTAX OCTET STRING (SIZE (8..16))
			MAX-ACCESS read-only
			STATUS current
			DESCRIPTION
				"Site IP address, default value is 192.168.0.10. Users need to configure the site IP address."
			::= { hwSiteSummary 6 }
		
		-- 1.3.6.1.4.1.2011.6.164.1.1.1.7
		hwSiteNetmask OBJECT-TYPE
			SYNTAX OCTET STRING (SIZE (8..16))
			MAX-ACCESS read-only
			STATUS current
			DESCRIPTION
				"Site netmask, default value is 255.255.0.0. Users need to configure the site netmask. "
			::= { hwSiteSummary 7 }
		
		-- 1.3.6.1.4.1.2011.6.164.1.1.1.8
		hwSiteGateway OBJECT-TYPE
			SYNTAX OCTET STRING (SIZE (8..16))
			MAX-ACCESS read-only
			STATUS current
			DESCRIPTION
				"Site gateway, default value: 192.168.0.1. Users need to configure the site gateway. "
			::= { hwSiteSummary 8 }
		
		-- 1.3.6.1.4.1.2011.6.164.1.1.1.10
		hwSiteRunningStatus OBJECT-TYPE
            SYNTAX INTEGER
                {
                normal(1),
                alarm(2)
                }
            MAX-ACCESS read-only
            STATUS current
            DESCRIPTION
                "State of the site alarm state. It is an enumeration type: 
                  If the enumeration value is 1, it indicates that the site is in the normal state;
                  If the enumeration value is 2, it indicates that the site is in the alarm state."
            ::= { hwSiteSummary 10 }
		
		-- 1.3.6.1.4.1.2011.6.164.1.1.1.9
		hwSiteDGWorkStatus OBJECT-TYPE
			SYNTAX INTEGER
				{
				idle(1),
				working(2),
				unknown(255)
				}
			MAX-ACCESS read-only
			STATUS current
			DESCRIPTION
				"State of the diesel working state. It is an enumeration type: 
				If the enumeration value is 1, it indicates that the diesel is in the idle state;
				If the enumeration value is 2, it indicates that the diesel is in the working state;     
				If the enumeration value is 255, it indicates diesel operation status unknown. "
			::= { hwSiteSummary 9 }
		-- 1.3.6.1.4.1.2011.6.164.1.1.2
		hwSiteAlarms OBJECT IDENTIFIER ::= { hwSiteInfo 2 }
		
		-- 1.3.6.1.4.1.2011.6.164.1.1.2.1
		hwDeviceTrapOrdinalNumber OBJECT-TYPE
			SYNTAX Unsigned32
			MAX-ACCESS read-write
			STATUS current
			DESCRIPTION
				"Site device event trap serial number (SN) is the unique ID of the device event trap. It is used to resend and synchronize event traps. Its value range is 0 to 4294967296.
				When the value exceeds the maximum value, the system automatically clears the value and numbers the alarm from 0 to 4294967296.  
				If the network management system (NMS) recieve the alarm number is not consequential, in such case that it notifies the SNMP agent the event trap number required. 
				So the monitor send the 50 event trap messages in maximum, after consequencial number required by NMS again.
				Specially, if NMS set the value to 0, the agent would clear the alarm queue automatically."
			::= { hwSiteAlarms 1 }
		
		-- 1.3.6.1.4.1.2011.6.164.1.1.2.2
		hwAlarmTrapOrdinalNumber OBJECT-TYPE
			SYNTAX Unsigned32
			MAX-ACCESS read-write
			STATUS current
			DESCRIPTION
				"Site alarm serial number (SN) is the unique ID of the alarm Trap. It is used to resend and synchronize alarms. Its value range is 0 to 4294967296.
				When the value exceeds the maximum value, the system automatically clears the value and numbers the alarm from 0 to 4294967296.  
				If the network management system (NMS) recieve the alarm number is not consequential, in such case that it notifies the SNMP agent the alarm number required. 
				So the monitor send the 50 alarm messages in maximum, after consequencial number required by NMS again.
				Specially, if NMS set the value to 0, the agent would clear the alarm queue automatically."
			::= { hwSiteAlarms 2 }
		
		-- 1.3.6.1.4.1.2011.6.164.1.1.2.3
		hwAlarmQuantity OBJECT-TYPE
			SYNTAX Unsigned32 (0..65535)
			MAX-ACCESS read-only
			STATUS current
			DESCRIPTION
				"Alarm number in site alarm list which are support. It is used for alarm list management by NMS, and value range is 0 to 65535. "
			::= { hwSiteAlarms 3 }
		
--  1.3.6.1.4.1.2011.6.1.5.10.7
		-- 1.3.6.1.4.1.2011.6.164.1.1.2.100
		hwSiteAlarmTable OBJECT-TYPE
			SYNTAX SEQUENCE OF HwSiteAlarmEntry
			MAX-ACCESS not-accessible
			STATUS current
			DESCRIPTION
				"Site alarms table. The table containing alarm information on the site management. Use this table to get site alarm name, alarm level, alarm signal description, and alarm port description, which can be used as VB of alarm traps. This table's index is hwAlarmIndex, clone site alarms table."
			::= { hwSiteAlarms 100 }
		
--  1.3.6.1.4.1.2011.6.1.5.10.7.1
		-- 1.3.6.1.4.1.2011.6.164.1.1.2.100.1
		hwSiteAlarmEntry OBJECT-TYPE
			SYNTAX HwSiteAlarmEntry
			MAX-ACCESS not-accessible
			STATUS current
			DESCRIPTION
				"Site alarms table entry."
			INDEX { hwAlarmIndex }
			::= { hwSiteAlarmTable 1 }

		
		HwSiteAlarmEntry ::=
			SEQUENCE { 
				hwAlarmIndex
					Integer32,
				hwAlarmText
					OCTET STRING,
				hwAlarmLevel
					INTEGER,
				hwAlarmSigDesc
					OCTET STRING,
				hwAlarmRowStatus
					RowStatus
			 }

		-- 1.3.6.1.4.1.2011.6.164.1.1.2.100.1.1
		hwAlarmIndex OBJECT-TYPE
			SYNTAX Integer32 (1..65535)
			MAX-ACCESS read-only
			STATUS current
			DESCRIPTION
				"Site alarm table index. It is the unique ID of the site alarm."
			::= { hwSiteAlarmEntry 1 }
		
		-- 1.3.6.1.4.1.2011.6.164.1.1.2.100.1.2
		hwAlarmText OBJECT-TYPE
			SYNTAX OCTET STRING (SIZE (0..63))
			MAX-ACCESS read-only
			STATUS current
			DESCRIPTION
				"Alarm name. It is of the character string type, and used to specify the content of a specific alarm.  "
			::= { hwSiteAlarmEntry 2 }
		
		-- 1.3.6.1.4.1.2011.6.164.1.1.2.100.1.3
		hwAlarmLevel OBJECT-TYPE
			SYNTAX INTEGER
				{
				critical(1),
				major(2),
				minor(3),
				warning(4),
				cleared(5),
				unknown(255)
				}
			MAX-ACCESS read-write
			STATUS current
			DESCRIPTION
				"Alarm level, which users can configure the alarm severity, is an enumeration type:
				If the enumeration value is 1, it indicates a critical alarm;
				If the enumeration value is 2, it indicates a major alarm;
				If the enumeration value is 3, it indicates a minor alarm;
				If the enumeration value is 4, it indicates a warning; 
				If the enumeration value is 5, it indicates the alarm is cleared."
			::= { hwSiteAlarmEntry 3 }
		
		-- 1.3.6.1.4.1.2011.6.164.1.1.2.100.1.4
		hwAlarmSigDesc OBJECT-TYPE
			SYNTAX OCTET STRING (SIZE (0..127))
			MAX-ACCESS read-write
			STATUS current
			DESCRIPTION
				"Alarm signal description. It is used to add and describe alarm content. Users can define the description of the alarm.
				Otherwise, the configured character can not be any other languages except English."
			::= { hwSiteAlarmEntry 4 }
		
		-- 1.3.6.1.4.1.2011.6.164.1.1.2.100.1.100
		hwAlarmRowStatus OBJECT-TYPE
			SYNTAX RowStatus
			MAX-ACCESS read-create
			STATUS current
			DESCRIPTION
				"RowStatus of site alarms table."
			::= { hwSiteAlarmEntry 100 }
		
		-- 1.3.6.1.4.1.2011.6.164.1.2
		hwSiteMonitors OBJECT IDENTIFIER ::= { hwSiteMonitorMIBObjects 2 }
		
		-- 1.3.6.1.4.1.2011.6.164.1.2.1
		hwMonitorsGroup OBJECT IDENTIFIER ::= { hwSiteMonitors 1 }
		
		-- 1.3.6.1.4.1.2011.6.164.1.2.1.1
		hwMonsGroupId OBJECT-TYPE
			SYNTAX Unsigned32
			MAX-ACCESS read-only
			STATUS current
			DESCRIPTION
				"Site monitor group ID, is the unique ID of the site monitors."
			::= { hwMonitorsGroup 1 }
		
		-- 1.3.6.1.4.1.2011.6.164.1.2.1.2
		hwMonsGroupName OBJECT-TYPE
			SYNTAX OCTET STRING (SIZE (0..63))
			MAX-ACCESS read-write
			STATUS current
			DESCRIPTION
				"Site monitor group name is of the character string type, used to specify the monitor group. Users can configure it.
				Otherwise, the configured character can not be any other languages except English. "
			::= { hwMonitorsGroup 2 }
		
		-- 1.3.6.1.4.1.2011.6.164.1.2.1.3
		hwMonsQuantity OBJECT-TYPE
			SYNTAX Unsigned32 (0..100)
			UNITS "pcs"
			MAX-ACCESS read-only
			STATUS current
			DESCRIPTION
				"Total site intelligent monitors. "
			::= { hwMonitorsGroup 3 }
		
		-- 1.3.6.1.4.1.2011.6.164.1.2.2
		hwMonitor OBJECT IDENTIFIER ::= { hwSiteMonitors 2 }
		
		-- 1.3.6.1.4.1.2011.6.164.1.2.2.1
		hwMonitorTable OBJECT-TYPE
			SYNTAX SEQUENCE OF HwMonitorEntry
			MAX-ACCESS not-accessible
			STATUS current
			DESCRIPTION
				"Site monitors table. Use this table to get site monitor equipment ID, site monitor equipment name, equipment software version, equipment PCB version, manufacturer, manufacture date, equipment serial No, equipment description, total runing time, and equipment controlled status, as well as to control monitor reset. This table's index is hwMonIndex, clone site monitors table."
			::= { hwMonitor 1 }
		
		-- 1.3.6.1.4.1.2011.6.164.1.2.2.1.1
		hwMonitorEntry OBJECT-TYPE
			SYNTAX HwMonitorEntry
			MAX-ACCESS not-accessible
			STATUS current
			DESCRIPTION
				"Site monitors table entry."
			INDEX { hwMonIndex }
			::= { hwMonitorTable 1 }

		
		HwMonitorEntry ::=
			SEQUENCE { 
				hwMonIndex
					Integer32,
				hwMonEquipId
					Unsigned32,
				hwMonEquipName
					OCTET STRING,
				hwMonEquipDescription
					OCTET STRING,
				hwMonEquipSoftwareVersion
					OCTET STRING,
				hwMonEquipPcbVersion
					OCTET STRING,
				hwMonEquipManufacturer
					OCTET STRING,
				hwMonEquipManuDate
					OCTET STRING,
				hwMonEquipSerialNo
					OCTET STRING,
				hwMonEquipOperTotalTime
					Unsigned32,
				hwSetMonEquipCtrlState
					INTEGER,
				hwCtrlMonEquipReset
					INTEGER,
				hwMonitorOperStatus
					INTEGER,
				hwMonRowStatus
					RowStatus
			 }

		-- 1.3.6.1.4.1.2011.6.164.1.2.2.1.1.1
		hwMonIndex OBJECT-TYPE
			SYNTAX Integer32 (1..100)
			MAX-ACCESS read-only
			STATUS current
			DESCRIPTION
				"Table index of the site monitors (hwSiteMonsTab) is restricted by the quantity of the site monitors (hwMonsQuantity). Value range: 1 to 100"
			::= { hwMonitorEntry 1 }
		
		-- 1.3.6.1.4.1.2011.6.164.1.2.2.1.1.2
		hwMonEquipId OBJECT-TYPE
			SYNTAX Unsigned32 (1001..1100)
			MAX-ACCESS read-only
			STATUS current
			DESCRIPTION
				"Site monitor ID. Value range: 001,001 to 001,100, in which the first three digits indicate the device type and the last three digits indicate the device SN.  "
			::= { hwMonitorEntry 2 }
		
		-- 1.3.6.1.4.1.2011.6.164.1.2.2.1.1.3
		hwMonEquipName OBJECT-TYPE
			SYNTAX OCTET STRING (SIZE (0..63))
			MAX-ACCESS read-write
			STATUS current
			DESCRIPTION
				"Monitor name. It is of the character string type, and users can set the name of the monitor. 
				Otherwise, the configured character can not be any other languages except English.   "
			::= { hwMonitorEntry 3 }
		
		-- 1.3.6.1.4.1.2011.6.164.1.2.2.1.1.4
		hwMonEquipDescription OBJECT-TYPE
			SYNTAX OCTET STRING (SIZE (0..127))
			MAX-ACCESS read-write
			STATUS current
			DESCRIPTION
				"Monitor description. It is of the character string type. Users can set the description of the monitor. 
				Otherwise, the configured character can not be any other languages except English."
			::= { hwMonitorEntry 4 }
		
		-- 1.3.6.1.4.1.2011.6.164.1.2.2.1.1.5
		hwMonEquipSoftwareVersion OBJECT-TYPE
			SYNTAX OCTET STRING (SIZE (0..63))
			MAX-ACCESS read-only
			STATUS current
			DESCRIPTION
				"Monitor software version. It is of the character string type."
			::= { hwMonitorEntry 5 }
		
		-- 1.3.6.1.4.1.2011.6.164.1.2.2.1.1.6
		hwMonEquipPcbVersion OBJECT-TYPE
			SYNTAX OCTET STRING (SIZE (0..63))
			MAX-ACCESS read-only
			STATUS current
			DESCRIPTION
				"Monitor printed circuit board (PCB) hardware version. It is of the character string type."
			::= { hwMonitorEntry 6 }
		
		-- 1.3.6.1.4.1.2011.6.164.1.2.2.1.1.7
		hwMonEquipManufacturer OBJECT-TYPE
			SYNTAX OCTET STRING (SIZE (0..63))
			MAX-ACCESS read-only
			STATUS current
			DESCRIPTION
				"Monitor manufacture. It is of the character string type, and is an inherent attribute of the device."
			::= { hwMonitorEntry 7 }
		
		-- 1.3.6.1.4.1.2011.6.164.1.2.2.1.1.8
		hwMonEquipManuDate OBJECT-TYPE
			SYNTAX OCTET STRING (SIZE (0..127))
			MAX-ACCESS read-only
			STATUS current
			DESCRIPTION
				"Monitor production date. It is of the character string type, and is an inherent attribute of the device.  "
			::= { hwMonitorEntry 8 }
		
		-- 1.3.6.1.4.1.2011.6.164.1.2.2.1.1.9
		hwMonEquipSerialNo OBJECT-TYPE
			SYNTAX OCTET STRING (SIZE (0..127))
			MAX-ACCESS read-only
			STATUS current
			DESCRIPTION
				"Production SN of the monitor. It is the electronic tag of the products."
			::= { hwMonitorEntry 9 }

		
		-- 1.3.6.1.4.1.2011.6.164.1.2.2.1.1.10
		hwMonEquipOperTotalTime OBJECT-TYPE
			SYNTAX Unsigned32 (0..65536)
			UNITS "hours"
			MAX-ACCESS read-only
			STATUS current
			DESCRIPTION
				"Total monitor runtime. The monitor counts the data in real time. The value is an integer (.0), and unit is hour (h). It is used for performance measurement and evaluation of the monitor."
			::= { hwMonitorEntry 10 }

		
		-- 1.3.6.1.4.1.2011.6.164.1.2.2.1.1.11
		hwSetMonEquipCtrlState OBJECT-TYPE
			SYNTAX INTEGER
				{
				manualMode(1),
				autoMode(2),
				unknown(255)
				}
			MAX-ACCESS read-write
			STATUS current
			DESCRIPTION
				"Monitor control status. It is an enumeration type:
				If the enumeration value is 1, it indicates the background control;
				If the enumeration value is 2, it indicates the automatic control.
				In manual state, monitor works under background commands; while monitors runs well automatically in auto state. 
				For details, see the corresponding user manual of the monitor."
			::= { hwMonitorEntry 11 }

		
		-- 1.3.6.1.4.1.2011.6.164.1.2.2.1.1.12
		hwCtrlMonEquipReset OBJECT-TYPE
			SYNTAX INTEGER
				{
				normal(1),
				reset(2),
				nullOper(255)
				}
			MAX-ACCESS read-write
			STATUS current
			DESCRIPTION
				"Warm-reset control of the monitor. It is an enumeration type:
				If the network management system (NMS) notifies the SNMP agent that this node is set to 1, it indicates that the reset of the monitor is not triggered;
				If the NMS notifies the SNMP agent that this node is set to 2, it indicates that the background starts the reset of the monitor. "
			::= { hwMonitorEntry 12 }

		
		-- 1.3.6.1.4.1.2011.6.164.1.2.2.1.1.99
		hwMonitorOperStatus OBJECT-TYPE
			SYNTAX INTEGER
				{
				normal(1),
				commRs485Fail(2),
				commNetFail(3),
				fault(4),
				alarmResume(254),
				other(255)
				}
			MAX-ACCESS read-only
			STATUS current
			DESCRIPTION
				"State of the site monitor module. It is an enumeration type: 
				If the enumeration value is 1, it indicates that the site monitor module is in the normal state;
				If the enumeration value is 2, it indicates that the monitor module RS485 port communication failed; 
				If the enumeration value is 3, it indicates that the monitor module net port communication failed;  
				If the enumeration value is 4, it indicates that a fault occurs on the monitor module; 
				If the enumeration value is 254, it indicates monitor module alarm resume;  
				If the enumeration value is 255, it indicates monitor module operation status unknown. "
			::= { hwMonitorEntry 99 }

		
		-- 1.3.6.1.4.1.2011.6.164.1.2.2.1.1.100
		hwMonRowStatus OBJECT-TYPE
			SYNTAX RowStatus
			MAX-ACCESS read-create
			STATUS current
			DESCRIPTION
				"RowStatus of site monitor."
			::= { hwMonitorEntry 100 }

		
		-- 1.3.6.1.4.1.2011.6.164.1.3
		hwSiteRectifiers OBJECT IDENTIFIER ::= { hwSiteMonitorMIBObjects 3 }

		
		-- 1.3.6.1.4.1.2011.6.164.1.3.1
		hwRectsGroup OBJECT IDENTIFIER ::= { hwSiteRectifiers 1 }

		
		-- 1.3.6.1.4.1.2011.6.164.1.3.1.1
		hwRectsGroupId OBJECT-TYPE
			SYNTAX Unsigned32
			MAX-ACCESS read-only
			STATUS current
			DESCRIPTION
				"Device group ID of the rectifier module. It is the unique ID of the rectifier module group, and its default value: 002,000. 
				The first digits indicate the device type and the last three digits indicate the device SN. If the last three digits are 000, it indicates a virtual device. "
			::= { hwRectsGroup 1 }

		
		-- 1.3.6.1.4.1.2011.6.164.1.3.1.2
		hwRectsGroupName OBJECT-TYPE
			SYNTAX OCTET STRING (SIZE (0..63))
			MAX-ACCESS read-write
			STATUS current
			DESCRIPTION
				"Name of the rectifier module group, character string type, is used to specify the rectifier module group. Users can configure it. 
				Otherwise, the configured character can not be any other languages except English."
			::= { hwRectsGroup 2 }

		
		-- 1.3.6.1.4.1.2011.6.164.1.3.1.3
		hwRectsTotalCurrent OBJECT-TYPE
			SYNTAX Unsigned32 (0..500000)
			UNITS "A"
			MAX-ACCESS read-only
			STATUS current
			DESCRIPTION
				"Total current of the rectifier module group on the site. It indicates the real-time statistics of the rectifier module group on the site. unit: A, and the value is accurate to one decimal place (.1). "
			::= { hwRectsGroup 3 }

		
		-- 1.3.6.1.4.1.2011.6.164.1.3.1.4
		hwRectsTotalQuantity OBJECT-TYPE
			SYNTAX Unsigned32 (0..256)
			UNITS "pcs"
			MAX-ACCESS read-only
			STATUS current
			DESCRIPTION
				"Total quantity of the rectifier modules. Value range: 0 to 256. "
			::= { hwRectsGroup 4 }

		
		-- 1.3.6.1.4.1.2011.6.164.1.3.1.5
		hwRectsRatedVoltage OBJECT-TYPE
			SYNTAX Unsigned32 (420..580)
			UNITS "V"
			MAX-ACCESS read-only
			STATUS current
			DESCRIPTION
				"Rated voltage of the rectifier module group. It is an inherent attribute. Value range: 42 to 58, Unit: V, and the value is accurate to one decimal place (.1). "
			::= { hwRectsGroup 5 }

		
		-- 1.3.6.1.4.1.2011.6.164.1.3.1.6
		hwModifyRectsOutputVoltage OBJECT-TYPE
			SYNTAX Unsigned32 (420..580)
			UNITS "V"
			MAX-ACCESS read-write
			STATUS current
			DESCRIPTION
				"Voltage adjustment of the rectifier module, which users can configure it. Value range: 42 to 58, Unit: V, and the value is accurate to one decimal space (.1). Based on the actual requirements, users can modify the output voltage of the rectifier module by modifying the value of the node.
				NOTES: Be cautious about changing the value of the node.  "
			::= { hwRectsGroup 6 }

		
		-- 1.3.6.1.4.1.2011.6.164.1.3.1.7
		hwSetRectsRedundEnable OBJECT-TYPE
			SYNTAX INTEGER
				{
				disable(1),
				enable(2),
				funcNotSupport(3)
				}
			MAX-ACCESS read-write
			STATUS current
			DESCRIPTION
				"Sleep function of the rectifier module group on the site. It is an enumeration value:
				If the NMS notifies the SNMP agent that this node is set to 1, it means to disable the sleep function of the rectifier module group;
				If the NMS notifies the SNMP agent that this node is set to 2, it means to enable the sleep function of the rectifier module group.
				If NMS get the node value is 3, it indicates that this function is not support, and in such case the value set to the agent is invalid.
				Default value: to disable the sleep function of the rectifier module group. For details, see the corresponding user manual of the monitor."
			::= { hwRectsGroup 7 }

		
		-- 1.3.6.1.4.1.2011.6.164.1.3.1.8
		hwCtrlRectsAllOnOff OBJECT-TYPE
			SYNTAX INTEGER
				{
				on(1),
				off(2),
				nullOper(255)
				}
			MAX-ACCESS read-write
			STATUS current
			DESCRIPTION
				"Power-on or power-off of the rectifier module group (all the rectifier modules) on the site. It is an enumeration value:
				If the NMS notifies the SNMP agent that this node is set to 1, it indicates power-on of all rectifier modules;
				If the NMS notifies the SNMP agent that this node is set to 2, it indicates power-off of all the rectifier modules. "
			::= { hwRectsGroup 8 }
		
		-- 1.3.6.1.4.1.2011.6.164.1.3.1.9
		hwRectsTotalDCPower OBJECT-TYPE
            SYNTAX Unsigned32 (0..100000000)
            MAX-ACCESS read-only
            STATUS current
            DESCRIPTION
                "Total power of the direct current output.
                Value range: 0 to 100000000,
                units: W, 
                and the value is an integer.
                If the value is 2147483647(0x7FFFFFFF), it indicates that the value is invalid."
            ::= { hwRectsGroup 9 }
		
		-- 1.3.6.1.4.1.2011.6.164.1.3.1.11
		hwRectsTotalACInputPower OBJECT-TYPE
            SYNTAX Unsigned32 (0..100000000)
            MAX-ACCESS read-only
            STATUS current
            DESCRIPTION
                "Total power of the direct current output. 
                Value range: 0 to 100000000, 
                units: W, 
                and the value is an integer. 
                If the value is 2147483647(0x7FFFFFFF), it indicates that the value is invalid."
            ::= { hwRectsGroup 11 }
		
		-- 1.3.6.1.4.1.2011.6.164.1.3.2
		hwRectifier OBJECT IDENTIFIER ::= { hwSiteRectifiers 2 }
		
		
		
--  1.3.6.1.4.1.2011.6.1.5.6
		-- 1.3.6.1.4.1.2011.6.164.1.3.2.1
		hwRectConfigTable OBJECT-TYPE
			SYNTAX SEQUENCE OF HwRectConfigEntry
			MAX-ACCESS not-accessible
			STATUS current
			DESCRIPTION
				"Rectifier config information table. Use this table to get rectifiers equipment ID, software version, manufacturer, rated current, efficency, AC input type, and to control equipment on or off. This table's index is hwRectConfigIndex, clone Rectifier config information table."
			::= { hwRectifier 1 }

		
--  1.3.6.1.4.1.2011.6.1.5.6.1
		-- 1.3.6.1.4.1.2011.6.164.1.3.2.1.1
		hwRectConfigEntry OBJECT-TYPE
			SYNTAX HwRectConfigEntry
			MAX-ACCESS not-accessible
			STATUS current
			DESCRIPTION
				"Rectifier config table entry."
			INDEX { hwRectConfigIndex }
			::= { hwRectConfigTable 1 }

		
		HwRectConfigEntry ::=
			SEQUENCE { 
				hwRectConfigIndex
					Integer32,
				hwRectEquipId
					Unsigned32,
				hwRectEquipName
					OCTET STRING,
				hwRectType
					INTEGER,
				hwRectSoftwareVersion
					OCTET STRING,
				hwRectManufacturer
					OCTET STRING,
				hwRectManuDate
					OCTET STRING,
				hwRectSerialNo
					OCTET STRING,
				hwRectRatedCurrent
					Unsigned32,
				hwRectEfficency
					Unsigned32,
				hwRectInputAcType
					INTEGER,
				hwCtrlRectOnOff
					INTEGER,
				hwRectConfigRowStatus
					RowStatus
			 }

--  1.3.6.1.4.1.2011.6.1.5.6.1.2
		-- 1.3.6.1.4.1.2011.6.164.1.3.2.1.1.1
		hwRectConfigIndex OBJECT-TYPE
			SYNTAX Integer32 (1..256)
			MAX-ACCESS read-only
			STATUS current
			DESCRIPTION
				"Index of the device configuration list for the rectifier modules, which value range: 1 to 256. Lines of the device list are restricted by the total quantity of the rectifier modules (hwRectTotleQuantity).
				"
			::= { hwRectConfigEntry 1 }

		
		-- 1.3.6.1.4.1.2011.6.164.1.3.2.1.1.2
		hwRectEquipId OBJECT-TYPE
			SYNTAX Unsigned32 (2001..2255)
			MAX-ACCESS read-only
			STATUS current
			DESCRIPTION
				"Rectifier module ID. Value range: 002'001 to 002'255. The first digits indicate the device type and last three digits indicate the device SN. "
			::= { hwRectConfigEntry 2 }

		
		-- 1.3.6.1.4.1.2011.6.164.1.3.2.1.1.3
		hwRectEquipName OBJECT-TYPE
			SYNTAX OCTET STRING (SIZE (0..63))
			MAX-ACCESS read-write
			STATUS current
			DESCRIPTION
				"Device name of the rectifier module, character string type, is used to specify the rectifier module. Users can configure it. 
				Otherwise, the configured character can not be any other languages except English."
			::= { hwRectConfigEntry 3 }

		
--  1.3.6.1.4.1.2011.6.1.5.6.1.3
		-- 1.3.6.1.4.1.2011.6.164.1.3.2.1.1.4
		hwRectType OBJECT-TYPE
			SYNTAX INTEGER
				{
				eps5(1),
				eps15(2),
				eps30(3),
				eps50(4),
				eps100(5),
				unknown(255)
				}
			MAX-ACCESS read-only
			STATUS current
			DESCRIPTION
				"Specific type of the rectifier module. It is an enumeration type:
				If the enumeration value is 1, it indicates a 5A rectifier module; 
				If the enumeration value is 2, it indicates a 15A rectifier module; 
				If the enumeration value is 3, it indicates a 30A rectifier module; 
				If the enumeration value is 4, it indicates a 50A rectifier module; 
				If the enumeration value is 5, it indicates a 100A rectifier module.
				 
				"
			::= { hwRectConfigEntry 4 }

		
		-- 1.3.6.1.4.1.2011.6.164.1.3.2.1.1.5
		hwRectSoftwareVersion OBJECT-TYPE
			SYNTAX OCTET STRING (SIZE (0..63))
			MAX-ACCESS read-only
			STATUS current
			DESCRIPTION
				"Software version of the rectifier module. It indicates the software version ID of the module. "
			::= { hwRectConfigEntry 5 }

		
		-- 1.3.6.1.4.1.2011.6.164.1.3.2.1.1.6
		hwRectManufacturer OBJECT-TYPE
			SYNTAX OCTET STRING (SIZE (0..63))
			MAX-ACCESS read-only
			STATUS current
			DESCRIPTION
				"Manufacture of the rectifier module."
			::= { hwRectConfigEntry 6 }

		
		-- 1.3.6.1.4.1.2011.6.164.1.3.2.1.1.7
		hwRectManuDate OBJECT-TYPE
			SYNTAX OCTET STRING (SIZE (0..127))
			MAX-ACCESS read-only
			STATUS current
			DESCRIPTION
				"Manufacture date of rectifiers is of string type."
			::= { hwRectConfigEntry 7 }

		
		-- 1.3.6.1.4.1.2011.6.164.1.3.2.1.1.8
		hwRectSerialNo OBJECT-TYPE
			SYNTAX OCTET STRING (SIZE (0..127))
			MAX-ACCESS read-only
			STATUS current
			DESCRIPTION
				"Rectifier module SN. It indicates the electronic tag of the product."
			::= { hwRectConfigEntry 8 }

		
		-- 1.3.6.1.4.1.2011.6.164.1.3.2.1.1.9
		hwRectRatedCurrent OBJECT-TYPE
			SYNTAX Unsigned32 (0..1000)
			UNITS "A"
			MAX-ACCESS read-only
			STATUS current
			DESCRIPTION
				"Rated voltage of the rectifier module, is an inherent attribute. Value range: 0 to 100, Unit: A, and the value is accurate to one decimal place (.1). "
			::= { hwRectConfigEntry 9 }

		
		-- 1.3.6.1.4.1.2011.6.164.1.3.2.1.1.10
		hwRectEfficency OBJECT-TYPE
			SYNTAX Unsigned32 (800..1000)
			UNITS "%"
			MAX-ACCESS read-only
			STATUS current
			DESCRIPTION
				"Efficiency of the rectifier module, is an inherent attribute. Value range: 80 to 100, Unit: %, and the value is accurate to one decimal place (.1)."
			::= { hwRectConfigEntry 10 }

		
		-- 1.3.6.1.4.1.2011.6.164.1.3.2.1.1.11
		hwRectInputAcType OBJECT-TYPE
			SYNTAX INTEGER
				{
				single(1),
				triple(2),
				unknown(255)
				}
			MAX-ACCESS read-only
			STATUS current
			DESCRIPTION
				"Input AC type of the rectifier module. It is an enumeration value:
				If the value of the node is 1, it indicates single-phase AC input; 
				If the value of the node is 2, it indicates three-phase AC input. "
			::= { hwRectConfigEntry 11 }

		
--  1.3.6.1.4.1.2011.6.1.5.6.1.8
		-- 1.3.6.1.4.1.2011.6.164.1.3.2.1.1.12
		hwCtrlRectOnOff OBJECT-TYPE
			SYNTAX INTEGER
				{
				on(1),
				off(2),
				nullOper(255)
				}
			MAX-ACCESS read-write
			STATUS current
			DESCRIPTION
				"Power-on or power-off of the rectifier module, is an enumeration value. Users can modify the enumeration value of this node, thus controlling of the power-on or power-off of the rectifier module:
				If the NMS notifies the SNMP agent that this node is set to 1, it indicates power-on of the rectifier module;
				If the NMS notifies the SNMP agent that this node is set to 2, it indicates power-off of the rectifier module. "
			::= { hwRectConfigEntry 12 }

		
--  1.3.6.1.4.1.2011.6.1.5.6.1.11
		-- 1.3.6.1.4.1.2011.6.164.1.3.2.1.1.100
		hwRectConfigRowStatus OBJECT-TYPE
			SYNTAX RowStatus
			MAX-ACCESS read-create
			STATUS current
			DESCRIPTION
				"RowStatus of rectifier config table."
			::= { hwRectConfigEntry 100 }

		
		-- 1.3.6.1.4.1.2011.6.164.1.3.2.2
		hwRectOperTable OBJECT-TYPE
			SYNTAX SEQUENCE OF HwRectOperEntry
			MAX-ACCESS not-accessible
			STATUS current
			DESCRIPTION
				"Rectifier runing information table. Use this table to get rectifiers output current, output voltage, totle runing time, and current run status. This table's index is hwRectRunIndex, clone rectifier runing information table."
			::= { hwRectifier 2 }

		
		-- 1.3.6.1.4.1.2011.6.164.1.3.2.2.1
		hwRectOperEntry OBJECT-TYPE
			SYNTAX HwRectOperEntry
			MAX-ACCESS not-accessible
			STATUS current
			DESCRIPTION
				"Rectifier runing table entry."
			INDEX { hwRectOperIndex }
			::= { hwRectOperTable 1 }

		
		HwRectOperEntry ::=
			SEQUENCE { 
				hwRectOperIndex
                    Integer32,
                hwRectOutputCurrent
                    Unsigned32,
                hwRectOutputVoltage
                    Unsigned32,
                hwRectDCOutputPower
                    Unsigned32,
                hwRectACVoltage
                    Unsigned32,
                hwRectRatedEfficiency
                    Unsigned32,
                hwRectifierTemperature
                    Integer32,
				hwRectTotalOperTime
				    Integer32,
                hwRectOperStatus
                    INTEGER,
                hwRectOperRowStatus
                    RowStatus
			 }

		-- 1.3.6.1.4.1.2011.6.164.1.3.2.2.1.1
		hwRectOperIndex OBJECT-TYPE
			SYNTAX Integer32 (1..256)
			MAX-ACCESS read-only
			STATUS current
			DESCRIPTION
				"Table index of the running rectifier modules, which value range: 1 to 256. Lines of the device list are restricted by the total quantity of the rectifier modules (hwRectTotleQuantity)."
			::= { hwRectOperEntry 1 }

		
--  1.3.6.1.4.1.2011.6.1.5.6.1.5
		-- 1.3.6.1.4.1.2011.6.164.1.3.2.2.1.2
		hwRectOutputCurrent OBJECT-TYPE
			SYNTAX Unsigned32 (0..2000)
			MAX-ACCESS read-only
			STATUS current
			DESCRIPTION
				"Output current of the rectifier module. It is a real-time analog parameter. Value range: 0 to 200, Unit: A, and the value is accurate to one decimal place (.1). "
			::= { hwRectOperEntry 2 }

		
--  1.3.6.1.4.1.2011.6.1.5.6.1.4
		-- 1.3.6.1.4.1.2011.6.164.1.3.2.2.1.3
		hwRectOutputVoltage OBJECT-TYPE
			SYNTAX Unsigned32 (0..600)
			UNITS "V"
			MAX-ACCESS read-only
			STATUS current
			DESCRIPTION
				"Output voltage of the rectifier module. It is a real-time analog parameter. Value range: 0 to 60, Unit: V, the value is accurate to one decimal place (.1). 
				"
			::= { hwRectOperEntry 3 }

		-- 1.3.6.1.4.1.2011.6.164.1.3.2.2.1.5
		hwRectDCOutputPower OBJECT-TYPE
            SYNTAX Unsigned32 (0..30000)
            MAX-ACCESS read-only
            STATUS current
            DESCRIPTION
                "DC output power. 
                Value range: 0 to 30000, 
                units: W, 
                and the value is an integer.(1). 
                If the value is 2147483647(0x7FFFFFFF), it indicates that the value is invalid."
            ::= { hwRectOperEntry 5 }
		
		-- 1.3.6.1.4.1.2011.6.164.1.3.2.2.1.6
		hwRectACVoltage OBJECT-TYPE
            SYNTAX Unsigned32 (0..6000)
            MAX-ACCESS read-only
            STATUS current
            DESCRIPTION
                "AC input voltage. 
                Value range: 0 to 600, 
                units: V, 
                and the value is accurate to one decimal space (.1).
                If the value is 2147483647(0x7FFFFFFF), it indicates that the value is invalid."
            ::= { hwRectOperEntry 6 }
		
		-- 1.3.6.1.4.1.2011.6.164.1.3.2.2.1.7
		hwRectRatedEfficiency OBJECT-TYPE
            SYNTAX Unsigned32 (0..100)
            MAX-ACCESS read-only
            STATUS current
            DESCRIPTION
                "Rated Efficiency. 
                Value range: 0 to 100, 
                units: %, 
                and the value is an integer.(1). 
                If the value is 2147483647(0x7FFFFFFF), it indicates that the value is invalid."
            ::= { hwRectOperEntry 7 }
		
		-- 1.3.6.1.4.1.2011.6.164.1.3.2.2.1.8
		hwRectifierTemperature OBJECT-TYPE
            SYNTAX Integer32 (-3000..3000)
            MAX-ACCESS read-only
            STATUS current
            DESCRIPTION
                "Rectifier Temperature. 
                Value range: -300 to 300, 
                units: degC, 
                and the value is accurate to one decimal space (.1). 
                If the value is 2147483647(0x7FFFFFFF), it indicates that the value is invalid."
            ::= { hwRectOperEntry 8 }
			
		-- 1.3.6.1.4.1.2011.6.164.1.3.2.2.1.4
		hwRectTotalOperTime OBJECT-TYPE
			SYNTAX Unsigned32
			UNITS "minutes"
			MAX-ACCESS read-only
			STATUS current
			DESCRIPTION
				"Total runtime of the rectifier module. Value unit: minute (m), and the value is an integer (.0).  "
			::= { hwRectOperEntry 4 }

		
		-- 1.3.6.1.4.1.2011.6.164.1.3.2.2.1.99
		hwRectOperStatus OBJECT-TYPE
			SYNTAX INTEGER
				{
				normal(1),
				fault(2),
				protect(3),
				commFail(4),
				switchOff(5),
				invalid(6),
				noConfig(7),
				alarmResume(254),
				other(255)
				}
			MAX-ACCESS read-only
			STATUS current
			DESCRIPTION
				"State of the rectifier module. It is an enumeration type: 
				If the enumeration value is 1, it indicates that the rectifier module is in the normal state;
				If the enumeration value is 2, it indicates that a fault occurs on the rectifier module; 
				If the enumeration value is 3, it indicates the automatic protection of the rectifier module;
				If the enumeration value is 4, it indicates that communication of the rectifier module fails;
				If the enumeration value is 5, it indicates that the rectifier module is shut down; 
				If the enumeration value is 6, it indicates that the rectifier module is invalid; 
				If the enumeration value is 7, it indicates that this rectifier is not configured; 
				If the enumeration value is 254, it indicates rectifier alarm resume; 
				If the enumeration value is 255, it indicates rectifier operation status unknown.
				 
				"
			::= { hwRectOperEntry 99 }

		
		-- 1.3.6.1.4.1.2011.6.164.1.3.2.2.1.100
		hwRectOperRowStatus OBJECT-TYPE
			SYNTAX RowStatus
			MAX-ACCESS read-create
			STATUS current
			DESCRIPTION
				"RowStatus of rectifier runing table."
			::= { hwRectOperEntry 100 }

		
		-- 1.3.6.1.4.1.2011.6.164.1.4
		hwSiteBatterys OBJECT IDENTIFIER ::= { hwSiteMonitorMIBObjects 4 }

		
		-- 1.3.6.1.4.1.2011.6.164.1.4.1
		hwBattsConfig OBJECT IDENTIFIER ::= { hwSiteBatterys 1 }

		
		-- 1.3.6.1.4.1.2011.6.164.1.4.1.1
		hwBattsGroupId OBJECT-TYPE
			SYNTAX Unsigned32
			MAX-ACCESS read-only
			STATUS current
			DESCRIPTION
				"Battery group ID. It is the unique ID of the battery group device. The first digits indicate the device type and the last three digits indicate the device SN. If the last three digits are 000, it indicates a virtual device. "
			::= { hwBattsConfig 1 }

		
		-- 1.3.6.1.4.1.2011.6.164.1.4.1.2
		hwBattsGroupName OBJECT-TYPE
			SYNTAX OCTET STRING (SIZE (0..63))
			MAX-ACCESS read-write
			STATUS current
			DESCRIPTION
				"Device name of the battery group. It is of the character string type, which can be configured by users.
				Otherwise, the configured character can not be any other languages except English."
			::= { hwBattsConfig 2 }

		
		-- 1.3.6.1.4.1.2011.6.164.1.4.1.3
		hwBattsTotalQuantity OBJECT-TYPE
			SYNTAX Unsigned32 (0..100)
			UNITS "strings"
			MAX-ACCESS read-write
			STATUS current
			DESCRIPTION
				"Total quantity of battery strings, which value range: 0 to 100."
			::= { hwBattsConfig 3 }

		
		-- 1.3.6.1.4.1.2011.6.164.1.4.1.4
		hwSetBattsHighTempAction OBJECT-TYPE
			SYNTAX INTEGER
				{
				blvd(1),
				lowerDcOutput(2),
				unknown(255)
				}
			MAX-ACCESS read-write
			STATUS current
			DESCRIPTION
				"Battery high-temperature protection mode. It is an enumeration value, and can be configured. 
				If the enumeration value is 1, it indicates the power-off protection mode;
				If the enumeration value is 2, it indicates the protection mode of lowering the output voltage of the rectifier module.
				unknown(255) it is do nothing "
			::= { hwBattsConfig 4 }

		
		-- 1.3.6.1.4.1.2011.6.164.1.4.1.5
		hwSetBattsHighTempVoltLimit OBJECT-TYPE
			SYNTAX Unsigned32 (0..600)
			UNITS "V"
			MAX-ACCESS read-write
			STATUS current
			DESCRIPTION
				"Battery protection voltage under high temperature. It works with the low-voltage power-off protection in battery high-temperature protection mode, which can be configured by users. If the low-voltage power-off protection mode (that is, the enumeration value is 1) is selected, the node is a low-voltage power-off node. Value range: 0 to 60, unit: V, and the value is accurate to one decimal place (.1). "
			::= { hwBattsConfig 5 }

		
		-- 1.3.6.1.4.1.2011.6.164.1.4.1.6
		hwSetBattsHTDLimit OBJECT-TYPE
			SYNTAX Integer32 (0..100)
			MAX-ACCESS read-write
			STATUS current
			DESCRIPTION
				"Upper threshold of the battery high temperature disconnection(HTD), can be configured by users. Value range: 0 to 100, Unit: centigrade (°„C), and the value is an integer (.0)."
			::= { hwBattsConfig 6 }

		
		-- 1.3.6.1.4.1.2011.6.164.1.4.1.7
		hwSetBattsHTDEnable OBJECT-TYPE
			SYNTAX INTEGER
				{
				enable(1),
				disable(2)
				}
			MAX-ACCESS read-write
			STATUS current
			DESCRIPTION
				"Battery high temperature disconnection enable. It is an enumeration type:
				If the enumeration value is 1, enable the operation of the battery disconnection in high temperature; 
				If the enumeration value is 2, disable the operation of the battery disconnection in high temperature. 
				The operation of the battery disconnection in high temperature is disabled by default. "
			::= { hwBattsConfig 7 }

		
		-- 1.3.6.1.4.1.2011.6.164.1.4.1.8
		hwSetBattsFloatVoltage OBJECT-TYPE
			SYNTAX Unsigned32 (420..580)
			UNITS "V"
			MAX-ACCESS read-write
			STATUS current
			DESCRIPTION
				"Float charge voltage of the batteries, can be configured by users. Value range: 42 to 58, unit: V, and the value is accurate to one decimal place (.1)"
			::= { hwBattsConfig 8 }

		
		-- 1.3.6.1.4.1.2011.6.164.1.4.1.9
		hwSetBattsBoostVoltage OBJECT-TYPE
			SYNTAX Unsigned32 (420..580)
			UNITS "V"
			MAX-ACCESS read-write
			STATUS current
			DESCRIPTION
				"Boostcharge voltage of the batteries, can be configured by users. Value range: 42 to 58, unit: V, and the value is accurate to one decimal place (.1)."
			::= { hwBattsConfig 9 }

		
		-- 1.3.6.1.4.1.2011.6.164.1.4.1.10
		hwSetBattsCurrLimitCoefficient OBJECT-TYPE
			SYNTAX Unsigned32 (5..25)
			UNITS "C10"
			MAX-ACCESS read-write
			STATUS current
			DESCRIPTION
				"Current-limiting point coefficient of the batteries, can be configured by users. Value range: 0.05 to 0.25, unit: C10, and the value is accurate to two decimal places (.2)."
			::= { hwBattsConfig 10 }

		
		-- 1.3.6.1.4.1.2011.6.164.1.4.1.11
		hwSetBattsCompFactor OBJECT-TYPE
			SYNTAX Unsigned32 (0..500)
			UNITS "mV per centigrades"
			MAX-ACCESS read-write
			STATUS current
			DESCRIPTION
				"Temperature compensated coefficient of the batteries, can be configured by user. Value range: 0 to 500, unit: mv per centigrade, and the value is an integer (.0)."
			::= { hwBattsConfig 11 }

		
		-- 1.3.6.1.4.1.2011.6.164.1.4.1.12
		hwCtrlBattsBoostFloat OBJECT-TYPE
			SYNTAX INTEGER
				{
				floatCharge(1),
				boostCharge(2),
				nullOper(255)
				}
			MAX-ACCESS read-write
			STATUS current
			DESCRIPTION
				"Control batteries charge mode between boost and float. It is an enumeration value. 
				Users actively control the conversion. 
				If the NMS notifies the SNMP agent that this node is set to 1, it means to start the float charge mode of the batteries; 
				If the NMS notifies the SNMP agent that this node is set to 2, it means to start the boost charge mode of the batteries. 
				"
			::= { hwBattsConfig 12 }

		
		-- 1.3.6.1.4.1.2011.6.164.1.4.2
		hwBattsOperate OBJECT IDENTIFIER ::= { hwSiteBatterys 2 }

		
		-- 1.3.6.1.4.1.2011.6.164.1.4.2.1
		hwBattsTotalCurrent OBJECT-TYPE
			SYNTAX Integer32 (-10000..10000)
			UNITS "A"
			MAX-ACCESS read-only
			STATUS current
			DESCRIPTION
				"Total current of the battery group. It indicates the real-time statistics of the battery group on the site. Value range: -1000 to +1000, unit: A, and the value is accurate to one decimal place (.1). "
			::= { hwBattsOperate 1 }

		
		-- 1.3.6.1.4.1.2011.6.164.1.4.2.2
		hwBattsPreDischargeTime OBJECT-TYPE
			SYNTAX Unsigned32 (0..65536)
			UNITS "minutes"
			MAX-ACCESS read-only
			STATUS current
			DESCRIPTION
				"Battery group backup time. It indicates the real-time statistics of the battery group. Value range: 0 to 65536, Unit: minute (m), and the value is an integer (.0). "
			::= { hwBattsOperate 2 }

		
		-- 1.3.6.1.4.1.2011.6.164.1.4.2.3
		hwBattsChargeStatus OBJECT-TYPE
			SYNTAX INTEGER
				{
				floatCharge(1),
				boostCharge(2),
				disCharge(3),
				unknown(255)
				}
			MAX-ACCESS read-only
			STATUS current
			DESCRIPTION
				"Battery charging state, indicates the charging and discharging information about the battery group. It is an enumeration type. 
				If the enumeration value is 1, it indicates a battery group in the float charging state. 
				If the enumeration value is 2, it indicates a battery group in the boost charging state. 
				If the enumeration value is 3, it indicates a battery group in the discharging state. 
				"
			::= { hwBattsOperate 3 }

		
		-- 1.3.6.1.4.1.2011.6.164.1.4.2.4
		hwBattsCurrLimitStatus OBJECT-TYPE
			SYNTAX INTEGER
				{
				unlimit(1),
				limit(2),
				unknown(255)
				}
			MAX-ACCESS read-only
			STATUS current
			DESCRIPTION
				"Battery group current-limiting state, indicates the state information about the battery group. It is an enumeration value. 
				If the enumeration value is 1, it indicates that the current of the battery group is not limited. 
				If the enumeration value is 2, it indicates the current of the battery group is limited. 
				"
			::= { hwBattsOperate 4 }
		
		-- 1.3.6.1.4.1.2011.6.164.1.4.2.5.
		hwBattsTemprature OBJECT-TYPE
            SYNTAX Integer32 ( -300..200)
            MAX-ACCESS read-only
            STATUS current
            DESCRIPTION
                "Battery temperature. It is a battery parameter collected in real time. 
                Value range: -300 to 200, 
                unit: centigrade (degC), 
                and the value is an integer .
                If the value is 2147483647(0x7FFFFFFF), it indicates that battery temperature sensor is not configured."
            ::= { hwBattsOperate 5 }
		
		-- 1.3.6.1.4.1.2011.6.164.1.4.2.8
		hwBattsRatedCapacity OBJECT-TYPE
            SYNTAX Unsigned32 (0..2147483647)
            MAX-ACCESS read-only
            STATUS current
            DESCRIPTION
                "Batteries actual capacity. 
                It is an analog parameter collected by the battery string in real time.
                Value range: 0 to 2147483647, 
                units: Ah, 
                the value is an integer (1).  
                If the value is 2147483647(0x7FFFFFFF), it indicates that the value is invalid."
            ::= { hwBattsOperate 8 }
		
		-- 1.3.6.1.4.1.2011.6.164.1.4.2.9
        hwBattsRemainCapacity OBJECT-TYPE
            SYNTAX Unsigned32 (0..2147483647)
            MAX-ACCESS read-only
            STATUS current
            DESCRIPTION
                "Remaining capacity of all of the battery. 
                It is an analog parameter collected by the battery string in real time. 
                Value range: 0 to 2147483647, 
                units: Ah, 
                and the value is an integer (1).  
                If the value is 2147483647(0x7FFFFFFF), it indicates that the value is invalid."
            ::= { hwBattsOperate 9 }
		
		-- 1.3.6.1.4.1.2011.6.164.1.4.2.10
		hwTotalRemainingCapacityPercent OBJECT-TYPE
            SYNTAX Unsigned32 (0..100)
            MAX-ACCESS read-only
            STATUS current
            DESCRIPTION
                "Total Remaining Capacity Percent. 
                Value range: 0 to 100, units: %, 
                and the value is an integer.(1). 
                If the value is 2147483647(0x7FFFFFFF), it indicates that the value is invalid."
            ::= { hwBattsOperate 10 }
		
		-- 1.3.6.1.4.1.2011.6.164.1.4.3
		hwBattsTest OBJECT IDENTIFIER ::= { hwSiteBatterys 3 }
		-- 1.3.6.1.4.1.2011.6.164.1.4.3.1
		hwBattsTestRecordCount OBJECT-TYPE
			SYNTAX Unsigned32 (0..100)
			MAX-ACCESS read-only
			STATUS current
			DESCRIPTION
				"Battery test records number."
			::= { hwBattsTest 1 }

		
		-- 1.3.6.1.4.1.2011.6.164.1.4.3.2
		hwSetBattsManuStdTestTime OBJECT-TYPE
			SYNTAX Unsigned32 (1..100)
			UNITS "hours"
			MAX-ACCESS read-write
			STATUS current
			DESCRIPTION
				"Battery standard test time, It can be configured by users, and its value is an integer (.0). 
				Here, if battery manual test is standard mode, value range defines between 1 to 6000, unit: minutes(m)"
			::= { hwBattsTest 2 }

		
		-- 1.3.6.1.4.1.2011.6.164.1.4.3.3
		hwSetBattsManuStdTestEndVolt OBJECT-TYPE
			SYNTAX Unsigned32 (170..220)
			UNITS "V per cell"
			MAX-ACCESS read-write
			STATUS current
			DESCRIPTION
				"Voltage when the battery test is ended, can be configured by users. Unit: V/cell, and the value is accurate to two decimal place (.2).
				Here, if battery manual test is standard mode, value range defines between 1.7 to 2.2"
			::= { hwBattsTest 3 }

		
		-- 1.3.6.1.4.1.2011.6.164.1.4.3.4
		hwSetBattsManuStdTestCellNum OBJECT-TYPE
			SYNTAX Unsigned32 (1..50)
			UNITS "cell"
			MAX-ACCESS read-write
			STATUS current
			DESCRIPTION
				"Battery cell number in each Group, which is used in the battery standard manual test, can be configured by users. Unit: psc or cell, value range defines between 1 to 50. and the value is accurate to one decimal place (.0)."
			::= { hwBattsTest 4 }

		
		-- 1.3.6.1.4.1.2011.6.164.1.4.3.5
		hwSetBattsManuShortTestTime OBJECT-TYPE
			SYNTAX Unsigned32 (1..240)
			UNITS "minutes"
			MAX-ACCESS read-write
			STATUS current
			DESCRIPTION
				"Battery short test time, It can be configured by users, and its value is an integer (.0). 
				If battery manual test is simple mode, value range defines between 1 to 240, unit: minutes(m)"
			::= { hwBattsTest 5 }

		
		-- 1.3.6.1.4.1.2011.6.164.1.4.3.6
		hwSetBattsManuShortTestEndVolt OBJECT-TYPE
			SYNTAX Unsigned32 (400..540)
			UNITS "V"
			MAX-ACCESS read-write
			STATUS current
			DESCRIPTION
				"Voltage when the battery short test is ended, can be configured by users. Unit: V, and the value is accurate to one decimal place (.1).
				Here, if battery manual test is standard mode, value range defines between 40 to 54.
				"
			::= { hwBattsTest 6 }

		
		-- 1.3.6.1.4.1.2011.6.164.1.4.3.7
		hwCtrlBattsTestStartStop OBJECT-TYPE
			SYNTAX INTEGER
				{
				stdTestStart(1),
				shortTestStart(2),
				testStop(3),
				nullOper(255)
				}
			MAX-ACCESS read-write
			STATUS current
			DESCRIPTION
				"Battery manualtest start and stop. It is an enumeration value. 
				If the NMS notifies the SNMP agent that the node is set to 1, it means to start a standard manual test; 
				If the NMS notifies the SNMP agent that the node is set to 2, it means to start a short manual test; 
				If the NMS notifies the SNMP agent that the node is set to 3, it means to stop the battery test. 
				Set the parameters, such as battery test time, and voltage when the battery test stops before the node controls the start of the battery test. If the parameters are not set this time, the system uses the configuration parameters by default; and if the battery test is started at the first time, the system uses the default value. 
				Battery test can only start up in some conditions, so that the reason of Start of battery short test failed may be as follow:
				                            1. Interval between this test and the latest AC outage or test is longer than the preset duration.
				2. No major alarm is raised.
				3. The number of healthy modules is greater than 0.
				4. The number of battery strings is greater than 0."
			::= { hwBattsTest 7 }

		
		-- 1.3.6.1.4.1.2011.6.164.1.4.3.100
		hwBattsTestResultTable OBJECT-TYPE
			SYNTAX SEQUENCE OF HwBattsTestResultEntry
			MAX-ACCESS not-accessible
			STATUS current
			DESCRIPTION
				"Battery test result record table. Use this table to get battery test inital time, test result, battery efficiency, battery discharge time, terminated voltage, average current, discharge AH value, test temperature and test terminated course. This table's index is hwBattsTestResultIndex, clone Battery test result record table."
			::= { hwBattsTest 100 }

		
		-- 1.3.6.1.4.1.2011.6.164.1.4.3.100.1
		hwBattsTestResultEntry OBJECT-TYPE
			SYNTAX HwBattsTestResultEntry
			MAX-ACCESS not-accessible
			STATUS current
			DESCRIPTION
				"Battery test result table entry."
			INDEX { hwBattsTestResultIndex }
			::= { hwBattsTestResultTable 1 }

		
		HwBattsTestResultEntry ::=
			SEQUENCE { 
				hwBattsTestResultIndex
					Integer32,
				hwBattsTestType
					INTEGER,
				hwBattsTestStartTime
					OCTET STRING,
				hwBattsTestResult
					INTEGER,
				hwBattsEfficiency
					Integer32,
				hwBattsDischargeTime
					Unsigned32,
				hwBattsDischargeEndVoltage
					Unsigned32,
				hwBattsDischargeAvCurrent
					Integer32,
				hwBattsDischargeAhValue
					Unsigned32,
				hwBattsTestTemprature
					Integer32,
				hwBattsTestEndCourse
					INTEGER,
				hwBattsTestResultRowStatus
					RowStatus
			 }

		-- 1.3.6.1.4.1.2011.6.164.1.4.3.100.1.1
		hwBattsTestResultIndex OBJECT-TYPE
			SYNTAX Integer32 (1..100)
			MAX-ACCESS read-only
			STATUS current
			DESCRIPTION
				"Table index of the battery test results. Currently up to 10 times of the battery test results are saved by default. "
			::= { hwBattsTestResultEntry 1 }

		
		-- 1.3.6.1.4.1.2011.6.164.1.4.3.100.1.2
		hwBattsTestType OBJECT-TYPE
			SYNTAX INTEGER
				{
				manualTest(1),
				acOffAutoTest(2),
				timedTest(3),
				shortTest(4),
				other(255)
				}
			MAX-ACCESS read-only
			STATUS current
			DESCRIPTION
				"Record test type of the battery test. It is an enumeration value: 
				If the NMS notifies the SNMP agent that this node is set to 1, it indicates a manual test; 
				If the NMS notifies the SNMP agent that this node is set to 2, it indicates a simplified test;
				If the NMS notifies the SNMP agent that this node is set to 3, it indicates a timed test;
				If the NMS notifies the SNMP agent that this node is set to 4, it indicates a short test;
				If the NMS notifies the SNMP agent that this node is set to 255, it indicates a other test."
			::= { hwBattsTestResultEntry 2 }

		
		-- 1.3.6.1.4.1.2011.6.164.1.4.3.100.1.3
		hwBattsTestStartTime OBJECT-TYPE
			SYNTAX OCTET STRING (SIZE (0..127))
			MAX-ACCESS read-only
			STATUS current
			DESCRIPTION
				"Test start time of the record in the battery test. It is of the character string type."
			::= { hwBattsTestResultEntry 3 }

		
		-- 1.3.6.1.4.1.2011.6.164.1.4.3.100.1.4
		hwBattsTestResult OBJECT-TYPE
			SYNTAX INTEGER
				{
				battNoResult(1),
				battNormal(2),
				battPreAlarm(3),
				battAlarm(4),
				unknown(255)
				}
			MAX-ACCESS read-only
			STATUS current
			DESCRIPTION
				"Battery test result. It is an enumeration value.
				If the enumeration value of the node is 1, it indicates that the battery test has no result: 
				If the enumeration value of the node is 2, it indicates that the battery is in the normal state: 
				If the enumeration value of the node is 3, it indicates that the battery is in the minor abnormal state, 
				If the enumeration value of the node is 4, it indicates that the battery is in the alarm state,
				If the enumeration value of the node is 255, it indicates that the battery state is unknown,"
			::= { hwBattsTestResultEntry 4 }

		
		-- 1.3.6.1.4.1.2011.6.164.1.4.3.100.1.5
		hwBattsEfficiency OBJECT-TYPE
			SYNTAX Integer32 (0..100)
			UNITS "%"
			MAX-ACCESS read-only
			STATUS current
			DESCRIPTION
				"Battery efficiency test. Value range: 0 to 100, Unit: %, and the value is an integer (.0).
				If the value is -1, it indicates that the test value is inefficient."
			::= { hwBattsTestResultEntry 5 }

		
		-- 1.3.6.1.4.1.2011.6.164.1.4.3.100.1.6
		hwBattsDischargeTime OBJECT-TYPE
			SYNTAX Unsigned32 (0..10000)
			UNITS "hours"
			MAX-ACCESS read-only
			STATUS current
			DESCRIPTION
				"Discharge time of the battery test records. Value range: 0 to 100, unit: hour (h), and the value is accurate to two decimal places (.2)."
			::= { hwBattsTestResultEntry 6 }

		
		-- 1.3.6.1.4.1.2011.6.164.1.4.3.100.1.7
		hwBattsDischargeEndVoltage OBJECT-TYPE
			SYNTAX Unsigned32 (0..600)
			UNITS "V"
			MAX-ACCESS read-only
			STATUS current
			DESCRIPTION
				"Discharge termination voltage of the battery test. Value range: 0 to 60, unit: V, and the value is accurate to one decimal place (.1)."
			::= { hwBattsTestResultEntry 7 }

		
		-- 1.3.6.1.4.1.2011.6.164.1.4.3.100.1.8
		hwBattsDischargeAvCurrent OBJECT-TYPE
			SYNTAX Integer32 (-10000..10000)
			UNITS "A"
			MAX-ACCESS read-only
			STATUS current
			DESCRIPTION
				"Average discharge current of the battery test. Value range: -10000 to 10000, unit: A, and the value is accurate to one decimal place (.1)."
			::= { hwBattsTestResultEntry 8 }

		
		-- 1.3.6.1.4.1.2011.6.164.1.4.3.100.1.9
		hwBattsDischargeAhValue OBJECT-TYPE
			SYNTAX Unsigned32 (0..5000)
			UNITS "Ah"
			MAX-ACCESS read-only
			STATUS current
			DESCRIPTION
				"Discharge ampere per hour the battery test. Value range: 0 to 5000, Unit: Ah, and the value is an integer (.0). "
			::= { hwBattsTestResultEntry 9 }

		
		-- 1.3.6.1.4.1.2011.6.164.1.4.3.100.1.10
		hwBattsTestTemprature OBJECT-TYPE
			SYNTAX Integer32 (-50..100)
			UNITS "centigrades"
			MAX-ACCESS read-only
			STATUS current
			DESCRIPTION
				"Battery temperature of the battery test termination. Value range: -50 to +100, Unit: centigrade (°„C), and the value is an integer (.0).
				If the value is -1024, it indicates that no battery temperature value sensor is detected."
			::= { hwBattsTestResultEntry 10 }

		
		-- 1.3.6.1.4.1.2011.6.164.1.4.3.100.1.11
		hwBattsTestEndCourse OBJECT-TYPE
			SYNTAX INTEGER
				{
				voltageToEnd(1),
				timeToEnd(2),
				acOnToEnd(3),
				manulToEnd(4),
				faultAlarmToEnd(5),
				other(255)
				}
			MAX-ACCESS read-only
			STATUS current
			DESCRIPTION
				"Termination factors of the battery test. It is an enumeration value. 
				If the enumeration value is 1, it indicates that the voltage value of the battery test reaches the set termination voltage; 
				If the enumeration value is 2, it indicates that the voltage value of the battery test reaches the timing limit; 
				If the enumeration value is 3, it indicates that an alarm related to the battery leads to the stop of the battery test; 
				If the enumeration value is 4, it indicates that a battery test is stopped manually,
				If the enumeration value is 5, it indicates that battery fault alarm happened,
				If the enumeration value is 255, it indicates that battery test end for other courses."
			::= { hwBattsTestResultEntry 11 }

		
		-- 1.3.6.1.4.1.2011.6.164.1.4.3.100.1.100
		hwBattsTestResultRowStatus OBJECT-TYPE
			SYNTAX RowStatus
			MAX-ACCESS read-create
			STATUS current
			DESCRIPTION
				"RowStatus of battery test table."
			::= { hwBattsTestResultEntry 100 }

		
		-- 1.3.6.1.4.1.2011.6.164.1.4.4
		hwBattString OBJECT IDENTIFIER ::= { hwSiteBatterys 4 }

		
		-- 1.3.6.1.4.1.2011.6.164.1.4.4.1
		hwBattStringConfigTable OBJECT-TYPE
			SYNTAX SEQUENCE OF HwBattStringConfigEntry
			MAX-ACCESS not-accessible
			STATUS current
			DESCRIPTION
				"Battery string config table. Use this table to get battery string equipment ID and equipment name, to set battery standard capacity and battery install time as well. This table's index is hwBattStringConfigIndex, clone battery string config table."
			::= { hwBattString 1 }

		
		-- 1.3.6.1.4.1.2011.6.164.1.4.4.1.1
		hwBattStringConfigEntry OBJECT-TYPE
			SYNTAX HwBattStringConfigEntry
			MAX-ACCESS not-accessible
			STATUS current
			DESCRIPTION
				"Battery string config table entry."
			INDEX { hwBattStringConfigIndex }
			::= { hwBattStringConfigTable 1 }

		
		HwBattStringConfigEntry ::=
			SEQUENCE { 
				hwBattStringConfigIndex
					Integer32,
				hwBattStringEquipId
					Unsigned32,
				hwBattStringEquipName
					OCTET STRING,
				hwSetBattsTempUpperLimit
					Integer32,
				hwSetBattsTempLowerLimit
					Integer32,
				hwSetBattsTempMeasureUpperLimit
					Integer32,
				hwSetBattsTempMeasureLowerLimit
					Integer32,
				hwSetBattStdCapacity
					Integer32,
				hwSetBattInstallTime
					OCTET STRING,
				hwBattStringConfigRowStatus
					RowStatus
			 }

		-- 1.3.6.1.4.1.2011.6.164.1.4.4.1.1.1
		hwBattStringConfigIndex OBJECT-TYPE
			SYNTAX Integer32 (1..100)
			MAX-ACCESS read-only
			STATUS current
			DESCRIPTION
				"Device table index of the battery string, which value range: 1 to 100."
			::= { hwBattStringConfigEntry 1 }

		
		-- 1.3.6.1.4.1.2011.6.164.1.4.4.1.1.2
		hwBattStringEquipId OBJECT-TYPE
			SYNTAX Unsigned32 (3001..3100)
			MAX-ACCESS read-only
			STATUS current
			DESCRIPTION
				"Batteries device ID, can be configured by users. Value range: 003,001 to 003,100, in which the first three digits specify the device type and the last three specify the device SN."
			::= { hwBattStringConfigEntry 2 }

		
		-- 1.3.6.1.4.1.2011.6.164.1.4.4.1.1.3
		hwBattStringEquipName OBJECT-TYPE
			SYNTAX OCTET STRING (SIZE (0..63))
			MAX-ACCESS read-write
			STATUS current
			DESCRIPTION
				"Batteries device name, of the character string type, is used to specify the batteries. Users can configure it.
				Otherwise, the configured character can not be any other languages except English."
			::= { hwBattStringConfigEntry 3 }

		
		-- 1.3.6.1.4.1.2011.6.164.1.4.4.1.1.4
		hwSetBattsTempUpperLimit OBJECT-TYPE
			SYNTAX Integer32 (-50..100)
			UNITS "centigrades"
			MAX-ACCESS read-write
			STATUS current
			DESCRIPTION
				"Upper threshold of the battery temperature alarm, can be configured by users. Value range: -50 to 100, Unit: centigrade (°„C), and the value is an integer (.0)."
			::= { hwBattStringConfigEntry 4 }

		
		-- 1.3.6.1.4.1.2011.6.164.1.4.4.1.1.5
		hwSetBattsTempLowerLimit OBJECT-TYPE
			SYNTAX Integer32 (-50..100)
			UNITS "centigrades"
			MAX-ACCESS read-write
			STATUS current
			DESCRIPTION
				"Lower threshold of the battery temperature alarm, can be configured by users. Value range: -50 to 100, Unit: centigrade (°„C), and the value is an integer (.0)."
			::= { hwBattStringConfigEntry 5 }

		
		-- 1.3.6.1.4.1.2011.6.164.1.4.4.1.1.6
		hwSetBattsTempMeasureUpperLimit OBJECT-TYPE
			SYNTAX Integer32 (0..100)
			UNITS "centigrades"
			MAX-ACCESS read-write
			STATUS current
			DESCRIPTION
				"Upper threshold of the battery temperature measurement, can be configured by users. Value range: 0 to 100, Unit: centigrade (°„C), and the value is an integer (.0)."
			::= { hwBattStringConfigEntry 6 }

		
		-- 1.3.6.1.4.1.2011.6.164.1.4.4.1.1.7
		hwSetBattsTempMeasureLowerLimit OBJECT-TYPE
			SYNTAX Integer32 (-50..0)
			UNITS "centigrades"
			MAX-ACCESS read-write
			STATUS current
			DESCRIPTION
				"Lower threshold of the battery temperature measurement, can be configured by users. Value range: -50 to 0, Unit: centigrade (°„C), and the value is an integer (.0)."
			::= { hwBattStringConfigEntry 7 }

		
		-- 1.3.6.1.4.1.2011.6.164.1.4.4.1.1.8
		hwSetBattStdCapacity OBJECT-TYPE
			SYNTAX Integer32 (0..10000)
			UNITS "Ah"
			MAX-ACCESS read-write
			STATUS current
			DESCRIPTION
				"Set battery standard capacity, is an inherent attribute of the device. Value range: 0 to 10000, unit: Ah, the value is an integer (.0). "
			::= { hwBattStringConfigEntry 8 }

		
		-- 1.3.6.1.4.1.2011.6.164.1.4.4.1.1.9
		hwSetBattInstallTime OBJECT-TYPE
			SYNTAX OCTET STRING (SIZE (0..128))
			MAX-ACCESS read-write
			STATUS current
			DESCRIPTION
				"Set battery install time, of the character string type, can be configured by users.
				Otherwise, the configured character can not be any other languages except English. "
			::= { hwBattStringConfigEntry 9 }

		
		-- 1.3.6.1.4.1.2011.6.164.1.4.4.1.1.100
		hwBattStringConfigRowStatus OBJECT-TYPE
			SYNTAX RowStatus
			MAX-ACCESS read-create
			STATUS current
			DESCRIPTION
				"RowStatus of battery string config table."
			::= { hwBattStringConfigEntry 100 }

		
		-- 1.3.6.1.4.1.2011.6.164.1.4.4.2
		hwBattStringOperTable OBJECT-TYPE
			SYNTAX SEQUENCE OF HwBattStringOperEntry
			MAX-ACCESS not-accessible
			STATUS current
			DESCRIPTION
				"Battery string runing table. Use this table to get battery string current, persent of remain capacity, battery remain capacity, battery actual capacity, as well as  battery temperature. This table's index is hwBattStringRunIndex, clone battery string runing table."
			::= { hwBattString 2 }

		
		-- 1.3.6.1.4.1.2011.6.164.1.4.4.2.1
		hwBattStringOperEntry OBJECT-TYPE
			SYNTAX HwBattStringOperEntry
			MAX-ACCESS not-accessible
			STATUS current
			DESCRIPTION
				"Battery string runing table entry."
			INDEX { hwBattStringOperIndex }
			::= { hwBattStringOperTable 1 }

		
		HwBattStringOperEntry ::=
			SEQUENCE { 
				hwBattStringOperIndex
					Integer32,
				hwBattStringCurrent
					Integer32,
				hwBattStringRemainCapacityPercent
					Unsigned32,
				hwBattStringRemainCapacity
					Unsigned32,
				hwBattStringActualCapacity
					Unsigned32,
				hwBattStringTemprature
					Integer32,
				hwBattStringOperStatus
					INTEGER,
				hwBattStringOperRowStatus
					RowStatus
			 }

		-- 1.3.6.1.4.1.2011.6.164.1.4.4.2.1.1
		hwBattStringOperIndex OBJECT-TYPE
			SYNTAX Integer32 (1..100)
			MAX-ACCESS read-only
			STATUS current
			DESCRIPTION
				"Device table index of the battery string, which value range: 1 to 100."
			::= { hwBattStringOperEntry 1 }

		
		-- 1.3.6.1.4.1.2011.6.164.1.4.4.2.1.2
		hwBattStringCurrent OBJECT-TYPE
			SYNTAX Integer32 (-10000..10000)
			UNITS "A"
			MAX-ACCESS read-only
			STATUS current
			DESCRIPTION
				"Batteries current. It is an analog parameter collected by the battery string in real time. Value range: -1000 to +1000, unit: A, and the value is accurate to one decimal place (.1)."
			::= { hwBattStringOperEntry 2 }

		
		-- 1.3.6.1.4.1.2011.6.164.1.4.4.2.1.3
		hwBattStringRemainCapacityPercent OBJECT-TYPE
			SYNTAX Unsigned32 (0..1000)
			UNITS "%"
			MAX-ACCESS read-only
			STATUS current
			DESCRIPTION
				"Remaining capacity percentage of the battery string. Value range: 0 to 100, unit: %, and the value is accurate to one decimal place (.1)."
			::= { hwBattStringOperEntry 3 }

		
		-- 1.3.6.1.4.1.2011.6.164.1.4.4.2.1.4
		hwBattStringRemainCapacity OBJECT-TYPE
			SYNTAX Unsigned32 (0..5000)
			UNITS "Ah"
			MAX-ACCESS read-only
			STATUS current
			DESCRIPTION
				"Remaining capacity of the battery string. It is an analog parameter collected by the battery string in real time. Value range: 0 to 5000, unit: Ah, and the value is an integer (.0)."
			::= { hwBattStringOperEntry 4 }

		
		-- 1.3.6.1.4.1.2011.6.164.1.4.4.2.1.5
		hwBattStringActualCapacity OBJECT-TYPE
			SYNTAX Unsigned32 (0..5000)
			UNITS "Ah"
			MAX-ACCESS read-only
			STATUS current
			DESCRIPTION
				"Batteries actual capacity. It is an analog parameter collected by the battery string in real time.Value range: 0 to 5000, unit: Ah, the value is an integer (.0)."
			::= { hwBattStringOperEntry 5 }

		
		-- 1.3.6.1.4.1.2011.6.164.1.4.4.2.1.6
		hwBattStringTemprature OBJECT-TYPE
			SYNTAX Integer32 (-500..1000)
			UNITS "centigrades"
			MAX-ACCESS read-only
			STATUS current
			DESCRIPTION
				"Battery temperature. It is a battery parameter collected in real time. Value range: -50 to +100, unit: centigrade (°„C), and the value is an integer (.1).
				If the value is -99999, it indicates that battery temperature sensor is not configured."
			::= { hwBattStringOperEntry 6 }

		
		-- 1.3.6.1.4.1.2011.6.164.1.4.4.2.1.99
		hwBattStringOperStatus OBJECT-TYPE
			SYNTAX INTEGER
				{
				normal(1),
				tempHigh(2),
				tempLow(3),
				loopBreak(4),
				overCurrent(5),
				unbalance(6),
				alarmResume(254),
				other(255)
				}
			MAX-ACCESS read-only
			STATUS current
			DESCRIPTION
				"State of the site battery string module. It is an enumeration type: 
				If the enumeration value is 1, it indicates that the site battery string is in the normal state; 
				If the enumeration value is 2, it indicates that the battery string is over upper alarm threshold of temperature; 
				If the enumeration value is 3, it indicates that the battery string is under lower alarm threshold of temperature;  
				If the enumeration value is 4, it indicates that battery string loop has disconnected;  
				If the enumeration value is 5, it indicates that the current of batery is over upper charging threshold;
				If the enumeration value is 254, it indicates battery string alarm resume; 
				If the enumeration value is 255, it indicates battery string operation status unknown. "
			::= { hwBattStringOperEntry 99 }

		
		-- 1.3.6.1.4.1.2011.6.164.1.4.4.2.1.100
		hwBattStringOperRowStatus OBJECT-TYPE
			SYNTAX RowStatus
			MAX-ACCESS read-create
			STATUS current
			DESCRIPTION
				"RowStatus of battery string runing table."
			::= { hwBattStringOperEntry 100 }

		
		-- 1.3.6.1.4.1.2011.6.164.1.5
		hwSiteAcDistributions OBJECT IDENTIFIER ::= { hwSiteMonitorMIBObjects 5 }

		
		-- 1.3.6.1.4.1.2011.6.164.1.5.1
		hwAcDistributionsGroup OBJECT IDENTIFIER ::= { hwSiteAcDistributions 1 }

		
		-- 1.3.6.1.4.1.2011.6.164.1.5.1.1
		hwAcsGroupId OBJECT-TYPE
			SYNTAX Unsigned32
			MAX-ACCESS read-only
			STATUS current
			DESCRIPTION
				"AC group ID, is the unique ID of the AC group. The first three digits indicate the device type and the last three indicate the device SN. If the last three digits are 000, it indicates a virtual device. "
			::= { hwAcDistributionsGroup 1 }

		
		-- 1.3.6.1.4.1.2011.6.164.1.5.1.2
		hwAcsGroupName OBJECT-TYPE
			SYNTAX OCTET STRING (SIZE (0..63))
			MAX-ACCESS read-write
			STATUS current
			DESCRIPTION
				"Device name of the AC group. It is of the character string type, and can be configured by users. 
				Otherwise, the configured character can not be any other languages except English."
			::= { hwAcDistributionsGroup 2 }

		
		-- 1.3.6.1.4.1.2011.6.164.1.5.1.3
		hwAcsTotalCurrent OBJECT-TYPE
			SYNTAX Unsigned32 (0..10000)
			UNITS "A"
			MAX-ACCESS read-only
			STATUS current
			DESCRIPTION
				"Total current of the AC group. It indicates the real-time statistics of the AC group. Value range: 0 to 1000, unit: A, and the value is accurate to one decimal place (.1)."
			::= { hwAcDistributionsGroup 3 }
		
		-- 1.3.6.1.4.1.2011.6.164.1.5.1.4
		hwAcsTotalQuantity OBJECT-TYPE
			SYNTAX Unsigned32 (0..100)
			MAX-ACCESS read-only
			STATUS current
			DESCRIPTION
				"Total quantity of the site ACUs. Value range: 0 to 100. "
			::= { hwAcDistributionsGroup 4 }

		
		-- 1.3.6.1.4.1.2011.6.164.1.5.1.5
		hwSetAcsUpperVoltLimit OBJECT-TYPE
			SYNTAX Unsigned32 (60..500)
			UNITS "V"
			MAX-ACCESS read-write
			STATUS current
			DESCRIPTION
				"Upper threshold of the AC voltage alarm, can be configured by users. Value range: 60 to 500, unit: V, and the value is an integer (.0)."
			::= { hwAcDistributionsGroup 5 }

		
		-- 1.3.6.1.4.1.2011.6.164.1.5.1.6
		hwSetAcsLowerVoltLimit OBJECT-TYPE
			SYNTAX Unsigned32 (60..500)
			UNITS "V"
			MAX-ACCESS read-write
			STATUS current
			DESCRIPTION
				"Lower threshold of the AC voltage alarm, can be configured by users. Value range: 60 to 500, unit: V, and the value is an integer (.0)."
			::= { hwAcDistributionsGroup 6 }

		
		-- 1.3.6.1.4.1.2011.6.164.1.5.2
		hwAcDistribution OBJECT IDENTIFIER ::= { hwSiteAcDistributions 2 }

		
--  1.3.6.1.4.1.2011.6.1.5.5
		-- 1.3.6.1.4.1.2011.6.164.1.5.2.1
		hwAcInputTable OBJECT-TYPE
			SYNTAX SEQUENCE OF HwAcInputEntry
			MAX-ACCESS not-accessible
			STATUS current
			DESCRIPTION
				"AC input table. Use this table to get AC distribution unit ID, AC distribution unit name, A phase or AB line voltage, B phase or BC line voltage, C phase or CA line voltage, AC input breaker status, as well as AC output breakers quantity, which defines hwAcOutputBreakerTable row number. This table's index is hwAcInputIndex, clone AC input table."
			::= { hwAcDistribution 1 }

		
--  1.3.6.1.4.1.2011.6.1.5.5.1
		-- 1.3.6.1.4.1.2011.6.164.1.5.2.1.1
		hwAcInputEntry OBJECT-TYPE
			SYNTAX HwAcInputEntry
			MAX-ACCESS not-accessible
			STATUS current
			DESCRIPTION
				"AC input table entry."
			INDEX { hwAcInputIndex }
			::= { hwAcInputTable 1 }

		
		HwAcInputEntry ::=
			SEQUENCE { 
				hwAcInputIndex
					Integer32,
				hwAcEquipId
					Unsigned32,
				hwAcEquipName
					OCTET STRING,
				hwApOrAblVoltage
					Unsigned32,
				hwBpOrBclVoltage
					Unsigned32,
				hwCpOrCalVoltage
					Unsigned32,
				hwAphaseCurrent
					Integer32,
				hwBphaseCurrent
					Integer32,
				hwCphaseCurrent
					Integer32,
				hwAcInputBreakersQuantity
					Unsigned32,
				hwAcInputOperStatus
					INTEGER,
				hwAcRowStatus
					RowStatus
			 }

--  1.3.6.1.4.1.2011.6.1.5.5.1.1
		-- 1.3.6.1.4.1.2011.6.164.1.5.2.1.1.1
		hwAcInputIndex OBJECT-TYPE
			SYNTAX Integer32 (1..100)
			MAX-ACCESS read-only
			STATUS current
			DESCRIPTION
				"ACU device table index, which value range: 1 to 100. Lines of the device list are restricted by the total quantity of ACUs (hwAcsInputQuantity)."
			::= { hwAcInputEntry 1 }

		
		-- 1.3.6.1.4.1.2011.6.164.1.5.2.1.1.2
		hwAcEquipId OBJECT-TYPE
			SYNTAX Unsigned32 (4001..4100)
			MAX-ACCESS read-only
			STATUS current
			DESCRIPTION
				"ACU device ID, which users can configure. Value range: 004,001 to 004,100, in which The first digits indicate the device type and the last three digits indicate the device SN."
			::= { hwAcInputEntry 2 }

		
		-- 1.3.6.1.4.1.2011.6.164.1.5.2.1.1.3
		hwAcEquipName OBJECT-TYPE
			SYNTAX OCTET STRING (SIZE (0..63))
			MAX-ACCESS read-write
			STATUS current
			DESCRIPTION
				"ACU device name, of the character string type, is used to specify the alternating current unit (ACU). Users can configure it.
				Otherwise, the configured character can not be any other languages except English."
			::= { hwAcInputEntry 3 }

		
--  1.3.6.1.4.1.2011.6.1.5.5.1.5
		-- 1.3.6.1.4.1.2011.6.164.1.5.2.1.1.4
		hwApOrAblVoltage OBJECT-TYPE
			SYNTAX Unsigned32 (0..5000)
			UNITS "V"
			MAX-ACCESS read-only
			STATUS current
			DESCRIPTION
				"ACU A-phase or AB-line voltage. Value range: 0 to 500, unit: V, and the value is accurate to one decimal place (.1)."
			::= { hwAcInputEntry 4 }

		
--  1.3.6.1.4.1.2011.6.1.5.5.1.6
		-- 1.3.6.1.4.1.2011.6.164.1.5.2.1.1.5
		hwBpOrBclVoltage OBJECT-TYPE
			SYNTAX Unsigned32 (0..5000)
			UNITS "V"
			MAX-ACCESS read-only
			STATUS current
			DESCRIPTION
				"ACU B-phase or BC-line voltage. Value range: 0 to 500, unit: V, and the value is accurate to one decimal place (.1)."
			::= { hwAcInputEntry 5 }

		
--  1.3.6.1.4.1.2011.6.1.5.5.1.7
		-- 1.3.6.1.4.1.2011.6.164.1.5.2.1.1.6
		hwCpOrCalVoltage OBJECT-TYPE
			SYNTAX Unsigned32 (0..5000)
			UNITS "V"
			MAX-ACCESS read-only
			STATUS current
			DESCRIPTION
				"ACU C-phase or CA-line voltage. Value range: 0 to 500, unit: V, and the value is accurate to one decimal place (.1)."
			::= { hwAcInputEntry 6 }

		
--  1.3.6.1.4.1.2011.6.1.5.5.1.11
		-- 1.3.6.1.4.1.2011.6.164.1.5.2.1.1.7
		hwAphaseCurrent OBJECT-TYPE
			SYNTAX Integer32 (0..1000)
			UNITS "A"
			MAX-ACCESS read-only
			STATUS current
			DESCRIPTION
				"ACU A-phase current. It is an analog parameter collected by the ACU in real time. Value range: 0 to 100, unit: A, and the value is accurate to one decimal place (.1)."
			::= { hwAcInputEntry 7 }

		
--  1.3.6.1.4.1.2011.6.1.5.5.1.12
		-- 1.3.6.1.4.1.2011.6.164.1.5.2.1.1.8
		hwBphaseCurrent OBJECT-TYPE
			SYNTAX Integer32 (0..1000)
			UNITS "A"
			MAX-ACCESS read-only
			STATUS current
			DESCRIPTION
				"ACU B-phase current. It is an analog parameter collected by the ACU in real time. Value range: 0 to 100, unit: A, and the value is accurate to one decimal place (.1)."
			::= { hwAcInputEntry 8 }

		
--  1.3.6.1.4.1.2011.6.1.5.5.1.13
		-- 1.3.6.1.4.1.2011.6.164.1.5.2.1.1.9
		hwCphaseCurrent OBJECT-TYPE
			SYNTAX Integer32 (0..1000)
			UNITS "A"
			MAX-ACCESS read-only
			STATUS current
			DESCRIPTION
				"ACU C-phase current. It is an analog parameter collected by the ACU in real time. Value range: 0 to 100, unit: A, and the value is accurate to one decimal place (.1)."
			::= { hwAcInputEntry 9 }

		
		-- 1.3.6.1.4.1.2011.6.164.1.5.2.1.1.10
		hwAcInputBreakersQuantity OBJECT-TYPE
			SYNTAX Unsigned32 (0..100)
			MAX-ACCESS read-only
			STATUS current
			DESCRIPTION
				"Quantity of the AC air circuit breakers. 
				As the ACU lower-level subset, the node indicates the quantity of the output air circuit breakers contained by each ACU lower-level subset. Value range: 0 to 100. 
				"
			::= { hwAcInputEntry 10 }

		
		-- 1.3.6.1.4.1.2011.6.164.1.5.2.1.1.99
		hwAcInputOperStatus OBJECT-TYPE
			SYNTAX INTEGER
				{
				normal(1),
				acOff(2),
				acAbsent(3),
				voltHigh(4),
				voltLow(5),
				alarmResume(254),
				other(255)
				}
			MAX-ACCESS read-only
			STATUS current
			DESCRIPTION
				"State of the site AC distribution uint. It is an enumeration type: 
				If the enumeration value is 1, it indicates that the site AC distribution uint is in the normal state; 
				If the enumeration value is 2, it indicates that AC distribution uint power off; 
				If the enumeration value is 3, it indicates that AC input phase absent;
				If the enumeration value is 4, it indicates that AC voltage is over upper alarm threshold;  
				If the enumeration value is 5, it indicates that AC voltage is under lower alarm threshold;  
				If the enumeration value is 254, it indicates AC distribution uint alarm resume; 
				If the enumeration value is 255, it indicates AC distribution uint operation status unknown. 
				"
			::= { hwAcInputEntry 99 }

		
--  1.3.6.1.4.1.2011.6.1.5.5.1.16
		-- 1.3.6.1.4.1.2011.6.164.1.5.2.1.1.100
		hwAcRowStatus OBJECT-TYPE
			SYNTAX RowStatus
			MAX-ACCESS read-create
			STATUS current
			DESCRIPTION
				"RowStatus of ACU."
			::= { hwAcInputEntry 100 }

		
		-- 1.3.6.1.4.1.2011.6.164.1.5.2.2
		hwAcInputBreakerTable OBJECT-TYPE
			SYNTAX SEQUENCE OF HwAcInputBreakerEntry
			MAX-ACCESS not-accessible
			STATUS current
			DESCRIPTION
				"Ac input breaker table. Use this table to get AC input breaker equipment ID, AC input breaker equipment name, and AC input breaker status. This table's index is hwAcInputBreakerIndex, which qualificated by hwAcInputBreakersQuantity in hwAcInputTable, clone Ac input breaker table."
			::= { hwAcDistribution 2 }

		
		-- 1.3.6.1.4.1.2011.6.164.1.5.2.2.1
		hwAcInputBreakerEntry OBJECT-TYPE
			SYNTAX HwAcInputBreakerEntry
			MAX-ACCESS not-accessible
			STATUS current
			DESCRIPTION
				"Ac input breaker table entry."
			INDEX { hwAcInputIndex, hwAcInputBreakerIndex }
			::= { hwAcInputBreakerTable 1 }

		
		HwAcInputBreakerEntry ::=
			SEQUENCE { 
				hwAcInputBreakerIndex
					Integer32,
				hwAcInputBreakerEquipId
					Unsigned32,
				hwAcInputBreakerEquipName
					OCTET STRING,
				hwAcInputBreakerOperStatus
					INTEGER,
				hwAcInputBreakerRowStatus
					RowStatus
			 }

		-- 1.3.6.1.4.1.2011.6.164.1.5.2.2.1.1
		hwAcInputBreakerIndex OBJECT-TYPE
			SYNTAX Integer32 (1..100)
			MAX-ACCESS read-only
			STATUS current
			DESCRIPTION
				"Device table index of the AC air circuit breaker. Value range: 1 to 100.
				An input air circuit breaker device can be uniquely identified through the ACU table index and device index of the AC air circuit breaker.  "
			::= { hwAcInputBreakerEntry 1 }

		
		-- 1.3.6.1.4.1.2011.6.164.1.5.2.2.1.2
		hwAcInputBreakerEquipId OBJECT-TYPE
			SYNTAX Unsigned32 (5001..5100)
			MAX-ACCESS read-only
			STATUS current
			DESCRIPTION
				"AC input air circuit breaker ID. Value range: 005,001 to 005,100. The first digits indicate the device type and the last three digits indicate the device SN."
			::= { hwAcInputBreakerEntry 2 }

		
		-- 1.3.6.1.4.1.2011.6.164.1.5.2.2.1.3
		hwAcInputBreakerEquipName OBJECT-TYPE
			SYNTAX OCTET STRING (SIZE (0..63))
			MAX-ACCESS read-write
			STATUS current
			DESCRIPTION
				"AC input air circuit breaker name, of the character string type, can configured by users.
				Otherwise, the configured character can not be any other languages except English."
			::= { hwAcInputBreakerEntry 3 }

		
		-- 1.3.6.1.4.1.2011.6.164.1.5.2.2.1.99
		hwAcInputBreakerOperStatus OBJECT-TYPE
			SYNTAX INTEGER
				{
				normal(1),
				disconnect(2),
				alarmResume(254),
				other(255)
				}
			MAX-ACCESS read-only
			STATUS current
			DESCRIPTION
				"Operation state of the site AC input breaker. It is an enumeration type: 
				If the enumeration value is 1, it indicates that the site AC input breaker is in the normal state; 
				If the enumeration value is 2, it indicates that the AC input breaker disconnect; 
				If the enumeration value is 254, it indicates AC input breaker alarm resume; 
				If the enumeration value is 255, it indicates AC input breaker operation status unknown. 
				"
			::= { hwAcInputBreakerEntry 99 }

		
		-- 1.3.6.1.4.1.2011.6.164.1.5.2.2.1.100
		hwAcInputBreakerRowStatus OBJECT-TYPE
			SYNTAX RowStatus
			MAX-ACCESS read-create
			STATUS current
			DESCRIPTION
				"RowStatus of AC input breaker."
			::= { hwAcInputBreakerEntry 100 }

		
		-- 1.3.6.1.4.1.2011.6.164.1.6
		hwSiteDcDistributions OBJECT IDENTIFIER ::= { hwSiteMonitorMIBObjects 6 }

		
		-- 1.3.6.1.4.1.2011.6.164.1.6.1
		hwDcDistributionsGroup OBJECT IDENTIFIER ::= { hwSiteDcDistributions 1 }

		
		-- 1.3.6.1.4.1.2011.6.164.1.6.1.1
		hwDcsGroupId OBJECT-TYPE
			SYNTAX Unsigned32
			MAX-ACCESS read-only
			STATUS current
			DESCRIPTION
				"DC group ID: unique ID of the DC group. in which The first digits indicate the device type and the last three digits indicate the device SN. If the last three digits are 000, it indicates a virtual device."
			::= { hwDcDistributionsGroup 1 }

		
		-- 1.3.6.1.4.1.2011.6.164.1.6.1.2
		hwDcsGroupName OBJECT-TYPE
			SYNTAX OCTET STRING (SIZE (0..63))
			MAX-ACCESS read-write
			STATUS current
			DESCRIPTION
				"Device name of the DC group, of the character string type, can be configured by users.
				Otherwise, the configured character can not be any other languages except English."
			::= { hwDcDistributionsGroup 2 }

		
		-- 1.3.6.1.4.1.2011.6.164.1.6.1.3
		hwDcsTotalVoltage OBJECT-TYPE
			SYNTAX Unsigned32 (0..600)
			UNITS "V"
			MAX-ACCESS read-only
			STATUS current
			DESCRIPTION
				"Total voltage of the DC group. Value range: 0 to 60, unit: V, and the value is accurate to one decimal place (.1)."
			::= { hwDcDistributionsGroup 3 }

		
		-- 1.3.6.1.4.1.2011.6.164.1.6.1.4
		hwDcsTotalCurrent OBJECT-TYPE
			SYNTAX Unsigned32 (0..1000000)
			UNITS "A"
			MAX-ACCESS read-only
			STATUS current
			DESCRIPTION
				"Total current of the DC group. Value range: 0 to 10000, unit: A, and the value is accurate to one decimal place (.1). "
			::= { hwDcDistributionsGroup 4 }

		
		-- 1.3.6.1.4.1.2011.6.164.1.6.1.5
		hwDcsTotalPower OBJECT-TYPE
			SYNTAX Unsigned32 (0..600000)
			UNITS "W"
			MAX-ACCESS read-only
			STATUS current
			DESCRIPTION
				"Total power of the DC group. Value range: 0 to 10000, unit: W, and the value is an integer (.0)."
			::= { hwDcDistributionsGroup 5 }

		
		-- 1.3.6.1.4.1.2011.6.164.1.6.1.6
		hwDcsTotalQuantity OBJECT-TYPE
			SYNTAX Unsigned32 (0..100)
			MAX-ACCESS read-only
			STATUS current
			DESCRIPTION
				"Total quantity of the DC units, and its Value range: 0 to 100."
			::= { hwDcDistributionsGroup 6 }

		
		-- 1.3.6.1.4.1.2011.6.164.1.6.1.7
		hwSetDcsUpperVoltLimit OBJECT-TYPE
			SYNTAX Unsigned32 (300..600)
			UNITS "V"
			MAX-ACCESS read-write
			STATUS current
			DESCRIPTION
				"Upper threshold of the DC voltage alarm, can be configued by users. Value range: 30 to 60, unit: V, and the value is accurate to one decimal space (.1)."
			::= { hwDcDistributionsGroup 7 }

		
		-- 1.3.6.1.4.1.2011.6.164.1.6.1.8
		hwSetDcsLowerVoltLimit OBJECT-TYPE
			SYNTAX Unsigned32 (300..600)
			UNITS "V"
			MAX-ACCESS read-write
			STATUS current
			DESCRIPTION
				"Lower threshold of the DC voltage alarm, can be configued by users. Value range: 30 to 60, unit: V, and the value is accurate to one decimal space (.1)."
			::= { hwDcDistributionsGroup 8 }

		
		-- 1.3.6.1.4.1.2011.6.164.1.6.2
		hwDcDistribution OBJECT IDENTIFIER ::= { hwSiteDcDistributions 2 }

		
		-- 1.3.6.1.4.1.2011.6.164.1.6.2.1
		hwDcOutputTable OBJECT-TYPE
			SYNTAX SEQUENCE OF HwDcOutputEntry
			MAX-ACCESS not-accessible
			STATUS current
			DESCRIPTION
				"DC output table. Use this table to get DC distribution unit ID, DC distribution unit name, DC output voltage, DC output power, and loads quantity in each DC distribution unit, which defines hwLoadsOutputTable row number. This table's index is hwDcOutputIndex, clone Dc output table."
			::= { hwDcDistribution 1 }

		
		-- 1.3.6.1.4.1.2011.6.164.1.6.2.1.1
		hwDcOutputEntry OBJECT-TYPE
			SYNTAX HwDcOutputEntry
			MAX-ACCESS not-accessible
			STATUS current
			DESCRIPTION
				"Dc output table entry."
			INDEX { hwDcOutputIndex }
			::= { hwDcOutputTable 1 }

		
		HwDcOutputEntry ::=
			SEQUENCE { 
				hwDcOutputIndex
					Integer32,
				hwDcOutputEquipId
					Unsigned32,
				hwDcOutputEquipName
					OCTET STRING,
				hwDcOutputVoltage
					Unsigned32,
				hwDcOutputCurrent
					Unsigned32,
				hwDcOutputPower
					Unsigned32,
				hwLoadsQuantity
					Unsigned32,
				hwDcOutputOperStatus
					INTEGER,
				hwDcOutputRowStatus
					RowStatus
			 }

		-- 1.3.6.1.4.1.2011.6.164.1.6.2.1.1.1
		hwDcOutputIndex OBJECT-TYPE
			SYNTAX Integer32 (1..100)
			MAX-ACCESS read-only
			STATUS current
			DESCRIPTION
				"Device table index of the DC units, which value range: 1 to 100. Lines of the device list are restricted by the total quantity of DC units (hwDcsQuantity)."
			::= { hwDcOutputEntry 1 }

		
		-- 1.3.6.1.4.1.2011.6.164.1.6.2.1.1.2
		hwDcOutputEquipId OBJECT-TYPE
			SYNTAX Unsigned32 (6001..6100)
			MAX-ACCESS read-only
			STATUS current
			DESCRIPTION
				"DC unit device ID, which value range: 006,001 to 006,100. The first digits indicate the device type and the last three digits indicate the device SN. "
			::= { hwDcOutputEntry 2 }

		
		-- 1.3.6.1.4.1.2011.6.164.1.6.2.1.1.3
		hwDcOutputEquipName OBJECT-TYPE
			SYNTAX OCTET STRING (SIZE (0..63))
			MAX-ACCESS read-write
			STATUS current
			DESCRIPTION
				"DC unit device name, of the character string type, can be configued by users. 
				Otherwise, the configured character can not be any other languages except English."
			::= { hwDcOutputEntry 3 }

		
		-- 1.3.6.1.4.1.2011.6.164.1.6.2.1.1.4
		hwDcOutputVoltage OBJECT-TYPE
			SYNTAX Unsigned32 (0..600)
			UNITS "V"
			MAX-ACCESS read-only
			STATUS current
			DESCRIPTION
				"DC output voltage. It is an analog parameter collected by the DC power in real time. Value range: 0 to 60, unit: V, and the value is accurate to one decimal space (.1)."
			::= { hwDcOutputEntry 4 }

		
		-- 1.3.6.1.4.1.2011.6.164.1.6.2.1.1.5
		hwDcOutputCurrent OBJECT-TYPE
			SYNTAX Unsigned32 (0..100000)
			UNITS "A"
			MAX-ACCESS read-only
			STATUS current
			DESCRIPTION
				"DC output current. It is an analog parameter collected by the DC power in real time. Value range: 0 to 10000, unit: A, and the value is accurate to one decimal space (.1)."
			::= { hwDcOutputEntry 5 }

		
		-- 1.3.6.1.4.1.2011.6.164.1.6.2.1.1.6
		hwDcOutputPower OBJECT-TYPE
			SYNTAX Unsigned32 (0..600000)
			UNITS "W"
			MAX-ACCESS read-only
			STATUS current
			DESCRIPTION
				"DC output power. It is an analog parameter collected by the DC power in real time. Value range: 0 to 600000, unit: W, and the value is an integer (.0)."
			::= { hwDcOutputEntry 6 }

		
		-- 1.3.6.1.4.1.2011.6.164.1.6.2.1.1.7
		hwLoadsQuantity OBJECT-TYPE
			SYNTAX Unsigned32 (0..100)
			MAX-ACCESS read-only
			STATUS current
			DESCRIPTION
				"Quantity of the DC load output branches, which value range: 0 to 100. 
				As the DC unit lower-level subset, the node indicates the quantity of the DC load output branches contained by each DC unit lower-level subset."
			::= { hwDcOutputEntry 7 }

		
		-- 1.3.6.1.4.1.2011.6.164.1.6.2.1.1.99
		hwDcOutputOperStatus OBJECT-TYPE
			SYNTAX INTEGER
				{
				normal(1),
				voltHigh(2),
				voltLow(3),
				alarmResume(254),
				other(255)
				}
			MAX-ACCESS read-only
			STATUS current
			DESCRIPTION
				"State of the site DC distribution uint. It is an enumeration type: 
				If the enumeration value is 1, it indicates that the site DC distribution uint is in the normal state; 
				If the enumeration value is 2, it indicates that DC voltage is over the upper alarm threshold;
				If the enumeration value is 3, it indicates that DC voltage is under the lower alarm threshold; 
				If the enumeration value is 254, it indicates DC distribution uint alarm resume; 
				If the enumeration value is 255, it indicates DC distribution uint operation status unknown. 
				"
			::= { hwDcOutputEntry 99 }

		
		-- 1.3.6.1.4.1.2011.6.164.1.6.2.1.1.100
		hwDcOutputRowStatus OBJECT-TYPE
			SYNTAX RowStatus
			MAX-ACCESS read-create
			STATUS current
			DESCRIPTION
				"RowStatus of Dc output equipments."
			::= { hwDcOutputEntry 100 }

		
		-- 1.3.6.1.4.1.2011.6.164.1.6.2.2
		hwLoadBranchTable OBJECT-TYPE
			SYNTAX SEQUENCE OF HwLoadBranchEntry
			MAX-ACCESS not-accessible
			STATUS current
			DESCRIPTION
				"Loads output table. Use this table to get load branch equipment ID, load branch equipment name, load branch current, and load branch power. This table's index is hwLoadBranchIndex, which qualificated by hwloadsQuantity in hwDcOutputTable, clone loads output table."
			::= { hwDcDistribution 2 }

		
		-- 1.3.6.1.4.1.2011.6.164.1.6.2.2.1
		hwLoadBranchEntry OBJECT-TYPE
			SYNTAX HwLoadBranchEntry
			MAX-ACCESS not-accessible
			STATUS current
			DESCRIPTION
				"Loads output table entry."
			INDEX { hwDcOutputIndex, hwLoadBranchIndex }
			::= { hwLoadBranchTable 1 }

		
		HwLoadBranchEntry ::=
			SEQUENCE { 
				hwLoadBranchIndex
					Integer32,
				hwLoadBranchEquipId
					Unsigned32,
				hwLoadBranchEquipName
					OCTET STRING,
				hwLoadBranchCurrent
					Unsigned32,
				hwLoadBranchPower
					Unsigned32,
				hwLoadBranchOperStatus
					INTEGER,
				hwLoadBranchRowStatus
					RowStatus
			 }

		-- 1.3.6.1.4.1.2011.6.164.1.6.2.2.1.1
		hwLoadBranchIndex OBJECT-TYPE
			SYNTAX Integer32 (1..100)
			MAX-ACCESS read-only
			STATUS current
			DESCRIPTION
				"Device table index of the DC load output branch, which value range: 1 to 100. 
				A DC load output branch can be uniquely identified through the DC unit table index and device index of the DC load output branch."
			::= { hwLoadBranchEntry 1 }

		
		-- 1.3.6.1.4.1.2011.6.164.1.6.2.2.1.2
		hwLoadBranchEquipId OBJECT-TYPE
			SYNTAX Unsigned32 (7001..7100)
			MAX-ACCESS read-only
			STATUS current
			DESCRIPTION
				"Device ID of the DC load output branch. Value range: 007,001 to 007,100. The first digits indicate the device type and the last three digits indicate the SN of the device. "
			::= { hwLoadBranchEntry 2 }

		
		-- 1.3.6.1.4.1.2011.6.164.1.6.2.2.1.3
		hwLoadBranchEquipName OBJECT-TYPE
			SYNTAX OCTET STRING (SIZE (0..63))
			MAX-ACCESS read-write
			STATUS current
			DESCRIPTION
				"Device name of the DC load output branch, of the character string type, can be configured by users.
				Otherwise, the configured character can not be any other languages except English."
			::= { hwLoadBranchEntry 3 }

		
		-- 1.3.6.1.4.1.2011.6.164.1.6.2.2.1.4
		hwLoadBranchCurrent OBJECT-TYPE
			SYNTAX Unsigned32 (0..100000)
			UNITS "A"
			MAX-ACCESS read-only
			STATUS current
			DESCRIPTION
				"DC load output branch current. It is an analog parameter collected by the load branch in real time. Value range: 0 to 10000, unit: A, and the value is accurate to one decimal space (.1)."
			::= { hwLoadBranchEntry 4 }

		
		-- 1.3.6.1.4.1.2011.6.164.1.6.2.2.1.5
		hwLoadBranchPower OBJECT-TYPE
			SYNTAX Unsigned32 (0..600000)
			UNITS "W"
			MAX-ACCESS read-only
			STATUS current
			DESCRIPTION
				"DC load branch power. It is an analog parameter collected by the DC power in real time. Value range: 0 to 600000, unit: W, and the value is an integer (.0)."
			::= { hwLoadBranchEntry 5 }

		
		-- 1.3.6.1.4.1.2011.6.164.1.6.2.2.1.99
		hwLoadBranchOperStatus OBJECT-TYPE
			SYNTAX INTEGER
				{
				normal(1),
				disconnect(2),
				alarmResume(254),
				other(255)
				}
			MAX-ACCESS read-only
			STATUS current
			DESCRIPTION
				"State of the site load output branch. It is an enumeration type: 
				If the enumeration value is 1, it indicates that the site load output branch is in the normal state; 
				If the enumeration value is 2, it indicates that the load output branch disconnect;
				If the enumeration value is 254, it indicates load output branch alarm resume; 
				If the enumeration value is 255, it indicates load output branch operation status unknown. 
				"
			::= { hwLoadBranchEntry 99 }

		
		-- 1.3.6.1.4.1.2011.6.164.1.6.2.2.1.100
		hwLoadBranchRowStatus OBJECT-TYPE
			SYNTAX RowStatus
			MAX-ACCESS read-create
			STATUS current
			DESCRIPTION
				"RowStatus of loads output branch."
			::= { hwLoadBranchEntry 100 }

		
		-- 1.3.6.1.4.1.2011.6.164.1.7
		hwLvdUnits OBJECT IDENTIFIER ::= { hwSiteMonitorMIBObjects 7 }

		
		-- 1.3.6.1.4.1.2011.6.164.1.7.1
		hwLvdsGroup OBJECT IDENTIFIER ::= { hwLvdUnits 1 }

		
		-- 1.3.6.1.4.1.2011.6.164.1.7.1.1
		hwLvdsGroupId OBJECT-TYPE
			SYNTAX Unsigned32
			MAX-ACCESS read-only
			STATUS current
			DESCRIPTION
				"LVD unit group ID. It is the unique ID of the LVD unit group. The first digits indicate the device type. The last three digits indicate the device SN. If the last three digits are 000, it indicates a virtual device."
			::= { hwLvdsGroup 1 }

		
		-- 1.3.6.1.4.1.2011.6.164.1.7.1.2
		hwLvdsGroupName OBJECT-TYPE
			SYNTAX OCTET STRING (SIZE (0..63))
			MAX-ACCESS read-write
			STATUS current
			DESCRIPTION
				"Low-voltage power-off unit group name, of the character string type, can be configured by users.
				Otherwise, the configured character can not be any other languages except English."
			::= { hwLvdsGroup 2 }

		
		-- 1.3.6.1.4.1.2011.6.164.1.7.1.3
		hwLvdsTotalQuantity OBJECT-TYPE
			SYNTAX Unsigned32 (0..100)
			MAX-ACCESS read-only
			STATUS current
			DESCRIPTION
				"Total quantity of power-off units. Value range: 0 to 100."
			::= { hwLvdsGroup 3 }

		
		-- 1.3.6.1.4.1.2011.6.164.1.7.2
		hwLvdUnit OBJECT IDENTIFIER ::= { hwLvdUnits 2 }

		
		-- 1.3.6.1.4.1.2011.6.164.1.7.2.1
		hwLvdBranchTable OBJECT-TYPE
			SYNTAX SEQUENCE OF HwLvdBranchEntry
			MAX-ACCESS not-accessible
			STATUS current
			DESCRIPTION
				"Power-off unit table. Use this table to get Lvd unit equipment ID and power-off unit equipment name, set power-off enable and power-off voltage, as well as control power-off unit disconnected. This table's index is hwLvdBranchIndex, which qualificated by hwLvdsQuantity, clone power-off unit table."
			::= { hwLvdUnit 1 }

		
		-- 1.3.6.1.4.1.2011.6.164.1.7.2.1.1
		hwLvdBranchEntry OBJECT-TYPE
			SYNTAX HwLvdBranchEntry
			MAX-ACCESS not-accessible
			STATUS current
			DESCRIPTION
				"Power-off table entry."
			INDEX { hwLvdBranchIndex }
			::= { hwLvdBranchTable 1 }

		
		HwLvdBranchEntry ::=
			SEQUENCE { 
				hwLvdBranchIndex
					Integer32,
				hwLvdUnitEquipId
					Unsigned32,
				hwLvdUnitEquipName
					OCTET STRING,
				hwSetLvdEnable
					INTEGER,
				hwSetLvdVoltage
					Integer32,
				hwCtrlLvd
					INTEGER,
				hwLvdBranchOperStatus
					INTEGER,
				hwLvdBranchRowStatus
					RowStatus
			 }

		-- 1.3.6.1.4.1.2011.6.164.1.7.2.1.1.1
		hwLvdBranchIndex OBJECT-TYPE
			SYNTAX Integer32 (1..100)
			MAX-ACCESS read-only
			STATUS current
			DESCRIPTION
				"Device table index of a power-off unit. Value range: 1 to 100. Lines of the device list are restricted by the total quantity of the power-off units (hwLvdsTotalQuantity). "
			::= { hwLvdBranchEntry 1 }

		
		-- 1.3.6.1.4.1.2011.6.164.1.7.2.1.1.2
		hwLvdUnitEquipId OBJECT-TYPE
			SYNTAX Unsigned32 (8001..8100)
			MAX-ACCESS read-only
			STATUS current
			DESCRIPTION
				"Device ID of a power-off unit. Value range: 8001 to 8100. The first digits indicate the device type and the last three digits indicate the device SN.  "
			::= { hwLvdBranchEntry 2 }

		
		-- 1.3.6.1.4.1.2011.6.164.1.7.2.1.1.3
		hwLvdUnitEquipName OBJECT-TYPE
			SYNTAX OCTET STRING (SIZE (0..63))
			MAX-ACCESS read-write
			STATUS current
			DESCRIPTION
				"Device name of a power-off unit, of the character string type, is used to specify the low-voltage power-off unit. Users can configure it.
				Otherwise, the configured character can not be any other languages except English. "
			::= { hwLvdBranchEntry 3 }

		
		-- 1.3.6.1.4.1.2011.6.164.1.7.2.1.1.4
		hwSetLvdEnable OBJECT-TYPE
			SYNTAX INTEGER
				{
				enabled(1),
				disabled(2)
				}
			MAX-ACCESS read-write
			STATUS current
			DESCRIPTION
				"Control power-off unit enabling. It is an enumeration value, and users actively set it. 
				If the enumeration value is 1, it means to enable the power-off unit; 
				If the enumeration value is 2, it means to disable the power-off unit. 
				When the power-off unit control is not configured, the power-off unit is enabled by default."
			::= { hwLvdBranchEntry 4 }

		
		-- 1.3.6.1.4.1.2011.6.164.1.7.2.1.1.5
		hwSetLvdVoltage OBJECT-TYPE
			SYNTAX Integer32 (350..600)
			UNITS "V"
			MAX-ACCESS read-write
			STATUS current
			DESCRIPTION
				"Low-voltage power-off voltage of a power-off unit can be configured by users. Its value range: 35 to 60, unit: V, and the value is accurate to one decimal space (.1)."
			::= { hwLvdBranchEntry 5 }

		
		-- 1.3.6.1.4.1.2011.6.164.1.7.2.1.1.6
		hwCtrlLvd OBJECT-TYPE
			SYNTAX INTEGER
				{
				powerOff(1),
				powerOn(2),
				nullOper(255)
				}
			MAX-ACCESS read-write
			STATUS current
			DESCRIPTION
				"Control of the power-off unit. It is an enumeration value, users control it manually. 
				If the NMS notifies the SNMP agent that the node is set to 1, it means to power off the power-off unit; 
				If the NMS notifies the SNMP agent that the node is set to 2, it means that the background controls the power-on of the LVD unit. 
				"
			::= { hwLvdBranchEntry 6 }

		
		-- 1.3.6.1.4.1.2011.6.164.1.7.2.1.1.99
		hwLvdBranchOperStatus OBJECT-TYPE
			SYNTAX INTEGER
				{
				normal(1),
				lowVoltOff(2),
				backgroundOff(3),
				localManualOff(4),
				lowTempOff(5),
				highTempOff(6),
				alarmResume(254),
				other(255)
				}
			MAX-ACCESS read-only
			STATUS current
			DESCRIPTION
				"State of the site LVD uint. It is an enumeration type: 
				If the enumeration value is 1, it indicates that the site LVD uint is in the normal state;
				If the enumeration value is 2, it indicates that the power-off uint disconnect for low voltage;  
				If the enumeration value is 3, it indicates that the power-off uint disconnect bakeground;   
				If the enumeration value is 4, it indicates that the power-off uint local disconnect manually;  
				If the enumeration value is 5, it indicates that the power-off uint disconnect for under temperature; 
				If the enumeration value is 6, it indicates that the power-off uint disconnect for over temperature; 
				If the enumeration value is 254, it indicates that the power-off uint alarm resume; 
				If the enumeration value is 255, it indicates LVD uint operation status unknown. "
			::= { hwLvdBranchEntry 99 }

		
		-- 1.3.6.1.4.1.2011.6.164.1.7.2.1.1.100
		hwLvdBranchRowStatus OBJECT-TYPE
			SYNTAX RowStatus
			MAX-ACCESS read-create
			STATUS current
			DESCRIPTION
				"RowStatus of lvd table."
			::= { hwLvdBranchEntry 100 }

		
		-- 1.3.6.1.4.1.2011.6.164.1.8
		hwSiteEnvUnits OBJECT IDENTIFIER ::= { hwSiteMonitorMIBObjects 8 }

		
		-- 1.3.6.1.4.1.2011.6.164.1.8.1
		hwEnvUnitsGroup OBJECT IDENTIFIER ::= { hwSiteEnvUnits 1 }

		
		-- 1.3.6.1.4.1.2011.6.164.1.8.1.1
		hwEnvUnitsGroupId OBJECT-TYPE
			SYNTAX Unsigned32
			MAX-ACCESS read-only
			STATUS current
			DESCRIPTION
				"Unit group ID of the site environment. It is the unique ID of the unit group on the site. The first digits indicate the device type. The last three digits indicate the device SN. If the last three digits are 000, it indicates a virtual device.  "
			::= { hwEnvUnitsGroup 1 }

		
		-- 1.3.6.1.4.1.2011.6.164.1.8.1.2
		hwEnvUnitsGroupName OBJECT-TYPE
			SYNTAX OCTET STRING (SIZE (0..63))
			MAX-ACCESS read-write
			STATUS current
			DESCRIPTION
				"Unit group name of the site environment, of the character string type, can be configured by users.
				Otherwise, the configured character can not be any other languages except English."
			::= { hwEnvUnitsGroup 2 }

		
		-- 1.3.6.1.4.1.2011.6.164.1.8.1.3
		hwCtrlSmokeReset OBJECT-TYPE
			SYNTAX INTEGER
				{
				normal(1),
				reset(2),
				nullOper(255)
				}
			MAX-ACCESS read-write
			STATUS current
			DESCRIPTION
				"Smoke sensor reset. It manually controls clearance of the smoke sensor alarm, and this node is of the enumeration type. 
				If the enumeration value is 1, it indicates that the reset of the smoke sensor is not required. 
				If the enumeration value of the node is 2, it indicates that the background controls the reset of the smoke sensor. 
				"
			::= { hwEnvUnitsGroup 3 }

		
		-- 1.3.6.1.4.1.2011.6.164.1.8.1.4
		hwCtrlDoorReset OBJECT-TYPE
			SYNTAX INTEGER
				{
				normal(1),
				reset(2),
				nullOper(255)
				}
			MAX-ACCESS read-write
			STATUS current
			DESCRIPTION
				"Door actuator reset control. It manually controls clearance of the door actuator alarm. This node is of the enumeration type. 
				If the enumeration value is 1, it indicates that clearance of the door actuator is not required;
				If the enumeration value is 2, it indicates that the background controls clearance of the door actuator. "
			::= { hwEnvUnitsGroup 4 }

		
		-- 1.3.6.1.4.1.2011.6.164.1.8.1.5
		hwCtrlBuzzerEnable OBJECT-TYPE
			SYNTAX INTEGER
				{
				enable(1),
				disable(2),
				nullOper(255)
				}
			MAX-ACCESS read-write
			STATUS current
			DESCRIPTION
				"Buzzer enabling. It manually controls the enabling of the buzzer alarm. This node is of the enumeration type. 
				When the enumeration value is 1, it means to enable the buzzer;
				When the enumeration value is 2, it means to disable the buzzer. 
				"
			::= { hwEnvUnitsGroup 5 }

		
		-- 1.3.6.1.4.1.2011.6.164.1.8.1.6
		hwEnvTempSensorsTotalQuantity OBJECT-TYPE
			SYNTAX Unsigned32 (0..256)
			MAX-ACCESS read-only
			STATUS current
			DESCRIPTION
				"Quantity of the environment temperature sensors, and its value range: 0 to 256."
			::= { hwEnvUnitsGroup 6 }

		
		-- 1.3.6.1.4.1.2011.6.164.1.8.1.7
		hwEnvHumiSensorsTotalQuantity OBJECT-TYPE
			SYNTAX Unsigned32 (0..256)
			MAX-ACCESS read-only
			STATUS current
			DESCRIPTION
				"Quantity of the environment humidity sensors, and its value range: 0 to 256."
			::= { hwEnvUnitsGroup 7 }

		
		-- 1.3.6.1.4.1.2011.6.164.1.8.1.8
		hwSpareDigitalsTotalQuantity OBJECT-TYPE
			SYNTAX Unsigned32 (0..256)
			MAX-ACCESS read-only
			STATUS current
			DESCRIPTION
				"Quantity of the Spare digitals, and its value range: 0 to 256."
			::= { hwEnvUnitsGroup 8 }

		
		-- 1.3.6.1.4.1.2011.6.164.1.8.2
		hwEnvSensor OBJECT IDENTIFIER ::= { hwSiteEnvUnits 2 }

		
		-- 1.3.6.1.4.1.2011.6.164.1.8.2.1
		hwEnvTempSensorTable OBJECT-TYPE
			SYNTAX SEQUENCE OF HwEnvTempSensorEntry
			MAX-ACCESS not-accessible
			STATUS current
			DESCRIPTION
				"Site environment temperature table. Use this table to get environment temperature equipment ID, environment temperature equipment name, and environment temperature, set environment temperature upper limit, environment temperature lower limit, and environment temperature alarm enable. This table's index is hwEnvTempSensorIndex, which qualificated by hwEnvTempSensorsQuantity, clone site environment temperature table."
			::= { hwEnvSensor 1 }

		
		-- 1.3.6.1.4.1.2011.6.164.1.8.2.1.1
		hwEnvTempSensorEntry OBJECT-TYPE
			SYNTAX HwEnvTempSensorEntry
			MAX-ACCESS not-accessible
			STATUS current
			DESCRIPTION
				"Site environment temperature table entry."
			INDEX { hwEnvTempSensorIndex }
			::= { hwEnvTempSensorTable 1 }

		
		HwEnvTempSensorEntry ::=
			SEQUENCE { 
				hwEnvTempSensorIndex
					Integer32,
				hwEnvTempEquipId
					Unsigned32,
				hwEnvTempEquipName
					OCTET STRING,
				hwEnvTemperature
					Integer32,
				hwSetEnvTempUpperLimit
					Integer32,
				hwSetEnvTempLowerLimit
					Integer32,
				hwSetEnvTempMeasureUpperLimit
					Integer32,
				hwSetEnvTempMeasureLowerLimit
					Integer32,
				hwSetEnvTempAlarmEnable
					INTEGER,
				hwEnvTempSensorOperStatus
					INTEGER,
				hwEnvTempSensorRowStatus
					RowStatus
			 }

		-- 1.3.6.1.4.1.2011.6.164.1.8.2.1.1.1
		hwEnvTempSensorIndex OBJECT-TYPE
			SYNTAX Integer32 (1..256)
			MAX-ACCESS read-only
			STATUS current
			DESCRIPTION
				"Table index of the environment temperature sensors. Value range: 1 to 256. Lines of the device table are restricted by the quantity of environment temperature sensors (hwEnvTempSensorsTotalQuantity). "
			::= { hwEnvTempSensorEntry 1 }

		
		-- 1.3.6.1.4.1.2011.6.164.1.8.2.1.1.2
		hwEnvTempEquipId OBJECT-TYPE
			SYNTAX Unsigned32 (9001..9255)
			MAX-ACCESS read-only
			STATUS current
			DESCRIPTION
				"Environment temperature sensor ID. Value range: 009'001 to 009'255, in which the first digits indicate the device type and the last three digits indicate the device SN. "
			::= { hwEnvTempSensorEntry 2 }

		
		-- 1.3.6.1.4.1.2011.6.164.1.8.2.1.1.3
		hwEnvTempEquipName OBJECT-TYPE
			SYNTAX OCTET STRING (SIZE (0..63))
			MAX-ACCESS read-write
			STATUS current
			DESCRIPTION
				"Environment temperature sensor name, of the character string type,  is used to specify an environment temperature sensor. Users can configure it.
				Otherwise, the configured character can not be any other languages except English. "
			::= { hwEnvTempSensorEntry 3 }

		
		-- 1.3.6.1.4.1.2011.6.164.1.8.2.1.1.4
		hwEnvTemperature OBJECT-TYPE
			SYNTAX Integer32 (-50..100)
			UNITS "centigrades"
			MAX-ACCESS read-only
			STATUS current
			DESCRIPTION
				"Environment temperature. It is an environment parameter collected in real time. Value range: -50 to +100, unit: centigrade (°„C), and the value is an integer (.0).  
				If the value is -1024, it indicates that the temperature sensor is not configured."
			::= { hwEnvTempSensorEntry 4 }

		
		-- 1.3.6.1.4.1.2011.6.164.1.8.2.1.1.5
		hwSetEnvTempUpperLimit OBJECT-TYPE
			SYNTAX Integer32 (-50..100)
			UNITS "centigrades"
			MAX-ACCESS read-write
			STATUS current
			DESCRIPTION
				"Upper threshold of the environment temperature alarm, can be configured by users. Value range: -50 to 100, unit: centigrade (°„C), and the value is an integer (.0)."
			::= { hwEnvTempSensorEntry 5 }

		
		-- 1.3.6.1.4.1.2011.6.164.1.8.2.1.1.6
		hwSetEnvTempLowerLimit OBJECT-TYPE
			SYNTAX Integer32 (-50..100)
			UNITS "centigrades"
			MAX-ACCESS read-write
			STATUS current
			DESCRIPTION
				"Lower threshold of the environment temperature alarm, can be configured by users. Value range: -50 to 100, unit: centigrade (°„C), and the value is an integer (.0)."
			::= { hwEnvTempSensorEntry 6 }

		
		-- 1.3.6.1.4.1.2011.6.164.1.8.2.1.1.7
		hwSetEnvTempMeasureUpperLimit OBJECT-TYPE
			SYNTAX Integer32 (0..100)
			UNITS "centigrades"
			MAX-ACCESS read-write
			STATUS current
			DESCRIPTION
				"Upper threshold of the environment temperature measurement, can be configured by users. Value range: 0 to 100, unit: centigrade (°„C), and the value is an integer (.0)."
			::= { hwEnvTempSensorEntry 7 }

		
		-- 1.3.6.1.4.1.2011.6.164.1.8.2.1.1.8
		hwSetEnvTempMeasureLowerLimit OBJECT-TYPE
			SYNTAX Integer32 (-50..0)
			UNITS "centigrades"
			MAX-ACCESS read-write
			STATUS current
			DESCRIPTION
				"Lower threshold of the environment temperature measurement, can be configured by users. Value range: -50 to 0, unit: centigrade (°„C), and the value is an integer (.0)."
			::= { hwEnvTempSensorEntry 8 }

		
		-- 1.3.6.1.4.1.2011.6.164.1.8.2.1.1.9
		hwSetEnvTempAlarmEnable OBJECT-TYPE
			SYNTAX INTEGER
				{
				enable(1),
				disable(2)
				}
			MAX-ACCESS read-write
			STATUS current
			DESCRIPTION
				"Environment temperature alarm. It is an enumeration type:
				If the enumeration value is 1, enable the alarm of the environment temperature; 
				If the enumeration value is 2, disable the alarm of the environment temperature. "
			::= { hwEnvTempSensorEntry 9 }

		
		-- 1.3.6.1.4.1.2011.6.164.1.8.2.1.1.99
		hwEnvTempSensorOperStatus OBJECT-TYPE
			SYNTAX INTEGER
				{
				normal(1),
				tempHigh(2),
				tempLow(3),
				notInslot(4),
				alarmResume(254),
				other(255)
				}
			MAX-ACCESS read-only
			STATUS current
			DESCRIPTION
				"State of the site environment temperature sensor. It is an enumeration type: 
				If the enumeration value is 1, it indicates that the site environment temperature sensor is in the normal state; 
				If the enumeration value is 2, it indicates that the environment temperature sensor is over temperature; 
				If the enumeration value is 3, it indicates that the environment temperature sensor is under temperature; 
				If the enumeration value is 4, it indicates that the environment temperature sensor is not in slot;
				If the enumeration value is 254, it indicates that environment temperature alarm resume; 
				If the enumeration value is 255, it indicates environment temperature sensor operation status unknown. 
				
				"
			::= { hwEnvTempSensorEntry 99 }

		
		-- 1.3.6.1.4.1.2011.6.164.1.8.2.1.1.100
		hwEnvTempSensorRowStatus OBJECT-TYPE
			SYNTAX RowStatus
			MAX-ACCESS read-create
			STATUS current
			DESCRIPTION
				"RowStatus of Environment temperature table."
			::= { hwEnvTempSensorEntry 100 }

		
		-- 1.3.6.1.4.1.2011.6.164.1.8.2.2
		hwEnvHumiSensorTable OBJECT-TYPE
			SYNTAX SEQUENCE OF HwEnvHumiSensorEntry
			MAX-ACCESS not-accessible
			STATUS current
			DESCRIPTION
				"Environment humidity table. Use this table to get environment humidity equipment ID , environment humidity equipment name, and environment humidity, set environment humidity upper limit, environment humidity lower limit, and environment humidity alarm enable. This table's index is hwEnvHumiSensorIndex, which qualificated by hwEnvHumiSensorIndex, clone site environment humidity table."
			::= { hwEnvSensor 2 }

		
		-- 1.3.6.1.4.1.2011.6.164.1.8.2.2.1
		hwEnvHumiSensorEntry OBJECT-TYPE
			SYNTAX HwEnvHumiSensorEntry
			MAX-ACCESS not-accessible
			STATUS current
			DESCRIPTION
				"Environment humidity table entry."
			INDEX { hwEnvHumiSensorIndex }
			::= { hwEnvHumiSensorTable 1 }

		
		HwEnvHumiSensorEntry ::=
			SEQUENCE { 
				hwEnvHumiSensorIndex
					Integer32,
				hwEnvHumiEquipId
					Unsigned32,
				hwEnvHumiEquipName
					OCTET STRING,
				hwEnvHumidity
					Integer32,
				hwSetEnvHumidityUpperLimit
					Integer32,
				hwSetEnvHumidityLowerLimit
					Integer32,
				hwSetEnvHumidityMeasureUpperLimit
					Integer32,
				hwSetEnvHumidityMeasureLowerLimit
					Integer32,
				hwSetEnvHumiAlarmEnable
					INTEGER,
				hwEnvHumiSensorOperStatus
					INTEGER,
				hwEnvHumiSensorRowStatus
					RowStatus
			 }

		-- 1.3.6.1.4.1.2011.6.164.1.8.2.2.1.1
		hwEnvHumiSensorIndex OBJECT-TYPE
			SYNTAX Integer32 (1..256)
			MAX-ACCESS read-only
			STATUS current
			DESCRIPTION
				"Table index of the environment humility sensors. Value range: 1 to 256. Lines of the device list are restricted by the quantity of environment humility sensors (hwEnvHumiSensorsTotalQuantity). "
			::= { hwEnvHumiSensorEntry 1 }

		
		-- 1.3.6.1.4.1.2011.6.164.1.8.2.2.1.2
		hwEnvHumiEquipId OBJECT-TYPE
			SYNTAX Unsigned32 (10001..10255)
			MAX-ACCESS read-only
			STATUS current
			DESCRIPTION
				"Environment humility sensor ID, can be configured by users. Value range: 010'001 to 010'255, in which the first digits indicate the device type and the last three digits indicate the device SN."
			::= { hwEnvHumiSensorEntry 2 }

		
		-- 1.3.6.1.4.1.2011.6.164.1.8.2.2.1.3
		hwEnvHumiEquipName OBJECT-TYPE
			SYNTAX OCTET STRING (SIZE (0..63))
			MAX-ACCESS read-write
			STATUS current
			DESCRIPTION
				"Environment humility sensor name, of the character string type, is used to specify an environment humility sensor. Users can configure it.
				Otherwise, the configured character can not be any other languages except English. "
			::= { hwEnvHumiSensorEntry 3 }

		
		-- 1.3.6.1.4.1.2011.6.164.1.8.2.2.1.4
		hwEnvHumidity OBJECT-TYPE
			SYNTAX Integer32 (0..100)
			UNITS "%RH"
			MAX-ACCESS read-only
			STATUS current
			DESCRIPTION
				"Environment humility. It is an environment parameter collected in real time. Value range: 0 to 100, unit: %RH, and the value is an integer (.0).
				If the value is 255, it indicates that the humidity sensor is not configured."
			::= { hwEnvHumiSensorEntry 4 }

		
		-- 1.3.6.1.4.1.2011.6.164.1.8.2.2.1.5
		hwSetEnvHumidityUpperLimit OBJECT-TYPE
			SYNTAX Integer32 (0..100)
			UNITS "%RH"
			MAX-ACCESS read-write
			STATUS current
			DESCRIPTION
				"Upper threshold of the environment humility alarm, can be configured by users. Value range: 0 to 100, unit: %RH, and the value is an integer (.0)."
			::= { hwEnvHumiSensorEntry 5 }

		
		-- 1.3.6.1.4.1.2011.6.164.1.8.2.2.1.6
		hwSetEnvHumidityLowerLimit OBJECT-TYPE
			SYNTAX Integer32 (0..100)
			UNITS "%RH"
			MAX-ACCESS read-write
			STATUS current
			DESCRIPTION
				"Lower threshold of the environment humility alarm, can be configured by users. Value range: 0 to 100, unit: %RH, and the value is an integer (.0)."
			::= { hwEnvHumiSensorEntry 6 }

		
		-- 1.3.6.1.4.1.2011.6.164.1.8.2.2.1.7
		hwSetEnvHumidityMeasureUpperLimit OBJECT-TYPE
			SYNTAX Integer32 (0..100)
			UNITS "%RH"
			MAX-ACCESS read-write
			STATUS current
			DESCRIPTION
				"Upper threshold of the environment humility measurement, can be configured by users. Value range: 0 to 100, unit: %RH, and the value is an integer (.0)."
			::= { hwEnvHumiSensorEntry 7 }

		
		-- 1.3.6.1.4.1.2011.6.164.1.8.2.2.1.8
		hwSetEnvHumidityMeasureLowerLimit OBJECT-TYPE
			SYNTAX Integer32 (0..100)
			UNITS "%RH"
			MAX-ACCESS read-write
			STATUS current
			DESCRIPTION
				"Lower threshold of the environment humility measurement, can be configured by users. Value range: 0 to 100, unit: %RH, and the value is an integer (.0)."
			::= { hwEnvHumiSensorEntry 8 }

		
		-- 1.3.6.1.4.1.2011.6.164.1.8.2.2.1.9
		hwSetEnvHumiAlarmEnable OBJECT-TYPE
			SYNTAX INTEGER
				{
				enable(1),
				disable(2)
				}
			MAX-ACCESS read-write
			STATUS current
			DESCRIPTION
				"Environment humility alarm. It is an enumeration type:
				If the enumeration value is 1, enable the alarm of the environment humility; 
				If the enumeration value is 2, disable the alarm of the environment humility. 
				The environment humility alarm is enabled by default. "
			::= { hwEnvHumiSensorEntry 9 }

		
		-- 1.3.6.1.4.1.2011.6.164.1.8.2.2.1.99
		hwEnvHumiSensorOperStatus OBJECT-TYPE
			SYNTAX INTEGER
				{
				normal(1),
				humidityHigh(2),
				humidityLow(3),
				notInslot(4),
				alarmResume(254),
				other(255)
				}
			MAX-ACCESS read-only
			STATUS current
			DESCRIPTION
				"State of the site environment humidity sensor. It is an enumeration type: 
				If the enumeration value is 1, it indicates that the site environment humidity sensor is in the normal state; 
				If the enumeration value is 2, it indicates that the environment humidity sensor is over humidity; 
				If the enumeration value is 3, it indicates that the environment humidity sensor is under humidity;
				If the enumeration value is 4, it indicates that the environment humidity sensor is not in slot;
				If the enumeration value is 254, it indicates that environment humidity alarm resume;   
				If the enumeration value is 255, it indicates environment humidity sensor operation status unknown.  "
			::= { hwEnvHumiSensorEntry 99 }

		
		-- 1.3.6.1.4.1.2011.6.164.1.8.2.2.1.100
		hwEnvHumiSensorRowStatus OBJECT-TYPE
			SYNTAX RowStatus
			MAX-ACCESS read-create
			STATUS current
			DESCRIPTION
				"RowStatus of Environment humidity table."
			::= { hwEnvHumiSensorEntry 100 }

		
		-- 1.3.6.1.4.1.2011.6.164.1.8.2.3
		hwSpareDigitalTable OBJECT-TYPE
			SYNTAX SEQUENCE OF HwSpareDigitalEntry
			MAX-ACCESS not-accessible
			STATUS current
			DESCRIPTION
				"Spare digital table. Use this table to get Spare digital equipment ID , Spare digital equipment name, and current Spare digital alarm tension, ae well as to set Spare digital alarm enable. This table's index is hwSpareDigitalIndex, which qualificated by hwSpareDigitalsTotalQuantity, clone switch input table."
			::= { hwEnvSensor 3 }

		
		-- 1.3.6.1.4.1.2011.6.164.1.8.2.3.1
		hwSpareDigitalEntry OBJECT-TYPE
			SYNTAX HwSpareDigitalEntry
			MAX-ACCESS not-accessible
			STATUS current
			DESCRIPTION
				"Spare digital table entry."
			INDEX { hwSpareDigitalIndex }
			::= { hwSpareDigitalTable 1 }

		
		HwSpareDigitalEntry ::=
			SEQUENCE { 
				hwSpareDigitalIndex
					Integer32,
				hwSpareDigitalEquipId
					Unsigned32,
				hwSpareDigitalEquipName
					OCTET STRING,
				hwSetSpareDigitalAlarmTension
					INTEGER,
				hwSetSpareDigitalAlarmEnable
					INTEGER,
				hwSpareDigitalOperStatus
					INTEGER,
				hwSpareDigitalRowStatus
					RowStatus
			 }

		-- 1.3.6.1.4.1.2011.6.164.1.8.2.3.1.1
		hwSpareDigitalIndex OBJECT-TYPE
			SYNTAX Integer32 (1..256)
			MAX-ACCESS read-only
			STATUS current
			DESCRIPTION
				"Spare digital table index, which value range: 1 to 256. Lines of the device list are restricted by the quantity of Spare digitals (hwSpareDigitalsTotalQuantity). "
			::= { hwSpareDigitalEntry 1 }

		
		-- 1.3.6.1.4.1.2011.6.164.1.8.2.3.1.2
		hwSpareDigitalEquipId OBJECT-TYPE
			SYNTAX Unsigned32 (11001..11255)
			MAX-ACCESS read-only
			STATUS current
			DESCRIPTION
				"Spare digital device ID. Value range: 011'001 to 011'255, in which the first digits indicate the device type and the last three digits indicate the device SN. "
			::= { hwSpareDigitalEntry 2 }

		
		-- 1.3.6.1.4.1.2011.6.164.1.8.2.3.1.3
		hwSpareDigitalEquipName OBJECT-TYPE
			SYNTAX OCTET STRING (SIZE (0..63))
			MAX-ACCESS read-write
			STATUS current
			DESCRIPTION
				"Spare digital name, of the character string type, is used to specify Spare digitals. Users can configure it.
				Otherwise, the configured character can not be any other languages except English. "
			::= { hwSpareDigitalEntry 3 }

		
		-- 1.3.6.1.4.1.2011.6.164.1.8.2.3.1.4
		hwSetSpareDigitalAlarmTension OBJECT-TYPE
			SYNTAX INTEGER
				{
				low(0),
				high(1)
				}
			MAX-ACCESS read-write
			STATUS current
			DESCRIPTION
				"Spare digital alarm state. It is an enumeration value.  
				If the value of the node is 0, it indicates a low-tension alarm;
				If the value of the node is 1, it indicates a high-tension alarm. "
			::= { hwSpareDigitalEntry 4 }

		
		-- 1.3.6.1.4.1.2011.6.164.1.8.2.3.1.5
		hwSetSpareDigitalAlarmEnable OBJECT-TYPE
			SYNTAX INTEGER
				{
				enable(1),
				disable(2)
				}
			MAX-ACCESS read-write
			STATUS current
			DESCRIPTION
				"Spare digital alarm enabling. It is an enumeration type: 
				If the enumeration value is 1, it means to enable the alarm; 
				If the enumeration value is 2, it means to disable the alarm. "
			::= { hwSpareDigitalEntry 5 }

		
		-- 1.3.6.1.4.1.2011.6.164.1.8.2.3.1.99
		hwSpareDigitalOperStatus OBJECT-TYPE
			SYNTAX INTEGER
				{
				normal(1),
				alarm(2),
				alarmResume(254),
				other(255)
				}
			MAX-ACCESS read-only
			STATUS current
			DESCRIPTION
				"State of the site Spare digital. It is an enumeration type: 
				If the enumeration value is 1, it indicates that the Spare digital operation state is normal; 
				If the enumeration value is 2, it indicates that a alarm occurs on the Spare digital;  
				If the enumeration value is 254, it indicates that spare digital alarm resume;  
				If the enumeration value is 255, it indicates Spare digital operation status unknown."
			::= { hwSpareDigitalEntry 99 }

		
		-- 1.3.6.1.4.1.2011.6.164.1.8.2.3.1.100
		hwSpareDigitalRowStatus OBJECT-TYPE
			SYNTAX RowStatus
			MAX-ACCESS read-create
			STATUS current
			DESCRIPTION
				"RowStatus of Spare digital device table."
			::= { hwSpareDigitalEntry 100 }
					

		-- 1.3.6.1.4.1.2011.6.164.1.9
		hwSitePDEs OBJECT IDENTIFIER ::= { hwSiteMonitorMIBObjects 9 }
		

		-- 1.3.6.1.4.1.2011.6.164.1.9.1
		hwPDEGroup OBJECT IDENTIFIER ::= { hwSitePDEs 1 }
		

		-- 1.3.6.1.4.1.2011.6.164.1.9.1.1
		hwPDEGroupId OBJECT-TYPE
			SYNTAX Unsigned32 (12000..12255)
			MAX-ACCESS read-only
			STATUS current
			DESCRIPTION
				"PDE unit group ID. It is the unique ID of the PDE unit group. The first digits indicate the device type. The last three digits indicate the device SN. If the last three digits are 000, it indicates a virtual device."
			::= { hwPDEGroup 1 }
		

		-- 1.3.6.1.4.1.2011.6.164.1.9.1.2
		hwPDEGroupName OBJECT-TYPE
			SYNTAX OCTET STRING (SIZE (0..64))
			MAX-ACCESS read-write
			STATUS current
			DESCRIPTION
				"PDE unit group name, of the character string type, can be configured by users.
				Otherwise, the configured character can not be any other languages except English."
			::= { hwPDEGroup 2 }
		

		-- 1.3.6.1.4.1.2011.6.164.1.9.1.3
		hwPDEGroupNum OBJECT-TYPE
			SYNTAX Unsigned32 (0..100)
			MAX-ACCESS read-only
			STATUS current
			DESCRIPTION
				"PDE Num,Value range: 0 to 100."
			::= { hwPDEGroup 3 }
		

		-- 1.3.6.1.4.1.2011.6.164.1.9.1.4
		hwPDEGroupCommNum OBJECT-TYPE
			SYNTAX Unsigned32 (0..100)
			MAX-ACCESS read-only
			STATUS current
			DESCRIPTION
				"Communication PDE Num,Value range: 0 to 100."
			::= { hwPDEGroup 4 }
		

		-- 1.3.6.1.4.1.2011.6.164.1.9.1.5
		hwPDEGroupTotalPower OBJECT-TYPE
			SYNTAX Unsigned32 (0..100000)
			UNITS "W"
			MAX-ACCESS read-only
			STATUS current
			DESCRIPTION
				"PDE Total Power,Value range: 0.0 to 10000.0.Unit: W.and the value is accurate to one decimal space (.1)."
			::= { hwPDEGroup 5 }
		

		-- 1.3.6.1.4.1.2011.6.164.1.9.1.6
		hwPDEGroupTotalCurrent OBJECT-TYPE
			SYNTAX Unsigned32 (0..3000)
			UNITS "A"
			MAX-ACCESS read-only
			STATUS current
			DESCRIPTION
				"PDE Total Current,Value range: 0.0 to 300.0.Unit: A.and the value is accurate to one decimal space (.1)."
			::= { hwPDEGroup 6 }
		

		-- 1.3.6.1.4.1.2011.6.164.1.9.1.7
		hwPDEGroupCommStatus OBJECT-TYPE
			SYNTAX INTEGER
				{
				commOk(1),
				commFail(2),
				unknown(255)
				}
			MAX-ACCESS read-only
			STATUS current
			DESCRIPTION
				"PDE Communication Status. It is an enumeration type: 
				If the enumeration value is 1, it indicates that communication is normal; 
				If the enumeration value is 2, it indicates that communication is abnormal. 
				If the enumeration value is 255, it indicates that communication is unknown."
			::= { hwPDEGroup 7 }
		

		-- 1.3.6.1.4.1.2011.6.164.1.9.3
		hwPDE OBJECT IDENTIFIER ::= { hwSitePDEs 3 }
		

		-- 1.3.6.1.4.1.2011.6.164.1.9.3.1
		hwPDETable OBJECT-TYPE
			SYNTAX SEQUENCE OF HwPDEEntry
			MAX-ACCESS not-accessible
			STATUS current
			DESCRIPTION
				"PDE table. Use this table to get PDE equipment ID , PDE equipment name, and current PDE status. This table's index is hwPDEIndex."
			::= { hwPDE 1 }
		

		-- 1.3.6.1.4.1.2011.6.164.1.9.3.1.1
		hwPDEEntry OBJECT-TYPE
			SYNTAX HwPDEEntry
			MAX-ACCESS not-accessible
			STATUS current
			DESCRIPTION
				"PDE table entry."
			INDEX { hwPDEIndex }
			::= { hwPDETable 1 }
		
		HwPDEEntry ::=
			SEQUENCE { 
				hwPDEIndex
					Integer32,
				hwPDEEquipId
					Unsigned32,
				hwPDEEquipName
					OCTET STRING,
				hwPDETotalRunningTime
					Unsigned32,
				hwPDEBranchNum
					Unsigned32,
				hwPDETotalPower
					Unsigned32,
				hwPDETotalCurrent
					Unsigned32,
				hwPDEBranch1Power
					Unsigned32,
				hwPDEBranch2Power
					Unsigned32,
				hwPDEBranch3Power
					Unsigned32,
				hwPDEBranch4Power
					Unsigned32,
				hwPDEBranch1Current
					Unsigned32,
				hwPDEBranch2Current
					Unsigned32,
				hwPDEBranch3Current
					Unsigned32,
				hwPDEBranch4Current
					Unsigned32,
				hwPDEBranch1Voltage
					Unsigned32,
				hwPDEBranch2Voltage
					Unsigned32,
				hwPDEBranch3Voltage
					Unsigned32,
				hwPDEBranch4Voltage
					Unsigned32,
				hwPDEBranch1Temperature
					Unsigned32,
				hwPDEBranch2Temperature
					Unsigned32,
				hwPDEBranch3Temperature
					Unsigned32,
				hwPDEBranch4Temperature
					Unsigned32,
				hwPDEOperStatus
					INTEGER,
				hwPDERowStatus
					RowStatus
			 }


		-- 1.3.6.1.4.1.2011.6.164.1.9.3.1.1.1
		hwPDEIndex OBJECT-TYPE
			SYNTAX Integer32 (1..10)
			MAX-ACCESS read-only
			STATUS current
			DESCRIPTION
				"PDE table index, which value range: 1 to 10. Lines of the device list are restricted by the quantity of PDE. "
			::= { hwPDEEntry 1 }

		-- 1.3.6.1.4.1.2011.6.164.1.9.3.1.1.2
		hwPDEEquipId OBJECT-TYPE
			SYNTAX Unsigned32 (12001..12255)
			MAX-ACCESS read-only
			STATUS current
			DESCRIPTION
				"PDE device ID. Value range: 012'001 to 012'255, in which the first digits indicate the device type and the last three digits indicate the device SN. "
			::= { hwPDEEntry 2 }
		

		-- 1.3.6.1.4.1.2011.6.164.1.9.3.1.1.3
		hwPDEEquipName OBJECT-TYPE
			SYNTAX OCTET STRING (SIZE (0..64))
			MAX-ACCESS read-write
			STATUS current
			DESCRIPTION
				"PDE name, of the character string type, is used to specify PDEs. Users can configure it.
				Otherwise, the configured character can not be any other languages except English. "
			::= { hwPDEEntry 3 }
		

		-- 1.3.6.1.4.1.2011.6.164.1.9.3.1.1.4
		hwPDETotalRunningTime OBJECT-TYPE
			SYNTAX Unsigned32 (0..876000)
			UNITS "H"
			MAX-ACCESS read-only
			STATUS current
			DESCRIPTION
				"PDE Total Running Time,Value range: 0 to 876000.Unit: H."
			::= { hwPDEEntry 4 }
		

		-- 1.3.6.1.4.1.2011.6.164.1.9.3.1.1.5
		hwPDEBranchNum OBJECT-TYPE
			SYNTAX Unsigned32 (0..6)
			MAX-ACCESS read-only
			STATUS current
			DESCRIPTION
				"PDE Branch Number,Value range: 0 to 6."
			::= { hwPDEEntry 5 }
		

		-- 1.3.6.1.4.1.2011.6.164.1.9.3.1.1.6
		hwPDETotalPower OBJECT-TYPE
			SYNTAX Unsigned32 (0..100000)
			UNITS "W"
			MAX-ACCESS read-only
			STATUS current
			DESCRIPTION
				"PDE Total Power,Value range: 0.0 to 10000.0.Unit: W.and the value is accurate to one decimal space (.1)."
			::= { hwPDEEntry 6 }
		

		-- 1.3.6.1.4.1.2011.6.164.1.9.3.1.1.7
		hwPDETotalCurrent OBJECT-TYPE
			SYNTAX Unsigned32 (0..300000)
			UNITS "A"
			MAX-ACCESS read-only
			STATUS current
			DESCRIPTION
				"PDE Total Current,Value range: 0.0 to 30000.0.Unit: A.and the value is accurate to one decimal space (.1)."
			::= { hwPDEEntry 7 }
		

		-- 1.3.6.1.4.1.2011.6.164.1.9.3.1.1.8
		hwPDEBranch1Power OBJECT-TYPE
			SYNTAX Unsigned32 (0..1000000)
			UNITS "W"
			MAX-ACCESS read-only
			STATUS current
			DESCRIPTION
				"PDE Branch1 Power,Value range: 0.0 to 100000.0.Unit: W.and the value is accurate to one decimal space (.1)."
			::= { hwPDEEntry 8 }
		

		-- 1.3.6.1.4.1.2011.6.164.1.9.3.1.1.9
		hwPDEBranch2Power OBJECT-TYPE
			SYNTAX Unsigned32 (0..1000000)
			UNITS "W"
			MAX-ACCESS read-only
			STATUS current
			DESCRIPTION
				"PDE Branch2 Power,Value range: 0.0 to 100000.0.Unit: W.and the value is accurate to one decimal space (.1)."
			::= { hwPDEEntry 9 }
		

		-- 1.3.6.1.4.1.2011.6.164.1.9.3.1.1.10
		hwPDEBranch3Power OBJECT-TYPE
			SYNTAX Unsigned32 (0..1000000)
			UNITS "W"
			MAX-ACCESS read-only
			STATUS current
			DESCRIPTION
				"PDE Branch3 Power,Value range: 0.0 to 100000.0.Unit: W.and the value is accurate to one decimal space (.1)."
			::= { hwPDEEntry 10 }
		

		-- 1.3.6.1.4.1.2011.6.164.1.9.3.1.1.11
		hwPDEBranch4Power OBJECT-TYPE
			SYNTAX Unsigned32 (0..1000000)
			UNITS "W"
			MAX-ACCESS read-only
			STATUS current
			DESCRIPTION
				"PDE Branch4 Power,Value range: 0.0 to 100000.0.Unit: W.and the value is accurate to one decimal space (.1)."
			::= { hwPDEEntry 11 }
		

		-- 1.3.6.1.4.1.2011.6.164.1.9.3.1.1.12
		hwPDEBranch1Current OBJECT-TYPE
			SYNTAX Unsigned32 (0..10000)
			UNITS "A"
			MAX-ACCESS read-only
			STATUS current
			DESCRIPTION
				"PDE Branch1 Current,Value range: 0.0 to 1000.0.Unit: A.and the value is accurate to one decimal space (.1)."
			::= { hwPDEEntry 12 }
		

		-- 1.3.6.1.4.1.2011.6.164.1.9.3.1.1.13
		hwPDEBranch2Current OBJECT-TYPE
			SYNTAX Unsigned32 (0..10000)
			UNITS "A"
			MAX-ACCESS read-only
			STATUS current
			DESCRIPTION
				"PDE Branch2 Current,Value range: 0.0 to 1000.0.Unit: A.and the value is accurate to one decimal space (.1)."
			::= { hwPDEEntry 13 }
		

		-- 1.3.6.1.4.1.2011.6.164.1.9.3.1.1.14
		hwPDEBranch3Current OBJECT-TYPE
			SYNTAX Unsigned32 (0..10000)
			UNITS "A"
			MAX-ACCESS read-only
			STATUS current
			DESCRIPTION
				"PDE Branch3 Current,Value range: 0.0 to 1000.0.Unit: A.and the value is accurate to one decimal space (.1)."
			::= { hwPDEEntry 14 }
		

		-- 1.3.6.1.4.1.2011.6.164.1.9.3.1.1.15
		hwPDEBranch4Current OBJECT-TYPE
			SYNTAX Unsigned32 (0..10000)
			UNITS "A"
			MAX-ACCESS read-only
			STATUS current
			DESCRIPTION
				"PDE Branch4 Current,Value range: 0.0 to 1000.0.Unit: A.and the value is accurate to one decimal space (.1)."
			::= { hwPDEEntry 15 }
		

		-- 1.3.6.1.4.1.2011.6.164.1.9.3.1.1.16
		hwPDEBranch1Voltage OBJECT-TYPE
			SYNTAX Unsigned32 (0..650)
			UNITS "V"
			MAX-ACCESS read-only
			STATUS current
			DESCRIPTION
				"PDE Branch1 Voltage,Value range: 0.0 to 65.0.Unit: V.and the value is accurate to one decimal space (.1)."
			::= { hwPDEEntry 16 }
		

		-- 1.3.6.1.4.1.2011.6.164.1.9.3.1.1.17
		hwPDEBranch2Voltage OBJECT-TYPE
			SYNTAX Unsigned32 (0..650)
			UNITS "V"
			MAX-ACCESS read-only
			STATUS current
			DESCRIPTION
				"PDE Branch2 Voltage,Value range: 0.0 to 65.0.Unit: V.and the value is accurate to one decimal space (.1)."
			::= { hwPDEEntry 17 }
		

		-- 1.3.6.1.4.1.2011.6.164.1.9.3.1.1.18
		hwPDEBranch3Voltage OBJECT-TYPE
			SYNTAX Unsigned32 (0..650)
			UNITS "V"
			MAX-ACCESS read-only
			STATUS current
			DESCRIPTION
				"PDE Branch3 Voltage,Value range: 0.0 to 65.0.Unit: V.and the value is accurate to one decimal space (.1)."
			::= { hwPDEEntry 18 }
		

		-- 1.3.6.1.4.1.2011.6.164.1.9.3.1.1.19
		hwPDEBranch4Voltage OBJECT-TYPE
			SYNTAX Unsigned32 (0..650)
			UNITS "V"
			MAX-ACCESS read-only
			STATUS current
			DESCRIPTION
				"PDE Branch4 Voltage,Value range: 0.0 to 65.0.Unit: V.and the value is accurate to one decimal space (.1)."
			::= { hwPDEEntry 19 }
		

		-- 1.3.6.1.4.1.2011.6.164.1.9.3.1.1.20
		hwPDEBranch1Temperature OBJECT-TYPE
			SYNTAX Unsigned32 (0..300)
			UNITS "deg"
			MAX-ACCESS read-only
			STATUS current
			DESCRIPTION
				"PDE Branch1 Temperature,Value range: 0 to 300.Unit: deg."
			::= { hwPDEEntry 20 }
		

		-- 1.3.6.1.4.1.2011.6.164.1.9.3.1.1.21
		hwPDEBranch2Temperature OBJECT-TYPE
			SYNTAX Unsigned32 (0..300)
			UNITS "deg"
			MAX-ACCESS read-only
			STATUS current
			DESCRIPTION
				"PDE Branch2 Temperature,Value range: 0 to 300.Unit: deg."
			::= { hwPDEEntry 21 }
		

		-- 1.3.6.1.4.1.2011.6.164.1.9.3.1.1.22
		hwPDEBranch3Temperature OBJECT-TYPE
			SYNTAX Unsigned32 (0..300)
			UNITS "deg"
			MAX-ACCESS read-only
			STATUS current
			DESCRIPTION
				"PDE Branch3 Temperature,Value range: 0 to 300.Unit: deg."
			::= { hwPDEEntry 22 }
		

		-- 1.3.6.1.4.1.2011.6.164.1.9.3.1.1.23
		hwPDEBranch4Temperature OBJECT-TYPE
			SYNTAX Unsigned32 (0..300)
			UNITS "deg"
			MAX-ACCESS read-only
			STATUS current
			DESCRIPTION
				"PDE Branch4 Temperature,Value range: 0 to 300.Unit: deg."
			::= { hwPDEEntry 23 }
		

		-- 1.3.6.1.4.1.2011.6.164.1.9.3.1.1.24
		hwPDEOperStatus OBJECT-TYPE
			SYNTAX INTEGER
				{
				normal(1),
				alarm(2),
				alarmResume(254),
				unknown(255)
				}
			MAX-ACCESS read-only
			STATUS current
			DESCRIPTION
				"State of the PDE. It is an enumeration type: 
				If the enumeration value is 1, it indicates that the PDE is in the normal state;
				If the enumeration value is 2, it indicates that the PDE is in the alarm state;  
				If the enumeration value is 254, it indicates that the PDE is in the resume state;   
				If the enumeration value is 255, it indicates PDE operation status unknown. "
			::= { hwPDEEntry 24 }
		

		-- 1.3.6.1.4.1.2011.6.164.1.9.3.1.1.100
		hwPDERowStatus OBJECT-TYPE
			SYNTAX RowStatus
			MAX-ACCESS read-create
			STATUS current
			DESCRIPTION
				"RowStatus of PDE table."
			::= { hwPDEEntry 100 }
		

		-- 1.3.6.1.4.1.2011.6.164.1.9.3.2
		hwPDEConfigTable OBJECT-TYPE
			SYNTAX SEQUENCE OF HwPDEConfigEntry
			MAX-ACCESS not-accessible
			STATUS current
			DESCRIPTION
				"PDE Config table. Use this table to get PDE equipment ID , PDE equipment name, and current PDE config parameter. This table's index is hwPDEConfigIndex."
			::= { hwPDE 2 }
		

		-- 1.3.6.1.4.1.2011.6.164.1.9.3.2.1
		hwPDEConfigEntry OBJECT-TYPE
			SYNTAX HwPDEConfigEntry
			MAX-ACCESS not-accessible
			STATUS current
			DESCRIPTION
				"PDE Config table entry."
			INDEX { hwPDEConfigIndex }
			::= { hwPDEConfigTable 1 }
		
		HwPDEConfigEntry ::=
			SEQUENCE { 
				hwPDEConfigIndex
					Integer32,
				hwPDEConfigEquipId
					Unsigned32,
				hwPDEConfigEquipName
					OCTET STRING,
				hwPDEOverTempProtect
					Unsigned32,
				hwPDEVolProtectEnable
					INTEGER,
				hwPDEOverVoltageProtect
					Unsigned32,
				hwPDEUnderVoltageProtect
					Unsigned32,
				hwPDEHysteresis
					Unsigned32,
				hwPDEReset
					INTEGER,
				hwPDEBranch1Control
					INTEGER,
				hwPDEBranch2Control
					INTEGER,
				hwPDEBranch3Control
					INTEGER,
				hwPDEBranch4Control
					INTEGER,
				hwPDEBranch1CurrentLimit
					Unsigned32,
				hwPDEBranch2CurrentLimit
					Unsigned32,
				hwPDEBranch3CurrentLimit
					Unsigned32,
				hwPDEBranch4CurrentLimit
					Unsigned32,
				hwPDEConfigRowStatus
					RowStatus
			 }


		-- 1.3.6.1.4.1.2011.6.164.1.9.3.2.1.1
		hwPDEConfigIndex OBJECT-TYPE
			SYNTAX Integer32 (1..10)
			MAX-ACCESS read-only
			STATUS current
			DESCRIPTION
				"PDE Config table index, which value range: 1 to 10. Lines of the device list are restricted by the quantity of PDE. "
			::= { hwPDEConfigEntry 1 }
		

		-- 1.3.6.1.4.1.2011.6.164.1.9.3.2.1.2
		hwPDEConfigEquipId OBJECT-TYPE
			SYNTAX Unsigned32 (12001..12255)
			MAX-ACCESS read-only
			STATUS current
			DESCRIPTION
				"PDE device ID. Value range: 012'001 to 012'255, in which the first digits indicate the device type and the last three digits indicate the device SN. "
			::= { hwPDEConfigEntry 2 }

		-- 1.3.6.1.4.1.2011.6.164.1.9.3.2.1.3
		hwPDEConfigEquipName OBJECT-TYPE
			SYNTAX OCTET STRING (SIZE (0..64))
			MAX-ACCESS read-write
			STATUS current
			DESCRIPTION
				"PDE name, of the character string type, is used to specify PDEs. Users can configure it.
				Otherwise, the configured character can not be any other languages except English. "
			::= { hwPDEConfigEntry 3 }
		

		-- 1.3.6.1.4.1.2011.6.164.1.9.3.2.1.4
		hwPDEOverTempProtect OBJECT-TYPE
			SYNTAX Unsigned32 (100..120)
			UNITS "deg"
			MAX-ACCESS read-write
			STATUS current
			DESCRIPTION
				"PDE Over Temperature Protect,Value range: 100 to 120.Unit: deg."
			::= { hwPDEConfigEntry 4 }
		

		-- 1.3.6.1.4.1.2011.6.164.1.9.3.2.1.5
		hwPDEVolProtectEnable OBJECT-TYPE
			SYNTAX INTEGER
				{
				enable(1),
				disable(2),
				unknown(255)
				}
			MAX-ACCESS read-write
			STATUS current
			DESCRIPTION
				"PDE Over Protect Enable,It is an enumeration value, and users actively set it. 
				If the enumeration value is 1, it means to enable the PDE voltage protect; 
				If the enumeration value is 2, it means to disable the PDE voltage protect. "
			::= { hwPDEConfigEntry 5 }
		

		-- 1.3.6.1.4.1.2011.6.164.1.9.3.2.1.6
		hwPDEOverVoltageProtect OBJECT-TYPE
			SYNTAX Unsigned32 (58..60)
			UNITS "V"
			MAX-ACCESS read-write
			STATUS current
			DESCRIPTION
				"PDE Over Voltage Protect,Value range: 58 to 60.Unit: V."
			::= { hwPDEConfigEntry 6 }
		

		-- 1.3.6.1.4.1.2011.6.164.1.9.3.2.1.7
		hwPDEUnderVoltageProtect OBJECT-TYPE
			SYNTAX Unsigned32 (40..48)
			UNITS "V"
			MAX-ACCESS read-write
			STATUS current
			DESCRIPTION
				"PDE Under Voltage Protect,Value range: 40 to 48.Unit: V."
			::= { hwPDEConfigEntry 7 }
		

-- 1.3.6.1.4.1.2011.6.164.1.9.3.2.1.8
		-- 1.3.6.1.4.1.2011.6.164.1.9.3.2.1.8
		hwPDEHysteresis OBJECT-TYPE
			SYNTAX Unsigned32 (1..3)
			UNITS "V"
			MAX-ACCESS read-write
			STATUS current
			DESCRIPTION
				"PDE Hysteresis,Value range: 1 to 3.Unit: V."
			::= { hwPDEConfigEntry 8 }
		

		-- 1.3.6.1.4.1.2011.6.164.1.9.3.2.1.9
		hwPDEReset OBJECT-TYPE
			SYNTAX INTEGER
				{
				reset(1),
				unknown(255)
				}
			MAX-ACCESS read-write
			STATUS current
			DESCRIPTION
				"PDE Reset Control,It is an enumeration value, and users actively set it. 
				If the enumeration value is 1, it means to reset the PDE; "
			::= { hwPDEConfigEntry 9 }
		

		-- 1.3.6.1.4.1.2011.6.164.1.9.3.2.1.10
		hwPDEBranch1Control OBJECT-TYPE
			SYNTAX INTEGER
				{
				open(1),
				close(2),
				unknown(255)
				}
			MAX-ACCESS read-write
			STATUS current
			DESCRIPTION
				"PDE Branch1 Control,It is an enumeration value, and users actively set it. 
				If the enumeration value is 1, it means to open the branch1; 
				If the enumeration value is 2, it means to close the branch1; "
			::= { hwPDEConfigEntry 10 }
		

		-- 1.3.6.1.4.1.2011.6.164.1.9.3.2.1.11
		hwPDEBranch2Control OBJECT-TYPE
			SYNTAX INTEGER
				{
				open(1),
				close(2),
				unknown(255)
				}
			MAX-ACCESS read-write
			STATUS current
			DESCRIPTION
				"PDE Branch2 Control,It is an enumeration value, and users actively set it. 
				If the enumeration value is 1, it means to open the branch2; 
				If the enumeration value is 2, it means to close the branch2; "
			::= { hwPDEConfigEntry 11 }
		

		-- 1.3.6.1.4.1.2011.6.164.1.9.3.2.1.12
		hwPDEBranch3Control OBJECT-TYPE
			SYNTAX INTEGER
				{
				open(1),
				close(2),
				unknown(255)
				}
			MAX-ACCESS read-write
			STATUS current
			DESCRIPTION
				"PDE Branch3 Control,It is an enumeration value, and users actively set it. 
				If the enumeration value is 1, it means to open the branch3; 
				If the enumeration value is 2, it means to close the branch3; "
			::= { hwPDEConfigEntry 12 }
		

		-- 1.3.6.1.4.1.2011.6.164.1.9.3.2.1.13
		hwPDEBranch4Control OBJECT-TYPE
			SYNTAX INTEGER
				{
				open(1),
				close(2),
				unknown(255)
				}
			MAX-ACCESS read-write
			STATUS current
			DESCRIPTION
				"PDE Branch4 Control,It is an enumeration value, and users actively set it. 
				If the enumeration value is 1, it means to open the branch4; 
				If the enumeration value is 2, it means to close the branch4; "
			::= { hwPDEConfigEntry 13 }
		

		-- 1.3.6.1.4.1.2011.6.164.1.9.3.2.1.14
		hwPDEBranch1CurrentLimit OBJECT-TYPE
			SYNTAX Unsigned32 (1..20)
			UNITS "A"
			MAX-ACCESS read-write
			STATUS current
			DESCRIPTION
				"PDE Branch1 Current Limit,Value range: 1 to 20.Unit: A."
			::= { hwPDEConfigEntry 14 }
		

		-- 1.3.6.1.4.1.2011.6.164.1.9.3.2.1.15
		hwPDEBranch2CurrentLimit OBJECT-TYPE
			SYNTAX Unsigned32 (1..30)
			UNITS "A"
			MAX-ACCESS read-write
			STATUS current
			DESCRIPTION
				"PDE Branch2 Current Limit,Value range: 1 to 30.Unit: A."
			::= { hwPDEConfigEntry 15 }
		

		-- 1.3.6.1.4.1.2011.6.164.1.9.3.2.1.16
		hwPDEBranch3CurrentLimit OBJECT-TYPE
			SYNTAX Unsigned32 (1..30)
			UNITS "A"
			MAX-ACCESS read-write
			STATUS current
			DESCRIPTION
				"PDE Branch3 Current Limit,Value range: 1 to 30.Unit: A."
			::= { hwPDEConfigEntry 16 }
		

		-- 1.3.6.1.4.1.2011.6.164.1.9.3.2.1.17
		hwPDEBranch4CurrentLimit OBJECT-TYPE
			SYNTAX Unsigned32 (1..20)
			UNITS "A"
			MAX-ACCESS read-write
			STATUS current
			DESCRIPTION
				"PDE Branch4 Current Limit,Value range: 1 to 20.Unit: A."
			::= { hwPDEConfigEntry 17 }
		
		-- 1.3.6.1.4.1.2011.6.164.1.9.3.2.1.100
		hwPDEConfigRowStatus OBJECT-TYPE
			SYNTAX RowStatus
			MAX-ACCESS read-create
			STATUS current
			DESCRIPTION
				"RowStatus of PDE config table."
			::= { hwPDEConfigEntry 100 }

		
		-- 1.3.6.1.4.1.2011.6.164.2
		hwSiteMonitorMIBTraps OBJECT IDENTIFIER ::= { hwSiteMonitorMIB 2 }

		
		-- 1.3.6.1.4.1.2011.6.164.2.1
		hwSiteAlarmTraps OBJECT IDENTIFIER ::= { hwSiteMonitorMIBTraps 1 }

		
--  1.3.6.1.4.1.2011.6.1.7.1
		-- 1.3.6.1.4.1.2011.6.164.2.1.0
		hwSiteAlarmTrapsPrefix OBJECT IDENTIFIER ::= { hwSiteAlarmTraps 0 }

		
--  1.3.6.1.4.1.2011.6.1.7.1.9
		-- 1.3.6.1.4.1.2011.6.164.2.1.0.1
		hwRectifierFaultAlarmTraps NOTIFICATION-TYPE
			OBJECTS { hwAlarmTrapOrdinalNumber, hwAlarmText, hwAlarmLevel, hwAlarmSigDesc, hwSiteName, hwSiteAdminAddr,
				hwNetIdentifier, hwSiteDescription, hwRectEquipId, hwRectEquipName,hwRectOperStatus }
			STATUS current
			DESCRIPTION 
				"When rectifiers fault alarms happen, a alarm trap will be send. Its correlation binding parameters: Site ID, Site name, Site description, NE ID, Alarm name, Alarm single description, Alarm port description, Alarm severity, and Site alarm SN. Additionally, in order to identify the device, rectifier equipment ID and equipment name are also include in VB(variable bondings).  "
			::= { hwSiteAlarmTrapsPrefix 1 }

		
--  1.3.6.1.4.1.2011.6.1.7.1.10
		-- 1.3.6.1.4.1.2011.6.164.2.1.0.2
		hwRectifierFaultAlarmResumeTraps NOTIFICATION-TYPE
			OBJECTS { hwAlarmTrapOrdinalNumber, hwAlarmText, hwAlarmLevel, hwAlarmSigDesc, hwSiteName, hwSiteAdminAddr, 
				hwNetIdentifier, hwSiteDescription, hwRectEquipId, hwRectEquipName, hwRectOperStatus   }
			STATUS current
			DESCRIPTION 
				"Rectifier Fault alarm resolved.Its correlation binding parameters: Site ID, Site name, Site description, NE ID, Alarm name, Alarm single description, Alarm port description, Alarm severity, and Site alarm SN. Additionally, in order to identify the device, rectifier equipment ID and equipment name are also include in VB(variable bondings).  "
			::= { hwSiteAlarmTrapsPrefix 2 }

		
		-- 1.3.6.1.4.1.2011.6.164.2.1.0.3
		hwRectifierAbnormalAlarmTraps NOTIFICATION-TYPE
			OBJECTS { hwAlarmTrapOrdinalNumber, hwAlarmText, hwAlarmLevel,hwAlarmSigDesc,hwSiteName, hwSiteAdminAddr, 
			       hwNetIdentifier,hwSiteDescription,hwRectEquipId, hwRectEquipName, hwRectOperStatus   }
			STATUS current
			DESCRIPTION 
				"Rectifier abnormal alarm, because of communication failure, module protection, or turnoff. Its correlation binding parameters:  Site ID, Site name, Site description, NE ID, Alarm name, Alarm single description, Alarm port description, Alarm severity, and Site alarm SN. Additionally, in order to identify the device, rectifier equipment ID and equipment name are also include in VB(variable bondings).  "
			::= { hwSiteAlarmTrapsPrefix 3 }

		
		-- 1.3.6.1.4.1.2011.6.164.2.1.0.4
		hwRectifierAbnormalAlarmResumeTraps NOTIFICATION-TYPE
			OBJECTS { hwAlarmTrapOrdinalNumber,hwAlarmText,hwAlarmLevel, hwAlarmSigDesc,hwSiteName ,hwSiteAdminAddr ,
			 		hwNetIdentifier,hwSiteDescription,hwRectEquipId, hwRectEquipName, hwRectOperStatus  }
			STATUS current
			DESCRIPTION 
				"Rectifier abnormal alarm resume. Description.Its correlation binding parameters:  Site ID, Site name, Site description, NE ID, Alarm name, Alarm single description, Alarm port description, Alarm severity, and Site alarm SN. Additionally, in order to identify the device, rectifier equipment ID and equipment name are also include in VB(variable bondings).  "
			::= { hwSiteAlarmTrapsPrefix 4 }

		
		-- 1.3.6.1.4.1.2011.6.164.2.1.0.5
		hwBattLoopBreakAlarmTraps NOTIFICATION-TYPE
			OBJECTS { hwAlarmTrapOrdinalNumber,hwAlarmText,hwAlarmLevel,hwAlarmSigDesc,hwSiteName, hwSiteAdminAddr,
			   		hwNetIdentifier,hwSiteDescription, hwBattStringEquipId, hwBattStringEquipName, hwBattStringOperStatus }
			STATUS current
			DESCRIPTION 
				"Battery loop disconnect. Its correlation binding parameters:  Site ID, Site name, Site description, NE ID, Alarm name, Alarm single description, Alarm port description, Alarm severity, and Site alarm SN. Additionally, in order to identify the device, battery string equipment ID and equipment name are also include in VB(variable bondings).    "
			::= { hwSiteAlarmTrapsPrefix 5 }

		
		-- 1.3.6.1.4.1.2011.6.164.2.1.0.6
		hwBattLoopBreakAlarmResumeTraps NOTIFICATION-TYPE
			OBJECTS { hwAlarmTrapOrdinalNumber,hwAlarmText,hwAlarmLevel,hwAlarmSigDesc,hwSiteName, hwSiteAdminAddr,
			   		hwNetIdentifier,hwSiteDescription, hwBattStringEquipId,hwBattStringEquipName,  hwBattStringOperStatus }
			STATUS current
			DESCRIPTION 
				"Battery loop break alarm resume. Its correlation binding parameters:  Site ID, Site name, Site description, NE ID, Alarm name, Alarm single description, Alarm port description, Alarm severity, and Site alarm SN. Additionally, in order to identify the device, battery string equipment ID and equipment name are also include in VB(variable bondings).     "
			::= { hwSiteAlarmTrapsPrefix 6 }

		
		-- 1.3.6.1.4.1.2011.6.164.2.1.0.7
		hwBattLvdAlarmTraps NOTIFICATION-TYPE
			OBJECTS { hwAlarmTrapOrdinalNumber,hwAlarmText,hwAlarmLevel,hwAlarmSigDesc,hwSiteName,hwSiteAdminAddr,
					hwNetIdentifier,hwSiteDescription,hwLvdUnitEquipId, hwLvdUnitEquipName,hwLvdBranchOperStatus }
			STATUS current
			DESCRIPTION 
				"Battery disconnect for low voltage. Its correlation binding parameters:  Site ID, Site name, Site description, NE ID, Alarm name, Alarm single description, Alarm port description, Alarm severity, and Site alarm SN. Additionally, in order to identify the device, battery LVD unit equipment ID and equipment name are also include in VB(variable bondings). "
			::= { hwSiteAlarmTrapsPrefix 7 }

		
		-- 1.3.6.1.4.1.2011.6.164.2.1.0.8
		hwBattLvdAlarmResumeTraps NOTIFICATION-TYPE
			OBJECTS { hwAlarmTrapOrdinalNumber, hwAlarmText,hwAlarmLevel,hwAlarmSigDesc,hwSiteName,hwSiteAdminAddr,
					 hwNetIdentifier,hwSiteDescription,hwLvdUnitEquipId, hwLvdUnitEquipName, hwLvdBranchOperStatus }
			STATUS current
			DESCRIPTION 
				"Battery LVD alarm resume. Its correlation binding parameters:  Site ID, Site name, Site description, NE ID, Alarm name, Alarm single description, Alarm port description, Alarm severity, and Site alarm SN. Additionally, in order to identify the device, battery LVD unit equipment ID and equipment name are also include in VB(variable bondings).  "
			::= { hwSiteAlarmTrapsPrefix 8 }

		
		-- 1.3.6.1.4.1.2011.6.164.2.1.0.9
		hwBattOverCurrAlarmTraps NOTIFICATION-TYPE
			OBJECTS {  hwAlarmTrapOrdinalNumber,hwAlarmText,hwAlarmLevel,hwAlarmSigDesc,hwSiteName, hwSiteAdminAddr,
					 hwNetIdentifier,hwSiteDescription,hwBattStringEquipId, hwBattStringEquipName, hwBattStringOperStatus }
			STATUS current
			DESCRIPTION 
				"Batterys charge in over current. Its correlation binding parameters:  Site ID, Site name, Site description, NE ID, Alarm name, Alarm single description, Alarm port description, Alarm severity, and Site alarm SN. Additionally, in order to identify the device, battery string equipment ID and equipment name are also include in VB(variable bondings).      "
			::= { hwSiteAlarmTrapsPrefix 9 }

		
		-- 1.3.6.1.4.1.2011.6.164.2.1.0.10
		hwBattOverCurrAlarmResumeTraps NOTIFICATION-TYPE
			OBJECTS { hwAlarmTrapOrdinalNumber,hwAlarmText,hwAlarmLevel, hwAlarmSigDesc, hwSiteName,hwSiteAdminAddr,
					 hwNetIdentifier,hwSiteDescription,  hwBattStringEquipId,hwBattStringEquipName,  hwBattStringOperStatus  }
			STATUS current
			DESCRIPTION 
				"Batterys over current alarm resume. Its correlation binding parameters:  Site ID, Site name, Site description, NE ID, Alarm name, Alarm single description, Alarm port description, Alarm severity, and Site alarm SN. Additionally, in order to identify the device, battery string equipment ID and equipment name are also include in VB(variable bondings).      "
			::= { hwSiteAlarmTrapsPrefix 10 }

		
		-- 1.3.6.1.4.1.2011.6.164.2.1.0.11
		hwBattStringTempAlarmTraps NOTIFICATION-TYPE
			OBJECTS { hwAlarmTrapOrdinalNumber,hwAlarmText,hwAlarmLevel,hwAlarmSigDesc,hwSiteName, hwSiteAdminAddr,
					  hwNetIdentifier,hwSiteDescription,  hwBattStringEquipId, hwBattStringEquipName,hwBattStringOperStatus}
			STATUS current
			DESCRIPTION 
				"Battery string temperature is too high or too low. Its correlation binding parameters:  Site ID, Site name, Site description, NE ID, Alarm name, Alarm single description, Alarm port description, Alarm severity, and Site alarm SN. Additionally, in order to identify the device, battery group ID and group name are also include in VB(variable bondings).      "
			::= { hwSiteAlarmTrapsPrefix 11 }

		
		-- 1.3.6.1.4.1.2011.6.164.2.1.0.12
		hwBattStringTempAlarmResumeTraps NOTIFICATION-TYPE
			OBJECTS { hwAlarmTrapOrdinalNumber,hwAlarmText,hwAlarmLevel,hwAlarmSigDesc, hwSiteName,hwSiteAdminAddr,
					 hwNetIdentifier,hwSiteDescription, hwBattStringEquipId, hwBattStringEquipName,  hwBattStringOperStatus }
			STATUS current
			DESCRIPTION 
				"Battery string temperature alarm resume. Its correlation binding parameters:  Site ID, Site name, Site description, NE ID, Alarm name, Alarm single description, Alarm port description, Alarm severity, and Site alarm SN. Additionally, in order to identify the device, battery group ID and group name are also include in VB(variable bondings).       "
			::= { hwSiteAlarmTrapsPrefix 12 }

		
		-- 1.3.6.1.4.1.2011.6.164.2.1.0.13
		hwBattDischargeAlarmTraps NOTIFICATION-TYPE
			OBJECTS { hwAlarmTrapOrdinalNumber,hwAlarmText,hwAlarmLevel,hwAlarmSigDesc,hwSiteName,hwSiteAdminAddr,
			 		hwNetIdentifier,hwSiteDescription,hwBattsGroupId, hwBattsGroupName }
			STATUS current
			DESCRIPTION 
				"Battery group discharge alarm. Its correlation binding parameters:  Site ID, Site name, Site description, NE ID, Alarm name, Alarm single description, Alarm port description, Alarm severity, and Site alarm SN. Additionally, in order to identify the device, battery group ID and group name are also include in VB(variable bondings).      "
			::= { hwSiteAlarmTrapsPrefix 13 }

		
		-- 1.3.6.1.4.1.2011.6.164.2.1.0.14
		hwBattDischargeAlarmResumeTraps NOTIFICATION-TYPE
			OBJECTS { hwAlarmTrapOrdinalNumber,hwAlarmText,hwAlarmLevel,hwAlarmSigDesc,hwSiteName,hwSiteAdminAddr,
			 		hwNetIdentifier,hwSiteDescription,  hwBattsGroupId, hwBattsGroupName }      
			STATUS current
			DESCRIPTION 
				"Battery group discharge alarm resume. Its correlation binding parameters:  Site ID, Site name, Site description, NE ID, Alarm name, Alarm single description, Alarm port description, Alarm severity, and Site alarm SN. Additionally, in order to identify the device, battery group ID and group name are also include in VB(variable bondings).      "
			::= { hwSiteAlarmTrapsPrefix 14 }

		
--  1.3.6.1.4.1.2011.6.1.7.1.32
		-- 1.3.6.1.4.1.2011.6.164.2.1.0.15
		hwAcInputAlarmTraps NOTIFICATION-TYPE
			OBJECTS { hwAlarmTrapOrdinalNumber,hwAlarmText,hwAlarmLevel, hwAlarmSigDesc, hwSiteName,hwSiteAdminAddr,
					 hwNetIdentifier,hwSiteDescription, hwAcEquipId, hwAcEquipName, hwAcInputOperStatus }
			STATUS current
			DESCRIPTION 
				"AC absent or AC power off alarms happened. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 15 }

		
--  1.3.6.1.4.1.2011.6.1.7.1.31
		-- 1.3.6.1.4.1.2011.6.164.2.1.0.16
		hwAcInputAlarmResumeTraps NOTIFICATION-TYPE
			OBJECTS { hwAlarmTrapOrdinalNumber,hwAlarmText,hwAlarmLevel, hwAlarmSigDesc,hwSiteName, hwSiteAdminAddr,
			 		hwNetIdentifier,hwSiteDescription,  hwAcEquipId,hwAcEquipName, hwAcInputOperStatus }
			STATUS current
			DESCRIPTION 
				"AC input alarm resumed. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 16 }

		
		-- 1.3.6.1.4.1.2011.6.164.2.1.0.17
		hwAcVoltAlarmTraps NOTIFICATION-TYPE
			OBJECTS { hwAlarmTrapOrdinalNumber,hwAlarmText,hwAlarmLevel,hwAlarmSigDesc,hwSiteName,hwSiteAdminAddr,
					 hwNetIdentifier,hwSiteDescription, hwAcEquipId, hwAcEquipName, hwAcInputOperStatus }
			STATUS current
			DESCRIPTION 
				"AC voltage too high or too low. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 17 }

		
		-- 1.3.6.1.4.1.2011.6.164.2.1.0.18
		hwAcVoltAlarmResumeTraps NOTIFICATION-TYPE
			OBJECTS { hwAlarmTrapOrdinalNumber,hwAlarmText, hwAlarmLevel, hwAlarmSigDesc,hwSiteName, hwSiteAdminAddr,
					hwNetIdentifier, hwSiteDescription,hwAcEquipId, hwAcEquipName, hwAcInputOperStatus }
			STATUS current
			DESCRIPTION 
				"AC voltage alarm resume. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 18 }

		
		-- 1.3.6.1.4.1.2011.6.164.2.1.0.19
		hwDcVoltAlarmTraps NOTIFICATION-TYPE
			OBJECTS { hwAlarmTrapOrdinalNumber,hwAlarmText,hwAlarmLevel, hwAlarmSigDesc,hwSiteName,hwSiteAdminAddr,
					  hwNetIdentifier,hwSiteDescription, hwDcOutputEquipId, hwDcOutputEquipName, hwDcOutputOperStatus }
			STATUS current
			DESCRIPTION 
				"DC voltage too high or too low. Its correlation binding parameters:  Site ID, Site name, Site description, NE ID, Alarm name, Alarm single description, Alarm port description, Alarm severity, and Site alarm SN. Additionally, in order to identify the device, DC equipment ID and equipment name are also include in VB(variable bondings).      "
			::= { hwSiteAlarmTrapsPrefix 19 }

		
		-- 1.3.6.1.4.1.2011.6.164.2.1.0.20
		hwDcVoltAlarmResumeTraps NOTIFICATION-TYPE
			OBJECTS { hwAlarmTrapOrdinalNumber, hwAlarmText,hwAlarmLevel,hwAlarmSigDesc,hwSiteName, hwSiteAdminAddr,
					hwNetIdentifier,hwSiteDescription, hwDcOutputEquipId, hwDcOutputEquipName,  hwDcOutputOperStatus }
			STATUS current
			DESCRIPTION 
				"DC voltage alarm resume. Its correlation binding parameters:  Site ID, Site name, Site description, NE ID, Alarm name, Alarm single description, Alarm port description, Alarm severity, and Site alarm SN. Additionally, in order to identify the device, DC equipment ID and equipment name are also include in VB(variable bondings).      "
			::= { hwSiteAlarmTrapsPrefix 20 }

		
		-- 1.3.6.1.4.1.2011.6.164.2.1.0.21
		hwLoadLvdAlarmTraps NOTIFICATION-TYPE
			OBJECTS { hwAlarmTrapOrdinalNumber,hwAlarmText,hwAlarmLevel, hwAlarmSigDesc,hwSiteName,hwSiteAdminAddr,
					 hwNetIdentifier, hwSiteDescription,hwLvdUnitEquipId,hwLvdUnitEquipName,hwLvdBranchOperStatus  }
			STATUS current
			DESCRIPTION 
				"Loads disconnect for low voltage. Its correlation binding parameters:  Site ID, Site name, Site description, NE ID, Alarm name, Alarm single description, Alarm port description, Alarm severity, and Site alarm SN. Additionally, in order to identify the device, load LVD unit equipment ID and equipment name are also include in VB(variable bondings). "
			::= { hwSiteAlarmTrapsPrefix 21 }

		
		-- 1.3.6.1.4.1.2011.6.164.2.1.0.22
		hwLoadLvdAlarmResumeTraps NOTIFICATION-TYPE
			OBJECTS { hwAlarmTrapOrdinalNumber,hwAlarmText, hwAlarmLevel,hwAlarmSigDesc,hwSiteName,hwSiteAdminAddr,
					 hwNetIdentifier,hwSiteDescription, hwLvdUnitEquipId, hwLvdUnitEquipName, hwLvdBranchOperStatus  }
			STATUS current
			DESCRIPTION 
				"Load LVD alarm resume. Its correlation binding parameters:  Site ID, Site name, Site description, NE ID, Alarm name, Alarm single description, Alarm port description, Alarm severity, and Site alarm SN. Additionally, in order to identify the device, load LVD unit equipment ID and equipment name are also include in VB(variable bondings). "
			::= { hwSiteAlarmTrapsPrefix 22 }

		
		-- 1.3.6.1.4.1.2011.6.164.2.1.0.23
		hwLoadFuseAlarmTraps NOTIFICATION-TYPE
			OBJECTS { hwAlarmTrapOrdinalNumber,hwAlarmText,hwAlarmLevel, hwAlarmSigDesc,hwSiteName,hwSiteAdminAddr,
					 hwNetIdentifier,hwSiteDescription,hwLoadBranchEquipId, hwLoadBranchEquipName,hwLoadBranchOperStatus}
			STATUS current
			DESCRIPTION 
				"Load fuse broken down. Its correlation binding parameters:  Site ID, Site name, Site description, NE ID, Alarm name, Alarm single description, Alarm port description, Alarm severity, and Site alarm SN. Additionally, in order to identify the device, battery string equipment ID and equipment name are also include in VB(variable bondings).    "
			::= { hwSiteAlarmTrapsPrefix 23 }

		
		-- 1.3.6.1.4.1.2011.6.164.2.1.0.24
		hwLoadFuseAlarmResumeTraps NOTIFICATION-TYPE
			OBJECTS { hwAlarmTrapOrdinalNumber,hwAlarmText,hwAlarmLevel,hwAlarmSigDesc,hwSiteName, hwSiteAdminAddr,
					hwNetIdentifier,hwSiteDescription, hwLoadBranchEquipId, hwLoadBranchEquipName, hwLoadBranchOperStatus }
			STATUS current
			DESCRIPTION 
				"Load fuse alarm resume. Its correlation binding parameters:  Site ID, Site name, Site description, NE ID, Alarm name, Alarm single description, Alarm port description, Alarm severity, and Site alarm SN. Additionally, in order to identify the device, battery string equipment ID and equipment name are also include in VB(variable bondings).    "
			::= { hwSiteAlarmTrapsPrefix 24 }

		
		-- 1.3.6.1.4.1.2011.6.164.2.1.0.25
		hwEnvTempAlarmTraps NOTIFICATION-TYPE
			OBJECTS { hwAlarmTrapOrdinalNumber,hwAlarmText,hwAlarmLevel,hwAlarmSigDesc,hwSiteName,hwSiteAdminAddr,
					  hwNetIdentifier,hwSiteDescription, hwEnvTempEquipId,hwEnvTempEquipName,  hwEnvTempSensorOperStatus }
			STATUS current
			DESCRIPTION 
				"Environment temperature is too high or too low. Its correlation binding parameters:  Site ID, Site name, Site description, NE ID, Alarm name, Alarm single description, Alarm port description, Alarm severity, and Site alarm SN. Additionally, in order to identify the device, envirenment temperature sensor equipment ID and equipment name are also include in VB(variable bondings).    "
			::= { hwSiteAlarmTrapsPrefix 25 }

		
		-- 1.3.6.1.4.1.2011.6.164.2.1.0.26
		hwEnvTempAlarmResumeTraps NOTIFICATION-TYPE
			OBJECTS { hwAlarmTrapOrdinalNumber,hwAlarmText,hwAlarmLevel,hwAlarmSigDesc,hwSiteName, hwSiteAdminAddr,
					hwNetIdentifier,hwSiteDescription, hwEnvTempEquipId,hwEnvTempEquipName, hwEnvTempSensorOperStatus }
			STATUS current
			DESCRIPTION 
				"Environment temperature alarm resume. Its correlation binding parameters:  Site ID, Site name, Site description, NE ID, Alarm name, Alarm single description, Alarm port description, Alarm severity, and Site alarm SN. Additionally, in order to identify the device, envirenment temperature sensor equipment ID and equipment name are also include in VB(variable bondings).    "
			::= { hwSiteAlarmTrapsPrefix 26 }

		
		-- 1.3.6.1.4.1.2011.6.164.2.1.0.27
		hwEnvHumiAlarmTraps NOTIFICATION-TYPE
			OBJECTS { hwAlarmTrapOrdinalNumber, hwAlarmText, hwAlarmLevel, hwAlarmSigDesc, hwSiteName, hwSiteAdminAddr,
					 hwNetIdentifier, hwSiteDescription,  hwEnvHumiEquipId, hwEnvHumiEquipName, hwEnvHumiSensorOperStatus }
			STATUS current
			DESCRIPTION 
				"Environment humidity is too high or too low. Its correlation binding parameters:  Site ID, Site name, Site description, NE ID, Alarm name, Alarm single description, Alarm port description, Alarm severity, and Site alarm SN. Additionally, in order to identify the device, envirenment humidity sensor equipment ID and equipment name are also include in VB(variable bondings).    "
			::= { hwSiteAlarmTrapsPrefix 27 }

		
		-- 1.3.6.1.4.1.2011.6.164.2.1.0.28
		hwEnvHumiAlarmResumeTraps NOTIFICATION-TYPE
			OBJECTS { hwAlarmTrapOrdinalNumber, hwAlarmText,  hwAlarmLevel,  hwAlarmSigDesc,hwSiteName, hwSiteAdminAddr,
					hwNetIdentifier,hwSiteDescription, hwEnvHumiEquipId, hwEnvHumiEquipName, hwEnvHumiSensorOperStatus }
			STATUS current
			DESCRIPTION 
				"Environment humidity alarm resume. Its correlation binding parameters:  Site ID, Site name, Site description, NE ID, Alarm name, Alarm single description, Alarm port description, Alarm severity, and Site alarm SN. Additionally, in order to identify the device, envirenment humidity sensor equipment ID and equipment name are also include in VB(variable bondings).    "
			::= { hwSiteAlarmTrapsPrefix 28 }

		
		-- 1.3.6.1.4.1.2011.6.164.2.1.0.29
		hwSpareDigitalAlarmTraps NOTIFICATION-TYPE
			OBJECTS { hwAlarmTrapOrdinalNumber,hwAlarmText, hwAlarmLevel,hwAlarmSigDesc, hwSiteName, hwSiteAdminAddr,
					hwNetIdentifier,hwSiteDescription, hwSpareDigitalEquipId, hwSpareDigitalEquipName, hwSpareDigitalOperStatus }
			STATUS current
			DESCRIPTION 
				"Spare digital fault. Its correlation binding parameters:  Site ID, Site name, Site description, NE ID, Alarm name, Alarm single description, Alarm port description, Alarm severity, and Site alarm SN. Additionally, in order to identify the device, Spare digital equipment ID and equipment name are also include in VB(variable bondings).    "
			::= { hwSiteAlarmTrapsPrefix 29 }

		
		-- 1.3.6.1.4.1.2011.6.164.2.1.0.30
		hwSpareDigitalAlarmResumeTraps NOTIFICATION-TYPE
			OBJECTS { hwAlarmTrapOrdinalNumber, hwAlarmText,hwAlarmLevel,hwAlarmSigDesc, hwSiteName, hwSiteAdminAddr,
					hwNetIdentifier, hwSiteDescription,hwSpareDigitalEquipId, hwSpareDigitalEquipName, hwSpareDigitalOperStatus }
			STATUS current
			DESCRIPTION 
				"Spare digital alarm resume.Its correlation binding parameters:  Site ID, Site name, Site description, NE ID, Alarm name, Alarm single description, Alarm port description, Alarm severity, and Site alarm SN. Additionally, in order to identify the device, Spare digital equipment ID and equipment name are also include in VB(variable bondings).    "
			::= { hwSiteAlarmTrapsPrefix 30 }

		
		-- 1.3.6.1.4.1.2011.6.164.2.1.0.31
		hwDoorAlarmTraps NOTIFICATION-TYPE
			OBJECTS { hwAlarmTrapOrdinalNumber,hwAlarmText,hwAlarmLevel, hwAlarmSigDesc,hwSiteName, hwSiteAdminAddr,
					 hwNetIdentifier,hwSiteDescription,  hwEnvUnitsGroupId, hwEnvUnitsGroupName }
			STATUS current
			DESCRIPTION 
				"Door open. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 31 }

		
		-- 1.3.6.1.4.1.2011.6.164.2.1.0.32
		hwDoorAlarmResumeTraps NOTIFICATION-TYPE
			OBJECTS { hwAlarmTrapOrdinalNumber, hwAlarmText,hwAlarmLevel,hwAlarmSigDesc, hwSiteName, hwSiteAdminAddr,
					hwNetIdentifier,hwSiteDescription, hwEnvUnitsGroupId, hwEnvUnitsGroupName }
			STATUS current
			DESCRIPTION 
				"Door alarm resume. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 32 }

		
		-- 1.3.6.1.4.1.2011.6.164.2.1.0.33
		hwWaterAlarmTraps NOTIFICATION-TYPE
			OBJECTS { hwAlarmTrapOrdinalNumber, hwAlarmText, hwAlarmLevel, hwAlarmSigDesc,hwSiteName,hwSiteAdminAddr,
					 hwNetIdentifier,hwSiteDescription,  hwEnvUnitsGroupId, hwEnvUnitsGroupName }
			STATUS current
			DESCRIPTION 
				"Water alarm. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 33 }

		
		-- 1.3.6.1.4.1.2011.6.164.2.1.0.34
		hwWaterAlarmResumeTraps NOTIFICATION-TYPE
			OBJECTS { hwAlarmTrapOrdinalNumber,  hwAlarmText,hwAlarmLevel,hwAlarmSigDesc,hwSiteName,  hwSiteAdminAddr,
					hwNetIdentifier,hwSiteDescription, hwEnvUnitsGroupId, hwEnvUnitsGroupName }
			STATUS current
			DESCRIPTION 
				"Water alarm resume. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 34 }

		
		-- 1.3.6.1.4.1.2011.6.164.2.1.0.35
		hwSmokeAlarmTraps NOTIFICATION-TYPE
			OBJECTS { hwAlarmTrapOrdinalNumber, hwAlarmText,hwAlarmLevel, hwAlarmSigDesc,hwSiteName,hwSiteAdminAddr,
					hwNetIdentifier, hwSiteDescription,  hwEnvUnitsGroupId,hwEnvUnitsGroupName }
			STATUS current
			DESCRIPTION 
				"Site is on fire, which is detected by smoke sensors. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 35 }

		
		-- 1.3.6.1.4.1.2011.6.164.2.1.0.36
		hwSmokeAlarmResumeTraps NOTIFICATION-TYPE
			OBJECTS { hwAlarmTrapOrdinalNumber, hwAlarmText,hwAlarmLevel,hwAlarmSigDesc,hwSiteName,hwSiteAdminAddr,
					  hwNetIdentifier,hwSiteDescription,hwEnvUnitsGroupId,hwEnvUnitsGroupName }
			STATUS current
			DESCRIPTION 
				"Smoke alarm resume. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 36 }

		
		-- 1.3.6.1.4.1.2011.6.164.2.1.0.37
		hwWireAlarmTraps NOTIFICATION-TYPE
			OBJECTS { hwAlarmTrapOrdinalNumber,hwAlarmText,hwAlarmLevel, hwAlarmSigDesc,hwSiteName, hwSiteAdminAddr,
					 hwNetIdentifier, hwSiteDescription, hwEnvUnitsGroupId, hwEnvUnitsGroupName }
			STATUS current
			DESCRIPTION 
				"Wire alarm.Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 37 }

		
		-- 1.3.6.1.4.1.2011.6.164.2.1.0.38
		hwWireAlarmResumeTraps NOTIFICATION-TYPE
			OBJECTS {  hwAlarmTrapOrdinalNumber,hwAlarmText,hwAlarmLevel,hwAlarmSigDesc,hwSiteName,hwSiteAdminAddr,
					  hwNetIdentifier,hwSiteDescription, hwEnvUnitsGroupId, hwEnvUnitsGroupName }
			STATUS current
			DESCRIPTION 
				"Wire alarm resume. Its correlation binding parameters:  Site ID, Site name, Site description, NE ID, Alarm name, Alarm single description, Alarm port description, Alarm severity, and Site alarm SN. Additionally, in order to identify the device, envirenment unit group ID and group name are also include in VB(variable bondings).      "
			::= { hwSiteAlarmTrapsPrefix 38 }

		
		-- 1.3.6.1.4.1.2011.6.164.2.1.0.39
		hwAcBreakerAlarmTraps NOTIFICATION-TYPE
			OBJECTS {  hwAlarmTrapOrdinalNumber,hwAlarmText, hwAlarmLevel,hwAlarmSigDesc, hwSiteName, hwSiteAdminAddr,
					hwNetIdentifier,hwSiteDescription, hwAcInputBreakerEquipId, hwAcInputBreakerEquipName, hwAcInputBreakerOperStatus}
			STATUS current
			DESCRIPTION 
				"AC breaker alarm.Its correlation binding parameters:  Site ID, Site name, Site description, NE ID, Alarm name, Alarm single description, Alarm port description, Alarm severity, and Site alarm SN. Additionally, in order to identify the device, AC distribution unit ID and its name are also include in VB(variable bondings).      "
			::= { hwSiteAlarmTrapsPrefix 39 }

		
		-- 1.3.6.1.4.1.2011.6.164.2.1.0.40
		hwAcBreakerAlarmResumeTraps NOTIFICATION-TYPE
			OBJECTS { hwAlarmTrapOrdinalNumber,hwAlarmText, hwAlarmLevel,hwAlarmSigDesc,hwSiteName, hwSiteAdminAddr,
					hwNetIdentifier,hwSiteDescription, hwAcInputBreakerEquipId, hwAcInputBreakerEquipName, hwAcInputBreakerOperStatus }
			STATUS current
			DESCRIPTION 
				"AC breaker alarm resume.Its correlation binding parameters:  Site ID, Site name, Site description, NE ID, Alarm name, Alarm single description, Alarm port description, Alarm severity, and Site alarm SN. Additionally, in order to identify the device, AC distribution unit ID and its name are also include in VB(variable bondings). "
			::= { hwSiteAlarmTrapsPrefix 40 }

		
		-- 1.3.6.1.4.1.2011.6.164.2.1.0.41
		hwMultiRectFailureAlarmTraps NOTIFICATION-TYPE
			OBJECTS { hwAlarmTrapOrdinalNumber,hwAlarmText, hwAlarmLevel,hwAlarmSigDesc,hwSiteName,hwSiteAdminAddr,
				 	hwNetIdentifier,hwSiteDescription, hwRectsGroupId, hwRectsGroupName }
			STATUS current
			DESCRIPTION 
				"More than one rectifier reported fault alarms in the same time. Its correlation binding parameters:  Site ID, Site name, Site description, NE ID, Alarm name, Alarm single description, Alarm port description, Alarm severity, and Site alarm SN. Additionally, in order to identify the device, rectifier group ID and group name are also include in VB(variable bondings).  "
			::= { hwSiteAlarmTrapsPrefix 41 }

		
		-- 1.3.6.1.4.1.2011.6.164.2.1.0.42
		hwMultiRectFailureAlarmResumeTraps NOTIFICATION-TYPE
			OBJECTS { hwAlarmTrapOrdinalNumber,hwAlarmText,hwAlarmLevel,hwAlarmSigDesc, hwSiteName,hwSiteAdminAddr,
					  hwNetIdentifier,hwSiteDescription, hwRectsGroupId, hwRectsGroupName }
			STATUS current
			DESCRIPTION 
				"Multi-rectifiers fault alarm resume. Its correlation binding parameters:  Site ID, Site name, Site description, NE ID, Alarm name, Alarm single description, Alarm port description, Alarm severity, and Site alarm SN. Additionally, in order to identify the device, rectifier group ID and group name are also include in VB(variable bondings).  "
			::= { hwSiteAlarmTrapsPrefix 42 }

		
		-- 1.3.6.1.4.1.2011.6.164.2.1.0.43
		hwRectRedundAlarmTraps NOTIFICATION-TYPE
			OBJECTS { hwAlarmTrapOrdinalNumber,hwAlarmText,hwAlarmLevel,hwAlarmSigDesc,hwSiteName,hwSiteAdminAddr,
					  hwNetIdentifier,hwSiteDescription,hwRectsGroupId,hwRectsGroupName }
			STATUS current
			DESCRIPTION 
				"Rectifiers work redundantly, in this case that some of rectifiers will going to sleep. Its correlation binding parameters:  Site ID, Site name, Site description, NE ID, Alarm name, Alarm single description, Alarm port description, Alarm severity, and Site alarm SN. Additionally, in order to identify the device, rectifier group ID and group name are also include in VB(variable bondings).   "
			::= { hwSiteAlarmTrapsPrefix 43 }

		
		-- 1.3.6.1.4.1.2011.6.164.2.1.0.44
		hwRectRedundAlarmResumeTraps NOTIFICATION-TYPE
			OBJECTS { hwAlarmTrapOrdinalNumber, hwAlarmText,hwAlarmLevel,hwAlarmSigDesc,hwSiteName, hwSiteAdminAddr,
					hwNetIdentifier,hwSiteDescription, hwRectsGroupId, hwRectsGroupName }
			STATUS current
			DESCRIPTION 
				"Rectifiers redundant alarm resume, when the power supply and requirement were in balance. Its correlation binding parameters:  Site ID, Site name, Site description, NE ID, Alarm name, Alarm single description, Alarm port description, Alarm severity, and Site alarm SN. Additionally, in order to identify the device, rectifier group ID and group name are also include in VB(variable bondings).   "
			::= { hwSiteAlarmTrapsPrefix 44 }

		
		-- 1.3.6.1.4.1.2011.6.164.2.1.0.45
		hwBattUnbalanceAlarmTraps NOTIFICATION-TYPE
			OBJECTS { hwAlarmTrapOrdinalNumber,hwAlarmText, hwAlarmLevel,hwAlarmSigDesc,hwSiteName, hwSiteAdminAddr,
					 hwNetIdentifier,hwSiteDescription,  hwBattStringEquipId, hwBattStringEquipName,hwBattStringOperStatus }
			STATUS current
			DESCRIPTION 
				"Battery works in unbalance state. Its correlation binding parameters:  Site ID, Site name, Site description, NE ID, Alarm name, Alarm single description, Alarm port description, Alarm severity, and Site alarm SN. Additionally, in order to identify the device, battery string equipment ID and equipment name are also include in VB(variable bondings).      "
			::= { hwSiteAlarmTrapsPrefix 45 }

		
		-- 1.3.6.1.4.1.2011.6.164.2.1.0.46
		hwBattUnbalanceAlarmResumeTraps NOTIFICATION-TYPE
			OBJECTS { hwAlarmTrapOrdinalNumber, hwAlarmText,hwAlarmLevel, hwAlarmSigDesc, hwSiteName,hwSiteAdminAddr,
				 	 hwNetIdentifier,hwSiteDescription, hwBattStringEquipId,  hwBattStringEquipName,hwBattStringOperStatus }
			STATUS current
			DESCRIPTION 
				"Battery unbalance alarm resume. Its correlation binding parameters:  Site ID, Site name, Site description, NE ID, Alarm name, Alarm single description, Alarm port description, Alarm severity, and Site alarm SN. Additionally, in order to identify the device, battery string equipment ID and equipment name are also include in VB(variable bondings).      "
			::= { hwSiteAlarmTrapsPrefix 46 }

		
		-- 1.3.6.1.4.1.2011.6.164.2.1.0.47
		hwAcFreqFaultAlarmTraps NOTIFICATION-TYPE
			OBJECTS { hwAlarmTrapOrdinalNumber,hwAlarmText,hwAlarmLevel,hwAlarmSigDesc,hwSiteName, hwSiteAdminAddr,
					hwNetIdentifier,hwSiteDescription, hwAcEquipId,hwAcEquipName, hwAcInputOperStatus }
			STATUS current
			DESCRIPTION 
				"AC frequency is fault. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 47 }

		
		-- 1.3.6.1.4.1.2011.6.164.2.1.0.48
		hwAcFreqFaultAlarmResumeTraps NOTIFICATION-TYPE
			OBJECTS {  hwAlarmTrapOrdinalNumber,hwAlarmText, hwAlarmLevel,hwAlarmSigDesc,hwSiteName,hwSiteAdminAddr,
					  hwNetIdentifier,hwSiteDescription, hwAcEquipId, hwAcEquipName,hwAcInputOperStatus }
			STATUS current
			DESCRIPTION 
				"AC frequency alarm resume. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 48 }

		
		-- 1.3.6.1.4.1.2011.6.164.2.1.0.49
		hwXmuSelfFaultAlarmTraps NOTIFICATION-TYPE
			OBJECTS { hwAlarmTrapOrdinalNumber,hwAlarmText,hwAlarmLevel, hwAlarmSigDesc,hwSiteName, hwSiteAdminAddr,
					 hwNetIdentifier,hwSiteDescription,hwMonEquipId,hwMonEquipName,hwMonitorOperStatus  }
			STATUS current
			DESCRIPTION 
				"There are some fault in XMU itself. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 49 }

		
		-- 1.3.6.1.4.1.2011.6.164.2.1.0.50
		hwXmuSelfFaultAlarmResumeTraps NOTIFICATION-TYPE
			OBJECTS { hwAlarmTrapOrdinalNumber, hwAlarmText,hwAlarmLevel, hwAlarmSigDesc, hwSiteName, hwSiteAdminAddr,
					 hwNetIdentifier,hwSiteDescription, hwMonEquipId, hwMonEquipName, hwMonitorOperStatus }
			STATUS current
			DESCRIPTION 
				"XMU fault alarm resume. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 50 }

		
		-- 1.3.6.1.4.1.2011.6.164.2.1.0.51
		hwRs485CommAlarmTraps NOTIFICATION-TYPE
			OBJECTS { hwAlarmTrapOrdinalNumber,hwAlarmText, hwAlarmLevel, hwAlarmSigDesc,hwSiteName, hwSiteAdminAddr,
					hwNetIdentifier,hwSiteDescription, hwMonEquipId, hwMonEquipName,hwMonitorOperStatus }
			STATUS current
			DESCRIPTION 
				"RS485 communication of monitors disconnect. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 51 }

		
		-- 1.3.6.1.4.1.2011.6.164.2.1.0.52
		hwRs485CommAlarmResumeTraps NOTIFICATION-TYPE
			OBJECTS { hwAlarmTrapOrdinalNumber,hwAlarmText,hwAlarmLevel,hwAlarmSigDesc,hwSiteName,hwSiteAdminAddr,
					 hwNetIdentifier,hwSiteDescription, hwMonEquipId, hwMonEquipName, hwMonitorOperStatus }
			STATUS current
			DESCRIPTION 
				"RS485 communication alarm resume. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 52 }

		
		-- 1.3.6.1.4.1.2011.6.164.2.1.0.53
		hwNetCommAlarmTraps NOTIFICATION-TYPE
			OBJECTS { hwAlarmTrapOrdinalNumber, hwAlarmText,hwAlarmLevel,hwAlarmSigDesc,hwSiteName, hwSiteAdminAddr,
					hwNetIdentifier,hwSiteDescription, hwMonEquipId, hwMonEquipName,hwMonitorOperStatus }
			STATUS current
			DESCRIPTION 
				"Network communication of monitors disconnect. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 53 }

		
		-- 1.3.6.1.4.1.2011.6.164.2.1.0.54
		hwNetCommAlarmResumeTraps NOTIFICATION-TYPE
			OBJECTS { hwAlarmTrapOrdinalNumber,hwAlarmText,hwAlarmLevel,hwAlarmSigDesc, hwSiteName, hwSiteAdminAddr,
					hwNetIdentifier,hwSiteDescription, hwMonEquipId, hwMonEquipName, hwMonitorOperStatus }
			STATUS current
			DESCRIPTION 
				"Network communication alarm resume. Its correlation binding parameters:  Site ID, Site name, Site description, NE ID, Alarm name, Alarm single description, Alarm port description, Alarm severity, and Site alarm SN. Additionally, in order to identify the device, monitor equipment ID and equipment name are also include in VB(variable bondings).      "
			::= { hwSiteAlarmTrapsPrefix 54 }

		
		-- 1.3.6.1.4.1.2011.6.164.2.1.0.55
		hwAcOffLongTimeAlarmTraps NOTIFICATION-TYPE
			OBJECTS { hwAlarmTrapOrdinalNumber,hwAlarmText,hwAlarmLevel, hwAlarmSigDesc, hwSiteName,hwSiteAdminAddr,
				 	hwNetIdentifier,hwSiteDescription, hwAcEquipId, hwAcEquipName, hwAcInputOperStatus }
			STATUS current
			DESCRIPTION 
				"AC power off for a long time alarms happened. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 55 }

		
		-- 1.3.6.1.4.1.2011.6.164.2.1.0.56
		hwAcOffLongTimeAlarmResumeTraps NOTIFICATION-TYPE
			OBJECTS {  hwAlarmTrapOrdinalNumber,hwAlarmText,hwAlarmLevel, hwAlarmSigDesc, hwSiteName,hwSiteAdminAddr,
					 hwNetIdentifier, hwSiteDescription, hwAcEquipId, hwAcEquipName,hwAcInputOperStatus }
			STATUS current
			DESCRIPTION 
				"AC power off for a long time alarms resume. Its correlation binding parameters:  Site ID, Site name, Site description, NE ID, Alarm name, Alarm single description, Alarm port description, Alarm severity, and Site alarm SN. Additionally, in order to identify the device, AC equipment ID and equipment name are also include in VB(variable bondings).      "
			::= { hwSiteAlarmTrapsPrefix 56 }

		
		-- 1.3.6.1.4.1.2011.6.164.2.1.0.57
		hwSpdAlarmTraps NOTIFICATION-TYPE
			OBJECTS {  hwAlarmTrapOrdinalNumber,hwAlarmText,hwAlarmLevel,hwAlarmSigDesc,hwSiteName,hwSiteAdminAddr,
					  hwNetIdentifier,hwSiteDescription, hwEnvUnitsGroupId, hwEnvUnitsGroupName }
			STATUS current
			DESCRIPTION 
				"Description."
			::= { hwSiteAlarmTrapsPrefix 57 }

		
		-- 1.3.6.1.4.1.2011.6.164.2.1.0.58
		hwSpdAlarmResumeTraps NOTIFICATION-TYPE
			OBJECTS { hwAlarmTrapOrdinalNumber,hwAlarmText,hwAlarmLevel, hwAlarmSigDesc,hwSiteName, hwSiteAdminAddr, 
					 hwNetIdentifier,hwSiteDescription, hwEnvUnitsGroupId, hwEnvUnitsGroupName }
			STATUS current
			DESCRIPTION 
				"Description."
			::= { hwSiteAlarmTrapsPrefix 58 }

		
		-- 1.3.6.1.4.1.2011.6.164.2.1.0.59
		hwBadBatteryTraps NOTIFICATION-TYPE
			OBJECTS { hwAlarmTrapOrdinalNumber,hwAlarmText,hwAlarmLevel, hwAlarmSigDesc,hwSiteName, hwSiteAdminAddr, 
					 hwNetIdentifier,hwSiteDescription, hwBattsGroupId, hwBattsGroupName }
			STATUS current
			DESCRIPTION 
				"Description."
			::= { hwSiteAlarmTrapsPrefix 59 }

		
		-- 1.3.6.1.4.1.2011.6.164.2.1.0.60
		hwBadBatteryResumeTraps NOTIFICATION-TYPE
			OBJECTS {  hwAlarmTrapOrdinalNumber,hwAlarmText, hwAlarmLevel,hwAlarmSigDesc,hwSiteName, hwSiteAdminAddr,
					 hwNetIdentifier,hwSiteDescription, hwBattsGroupId, hwBattsGroupName }
			STATUS current
			DESCRIPTION 
				"Description."
			::= { hwSiteAlarmTrapsPrefix 60 }

		
		-- 1.3.6.1.4.1.2011.6.164.2.1.0.61
		hwLvd2DisconnectingTraps NOTIFICATION-TYPE
			OBJECTS { hwAlarmTrapOrdinalNumber,hwAlarmText, hwAlarmLevel, hwAlarmSigDesc,hwSiteName, hwSiteAdminAddr,
					  hwNetIdentifier,hwSiteDescription, hwLvdUnitEquipId, hwLvdUnitEquipName, hwLvdBranchOperStatus }
			STATUS current
			DESCRIPTION 
				"Description."
			::= { hwSiteAlarmTrapsPrefix 61 }

		
		-- 1.3.6.1.4.1.2011.6.164.2.1.0.62
		hwLvd2DisconnectingResumeTraps NOTIFICATION-TYPE
			OBJECTS {  hwAlarmTrapOrdinalNumber,hwAlarmText,hwAlarmLevel,hwAlarmSigDesc,hwSiteName, hwSiteAdminAddr, 
					hwNetIdentifier,hwSiteDescription,  hwLvdUnitEquipId, hwLvdUnitEquipName, hwLvdBranchOperStatus }
			STATUS current
			DESCRIPTION 
				"Description."
			::= { hwSiteAlarmTrapsPrefix 62 }

		
		-- 1.3.6.1.4.1.2011.6.164.2.1.0.63
		hwBattHighTempTraps NOTIFICATION-TYPE
			OBJECTS { hwAlarmTrapOrdinalNumber,hwAlarmText,hwAlarmLevel, hwAlarmSigDesc,hwSiteName,hwSiteAdminAddr, 
					 hwNetIdentifier,hwSiteDescription, hwBattStringEquipId, hwBattStringEquipName,hwBattStringOperStatus }
			STATUS current
			DESCRIPTION 
				"Description."
			::= { hwSiteAlarmTrapsPrefix 63 }

		
		-- 1.3.6.1.4.1.2011.6.164.2.1.0.64
		hwBattHighTempResumeTraps NOTIFICATION-TYPE
			OBJECTS {  hwAlarmTrapOrdinalNumber,hwAlarmText,hwAlarmLevel, hwAlarmSigDesc,hwSiteName, hwSiteAdminAddr, 
					hwNetIdentifier, hwSiteDescription,   hwBattStringEquipId, hwBattStringEquipName,hwBattStringOperStatus }
			STATUS current
			DESCRIPTION 
				"Description."
			::= { hwSiteAlarmTrapsPrefix 64 }
		-- 1.3.6.1.4.1.2011.6.164.2.1.0.65
		hwBattLowTempTraps NOTIFICATION-TYPE
			OBJECTS { hwAlarmTrapOrdinalNumber,hwAlarmText,hwAlarmLevel, hwAlarmSigDesc, hwSiteName, hwSiteAdminAddr, 
					hwNetIdentifier,hwSiteDescription,  hwBattStringEquipId,hwBattStringEquipName, hwBattStringOperStatus }
			STATUS current
			DESCRIPTION 
				"Description."
			::= { hwSiteAlarmTrapsPrefix 65 }
		-- 1.3.6.1.4.1.2011.6.164.2.1.0.66
		hwBattLowTempResumeTraps NOTIFICATION-TYPE
			OBJECTS { hwAlarmTrapOrdinalNumber,hwAlarmText,hwAlarmLevel,hwAlarmSigDesc,hwSiteName, hwSiteAdminAddr, 
					hwNetIdentifier,hwSiteDescription, hwBattStringEquipId, hwBattStringEquipName, hwBattStringOperStatus }
			STATUS current
			DESCRIPTION 
				"Description."
			::= { hwSiteAlarmTrapsPrefix 66 }

		
		-- 1.3.6.1.4.1.2011.6.164.2.1.0.67
		hwDcUltraOverVoltageTraps NOTIFICATION-TYPE
			OBJECTS { hwAlarmTrapOrdinalNumber,hwAlarmText,hwAlarmLevel,hwAlarmSigDesc,hwSiteName, hwSiteAdminAddr, 
					hwNetIdentifier,hwSiteDescription, hwDcOutputEquipId, hwDcOutputEquipName, hwDcOutputOperStatus }
			STATUS current
			DESCRIPTION 
				"Description."
			::= { hwSiteAlarmTrapsPrefix 67 }

		
		-- 1.3.6.1.4.1.2011.6.164.2.1.0.68
		hwDcUltraOverVoltageResumeTraps NOTIFICATION-TYPE
			OBJECTS { hwAlarmTrapOrdinalNumber,hwAlarmText, hwAlarmLevel,hwAlarmSigDesc,hwSiteName, hwSiteAdminAddr,
					hwNetIdentifier, hwSiteDescription, hwDcOutputEquipId, hwDcOutputEquipName, hwDcOutputOperStatus }
			STATUS current
			DESCRIPTION 
				"Description."
			::= { hwSiteAlarmTrapsPrefix 68 }

		
		-- 1.3.6.1.4.1.2011.6.164.2.1.0.69
		hwDcUltraUnderVoltageTraps NOTIFICATION-TYPE
			OBJECTS {  hwAlarmTrapOrdinalNumber,hwAlarmText,hwAlarmLevel, hwAlarmSigDesc,hwSiteName, hwSiteAdminAddr,
					 hwNetIdentifier,hwSiteDescription, hwDcOutputEquipId, hwDcOutputEquipName, hwDcOutputOperStatus }
			STATUS current
			DESCRIPTION 
				"Description."
			::= { hwSiteAlarmTrapsPrefix 69 }

		
		-- 1.3.6.1.4.1.2011.6.164.2.1.0.70
		hwDcUltraUnderVoltageResumeTraps NOTIFICATION-TYPE
			OBJECTS { hwAlarmTrapOrdinalNumber,hwAlarmText,hwAlarmLevel, hwAlarmSigDesc,hwSiteName, hwSiteAdminAddr, 
					hwNetIdentifier,hwSiteDescription, hwDcOutputEquipId, hwDcOutputEquipName, hwDcOutputOperStatus }
			STATUS current
			DESCRIPTION 
				"Description."
			::= { hwSiteAlarmTrapsPrefix 70 }

		
		-- 1.3.6.1.4.1.2011.6.164.2.1.0.71
		hwUmiCommFailTraps NOTIFICATION-TYPE
			OBJECTS {  hwAlarmTrapOrdinalNumber,hwAlarmText, hwAlarmLevel, hwAlarmSigDesc, hwSiteName, hwSiteAdminAddr, 
					hwNetIdentifier,hwSiteDescription, hwEnvUnitsGroupId, hwEnvUnitsGroupName }
			STATUS current
			DESCRIPTION 
				"Description."
			::= { hwSiteAlarmTrapsPrefix 71 }

		
		-- 1.3.6.1.4.1.2011.6.164.2.1.0.72
		hwUmiCommFailResumeTraps NOTIFICATION-TYPE
			OBJECTS {  hwAlarmTrapOrdinalNumber,hwAlarmText, hwAlarmLevel, hwAlarmSigDesc,hwSiteName, hwSiteAdminAddr, 
					 hwNetIdentifier, hwSiteDescription,hwEnvUnitsGroupId, hwEnvUnitsGroupName }
			STATUS current
			DESCRIPTION 
				"Description."
			::= { hwSiteAlarmTrapsPrefix 72 }

		
		-- 1.3.6.1.4.1.2011.6.164.2.1.0.73
		hwShortTestFailTraps NOTIFICATION-TYPE
			OBJECTS {  hwAlarmTrapOrdinalNumber,hwAlarmText, hwAlarmLevel, hwAlarmSigDesc,hwSiteName, hwSiteAdminAddr, 
					hwNetIdentifier,hwSiteDescription, hwRectsGroupId, hwRectsGroupName }
			STATUS current
			DESCRIPTION 
				"Description."
			::= { hwSiteAlarmTrapsPrefix 73 }
		-- 1.3.6.1.4.1.2011.6.164.2.1.0.74
		hwShortTestFailResumeTraps NOTIFICATION-TYPE
			OBJECTS {  hwAlarmTrapOrdinalNumber,hwAlarmText, hwAlarmLevel, hwAlarmSigDesc,hwSiteName, hwSiteAdminAddr,
					  hwNetIdentifier,hwSiteDescription, hwBattsGroupId, hwBattsGroupName }
			STATUS current
			DESCRIPTION 
				"Description."
			::= { hwSiteAlarmTrapsPrefix 74 }
		-- 1.3.6.1.4.1.2011.6.164.2.1.0.75
		hwMissingBattTempSensorTraps NOTIFICATION-TYPE
			OBJECTS { hwAlarmTrapOrdinalNumber,hwAlarmText, hwAlarmLevel, hwAlarmSigDesc,hwSiteName, hwSiteAdminAddr, 
					 hwNetIdentifier,hwSiteDescription, hwBattsGroupId, hwBattsGroupName }
			STATUS current
			DESCRIPTION 
				"Description."
			::= { hwSiteAlarmTrapsPrefix 75 }

		
		-- 1.3.6.1.4.1.2011.6.164.2.1.0.76
		hwMissingBattTempSensorResumeTraps NOTIFICATION-TYPE
			OBJECTS { hwAlarmTrapOrdinalNumber,hwAlarmText, hwAlarmLevel, hwAlarmSigDesc, hwSiteName, hwSiteAdminAddr,
					  hwNetIdentifier,hwSiteDescription, hwBattsGroupId, hwBattsGroupName }
			STATUS current
			DESCRIPTION 
				"Description."
			::= { hwSiteAlarmTrapsPrefix 76 }
		-- 1.3.6.1.4.1.2011.6.164.2.1.0.77
		hwBattTempSensorFaultTraps NOTIFICATION-TYPE
			OBJECTS {  hwAlarmTrapOrdinalNumber,hwAlarmText, hwAlarmLevel, hwAlarmSigDesc,hwSiteName, hwSiteAdminAddr, 
						hwNetIdentifier,hwSiteDescription, hwBattsGroupId, hwBattsGroupName }
			STATUS current
			DESCRIPTION 
				"Description."
			::= { hwSiteAlarmTrapsPrefix 77 }
		-- 1.3.6.1.4.1.2011.6.164.2.1.0.78
		hwBattTempSensorFaultResumeTraps NOTIFICATION-TYPE
			OBJECTS { hwAlarmTrapOrdinalNumber,	hwAlarmText, hwAlarmLevel, hwAlarmSigDesc,hwSiteName, hwSiteAdminAddr,
					  hwNetIdentifier,hwSiteDescription,hwBattsGroupId, hwBattsGroupName }
			STATUS current
			DESCRIPTION 
				"Description."
			::= { hwSiteAlarmTrapsPrefix 78 }

		
		-- 1.3.6.1.4.1.2011.6.164.2.1.0.79
		hwAcOverVoltageTraps NOTIFICATION-TYPE
			OBJECTS {  hwAlarmTrapOrdinalNumber,hwAlarmText, hwAlarmLevel, hwAlarmSigDesc,hwSiteName, hwSiteAdminAddr, 
					hwNetIdentifier,hwSiteDescription, hwAcEquipId, hwAcEquipName, hwAcInputOperStatus }
			STATUS current
			DESCRIPTION 
				"Description."
			::= { hwSiteAlarmTrapsPrefix 79 }

		
		-- 1.3.6.1.4.1.2011.6.164.2.1.0.80
		hwAcOverVoltageResumeTraps NOTIFICATION-TYPE
			OBJECTS {hwAlarmTrapOrdinalNumber, hwAlarmText, hwAlarmLevel, hwAlarmSigDesc,hwSiteName, hwSiteAdminAddr, 
					hwNetIdentifier, hwSiteDescription, hwAcEquipId, hwAcEquipName, hwAcInputOperStatus }
			STATUS current
			DESCRIPTION 
				"Description."
			::= { hwSiteAlarmTrapsPrefix 80 }

		
		-- 1.3.6.1.4.1.2011.6.164.2.1.0.81
		hwAcUnderVoltageTraps NOTIFICATION-TYPE
			OBJECTS {  hwAlarmTrapOrdinalNumber,hwAlarmText, hwAlarmLevel, hwAlarmSigDesc,hwSiteName, hwSiteAdminAddr,
					 hwNetIdentifier,hwSiteDescription, hwAcEquipId, hwAcEquipName, hwAcInputOperStatus }
			STATUS current
			DESCRIPTION 
				"Description."
			::= { hwSiteAlarmTrapsPrefix 81 }

		
		-- 1.3.6.1.4.1.2011.6.164.2.1.0.82
		hwAcUnderVoltageResumeTraps NOTIFICATION-TYPE
			OBJECTS {  hwAlarmTrapOrdinalNumber,hwAlarmText, hwAlarmLevel, hwAlarmSigDesc,hwSiteName, hwSiteAdminAddr, 
					 hwNetIdentifier,hwSiteDescription,hwAcEquipId, hwAcEquipName, hwAcInputOperStatus }
			STATUS current
			DESCRIPTION 
				"Description."
			::= { hwSiteAlarmTrapsPrefix 82 }
                                                           
		
		-- 1.3.6.1.4.1.2011.6.164.2.1.0.83
		hwPDELoadFaultTraps NOTIFICATION-TYPE
			OBJECTS { hwAlarmTrapOrdinalNumber,hwAlarmText, hwAlarmLevel, hwAlarmSigDesc,hwSiteName, hwSiteAdminAddr, 
					hwNetIdentifier,hwSiteDescription,  hwPDEGroupId, hwPDEGroupName  }
			STATUS current
			DESCRIPTION 
				"Description."
			::= { hwSiteAlarmTrapsPrefix 83 }
		
		-- 1.3.6.1.4.1.2011.6.164.2.1.0.84
		hwPDELoadFaultResumeTraps NOTIFICATION-TYPE
			OBJECTS { hwAlarmTrapOrdinalNumber,hwAlarmText, hwAlarmLevel, hwAlarmSigDesc, hwSiteName,hwSiteAdminAddr, 
					hwNetIdentifier,hwSiteDescription, hwPDEGroupId, hwPDEGroupName }
			STATUS current
			DESCRIPTION 
				"Description."
			::= { hwSiteAlarmTrapsPrefix 84 }
		
		-- 1.3.6.1.4.1.2011.6.164.2.1.0.85
		hwPDENoResponseTraps NOTIFICATION-TYPE
			OBJECTS { hwAlarmTrapOrdinalNumber,hwAlarmText, hwAlarmLevel, hwAlarmSigDesc,hwSiteName, hwSiteAdminAddr,
					 hwNetIdentifier,hwSiteDescription,  hwPDEEquipId, hwPDEEquipName, hwPDEOperStatus }
			STATUS current
			DESCRIPTION 
				"Description."
			::= { hwSiteAlarmTrapsPrefix 85 }
		
		-- 1.3.6.1.4.1.2011.6.164.2.1.0.86
		hwPDENoResponseResumeTraps NOTIFICATION-TYPE
			OBJECTS { hwAlarmTrapOrdinalNumber,hwAlarmText, hwAlarmLevel, hwAlarmSigDesc,hwSiteName, hwSiteAdminAddr, 
					 hwNetIdentifier,hwSiteDescription, hwPDEEquipId, hwPDEEquipName, hwPDEOperStatus }
			STATUS current
			DESCRIPTION 
				"Description."
			::= { hwSiteAlarmTrapsPrefix 86 }
		
		-- 1.3.6.1.4.1.2011.6.164.2.1.0.87
		hwPDEFailureTraps NOTIFICATION-TYPE
			OBJECTS { hwAlarmTrapOrdinalNumber,hwAlarmText, hwAlarmLevel, hwAlarmSigDesc,hwSiteName, hwSiteAdminAddr,
					  hwNetIdentifier,hwSiteDescription,hwPDEEquipId, hwPDEEquipName, hwPDEOperStatus }
			STATUS current
			DESCRIPTION 
				"Description."
			::= { hwSiteAlarmTrapsPrefix 87 }
		
		-- 1.3.6.1.4.1.2011.6.164.2.1.0.88
		hwPDEFailureResumeTraps NOTIFICATION-TYPE
			OBJECTS {  hwAlarmTrapOrdinalNumber,hwAlarmText, hwAlarmLevel, hwAlarmSigDesc,hwSiteName, hwSiteAdminAddr,
					 hwNetIdentifier,hwSiteDescription, hwPDEEquipId, hwPDEEquipName, hwPDEOperStatus }
			STATUS current
			DESCRIPTION 
				"Description."
			::= { hwSiteAlarmTrapsPrefix 88 }
		
		-- 1.3.6.1.4.1.2011.6.164.2.1.0.89
		hwPDEBr1FailureTraps NOTIFICATION-TYPE
			OBJECTS { hwAlarmTrapOrdinalNumber,hwAlarmText, hwAlarmLevel, hwAlarmSigDesc,hwSiteName, hwSiteAdminAddr,
					 hwNetIdentifier,hwSiteDescription,  hwPDEEquipId, hwPDEEquipName, hwPDEOperStatus }
			STATUS current
			DESCRIPTION 
				"Description."
			::= { hwSiteAlarmTrapsPrefix 89 }
		
		-- 1.3.6.1.4.1.2011.6.164.2.1.0.90
		hwPDEBr1FailureResumeTraps NOTIFICATION-TYPE
			OBJECTS { hwAlarmTrapOrdinalNumber,hwAlarmText, hwAlarmLevel, hwAlarmSigDesc,hwSiteName, hwSiteAdminAddr,
					 hwNetIdentifier,hwSiteDescription, hwPDEEquipId, hwPDEEquipName, hwPDEOperStatus }
			STATUS current
			DESCRIPTION 
				"Description."
			::= { hwSiteAlarmTrapsPrefix 90 }
		
		-- 1.3.6.1.4.1.2011.6.164.2.1.0.91
		hwPDEBr2FailureTraps NOTIFICATION-TYPE
			OBJECTS {  hwAlarmTrapOrdinalNumber,hwAlarmText, hwAlarmLevel, hwAlarmSigDesc,hwSiteName, hwSiteAdminAddr,
					 hwNetIdentifier,hwSiteDescription, hwPDEEquipId, hwPDEEquipName, hwPDEOperStatus }
			STATUS current
			DESCRIPTION 
				"Description."
			::= { hwSiteAlarmTrapsPrefix 91 }
		
		-- 1.3.6.1.4.1.2011.6.164.2.1.0.92
		hwPDEBr2FailureResumeTraps NOTIFICATION-TYPE
			OBJECTS { hwAlarmTrapOrdinalNumber,hwAlarmText, hwAlarmLevel, hwAlarmSigDesc,hwSiteName, hwSiteAdminAddr, 
					hwNetIdentifier,hwSiteDescription,  hwPDEEquipId, hwPDEEquipName, hwPDEOperStatus }
			STATUS current
			DESCRIPTION 
				"Description."
			::= { hwSiteAlarmTrapsPrefix 92 }
		
		-- 1.3.6.1.4.1.2011.6.164.2.1.0.93
		hwPDEBr3FailureTraps NOTIFICATION-TYPE
			OBJECTS { hwAlarmTrapOrdinalNumber,hwAlarmText, hwAlarmLevel, hwAlarmSigDesc,hwSiteName, hwSiteAdminAddr, 
					 hwNetIdentifier, hwSiteDescription, hwPDEEquipId, hwPDEEquipName, hwPDEOperStatus }
			STATUS current
			DESCRIPTION 
				"Description."
			::= { hwSiteAlarmTrapsPrefix 93 }
		
		-- 1.3.6.1.4.1.2011.6.164.2.1.0.94
		hwPDEBr3FailureResumeTraps NOTIFICATION-TYPE
			OBJECTS {  hwAlarmTrapOrdinalNumber,hwAlarmText, hwAlarmLevel, hwAlarmSigDesc,hwSiteName, hwSiteAdminAddr,
					 hwNetIdentifier, hwSiteDescription, hwPDEEquipId, hwPDEEquipName, hwPDEOperStatus }
			STATUS current
			DESCRIPTION 
				"Description."
			::= { hwSiteAlarmTrapsPrefix 94 }
		
		-- 1.3.6.1.4.1.2011.6.164.2.1.0.95
		hwPDEBr4FailureTraps NOTIFICATION-TYPE
			OBJECTS { hwAlarmTrapOrdinalNumber,hwAlarmText, hwAlarmLevel, hwAlarmSigDesc,hwSiteName, hwSiteAdminAddr,
					 hwNetIdentifier,hwSiteDescription,  hwPDEEquipId, hwPDEEquipName, hwPDEOperStatus }
			STATUS current
			DESCRIPTION 
				"Description."
			::= { hwSiteAlarmTrapsPrefix 95 }
		
		-- 1.3.6.1.4.1.2011.6.164.2.1.0.96
		hwPDEBr4FailureResumeTraps NOTIFICATION-TYPE
			OBJECTS { hwAlarmTrapOrdinalNumber,hwAlarmText, hwAlarmLevel, hwAlarmSigDesc,hwSiteName, hwSiteAdminAddr,
					 hwNetIdentifier, hwSiteDescription, hwPDEEquipId, hwPDEEquipName, hwPDEOperStatus }
			STATUS current
			DESCRIPTION 
				"Description."
			::= { hwSiteAlarmTrapsPrefix 96 }
		
		-- 1.3.6.1.4.1.2011.6.164.2.1.0.97
		hwPDEBr1ProtectTraps NOTIFICATION-TYPE
			OBJECTS { hwAlarmTrapOrdinalNumber,hwAlarmText, hwAlarmLevel, hwAlarmSigDesc,hwSiteName, hwSiteAdminAddr,
					 hwNetIdentifier, hwSiteDescription, hwPDEEquipId, hwPDEEquipName, hwPDEOperStatus }
			STATUS current
			DESCRIPTION 
				"Description."
			::= { hwSiteAlarmTrapsPrefix 97 }
		
		-- 1.3.6.1.4.1.2011.6.164.2.1.0.98
		hwPDEBr1ProtectResumeTraps NOTIFICATION-TYPE
			OBJECTS { hwAlarmTrapOrdinalNumber,	hwAlarmText, hwAlarmLevel, hwAlarmSigDesc,hwSiteName, hwSiteAdminAddr, 
					hwNetIdentifier,hwSiteDescription, hwPDEEquipId, hwPDEEquipName, hwPDEOperStatus }
			STATUS current
			DESCRIPTION 
				"Description."
			::= { hwSiteAlarmTrapsPrefix 98 }
		
		-- 1.3.6.1.4.1.2011.6.164.2.1.0.99
		hwPDEBr2ProtectTraps NOTIFICATION-TYPE
			OBJECTS { hwAlarmTrapOrdinalNumber,hwAlarmText, hwAlarmLevel, hwAlarmSigDesc,hwSiteName, hwSiteAdminAddr, 
					 hwNetIdentifier,hwSiteDescription,  hwPDEEquipId, hwPDEEquipName, hwPDEOperStatus }
			STATUS current
			DESCRIPTION 
				"Description."
			::= { hwSiteAlarmTrapsPrefix 99 }
		
		-- 1.3.6.1.4.1.2011.6.164.2.1.0.100
		hwPDEBr2ProtectResumeTraps NOTIFICATION-TYPE
			OBJECTS { hwAlarmTrapOrdinalNumber,hwAlarmText, hwAlarmLevel, hwAlarmSigDesc,hwSiteName, hwSiteAdminAddr, 
					hwNetIdentifier,hwSiteDescription, hwPDEEquipId, hwPDEEquipName, hwPDEOperStatus }
			STATUS current
			DESCRIPTION 
				"Description."
			::= { hwSiteAlarmTrapsPrefix 100 }
		
		-- 1.3.6.1.4.1.2011.6.164.2.1.0.101
		hwPDEBr3ProtectTraps NOTIFICATION-TYPE
			OBJECTS { hwAlarmTrapOrdinalNumber,hwAlarmText, hwAlarmLevel, hwAlarmSigDesc,hwSiteName, hwSiteAdminAddr, 
					 hwNetIdentifier,hwSiteDescription, hwPDEEquipId, hwPDEEquipName, hwPDEOperStatus }
			STATUS current
			DESCRIPTION 
				"Description."
			::= { hwSiteAlarmTrapsPrefix 101 }
		
		-- 1.3.6.1.4.1.2011.6.164.2.1.0.102
		hwPDEBr3ProtectResumeTraps NOTIFICATION-TYPE
			OBJECTS { hwAlarmTrapOrdinalNumber, hwAlarmText, hwAlarmLevel, hwAlarmSigDesc,hwSiteName, hwSiteAdminAddr, 
					hwNetIdentifier,hwSiteDescription, hwPDEEquipId, hwPDEEquipName, hwPDEOperStatus }
			STATUS current
			DESCRIPTION 
				"Description."
			::= { hwSiteAlarmTrapsPrefix 102 }
		
		-- 1.3.6.1.4.1.2011.6.164.2.1.0.103
		hwPDEBr4ProtectTraps NOTIFICATION-TYPE
			OBJECTS { hwAlarmTrapOrdinalNumber,hwAlarmText, hwAlarmLevel, hwAlarmSigDesc,hwSiteName, hwSiteAdminAddr, 
					hwNetIdentifier,hwSiteDescription, hwPDEEquipId, hwPDEEquipName, hwPDEOperStatus }
			STATUS current
			DESCRIPTION 
				"Description."
			::= { hwSiteAlarmTrapsPrefix 103 }
		
		-- 1.3.6.1.4.1.2011.6.164.2.1.0.104
		hwPDEBr4ProtectResumeTraps NOTIFICATION-TYPE
			OBJECTS {hwAlarmTrapOrdinalNumber,hwAlarmText, hwAlarmLevel, hwAlarmSigDesc, hwSiteName, hwSiteAdminAddr,
					 hwNetIdentifier,hwSiteDescription,hwPDEEquipId, hwPDEEquipName,hwPDEOperStatus }
			STATUS current
			DESCRIPTION 
				"Description."
			::= { hwSiteAlarmTrapsPrefix 104 }
		
		-- 1.3.6.1.4.1.2011.6.164.2.1.0.105
		hwPDELostTraps NOTIFICATION-TYPE
			OBJECTS { hwAlarmTrapOrdinalNumber,hwAlarmText, hwAlarmLevel, hwAlarmSigDesc,hwSiteName, hwSiteAdminAddr,
					  hwNetIdentifier,hwSiteDescription, hwPDEGroupId, hwPDEGroupName }
			STATUS current
			DESCRIPTION 
				"Description."
			::= { hwSiteAlarmTrapsPrefix 105 }
		
		-- 1.3.6.1.4.1.2011.6.164.2.1.0.106
		hwPDELostResumeTraps NOTIFICATION-TYPE
			OBJECTS {  hwAlarmTrapOrdinalNumber,hwAlarmText, hwAlarmLevel, hwAlarmSigDesc,hwSiteName, hwSiteAdminAddr, 
					 hwNetIdentifier,hwSiteDescription, hwPDEGroupId, hwPDEGroupName }
			STATUS current
			DESCRIPTION 
				"Description."
			::= { hwSiteAlarmTrapsPrefix 106 }
                                                           
		
		-- 1.3.6.1.4.1.2011.6.164.2.2
		hwSiteDevicesTraps OBJECT IDENTIFIER ::= { hwSiteMonitorMIBTraps 2 }

		
		-- 1.3.6.1.4.1.2011.6.164.2.2.0
		hwDevicesTrapsPrefix OBJECT IDENTIFIER ::= { hwSiteDevicesTraps 0 }

		
		-- 1.3.6.1.4.1.2011.6.164.2.2.0.1
		hwRectifiersInslotChange NOTIFICATION-TYPE
			OBJECTS { hwDeviceTrapOrdinalNumber, hwSiteName, hwSiteAdminAddr, hwNetIdentifier, hwSiteDescription,  
					hwRectEquipId, hwRectEquipName, hwRectOperStatus }
			STATUS current
			DESCRIPTION 
				"When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
				This trap is the unique trigger condition that causes the NMS to add or delete entries to or from hwRectConfigTable or hwRectOperTable."
			::= { hwDevicesTrapsPrefix 1 }

		
		-- 1.3.6.1.4.1.2011.6.164.2.2.0.2
		hwBatterysInslotChange NOTIFICATION-TYPE
			OBJECTS { hwDeviceTrapOrdinalNumber, hwSiteName, hwSiteAdminAddr, hwNetIdentifier, hwSiteDescription,  
					hwBattStringEquipId, hwBattStringEquipName, hwBattStringOperStatus }
			STATUS current
			DESCRIPTION 
				"When the presence status of a battery string changes, the node reports an event. Then the NMS adds or deletes the corresponding entry to or from hwBatttConfigTable or hwBatttOperTable. The bound information includes the site address, site name, site description, and NE identifier. In addition, the ID, name, and status of the battery string are bound to identify the specific battery string and its operation type. When an entry is added, the device status is reported as normal (1); when an entry is deleted, the device status is reported as loopBreak (4).
				This trap is the unique trigger condition that causes the NMS to add or delete entries to or from hwBatttConfigTable or hwBatttOperTable."
			::= { hwDevicesTrapsPrefix 2 }

		
		-- 1.3.6.1.4.1.2011.6.164.2.2.0.3
		hwBattTestRecordsAdd NOTIFICATION-TYPE
			OBJECTS { hwDeviceTrapOrdinalNumber, hwSiteName, hwSiteDescription, hwNetIdentifier,  hwSiteAdminAddr }
			STATUS current
			DESCRIPTION 
				"After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
				This trap is the unique trigger condition that causes the NMS to add entries from hwBattsTestResultTable.
				The battery test table allows you only to add entries."
			::= { hwDevicesTrapsPrefix 3 }

		
		-- 1.3.6.1.4.1.2011.6.164.2.2.0.4
		hwEnvTempSensInslotChange NOTIFICATION-TYPE
			OBJECTS {  hwDeviceTrapOrdinalNumber, hwSiteName,hwSiteAdminAddr, hwNetIdentifier,hwSiteDescription,  
					hwEnvTempEquipId, hwEnvTempEquipName, hwEnvTempSensorOperStatus }
			STATUS current
			DESCRIPTION 
				"When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
				This trap is the unique trigger condition that causes the NMS to add or delete entries to or from hwEnvTempSensorTable."
			::= { hwDevicesTrapsPrefix 4 }

		
		-- 1.3.6.1.4.1.2011.6.164.2.2.0.5
		hwEnvHumiSensInslotChange NOTIFICATION-TYPE
			OBJECTS { hwDeviceTrapOrdinalNumber, hwSiteName, hwSiteAdminAddr, hwNetIdentifier,hwSiteDescription, 
					hwEnvHumiEquipId, hwEnvHumiEquipName, hwEnvHumiSensorOperStatus   }
			STATUS current
			DESCRIPTION 
				"When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
				This trap is the unique trigger condition that causes the NMS to add or delete entries to or from hwEnvHumiSensorTable."
			::= { hwDevicesTrapsPrefix 5 }
			
					-- 1.3.6.1.4.1.2011.6.164.2.2.0.6
		hwPDEsInslotChange NOTIFICATION-TYPE
			OBJECTS { hwDeviceTrapOrdinalNumber,hwSiteName, hwSiteAdminAddr, hwNetIdentifier,hwSiteDescription, 
				 hwPDEEquipId, hwPDEEquipName, hwPDEOperStatus  }
			STATUS current
			DESCRIPTION 
				"Description."
			::= { hwDevicesTrapsPrefix 6 }
                                               
                                               
                                               
		
		-- 1.3.6.1.4.1.2011.6.164.2.3
		hwV101SiteDevicesTraps OBJECT IDENTIFIER ::= { hwSiteMonitorMIBTraps 3 }

		
		-- 1.3.6.1.4.1.2011.6.164.2.3.0
		hwV101DevicesTrapsPrefix OBJECT IDENTIFIER ::= { hwV101SiteDevicesTraps 1 }

		
		-- 1.3.6.1.4.1.2011.6.164.2.3.0.1
		hwRectifiersInslotChange NOTIFICATION-TYPE
			OBJECTS { hwDeviceTrapOrdinalNumber, hwSiteName, hwSiteAdminAddr, hwNetIdentifier, hwSiteDescription,  
					hwRectEquipId, hwRectEquipName, hwRectOperStatus }
			STATUS current
			DESCRIPTION 
				"When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
				This trap is the unique trigger condition that causes the NMS to add or delete entries to or from hwRectConfigTable or hwRectOperTable."
			::= { hwV101DevicesTrapsPrefix 1 }

		
		-- 1.3.6.1.4.1.2011.6.164.2.3.0.2
		hwBatterysInslotChange NOTIFICATION-TYPE
			OBJECTS { hwDeviceTrapOrdinalNumber, hwSiteName, hwSiteAdminAddr, hwNetIdentifier, hwSiteDescription,  
					hwBattStringEquipId, hwBattStringEquipName, hwBattStringOperStatus }
			STATUS current
			DESCRIPTION 
				"When the presence status of a battery string changes, the node reports an event. Then the NMS adds or deletes the corresponding entry to or from hwBatttConfigTable or hwBatttOperTable. The bound information includes the site address, site name, site description, and NE identifier. In addition, the ID, name, and status of the battery string are bound to identify the specific battery string and its operation type. When an entry is added, the device status is reported as normal (1); when an entry is deleted, the device status is reported as loopBreak (4).
				This trap is the unique trigger condition that causes the NMS to add or delete entries to or from hwBatttConfigTable or hwBatttOperTable."
			::= { hwV101DevicesTrapsPrefix 2 }

		
		-- 1.3.6.1.4.1.2011.6.164.2.3.0.3
		hwBattTestRecordsAdd NOTIFICATION-TYPE
			OBJECTS { hwDeviceTrapOrdinalNumber, hwSiteName, hwSiteDescription, hwNetIdentifier,  hwSiteAdminAddr }
			STATUS current
			DESCRIPTION 
				"After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
				This trap is the unique trigger condition that causes the NMS to add entries from hwBattsTestResultTable.
				The battery test table allows you only to add entries."
			::= { hwV101DevicesTrapsPrefix 3 }

		
		-- 1.3.6.1.4.1.2011.6.164.2.3.0.4
		hwEnvTempSensInslotChange NOTIFICATION-TYPE
			OBJECTS {  hwDeviceTrapOrdinalNumber, hwSiteName,hwSiteAdminAddr, hwNetIdentifier,hwSiteDescription,  
					hwEnvTempEquipId, hwEnvTempEquipName, hwEnvTempSensorOperStatus }
			STATUS current
			DESCRIPTION 
				"When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
				This trap is the unique trigger condition that causes the NMS to add or delete entries to or from hwEnvTempSensorTable."
			::= { hwV101DevicesTrapsPrefix  4 }

		
		-- 1.3.6.1.4.1.2011.6.164.2.3.0.5
		hwEnvHumiSensInslotChange NOTIFICATION-TYPE
			OBJECTS { hwDeviceTrapOrdinalNumber, hwSiteName, hwSiteAdminAddr, hwNetIdentifier,hwSiteDescription, 
					hwEnvHumiEquipId, hwEnvHumiEquipName, hwEnvHumiSensorOperStatus   }
			STATUS current
			DESCRIPTION 
				"When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
				This trap is the unique trigger condition that causes the NMS to add or delete entries to or from hwEnvHumiSensorTable."
			::= { hwV101DevicesTrapsPrefix 5 }
			
		-- 1.3.6.1.4.1.2011.6.164.2.3.0.6
		hwPDEsInslotChange NOTIFICATION-TYPE
			OBJECTS { hwDeviceTrapOrdinalNumber,hwSiteName, hwSiteAdminAddr, hwNetIdentifier,hwSiteDescription, 
				 hwPDEEquipId, hwPDEEquipName, hwPDEOperStatus  }
			STATUS current
			DESCRIPTION 
				"Description."
			::= { hwV101DevicesTrapsPrefix 6 }
                                               
		
		-- 1.3.6.1.4.1.2011.6.164.3
		hwSiteMonitorMIBConformance OBJECT IDENTIFIER ::= { hwSiteMonitorMIB 3 }

		
		-- 1.3.6.1.4.1.2011.6.164.3.1
		hwSiteMonitorGroups OBJECT IDENTIFIER ::= { hwSiteMonitorMIBConformance 1 }

		
--  1.3.6.1.4.1.2011.6.1.6
		-- 1.3.6.1.4.1.2011.6.164.3.1.1
		hwSiteInfoGroup OBJECT-GROUP
			OBJECTS { hwSiteName, hwSiteDescription, hwSiteId, hwSiteIp, hwSiteNetmask, 
				hwAlarmIndex, hwAlarmLevel, hwAlarmSigDesc, hwAlarmQuantity, hwAlarmRowStatus, 
				hwSiteGateway, hwNetIdentifier, hwAlarmText, hwDeviceTrapOrdinalNumber, hwAlarmTrapOrdinalNumber, 
				hwSiteAdminAddr }
			STATUS current
			DESCRIPTION 
				"Site information group."
			::= { hwSiteMonitorGroups 1 }

		
		-- 1.3.6.1.4.1.2011.6.164.3.1.2
		hwSiteMonitorsGroup OBJECT-GROUP
			OBJECTS { hwMonsGroupId, hwMonsGroupName, hwMonIndex, hwMonEquipId, hwMonEquipName, 
				hwMonEquipPcbVersion, hwMonEquipManufacturer, hwMonEquipManuDate, hwMonEquipSerialNo, hwMonEquipDescription, 
				hwCtrlMonEquipReset, hwMonRowStatus, hwMonitorOperStatus, hwMonsQuantity, hwMonEquipOperTotalTime, 
				hwMonEquipSoftwareVersion, hwSetMonEquipCtrlState }
			STATUS current
			DESCRIPTION 
				"Site monitor group."
			::= { hwSiteMonitorGroups 2 }

		
		-- 1.3.6.1.4.1.2011.6.164.3.1.3
		hwSiteRectifiersGroup OBJECT-GROUP
			OBJECTS { hwRectSerialNo, hwRectType, hwRectManufacturer, hwRectOutputCurrent, hwRectOutputVoltage,
				hwRectDCOutputPower, hwRectACVoltage, hwRectRatedEfficiency, hwRectifierTemperature,
				hwCtrlRectOnOff, hwRectEquipId, hwRectEquipName, hwRectRatedCurrent, hwRectInputAcType, 
				hwRectEfficency, hwRectConfigIndex, hwRectConfigRowStatus, hwRectsGroupId, hwRectsGroupName, 
				hwRectsTotalQuantity, hwRectsRatedVoltage, hwModifyRectsOutputVoltage, hwSetRectsRedundEnable, hwRectManuDate, 
				hwCtrlRectsAllOnOff, hwRectsTotalDCPower, hwRectsTotalACInputPower, hwRectsTotalCurrent, hwRectOperStatus, hwRectOperIndex, hwRectTotalOperTime, 
				hwRectSoftwareVersion, hwRectOperRowStatus }
			STATUS current
			DESCRIPTION 
				"Site rectifier group."
			::= { hwSiteMonitorGroups 3 }

		
		-- 1.3.6.1.4.1.2011.6.164.3.1.4
		hwSiteBatterysGroup OBJECT-GROUP
			OBJECTS { hwBattStringCurrent, hwBattStringRemainCapacity, hwSetBattInstallTime, hwBattStringEquipId, hwBattStringEquipName, 
				hwBattStringRemainCapacityPercent, hwBattStringActualCapacity, hwSetBattStdCapacity, hwBattStringTemprature, hwBattsGroupId, 
				hwBattsGroupName, hwSetBattsHighTempAction, hwSetBattsHighTempVoltLimit, hwSetBattsFloatVoltage, hwSetBattsBoostVoltage, 
				hwSetBattsCompFactor, hwBattsChargeStatus, hwBattsCurrLimitStatus, hwBattsTemprature, hwBattsRatedCapacity, hwBattsRemainCapacity, 
				hwCtrlBattsTestStartStop, hwBattsTestResultIndex, hwTotalRemainingCapacityPercent, 
				hwBattsTestType, hwBattsTestStartTime, hwBattsTestResult, hwBattsEfficiency, hwBattsDischargeTime, 
				hwBattsDischargeEndVoltage, hwBattsDischargeAvCurrent, hwBattsDischargeAhValue, hwBattsTestTemprature, hwBattsTestEndCourse, 
				hwBattsTestResultRowStatus, hwBattStringConfigIndex, hwBattStringConfigRowStatus, hwSetBattsTempUpperLimit, hwSetBattsTempLowerLimit, 
				hwSetBattsCurrLimitCoefficient, hwBattsTotalCurrent, hwSetBattsHTDLimit, hwBattsTestRecordCount, hwBattStringOperStatus, 
				hwSetBattsTempMeasureUpperLimit, hwSetBattsTempMeasureLowerLimit, hwBattsPreDischargeTime, hwBattsTotalQuantity, hwSetBattsManuStdTestTime, 
				hwSetBattsManuStdTestEndVolt, hwSetBattsManuStdTestCellNum, hwSetBattsManuShortTestTime, hwSetBattsManuShortTestEndVolt, hwBattStringOperIndex, 
				hwSetBattsHTDEnable, hwBattStringOperRowStatus, hwCtrlBattsBoostFloat }
			STATUS current
			DESCRIPTION 
				"Site battery group."
			::= { hwSiteMonitorGroups 4 }

		
		-- 1.3.6.1.4.1.2011.6.164.3.1.5
		hwSiteAcDistributionsGroup OBJECT-GROUP
			OBJECTS { hwSetAcsUpperVoltLimit, hwSetAcsLowerVoltLimit, hwApOrAblVoltage, hwBpOrBclVoltage, hwCpOrCalVoltage, 
				hwAphaseCurrent, hwBphaseCurrent, hwCphaseCurrent, hwAcsGroupId, hwAcsGroupName, 
				hwAcInputIndex, hwAcRowStatus, hwAcEquipId, hwAcInputOperStatus, hwAcEquipName, 
				hwAcsTotalCurrent, hwAcsTotalQuantity, hwSiteDescription, hwAcInputBreakerIndex, hwAcInputBreakerEquipId, 
				hwAcInputBreakerEquipName, hwAcInputBreakerOperStatus, hwAcInputBreakerRowStatus, hwAcInputBreakersQuantity }
			STATUS current
			DESCRIPTION 
				"Site AC distribution group."
			::= { hwSiteMonitorGroups 5 }

		
		-- 1.3.6.1.4.1.2011.6.164.3.1.6
		hwSiteDcDistributionsGroup OBJECT-GROUP
			OBJECTS { hwSetDcsUpperVoltLimit, hwSetDcsLowerVoltLimit, hwDcOutputIndex, hwDcOutputVoltage, hwDcOutputCurrent, 
				hwDcOutputPower, hwDcOutputRowStatus, hwLoadBranchIndex, hwLoadBranchPower, hwDcOutputEquipId, 
				hwDcOutputEquipName, hwLoadBranchEquipId, hwDcOutputOperStatus, hwLoadBranchOperStatus, hwLoadBranchRowStatus, 
				hwLvdUnitEquipName, hwLoadBranchEquipName, hwDcsGroupId, hwDcsGroupName, hwDcsTotalVoltage, 
				hwDcsTotalCurrent, hwDcsTotalPower, hwDcsTotalQuantity, hwLoadsQuantity, hwLoadBranchCurrent
				 }
			STATUS current
			DESCRIPTION 
				"Site DC distribution group."
			::= { hwSiteMonitorGroups 6 }

		
		-- 1.3.6.1.4.1.2011.6.164.3.1.7
		hwSiteLvdUnitsGroup OBJECT-GROUP
			OBJECTS { hwLvdBranchIndex, hwLvdBranchRowStatus, hwLvdUnitEquipId, hwLvdsGroupId, hwLvdUnitEquipName, 
				hwLvdsGroupName, hwSetLvdVoltage, hwCtrlLvd, hwLvdsTotalQuantity, hwLvdBranchOperStatus, 
				hwSetLvdEnable }
			STATUS current
			DESCRIPTION 
				"Site low voltage disconnection unit group."
			::= { hwSiteMonitorGroups 7 }

		
		-- 1.3.6.1.4.1.2011.6.164.3.1.8
		hwSiteEnvUnitsGroup OBJECT-GROUP
			OBJECTS { hwCtrlSmokeReset, hwCtrlDoorReset, hwEnvTempSensorIndex, hwEnvTemperature, hwEnvHumiSensorIndex, 
				hwEnvHumidity, hwEnvHumiEquipId, hwEnvHumiEquipName, hwEnvTempEquipId, hwEnvTempEquipName, 
				hwEnvUnitsGroupId, hwEnvUnitsGroupName, hwSetEnvTempAlarmEnable, hwSetEnvHumiAlarmEnable, hwCtrlBuzzerEnable, 
				hwSetEnvTempUpperLimit, hwSetEnvTempLowerLimit, hwEnvTempSensorRowStatus, hwSetEnvHumidityUpperLimit, hwSetEnvHumidityLowerLimit, 
				hwEnvHumiSensorRowStatus, hwEnvTempSensorOperStatus, hwEnvHumiSensorOperStatus, hwSetEnvTempMeasureUpperLimit, hwSetEnvTempMeasureLowerLimit, 
				hwSetEnvHumidityMeasureUpperLimit, hwSetEnvHumidityMeasureLowerLimit, hwEnvTempSensorsTotalQuantity, hwEnvHumiSensorsTotalQuantity, hwSpareDigitalIndex, 
				hwSpareDigitalEquipId, hwSpareDigitalEquipName, hwSetSpareDigitalAlarmTension, hwSetSpareDigitalAlarmEnable, hwSpareDigitalOperStatus, 
				hwSpareDigitalRowStatus, hwSpareDigitalsTotalQuantity }
			STATUS current
			DESCRIPTION 
				"Site envirenment unit group."
			::= { hwSiteMonitorGroups 8 }

		
--  1.3.6.1.4.1.2011.6.1.7.3
		-- 1.3.6.1.4.1.2011.6.164.3.1.9
		hwSiteAlarmTrapsGroup NOTIFICATION-GROUP
			NOTIFICATIONS { hwAcInputAlarmTraps, hwAcInputAlarmResumeTraps, hwAcVoltAlarmTraps, hwAcVoltAlarmResumeTraps, hwDcVoltAlarmTraps, 
				hwDcVoltAlarmResumeTraps, hwLoadLvdAlarmTraps, hwLoadLvdAlarmResumeTraps, hwBattLvdAlarmTraps, hwBattLvdAlarmResumeTraps, 
				hwBattLoopBreakAlarmTraps, hwBattLoopBreakAlarmResumeTraps, hwEnvTempAlarmTraps, hwEnvTempAlarmResumeTraps, hwEnvHumiAlarmTraps, 
				hwEnvHumiAlarmResumeTraps, hwDoorAlarmTraps, hwDoorAlarmResumeTraps, hwWaterAlarmTraps, hwWaterAlarmResumeTraps, 
				hwSmokeAlarmTraps, hwSmokeAlarmResumeTraps, hwRectifierFaultAlarmTraps, hwRectifierFaultAlarmResumeTraps, hwRectifierAbnormalAlarmTraps, 
				hwRectifierAbnormalAlarmResumeTraps, hwBattOverCurrAlarmTraps, hwBattOverCurrAlarmResumeTraps, hwLoadFuseAlarmTraps, hwLoadFuseAlarmResumeTraps, 
				hwRs485CommAlarmTraps, hwRs485CommAlarmResumeTraps, hwNetCommAlarmTraps, hwNetCommAlarmResumeTraps, hwMultiRectFailureAlarmTraps, 
				hwMultiRectFailureAlarmResumeTraps, hwRectRedundAlarmTraps, hwRectRedundAlarmResumeTraps, hwBattUnbalanceAlarmTraps, hwBattUnbalanceAlarmResumeTraps, 
				hwAcFreqFaultAlarmTraps, hwWireAlarmTraps, hwWireAlarmResumeTraps, hwAcFreqFaultAlarmResumeTraps, hwXmuSelfFaultAlarmTraps, 
				hwAcBreakerAlarmTraps, hwAcBreakerAlarmResumeTraps, hwBattDischargeAlarmTraps, hwBattDischargeAlarmResumeTraps, hwXmuSelfFaultAlarmResumeTraps, 
				hwBattStringTempAlarmTraps, hwBattStringTempAlarmResumeTraps, hwSpareDigitalAlarmTraps, hwSpareDigitalAlarmResumeTraps, hwAcOffLongTimeAlarmTraps, 
				hwAcOffLongTimeAlarmResumeTraps, hwSpdAlarmTraps, hwSpdAlarmResumeTraps, hwBadBatteryTraps, hwBadBatteryResumeTraps, 
				hwLvd2DisconnectingTraps, hwLvd2DisconnectingResumeTraps, hwBattHighTempTraps, hwBattHighTempResumeTraps, hwBattLowTempTraps, 
				hwBattLowTempResumeTraps, hwDcUltraOverVoltageTraps, hwDcUltraOverVoltageResumeTraps, hwDcUltraUnderVoltageTraps, hwDcUltraUnderVoltageResumeTraps, 
				hwUmiCommFailTraps, hwUmiCommFailResumeTraps, hwShortTestFailTraps, hwShortTestFailResumeTraps, hwMissingBattTempSensorTraps, 
				hwMissingBattTempSensorResumeTraps, hwBattTempSensorFaultTraps, hwBattTempSensorFaultResumeTraps, hwAcOverVoltageTraps, hwAcOverVoltageResumeTraps, 
				hwAcUnderVoltageTraps, hwAcUnderVoltageResumeTraps, hwBattTestRecordsAdd, hwPDENoResponseTraps, hwPDENoResponseResumeTraps, 
				hwPDELostTraps, hwPDELostResumeTraps, hwPDELoadFaultTraps, hwPDELoadFaultResumeTraps, hwPDEFailureTraps, 
				hwPDEFailureResumeTraps, hwPDEBr1FailureTraps, hwPDEBr1FailureResumeTraps, hwPDEBr2FailureTraps, hwPDEBr2FailureResumeTraps, 
				hwPDEBr3FailureTraps, hwPDEBr3FailureResumeTraps, hwPDEBr4FailureTraps, hwPDEBr4FailureResumeTraps, hwPDEBr1ProtectTraps, 
				hwPDEBr1ProtectResumeTraps, hwPDEBr2ProtectTraps, hwPDEBr2ProtectResumeTraps, hwPDEBr3ProtectTraps, hwPDEBr3ProtectResumeTraps, 
				hwPDEBr4ProtectTraps, hwPDEBr4ProtectResumeTraps }
			STATUS current
			DESCRIPTION 
				"Site alarm trap group."
			::= { hwSiteMonitorGroups 9 }

		
		-- 1.3.6.1.4.1.2011.6.164.3.1.10
		hwSiteDeviceTrapsGroup NOTIFICATION-GROUP
			NOTIFICATIONS { hwRectifiersInslotChange, hwBatterysInslotChange, hwBattTestRecordsAdd, hwEnvTempSensInslotChange, hwEnvHumiSensInslotChange, 
				hwPDEsInslotChange }
			STATUS current
			DESCRIPTION 
				"Description."
			::= { hwSiteMonitorGroups 10 }

		-- 1.3.6.1.4.1.2011.6.164.3.1.11
		hwSiteEfusesGroup OBJECT-GROUP
			OBJECTS { hwPDEGroupId, hwPDEGroupName, hwPDEGroupNum, hwPDEGroupCommNum, hwPDEGroupTotalPower, 
				hwPDEGroupTotalCurrent, hwPDEGroupCommStatus, hwPDEIndex, hwPDEEquipId, hwPDEEquipName, 
				hwPDETotalRunningTime, hwPDEBranchNum, hwPDETotalPower, hwPDETotalCurrent, hwPDEBranch1Power, 
				hwPDEBranch2Power, hwPDEBranch3Power, hwPDEBranch4Power, hwPDEBranch1Current, hwPDEBranch2Current, 
				hwPDEBranch3Current, hwPDEBranch4Current, hwPDEBranch1Voltage, hwPDEBranch2Voltage, hwPDEBranch3Voltage, 
				hwPDEBranch4Voltage, hwPDEBranch1Temperature, hwPDEBranch2Temperature, hwPDEBranch3Temperature, hwPDEBranch4Temperature, 
				hwPDEOperStatus, hwPDERowStatus, hwPDEConfigIndex, hwPDEConfigEquipId, hwPDEConfigEquipName, 
				hwPDEOverTempProtect, hwPDEVolProtectEnable, hwPDEOverVoltageProtect, hwPDEUnderVoltageProtect, hwPDEHysteresis, 
				hwPDEReset, hwPDEBranch1Control, hwPDEBranch2Control, hwPDEBranch3Control, hwPDEBranch4Control, 
				hwPDEBranch1CurrentLimit, hwPDEBranch2CurrentLimit, hwPDEBranch3CurrentLimit, hwPDEBranch4CurrentLimit, hwPDEConfigRowStatus
				 }
			STATUS current
			DESCRIPTION 
				"Description."
			::= { hwSiteMonitorGroups 11 }
		
	
	END

--
-- HUAWEI-SITE-MONITOR-MIB.mib
--
