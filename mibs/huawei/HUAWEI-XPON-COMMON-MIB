-- =================================================================                                                  
-- Copyright (C) 2019 by HUAWEI TECHNOLOGIES. All rights reserved                                                   
-- Description:  The MIB is used for defining Huawei's GPON management common MIB objects for both                 
--               profile-mode and distributing-mode.                                                             
-- Reference:                                                                                                 
-- Version: V2.33
-- ================================================================                    
    HUAWEI-XPON-COMMON-MIB DEFINITIONS ::= BEGIN
        IMPORTS
            MODULE-IDENTITY, mib-2, OBJECT-TYPE, Counter32, Counter64,
            Unsigned32, Integer32, zeroDotZero, IpAddress, Gauge32, NOTIFICATION-TYPE
                FROM SNMPv2-SMI
            TruthValue, DateAndTime, RowStatus, MacAddress,TEXTUAL-CONVENTION
                FROM SNMPv2-TC
            InetAddressType,InetAddress
                FROM INET-ADDRESS-MIB     -- RFC 4001
            ifIndex
                FROM IF-MIB
            MODULE-COMPLIANCE, OBJECT-GROUP
                FROM SNMPv2-CONF
            OwnerString, EntryStatus
                FROM RMON-MIB
            huaweiMgmt, huaweiUtility
                FROM HUAWEI-MIB
            hwFrameIndex, hwSlotIndex
		FROM HUAWEI-DEVICE-MIB;    


        hwXponCommonMIB MODULE-IDENTITY
            LAST-UPDATED "201909041000Z"
            ORGANIZATION "Huawei Technologies Co.,Ltd."
            CONTACT-INFO                                        
                         "Huawei Industrial Base                
                          Bantian, Longgang                     
                          Shenzhen 518129                       
                          People's Republic of China            
                          Website: http://www.huawei.com        
                          Email: support@huawei.com             
                         "                                      
            DESCRIPTION  "The MIB is used for defining Huawei's GPON management common MIB objects for both profile-mode and distributing-mode."
  
    --  Revision history
            REVISION     "201909041000Z"
            DESCRIPTION  "V2.33, changes in this revision:
                          - Add the leaf hw10GponOltOpticsModuleInfoPartNum in table Hw10GponOltOpticsModuleInformationEntry.
						  - Add the enum value of the leaf hwGponPortRunFlexMode in table hwGponPortInfoEntry
                         " 
            REVISION     "201907251000Z"
            DESCRIPTION  "V2.32, changes in this revision:
                          - Add the enumerate of the leaf  hwXponOpticalType in table hwXponOpticalDdmProfileReferenceTable.
                          - Add the enumerate of the leaf hwXponOpticalSubType.
                         " 

            REVISION     "201907101000Z"
            DESCRIPTION  "V2.31, changes in this revision:
                          - Add the offline reason in the description of the hwXponOntBatchQueryInfo node in the hwXponOntBatchInfoTable table.
                         " 

            REVISION     "201905281000Z"  
            DESCRIPTION  "V2.30, changes in this revision:    	
                          - Add the enumerate of the leaf hwXponOntInfoInteroperabilityStandard.
                          - Add the enumerate of the leaf hwGponInteroperModeSwitch. 
                          - Add the enumerate of the leaf hwGponOntInteroperabilityMode.
                         " 
						 
            REVISION     "201904101000Z"
            DESCRIPTION  "V2.29, changes in this revision:
                         - Add a table hwXponOntDIDOTable.
                         "

            REVISION     "201903161000Z"  
            DESCRIPTION  "V2.28, changes in this revision:    
	                     - Add the enum value of the leaf  hwXponOpticsDdmInfoExSubType in table hwXponOpticsDdmInfoExTable.
			     - Add the enum value of the leaf  hwXponOpticalSubType in table hwXponOpticalDdmProfileReferenceTable.
			     - Add the enum value of the leaf  hw10GponOltOpticsModuleXponSubType in table hw10GponOltOpticsModuleInformationTable. 	
	                     	
	                     " 
            REVISION     "201903151000Z"  
            DESCRIPTION  "V2.27, changes in this revision:    	
                         - Modify the value range of the leaf hwXponOntTr069ServerProfileUserName in table hwXponOntTr069ServerProfileTable.
                         - Modify the value range of the leaf hwXponOntTr069ServerProfilePassword in table hwXponOntTr069ServerProfileTable.
                         - Modify the value range of the leaf hwXponOntFtpServerProfileUserName in table hwXponOntFtpServerProfileTable.
                         - Modify the value range of the leaf hwXponOntFtpServerProfilePassword in table hwXponOntFtpServerProfileTable.
                         " 
	    REVISION     "201903011000Z"  
            DESCRIPTION  "V2.26, changes in this revision:    	
                          - Add the enumerate of the leaf hwXponOntInfoInteroperabilityStandard.
                          - Add the enumerate of the leaf hwGponInteroperModeSwitch. 
                          - Add the enumerate of the leaf hwGponOntInteroperabilityMode.
                         " 		 
            REVISION     "201901041000Z"  
            DESCRIPTION  "V2.25, changes in this revision:    	
                          - Add the enumerate of the leaf hwXponOntInfoInteroperabilityStandard.
                          - Add the enumerate of the leaf hwGponInteroperModeSwitch. 
                          - Add the enumerate of the leaf hwGponOntInteroperabilityMode.
                         " 
						 
	        REVISION     "201808261000Z"  
            DESCRIPTION  "V2.24, changes in this revision:    
	                     - Add the enmu value of the leaf  hwGponBoardWorkMode in table hwGponBoardWorkModeTable. 	
	                     - Add the enmu value of the leaf hwGponPortControlFlexMode in table hwGponPortControlTable.							 
	                   " 
					   
	        REVISION     "201808251000Z"  
            DESCRIPTION  "V2.23, changes in this revision:                                      
	                     - Add the leaf hwXponPortTrafficStatisticUp1GChannelRate in table hwXponPortTrafficStatisticTable.
	                     - Add the leaf hwXponPortTrafficStatisticUp1GChannelBandwidthUsage in table hwXponPortTrafficStatisticTable.
	                     - Add the leaf hwXponPortTrafficStatisticUp1GChannelUnicastRate in table hwXponPortTrafficStatisticTable.
	                     - Add the leaf hwXponPortTrafficStatisticUp1GChannelMulticastRate in table hwXponPortTrafficStatisticTable.
	                     - Add the leaf hwXponPortTrafficStatisticUp1GChannelBroadcastRate in table hwXponPortTrafficStatisticTable.
	                     - Add the leaf hwXponPortTrafficStatisticUp10GChannelRate in table hwXponPortTrafficStatisticTable.
	                     - Add the leaf hwXponPortTrafficStatisticUp10GChannelBandwidthUsage in table hwXponPortTrafficStatisticTable.
	                     - Add the leaf hwXponPortTrafficStatisticUp10GChannelUnicastRate in table hwXponPortTrafficStatisticTable.
	                     - Add the leaf hwXponPortTrafficStatisticUp10GChannelMulticastRate in table hwXponPortTrafficStatisticTable.
	                     - Add the leaf hwXponPortTrafficStatisticUp10GChannelBroadcastRate in table hwXponPortTrafficStatisticTable.
	                     - Add the leaf hwXponPortTrafficStatisticDown1GChannelRate in table hwXponPortTrafficStatisticTable.
	                     - Add the leaf hwXponPortTrafficStatisticDown1GChannelBandwidthUsage in table hwXponPortTrafficStatisticTable.
	                     - Add the leaf hwXponPortTrafficStatisticDown1GChannelUnicastRate in table hwXponPortTrafficStatisticTable.
	                     - Add the leaf hwXponPortTrafficStatisticDown1GChannelMulticastRate in table hwXponPortTrafficStatisticTable.
	                     - Add the leaf hwXponPortTrafficStatisticDown1GChannelBroadcastRate in table hwXponPortTrafficStatisticTable.
	                     - Add the leaf hwXponPortTrafficStatisticDown10GChannelRate in table hwXponPortTrafficStatisticTable.
	                     - Add the leaf hwXponPortTrafficStatisticDown10GChannelBandwidthUsage in table hwXponPortTrafficStatisticTable.
	                     - Add the leaf hwXponPortTrafficStatisticDown10GChannelUnicastRate in table hwXponPortTrafficStatisticTable.
	                     - Add the leaf hwXponPortTrafficStatisticDown10GChannelMulticastRate in table hwXponPortTrafficStatisticTable.
	                     - Add the leaf hwXponPortTrafficStatisticDown10GChannelBroadcastRate in table hwXponPortTrafficStatisticTable.
	                     - Add the leaf hwXponPortTrafficStatisticUp2GChannelRate in table hwXponPortTrafficStatisticTable.
	                     - Add the leaf hwXponPortTrafficStatisticUp2GChannelBandwidthUsage in table hwXponPortTrafficStatisticTable.
	                     - Add the leaf hwXponPortTrafficStatisticUp2GChannelUnicastRate in table hwXponPortTrafficStatisticTable.
	                     - Add the leaf hwXponPortTrafficStatisticUp2GChannelMulticastRate in table hwXponPortTrafficStatisticTable.
	                     - Add the leaf hwXponPortTrafficStatisticUp2GChannelBroadcastRate in table hwXponPortTrafficStatisticTable.
	                   "
	
        REVISION     "201808201000Z"  
        DESCRIPTION  "V2.22, changes in this revision:
                        - Change value range the leaf hwXponPortOtdrCapability in table hwXponPortInfoTable.
                        - Change value range the leaf hwXponDeviceOtdrTestResult in table hwXponDeviceOtdrTestTable.
                        - Change value range the leaf hwXponDeviceOtdrTestWave in table hwXponDeviceOtdrTestTable.
                       "
		       	

	
          REVISION     "201808151000Z"  
          DESCRIPTION  "V2.21, changes in this revision:                                     
	                 - Add the leaf hwXponDeviceTotalONTNumber, hwXponDeviceTotalOnlineONTNumber and hwXponDeviceTotalOfflineONTNumber in table hwXponDeviceCommonGlobalObjects. 
	                 - Add the leaf hwXponPortOnlineONTNumber in table hwXponPortInfoTable. 
	                 "
          REVISION     "201808081000Z"  
          DESCRIPTION  "V2.20, changes in this revision:                                      
	                     - Add the leaf hwGponPortControlLightTestTimeduration in table hwGponPortControlTable.
	                     - Add the leaf hwGponPortControlLightTestTestStatus in table hwGponPortControlTable.
	                     - Add the leaf hwGponPortControlLightTestFinshStatus in table hwGponPortControlTable.
	                   " 
	                 
	  REVISION     "201808031000Z"                 
          DESCRIPTION  "V2.19, changes in this revision:                                     
	                 - Add the leaf hwXponDeviceLosAlarmControlDyingGaspONTNumberRatio in table hwXponDeviceCommonGlobalObjects. 
	                 - Add the leaf hwXponDeviceLosAlarmControlDyingGaspONTTime in table hwXponDeviceCommonGlobalObjects. 
	                 "
          REVISION     "201808021000Z"  
          DESCRIPTION  "V2.18, changes in this revision:                                      
	                     - Add the leaf hwGponPortControlDbaLowlatency in table hwGponPortControlTable.
	                   "   
	                   
          REVISION     "201807131000Z"
          DESCRIPTION  "V2.17, changes in this revision:
                         - Add the table hwXponOntQueueStatisticTable. 
                         - Add the table hwXponOntQueueStatisticControlTable. 
                         "

	  REVISION     "201807121100Z"  
          DESCRIPTION  "V2.16, changes in this revision:                                     
	                 - Add a table hwGponBoardFlexLicenseTable.  
	                 - Add the leaf hwGponPortControlFlexMode in table hwGponPortControlTable.
					 - Add the leaf hwGponPortRunFlexMode in table hwGponPortInfoTable.
	 		"
			
	  REVISION     "201806131100Z"  
          DESCRIPTION  "V2.15, changes in this revision:
                     - Add the enmu value of the leaf  hwXponOntInfoNoOnLineReason in table hwXponOntInfoTable.   
	             - Add the enum value of the leaf node hwXponOntBatchQueryInfo.
                       "
          REVISION     "201806011100Z"  
          DESCRIPTION  "V2.14, changes in this revision:                                     
	                 - Add a table hwXponPortOpticConfigTable.  
	                 - Add a table hwXponPortOpticListTable. 
	                 - Add the leaf hwXponDeviceOpticalTraceabilitySwitch in table hwXponDeviceCommonGlobalObjects. 
	                 "
	                 
          REVISION     "201805281400Z"
          DESCRIPTION  "V2.13, changes in this revision:
                         - Add the leaf hwXponOntAutoPingClearResult in table  hwXponOntAutoPingTable.
                         - Add the leaf hwXponPortAutoPingClearResult in table  hwXponPortAutoPingTable.
                         - Add the enumerate of leaf hwXponOntAutoPingResultCode in table hwXponOntAutoPingTable.
                         "
			         
          REVISION     "201805231400Z"
          DESCRIPTION  "V2.12, changes in this revision:
                         - Add the leaves hwXponDeviceOpticalModuleAlarmControlSwitch in table  hwXponDeviceCommonGlobalObjects. 
                         "	    
    
          REVISION     "201805151400Z"
          DESCRIPTION  "V2.11, changes in this revision:
                         - Add the leaves hwXponDeviceAutoFindAdditionalNoticeTimes and hwXponDeviceAutoFindAdditionalNoticeDistanceTime in table  hwXponDeviceCommonGlobalObjects. 
                         "	    
          REVISION     "201804181700Z"  
          DESCRIPTION  "V2.10, changes in this revision:
	               - Add a table hwXponOntOpticalDdmInfoHistoryTable.
	               "

          REVISION     "201803201700Z"  
          DESCRIPTION  "V2.09, changes in this revision:
	               - Add a table hwXponDeviceGetOntInfoByAuthInfoTable.
	               "
	               
          REVISION     "201803151000Z"
          DESCRIPTION  "V2.08, changes in this revision:      
                       - Add the leaf hwXponDeviceOperatorCheckVersion in table hwXponDeviceCommonGlobalObjects.
                       "
		       
          REVISION     "201803081700Z"  
          DESCRIPTION  "V2.07, changes in this revision:
                        - Add the leaf hwGponDeviceOntLOOCiAlarmThreshold in table hwGponDeviceCommonGlobalObjects.
                        - Add the leaf hwGponDeviceOntLOOCiAlarmRestoreThreshold in table hwGponDeviceCommonGlobalObjects.
                        - Add the leaf hwGponDeviceOntLOOCiAlarmMonitorPeriod in table hwGponDeviceCommonGlobalObjects.
                       "
					   
          REVISION     "201803021700Z"  
          DESCRIPTION  "V2.06, changes in this revision:
                        - Change value range the leaf hwEponInteroperModeStandardVersion in table hwEponInteroperModeConfigTable.
                        - Change value range the leaf hwEponInteroperModeGlobalStandardVersion in table hwEponDeviceCommonGlobalObjects.
                       "

          REVISION     "201803011000Z"  
          DESCRIPTION  "V2.05, changes in this revision:
                        - Add the enumerate of leaf hw10GponOltOpticsModuleXponSubType in table hw10GponOltOpticsModuleInformationTable.
                        - Add the enumerate of leaf hw10GponOltOpticsModuleXponUsedType in table hw10GponOltOpticsModuleInformationTable.
                       "
          REVISION     "201802241000Z"
          DESCRIPTION  "V2.04, changes in this revision:      
                       - Add the leaf hwXponOntSupportSingleRingCheck in table hwXponOntCapabilityInfoTable.
                       " 

          REVISION     "201801311000Z"
          DESCRIPTION  "V2.03, changes in this revision:      
                       - Add the leaf hwEponInteroperModeStandardVersion in table hwEponInteroperModeConfigTable.
                       - Add the leaf hwEponInteroperModeGlobalStandardVersion in table hwEponDeviceCommonGlobalObjects. 
                       " 

          REVISION     "201801081900Z"
          DESCRIPTION  "V2.02, changes in this revision:      
                       - Add the enumerate of the leaf hwXponOntInfoInteroperabilityStandard.
                       - Add the enumerate of the leaf hwGponInteroperModeSwitch. 
                       - Add the enumerate of the leaf hwGponOntInteroperabilityMode.
                       "
					   
          REVISION     "201712251900Z"
          DESCRIPTION  "V2.01, changes in this revision:
			- Add the enumerate of the leaf hwXponOntEthPortPoeMode in table hwXponOntEthPortPoeConfigTable.
                        - Add the leaf hwXponOntEthPortPoeMaxPowerValue in table hwXponOntEthPortPoeConfigTable.
			- Add the leaf hwXponOntEthPortPoeForcePowerSwitch in table hwXponOntEthPortPoeConfigTable.
			- Add the leaf hwXponOntEthPortPoeStatusOutPutPowerCurrentValue in table hwXponOntEthPortPoeStatusTable.
			- Add the leaf hwXponOntEthPortPoeStatusOutPutPowerAverageValue in table hwXponOntEthPortPoeStatusTable.
			- Add the leaf hwXponOntEthPortPoeStatusOutPutPowerPeakValue in table hwXponOntEthPortPoeStatusTable.
                       "
					   
          REVISION     "201712221000Z"  
          DESCRIPTION  "V2.00, changes in this revision:
                        - Add the enumerate of leaf hwXponOpticsDdmInfoExModuleType in table hwXponOpticsDdmInfoExTable.
                        - Add the enumerate of leaf hw10GponOltOpticsModuleXponSubType in table hw10GponOltOpticsModuleInformationTable.
		       "
					   
          REVISION     "201712061000Z"  
	  DESCRIPTION  "V1.99, changes in this revision:
                        - Add the table hwXponOntAutoPingTable.
                        - Add the table hwXponPortAutoPingTable.
                       "
		        
          REVISION     "201711301900Z"  
          DESCRIPTION  "V1.98, changes in this revision:
                        - Add the leaf hwGponPortControlComboMode in table hwGponPortControlTable.
                       "
			 
          REVISION     "201711211700Z"  
          DESCRIPTION  "V1.97, changes in this revision:
                        - Add the leaf hwXponOntPortCfgL2IsolateSwitch in table hwXponOntPortConfigTable.
	                   "
    
          REVISION     "201711171000Z"  
          DESCRIPTION  "V1.96, changes in this revision:
                        - Modify the description of hwXponOntInfoNoOnLineReason.
                       "
                       
          REVISION     "201711061000Z"  
          DESCRIPTION  "V1.95, changes in this revision:
                        - Add the enumerate of leaf hwXponOpticalSubType in table hwXponOpticalDdmProfileReferenceTable.
                        - Add the enumerate of leaf hwXponOntEthernetPortOpticalGEComplianceCodes in table hwXponOntEthernetPortOpticalStaticInfoTable.
                       "
	  REVISION     "201710271900Z"  
          DESCRIPTION  "V1.94, changes in this revision:
                        - Modify the value range of leaf hwXponOpticsDdmInfoExEncapsulationType.     
                        - Modify the value range of leaf hw10GponOltOpticsModuleInfoIdentifier.
                        - Modify the value range of leaf hw10GponOltOpticsModuleXponEncapsulationType.
                        - Add the leaf hwGponPortInfoAvailableBwFor2dot5G in table hwGponPortInfoTable.  
                        - Add the leaf hwGponPortInfoAvailableBwFor10G in table hwGponPortInfoTable.
						- Add the leaf hwXponDeviceAuthConflictCheckByLoidSwitch in table hwXponDeviceCommonGlobalObjects.  
                        "
			 
          REVISION     "201710131900Z"  
          DESCRIPTION  "V1.93, changes in this revision:
                       - Add the enumerate of the leaf hwXponDeviceSuppressInitialAlarmState in table hwXponDeviceCommonGlobalObjects.
                       "
                       
          REVISION     "201709160900Z"  
          DESCRIPTION  "V1.92, changes in this revision:
                       - Modify the value range of leaf hwEponInteroperModeOntSoftwareVersionInfoIndex.
                       "
                       
          REVISION     "201709071000Z"  
          DESCRIPTION  "V1.91, changes in this revision:
                        - Add the table hwGponPortConfigInfoTable.
                        "
                        
    	  REVISION     "201708271000Z"  
	  DESCRIPTION  "V1.90, changes in this revision:                                     
                         - Modify the enumerate of the leaf hwXponDeviceOntPotsPortCTPSrvCode in table hwXponDeviceOntPotsPortStateTable. 
	                     "

          REVISION     "201708261100Z"  
	  DESCRIPTION  "V1.89, changes in this revision:                                     
	                - Add the leaf hwXponDeviceAutoRecoverySwitch in table hwXponDeviceCommonGlobalObjects.  
                       "  
          
          REVISION     "201708241100Z"  
          DESCRIPTION  "V1.88, changes in this revision:                                     
	                - Add the leaf hwXponDeviceOntOpticalDdmQuickQuerySwitch in table hwXponDeviceCommonGlobalObjects.  
                                   - Add the leaf hwXponDeviceAuthConflictCheckBySnSwitch in table hwXponDeviceCommonGlobalObjects.  
                                   "
		       
          REVISION     "201708141100Z"  
	  DESCRIPTION  "V1.87, changes in this revision:                                     
	                - Add the leaf hwXponDeviceAntiRogueOamOntAutoIsolateMode in table hwXponDeviceCommonGlobalObjects.  
	                - Add the leaf hwXponDeviceAntiRogueSnmpOntAutoIsolateMode in table hwXponDeviceCommonGlobalObjects. 
                       "  
	  
          REVISION     "201708080900Z"  
          DESCRIPTION  "V1.86, changes in this revision:
                        - Add the table hwXponPortTrafficStatisticTable.
                        - Add the leaf hwXponPortTrafficStatisticCurrentUpstreamRate in table hwXponPortTrafficStatisticTable.  
                        - Add the leaf hwXponPortTrafficStatisticCurrentDownstreamRate in table hwXponPortTrafficStatisticTable.
                        "
          REVISION     "201707210900Z"  
          DESCRIPTION  "V1.85, changes in this revision:
                         - Add the enumerate of leaf hwXponOpticsDdmInfoExSubType in table hwXponOpticsDdmInfoExTable.
			 - Add the enumerate of leaf hwXponOpticalModuleSubType in table hwXponOpticsParameterRangeEntry.
			"
			
          REVISION     "201707171100Z"  
          DESCRIPTION  "V1.84, changes in this revision:                                     
	                - Add the leaf hwGponDeviceGemPortEncryptMode in table hwGponDeviceCommonGlobalObjects.  
	               "
	               
          REVISION     "201707141500Z"  
          DESCRIPTION  "V1.83, changes in this revision: 
                        - Add leaf hwXponOntIpRemotePingSize in table hwXponOntIpMaintainTable.
                        - Add leaf hwXponOntIpRemotePingCount in table hwXponOntIpMaintainTable.
                        - Add leaf hwXponOntIpRemotePingStop in table hwXponOntIpMaintainTable.
                       "    

          REVISION     "201707071020Z"  
          DESCRIPTION  "V1.82, changes in this revision: 
                        - Add the table of hwXponPortChannelMaxRateInfoTable.
                       "
                        
          REVISION     "201707061020Z"
          DESCRIPTION  "V1.81, changes in this revision:      
                         - Add the enumerate of the leaf hwXponOntInfoInteroperabilityStandard.  
                         - Add the enumerate of the leaf hwGponOntInteroperabilityMode.
                         - Add the enumerate of the leaf hwGponInteroperModeSwitch.
                         - Add the leaf hwXponOntEthernetPortOpticalSFF8472Compliance in table hwXponOntEthernetPortOpticalStaticInfoTable.  
                         - Add the leaf hwXponOntEthernetPortOptical10GEComplianceCodes in table hwXponOntEthernetPortOpticalStaticInfoTable.   
                         - Add the leaf hwXponOntEthernetPortOpticalGEComplianceCodes in table hwXponOntEthernetPortOpticalStaticInfoTable.  
                         - Add the leaf hwXponOntEthernetPortOpticalSpeed in table hwXponOntEthernetPortOpticalStaticInfoTable.  
                         - Add the leaf hwXponOntEthernetPortOpticalLength9Micronkm in table hwXponOntEthernetPortOpticalStaticInfoTable.  
                         - Add the leaf hwXponOntEthernetPortOpticalLength9Micron in table hwXponOntEthernetPortOpticalStaticInfoTable.  
                         - Add the leaf hwXponOntEthernetPortOpticalLength50Micron in table hwXponOntEthernetPortOpticalStaticInfoTable.  
                         - Add the leaf hwXponOntEthernetPortOpticalLength62Micron5 in table hwXponOntEthernetPortOpticalStaticInfoTable.  
                         - Add the leaf hwXponOntEthernetPortOpticalLengthCopper in table hwXponOntEthernetPortOpticalStaticInfoTable.  
                         - Add the leaf hwXponOntEthernetPortOpticalWaveLength in table hwXponOntEthernetPortOpticalStaticInfoTable.  
                         - Add the leaf hwXponOntEthernetPortOpticalBrNominal in table hwXponOntEthernetPortOpticalStaticInfoTable.  
                         - Add the leaf hwXponOntEthernetPortOpticalBrMax in table hwXponOntEthernetPortOpticalStaticInfoTable.  
                         - Add the leaf hwXponOntEthernetPortOpticalBrMin in table hwXponOntEthernetPortOpticalStaticInfoTable.  
                         - Add the leaf hwXponOntEthernetPortOpticalCcBase in table hwXponOntEthernetPortOpticalStaticInfoTable.  
                         - Add the leaf hwXponOntEthernetPortOpticalCcExt in table hwXponOntEthernetPortOpticalStaticInfoTable. 
                         - Add the table hwXponDeviceOntPotsPortStateTable.
                         - Add the leaf hwXponDeviceOntPotsPortPTPSrvState  in table hwXponDeviceOntPotsPortStateTable.   
                         - Add the leaf hwXponDeviceOntPotsPortPTPAdminState  in table hwXponDeviceOntPotsPortStateTable.
                         - Add the leaf hwXponDeviceOntPotsPortPTPHookState  in table hwXponDeviceOntPotsPortStateTable.
                         - Add the leaf hwXponDeviceOntPotsPortCTPSrvState  in table hwXponDeviceOntPotsPortStateTable.
                         - Add the leaf hwXponDeviceOntPotsPortCTPSrvType  in table hwXponDeviceOntPotsPortStateTable.   
                         - Add the leaf hwXponDeviceOntPotsPortCTPSrvCode  in table hwXponDeviceOntPotsPortStateTable.   
                         - Modify the value range of leaf hwXponPortPhysicalUpRate.
                         - Modify the value range of leaf hwXponPortPhysicalDownRate.
                       "
          REVISION     "201706281020Z"
          DESCRIPTION  "V1.80, changes in this revision:      
                        - Modify the syntax of hwXponOntPppoeSimuMulticastGroupIP from IpAddress to InetAddress.
                        - Modify the syntax of hwXponOntPppoeSimuMulticastSourceIP from IpAddress to InetAddress.
                       "
                       
          REVISION     "201706071020Z"
          DESCRIPTION  "V1.79, changes in this revision:      
                        - Add the enumerate of the leaf hw10GponOltOpticsModuleXponType.
                        - Add the leaf hw10GponOltOpticsModuleComboMode in table hw10GponOltOpticsModuleInformationTable.   
                       "
                       
          REVISION     "201706011020Z"  
          DESCRIPTION  "V1.78, changes in this revision: 
                        - Add leaf hwXponDeviceOntLowBandwidthUsageMonitorSwitch in table hwXponDeviceCommonGlobalObjects.
                       "    

          REVISION     "201705261020Z"
          DESCRIPTION  "V1.77, changes in this revision:      
                        - Modify the description of hwXponOntEthernetPortOpticalStaticInfoTable.
                       "
                     
          REVISION     "201705221020Z"
          DESCRIPTION  "V1.76, changes in this revision:      
                        - Add the leaf hwXponOntInfoPowerType in table hwXponOntInfoTable.   
                        - Add the leaf hwXponOntInfoSystemUpDuration in table hwXponOntInfoTable.
                        - Add the leaf hwXponOntControlRollbackSoftware in table hwXponOntControlTable.
                        - Add the table hwXponOntEthernetPortOpticalStaticInfoTable.
                        - Add the table hwXponOntEthernetPortOpticalDdmInfoTable.
	                 "

            REVISION     "201705201100Z"  
            DESCRIPTION  "V1.75, changes in this revision:                                     
	                 - Add leaf hwXponPortPhysicalUpRate and hwXponPortPhysicalDownRate in hwXponPortInfoTable.
	                 "
	                 
	    REVISION     "201704171020Z"
            DESCRIPTION  "V1.74, changes in this revision:      
                         - Add the leaf hwXponOntPppoeSimuMulticastGroupIPType in table hwXponOntPppoeSimuTestInfoTable.   
                         - Add the leaf hwXponOntPppoeSimuMulticastGroupIP in table hwXponOntPppoeSimuTestInfoTable.
                         - Add the leaf hwXponOntPppoeSimuMulticastVersion in table hwXponOntPppoeSimuTestInfoTable.
                         - Add the leaf hwXponOntPppoeSimuMulticastSourceIPType in table hwXponOntPppoeSimuTestInfoTable.   
                         - Add the leaf hwXponOntPppoeSimuMulticastSourceIP in table hwXponOntPppoeSimuTestInfoTable.
                         - Add the leaf hwXponOntPppoeSimuMulticastDataRate in table hwXponOntPppoeSimuTestInfoTable.
                         "
            REVISION     "201702281020Z"
            DESCRIPTION  "V1.73, changes in this revision:      
                          - Add the table hwXponOntRegAndAuthStatTable.
                          - Add the leaf hwXponOntRegAndAuthStatRegisterAcceptedCounter in table hwXponOntRegAndAuthStatTable.   
                          - Add the leaf hwXponOntRegAndAuthStatRegisterRejectedCounter in table hwXponOntRegAndAuthStatTable.
                          - Add the leaf hwXponOntRegAndAuthStatAuthAcceptedCounter in table hwXponOntRegAndAuthStatTable.
                          - Add the leaf hwXponOntRegAndAuthStatAuthRejectedCounter in table hwXponOntRegAndAuthStatTable.
                          - Add the leaf hwXponOntRegAndAuthStatChallengedCounter in table hwXponOntRegAndAuthStatTable.   
                         "
            REVISION     "201702181020Z"
            DESCRIPTION  "V1.72, changes in this revision:      
                         - Add the leaf hwGponInteroperModeAniMVlanFilter in table hwGponInteroperModeConfigTable.
                         - Add the leaf hwGponOntAniMVlanFilter in table hwGponDeviceCommonGlobalObjects.
                         - Add the leaf hwGponOntQueueMapQueue0Id in table hwGponDeviceCommonGlobalObjects.
                         - Add the leaf hwGponOntQueueMapQueue1Id in table hwGponDeviceCommonGlobalObjects.
                         - Add the leaf hwGponOntQueueMapQueue2Id in table hwGponDeviceCommonGlobalObjects.
                         - Add the leaf hwGponOntQueueMapQueue3Id in table hwGponDeviceCommonGlobalObjects.
                         - Add the leaf hwGponOntQueueMapQueue4Id in table hwGponDeviceCommonGlobalObjects.
                         - Add the leaf hwGponOntQueueMapQueue5Id in table hwGponDeviceCommonGlobalObjects.
                         - Add the leaf hwGponOntQueueMapQueue6Id in table hwGponDeviceCommonGlobalObjects.
                         - Add the leaf hwGponOntQueueMapQueue7Id in table hwGponDeviceCommonGlobalObjects.
                         - Add the enumerate of the leaf hwXponOntInfoInteroperabilityStandard.  
                         - Add the enumerate of the leaf hwGponOntInteroperabilityMode.
                         - Add the enumerate of the leaf hwGponInteroperModeSwitch.
                         - Add the enumerate of the leaf hwXponOntConfigFactoryConfiguration.
                         "
            REVISION     "201702171039Z"
            DESCRIPTION  "V1.71, changes in this revision:      
                         - Add the leaf hwXponDeviceVsOntIdAllocPolicy in table hwXponDeviceCommonGlobalObjects.
                         - Add the leaf hwGponXponOntVsID in table hwXponOntInfoTable.
                         - Add the leaf hwGponXponGlobalOntID in table hwXponOntInfoTable.
                         - Add the table hwXponPortVsResourceTable.
                         "
			 
            REVISION     "201701051039Z"
            DESCRIPTION  "V1.70, changes in this revision:      
                         - Add the enumerate of the leaf hwXponOpticsDdmInfoExModuleType.
                         - Add the enumerate of the leaf hw10GponOltOpticsModuleXponType.
                         - Add the leaf hw10GponOltOpticsModuleInfoWaveLength in table hw10GponOltOpticsModuleInformationTable.
                         - Add the leaf hwGponDeviceOntActualWorkChannel in table hwXponOntInfoTable.  
                         - Add the leaf hwGponPortControlWaveLengthID in table hwGponPortControlTable.
                         - Add the table hwGponTwdmChannelGroupTable.
                         - Add the table hwGponTwdmChannelMemberTable.
                         - Add the table hwGponBoardWorkModeTable.
                         "    
            REVISION     "201701041100Z"  
            DESCRIPTION  "V1.69, changes in this revision:      
                         - Add leaf hwXponDeviceOltOpticalAlarmAutoMonitorSwitch in table hwXponDeviceCommonGlobalObjects.
	      - Add leaf hwXponDeviceOntOpticalAlarmAutoMonitorSwitch in table hwXponDeviceCommonGlobalObjects.
                         "
            REVISION     "201701031039Z"
            DESCRIPTION  "V1.68, changes in this revision:      
                         - Add the leaf hwGponInteroperModeOntVlanTagOperMode in table hwGponInteroperModeConfigTable.
                         - Add the leaf hwGponOntVlanTagOperMode in table hwGponDeviceCommonGlobalObjects.      
                         " 
                         
            REVISION     "201612201630Z"  
            DESCRIPTION  "V1.67, changes in this revision:      
                         - Change the name of hwXponOntUpstreamFec to hwXponOntFec
                         - Change the name of hwXponOntUpstreamFecStatus to hwXponOntFecStatus
                         "
			 
            REVISION     "201612131630Z"  
            DESCRIPTION  "V1.66, changes in this revision:      
                         - Add the enumerate of the leaf hwXponOntInfoInteroperabilityStandard.
                         - Add the enumerate of the leaf hwGponOntInteroperabilityMode.    
                         - Add the enumerate of the leaf hwGponInteroperModeSwitch.
                         "
    
            REVISION     "201612061630Z"  
            DESCRIPTION  "V1.65, changes in this revision:      
                         - Add the leaf hwXponDeviceTypeBLosAlarmControlState in table hwXponDeviceCommonGlobalObjects.
			"
			
            REVISION     "201610281100Z"  
            DESCRIPTION  "V1.64, changes in this revision:      
                         - Add the leaf hwXponOntIpRemotePingSourceIpAddress in table hwXponOntIpMaintainTable.
                         "
			 
            REVISION     "201610151100Z"  
            DESCRIPTION  "V1.63, changes in this revision:      
                         - Add leaf hwXponOntControlWanAccessHttp in table hwXponOntControlTable.
                         - Add leaf hwXponOntControlLanAccessTelnet in table hwXponOntControlTable.                               
                         "

            REVISION     "201610121100Z"  
            DESCRIPTION  "V1.62, changes in this revision:      
                         - Add the leaf hwXponOntUpstreamFecStatus in table hwXponOntInfoTable.
                         - Add the leaf hwXponOntUpstreamFec in table hwXponOntControlTable.                               
                         - Add leaf hwXponDeviceOntOfflineMonitorSwitch in table hwXponDeviceCommonGlobalObjects.
                         - Add leaf hwXponDeviceOntOfflineMonitorAlarmThresholdRatio in table hwXponDeviceCommonGlobalObjects.
                         - Add leaf hwXponDeviceOntOfflineMonitorRestoreThresholdRatio in table hwXponDeviceCommonGlobalObjects.
				         "
            REVISION     "201610082000Z"  
            DESCRIPTION  "V1.61, changes in this revision: 
                         - Modify the description of hwXponOntInfoNoOnLineReason.
                         - Add the enumerate of leaf hw10GponOltOpticsModuleXponType in table hw10GponOltOpticsModuleInformationTable.
                         - Modify the description of hwXponOntStatProbeConfigParameter.
                         - Modify the value range of leaf hwXponOntStatProbeConfigParameter.
                         - Add the enumerate of the leaf hwXponOntStatProbeConfigType.
			             "  
            REVISION     "201608311100Z"  
            DESCRIPTION  "V1.60, changes in this revision: 
	    		         - Add leaf hwXponOntInfoHostName in hwXponOntInfoTable.
			             "    
            REVISION     "201608041100Z"  
            DESCRIPTION  "V1.59, changes in this revision:                                     
	                 	 - Modify the description of hwGponDeviceOntActualNniType.
	                 	 - Modify the description of hwGponDeviceOntLastActualNniType.
	                 	 - Add leaf hwXponPortOpticalModulePhysicalForm in hwXponPortInfoTable.
	                 	 - Add a table hwGponComboOltEthernetStatisticTable.
	                 	 - Add a table hwGponComboOltGemStatisticTable. 
	                 	 - Add a table hwOltGponComboPortInfoTable.
                         "
            REVISION     "201607211100Z"  
            DESCRIPTION  "V1.58, changes in this revision:   
                         - Add the table hwXponOntPortVlanExtConfigTable.
                         - Add the table hwXponOntPortVlanDiscardTable.
                         - Add the leaf hwGponOntPortCfgQinqMode in table hwGponOntPortServiceCfgTable.
                         - Add the enumerate of leaf hwGponOntifType in table hwGponOntPortServiceCfgTable.
                         - Add leaf hwGponDeviceOntCapInfoWiFiPortNum in table hwGponDeviceOntCapabilityInfoTable.
                         "
            REVISION     "201606301100Z"  
            DESCRIPTION  "V1.57, changes in this revision: 
	                 - Add leaf hwGponDeviceOmciBandwidthCompensateSwitch in hwGponDeviceCommonGlobalObjects.
                         - Modify the description of hwXponOpticalModuleSubType.
                         - Add the enumerate of leaf hwXponOpticsDdmInfoExSubType in table hwXponOpticsDdmInfoExTable.
                         - Add the enumerate of the leaf hw10GponOltOpticsModuleXponSubType.
                         "
                         
            REVISION     "201606021100Z"  
            DESCRIPTION  "V1.56, changes in this revision:   
                         - Add leaf hwXponDeviceRogueOntSelfDetectSwitch in table hwXponDeviceCommonGlobalObjects.
                         - Modify the description of hwXponOntEthPortPoePowerClassificationStatus.
                         "
    				       
            REVISION     "201605160900Z"  
            DESCRIPTION  "V1.55, changes in this revision:   
                         - Add the enumerate of the leaf hwXponOntInfoInteroperabilityStandard.
                         - Add the enumerate of the leaf hwGponOntInteroperabilityMode.    
                         - Add the enumerate of the leaf hwGponInteroperModeSwitch.
                         - Add leaf hwGponDeviceSnOutPutFormatPolicy in hwGponDeviceCommonGlobalObjects.
                         - Modify the description of the table hwXponOpticalDdmProfileReferenceTable.
                         - Modify the description of the table hwGponPortTrafficStatisticTable.
                         "
                             
            REVISION     "201605050900Z"
            DESCRIPTION  "V1.54, changes in this revision:
                         - Add table hwXponOntWanProfileTable for ONT wan profile.
                         - Add table hwXponOntPolicyRouteProfileTable for ONT policy route profile.
                         - Add table hwXponOntPolicyRouteProfilePortCfgTable for ONT policy route rule profile.
                         - Add the leaf hwXponOntIpConfigUsedWanProfName in table hwXponOntIpConfigTable.
                         - Add leafs hwXponOntUsedPolicyRouteProfileName, hwXponOntUsedInternetWanIpIndex, hwXponOntUsedMulticastWanIpIndex and hwXponOntUsedMulticastProfileName in table hwXponOntConfigTable.
                         - Add the leaf hwXponOntPortCfgRouteSwitch in table hwXponOntPortConfigTable.
                         - Add the leaf hwGponOntHomeGatewayConfigMethod in table hwGponDeviceCommonGlobalObjects.
                         - Add the enumerate of leaf hwGponOntifType in table hwGponOntPortMulticastVlanTranslationTable.       
                         " 
	                 
            REVISION     "201603280900Z"  
            DESCRIPTION  "V1.53, changes in this revision:   
                         - Modify the description of the leaf hwGponDeviceOntActualNniType in table hwXponOntInfoTable.                                   
                         - Modify the description of the leaf hwGponDeviceOntLastActualNniType in table hwXponOntInfoTable.
                         - Add the enumerate of the leaf hwXponOntInfoInteroperabilityStandard.
                         - Add the enumerate of the leaf hwGponOntInteroperabilityMode.    
                         - Add the enumerate of the leaf hwGponInteroperModeSwitch. 
                         "
            
            REVISION     "201603250900Z"  
            DESCRIPTION  "V1.52, changes in this revision:   
                         - Add the leaf hwXponDevicePortFaultCheckSwitch in table hwXponDeviceCommonGlobalObjects.                                   
                         "
            REVISION     "201603030900Z"  
            DESCRIPTION  "V1.51, changes in this revision:   
                         - Add the leaf hwXponDeviceOntUserMulticastProcess in table hwXponDeviceCommonGlobalObjects.                                   
                         - Add the leaf hwXponOntControlRogueIsolateSwitch in table hwXponOntControlTable.
                         "
      
            REVISION     "201602140900Z"           
            DESCRIPTION  "V1.50, changes in this revision:
                         - Add the leaf hwGponDeviceAntiDosPloamSwitch in table hwGponDeviceCommonGlobalObjects.
                         - Add leaves hwGponDeviceOntActualNniType and hwGponDeviceOntLastActualNniType in table hwXponOntInfoTable.
                         - Add the enumerate of leaf hw10GponOltOpticsModuleXponType in table hw10GponOltOpticsModuleInformationTable.
                         - Add the enumerate of leaf hwXponOpticsDdmInfoExModuleType in table hwXponOpticsDdmInfoExTable. 
                         - Modify the description of hwXponOpticalType in table hwXponOpticalDdmProfileReferenceTable.
                         "
			 
            REVISION     "201512081100Z"            
            DESCRIPTION  "V1.49, changes in this revision: 
                         - Add table hwGponDevicePotsPortHis15MinStatisticTable for ONT VOIP statistic .             
                         "
	
            REVISION     "201512071100Z"            
            DESCRIPTION  "V1.48, changes in this revision: 
                         - Add leaves hwXponOntInfoNniPhysicalUpRate and hwXponOntInfoNniPhysicalDownRate in table hwXponOntInfoTable.             
                         "
                             
            REVISION     "201511021100Z"            
            DESCRIPTION  "V1.47, changes in this revision: 
                         - Modify MAX-ACCESS of leaf hwXponOpticalUseType to not-accessible.  
                         - Modify MAX-ACCESS of leaf hwXponOpticalGradeType to not-accessible.
                         - Modify MAX-ACCESS of leaf hwXponOpticalType to not-accessible.
                         - Modify MAX-ACCESS of leaf hwXponOpticalSubType to not-accessible. 
                         - Modify the enumerate of leaf hwXponOpticalUseType.  
                         - Modify the enumerate of leaf hwXponOpticalGradeType.
                         - Modify the enumerate of leaf hwXponOpticalType.
                         - Modify the enumerate of leaf hwXponOpticalSubType.                                                    
                         - Delete leaf hwXponOptical10GRxAlarmUpper from table hwXponOpticalDdmProfileReferenceTable.  
                         - Delete leaf hwXponOptical10GRxAlarmLower from table hwXponOpticalDdmProfileReferenceTable.
                         - Delete leaf hwXponOptical10GRxWarnUpper from table hwXponOpticalDdmProfileReferenceTable.
                         - Delete leaf hwXponOptical10GRxWarnLower from table hwXponOpticalDdmProfileReferenceTable.
                         - Add table hwXponTrafficAlarmProfileTable in hwXponDeviceProfileObjects, this table is used for add, modify and delete traffic alarm profile.                                               
                         - Add table hwGponPortTrafficStatisticTable in hwXponCommonStatisticObjects, this table is used for querying the current-period or last-period
                           traffic congestion statistics.
                         - Add leaf hwGponPortControlTrafficAlarmProfileName in table hwGponPortControlTable.
                         - Add leaf hwGponPortControlMaxGuaranteedBandwidth in table hwGponPortControlTable.
                         "
            REVISION     "201510121100Z"            
            DESCRIPTION  "V1.46, changes in this revision: 
                         - Add table hwXponOpticalDdmProfileReferenceTable in hwXponCommonControlObjects, this table is used for querying the reference thresholds of 
                         the optical transceiver.                                          
                         "
            REVISION     "201509071500Z"            
            DESCRIPTION  "V1.45, changes in this revision: 
                         - Modify the description of hwXponOntInfoNoOnLineReason.                                          
                         "
            REVISION     "201508121500Z"            
            DESCRIPTION  "V1.44, changes in this revision: 
                         - Modify the description of hwXponOntUsedDot1xProfName.                                          
                         "     
    
            REVISION     "201507061500Z"            
            DESCRIPTION  "V1.43, changes in this revision: 
                         - Add leaf hwXponOntUsedPowerReductionProfName in table hwXponOntConfigTable. 
                         - Add table hwXponOntPowerReductionStatisticTable in hwXponCommonStatisticObjects,this table is only used for defining 
                           GPON management common MIB objects for both profile-mode and distributing-mode.
                         - Add leaf hwXponOntPowerReductionDozeTime,hwXponOntPowerReductionCyclicSleepTime,hwXponOntPowerReductionWatchfulSleepTime,
                           hwXponOntPowerReductionEnergysaved,hwXponOntPowerReductionCountClear in table hwXponOntPowerReductionStatisticTable.
                         - Add leaf hwXponOntInfoPowerReductionStatus in table hwXponOntInfoTable
                         - Add scalar leaf hwXponCommonDeviceOntPowerReductionSwitch in hwXponDeviceCommonGlobalObjects.
                         - Modify the value range of leaf hwXponOntEthPortPoeSwitch in table hwXponOntEthPortPoeConfigTable.
                         - Modify the value range of leaf hwXponOntEthPortPoePowerDetectionStatus in table hwXponOntEthPortPoeStatusTable.
                         - Modify the description of row status.                                          
                         "  
            REVISION     "201505070300Z"            
            DESCRIPTION  "V1.42, changes in this revision: 
                         - Modify the description of hwXponDeviceOntActiveAlarmList.             
                         - Modify the description of hwXponDeviceOntPortActiveAlarmList.
                         - Add the enumerate of the leaf hwXponOntInfoInteroperabilityStandard.
                         - Add the enumerate of the leaf hwGponOntInteroperabilityMode.    
                         - Add the enumerate of the leaf hwGponInteroperModeSwitch.                    
                         "  
                                                  
            REVISION     "201505062200Z"            
            DESCRIPTION  "V1.41, changes in this revision: 
                         - Add the leaves hwXponOntUsedLldpProfName and hwXponOntUsedDot1xProfName in the table hwXponOntConfigTable.             
                         - Add the tables of hwXponDeviceOntPowerReductionProfileTable, hwXponOntEthPortPoeConfigTable and hwXponOntEthPortPoeStatusTable.                    
                         "
    
            REVISION     "201505060900Z"            
            DESCRIPTION  "V1.40, changes in this revision: 
                         -  Modify the enmu value of the leaf  hwXponOntInfoNoOnLineReason in table hwXponOntInfoTable.                   
                         "
                                   
            REVISION     "201501270900Z"            
            DESCRIPTION  "V1.39, changes in this revision: 
                         - Add leaf hwXponDeviceOperatorCheckSwitch, hwXponDeviceOperatorCheckCode, hwXponDeviceOperatorCheckHistoryCodeMaxNumber 
                           and hwXponDeviceOperatorCheckHistoryCodeClear in table hwXponDeviceCommonGlobalObjects. 
                         - Add leaf hwXponOntControlOperatorCheckReset in table hwXponOntControlTable.                    
                         "      
            REVISION     "201501210900Z"            
            DESCRIPTION  "V1.38, changes in this revision: 
                         - Add table hwXponOntLoadInfoTable for ONT load. 
                         "  

            REVISION     "201411200900Z"           
            DESCRIPTION  "V1.37, changes in this revision:
                         - Modify the description of hwXponOntIpIndex.  
                         "   
                         
            REVISION     "201410130900Z"           
            DESCRIPTION  "V1.36, changes in this revision:
                         - Add the leaf node hwGponOntWanConfigMode in table hwGponDeviceCommonGlobalObjects.
                         - Add the leaf node hwGponInteroperModeOntWanConfigMode in table hwGponInteroperModeConfigTable.
                         - Modify the MAX-ACCESS value of the leaf hwGponOntPortMulticastVlanCfgRowStatus, hwXponDeviceOntNoAuthRowStatus, hwXponOntTr069ServerProfileRowStatus.
                         - Modify the implied value of the leaf hwXponOntAlarmPolicyNameIndex, hwXponDeviceOntPowerSheddingProfileNameIndex, hwXponOntTr069ServerProfileName, hwXponOntFtpServerProfileNameIndex.
			 "  
                             
            REVISION     "201408050900Z"           
            DESCRIPTION  "V1.35, changes in this revision:
                         - Add the leaf node hwXponOntTransmittingFree in table hwXponOntFileTransmitionTable.
                         - Modify the description of hwXponOntInfoNoOnLineReason.  
                         - Modify the value range of leaf hwXponStaticMacVlanID. 
                         "   
                         
            REVISION     "201407100900Z"           
            DESCRIPTION  "V1.34, changes in this revision:
                         - modify the description of hwXponOntStatProbeConfigParameter to support IPHOST port.
                         - Add table hwXponOntPortConfigTable to config the static mac learning switch for the ont port.
                         - Add table hwXponOntPortStaticMacTable to config the static mac address and vlan for the ont port.
                         "   

            REVISION     "201406160900Z"           
            DESCRIPTION  "V1.33, changes in this revision:
                         - Fix the errors for OMSYS.
                         "   

           REVISION     "201404030900Z"
           DESCRIPTION  "V1.32, changes in this revision:
                        - Modify the description of hwXponOntIpIndex.
                        - Modify the value range of leaf hwXponOpticsDdmInfoExSubType in table hwXponOpticsDdmInfoExTable.
                        - Add leaf hw10GponOltOpticsModuleInfoCcBaseState and hw10GponOltOpticsModuleInfoCcExtState in table hw10GponOltOpticsModuleInformationTable.
                        - Modify the description of hwXponOpticalModuleSubType.
                        - Modify the description of hwXponOntStatProbeConfigType.
	                - Add leaf hwGponOntSupportMulticastEncrypt in table hwGponDeviceOntCapabilityInfoTable.
	                - Add leaf hwGponPortMulticastEncryptMode in table hwGponPortControlTable.
                        - Add table hwGponPortInfoTable to query the Gpon port information.
                        - Add a enum values of the leaf node hwXponOntBatchQueryInfo.
                        - Add leaf hwXponOntIpconfigVlanMode and hwXponOntIpConfigPppoeAuthentication in table hwXponOntIpConfigTable.  
                        - Add the enumerate of the leaf hwXponOntInfoInteroperabilityStandard.
                        - Add the enumerate of the leaf hwGponOntInteroperabilityMode.    
                        - Add the enumerate of the leaf hwGponInteroperModeSwitch.
                        - Add the object hwEponDeviceCommonGlobalObjects.  
                        - Add table hwEponInteroperModeConfigTable for EPON ONT's interoper mode configuration. 
                        - Modify the description of hwXponOntBatchQueryInfo.
                        - Add a leaf hwGponDeviceXgMulticastGemportId in table hwGponDeviceCommonGlobalObjects.
                        - Modify the description of hwXponOntInfoNoOnLineReason.
                        - Modify the description of hwXponOntBatchQueryInfo.
                        - Modify the description of hwGponPortControlPonIdIdentifier.
                        - Add leaf hwXponOntInteroperabilityFileVersion in table hwXponDeviceCommonGlobalObjects. 
                        - Add table hwXponUnconfiguredRogueOntTable to query the information about rogue ONTs that is not added.
                        - Add leaf hwGponPortControlDbaSurplusAssign in table hwGponPortControlTable.
                        - Add leaf hwGponPortControlBEAssignMode in table hwGponPortControlTable.
                        "
            REVISION     "201308271200Z"   
            DESCRIPTION  "V1.31, changes in this revision:
                          - Add a table of hwXponOltOpticsModuleExtInfoTable.
                          - Add a leaf hwGponDeviceTcontAutoCreateSwitch in table hwGponDeviceCommonGlobalObjects.
                          - Rename hwXponOntPppoeSimuEthPortID to hwXponOntPppoeSimuPortID, and modify the description.
                          - Rename hwGponOntifEthType to hwGponOntifType, and add the enumerate of the leaf hwGponOntifType. 
                          - Rename hwGponOntifEthPort to hwGponOntifPort, and modify the description.
                          - modify the description of hwGponOntPortMulticastVlanTranslationTable.
                          - modify the description of hwGponOntPortMulticastVlanTranslationEntry.
                          - modify the description of hwGponOntPortMulticastVlanIndex.
                          - modify the description of hwGponOntPortMulticastVlanCfgTranslatedVlan.
                          - modify the description of hwGponOntPortMulticastStripSwitch.
                          - Add leaf hwGponDeviceOntCapInfoVdslPortNum in table hwGponDeviceOntCapabilityInfoTable.
                          - Add a table of hwGponOntPortServiceCfgTable.
                          - modify the description of hwXponOntStatProbeConfigParameter to support VDSL port.
                          - Add a table of hwXponOntPortEthernetStatsTable.
                          - Add the enumerate of the leaf hwGponDeviceOntCapInfoDeviceType.
                          - Add the leaf node hwXponOntInfoUsedMutualAuth in table hwXponOntInfoTable.
                          - Add a leaf hwGponOntPriorityQueueMappingPolicySwitch in table hwGponDeviceCommonGlobalObjects.
                          - Add the table hwXponDeviceOntNoAuthConfigTable.
                          - Add the enumerate of the leaf hwXponOntInfoAppLoadState.
                          - modify the description of hwXponOntBatchQueryInfo.
                         "
    
            REVISION     "201304170900Z"   
            DESCRIPTION  "V1.30, changes in this revision:
                          - Add the enumerate of the leaf hwXponOntBatchQueryInfo. 
                          - rename hwXponPortControlTable to hwGponPortControlTable.
                          - rename hwXponPortControlDbaAssignMode to hwGponPortControlDbaAssignMode.
                          - Add leaf hwGponPortControlPonIdSwitch in table hwGponPortControlTable.
                          - Add leaf hwGponPortControlPonIdInputMode in table hwGponPortControlTable.
                          - Add leaf hwGponPortControlPonIdIdentifier in table hwGponPortControlTable.
                          - Add leaf hwGponDeviceOntCapInfoEthOamSupport in table hwGponDeviceOntCapabilityInfoTable.
                          - Add a leaf hwGponDeviceOntObjectExtendFrameID in table hwXponOntInfoTable.  
                          - Modify the name of leaf hwXponOntFtpServerProfileName to hwXponOntFtpServerProfileNameIndex in table hwXponOntFtpServerProfileTable.
                          - Add the enumerate of the leaf hwXponOntInfoInteroperabilityStandard.
                          - Add the table hwGponOntTdmPortPerf15MinTable.
                          - Add leaf hwXponOntInfoInteroperabilityStandard in table hwXponOntInfoTable.
                          - Add the enumerate of the leaf hwGponInteroperModeSwitch.
                          - Add the enumerate of the leaf hwGponOntInteroperabilityMode.
                          - Add a table of hwGponOntMulticastGemPortStatisticTable.
                          - Add a leaf hwGponOntInteroperModeActiveMode in table hwGponDeviceCommonGlobalObjects.
                          - Add the enumerate of the leaf hwXponOntInfoAppLoadState.                         
                         "
                         
            REVISION     "201301080900Z"   
            DESCRIPTION  "V1.29, changes in this revision:
                          - Modify the description of leaf hwXponOntInfoAppLoadState.
                          - Add the table hwXponOntStatProbeConfigTable.
                          - Add the table hwXponOntProbeStatTable.   
                          - Add leaf hwXponOntWanExtendInfoDetail in table hwXponOntWanInfoTable.
                          - Modify the description of leaf hwXponDeviceOtdrTestFilterPara.
                         "
                          
            REVISION     "201212040900Z"   
            DESCRIPTION  "V1.28, changes in this revision:
                          - Modify the description of leaf hwXponDeviceOtdrTestDownPowerUsage.
                          - Modify the description of leaf hwXponDeviceOtdrTestPulseWidth.
                          - Modify the description of leaf hwXponDeviceOtdrTestResult.
                         "
    
            REVISION     "201210181600Z"   
            DESCRIPTION  "V1.27, changes in this revision:
                          - Add leaf hwXponOntInfoXmlLoadErrorInfo in table hwXponOntInfoTable.
                          - Add table hwGponInteroperModeConfigTable to config ONT interoperability mode and multicust-auth mode.
                         "   
                         
            REVISION     "201209060900Z"   
            DESCRIPTION  "V1.26, changes in this revision:
                          - Add leaf hwXponDeviceOtdrTestFilterOrder in table hwXponDeviceOtdrTestTable.
                         "  
                         
            REVISION     "201209040900Z"   
            DESCRIPTION  "V1.25, changes in this revision:
                          - Modify the description of leaf hwXponOntBatchQueryItemMask and hwXponOntBatchQueryInfo.
                         "    
             
            REVISION     "201207280900Z"   
            DESCRIPTION  "V1.24, changes in this revision:
                          - Modify the description of leaf hwXponDeviceOtdrTestOpticalFibreLength.
                          - Modify the description of leaf hwXponOpticalModuleType, hwXponOpticalModuleOltOntType and hwXponOpticalModuleBandwidthType.
                         "  
                           
            REVISION     "201207200000Z"   
            DESCRIPTION  "V1.23, changes in this revision:
                          - Delete unnecessary en dashes.
                         "
                         
            REVISION     "201206190900Z"   
            DESCRIPTION  "V1.22, changes in this revision:
                          - Add leaf hwGponOnuTcontPriorityQueuePriorityReverse in table hwGponDeviceCommonGlobalObjects. 
                          - Add leaf hwXponDeviceAllowDifferentRangeSwitch in table hwXponDeviceCommonGlobalObjects.
                          - Add table hwXponOpticsParameterRangeTable for xpon optical module info.
                         "
                         
            REVISION     "201204130900Z"   
            DESCRIPTION  "V1.21, changes in this revision:
                          - Add the table of hwXponDeviceOtdrTestTable 
                            and the trap of hwXponPortOtdrResultTrap for OTDR test.
                          - Modify the table name of hwXponPortStateTable from hwXponPortStateTable to hwXponPortInfoTable.
                          - Add the leaf nodes hwXponPortOtdrCapability in table hwXponPortInfoTable.                                 
                          - Delete table hwXponDeviceOntFtpCfgServerTable, the table has never been used.
                          - Delete table hwXponDeviceOntFtpCfgTable, the table has never been used.
                          - Add table hwXponOntVoipConfigTable to config the ONT's voip service.
                          - Add table hwXponOntFtpServerProfileTable to config the FTP server profile.
                          - Modify the name of the leaf node hwGponDeviceOntVoipCfgResult to hwGponDeviceOntVoipFtpCfgResult. 
                          - Add the table hwXponOpticsDdmInfoExTable.                               
                         "
    
            REVISION     "201203120900Z"   
            DESCRIPTION  "V1.20, changes in this revision:
                          - Modify MAX-ACCESS of leaf hwXponOntTr069ServerProfileName to not-accessible.
                          - Modify the string length of hwXponOntTr069ServerProfileUserName from 16 to 50.
                          - Modify the string length of hwXponOntTr069ServerProfilePassword from 16 to 25. 
                          - Delete leaf hwXponOntVlanIdForTr069Server from table hwXponOntConfigTable.
                          - Delete leaf hwXponOntPriorityForTr069Server from table hwXponOntConfigTable.  
                          - Delete leaf hwXponOntAdminStateForTr069Server from table hwXponOntConfigTable. 
                          - Add leaf hwXponOntAlarmPolicyAppendIpAddress, hwXponOntAlarmPolicyAppendMac, 
                            hwXponOntAlarmPolicyAppendSn, hwXponOntAlarmPolicyAppendLoid,
                            hwXponOntAlarmPolicyAppendPolicyName in table hwXponOntAlarmPolicyTable. 
                          - Add table hwXponOntAlarmPolicyAlarmTable to set the ONT alarm level.
                          - Modify the range of leaf hwXponOntIpConfigPppoeUserName and hwXponOntIpConfigPppoePassword.
                         "

            REVISION     "201203010900Z"
            DESCRIPTION  "V1.19, changes in this revision:
                          - Add leaf hwXponOntUsedTr069ServerProfName in table hwXponOntConfigTable. 
                          - Add leaf hwXponOntVlanIdForTr069Server in table hwXponOntConfigTable.
                          - Add leaf hwXponOntPriorityForTr069Server in table hwXponOntConfigTable. 
                          - Add leaf hwXponOntAdminStateForTr069Server in table hwXponOntConfigTable. 
                          - Add the table of hwXponOntTr069ServerProfileTable for gpon ont server management. 
                          - Add leaf hwGponOntMutlicastAuthMode in hwXponDeviceCommonGlobalObjects for the ONT multicust-auth mode.    
                          - Add leaf hwXponOntControlGracefulReset in hwXponOntControlTable to reset the ONT gracefully.                          
                          - Add leaf hwXponOntControlGraceTime in hwXponOntControlTable to specify the maximum time to wait for the ONT to reset gracefully.                          
                          - Modify the chinese description of leaf hwXGponOltOpticsModuleXponTemperatureLevel into English. 
                          - Add the table hwXponDeviceOntPowerSheddingProfileTable to set the power shedding interval.                    
                          - Add the table hwXponOntPowerSheddingStatusQueryTable to query the power shedding status of the ONT. 
                          - Add leaf hwXponOntPowerSheddingProfName in table hwXponOntConfigTable.          
                          - Add leaf hwXponOntDeleteVasService in hwXponOntControlTable for omci/oam.
                          - Add the table of hwXponOntCapabilityInfoTable for omci/oam. 
                          - Modify the table name of hwXponOntIpConfigTable to hwXponOntIpMaintainTable.  
                          - Add the table of hwXponOntIpConfigTable for omci/oam.                    
                          - Add leaf hwXponPortMacChipState in hwXponPortStateTable.
                          - Add table hwGponOntPerfEverbeforeDataTable for XGPON everbefore statistics.
                          - Add leaf hwGponOntEverbeforeDownFrameFecCorrectedBytes in table hwGponOntPerfEverbeforeDataTable.
                          - Add leaf hwGponOntEverbeforeDownFrameFecCorrectedCodeWords in table hwGponOntPerfEverbeforeDataTable.
                          - Add leaf hwGponOntEverbeforeDownFrameFecUncorrectableCodeWords in table hwGponOntPerfEverbeforeDataTable. 
                          - Add leaf hwGponOntEverbeforeDownFrameTotalRecCodeWords in table hwGponOntPerfEverbeforeDataTable. 
                          - Add leaf hwGponOntEverbeforeDownFrameFecSeconds in table hwGponOntPerfEverbeforeDataTable. 
                          - Add leaf hwGponOntEverbeforeRangingTimeCount in table hwGponOntPerfEverbeforeDataTable. 
                          - Add leaf hwGponOntEverbeforeTransmittedGemFrames in table hwGponOntPerfEverbeforeDataTable. 
                          - Add leaf hwGponOntEverbeforeXgemKeyErrorCount in table hwGponOntPerfEverbeforeDataTable. 
                          - Add leaf hwGponOntEverbeforeXgemHecErrorCount in table hwGponOntPerfEverbeforeDataTable. 
                          - Modify hwGponOntPerfDataTable to hwGponOntPerfCurr15MinDataTable. 
                          - Modify the description of hwGponOntPerfCurr15MinDataTable.  
                          - Modify HwGponOntPerfDataEntry to HwGponOntPerfCurr15MinDataEntry. 
                          - Modify the description of HwGponOntPerfCurr15MinDataEntry.                          
                          - Modify hwGponOntPerfCurr15MinFECCorrectByte to hwGponOntPerfCurr15MinFecCorrectByte.
                          - Modify hwGponOntPerfCurr15MinFECCorrectCodeWords to hwGponOntPerfCurr15MinFecCorrectCodeWords.
                          - Modify hwGponOntPerfCurr15MinFECUncorrectCodeWords to hwGponOntPerfCurr15MinFecUncorrectCodeWords.
                          - Modify hwGponOntPerfCurr15MinFECTotalCodeWords to hwGponOntPerfCurr15MinFecTotalCodeWords.
                          - Modify hwGponOntPerfCurr15MinFECSeconds to hwGponOntPerfCurr15MinFecSeconds.
                          - Add leaf hwGponOntPerfCurr15MinRangingTimeCount in table hwGponOntPerfCurr15MinDataTable.
                          - Add leaf hwGponOntPerfCurr15MinTransmittedGemFrames in table hwGponOntPerfCurr15MinDataTable.
                          - Add leaf hwGponOntPerfCurr15MinXgemKeyErrorCount in table hwGponOntPerfCurr15MinDataTable.
                          - Add leaf hwGponOntPerfCurr15MinXgemHecErrorCount in table hwGponOntPerfCurr15MinDataTable.
                          - Modify hwGponOntPerfHis15MinFECCorrectByte to hwGponOntPerfHis15MinFecCorrectByte.
                          - Modify hwGponOntPerfHis15MinFECCorrectCodeWords to hwGponOntPerfHis15MinFecCorrectCodeWords.
                          - Modify hwGponOntPerfHis15MinFECUncorrectCodeWords to hwGponOntPerfHis15MinFecUncorrectCodeWords.
                          - Modify hwGponOntPerfHis15MinFECTotalCodeWords to hwGponOntPerfHis15MinFecTotalCodeWords.
                          - Modify hwGponOntPerfHis15MinFECSeconds to hwGponOntPerfHis15MinFecSeconds.
                          - Add leaf hwGponOntPerfHis15MinRangingTimeCount in table hwGponOntPerfHis15MinTable.
                          - Add leaf hwGponOntPerfHis15MinTransmittedGemFrames in table hwGponOntPerfHis15MinTable.
                          - Add leaf hwGponOntPerfHis15MinXgemKeyErrorCount in table hwGponOntPerfHis15MinTable.
                          - Add leaf hwGponOntPerfHis15MinXgemHecErrorCount in table hwGponOntPerfHis15MinTable.
                          - Modify the description of the object hwXponOntInfoAppLoadState.
                          - Modify the description of the object hwXponOntBatchQueryInfo.
                          - Add a table hwXGponOltOpticsModuleInformationTable.  
                          - Modify the description of leaf hwGponOntPerfHis15MinFecCorrectCodeWords. 
                          - Modify the description of leaf hwGponOntPerfHis15MinFecUncorrectCodeWords and hwGponOntPerfHis15MinFecTotalCodeWords.  
                          - Add leaf hwXponDeviceAlarmClearOnShutdown in hwXponDeviceCommonGlobalObjects for clear on shutdown switch.
                          - Add table hwGponCommonOntStatisticTable for the information about the priority queue alarm.
                          - Modify the name of every leaf in table hwXGponOltOpticsModuleInformationTable, modify XGPON  to 10GPON.
                          - Add the table hwGponDeviceOntCapabilityInfoTable to query the capability of the GPON ONT.        
                          - Add leaf hwXponOntInfoNoOnLineReason in hwXponOntInfoTable.              
                          - Modify the description option of hwXponPortSignalDetect.
                          - Change the name of hwXponOntActiveAlarmEntry to hwXponDeviceOntActiveAlarmEntry
                          - Add leaf hwXponDeviceSuppressInitialAlarmState in hwXponDeviceCommonGlobalObjects to suppress xpon initial alarm. 
                          - Add the enumerate of the leaf hw10GponOltOpticsModuleXponSubType.
                         "  
            REVISION     "201109010900Z"   
            DESCRIPTION  "V1.18, changes in this revision:
                          - Add leaf hwXponDeviceModifyBoundProfileSwitch in hwXponDeviceCommonGlobalObjects for enable or disable modify bound profile control.                      
                         "  
                         
            REVISION     "201107250900Z"   
            DESCRIPTION  "V1.17, changes in this revision:
                          - Delete the node hwXponPortControlDbaCalculatePeriod from table hwXponPortControlTable.                          
                         "  
                         
            REVISION     "201107080900Z"   
            DESCRIPTION  "V1.16, changes in this revision:
                          - Add leaf hwXponDeviceAutofindConflictCheckSwitch in hwXponDeviceCommonGlobalObjects for the ONT autofind conflict-check switch.
                         "  
                         
            REVISION     "201106250900Z"   
            DESCRIPTION  "V1.15, changes in this revision:
                          - Add leaf hwGponOntInteroperabilityMode in hwGponDeviceCommonGlobalObjects for interoperability mode.
                          - Add leaf hwGponDeviceOntDefaultLineProfName in hwGponDeviceCommonGlobalObjects for default profile.
                          - Add leaf hwGponDeviceOntDefaultSrvProfName in hwGponDeviceCommonGlobalObjects for default profile.
                          - Add the table HwGponOntIphostStatsTable to querying and clearing the information about the IPHOST port.
                          - Add the table of hwXponPortControlTable.
                          - Add the table of hwXponDeviceOntActiveAlarmTable. 
                          - Add hwXponCommonOntCatvDefaultState to support the global settings for ONT CATV ports.
                          - Add leaf hwXponDeviceGroupPowerOffControlState in hwXponDeviceCommonGlobalObjects for group power off report switch.
                          - Add the leaf hwXponOntLastDistance in table hwXponOntInfoTable.
                          - Move all TRAP objects from HUAWEI-XPON-COMMON-MIB.mib to HUAWEI-XPON-TRAP-MIB.mib.
                         "
    
            REVISION     "201105180900Z"
            DESCRIPTION  "V1.14, changes in this revision:
                          - Modify the description of leaf hwXponOntBatchQueryInfo. 
                          - Modify the description of leaf hwXponOntInfoXmlLoadState and hwXponOntInfoAppLoadState. 
                          - Add the object of hwXponDeviceCommonProfileObjects.
                          - Add the table of hwXponOntAlarmPolicyTable. 
                          - Add the table of hwXponOntConfigTable.  
                          - Modify the description of leaf hwXponOntBatchInfoTable to query the reason why the ONT last went offline.
                          - Add table hwXponOntWanInfoTable to query the information about WAN ports.
                          - Add trap hwGponOntFECUncorrectCodeWordsAlarmTrap,hwGponOntFECUncorrectCodeWordsRecoverAlarmTrap,
                            hwGponOntFECCorrectCodeWordsAlarmTrap and hwGponOntFECCorrectCodeWordsRecoverAlarmTrap.
                          - Add two leaves hwXponCommonOntFECUncorrectCodeWordsThreshold and hwXponCommonOntFECCorrectCodeWordsThreshold in hwXponCommonTrapsVbOids
                         "
                          
            REVISION     "201102280900Z"
            DESCRIPTION  "V1.14, changes in this revision:
                          - Add the table of hwGponDevicePerfDataTable.
                          - Add the table of hwGponOntPortMulticastVlanTranslationTable for the multicast vlan translation of GPON ONT ETH port. 
                          - Add a leaf hwGponDeviceOntVoipCfgResult in hwGponDeviceOntVoipCfgFileInfoTable.
                          - Add the table of hwXponDeviceOntFtpCfgServerTable.
                          - Add the table of hwXponDeviceOntFtpCfgTable.
                          - Add a leaf hwXponOntInfoSupportXmlVersion.  
                          - Add the table of hwGponOntPerfDataTable.
                          - Add the table of hwGponOntPerfHis15MinTable.
                          - Delete the table of hwGponDevicePerfDataTable.
                          - Add trap hwGponDeviceOntVersionTrap.
                          - Add trap hwGponProfOntVersionTrap.
                          - Add trap hwEponProfOntUpVersionTrap.
                          - Add a leaf hwXponRogueOntManualDetectState in hwXponCommonTrapsVbOids.
                          - Add a trap node hwXponCommonRogueOntManualDetectTrap for notifying the result of rogue ont manual detect.                          
                         "

            REVISION     "201012100900Z"
            DESCRIPTION  "V1.13, changes in this revision:
                          - Add the hwXponOntSurvivalAlarmTrap and hwXponOntSurvivalRecoverAlarmTrap
                            to support the work mode of ONT.
                          - Modify the table of hwXponOntBatchInfoTable to optimize thebatch query.
                          - Modify the nodes in the table of hwXponOntPppoeSimuTestInfoTable to support the priority of vlan.
                          - Modify the trap of hwXponCommonDeviceOntPppoeSimuTrap.
                         "

            REVISION     "201011250900Z"
            DESCRIPTION  "V1.12, changes in this revision:
                          - Modify the description of the flowing leaves:
                            hwGponOltMinBandwidth
                            hwGponOltAutoUpdateOntFlag
                          - Add a leaf hwGponOltChangePasswordIntervalTime in hwXponCommonTrapsVbOids for the trap hwXponConfigPmConfigTrap
                          - Modify the member of the trap hwXponConfigPmConfigTrap
                          - Add the table hwXponDeviceCommonGlobalObjects for setting or obtaining device common global information of XPON.
                          - Add leaf hwXponDeviceLosAlarmControlState in hwXponDeviceCommonGlobalObjects for alarm los-control.
                         "
                         
            REVISION     "201011030900Z"
            DESCRIPTION  "V1.11, changes in this revision:
                          - Add the table of hwXponOntBatchInfoTable to query all of the ont information.
                          - Add the table of hwXponOntPppoeSimuTestInfoTable 
                            and the trap of hwXponCommonDeviceOntPppoeSimuTrap for PPPOE test.
                          - Modify the node of the hwXponCommonDeviceOntPingResult, 
                            add the node of hwXponCommonDeviceReceivedErrorCode for the test of remote ping
                          - Add the table of the hwXponOntControlTable for ONT configration.
                          - Add the node of the hwXponOntInfoCfgFileCrc
                          - Add the node of the hwXponOntInfoAppLoadState and hwXponOntInfoXmlLoadState 
                            for ONT load.
                          - Modify the description of the hwGponConfigOntPortNativeVlanTrap.
                         "

            REVISION     "201009280900Z"
            DESCRIPTION  "V1.10, changes in this revision:
                          - Modify the description of the MIB file.
                         "

            REVISION     "201008250900Z"
            DESCRIPTION  "V1.09, changes in this revision:
                          - Modify the value range of the leaf hwGponOntPortTDMCodeMode.
                         "

            REVISION     "201008110900Z"
            DESCRIPTION  "V1.08, changes in this revision:
                          - Add leaf hwGponDeviceTcontAutoCombineSwitch in hwGponDeviceCommonGlobalObjects for T-CONT auto-combine."

            REVISION     "201007070900Z"
            DESCRIPTION  "V1.07, changes in this revision:
                          Add the leaf nodes hwXponModeSwitchResult, hwXponConfigMode, hwGponOltMinBandwidth, hwGponOltNearestDistance,hwGponOltFarestDistance,
                          hwGponOltAutoFindOntFlag,hwGponOltAutoUpdateOntFlag,hwGponOltDownFecEnableFlag,hwGponOntPortTDMCodeMode,hwGponOntPortManagementStatus,
                          hwGponOntEthPortLoopback,hwGponOntE1PortLoopback,hwGponOntPortVlanDefault, hwGponOntPortVlanDefaultPriority in hwXponCommonTrapsVbOids
                          for standard traps.
                          Add the definition of the trap node: hwXponSwitchModeResultTrap,hwXponConfigModeTrap,hwXponConfigChangeSnmpProfileTrap,
                          hwXponConfigPmConfigTrap,hwXponConfigOltTypeBDparentDelTrap,hwGponConfigOltTypeBDparentTrap,hwGponConfigOltTypeBDparentCreateTrap,
                          hwGponConfigOltTypeBDparentCreateTrap,hwGponConfigOntPortNativeTrap,in hwXponCommonGeneralTraps for standard traps.
                          Modify the definition of the leaf node, include:hwXponCommonDeviceOntRemotePingTrap for trap optimization.
                          Modify the attribute value,include node:hwGponDeviceOntPotsPortPTPSrvState,hwGponDeviceOntPotsPortPTPAdminState,
                          hwGponDeviceOntPotsPortPTPHookState,hwGponDeviceOntPotsPortCTPSrvState,hwGponDeviceOntPotsPortCTPSrvType,hwGponDeviceOntPotsPortCTPSrvCode.
                         "

            REVISION     "201006070900Z"
            DESCRIPTION  "V1.06, changes in this revision:
                          Modify the definition difference between MIB file and tree.c                          
                         "

            REVISION     "201004290900Z"
            DESCRIPTION  "V1.05, changes in this revision:
                          Add the table hwGponDeviceCommonGlobalObjects for setting or obtaining device common global information of GPON.
                          Add the leaf nodes hwXponOntInfoMemoryOccupation,hwXponOntInfoCpuOccupation,hwXponOntInfoTemperature,hwXponOntInfoProductDescription
                          in table hwXponOntInfoTable for obtaining ONT information.
                          Add the leaf nodes hwXponDeviceOntControlPrimaryStatus ,hwXponDeviceOntControlSecondaryStatus
                          in table hwXponOntInfoTable for obtaining ONT status of the Board.
                          Add the table hwXponOntIpConfigTable to config the ONT.
                          Add the table hwXponCommonTrapsVbOids and hwXponCommonTraps for standard traps.
                          Add leaf nodes hwXponPortStateChangeTrap and hwXponOntCfgStateChangeTrap in hwXponCommonGeneralTraps for standard traps.
                          Add the table hwXponPortStateTable to query the port state information.
                         "

            REVISION     "201004070900Z"
            DESCRIPTION  "V1.04, changes in this revision:
                          Add the table hwXponOntInfoTable to query the ont information.
                         "

            REVISION     "201003170900Z"
            DESCRIPTION  "V1.03, changes in this revision:
                          Modify the attribute value,include node:hwGponDeviceOntPotsPortPTPSrvState,hwGponDeviceOntPotsPortPTPAdminState,
                          hwGponDeviceOntPotsPortPTPHookState,hwGponDeviceOntPotsPortCTPSrvState,hwGponDeviceOntPotsPortCTPSrvType,
                          hwGponDeviceOntPotsPortCTPSrvCode.
                         "

            REVISION     "201003100900Z"
            DESCRIPTION  "V1.02, changes in this revision:
                          Add the leaf node hwXponOntTransmittingFileLength in table hwXponOntFileTransmitionTable for setting or obtaining
                          the length of the file to be transmit.
                         "

            REVISION     "201001210900Z"
            DESCRIPTION  "V1.01, invariant."

            REVISION     "200912300900Z"
            DESCRIPTION  "V1.00, Initial version."
            ::= { huaweiUtility  145 }

        hwXponCommonObjectMIB OBJECT IDENTIFIER ::= { hwXponCommonMIB 1}

        hwXponCommonObjects OBJECT IDENTIFIER ::= { hwXponCommonObjectMIB  1}

        hwXponCommonControlObjects OBJECT IDENTIFIER ::= { hwXponCommonObjects 1}

        hwXponCommonStatisticObjects OBJECT IDENTIFIER ::= { hwXponCommonObjects 2}

        hwGponDeviceCommonGlobalObjects OBJECT IDENTIFIER ::= { hwXponCommonObjects 3}
        
        hwXponDeviceCommonGlobalObjects OBJECT IDENTIFIER ::= { hwXponCommonObjects 4}
        
        hwXponDeviceCommonProfileObjects OBJECT IDENTIFIER ::= { hwXponCommonObjects 5}
        
        hwEponDeviceCommonGlobalObjects OBJECT IDENTIFIER ::= { hwXponCommonObjects 6}

   --Table hwGponDeviceOntVoipCfgFileInfoTable
        hwGponDeviceOntVoipCfgFileInfoTable OBJECT-TYPE
            SYNTAX SEQUENCE OF HwGponDeviceOntVoipCfgFileInfoEntry
            MAX-ACCESS not-accessible
            STATUS     current
            DESCRIPTION
                "The hwGponDeviceOntVoipCfgFileInfoTable is used to query the version information and validation status of the ONT voice configuration file.
                 The indexes of this table are ifIndex and hwGponDeviceOntObjIndex.
                "
            ::= { hwXponCommonControlObjects 1 }

        hwGponDeviceOntVoipCfgFileInfoEntry OBJECT-TYPE
            SYNTAX HwGponDeviceOntVoipCfgFileInfoEntry
            MAX-ACCESS not-accessible
            STATUS current
            DESCRIPTION
                "The hwGponDeviceOntVoipCfgFileInfoTable is used to query the version information and validation status of the ONT voice configuration file.
                 The indexes of this entry are ifIndex and hwGponDeviceOntObjIndex.
                "
            INDEX       { ifIndex, hwGponDeviceOntObjIndex }
            ::= { hwGponDeviceOntVoipCfgFileInfoTable 1 }

        HwGponDeviceOntVoipCfgFileInfoEntry ::=
            SEQUENCE
                {
                hwGponDeviceOntObjIndex               Integer32,
                hwGponDeviceOntVoipCfgFileState       INTEGER,
                hwGponDeviceOntVoipCfgFileVersion     OCTET STRING,
                hwGponDeviceOntVoipFtpCfgResult       INTEGER
                }

        hwGponDeviceOntObjIndex  OBJECT-TYPE
            SYNTAX       Integer32
            MAX-ACCESS   not-accessible
            STATUS       current
            DESCRIPTION
                "ONT ID, range: 0-127."
            ::= { hwGponDeviceOntVoipCfgFileInfoEntry 1}

        hwGponDeviceOntVoipCfgFileState OBJECT-TYPE
            SYNTAX      INTEGER
                {
                inactive (1),
                active (2),
                initializing (3),
                fault (4),
                invalid (-1)
                }
            MAX-ACCESS  read-only
            STATUS      current
            DESCRIPTION
                "ONT VOIP configuration file state.
                 Options:
                 1. inactive(1)     - Configuration retrieval has not been attempted
                 2. active(2)       - Configuration was retrieved
                 3. initializing(3) - Configuration is now being retrieved
                 4. fault(4)        - Configuration retrieval process failed
                 5. invalid(-1)     - Indicates that the query fails or no information is detected
                "
            ::= { hwGponDeviceOntVoipCfgFileInfoEntry 2 }

        hwGponDeviceOntVoipCfgFileVersion OBJECT-TYPE
            SYNTAX      OCTET STRING (SIZE(0..25))
            MAX-ACCESS  read-only
            STATUS      current
            DESCRIPTION
                "ONT VOIP file version."
            ::= { hwGponDeviceOntVoipCfgFileInfoEntry 3 }

       hwGponDeviceOntVoipFtpCfgResult OBJECT-TYPE
            SYNTAX     INTEGER
                {
                success(0),
                resolvefail(1),
                notreach(2),
                notconnect(3),
                notvalidate(4),
                notauthenticate(5),
                responsetimeout(6),
                responsefail(7),
                configfileerror(8),
                invalid(-1)
                }
            MAX-ACCESS read-only
            STATUS     current
            DESCRIPTION
                "Query the failed alarm information of config XML file.
                 Options:
                 1. success(0)            - The ONT configuration is successful
                 2. resolvefail(1)        - Failed to resolve the configuration server name
                 3. notreach(2)           - Cannot reach configuration server(The port cannot be reached, ICMP errors)
                 4. notconnect(3)         - Cannot connect to configuration server (due to bad credentials or other fault after the port responded)
                 5. notvalidate(4)        - Cannot validate configuration server
                 6. notauthenticate(5)    - Cannot authenticate configuration session (e.g. missing credentials)
                 7. responsetimeout(6)    - Timeout waiting for response from configuration server
                 8. responsefail(7)       - Failure response received from configuration server
                 9. configfileerror(8)    - Configuration file received has an error
                 10. invalid(-1)          - Other errors
                 "
            ::= { hwGponDeviceOntVoipCfgFileInfoEntry  4 } 
            
  -- Table hwGponDeviceOntPotsPortStateTable
        hwGponDeviceOntPotsPortStateTable OBJECT-TYPE
            SYNTAX SEQUENCE OF HwGponDeviceOntPotsPortStateEntry
            MAX-ACCESS not-accessible
            STATUS     current
            DESCRIPTION
                "Query the state of ONT POTS port table.The table is used to query the
                 state of ONT POTS port.
                 The indexes of this table are ifIndex, hwGponDeviceOntObjIndex and hwGponDeviceOntPotsPortId.
                "
            ::= { hwXponCommonControlObjects 2 }

        hwGponDeviceOntPotsPortStateEntry OBJECT-TYPE
            SYNTAX HwGponDeviceOntPotsPortStateEntry
            MAX-ACCESS not-accessible
            STATUS     current
            DESCRIPTION
                "Query the state of ONT POTS port table.The table is used to query the
                 state of ONT POTS port.
                 The indexes of this entry are ifIndex, hwGponDeviceOntObjIndex and hwGponDeviceOntPotsPortId.
                "
            INDEX       { ifIndex, hwGponDeviceOntObjIndex, hwGponDeviceOntPotsPortId }
            ::= { hwGponDeviceOntPotsPortStateTable 1 }

        HwGponDeviceOntPotsPortStateEntry ::=
            SEQUENCE
                {
                hwGponDeviceOntPotsPortId                Integer32,
                hwGponDeviceOntPotsPortPTPSrvState       INTEGER,
                hwGponDeviceOntPotsPortPTPAdminState     INTEGER,
                hwGponDeviceOntPotsPortPTPHookState      INTEGER,
                hwGponDeviceOntPotsPortCTPSrvState       INTEGER,
                hwGponDeviceOntPotsPortCTPSrvType        INTEGER,
                hwGponDeviceOntPotsPortCTPSrvCode        INTEGER
                }

        hwGponDeviceOntPotsPortId OBJECT-TYPE
            SYNTAX      Integer32
            MAX-ACCESS  not-accessible
            STATUS      current
            DESCRIPTION
                "ONT POTS port ID."
            ::= { hwGponDeviceOntPotsPortStateEntry 1 }

        hwGponDeviceOntPotsPortPTPSrvState OBJECT-TYPE
            SYNTAX   INTEGER
                {
                normal (1),
                fail (2),
                invalidState (-1)
                }
            MAX-ACCESS  read-only
            STATUS      current
            DESCRIPTION
                "ONT POTS port physics running state.
                 Options:
                 1. normal(1)        - Normal state
                 2. fail(2)          - Fail state
                 3. invalidState(-1) - Returned in case of query failure or error
                "
            ::= { hwGponDeviceOntPotsPortStateEntry 2 }

        hwGponDeviceOntPotsPortPTPAdminState OBJECT-TYPE
            SYNTAX      INTEGER
                {
                lock (1),
                unlock (2),
                invalidState (-1)
                }
            MAX-ACCESS  read-only
            STATUS      current
            DESCRIPTION
                "ONT POTS port physics admin state.
                 Options:
                 1. lock(1)          - All user functions of this circuit pack are blocked, and alarm for this managed entity
                                       are no longer generated
                 2. unlock(2)        - Unlock state, all user functions of this circuit pack are normal
                 3. invalidState(-1) - This value is return when can't query or have some errors in query
                "
            ::= { hwGponDeviceOntPotsPortStateEntry 3 }

        hwGponDeviceOntPotsPortPTPHookState OBJECT-TYPE
            SYNTAX   INTEGER
                {
                onHook (1),
                offHook (2),
                invalidState (-1)
                }
            MAX-ACCESS  read-only
            STATUS      current
            DESCRIPTION
                   "ONT POTS port physics hook state.
                    Options:
                    1. onHook(1)        - ONT POTS port physics is onHook
                    2. offHook(2)       - ONT POTS port physics is offHook
                    3. invalidState(-1) - Returned in case of query failure or error
                   "
            ::= { hwGponDeviceOntPotsPortStateEntry 4 }

        hwGponDeviceOntPotsPortCTPSrvState OBJECT-TYPE
            SYNTAX   INTEGER
                {
                noneOrinitial (1),
                registered (2),
                inSession (3),
                failedRegistration (4),
                failedInvite (5),
                portNotconfigured (6),
                configDone (7),
                invalidState (-1)
                }
            MAX-ACCESS  read-only
            STATUS      current
            DESCRIPTION
                "ONT POTS port service running state.
                 Options:
                 1. noneOrinitial(1)      - None or initial state
                 2. registered(2)         - Registered state
                 3. inSession(3)          - In session
                 4. failedRegistration(4) - Failed in registration
                 5. failedInvite(5)       - Failed in invite
                 6. portNotconfigured(6)  - Port doesn't configure
                 7. configDone(7)         - Config has been done
                 8. invalidState(-1)      - Returned in case of query failure or error
                "
            ::= { hwGponDeviceOntPotsPortStateEntry 5 }

        hwGponDeviceOntPotsPortCTPSrvType OBJECT-TYPE
            SYNTAX   INTEGER
                {
                idleOrnone (1),
                twoWay (2),
                threeWay (3),
                fax (4),
                telem (5),
                conference (6),
                invalidType (-1)
                }
            MAX-ACCESS  read-only
            STATUS      current
            DESCRIPTION
                "ONT POTS port service type.
                 Options:
                 1. idleOrnone(1)       - Idle or none type
                 2. twoWay(2)           - Two way type
                 3. threeWay(3)         - Three way type
                 4. fax(4)              - Fax type
                 5. telem(5)            - Telem type
                 6. conference(6)       - Conference type
                 7. invalidType(-1)     - Invalid type
                "
            ::= { hwGponDeviceOntPotsPortStateEntry 6 }

        hwGponDeviceOntPotsPortCTPSrvCode OBJECT-TYPE
            SYNTAX   INTEGER
                {
                pcmu (1),
                reserved1 (2),
                reserved2 (3),
                gsm (4),
                g723 (5),
                dvi4ClockRate8000 (6),
                dvi4ClockRate16000 (7),
                lpc (8),
                pcma (9),
                g722 (10),
                l16TwoChannels  (11),
                l16OneChannel (12),
                qcelp (13),
                cn (14),
                mpa (15),
                g728 (16),
                dvi4ClockRate11025 (17),
                dvi4ClockRate22050 (18),
                g729 (19),
                t38(20),
                invalidCode (-1)
                }
            MAX-ACCESS  read-only
            STATUS      current
            DESCRIPTION
                "ONT POTS port code mode.
                 Options:
                 1.  pcmu(1)                - Audio data is encoded as eight bits per sample, after logarithmic scaling.
                                              PCMU denotes mu-law scaling
                 2.  reserved1(2)           - Reserved
                 3.  reserved2(3)           - Reserved
                 4.  gsm(4)                 - GSM denotes the European GSM 06.10 standard for full-rate
                                              speech transcoding, ETS 300 961, which is based on RPE/LTP (residual pulse
                                              excitation/long term prediction) coding at a rate of 13 kb/
                 5.  g723(5)                - Dual-rate speech coder for multimedia communications transmitting at 5.3 and 6.3
                                              kbit/s
                 6.  dvi4ClockRate8000(6)   - DVI4 uses an adaptive delta pulse code modulation (ADPCM) encoding scheme that was
                                              specified by the Interactive Multimedia Association (IMA) as the IMA ADPCM wave type,
                                              and the clock rate is 8000HZ
                 7.  dvi4ClockRate16000(7)  - DVI4 uses an adaptive delta pulse code modulation (ADPCM) encoding scheme that was
                                              specified by the Interactive Multimedia Association (IMA) as the IMA ADPCM wave type,
                                              and the clock rate is 16000HZ
                 8.  lpc(8)                 - LPC designates an experimental linear predictive encoding contributed by Ron Frederick,
                                              which is based on an implementation written by Ron Zuckerman posted to the Usenet group
                                              comp
                 9.  pcma(9)                - Audio data is encoded as eight bits per sample, after logarithmic scaling. PCMA denotes
                                              A-law scaling
                 10. g722(10)               - 7 kHz audio-coding within 64 kbit/s
                 11. l16TwoChannels(11)     - Two channel encoding
                 12. l16OneChannel(12)      - One channel encoding
                 13. qcelp(13)              - QCELP CODEC compresses each 20 milliseconds of 8,000 Hz
                 14. cn(14)                 - Comfort Noise
                 15. mpa(15)                - MPA denotes MPEG-1 or MPEG-2 audio encapsulated as elementary streams
                 16. g728(16)               - Coding of speech at 16 kbit/s using low-delay code excited linear prediction
                 17. dvi4ClockRate11025(17) - DVI4 uses an adaptive delta pulse code modulation (ADPCM) encoding scheme that was specified
                                              by the Interactive Multimedia Association (IMA) as the IMA ADPCM wave type, and the clock rate
                                              is 11025HZ.
                 18. dvi4ClockRate22050(18) - DVI4 uses an adaptive delta pulse code modulation (ADPCM) encoding  scheme that was specified
                                              by the Interactive Multimedia Association (IMA) as the IMA ADPCM wave type, and the clock rate
                                              is 11025HZ.
                 19. g729(19)               - Coding of speech at 8 kbit/s using conjugate structure-algebraic code excited linear prediction
                 20. t38(20)                - T.38 is used by the IFP peer to verify message alignment. It is identified by an ASN.1 Application tag
                 21. invalidCode(-1)        - Invalid code
                "
            ::= { hwGponDeviceOntPotsPortStateEntry 7 }

  --Table hwXponOntFileTransmitionTable
        hwXponOntFileTransmitionTable OBJECT-TYPE
            SYNTAX     SEQUENCE OF HwXponOntFileTransmitionEntry
            MAX-ACCESS not-accessible
            STATUS     current
            DESCRIPTION
                "This is ONT file transmission table. This table is used to
                 transmit the config or diagnose files between BMS and ONU.
                 The indexes of this table are ifIndex, hwXponOntIndex and
                 hwXponOntTransmittingSerialNo.
                "
            ::= { hwXponCommonControlObjects 3 }

        hwXponOntFileTransmitionEntry OBJECT-TYPE
            SYNTAX     HwXponOntFileTransmitionEntry
            MAX-ACCESS not-accessible
            STATUS     current
            DESCRIPTION
                "This is ONT file transmission table. This table is used to
                 transmit the config or diagnose files between BMS and ONU.
                 The indexes of this entry are ifIndex, hwXponOntIndex and
                 hwXponOntTransmittingSerialNo.
                "
            INDEX       { ifIndex, hwXponOntIndex, hwXponOntTransmittingSerialNo }
            ::= { hwXponOntFileTransmitionTable 1 }

        HwXponOntFileTransmitionEntry  ::=
            SEQUENCE
                {
                hwXponOntIndex                            Integer32,
                hwXponOntTransmittingSerialNo             Integer32,
                hwXponOntTransmittingFileValue            OCTET STRING,
                hwXponOntTransmittingFileLength           Unsigned32,
                hwXponOntTransmittingFree                 INTEGER
                }

        hwXponOntIndex   OBJECT-TYPE
            SYNTAX       Integer32
            MAX-ACCESS   not-accessible
            STATUS       current
            DESCRIPTION
                "ONT ID, range: 0-254."
            ::= { hwXponOntFileTransmitionEntry 1}

        hwXponOntTransmittingSerialNo OBJECT-TYPE
            SYNTAX      Integer32
            MAX-ACCESS  not-accessible
            STATUS      current
            DESCRIPTION
                "The serial number of transmission."
            ::= { hwXponOntFileTransmitionEntry  2 }

        hwXponOntTransmittingFileValue OBJECT-TYPE
            SYNTAX      OCTET STRING (SIZE (0..8192))
            MAX-ACCESS  read-write
            STATUS      current
            DESCRIPTION
                "The file to be transmitted."
            ::= { hwXponOntFileTransmitionEntry  3 }

        hwXponOntTransmittingFileLength OBJECT-TYPE
            SYNTAX      Unsigned32
            MAX-ACCESS  read-write
            STATUS      current
            DESCRIPTION
                "The length of the file to be transmitted."
            ::= { hwXponOntFileTransmitionEntry  4 }
            
        hwXponOntTransmittingFree OBJECT-TYPE
            SYNTAX      INTEGER
                {
                clear(1),
                invalid(-1)
                }
            MAX-ACCESS  read-write
            STATUS      current
            DESCRIPTION
                "This object is used to free ONT transmitting buffer.
                 Options:
                 1. clear(1)            - Execute to free ONT transmitting buffer.
                 2. invalid(-1)         - Indicates that the query fails or no information is detected.
                 "
            ::= { hwXponOntFileTransmitionEntry  5 }
            
  --Table hwXponOntInfoTable
        hwXponOntInfoTable OBJECT-TYPE
            SYNTAX     SEQUENCE OF HwXponOntInfoEntry
            MAX-ACCESS not-accessible
            STATUS     current
            DESCRIPTION
                "The ont info table. This table is used to query the ont information.
                 The indexes of this table are ifIndex and hwXponOntIndex.
                "
            ::= { hwXponCommonControlObjects 4 }

        hwXponOntInfoEntry OBJECT-TYPE
            SYNTAX     HwXponOntInfoEntry
            MAX-ACCESS not-accessible
            STATUS     current
            DESCRIPTION
                "The ont info table. This table is used to query the ont information.
                 The indexes of this entry are ifIndex and hwXponOntIndex.
                "
            INDEX       { ifIndex, hwXponOntIndex}
            ::= { hwXponOntInfoTable 1 }

        HwXponOntInfoEntry  ::=
            SEQUENCE
                {
                hwXponOntInfoOnlineDuration            Gauge32,
                hwXponOntInfoMemoryOccupation          Integer32,
                hwXponOntInfoCpuOccupation             Integer32,
                hwXponOntInfoTemperature               Integer32,
                hwXponOntInfoProductDescription        OCTET STRING,
                hwXponDeviceOntControlPrimaryStatus    INTEGER,
                hwXponDeviceOntControlSecondaryStatus  BITS,
                hwXponOntInfoCfgFileCrc                Integer32,
                hwXponOntInfoAppLoadState              Integer32,
                hwXponOntInfoXmlLoadState              Integer32,
                hwXponOntInfoSupportXmlVersion         OCTET STRING,
                hwXponOntLastDistance                  Integer32,
                hwXponOntInfoNoOnLineReason            Integer32,
                hwXponOntInfoXmlLoadErrorInfo          OCTET STRING,
                hwXponOntInfoInteroperabilityStandard  INTEGER,
                hwGponDeviceOntObjectExtendFrameID     Integer32,
                hwXponOntInfoUsedMutualAuth            INTEGER,
                hwXponOntInfoPowerReductionStatus      INTEGER,
                hwXponOntInfoNniPhysicalUpRate         Integer32,
                hwXponOntInfoNniPhysicalDownRate       Integer32,
                hwGponDeviceOntActualNniType           INTEGER,
                hwGponDeviceOntLastActualNniType       INTEGER,
                hwXponOntInfoHostName                  OCTET STRING,
                hwXponOntFecStatus                     INTEGER,
                hwGponXponOntVsID                      Integer32,
                hwGponXponGlobalOntID                  Integer32,
                hwGponDeviceOntActualWorkChannel       Integer32,
                hwXponOntInfoPowerType                 INTEGER,
                hwXponOntInfoSystemUpDuration          Gauge32
		}

        hwXponOntInfoOnlineDuration OBJECT-TYPE
            SYNTAX      Gauge32
            UNITS       "second"
            MAX-ACCESS  read-only
            STATUS      current
            DESCRIPTION
                "The one-time online duration of the ONT.
                 Unit: second
                "
            ::= { hwXponOntInfoEntry  1 }

        hwXponOntInfoMemoryOccupation OBJECT-TYPE
            SYNTAX      Integer32
            MAX-ACCESS  read-only
            STATUS      current
            DESCRIPTION
                "The Memory occupation of the ONT, range: 0-100."
            ::= { hwXponOntInfoEntry  2 }

        hwXponOntInfoCpuOccupation OBJECT-TYPE
            SYNTAX      Integer32
            MAX-ACCESS  read-only
            STATUS      current
            DESCRIPTION
                "The CPU occupation of the ONT, range: 0-100."
            ::= { hwXponOntInfoEntry  3 }

        hwXponOntInfoTemperature OBJECT-TYPE
            SYNTAX      Integer32
            UNITS       "degree centigrade"
            MAX-ACCESS  read-only
            STATUS      current
            DESCRIPTION
                "The temperature of the ONT.
                 Unit: degree centigrade
                "
            ::= { hwXponOntInfoEntry  4 }

        hwXponOntInfoProductDescription  OBJECT-TYPE
            SYNTAX       OCTET STRING (SIZE (0..256))
            MAX-ACCESS   read-only
            STATUS       current
            DESCRIPTION
                "The product description of the ONT."
            ::= { hwXponOntInfoEntry 5 }

        hwXponDeviceOntControlPrimaryStatus OBJECT-TYPE
            SYNTAX     INTEGER
                {
                isNr(1),
                isAnr(2),
                isRst(3),
                isAnrst(4),
                oosAu(5),
                oosMa(6),
                oosAuma(7),
                oosAurst(8),
                oosMaanr(9)
                }
            MAX-ACCESS read-only
            STATUS     current
            DESCRIPTION
                "The primary status of the Board.This parameter indicates the current overall
                 service condition of an entity, i.e., whether it is in-service or out-of-service.
                 Options:
                 1. isNr(1)     - Normal
                 2. isAnr(2)    - Abnormal
                 3. isRst(3)    - Restricted
                 4. isAnrst(4)  - Abnormal & Restricted
                 5. oosAu(5)    - Autonomous
                 6. oosMa(6)    - Management
                 7. oosAuma(7)  - Autonomous & Management
                 8. oosAurst(8) - Autonomous & Restricted
                 9. oosMaanr(9) - Management & Abnormal
                "
            ::= { hwXponOntInfoEntry  6 }

        hwXponDeviceOntControlSecondaryStatus OBJECT-TYPE
            SYNTAX     BITS
                {
                sstAins(0),
                sstFaf(1),
                sstFlt(2),
                sstLpbk(3),
                sstMea(4),
                sstSgeo(5),
                sstStbyh(6),
                sstTs(7),
                sstUas(8),
                sstUeq(9),
                sstWrk(10),
                sstPwr(11)
                }
            MAX-ACCESS read-only
            STATUS     current
            DESCRIPTION
                "This parameter indicates the secondary status of the board. The parameter provides additional
                 information pertaining to PST and PSTQ. For example, it may indicate the type and/or reason of
                 the external command, the event that occurred in the Network Element, etc. Multiple values may
                 apply to an entity at a given moment. The highest bit of SST value indicates the sstAins(0)
                 status;
                 The second highest bit of SST value indicates the sstFaf(1) status, and the rest can be deduced
                 by analogy.
                 This BITS structure can report the following status:
                 1.  sstAins(0)  - this bit position positively reports that the status of the board is automatic in-service
                 2.  sstFaf(1)   - Facility Failure
                 3.  sstFlt(2)   - Fault
                 4.  sstLpbk(3)  - Loopback
                 5.  sstMea(4)   - Mismatch of Equipment and Attributes
                 6.  sstSgeo(5)  - Supporting Entity Outage
                 7.  sstStbyh(6) - Standby-Hot
                 8.  sstTs(7)    - Test
                 9.  sstUas(8)   - Unassigned
                 10. sstUeq(9)   - Unequipped
                 11. sstWrk(10)  - Working
                 12. sstPwr(11)  - Power
                 "
            ::= { hwXponOntInfoEntry  7 }

        hwXponOntInfoCfgFileCrc OBJECT-TYPE
            SYNTAX      Integer32
            MAX-ACCESS  read-only
            STATUS      current
            DESCRIPTION
                "The CRC value of the ONT."
            ::= { hwXponOntInfoEntry  8 }

        hwXponOntInfoAppLoadState OBJECT-TYPE
            SYNTAX      Integer32
            MAX-ACCESS  read-only
            STATUS      current
            DESCRIPTION
                "The state of the app load for ONT.
                 0x01 initstate
                 0x02 process %0
                 0x03 ftp load fail
                 0x04 loaded to mainboard process %10
                 0x05 loaded to ponboard process %20
                 0x06 loaded to ponboard fail
                 0x07 process %80
                 0x08 fail:user stop
                 0x09 fail:ont offline 
                 0x0a fail:ont response fail
                 0x0b fail:ont response timeout
                 0x0c fail:pon inner error
                 0x0d process %100,ont restart
                 0x0e Process %100 the ont now is in survival mode
                 0x0f fail:system is busy because the ponboard's channel is occupied
                 0x10 fail:failed to verify the version information
                 0x11 fail:processing the loading task timed out
                 0x12 fail:ont file check failure
                 0x13 fail:code file validate failure
                 0x14 fail:system buffer is insufficient
                 0x15 fail:ont not support load
                 0x16 fail:ont storage space insufficient
                 0x17 fail:ont image file error
                 0x18 fail:ont image file existed
                 0x19 fail:ont activate image file fail
                 0x1a fail:ont commit image file fail
                 0x1b fail:ont image file crc error
                 0xff fail:unknown reason
                "
            ::= { hwXponOntInfoEntry  9 }

        hwXponOntInfoXmlLoadState OBJECT-TYPE
            SYNTAX      Integer32
            MAX-ACCESS  read-only
            STATUS      current
            DESCRIPTION
                "The state of the xml load for ONT.
                 0x01 initstate
                 0x02 process %0
                 0x03 ftp load fail
                 0x04 loaded to mainboard process %10
                 0x05 loaded to ponboard process %20
                 0x06 loaded to ponboard fail
                 0x07 process %80
                 0x08 process %100
                 0x09 fail:user stop
                 0x0a fail:ont not support xml
                 0x0b fail:ont offline 
                 0x0c fail:ont response unknown fail
                 0x0d fail:ont response timeout
                 0x0e fail:xml error ont will reconfigure fail
                 0x0f fail:xml format error 
                 0x10 fail:xml content error
                 0x11 fail:ont find xml transfer error
                 0x12 fail:unknown error from ont
                 0x13 fail:unknown error from ponboard
                 0x14 fail:system is busy because the ponboard's channel is occupied
                 0xff fail:unknown reason
                "
            ::= { hwXponOntInfoEntry  10 }
            
        hwXponOntInfoSupportXmlVersion OBJECT-TYPE
            SYNTAX       OCTET STRING (SIZE (0..25))
            MAX-ACCESS   read-only
            STATUS       current
            DESCRIPTION
                "The xml version that the ONT supports, it is a V.R.C.SP string."
            ::= { hwXponOntInfoEntry 11 }          
                     
        hwXponOntLastDistance OBJECT-TYPE
            SYNTAX      Integer32
            UNITS       "m"
            MAX-ACCESS  read-only
            STATUS      current
            DESCRIPTION
                "The last ranging value of the ONT.
                 Unit: m
                 Options: 
                 1. invalid (-1)            - Indicates that the query fails or no information is detected."
            ::= { hwXponOntInfoEntry  12 }

        hwXponOntInfoNoOnLineReason OBJECT-TYPE
            SYNTAX      Integer32
            MAX-ACCESS  read-only
            STATUS      current
            DESCRIPTION
                "This object indicates the reason why the ONT goes offline.
                 The value (1) indicates that there is no third-party ONT interoperability certification.
                 The value (2) indicates that the ONT interoperability mode mismatches with the OLT's.
                 The value (3) indicates that the ONT basic information fails to be obtained.
                 The value (5) indicates that the ONT interoperability file mismatches with the OLT's.
                 The value (8) indicates that the ONT is incompatible with the OLT.
                 The value (9) indicates that the actual ONT optical power is lower than the threshold for the optical power of the ONT going online.
                 The value (10) indicates that the ONT is not in the white list.
                 The value (-1) indicates that the ONT has interoperability access license."
            ::= { hwXponOntInfoEntry  13 }
        hwXponOntInfoXmlLoadErrorInfo  OBJECT-TYPE
            SYNTAX       OCTET STRING (SIZE (0..280))
            MAX-ACCESS   read-only
            STATUS       current
            DESCRIPTION
                "Indicates the error information when the ONT XML configuration fails to be loaded."
            ::= { hwXponOntInfoEntry 14 }
            
        hwXponOntInfoInteroperabilityStandard  OBJECT-TYPE
            SYNTAX       INTEGER
                {
                ituT(1),
                ctc(2),
                ericV1(3),
                ericV2(4),
                ituTG984(5),
                ituTG988(6),
                cuc(7),
                cmcc(8),
                eci(9),
                mode1(10),
                mode2(11),
                mode2V2(12),
                mode3(13),
                mode4(14),
                mode2V3(15),
                mode2V4(16),
                mode5(17),
                eciV2(18),
                mode1V2(19),
                invalid(-1)
                }
            MAX-ACCESS   read-only
            STATUS       current
            DESCRIPTION
                "The interoperability mode of the ONT.
                 Options:
                 1. ituT(1)    	  - Indicates that the interoperability standard of the ONT is ituT
                 2. ctc(2)        - Indicates that the interoperability standard of the ONT ctc
                 3. ericV1(3)     - Indicates that the interoperability standard of the ONT is ericV1
                 4. ericV2(4)     - Indicates that the interoperability standard of the ONT is ericV2
                 5. ituTG984(5)   - Indicates that the interoperability standard of the ONT is ituTG984
                 6. ituTG988(6)   - Indicates that the interoperability standard of the ONT is ituTG988 
                 7. cuc(7)        - Indicates that the interoperability standard of the ONT is cuc
                 8. cmcc(8)       - Indicates that the interoperability standard of the ONT is cmcc     
                 9. eci(9)        - Indicates that the interoperability standard of the ONT is eci
                 10. mode1(10)    - Indicates that the interoperability standard of the ONT is mode1 
                 11. mode2(11)    - Indicates that the interoperability standard of the ONT is mode2                      
                 12. mode2V2(12)  - Indicates that the interoperability standard of the ONT is mode2V2  
                 13. mode3(13)    - Indicates that the interoperability standard of the ONT is mode3    
                 14. mode4(14)    - Indicates that the interoperability standard of the ONT is mode4 
                 15. mode2V3(15)  - Indicates that the interoperability standard of the ONT is mode2V3
                 16. mode2V4(16)  - Indicates that the interoperability standard of the ONT is mode2V4 
                 17. mode5(17)    - Indicates that the interoperability standard of the ONT is mode5 
                 18. eciV2(18)    - Indicates that the interoperability standard of the ONT is eciV2
                 19. mode1V2(19)  - Indicates that the interoperability standard of the ONT is mode1V2
                 20. invalid(-1)  - Indicates that the query fails or no information is detected
                 "
            ::= { hwXponOntInfoEntry 15 } 
                       
                    hwGponDeviceOntObjectExtendFrameID  OBJECT-TYPE
                        SYNTAX      Integer32
                        MAX-ACCESS  read-only
                        STATUS      current
                        DESCRIPTION
                            "Extend Frame ID. The issued value (-1) of Extend Frame ID indicates that the ONT is not specified to any Extend Frame."
                        ::= { hwXponOntInfoEntry 16 } 
                        
        hwXponOntInfoUsedMutualAuth OBJECT-TYPE
            SYNTAX INTEGER {
                   yes (1),
                   no (2),
                   invalid (-1)
            }
            MAX-ACCESS read-only
            STATUS current
            DESCRIPTION
                 "Indicates whether the ONT uses mutual authentication.
                  Options:
                  1. yes (1)           -Indicates the ONT uses mutual authentication.
                  2. no (2)            -Indicates the ONT does not use mutual authentication.
                  3. invalid (-1)      -Indicates the invalid value.
                 "
            ::= { hwXponOntInfoEntry 17 }  
            
       hwXponOntInfoPowerReductionStatus OBJECT-TYPE
            SYNTAX  INTEGER{
                normal (1), 
                doze (2),
                cyclicSleep (3),
                watchfulSleep (4),
                invalid (-1) 
            }
            MAX-ACCESS read-only
            STATUS current
            DESCRIPTION
                 "Indicates whether the ONT is in power reduction state and its actual power reduction state.
                  Options:
                  1. normal(1)           -It means the ONT is in normal state,it is running normally and is not performing power reduction function.
                  2. doze(2)             -doze mode:when in a LowPower state (the Asleep state) in this mode the ONT receiver remains active, ONT can receive downstream traffic,but it will deactivate its transmitter periodicly ,at this time it can't send its upstream traffic. 
                  3. cyclicSleep(3)      -cyclic sleep mode:when in a LowPower state (the Asleep state) in this mode, the ONT receiver is inactive;the ONT cannot receive downstream traffic. its transmitter is also inactive,so it can't send its upstream traffic.  
                  4. watchfulSleep(4)    -watchful sleep mode:when in a LowPower state (the Watch state) in this mode, the ONT periodically checks the downstream traffic for wakeup indications from the OLT.         
                  5. invalid(-1)         -Indicates that the query fails or no information is detected.  
                 "
            ::= { hwXponOntInfoEntry 18 }
            
       hwXponOntInfoNniPhysicalUpRate OBJECT-TYPE
            SYNTAX Integer32 (-1 | 0..10000000)
            MAX-ACCESS read-only
            STATUS current
            DESCRIPTION
                "This object indicates the upstream physical rate negotiated between the ONT and OLT.
                 Unit: Kbps
                 For example,
                 The upstream physical rate of the ONT is 1,000,000 Kbps in the EPON or asymmetric 10G EPON system.
                 The upstream physical rate of the ONT is 1,244,160 Kbps in the GPON system.
                 The upstream physical rate of the ONT is 2,488,320 Kbps in the XG-PON system.
                 The upstream physical rate of the ONT is 10,000,000 Kbps in the symmetric 10G EPON system.
                 The invalid value is -1.
                "
            ::= { hwXponOntInfoEntry 19 }   
            
       hwXponOntInfoNniPhysicalDownRate OBJECT-TYPE
            SYNTAX Integer32 (-1 | 0..10000000)
            MAX-ACCESS read-only
            STATUS current
            DESCRIPTION
                "This object indicates the downstream physical rate negotiated between the ONT and OLT.
                 Unit: Kbps
                 For example,
                 The downstream physical rate of the ONT is 1,000,000 Kbps in the EPON system.
                 The downstream physical rate of the ONT is 2,488,320 Kbps in the GPON system.
                 The downstream physical rate of the ONT is 9,953,280 Kbps in the XG-PON or XGS-PON system.
                 The downstream physical rate of the ONT is 10,000,000 Kbps in the 10G EPON system.
                 The invalid value is -1.
                "
            ::= { hwXponOntInfoEntry 20 }  
            
       hwGponDeviceOntActualNniType OBJECT-TYPE
            SYNTAX INTEGER {
                 rate2dot5G1dot25G (1),
                 rate10G2dot5G (2), 
                 rate10G10G (3),                
                 invalid (-1)
            }
            MAX-ACCESS read-only
            STATUS current
            DESCRIPTION
                 "Indicates whether the actual NNI type of the ont.
                  Options:
                  1. rate2dot5G1dot25G(1)  -Downstream rate 2.5Gbps, upstream rate 1.25Gbps.
                  2. rate10G2dot5G (2)     -Downstream rate 10Gbps, upstream rate 2.5Gbps.
                  3. rate10G10G (3)        -Downstream rate 10Gbps, upstream rate 10Gbps.                 
                  4. invalid (-1)          -Indicates the invalid value.
                 "
            ::= { hwXponOntInfoEntry 21 }  
            
        hwGponDeviceOntLastActualNniType OBJECT-TYPE
            SYNTAX INTEGER {
                 rate2dot5G1dot25G (1),
                 rate10G2dot5G (2), 
                 rate10G10G (3),                
                 invalid (-1)
            }
            MAX-ACCESS read-only
            STATUS current
            DESCRIPTION
                 "Indicates whether the last actual NNI type of the ont.
                  Options:
                  1. rate2dot5G1dot25G(1)  -Downstream rate 2.5Gbps, upstream rate 1.25Gbps.
                  2. rate10G2dot5G (2)     -Downstream rate 10Gbps, upstream rate 2.5Gbps.
                  3. rate10G10G (3)        -Downstream rate 10Gbps, upstream rate 10Gbps.                 
                  4. invalid (-1)          -Indicates the invalid value.
                 "
            ::= { hwXponOntInfoEntry 22 }  
            
         hwXponOntInfoHostName  OBJECT-TYPE
             SYNTAX       OCTET STRING (SIZE (0..256))
             MAX-ACCESS   read-only
             STATUS       current
             DESCRIPTION
                  "The host name of the ONT."
             ::= { hwXponOntInfoEntry 23 }
             
         hwXponOntFecStatus OBJECT-TYPE
             SYNTAX INTEGER {
                enable(1),
                disable(2),
                invalidValue(-1)
                }
             MAX-ACCESS read-only
             STATUS  current
             DESCRIPTION
                "This object indicates the ONT FEC switch status.
                 Options:
                 1. enable(1)                - Indicates that the ONT FEC switch is enabled.
                 2. disable(2)               - Indicates that the ONT FEC switch is disabled.
                 3. invalidValue(-1)         - Indicates that the query fails or no information is detected.
                "              
             ::= { hwXponOntInfoEntry 24 }
             
         hwGponXponOntVsID OBJECT-TYPE
            SYNTAX Integer32
            MAX-ACCESS read-only
            STATUS current
            DESCRIPTION
                "This object indicates the indexes of virtual system,range: 0-3.
                 The invalid value is -1.
                "
            ::= { hwXponOntInfoEntry 25 }  
            
         hwGponXponGlobalOntID   OBJECT-TYPE
            SYNTAX Integer32 (-1 | 0..255)
            MAX-ACCESS read-only
            STATUS       current
            DESCRIPTION
                "This object indicates the Global ONT ID in system, range: 0-255.
                 The invalid value is -1.
                "
            ::= { hwXponOntInfoEntry 26}
        
	hwGponDeviceOntActualWorkChannel OBJECT-TYPE
            SYNTAX Integer32
            MAX-ACCESS read-only
            STATUS current
            DESCRIPTION
                 "Indicates the actual work channel of the ont.
                 "
            ::= { hwXponOntInfoEntry 27 }
            
         hwXponOntInfoPowerType OBJECT-TYPE
             SYNTAX INTEGER {
                dc(1),
                ac(2),
                invalid(-1)
                }
             MAX-ACCESS read-only
             STATUS  current
             DESCRIPTION
                "This object indicates the power type of the ONT.
                 Options:
                 1. dc(1)                - Indicates that the ONT power type is DC.
                 2. ac(2)                - Indicates that the ONT power type is AC.
                 3. invalid (-1)          -Indicates that the query fails or no information is detected.
                "              
         ::= { hwXponOntInfoEntry 28 }
             
        hwXponOntInfoSystemUpDuration OBJECT-TYPE
            SYNTAX      Gauge32
            UNITS       "second"
            MAX-ACCESS  read-only
            STATUS      current
            DESCRIPTION
                "The system up duration of the ONT.
                 Unit: second
                "
            ::= { hwXponOntInfoEntry  29 }
            
	    
   --Table hwXponOntIpMaintainTable
        hwXponOntIpMaintainTable OBJECT-TYPE
            SYNTAX     SEQUENCE OF HwXponOntIpMaintainEntry
            MAX-ACCESS not-accessible
            STATUS     current
            DESCRIPTION
                    "The ONT IP maintain table. This table is used to config the ONT.
                     The indexes of this table are ifIndex hwXponOntIndex and hwXponOntIpMaintainIndex.
                    "
            ::= { hwXponCommonControlObjects 5 }

        hwXponOntIpMaintainEntry OBJECT-TYPE
            SYNTAX     HwXponOntIpMaintainEntry
            MAX-ACCESS not-accessible
            STATUS     current
            DESCRIPTION
                    "The ONT IP maintain table. This table is used to config the ONT.
                     The indexes of this entry are ifIndex hwXponOntIndex and hwXponOntIpMaintainIndex.
                    "
            INDEX       { ifIndex, hwXponOntIndex, hwXponOntIpMaintainIndex}
            ::= { hwXponOntIpMaintainTable 1 }

        HwXponOntIpMaintainEntry  ::=
            SEQUENCE
                {
                hwXponOntIpMaintainIndex                 Integer32,
                hwXponOntIpRemotePingIpAddress           IpAddress,            
                hwXponOntIpRemotePingSourceIpAddress     IpAddress,
                hwXponOntIpRemotePingSize                Integer32,
                hwXponOntIpRemotePingCount               Integer32,
                hwXponOntIpRemotePingStop                INTEGER
                }

        hwXponOntIpMaintainIndex OBJECT-TYPE
            SYNTAX       Integer32
            MAX-ACCESS   not-accessible
            STATUS       current
            DESCRIPTION
                "The IP index of the ont IP host."
            ::= { hwXponOntIpMaintainEntry  1 }

        hwXponOntIpRemotePingIpAddress OBJECT-TYPE
            SYNTAX      IpAddress
            MAX-ACCESS   read-write
            STATUS       current
            DESCRIPTION
                "The destination IP address of the ONT ping."
            ::= { hwXponOntIpMaintainEntry  2 }                       
			
        hwXponOntIpRemotePingSourceIpAddress OBJECT-TYPE
            SYNTAX      IpAddress
            MAX-ACCESS   read-write
            STATUS       current
            DESCRIPTION
                "The source IP address of the ONT ping."
            ::= { hwXponOntIpMaintainEntry  3 }	
            		
        hwXponOntIpRemotePingSize OBJECT-TYPE
            SYNTAX      Integer32 (1..65500)
            MAX-ACCESS   read-write
            STATUS       current
            DESCRIPTION
                "The packet length of the ONT ping.
                 The default value is 56."
            ::= { hwXponOntIpMaintainEntry  4 }	
            
        hwXponOntIpRemotePingCount OBJECT-TYPE
            SYNTAX      Integer32 (1..3600)
            MAX-ACCESS   read-write
            STATUS       current
            DESCRIPTION
                "The packet count of the ONT ping.
                 The default value is 4."
            ::= { hwXponOntIpMaintainEntry  5 }	
            
        hwXponOntIpRemotePingStop OBJECT-TYPE
            SYNTAX      INTEGER 
            {
                stop(1),
                invalid(-1)
            }
            MAX-ACCESS   read-write
            STATUS       current
            DESCRIPTION
                "This object is used to stop ONT ping test.
                 Options:
                 1. stop(1)         - Stop ONT remote-ping.
                 2. invalid(-1)     - Indicates that the query fails or no information is detected"
            ::= { hwXponOntIpMaintainEntry  6 }	            
                        
  --Table hwXponPortInfoTable
        hwXponPortInfoTable OBJECT-TYPE
            SYNTAX     SEQUENCE OF HwXponPortInfoEntry
            MAX-ACCESS not-accessible
            STATUS     current
            DESCRIPTION
                "XPON port Info table. This table is used to query the port information.
                 The index of this table is ifIndex.
                "
            ::= { hwXponCommonControlObjects 6 }

        hwXponPortInfoEntry OBJECT-TYPE
            SYNTAX     HwXponPortInfoEntry
            MAX-ACCESS not-accessible
            STATUS     current
            DESCRIPTION
                "XPON port Info table. This table is used to query the port information.
                 The index of this entry is ifIndex.
                "
            INDEX       { ifIndex}
            ::= { hwXponPortInfoTable 1 }

        HwXponPortInfoEntry  ::=
            SEQUENCE
                {
                hwXponPortSignalDetect               INTEGER,
                hwXponPortMacChipState               INTEGER,
                hwXponPortOtdrCapability             INTEGER,
                hwXponPortOpticalModulePhysicalForm  INTEGER,
                hwXponPortPhysicalUpRate             Integer32,
                hwXponPortPhysicalDownRate           Integer32,
                hwXponPortOnlineONTNumber            Integer32
                }

        hwXponPortSignalDetect OBJECT-TYPE
            SYNTAX      INTEGER
                {
                normal (1),
                fault (2),
                unsupport(255)
                }
            MAX-ACCESS  read-only
            STATUS      current
            DESCRIPTION
                "Query the signal detect info of the port.
                 Options:
                 1. normal(1)      - Optical signals are detected
                 2. fault(2)       - Optical signals are not detected
                 3. unsupport(255) - Signal detection is not supported
                "
            ::= { hwXponPortInfoEntry  1 }

        hwXponPortMacChipState OBJECT-TYPE
            SYNTAX      INTEGER
                {
                normal (1),
                fail (2)
                }
            MAX-ACCESS  read-only
            STATUS      current
            DESCRIPTION
                "Query the mac chipset state info of the port.
                 Options:
                 1. normal(1)      - The XPON MAC chipset is normal
                 2. fail(2)       - The XPON MAC chipset is fault
                "
            ::= { hwXponPortInfoEntry  2 }
                        
        hwXponPortOtdrCapability OBJECT-TYPE
            SYNTAX      INTEGER
                {
                support(1),
                notSupport(2),
                supportdownupwave(3),
                supportindependant(4),
                invalid(-1)
                }
            MAX-ACCESS read-only
            STATUS current
            DESCRIPTION
                "This object indicates whether the optical module supports the OTDR test.
                 Options:
                 1. support(1)             - Indicates that the optical module supports downwave eOTDR. 
                 2. notSupport(2)          - Indicates that the optical module does not support the EOTDR
                 3. supportdownupwave(3)   - Indicates that the optical module supports down and up wavelength eOTDR
                 4. supportindependant(4)  - Indicates that the optical module supports independanct wavelength eOTDR
                 5. invalid(-1)            - Indicates that the query fails or no information is detected.
                "
            ::= { hwXponPortInfoEntry  3 }    
        hwXponPortOpticalModulePhysicalForm OBJECT-TYPE
            SYNTAX      INTEGER
                {
                single(1),
                combointegrated(2),
                comboseperated(3),
                wdmpon(4),
                invalid(-1)
                }
            MAX-ACCESS read-only
            STATUS current
            DESCRIPTION
                "This object indicates the optical module physical form.
                 Options:
                 1. single(1)                   - GPON, EPON, XG-PON, XGS-PON, 10G EPON
                 2. combointegrated(2)          - Integrated Combo PON
                 3. comboseperated(3)           - Seperated Combo PON
                 4. wdmpon(4)                   - WDM PON
                 5. invalid(-1)                 - Indicates that the query fails or no information is detected.
                "
            ::= { hwXponPortInfoEntry  4 }  
              
        hwXponPortPhysicalUpRate OBJECT-TYPE
            SYNTAX Integer32 (-1 | 0..20000000)
            MAX-ACCESS read-only
            STATUS current
            DESCRIPTION
                "This object indicates the upstream physical rate negotiated between the port and OLT.
                 Unit: Kbps.
		 The invalid value is -1.
                "
            ::= { hwXponPortInfoEntry  5 }    
            
        hwXponPortPhysicalDownRate OBJECT-TYPE
            SYNTAX Integer32 (-1 | 0..20000000)
            MAX-ACCESS read-only
            STATUS current
            DESCRIPTION
                "This object indicates the downstream physical rate negotiated between the port and OLT.
                 Unit: Kbps.
		 The invalid value is -1.
                "
            ::= { hwXponPortInfoEntry  6 }    
            
        hwXponPortOnlineONTNumber OBJECT-TYPE
            SYNTAX Integer32
            MAX-ACCESS read-only
            STATUS current
            DESCRIPTION
                "This object indicates the the online ONT number of the port.
                "
            ::= { hwXponPortInfoEntry  7 }    
            
  --Table hwXponOntBatchInfoTable
        hwXponOntBatchInfoTable OBJECT-TYPE
            SYNTAX SEQUENCE OF HwXponOntBatchInfoEntry
            MAX-ACCESS not-accessible
            STATUS current
            DESCRIPTION
                "This table is used to query the ont run state, config state, admin state, load state, 
                 equipment ID, software version, system status, CRC value and offline reason. The length of query result can not exceed 7000 BYTEs.
                 This table can not support the operation of get next.
                 The index of this table is hwXponOntBatchQueryIndex.
                "
            ::= { hwXponCommonControlObjects 7 }

        hwXponOntBatchInfoEntry OBJECT-TYPE
            SYNTAX HwXponOntBatchInfoEntry
            MAX-ACCESS not-accessible
            STATUS current
            DESCRIPTION
                "This table is used to query the ont run state, config state, admin state, load state, 
                 equipment ID, software version, system status, CRC value and offline reason. The length of query result can not exceed 7000 BYTEs.
                 This table can not support the operation of get next.
                 The index of this entry is hwXponOntBatchQueryIndex.
                "
            INDEX { hwXponOntBatchQueryIndex }
            ::= { hwXponOntBatchInfoTable 1 }

        HwXponOntBatchInfoEntry ::=
            SEQUENCE 
            {
            hwXponOntBatchQueryIndex          Unsigned32,
            hwXponOntBatchQueryItemMask       Unsigned32,
            hwXponOntBatchQueryList           OCTET STRING,
            hwXponOntBatchQueryInfo           OCTET STRING
            }

        hwXponOntBatchQueryIndex OBJECT-TYPE
            SYNTAX Unsigned32 
            MAX-ACCESS not-accessible
            STATUS current
            DESCRIPTION
                "The object indicates the index of the table hwXponOntBatchInfoTable."
            ::= { hwXponOntBatchInfoEntry 1 }

        hwXponOntBatchQueryItemMask OBJECT-TYPE
            SYNTAX Unsigned32
            MAX-ACCESS read-write
            STATUS current
            DESCRIPTION
                "The items of ont status need query, include ont run state, config state, 
                 admin state, app load state, xml load state, equipment ID, software version, system status, 
                 CRC value, offline reason and hardware version.
                "
            ::= { hwXponOntBatchInfoEntry 2 }

        hwXponOntBatchQueryList OBJECT-TYPE
            SYNTAX OCTET STRING (SIZE (0..4096))
            MAX-ACCESS read-write
            STATUS current
            DESCRIPTION
                "The object indicates the ONT list, and each ONT takes 4 bytes, include 
                 frame(4bit), slot(6bit), port(6bit) and ontid(16bits) and the most number of ONT is 1024.
                "
            ::= { hwXponOntBatchInfoEntry 3 }

        hwXponOntBatchQueryInfo OBJECT-TYPE
            SYNTAX OCTET STRING
            MAX-ACCESS read-only
            STATUS current
            DESCRIPTION
                "The value of ont status:
                 run state(1byte)         : 1-online,2-offline,255-invalid
                 config state(1byte)      : 1-init,2-normal,3-fail,4-noresume,5-config,255-invalid
                 admin state(1byte)       : 1-activated,2-deactivated,255-invalid
                 app load state(1byte)    : 1-init,2-start,3-ftpfail,4-loadtoscu,5-loadtopon,6-loadtoponfail,
                                            7-loadtoont,8-userstop,9-ontoffline,10-ontackfail,11-ontresponsetimeout,
                                            12-errpon,13-ontreset,14-survival,15-channeloccupied,
                                            16-errversion,17-tasktimeout,18-ontfilecheckerr,19-ontfilevalidatefail,
                                            20-bufferinsufficient,21-ontnotsupport,22-ontstorageinfficient,
                                            23-ontimagefilerr,24-ontimagefileexisted,25-ontimagefileactivatefail,
                                            26-ontimagefilecommitfail,27-ontimagefilcrcerr,255-invalid
                 xml load state(1byte)    : 1-init,2-start,3-ftpfail,4-loadtoscu,5-loadtopon,6-loadtoponfail,7-loadtoont,
                                            8-crcreport,9-userstop,10-notsupport,11-ontoffline,12-ontackfail,
                                            13-ontresponsetimeout,14-cfgfail,15-errformat,16-errcontent,17-errtransfer,
                                            18-errontinner,19-errponboardinner,20-channeloccupied,255-invalid
                 equipment ID(20bytes)    : the equipment ID of the ONT
                 software version(16bytes): the software version of the ONT
                 system status(1byte)     : 1-normal,2-survival
                 CRC value(4bytes)        : the CRC value report from the ONT
                 offline reason(1byte)    : 1-LOS(Loss of signal),2-LOSi(Loss of signal for ONUi),
                                            3-LOFi(Loss of frame of ONUi),4-SFi(Signal fail of ONUi),
                                            5-LOAi(Loss of acknowledge with ONUi),6-LOAMi(Loss of PLOAM for ONUi),
                                            7-deactive ONT fails,8-deactive ONT success,9-reset ONT,10-re-register ONT,
                                            11-pop up fail,12-authentication fail,13-dying-gasp,15-LOKI(Loss of key synch with ONUi),
                                            18-ring-deactivated,30-shut down ONT optical module,31-reset ONT by ONT command,
                                            32-reset ONT by ONT reset button,33-reset ONT by ONT software,34-broadcast-attack-deactivated,
                                            35-operator check fail,37-ONT self check is rogueont(The enumeration value is based on the board),
                                            38-auto isolate reset,39-auto isolate deactivate,40-ONT is not in white list,
                                            255-invalid
                 hardware version(16bytes): the hardware version of the ONT
                "
            ::= { hwXponOntBatchInfoEntry 4 }
            
  --Table hwXponOntPppoeSimuTestInfoTable
        hwXponOntPppoeSimuTestInfoTable OBJECT-TYPE
            SYNTAX SEQUENCE OF HwXponOntPppoeSimuTestInfoEntry
            MAX-ACCESS not-accessible
            STATUS current
            DESCRIPTION
                "This table is used for the PPPoE testing.
                 The index of this table is a combination of ifIndex and hwXponOntIndex.
                "
            ::= { hwXponCommonControlObjects 8 }

        hwXponOntPppoeSimuTestInfoEntry OBJECT-TYPE
            SYNTAX HwXponOntPppoeSimuTestInfoEntry
            MAX-ACCESS not-accessible
            STATUS current
            DESCRIPTION
                "This table is used for the PPPoE testing.
                 The index of this entry is a combination of ifIndex and hwXponOntIndex.
                "
            INDEX { ifIndex, hwXponOntIndex }
            ::= { hwXponOntPppoeSimuTestInfoTable 1 }
                
        HwXponOntPppoeSimuTestInfoEntry ::=
            SEQUENCE { 
            hwXponOntPppoeSimuPortID                Integer32,
            hwXponOntPppoeSimuOuterCVlanID          Integer32,
            hwXponOntPppoeOuterSimuCVlanPri         Integer32,
            hwXponOntPppoeSimuPppoeUsername         OCTET STRING,
            hwXponOntPppoeSimuPppoePassword         OCTET STRING,
            hwXponOntPppoeSimuPppoeAuthProtocol     INTEGER,
            hwXponOntPppoeSimuSwitch                INTEGER,
            hwXponOntPppoeSimuMulticastGroupIPType  InetAddressType,
            hwXponOntPppoeSimuMulticastGroupIP      InetAddress,
            hwXponOntPppoeSimuMulticastVersion      INTEGER,
            hwXponOntPppoeSimuMulticastSourceIPType InetAddressType,
            hwXponOntPppoeSimuMulticastSourceIP     InetAddress,
            hwXponOntPppoeSimuMulticastDataRate     Integer32
            }

        hwXponOntPppoeSimuPortID OBJECT-TYPE
            SYNTAX Integer32
            MAX-ACCESS read-write
            STATUS current
            DESCRIPTION
                "The object indicates the type and ID of the ONT port.
                 port type(2 bytes) + port ID(2 bytes).
                 The OLT supports port type 0 for an ETH port to be compatible with the NMS of an earlier version."
            ::= { hwXponOntPppoeSimuTestInfoEntry 1 }

        hwXponOntPppoeSimuOuterCVlanID OBJECT-TYPE
            SYNTAX Integer32 (-1..4095)
            MAX-ACCESS read-write
            STATUS current
            DESCRIPTION
                "The object indicts the vlan ID, GPON : 0 - 4095; EPON : 1 - 4094; the value -1 indicts that the query fails."
            ::= { hwXponOntPppoeSimuTestInfoEntry 2 }
                
        hwXponOntPppoeOuterSimuCVlanPri OBJECT-TYPE
            SYNTAX Integer32 ( -1 | 0..7 )
            MAX-ACCESS read-write
            STATUS current
            DESCRIPTION
                "The priority of vlan."
            ::= { hwXponOntPppoeSimuTestInfoEntry 3 }

        hwXponOntPppoeSimuPppoeUsername OBJECT-TYPE
            SYNTAX OCTET STRING (SIZE (0..64))
            MAX-ACCESS read-write
            STATUS current
            DESCRIPTION
                "The user name of PPPoE test."
            ::= { hwXponOntPppoeSimuTestInfoEntry 4 }
                
        hwXponOntPppoeSimuPppoePassword OBJECT-TYPE
            SYNTAX OCTET STRING (SIZE (0..64))
            MAX-ACCESS read-write
            STATUS current
            DESCRIPTION
                "The password of PPPoE test."
            ::= { hwXponOntPppoeSimuTestInfoEntry 5 }
                
        hwXponOntPppoeSimuPppoeAuthProtocol OBJECT-TYPE
            SYNTAX INTEGER
                {
                chap(1),
                pap(2),
                invalid (-1)
                }
            MAX-ACCESS read-write
            STATUS current
            DESCRIPTION
                "The protocol type of PPPoE test.
                 Options: 
                 1. chap (1)                - The protocol type of PPPoE test is chap.
                 2. pap (2)                 - The protocol type of PPPoE test is pap.
                 3. invalid (-1)            - Indicates that the query fails.
                "
            ::= { hwXponOntPppoeSimuTestInfoEntry 6 }
                
        hwXponOntPppoeSimuSwitch OBJECT-TYPE
            SYNTAX INTEGER
                {
                 start(1),
                 stop(2),
                 invalid (-1)
                }
            MAX-ACCESS read-write
            STATUS current
            DESCRIPTION
                "The object is used to start or stop the PPPoE test.
                 Options: 
                 1. start (1)                - Start the PPPoE test.
                 2. stop (2)                 - Stop the PPPoE test.
                 3. invalid (-1)             - Indicates that the query fails.
                "
            ::= { hwXponOntPppoeSimuTestInfoEntry 7 }
        
        hwXponOntPppoeSimuMulticastGroupIPType OBJECT-TYPE
            SYNTAX  InetAddressType 
            MAX-ACCESS  read-write
            STATUS      current
            DESCRIPTION
                "Indicates the address type.                    
                Options:   
                1. unknown(0) - An unknown address type.  This value MUST
                                be used if the value of the corresponding
                                InetAddress object is a zero-length string.
                                It may also be used to indicate an IP address
                                that is not in one of the formats defined
                                below.                          
                2. IPv4(1)    - An IPv4 address as defined by the
                                InetAddressIPv4 textual convention.
                "
            ::= { hwXponOntPppoeSimuTestInfoEntry 8 }
		        
        hwXponOntPppoeSimuMulticastGroupIP OBJECT-TYPE
            SYNTAX      InetAddress
            MAX-ACCESS  read-write
            STATUS      current
            DESCRIPTION
                "Indicates the group IP address of the program.                       
                 The format of this index is consistent with that of the address type.
                 The default value is 0.0.0.0.
                "
            ::= { hwXponOntPppoeSimuTestInfoEntry 9 }
		        
        hwXponOntPppoeSimuMulticastVersion OBJECT-TYPE
            SYNTAX INTEGER
                {
                 igmpV2(1),
                 igmpV3(2),
                 invalid(-1)
                }
            MAX-ACCESS read-write
            STATUS current
            DESCRIPTION
                "Indicates the multicast version in the ONT Multicast simulation instance.
                 Options:                                                                 
                 1. igmpV2(1)     - Indicates the multicast version is IGMPV2.                 
                 2. igmpV3(2)     - Indicates the multicast version is IGMPV3.  
                 3. invalid(-1)   - Indicates that the query fails.               
                 Default: igmpV2(1).                                                      
                "
            ::= { hwXponOntPppoeSimuTestInfoEntry 10 }
		        
        hwXponOntPppoeSimuMulticastSourceIPType OBJECT-TYPE
            SYNTAX  InetAddressType 
            MAX-ACCESS  read-write
            STATUS      current
            DESCRIPTION
                "Indicates the address type.                    
                Options:                                       
                1. unknown(0) - An unknown address type.  This value MUST
                                be used if the value of the corresponding
                                InetAddress object is a zero-length string.
                                It may also be used to indicate an IP address
                                that is not in one of the formats defined
                                below.                          
                2. IPv4(1)    - An IPv4 address as defined by the
                                InetAddressIPv4 textual convention.
                "
            ::= { hwXponOntPppoeSimuTestInfoEntry 11 }
		        
        hwXponOntPppoeSimuMulticastSourceIP OBJECT-TYPE
            SYNTAX      InetAddress
            MAX-ACCESS  read-write
            STATUS      current
            DESCRIPTION
                "Indicates the source IP address of the program.                       
                 The format of this index is consistent with that of the address type.
                 The default value is 0.0.0.0.
                "
            ::= { hwXponOntPppoeSimuTestInfoEntry 12 }
		        
        hwXponOntPppoeSimuMulticastDataRate OBJECT-TYPE
            SYNTAX Integer32
            MAX-ACCESS read-only
            STATUS current
            DESCRIPTION
                "Indicates the multicast date rate of the current simulation instance,
                 it is valid when the simulation result is success.  
                Unit: kbps.  
                The invalid value is -1.                                                                                                           
                "
            ::= { hwXponOntPppoeSimuTestInfoEntry 13 }
                
   --Table hwXponOntControlTable
        hwXponOntControlTable OBJECT-TYPE
            SYNTAX SEQUENCE OF HwXponOntControlEntry
            MAX-ACCESS not-accessible
            STATUS     current
            DESCRIPTION
                "The hwXponOntControlTable is used to config the ONT.
                 The indexes of this table are ifIndex and hwXponOntIndex.
                "
            ::= { hwXponCommonControlObjects 9 }

        hwXponOntControlEntry OBJECT-TYPE
            SYNTAX HwXponOntControlEntry
            MAX-ACCESS not-accessible
            STATUS current
            DESCRIPTION
                "The hwXponOntControlTable is used to config the ONT.
                 The indexes of this entry are ifIndex and hwXponOntIndex.
                "
            INDEX       { ifIndex, hwXponOntIndex }
            ::= { hwXponOntControlTable 1 }

        HwXponOntControlEntry ::=
            SEQUENCE
                {
                hwXponOntConfigFactoryConfiguration    INTEGER,
                hwXponOntControlGracefulReset          INTEGER,
                hwXponOntControlGraceTime              Integer32,
                hwXponOntDeleteVasService              INTEGER,
                hwXponOntControlOperatorCheckReset     INTEGER,
                hwXponOntControlRogueIsolateSwitch     INTEGER,
                hwXponOntFec                           INTEGER,
                hwXponOntControlWanAccessHttp          INTEGER,
                hwXponOntControlLanAccessTelnet        INTEGER,
                hwXponOntControlRollbackSoftware       INTEGER
                }
                
        hwXponOntConfigFactoryConfiguration OBJECT-TYPE
            SYNTAX   INTEGER{
                    restore (1),
                    completelyrestore (2),
                    invalid (-1)
                }
            MAX-ACCESS read-write
            STATUS     current
            DESCRIPTION
                "This parameter is used to restore the ONT to factory configuration.
                 Options:
                 1. restore (1)                 - Restore
                 2. completelyrestore(2) - Completely restore
                 3. invalid (-1)                 - Indicates that the query fails or no information is detected
                "
            ::= { hwXponOntControlEntry  1 }

        hwXponOntControlGracefulReset OBJECT-TYPE
            SYNTAX   INTEGER{
                    gracefullyreset (1),
                    invalid (-1)
                }
            MAX-ACCESS read-write
            STATUS     current
            DESCRIPTION
                "This parameter is used to reset the ONT gracefully. 
                 Options:
                 1. gracefullyreset (1) - Indicates that the ONT resets gracefully
                 2. invalid (-1)        - Indicates the invalid value
                "
            ::= { hwXponOntControlEntry  2 }

        hwXponOntControlGraceTime OBJECT-TYPE
            SYNTAX   Integer32 (-1 | 1..65535)
            MAX-ACCESS read-write
            STATUS     current
            DESCRIPTION
                "This parameter is used to specify the maximum time to wait for the ONT to reset gracefully. 
                 The default maximum time for wait is 14400 seconds.
                 The invalid value is -1.
                "
            ::= { hwXponOntControlEntry  3 }
                
         hwXponOntDeleteVasService OBJECT-TYPE
             SYNTAX INTEGER {
                delete(1),
                invalid(-1)
                }
             MAX-ACCESS read-write
             STATUS  current
             DESCRIPTION
                "Delete the vas service of the ONT.
                 Options:
                 1. delete(1)                    - Delete the vas service of the ONT
                 2. invalid(-1)                  - invalid value
                 "
             ::= { hwXponOntControlEntry 4 }
         hwXponOntControlOperatorCheckReset OBJECT-TYPE
             SYNTAX INTEGER {
                reset(1),
                invalid(-1)
                }
             MAX-ACCESS read-write
             STATUS  current
             DESCRIPTION
                "Reset operator check code of the ONT.
                 Options:
                 1. reset(1)                     - Reset operator check code of the ONT
                 2. invalid(-1)                  - Invalid value
                 "
             ::= { hwXponOntControlEntry 5 }
	     
         hwXponOntControlRogueIsolateSwitch OBJECT-TYPE
             SYNTAX INTEGER {
                isolate(1),
                undoIsolate(2)
                }
             MAX-ACCESS read-write
             STATUS  current
             DESCRIPTION
                "This object indicates the switch of isolating or de-isolating a rogue ONT.
                 Options:
                 1. isolate(1)                - Isolate the rogue ONT
                 2. undoIsolate(2)        - Undo isolate the rogue ONT
                 The default value is undoIsolate(2).
                "              
             ::= { hwXponOntControlEntry 6 }	  
             
             
         hwXponOntFec OBJECT-TYPE
             SYNTAX INTEGER {
                enable(1),
                disable(2),
                useProfileConfig(3),
                invalidValue(-1)
                }
             MAX-ACCESS read-write
             STATUS  current
             DESCRIPTION
                "This object is used to configure the ONT upstream FEC switch.
                 Options:
                 1. enable(1)                - Indicates that the ONT FEC switch is enabled.
                 2. disable(2)               - Indicates that the ONT FEC switch is disabled.
                 3. useProfileConfig(3)      - Indicates that the ONT FEC switch is using line profile configuration.
                 4. invalidValue(-1)         - Indicates that the query fails or no information is detected.
                 The default value is enable(1) for XG-PON ONT and EPON 10g/2g type ONT.
                 The default value is useProfileConfig(3) for others in profile-mode.
                 The default value is disable(2) for others in distributing-mode.
                "              
             ::= { hwXponOntControlEntry 7 }
                
         hwXponOntControlWanAccessHttp OBJECT-TYPE
             SYNTAX INTEGER {
                enable(1),
                disable(2),
                invalid(-1)
                }
             MAX-ACCESS read-write
             STATUS  current
             DESCRIPTION
                "This object is used to configure the ONT WAN Access of Web.
                 Options:
                 1. enable(1)                 - Indicates that the ONT WAN Access of Web is enabled.
                 2. disable(2)                - Indicates that the ONT WAN Access of Web is disabled.
                 3. invalid(-1)               - Indicates that the query fails or no information is detected.  
                 The default value is disable(2).
                "              
             ::= { hwXponOntControlEntry 8 }     
                    
         hwXponOntControlLanAccessTelnet OBJECT-TYPE
             SYNTAX INTEGER {
                enable(1),
                disable(2),
                invalid(-1)
                }
             MAX-ACCESS read-write
             STATUS  current
             DESCRIPTION
                "This object is used to configure the ONT LAN Access of Telnet.
                 Options:
                 1. enable(1)                 - Indicates that the ONT LAN Access of Telnet is enabled.
                 2. disable(2)                - Indicates that the ONT LAN Access of Telnet is disabled.
                 3. invalid(-1)               - Indicates that the query fails or no information is detected.  
                 The default value is disable(2).
                "              
             ::= { hwXponOntControlEntry 9 }
	     
	     hwXponOntControlRollbackSoftware OBJECT-TYPE
             SYNTAX INTEGER {
                rollbacksoftware(1),             
                invalid(-1)
                }
             MAX-ACCESS read-write
             STATUS  current
             DESCRIPTION
                "This parameter is used to rollback the software of the ONT.
                 Options:
                 1. rollbacksoftware(1)     - Indicates that the ONT software version rolls back.
                 2. invalid(-1)             - Indicates the invalid value.             
                "              
             ::= { hwXponOntControlEntry 10 }
                
   --Table hwGponOntPortMulticastVlanTranslationTable
        hwGponOntPortMulticastVlanTranslationTable OBJECT-TYPE
            SYNTAX SEQUENCE OF HwGponOntPortMulticastVlanTranslationEntry
            MAX-ACCESS not-accessible
            STATUS     current
            DESCRIPTION
                "The hwGponOntPortMulticastVlanTranslationTable is used to config the multicast vlan translation of GPON ONT port.
                 The indexes of this table are ifindex, hwGponDeviceOntObjectIndex, hwGponOntifType, hwGponOntifPort, hwGponOntPortMulticastVlanIndex.
                "
            ::= { hwXponCommonControlObjects 10 }  
            
        hwGponOntPortMulticastVlanTranslationEntry OBJECT-TYPE
            SYNTAX HwGponOntPortMulticastVlanTranslationEntry
            MAX-ACCESS not-accessible
            STATUS     current
            DESCRIPTION
                "The hwGponOntPortMulticastVlanTranslationTable is used to config the multicast vlan translation of GPON ONT port.
                 The indexes of this entry are ifindex, hwGponDeviceOntObjectIndex, hwGponOntifType, hwGponOntifPort, hwGponOntPortMulticastVlanIndex.
                "
            INDEX       
                { 
                ifIndex, 
                hwGponDeviceOntObjIndex,
                hwGponOntifType,
                hwGponOntifPort,
                hwGponOntPortMulticastVlanIndex
                }
            ::= { hwGponOntPortMulticastVlanTranslationTable 1 }

        HwGponOntPortMulticastVlanTranslationEntry ::=
            SEQUENCE
                {
                hwGponOntifType                               INTEGER,
                hwGponOntifPort                               Integer32,
                hwGponOntPortMulticastVlanIndex               Integer32,
                hwGponOntPortMulticastVlanCfgTranslatedVlan   Integer32,
                hwGponOntPortMulticastStripSwitch             INTEGER,
                hwGponOntPortMulticastVlanCfgRowStatus        RowStatus
                }

        hwGponOntifType OBJECT-TYPE
            SYNTAX INTEGER {
                           vdsl(37),
                           wifi(40),
                           eth(47),
                           ippath(61)
                           }
            MAX-ACCESS    not-accessible
            STATUS      current
            DESCRIPTION
                "The ONT port type.
                 Options:
                 1. vdsl(37)   -The ONT port type is vdsl
                 2. wifi(40)   -The ONT port type is wifi
                 3. eth(47)    -The ONT port type is eth
                 4. ippath(61) -The ONT port type is ippath
                "
            ::= { hwGponOntPortMulticastVlanTranslationEntry 1 }

        hwGponOntifPort OBJECT-TYPE
            SYNTAX     Integer32
            MAX-ACCESS    not-accessible
            STATUS      current
            DESCRIPTION
                "The ONT port ID."
            ::= { hwGponOntPortMulticastVlanTranslationEntry 2 }

        hwGponOntPortMulticastVlanIndex OBJECT-TYPE
            SYNTAX        Integer32
            MAX-ACCESS    not-accessible
            STATUS        current
            DESCRIPTION
               "The multicast vlan index of ONT port.
                Ranging from 1 to 4095.
               "
            ::= { hwGponOntPortMulticastVlanTranslationEntry  3 }

        hwGponOntPortMulticastVlanCfgTranslatedVlan OBJECT-TYPE
            SYNTAX        Integer32 (-1 | 1..4095)
            MAX-ACCESS    read-write
            STATUS        current
            DESCRIPTION
               "The translation vlan of ONT port, when the GPON ONT port multicast vlan transmit mode is translation."
            ::= { hwGponOntPortMulticastVlanTranslationEntry  4 }

        hwGponOntPortMulticastStripSwitch OBJECT-TYPE
            SYNTAX INTEGER {
                untag(1),
                tag(2),
                translation(3),  
                invalid(-1)
                }
             MAX-ACCESS read-write
             STATUS current
             DESCRIPTION
                 "This object indicates the multicast vlan transmit mode of GPON ONT port.
                  Options:
                  1. untag(1)          - Indicates that the GPON ONT port multicast vlan transmit mode is untag          
                  2. tag(2)            - Indicates that the GPON ONT port multicast vlan transmit mode is tag     
                  3. translation(3)    - Indicates that the GPON ONT port multicast vlan transmit mode is translation
                  4. invalid(-1)       - Indicates that the query fails or no information is detected
                 "
            ::= { hwGponOntPortMulticastVlanTranslationEntry  5 }

        hwGponOntPortMulticastVlanCfgRowStatus OBJECT-TYPE
            SYNTAX        RowStatus
            MAX-ACCESS    read-create
            STATUS        current
            DESCRIPTION
                "Row status. This object is used to differentiate the
                 creation, modification and deletion operations for an object.
                 Options:
                 1. createAndGo(4) -create a new instance of a conceptual row 
                 2. destroy(6)     -delete the instances associated with an existing conceptual row
                "
            ::= { hwGponOntPortMulticastVlanTranslationEntry 6 } 

   --Table hwXponOntVoipConfigTable
        hwXponOntVoipConfigTable OBJECT-TYPE
            SYNTAX SEQUENCE OF HwXponOntVoipConfigEntry
            MAX-ACCESS not-accessible
            STATUS     current
            DESCRIPTION
                "The hwXponOntVoipConfigTable is used to config the FTP Server and config the configuration files name.
                 The indexes of this table are ifindex and hwXponOntIndex.
                "
            ::= { hwXponCommonControlObjects 12 }  
            
        hwXponOntVoipConfigEntry OBJECT-TYPE
            SYNTAX HwXponOntVoipConfigEntry
            MAX-ACCESS not-accessible
            STATUS     current
            DESCRIPTION
                "The hwXponOntVoipConfigTable is used to config the FTP Server and config the configuration files name.
                 The indexes of this entry are ifindex and hwXponOntIndex.
                "
            INDEX       
                { 
                ifIndex, 
                hwXponOntIndex
                }
            ::= { hwXponOntVoipConfigTable 1 }

        HwXponOntVoipConfigEntry ::=
            SEQUENCE
                { 
                hwXponOntVoipUsedFtpServerProfile             OCTET STRING,
                hwXponOntVoipFtpFileName                      OCTET STRING,
                hwXponOntVoipFtpFileTrigger                   Integer32,
                hwXponOntVoipConfigMethod                     INTEGER
                }
                     
        hwXponOntVoipUsedFtpServerProfile OBJECT-TYPE
            SYNTAX OCTET STRING (SIZE (0..15))
            MAX-ACCESS read-write
            STATUS current
            DESCRIPTION
                "The server of used."
            ::= { hwXponOntVoipConfigEntry 1 }

        hwXponOntVoipFtpFileName OBJECT-TYPE
            SYNTAX OCTET STRING (SIZE (0..63))
            MAX-ACCESS read-write
            STATUS current
            DESCRIPTION
                "The configuration file name."
            ::= { hwXponOntVoipConfigEntry 2 }

        hwXponOntVoipFtpFileTrigger OBJECT-TYPE
            SYNTAX        Integer32
            MAX-ACCESS    read-write
            STATUS        current
            DESCRIPTION
               "This leaf set 1 when config the FTP Server and config the configuration file name.
               "
            ::= { hwXponOntVoipConfigEntry  3 }
            
        hwXponOntVoipConfigMethod OBJECT-TYPE
             SYNTAX INTEGER {
                default(1),
                omci(2),
                ftp(3),
                tr069(4)
                }
             MAX-ACCESS read-write
             STATUS  current
             DESCRIPTION
                "Config tht ONT's voip service.
                 Options:
                 1. default(1)        - do not configure, ont default           
                 2. omci(2)           - OMCI
                 3. ftp(3)            - configuration file retrieval
                 4. tr069(4)          - tr069
                 The default value is default(1).                
                 "
             ::= { hwXponOntVoipConfigEntry 4 }
  
  --Table hwXponOntConfigTable
        hwXponOntConfigTable OBJECT-TYPE
            SYNTAX SEQUENCE OF HwXponOntConfigEntry
            MAX-ACCESS not-accessible
            STATUS     current
            DESCRIPTION
                "The hwXponOntConfigTable is used to config the ONT.
                 The indexes of this table are ifIndex and hwXponOntIndex.
                "
            ::= { hwXponCommonControlObjects 13 }

        hwXponOntConfigEntry OBJECT-TYPE
            SYNTAX HwXponOntConfigEntry
            MAX-ACCESS not-accessible
            STATUS current
            DESCRIPTION
                "The hwXponOntConfigTable is used to config the ONT.
                 The indexes of this entry are ifIndex and hwXponOntIndex.
                "
            INDEX       { ifIndex, hwXponOntIndex }
            ::= { hwXponOntConfigTable 1 }

        HwXponOntConfigEntry ::=
            SEQUENCE
                {
                hwXponOntUsedAlarmPolicyName                  OCTET STRING,
                hwXponOntPowerSheddingProfName                OCTET STRING,
                hwXponOntUsedTr069ServerProfName              OCTET STRING,
                hwXponOntUsedLldpProfName                     OCTET STRING,
                hwXponOntUsedDot1xProfName                    OCTET STRING,
	        hwXponOntUsedPowerReductionProfName           OCTET STRING,
	        hwXponOntUsedPolicyRouteProfileName           OCTET STRING,
	        hwXponOntUsedInternetWanIpIndex               Integer32,
	        hwXponOntUsedMulticastWanIpIndex              Integer32,
	        hwXponOntUsedMulticastProfileName             OCTET STRING
                }
                
        hwXponOntUsedAlarmPolicyName OBJECT-TYPE
            SYNTAX      OCTET STRING (SIZE (0..32))
            MAX-ACCESS  read-write
            STATUS      current
            DESCRIPTION
                "The name of alarm policy profile which used by the ONT."
            ::= { hwXponOntConfigEntry 1 }
            
        hwXponOntPowerSheddingProfName OBJECT-TYPE
            SYNTAX      OCTET STRING (SIZE (0..32))
            MAX-ACCESS  read-write
            STATUS      current
            DESCRIPTION
                "The name of the power shedding profile that is bound to the ONT."
            ::= { hwXponOntConfigEntry 2 }

        hwXponOntUsedTr069ServerProfName OBJECT-TYPE
            SYNTAX      OCTET STRING (SIZE (0..32))
            MAX-ACCESS  read-write
            STATUS      current
            DESCRIPTION
                "This object indicates the name of the tr069 service profile that is bound to the ONT."
            ::= { hwXponOntConfigEntry 3}
            
        hwXponOntUsedLldpProfName OBJECT-TYPE
            SYNTAX      OCTET STRING (SIZE (0..32))
            MAX-ACCESS  read-write
            STATUS      current
            DESCRIPTION
                "This object indicates the name of the lldp profile that is bound to the ONT."
            ::= { hwXponOntConfigEntry 4}
            
        hwXponOntUsedDot1xProfName OBJECT-TYPE
            SYNTAX      OCTET STRING (SIZE (0..32))
            MAX-ACCESS  read-write
            STATUS      current
            DESCRIPTION
                "This object indicates the name of the 802.1X profile that is bound to the ONT."
            ::= { hwXponOntConfigEntry 5}    
	    
        hwXponOntUsedPowerReductionProfName OBJECT-TYPE
            SYNTAX      OCTET STRING (SIZE (0..32))
            MAX-ACCESS  read-write
            STATUS      current
            DESCRIPTION
                "This object indicates the name of the power reduction profile that is bound to the ONT."
            ::= { hwXponOntConfigEntry 6}
            
        hwXponOntUsedPolicyRouteProfileName OBJECT-TYPE
            SYNTAX      OCTET STRING (SIZE (0..32))
            MAX-ACCESS  read-write
            STATUS      current
            DESCRIPTION
                "This object indicates the name of the policy route profile that is bound to the ONT."
            ::= { hwXponOntConfigEntry 7}
            
        hwXponOntUsedInternetWanIpIndex OBJECT-TYPE
            SYNTAX      Integer32
            MAX-ACCESS  read-write
            STATUS      current
            DESCRIPTION
                "This object indicates the ip index of ont internet wan.
                 value list:0~3, -1 means delete"
            ::= { hwXponOntConfigEntry 8}
            
        hwXponOntUsedMulticastWanIpIndex OBJECT-TYPE
            SYNTAX      Integer32
            MAX-ACCESS  read-write
            STATUS      current
            DESCRIPTION
                "This object indicates the ip index of ont Iptv wan.
                 value list:0~3, -1 means delete"
            ::= { hwXponOntConfigEntry 9} 
            
        hwXponOntUsedMulticastProfileName OBJECT-TYPE
            SYNTAX      OCTET STRING (SIZE (0..32))
            MAX-ACCESS  read-write
            STATUS      current
            DESCRIPTION
                "This object indicates the name of the multicast profile that is bound to the ONT."
            ::= { hwXponOntConfigEntry 10}                           

  --Table hwXponOntWanInfoTable
        hwXponOntWanInfoTable OBJECT-TYPE
            SYNTAX SEQUENCE OF HwXponOntWanInfoEntry
            MAX-ACCESS not-accessible
            STATUS     current
            DESCRIPTION
                "The hwXponOntWanInfoTable is used to query the information about WAN ports.
                 The indexes of this table are ifIndex and hwXponOntIndex.
                "
            ::= { hwXponCommonControlObjects 14 }

        hwXponOntWanInfoEntry OBJECT-TYPE
            SYNTAX HwXponOntWanInfoEntry
            MAX-ACCESS not-accessible
            STATUS current
            DESCRIPTION
                "The hwXponOntWanInfoTable is used to query the information about WAN ports.
                 The indexes of this entry are ifIndex and hwXponOntIndex.
                "
            INDEX       { ifIndex, hwXponOntIndex }
            ::= { hwXponOntWanInfoTable 1 }

        HwXponOntWanInfoEntry ::=
            SEQUENCE
                {
                hwXponOntWanInfoDetail    OCTET STRING,
                hwXponOntWanExtendInfoDetail   OCTET STRING
                }
                
        hwXponOntWanInfoDetail OBJECT-TYPE
            SYNTAX      OCTET STRING (SIZE (0..800))
            MAX-ACCESS  read-only
            STATUS      current
            DESCRIPTION
                "This object indicates the information about WAN ports."
            ::= { hwXponOntWanInfoEntry 1 }     
                    
        hwXponOntWanExtendInfoDetail OBJECT-TYPE
            SYNTAX      OCTET STRING (SIZE (0..1500))
            MAX-ACCESS  read-only
            STATUS      current
            DESCRIPTION
                "This object indicates the information about WAN ports including IPv6 WAN.
                 This object consists of length, version, the number of WAN ports (n)
                 and n * WAN ports information. 
                 Principles to extend this object:
                 1. to add parameters, version should be upgraded, and the new parameters should 
                 be appended to the tail of each WAN information.
                 2. if the the version of OLT device or NMS is old, the OLT device or NMS
                 only have to parse the content they can recognize.   
                 The format of this object is as follows:
                 --------------------------------------------------------------------------------------
                 |field          |field length |                  field description                   |
                 --------------------------------------------------------------------------------------
                 |Total_Length   |2            |Length from Version to WAN_port_N_info.               |  
                 --------------------------------------------------------------------------------------
                 |Version        |1            |Version indicates the format of WAN port info, which  |                                               
                 |               |             |will be described detailly in SOI document.           |    
                 --------------------------------------------------------------------------------------
                 |WAN_port_num   |1            |Total number of WAN ports.                            | 
                 --------------------------------------------------------------------------------------
                 |WAN_port_1_info|x            | x = (Total_Length - 2)/WAN_port_num                  |  
                 --------------------------------------------------------------------------------------  
                 |WAN_port_2_info|x            |                                                      |  
                 --------------------------------------------------------------------------------------
                 |......         |x            |                                                      |  
                 --------------------------------------------------------------------------------------
                 |WAN_port_N_info|x            |                                                      |  
                 --------------------------------------------------------------------------------------
                "
            ::= { hwXponOntWanInfoEntry 2 } 
                        
  --Table hwGponPortControlTable
        hwGponPortControlTable OBJECT-TYPE
            SYNTAX SEQUENCE OF HwGponPortControlEntry
            MAX-ACCESS not-accessible
            STATUS     current
            DESCRIPTION
                "The hwGponPortControlTable is used to config the information about ports.
                 The index of this table is ifIndex.
                "
            ::= { hwXponCommonControlObjects 15 }

        hwGponPortControlEntry OBJECT-TYPE
            SYNTAX HwGponPortControlEntry
            MAX-ACCESS not-accessible
            STATUS current
            DESCRIPTION
                "The hwGponPortControlTable is used to config the information about ports.
                 The index of this entry is ifIndex.
                "
            INDEX       { ifIndex }
            ::= { hwGponPortControlTable 1 }

        HwGponPortControlEntry ::=
            SEQUENCE
                {
                hwGponPortControlDbaAssignMode      INTEGER,
                hwGponPortControlPonIdSwitch        INTEGER,
                hwGponPortControlPonIdInputMode     INTEGER,
                hwGponPortControlPonIdIdentifier    OCTET STRING,
                hwGponPortMulticastEncryptMode      INTEGER,
                hwGponPortControlDbaSurplusAssign   INTEGER,
                hwGponPortControlBEAssignMode       INTEGER,
                hwGponPortControlTrafficAlarmProfileName   OCTET STRING,
                hwGponPortControlMaxGuaranteedBandwidth   Integer32,
                hwGponPortControlWaveLengthID         INTEGER,
                hwGponPortControlComboMode          INTEGER,
                hwGponPortControlFlexMode 			INTEGER,	
                hwGponPortControlDbaLowlatency  	INTEGER,
                hwGponPortControlLightTestTimeduration  Integer32,
                hwGponPortControlLightTestTestStatus  	INTEGER,
                hwGponPortControlLightTestFinshStatus  	INTEGER	
                }
                
        hwGponPortControlDbaAssignMode OBJECT-TYPE
          SYNTAX     INTEGER {
               maxbandwidthusage(1),
               minloopdelay(2),
               manual(3),
               default(4),
               invalid(-1)
          }
          MAX-ACCESS   read-write
          STATUS      current
          DESCRIPTION
            "This object is used to configure the DBA bandwidth assignment mode.
             Options:
             1. maxbandwidthusage(1) - max bandwidth usage mode 
             2. minloopdelay(2)      - min loop delay mode
             3. manual(3)            - manual mode, this value is read-only             
             4. default(4)           - default mode, the same with global DBA assignment mode
             5. invalid(-1)          - Indicates that the query fails or no information is detected
            "
          ::= { hwGponPortControlEntry 1 }

        hwGponPortControlPonIdSwitch OBJECT-TYPE
          SYNTAX     INTEGER {
               enable(1),
               disable(2),
               invalid(-1)
          }
          MAX-ACCESS   read-write
          STATUS      current
          DESCRIPTION
            "This object is used to configure the PON-ID switch.
             Options:
             1. enable(1)       - Indicates that the PON-ID switch is enabled
             2. disable(2)      - Indicates that the PON-ID switch is disabled
             3. invalid(-1)     - Indicates that the query fails or no information is detected
            "
          ::= { hwGponPortControlEntry 2 }

        hwGponPortControlPonIdInputMode OBJECT-TYPE
          SYNTAX     INTEGER {
               text(1),
               hex(2),
               invalid(-1)
          }
          MAX-ACCESS   read-write
          STATUS      current
          DESCRIPTION
            "This object is used to configure the input mode of PON-ID identifier.
             Options:
             1. text(1)         - Indicates that the input mode of PON-ID identifier is text
             2. hex(2)          - Indicates that the input mode of PON-ID identifier is hex
             3. invalid(-1)     - Indicates that the query fails or no information is detected
            "
          ::= { hwGponPortControlEntry 3 }
          
        hwGponPortControlPonIdIdentifier OBJECT-TYPE
          SYNTAX      OCTET STRING (SIZE (1..7))
          MAX-ACCESS  read-write
          STATUS      current
          DESCRIPTION
            "This object is used to configure the PON-ID identifier.
             The GPON port supports a maximum of 7 characters to be input for configuring the PON-ID identifier.
             The XG PON port supports a maximum of 4 characters to be input for configuring the PON-ID identifier.
            "
          ::= { hwGponPortControlEntry 4 }
          
       hwGponPortMulticastEncryptMode OBJECT-TYPE
          SYNTAX     INTEGER {
               disable(1),
               enable(2),
               adapt(3),
               invalid(-1)
          }
          MAX-ACCESS   read-write
          STATUS      current
          DESCRIPTION
            "This object is used to configure the Multicast GEM Port encypt mode.
             Options:
             1. disable(1)       - Indicates that the Multicast GEM Port encypt mode is disable
             2. enable(2)        - Indicates that the Multicast GEM Port encypt mode is enable
             3. adapt(3)         - Indicates that the Multicast GEM Port encypt mode is adapt
             4. invalid(-1)      - Indicates that the query fails or no information is detected
             Default:disable(1).
            "
          ::= { hwGponPortControlEntry 5 }

       hwGponPortControlDbaSurplusAssign OBJECT-TYPE
          SYNTAX     INTEGER {
               enable(1),
               disable(2),	       
               invalid(-1)
          }
          MAX-ACCESS   read-write
          STATUS      current
          DESCRIPTION
            "This object is used to configure the surplus bandwidth assignment swith.
             Options:
             1. enable(1)            - Indicates that the surplus bandwidth assignment is enable
             2. disable(2)           - Indicates that the  surplus bandwidth assignment is disable
             3. invalid(-1)          - Indicates that the query fails or no information is detected
             Default:disable(2).
            "
          ::= { hwGponPortControlEntry 6 }

       hwGponPortControlBEAssignMode OBJECT-TYPE
          SYNTAX     INTEGER {
               rateProportion(1),
               priorityWeight(2),
               invalid(-1)
          }
          MAX-ACCESS   read-write
          STATUS      current
          DESCRIPTION
            "This object is used to configure the best effort assign mode.
             Options:
             1. rateProportion(1)    - Indicates that the best effort assign mode is rate proportion
             2. priorityWeight(2)    - Indicates that the best effort assign mode is priority and weight
             3. invalid(-1)           - Indicates that the query fails or the mode is average
            "
          ::= { hwGponPortControlEntry 7 }
          
        hwGponPortControlTrafficAlarmProfileName OBJECT-TYPE
             SYNTAX OCTET STRING (SIZE(0..32))
             MAX-ACCESS read-write
             STATUS current
             DESCRIPTION
                 "This object indicates the traffic alarm profile name.
                  This object is used to configure the traffic alarm profile.
                  An empty string is used to unbind the traffic alarm profile."
           ::= { hwGponPortControlEntry 8 }

        hwGponPortControlMaxGuaranteedBandwidth OBJECT-TYPE
            SYNTAX  Integer32
            UNITS   "kbps"
            MAX-ACCESS read-write
            STATUS current
            DESCRIPTION
                "This object indicates the maximum guaranteed bandwidth, The value must be greater than or equal to 128 but cannot be larger than the maximum physical bandwidth  of a PON port.
                 Unit: kbps
                 If the value of hwGponPortControlMaxGuaranteedBandwidth is set to 0xFFFFFFFF, the configured max guaranteed-bandwidth value will be canceled.
                "
          ::= { hwGponPortControlEntry 9 }
          
        hwGponPortControlWaveLengthID OBJECT-TYPE
            SYNTAX  INTEGER {
               waveLengthID0(0),
               waveLengthID1(1),
               waveLengthID2(2),
               waveLengthID3(3),
               waveLengthID4(4),
               waveLengthID5(5),
               waveLengthID6(6),
               waveLengthID7(7),
               waveLengthIDAuto(65534),
               invalid(-1)
          }
            MAX-ACCESS read-write
            STATUS current
            DESCRIPTION
                "This object indicates the wavelength of TWDM-PON port.
                 Options:
                 1. waveLengthID0(0)              - Indicates that the wavelength of TWDM-PON port is 1596.34nm.
                 2. waveLengthID1(1)              - Indicates that the wavelength of TWDM-PON port is 1597.19nm.
                 3. waveLengthID2(2)              - Indicates that the wavelength of TWDM-PON port is 1598.04nm.
                 4. waveLengthID3(3)              - Indicates that the wavelength of TWDM-PON port is 1598.89nm.
                 5. waveLengthID4(4)              - Indicates that the wavelength of TWDM-PON port is 1599.75nm.
                 6. waveLengthID5(5)              - Indicates that the wavelength of TWDM-PON port is 1600.60nm.
                 7. waveLengthID6(6)              - Indicates that the wavelength of TWDM-PON port is 1601.46nm.
                 8. waveLengthID7(7)              - Indicates that the wavelength of TWDM-PON port is 1602.31nm.
                 9. waveLengthIDAuto(65534)       - Indicates that the wavelength of TWDM-PON port is automatic.
                 10. invalid(-1)                  - Indicates that the wavelength of TWDM-PON port is invalid.
                "
          ::= { hwGponPortControlEntry 10 } 
          
        hwGponPortControlComboMode OBJECT-TYPE
            SYNTAX  INTEGER {
               auto(1),
               wdm(2),
               invalid(-1)
            }
            MAX-ACCESS read-write
            STATUS current
            DESCRIPTION
                "This object indicates the combo mode of COMBO-PON port.
                 Options:
                 1. auto(1)                       - Indicates that the combo mode is auto.
                 2. wdm(2)                        - Indicates that the combo mode is WDM.
                 3. invalid(-1)                   - Indicates that the query fails or no information is detect.
                 The default value is auto(1).
                "
          ::= { hwGponPortControlEntry 11 }       
       
        hwGponPortControlFlexMode OBJECT-TYPE
            SYNTAX  INTEGER {
               gpon(2),
               xgpon(3),
               xgspon(4),
               xgComboAuto(5),
               xgComboWdm(6),
               xgsComboAuto(7), 
               xgsComboWdm(8),
               twdmpon(9),
               invalid(-1)
            }
            MAX-ACCESS read-write
            STATUS current
            DESCRIPTION
                "This object indicates the flex mode of COMBO-PON port.
				 Options:
				 1. gpon(2)               -Indicates that the flex mode is Gpon.
				 2. xgpon(3)              -Indicates that the flex mode is XG-Pon.
				 3. xgspon(4)             -Indicates that the flex mode is XGS-Pon.
				 4. xgComboAuto(5)        -Indicates that the flex mode is XG/G Combo auto Pon.
				 5. xgComboWdm(6)         -Indicates that the flex mode is XG/G Combo wdm Pon.   
				 6. xgsComboAuto(7)       -Indicates that the flex mode is XGS/G Combo auto Pon.
				 7. xgsComboWdm(8)        -Indicates that the flex mode is XGS/G Combo wdm Pon.
				 8. twdmpon(9)            -Indicates that the flex mode is TWDM-Pon.
				 9. invalid(-1)           -Indicates that the query fails or no information is detect.
				"
          ::= { hwGponPortControlEntry 12 } 
		  
	hwGponPortControlDbaLowlatency OBJECT-TYPE
          SYNTAX     INTEGER {
               enable(1),
               disable(0),	       
               invalid(-1)
          }
          MAX-ACCESS   read-write
          STATUS      current
          DESCRIPTION
            "This object is used to configure the low latency switch.
             Options:
             1. enable(1)            -Indicates that the lowlatency is enable
             2. disable(0)           -Indicates that the lowlatency is disable
             3. invalid(-1)          -Indicates that the query fails or no information is detected
            "
          ::= { hwGponPortControlEntry 13 }
		                   
    hwGponPortControlLightTestTimeduration OBJECT-TYPE
          SYNTAX  Integer32
          UNITS   "s"
          MAX-ACCESS   read-write
          STATUS      current
          DESCRIPTION
            "This object is used to configure the time duration of light test, 0s ~ 3600s, 0s means stopping the testing immidiately
            "
          ::= { hwGponPortControlEntry 14 }
          
	hwGponPortControlLightTestTestStatus OBJECT-TYPE
          SYNTAX     INTEGER {
               enable(1),
               disable(2),	       
               invalid(-1)
          }
          MAX-ACCESS   read-write
          STATUS      current
          DESCRIPTION
            "This object is used to configure the laser test status.
             Options:
             1. enable(1)            - laser tx is enable
             2. disable(2)           - laser tx is disable
             3. invalid(-1)
             Default:invalid(-1).
            "
          ::= { hwGponPortControlEntry 15 }
          
	hwGponPortControlLightTestFinshStatus OBJECT-TYPE
          SYNTAX     INTEGER {
               enable(1),
               disable(2),
               original(3),	       
               invalid(-1)
          }
          MAX-ACCESS   read-write
          STATUS      current
          DESCRIPTION
            "This object is used to configure the laser status after the test is completed.
             Options:
             1. enable(1)        - laser tx is enable
             2. disable(2)       - laser tx is disable
             3. original(3)      - returned to its original status 
             4. invalid(-1)
             Default:invalid(-1).
            " 
          ::= { hwGponPortControlEntry 16 }	
          	                   
  --Table hwXponDeviceOntActiveAlarmTable
        hwXponDeviceOntActiveAlarmTable OBJECT-TYPE
            SYNTAX SEQUENCE OF HwXponDeviceOntActiveAlarmEntry
            MAX-ACCESS not-accessible
            STATUS     current
            DESCRIPTION
                "The hwXponDeviceOntActiveAlarmTable is used to query the active alarm about ONT.
                 The indexes of this table are ifIndex and hwXponOntIndex.
                "
            ::= { hwXponCommonControlObjects 16 }

        hwXponDeviceOntActiveAlarmEntry OBJECT-TYPE
            SYNTAX HwXponDeviceOntActiveAlarmEntry
            MAX-ACCESS not-accessible
            STATUS current
            DESCRIPTION
                "The hwXponDeviceOntActiveAlarmTable is used to query the active alarm about ONT.
                 The indexes of this entry are ifIndex and hwXponOntIndex.
                "
            INDEX       { ifIndex, hwXponOntIndex }
            ::= { hwXponDeviceOntActiveAlarmTable 1 }

        HwXponDeviceOntActiveAlarmEntry ::=
            SEQUENCE
                {
                hwXponDeviceOntActiveAlarmNum  Integer32,
                hwXponDeviceOntActiveAlarmList    OCTET STRING,
                hwXponDeviceOntPortActiveAlarmNum Integer32,
                hwXponDeviceOntPortActiveAlarmList OCTET STRING
                }
                
        hwXponDeviceOntActiveAlarmNum OBJECT-TYPE
            SYNTAX      Integer32
            MAX-ACCESS  read-only
            STATUS      current
            DESCRIPTION
                "This object indicates the active alarm number about ONT."
            ::= { hwXponDeviceOntActiveAlarmEntry 1 }

        hwXponDeviceOntActiveAlarmList OBJECT-TYPE
            SYNTAX      OCTET STRING (SIZE (0..400))
            MAX-ACCESS  read-only
            STATUS      current
            DESCRIPTION
                "This object indicates the active alarm list about ONT. 
                 This list supports a maximum number of 100 ONT alarms and each alarm ID has 4 bytes"
            ::= { hwXponDeviceOntActiveAlarmEntry 2 }
            
        hwXponDeviceOntPortActiveAlarmNum OBJECT-TYPE
            SYNTAX      Integer32
            MAX-ACCESS  read-only
            STATUS      current
            DESCRIPTION
                "This object indicates active alarm number about ONT ports."
            ::= { hwXponDeviceOntActiveAlarmEntry 3 }
            
        hwXponDeviceOntPortActiveAlarmList OBJECT-TYPE
            SYNTAX      OCTET STRING (SIZE (0..600))
            MAX-ACCESS  read-only
            STATUS      current
            DESCRIPTION
                "This object indicates the active alarm list about ONT ports. 
                 This list supports a maximum number of 100 ONT alarms and each ONT port alarm has 6 bytes, 
                 including ONT port type (1 byte), ONT port ID (1 byte), alarm ID (4 bytes).
                 The ONT port type value list:
                 The value (13) indicates that the port type is T1,
                 The value (14) indicates that the port type is E1,
                 The value (32) indicates that the port type is POTS,
                 The value (47) indicates that the port type is ETH,   
                 The value (48) indicates that the port type is CATV."
            ::= { hwXponDeviceOntActiveAlarmEntry 4 }
  
  --Table hwXponOntIpConfigTable
        hwXponOntIpConfigTable OBJECT-TYPE
            SYNTAX     SEQUENCE OF HwXponOntIpConfigEntry
            MAX-ACCESS not-accessible
            STATUS     current
            DESCRIPTION
                    "The ONT IP config table. This table is used to configure and query
                     the IP configuration mode and IP address of an ONT.
                     The indexes of this table are ifIndex, hwXponOntIndex and hwXponOntIpIndex.
                    "
            ::= { hwXponCommonControlObjects 17 }

        hwXponOntIpConfigEntry OBJECT-TYPE
            SYNTAX     HwXponOntIpConfigEntry
            MAX-ACCESS not-accessible
            STATUS     current
            DESCRIPTION
                    "The ONT IP config table. This table is used to configure and query
                     the IP configuration mode and IP address of an ONT.
                     The indexes of this entry are ifIndex, hwXponOntIndex and hwXponOntIpIndex.
                    "
            INDEX       { ifIndex, hwXponOntIndex, hwXponOntIpIndex}
            ::= { hwXponOntIpConfigTable 1 }

        HwXponOntIpConfigEntry  ::=
            SEQUENCE
                {
                hwXponOntIpIndex                         Integer32,
                hwXponOntIpConfigMode                    INTEGER,
                hwXponOntIpConfigVlan                    Integer32,              
                hwXponOntIpConfigPriority                Integer32,
                hwXponOntIpconfigDscpDefaultPriority     Integer32,
                hwXponOntIpconfigDscpProfIndex           Integer32,                         
                hwXponOntIpAddress                       IpAddress,
                hwXponOntNetMask                         IpAddress,
                hwXponOntNetGateway                      IpAddress,             
                hwXponOntMasterDNS                       IpAddress,
                hwXponOntSlaveDNS                        IpAddress,
                hwXponOntIpConfigPppoeAccountMode        INTEGER,
                hwXponOntIpConfigPppoeUserName           OCTET STRING,                                           
                hwXponOntIpConfigPppoePassword           OCTET STRING,
                hwXponOntIpconfigDhcpReset               INTEGER,
                hwXponOntIpconfigRowStatus               RowStatus,
                hwXponOntIpconfigVlanMode                INTEGER,
                hwXponOntIpConfigPppoeAuthentication     INTEGER,
                hwXponOntIpConfigUsedWanProfName         OCTET STRING
                }

        hwXponOntIpIndex OBJECT-TYPE
            SYNTAX       Integer32
            MAX-ACCESS   not-accessible
            STATUS       current
            DESCRIPTION
                "The IP index of the ont IP host."
            ::= { hwXponOntIpConfigEntry  1 }  
            
        hwXponOntIpConfigMode  OBJECT-TYPE
                SYNTAX     INTEGER{
                            dhcp(1),
                            static(2),
                            nonOLTconfiguration(3),
                            pppoe(4)
                            }
                MAX-ACCESS   read-write
                STATUS      current
                DESCRIPTION
                    "IP configuration mode.
                     Options:
                     1. dhcp(1)                 - Indicates the dynamic allocation mode
                     2. static(2)               - Indicates the static allocation mode
                     3. nonOLTconfiguration(3)  - Indicates the nonOLTconfiguration mode(IP configuration mode is not set in the OLT)
                     4. pppoe(4)                - Indicates the pppoe allocation mode
                     "
                ::= { hwXponOntIpConfigEntry 2 } 
            
        hwXponOntIpConfigVlan  OBJECT-TYPE
                SYNTAX     Integer32
                MAX-ACCESS   read-write
                STATUS      current
                DESCRIPTION
                    "The VLAN of ONT IP host.
                     range: 0-4095"
               ::= { hwXponOntIpConfigEntry 3 }  
               
        hwXponOntIpConfigPriority  OBJECT-TYPE
                SYNTAX     Integer32
                MAX-ACCESS   read-write
                STATUS      current
                DESCRIPTION
                    "The priority of ONT IP host. range: 0-7, 0xfe: dscp-mapping."
                     DEFVAL { 0 }
                ::= { hwXponOntIpConfigEntry 4 } 
                
        hwXponOntIpconfigDscpDefaultPriority OBJECT-TYPE
               SYNTAX      Integer32
               MAX-ACCESS  read-write
               STATUS      current
               DESCRIPTION
                   "The default priority for dscp-mapping policy.
                    range: 0-7"
               ::= { hwXponOntIpConfigEntry 5 }

         hwXponOntIpconfigDscpProfIndex OBJECT-TYPE
               SYNTAX      Integer32
               MAX-ACCESS  read-write
               STATUS      current
               DESCRIPTION
                       "The dscp profile index of the ONT ip host, and the range is 1~50"
               ::= { hwXponOntIpConfigEntry 6 }                    
                        
          hwXponOntIpAddress  OBJECT-TYPE
                SYNTAX     IpAddress
                MAX-ACCESS   read-write
                STATUS      current
                DESCRIPTION
                "ONT ip address."
                ::= { hwXponOntIpConfigEntry 7 }     
                      
          hwXponOntNetMask  OBJECT-TYPE
                SYNTAX     IpAddress
                MAX-ACCESS   read-write
                STATUS      current
                DESCRIPTION
                    "Subnet mask."
                ::= { hwXponOntIpConfigEntry 8 }   
                 
         hwXponOntNetGateway  OBJECT-TYPE
                SYNTAX     IpAddress
                MAX-ACCESS   read-write
                STATUS      current
                DESCRIPTION
                    "The default network gateway."
                ::= { hwXponOntIpConfigEntry 9 }
         
         hwXponOntMasterDNS  OBJECT-TYPE
                SYNTAX     IpAddress
                MAX-ACCESS   read-write
                STATUS      current
                DESCRIPTION
                    "The active DNS address."
                ::= { hwXponOntIpConfigEntry 10 }       
                        
         hwXponOntSlaveDNS  OBJECT-TYPE
                SYNTAX     IpAddress
                MAX-ACCESS   read-write
                STATUS      current
                DESCRIPTION
                    "The slave DNS address."
                ::= { hwXponOntIpConfigEntry 11 } 
         
         hwXponOntIpConfigPppoeAccountMode          OBJECT-TYPE
               SYNTAX     INTEGER{
                          oltcfg(1),
                          ontcfg(2),
                          invalid(-1)
                          }
               MAX-ACCESS   read-write
               STATUS      current
               DESCRIPTION
                   "The input method of pppoe user account.
                    Options:
                    1. oltcfg(1)              - Indicates the user account is input on the ont
                    2. ontcfg(2)              - Indicates the user account is input on the olt
                    3. invalid(-1)            - Indicates that the query fails
                   "       
               DEFVAL { ontcfg }
               ::= { hwXponOntIpConfigEntry 12 }
          
         hwXponOntIpConfigPppoeUserName OBJECT-TYPE
               SYNTAX OCTET STRING (SIZE (0..64))
               MAX-ACCESS read-write
               STATUS current
               DESCRIPTION
                   "The username of the pppoe allocation mode."
               ::= { hwXponOntIpConfigEntry 13 }
                
         hwXponOntIpConfigPppoePassword OBJECT-TYPE
               SYNTAX OCTET STRING (SIZE (0..64))
               MAX-ACCESS read-write
               STATUS current
               DESCRIPTION
                   "The password of the pppoe allocation mode."
               ::= { hwXponOntIpConfigEntry 14 }         
         
         hwXponOntIpconfigDhcpReset     OBJECT-TYPE
              SYNTAX      INTEGER
              {
                 reset(1),
                 invalid(-1)
              }
              MAX-ACCESS  read-write        
              STATUS      current
              DESCRIPTION
                  "This object is used for resetting the ip host in the DHCP mode.
                  Options:
                   1. reset(1)            - DHCP reset in the DHCP mode
                   2. invalid(-1)         - invalid 
                   "
              ::= { hwXponOntIpConfigEntry 15 }  
                        
         hwXponOntIpconfigRowStatus OBJECT-TYPE
              SYNTAX RowStatus
              MAX-ACCESS read-create
              STATUS current
              DESCRIPTION
                  "The hwXponOntIpconfigRowStatus is used to create a new row
                   or to modify or delete an existing row in this table.
                   Options:
                   1. createAndGo(4) -create a new instance of a conceptual row 
                   2. destroy(6)     -delete the instances associated with an existing conceptual row
                  "
              ::= { hwXponOntIpConfigEntry 16 }   
              
         hwXponOntIpconfigVlanMode OBJECT-TYPE
              SYNTAX INTEGER
              {
                 transparent(1),
                 single(2),
                 invalid(-1)
              }
              MAX-ACCESS read-write
              STATUS current
              DESCRIPTION
                  "This object indicates the vlan mode.
                  Options:
                   1. transparent(1)        - Indicates that the VLAN mode is transparent
                   2. single(2)             - Indicates that the VLAN mode is single tag
                   3. invalid(-1)           - Indicates that the query fails or no information is detected 
                  "
              ::= { hwXponOntIpConfigEntry 17 } 
              
         hwXponOntIpConfigPppoeAuthentication OBJECT-TYPE
              SYNTAX INTEGER
              {
                 auto(1),
                 pap(2),
                 chap(3),
                 invalid(-1)
              }
              MAX-ACCESS read-write
              STATUS current
              DESCRIPTION
                  "This object indicates the pppoe authentication mode.
                  Options:
                   1. auto(1)                - Indicates that the pppoe authentication mode is auto
                   2. pap(2)                 - Indicates that the pppoe authentication mode is pap
                   3. chap(3)                - Indicates that the pppoe authentication mode is chap
                   4. invalid(-1)            - Indicates that the query fails or no information is detected 
                  "
              ::= { hwXponOntIpConfigEntry 18 } 
              
         hwXponOntIpConfigUsedWanProfName OBJECT-TYPE
               SYNTAX OCTET STRING (SIZE (0..32))
               MAX-ACCESS read-write
               STATUS current
               DESCRIPTION
                   "This object indicates the name of wan profile that is bound to the ONT"
               ::= { hwXponOntIpConfigEntry 19 }     
  
  --Table hwXponOntCapabilityInfoTable
        hwXponOntCapabilityInfoTable OBJECT-TYPE
            SYNTAX     SEQUENCE OF HwXponOntCapabilityInfoEntry
            MAX-ACCESS not-accessible
            STATUS     current
            DESCRIPTION
                "The ont info table. This table is used to query capability of the ont.
                 The indexes of this table are ifIndex and hwXponOntIndex.
                "
            ::= { hwXponCommonControlObjects 18 }

        hwXponOntCapabilityInfoEntry OBJECT-TYPE
            SYNTAX     HwXponOntCapabilityInfoEntry
            MAX-ACCESS not-accessible
            STATUS     current
            DESCRIPTION
                "The ont info table. This table is used to query capability of the ont.
                 The indexes of this entry are ifIndex and hwXponOntIndex.
                "
            INDEX       { ifIndex, hwXponOntIndex}
            ::= { hwXponOntCapabilityInfoTable 1 }

        HwXponOntCapabilityInfoEntry  ::=
            SEQUENCE
                {
                hwXponOntSupportVoipCfgMethod          BITS,
                hwXponOntSupportVoipSignalProtocol     BITS,
                hwXponOntSupportSingleRingCheck        INTEGER
                }
        
        hwXponOntSupportVoipCfgMethod OBJECT-TYPE
            SYNTAX     BITS
                {
                omcioam(0),
                configurationFile(1),
                tr069(2)
                }
            MAX-ACCESS read-only
            STATUS     current
            DESCRIPTION
                "This parameter indicates the voip configuration mode that the ONT supports.
                 This BITS structure can report the following status:
                 1.  omcioam(0)                  - This bit position positively reports that the ONT supports omci/oam configuration mode
                 2.  configurationFile(ftp)(1)   - This bit position positively reports that the ONT supports configurationFile(ftp) configuration mode
                 3.  tr069(2)                    - This bit position positively reports that the ONT supports tr069 configuration mode                 
                 "
            ::= { hwXponOntCapabilityInfoEntry  1 }
         
         hwXponOntSupportVoipSignalProtocol OBJECT-TYPE
            SYNTAX     BITS
                {
                sip(0),
                h248(1),
                mgcp(2)
                }
            MAX-ACCESS read-only
            STATUS     current
            DESCRIPTION
                "This parameter indicates the voip signal protocol that the ONT supports.
                 This BITS structure can report the following status:
                 1.  sip(0)          - This bit position positively reports that the ONT supports SIP Protocol
                 2.  h248(1)         - This bit position positively reports that the ONT supports H.248 Protocol
                 3.  mgcp(2)         - This bit position positively reports that the ONT supports MGCP Protocol
                 "
            ::= { hwXponOntCapabilityInfoEntry  2 }      
            
            hwXponOntSupportSingleRingCheck OBJECT-TYPE
            SYNTAX     INTEGER
                {
                support(1),
                notSupport(2),
                invalid(-1)
                }
            MAX-ACCESS read-only
            STATUS current
            DESCRIPTION                              
                "This object indicates whether the ONT supports the  single ring check.
                 Options:
                 1. support(1)                         - The value (1) indicates that the ONT supports the single ring  check.   
                 2. notSupport(2)                    - The value (2) indicates that the ONT not supports the single ring  check.
                 3. invalid(-1)                           - The value (-1) indicates that the query fails or no information is detected.
                "
                ::= { hwXponOntCapabilityInfoEntry  3 }   
                        
  --Table hwXponOntPowerSheddingStatusQueryTable  begin
        hwXponOntPowerSheddingStatusQueryTable OBJECT-TYPE
            SYNTAX SEQUENCE OF HwXponOntPowerSheddingStatusQueryEntry
            MAX-ACCESS not-accessible
            STATUS     current
            DESCRIPTION
                "The hwXponOntPowerSheddingStatusQueryTable is used to query the power shedding status of the ONT.
                 The indexes of this table are ifIndex and hwXponOntIndex.
                "
            ::= { hwXponCommonControlObjects 19 }

        hwXponOntPowerSheddingStatusQueryEntry OBJECT-TYPE
            SYNTAX HwXponOntPowerSheddingStatusQueryEntry
            MAX-ACCESS not-accessible
            STATUS current
            DESCRIPTION
                "The hwXponOntPowerSheddingStatusQueryTable is used to query the power shedding status of the ONT.
                 The indexes of this entry are ifIndex and hwXponOntIndex.
                "
            INDEX       { ifIndex, hwXponOntIndex }
            ::= { hwXponOntPowerSheddingStatusQueryTable 1 }

        HwXponOntPowerSheddingStatusQueryEntry ::=
            SEQUENCE
                {
                hwXponDeviceOntPowerSheddingStatus    Integer32
                }
                
        hwXponDeviceOntPowerSheddingStatus OBJECT-TYPE
            SYNTAX      Integer32
            MAX-ACCESS  read-only
            STATUS      current
            DESCRIPTION
                "Binary indication of power shedding status for each shedding class.
                 The ONU sets each bit to 1 when power shedding is active, and clears it to 0 when the service is restored.
                 bit0:      Data class
                         bit1:      Voice class
                         bit2:      Video overlay class
                         bit3:      Video return class
                         bit4:      DSL class
                         bit5:      ATM class
                         bit6:      CES class
                         bit7:      Frame class
                         bit8:      Sdh-sonet class
                         bit[15,9]: Reserved and set to 0
                         others:    Unconcern  
                "
            ::={ hwXponOntPowerSheddingStatusQueryEntry 1 }
            
  --Table hwXponOntPowerSheddingStatusQueryTable  end

  --Table hwGponDeviceOntCapabilityInfoTable  begin
        hwGponDeviceOntCapabilityInfoTable OBJECT-TYPE
            SYNTAX SEQUENCE OF HwGponDeviceOntCapabilityInfoEntry
            MAX-ACCESS not-accessible
            STATUS     current
            DESCRIPTION
                "The ont capability table. This table is used to query capability of the gpon ont.
                 The indexes of this table are ifIndex and hwGponDeviceOntObjIndex.
                "
            ::= { hwXponCommonControlObjects 20 }

        hwGponDeviceOntCapabilityInfoEntry OBJECT-TYPE
            SYNTAX HwGponDeviceOntCapabilityInfoEntry
            MAX-ACCESS not-accessible
            STATUS     current
            DESCRIPTION
                "The ont capability table. This table is used to query capability of the gpon ont.
                 The indexes of this entry are ifIndex and hwGponDeviceOntObjIndex.
                "
            INDEX       { ifIndex, hwGponDeviceOntObjIndex }
            ::= { hwGponDeviceOntCapabilityInfoTable 1 }

        HwGponDeviceOntCapabilityInfoEntry ::=
            SEQUENCE
                { 
                hwGponDeviceOntCapInfoEquipmentID          OCTET STRING,
                hwGponDeviceOntCapInfoUplinkPonPortNum     Integer32,
                hwGponDeviceOntCapInfoPotsPortNum          Integer32,
                hwGponDeviceOntCapInfoEthPortNum           Integer32,
                hwGponDeviceOntCapInfoTdmPortNum           Integer32,
                hwGponDeviceOntCapInfoMocaPortNum          Integer32,
                hwGponDeviceOntCapInfoCatvAniPortNum       Integer32,
                hwGponDeviceOntCapInfoCatvUniPortNum       Integer32,
                hwGponDeviceOntCapInfoGemPortNum           Integer32,
                hwGponDeviceOntCapInfoIpConfigurationMode  INTEGER,
                hwGponDeviceOntCapInfoTrafficSchedulerNum  Integer32,
                hwGponDeviceOntCapInfoTcontNum             Integer32,
                hwGponDeviceOntCapInfoTypeOfFlowControl    INTEGER,
                hwGponDeviceOntCapInfoDeviceType           INTEGER,
                hwGponDeviceOntCapInfoPowerSupplyControl   INTEGER,
                hwGponDeviceOntCapInfoExtOmciMsgFormat     INTEGER,
                hwGponDeviceOntCapInfoNumberOfPqInTcont    OCTET STRING,
                hwGponDeviceOntCapInfoEthOamSupport        Integer32,
                hwGponDeviceOntCapInfoVdslPortNum          Integer32,
                hwGponOntSupportMulticastEncrypt           INTEGER,
                hwGponDeviceOntCapInfoWifiPortNum          Integer32
                }

         hwGponDeviceOntCapInfoEquipmentID OBJECT-TYPE
            SYNTAX OCTET STRING (SIZE (0..20))
            MAX-ACCESS read-only
            STATUS current
            DESCRIPTION
                "The ONT equipment ID."
            ::= { hwGponDeviceOntCapabilityInfoEntry 1 }
         
         hwGponDeviceOntCapInfoUplinkPonPortNum OBJECT-TYPE
            SYNTAX Integer32
            MAX-ACCESS read-only
            STATUS current
            DESCRIPTION
                "This object indicates the number of uplink PON ports.
                -1 indicates the invalid value."
            ::= { hwGponDeviceOntCapabilityInfoEntry 2 }
         
         hwGponDeviceOntCapInfoPotsPortNum OBJECT-TYPE
            SYNTAX Integer32
            MAX-ACCESS read-only
            STATUS current
            DESCRIPTION
                "This object indicates the number of POTS ports.
                -1 indicates the invalid value."
            ::= { hwGponDeviceOntCapabilityInfoEntry 3 }
         
         hwGponDeviceOntCapInfoEthPortNum OBJECT-TYPE
            SYNTAX Integer32
            MAX-ACCESS read-only
            STATUS current
            DESCRIPTION
                "This object indicates the number of ETH ports.
                -1 indicates the invalid value."
            ::= { hwGponDeviceOntCapabilityInfoEntry 4 }
         
         hwGponDeviceOntCapInfoTdmPortNum OBJECT-TYPE
            SYNTAX Integer32
            MAX-ACCESS read-only
            STATUS current
            DESCRIPTION
                "This object indicates the number of TDM ports.
                -1 indicates the invalid value."
            ::= { hwGponDeviceOntCapabilityInfoEntry 5 }

         hwGponDeviceOntCapInfoMocaPortNum OBJECT-TYPE
            SYNTAX Integer32
            MAX-ACCESS read-only
            STATUS current
            DESCRIPTION
                "This object indicates the number of MOCA ports.
                -1 indicates the invalid value."
            ::= { hwGponDeviceOntCapabilityInfoEntry 6 }

         hwGponDeviceOntCapInfoCatvAniPortNum OBJECT-TYPE
            SYNTAX Integer32
            MAX-ACCESS read-only
            STATUS current
            DESCRIPTION
                "This object indicates the number of CATV ANI ports.
                -1 indicates the invalid value."
            ::= { hwGponDeviceOntCapabilityInfoEntry 7 }

         hwGponDeviceOntCapInfoCatvUniPortNum OBJECT-TYPE
            SYNTAX Integer32
            MAX-ACCESS read-only
            STATUS current
            DESCRIPTION
                "This object indicates the number of CATV UNI ports.
                -1 indicates the invalid value."
            ::= { hwGponDeviceOntCapabilityInfoEntry 8 }

         hwGponDeviceOntCapInfoGemPortNum OBJECT-TYPE
            SYNTAX Integer32
            MAX-ACCESS read-only
            STATUS current
            DESCRIPTION
                "This object indicates the number of GEM ports.
                -1 indicates the invalid value."
            ::= { hwGponDeviceOntCapabilityInfoEntry 9 }

         hwGponDeviceOntCapInfoIpConfigurationMode OBJECT-TYPE
            SYNTAX INTEGER
                {
                notsupport(1),
                support(2),
                dhcp(3),
                static(4),
                invalid(-1)
                }
            MAX-ACCESS read-only
            STATUS current
            DESCRIPTION
                "The mode of IP configuration.
                 Options:
                 1. notsupport(1)          - Not support
                 2. support(2)             - Support
                 3. dhcp(3)                - DHCP mode
                 4. static(4)              - Static mode
                 5. invalid(-1)            - Indicates the invalid value
                "
            ::= { hwGponDeviceOntCapabilityInfoEntry 10 }

         hwGponDeviceOntCapInfoTrafficSchedulerNum OBJECT-TYPE
            SYNTAX Integer32
            MAX-ACCESS read-only
            STATUS current
            DESCRIPTION
                "This object indicates the number of the traffic scheduler."
            ::= { hwGponDeviceOntCapabilityInfoEntry 11 }

         hwGponDeviceOntCapInfoTcontNum OBJECT-TYPE
            SYNTAX Integer32
            MAX-ACCESS read-only
            STATUS current
            DESCRIPTION
                "This object indicates the number of T-CONTs.
                -1 indicates the invalid value."
            ::= { hwGponDeviceOntCapabilityInfoEntry 12 }

         hwGponDeviceOntCapInfoTypeOfFlowControl OBJECT-TYPE
            SYNTAX INTEGER
                {
                pq(1),
                gemportcar(2),
                flowcar(3),
                gemportcarandpq(4),
                gemportcarorpq(5),
                invalid(-1)
                }
            MAX-ACCESS read-only
            STATUS current
            DESCRIPTION
                "The type of the ONT flow control.
                 Options:
                 1. pq(1)                - PQ 
                 2. gemportcar(2)        - GEMPORT CAR
                 3. flowcar(3)           - FLOW CAR
                 4. gemportcarandpq(4)   - GEMPORT CAR and PQ
                 5. gemportcarorpq(5)    - GEMPORT CAR or PQ
                 6. invalid(-1)          - Indicates the invalid value
                "
            ::= { hwGponDeviceOntCapabilityInfoEntry 13 }

         hwGponDeviceOntCapInfoDeviceType OBJECT-TYPE
            SYNTAX INTEGER
                {
                sfu(1),
                hgu(2),
                sbu(3),
                cbu(4),
                mdu(5),
                mtu(6),    
                sfu1fe1pots(7),
                invalid(-1)
                }
            MAX-ACCESS read-only
            STATUS current
            DESCRIPTION
                "This object indicates the ONT type.
                 Options:
                 1. sfu(1)            - The ONT type is SFU 
                 2. hgu(2)            - The ONT type is HGU
                 3. sbu(3)            - The ONT type is SBU
                 4. cbu(4)            - The ONT type is CBU
                 5. mdu(5)            - The ONT type is MDU
                 6. mtu(6)            - The ONT type is MTU    
                 7. sfu1fe1pots(7)  - The ONT type is SFU(1FE+1POTS) 
                 8. invalid(-1)       - Indicates the invalid value
                "
            ::= { hwGponDeviceOntCapabilityInfoEntry 14 }

         hwGponDeviceOntCapInfoPowerSupplyControl OBJECT-TYPE
            SYNTAX INTEGER
                {
                notsupport(1),
                support(2),
                txrxcoupling(3),
                txrxindependent(4),
                invalid(-1)
                }
            MAX-ACCESS read-only
            STATUS current
            DESCRIPTION
                "This object indicates if the ONT supports the power control.
                 Options:
                 1. notsupport(1)            - The ONT doesn't support the power control 
                 2. support(2)               - The ONT supports the power control
                 3. txrxcoupling(3)          - The ONT supports the power control.The TX and RX are coupling
                 4. txrxindependent(4)       - The ONT supports the power control.The TX and RX are independent
                 5. invalid(-1)              - Indicates the invalid value
                "
            ::= { hwGponDeviceOntCapabilityInfoEntry 15 }

         hwGponDeviceOntCapInfoExtOmciMsgFormat OBJECT-TYPE
            SYNTAX INTEGER
                {
                notsupport(1),
                support(2),
                invalid(-1)
                }
            MAX-ACCESS read-only
            STATUS current
            DESCRIPTION
                "This object indicates if the ONT supports Extended OMCI message format.
                 Options:
                 1. notsupport(1)                         - The ONT doesn't support the Extended OMCI message format 
                 2. support(2)                            - The ONT supports the Extended OMCI message format
                 3. invalid(-1)                           - Indicates the invalid value
                "
            ::= { hwGponDeviceOntCapabilityInfoEntry 16 }

         hwGponDeviceOntCapInfoNumberOfPqInTcont OBJECT-TYPE
            SYNTAX OCTET STRING (SIZE (0..512))
            MAX-ACCESS read-only
            STATUS current
            DESCRIPTION
                "This object indicates the number of PQs in T-CONT."
            ::= { hwGponDeviceOntCapabilityInfoEntry 17 }
                      
         hwGponDeviceOntCapInfoEthOamSupport OBJECT-TYPE
            SYNTAX      Integer32
            MAX-ACCESS  read-only
            STATUS      current
            DESCRIPTION
                "This object indicates if the ONT supports the type of ETHOAM by each bit.
                 The ONT sets each bit to 1 when the ONT supports the type of ETHOAM.
                 bit0:      Y.1731
                 bit[31,1]: Reserved and set to 0
                "
            ::= { hwGponDeviceOntCapabilityInfoEntry 19 }
            
        hwGponDeviceOntCapInfoVdslPortNum OBJECT-TYPE
            SYNTAX Integer32
            MAX-ACCESS read-only
            STATUS current
            DESCRIPTION
                "This object indicates the number of VDSL ports.
                -1 indicates the invalid value."
            ::= { hwGponDeviceOntCapabilityInfoEntry 20 }
       
        hwGponOntSupportMulticastEncrypt OBJECT-TYPE
            SYNTAX     INTEGER
                {
                notsupport(1),
                support(2),
                invalid(-1)
                }
            MAX-ACCESS read-only
            STATUS     current
            DESCRIPTION
                "This parameter indicates the capability of multicast encrypt that the ONT supports.
                 Options:
                 1. notsupport(1)               - Indicates that the ONT doesn't support the multicast encrypt.
                 2. support(2)                  - Indicates that the ONT supports the multicast encrypt.
                 3. invalid(-1)                 - Indicates that the query fails or no information is detected.
                 "
            ::= { hwGponDeviceOntCapabilityInfoEntry 21 }
            
        hwGponDeviceOntCapInfoWifiPortNum OBJECT-TYPE
            SYNTAX Integer32
            MAX-ACCESS read-only
            STATUS current
            DESCRIPTION
                "This object indicates the number of WiFi ports.
                -1 indicates the invalid value."
            ::= { hwGponDeviceOntCapabilityInfoEntry 22 }
                       
  --Table hwGponDeviceOntCapabilityInfoTable  end
 
 --Table hwXponDeviceOtdrTestTable
        hwXponDeviceOtdrTestTable OBJECT-TYPE
            SYNTAX SEQUENCE OF HwXponDeviceOtdrTestEntry 
            MAX-ACCESS not-accessible
            STATUS current
            DESCRIPTION
                "This table is used for the OTDR testing.
                 The index of this table is ifIndex.
                "
            ::= { hwXponCommonControlObjects 21 }

        hwXponDeviceOtdrTestEntry OBJECT-TYPE
            SYNTAX HwXponDeviceOtdrTestEntry
            MAX-ACCESS not-accessible
            STATUS current
            DESCRIPTION
                "This table is used for the OTDR testing.
                 The index of this entry is ifIndex.
                "
            INDEX { ifIndex }
            ::= { hwXponDeviceOtdrTestTable 1 }
                
        HwXponDeviceOtdrTestEntry ::=
            SEQUENCE { 
            hwXponDeviceOtdrTestOper                  INTEGER,                             
            hwXponDeviceOtdrTestStatus                INTEGER,
            hwXponDeviceOtdrTestResult                Integer32,
            hwXponDeviceOtdrTestWave                  INTEGER,
            hwXponDeviceOtdrTestPulseWidth            Integer32,
            hwXponDeviceOtdrClockRate                 INTEGER,
            hwXponDeviceOtdrTestSignalType            INTEGER,
            hwXponDeviceOtdrTestFreq                  INTEGER,               
            hwXponDeviceOtdrTestFilterSwitch          INTEGER,
            hwXponDeviceOtdrTestFilterMode            INTEGER,
            hwXponDeviceOtdrTestFilterPara            OCTET STRING,
            hwXponDeviceOtdrTestAverageTime           INTEGER,
            hwXponDeviceOtdrTestOpticalFibreLength    Integer32,
            hwXponDeviceOtdrTestDownPowerUsage        Integer32,
            hwXponDeviceOtdrUpTestMode                INTEGER,
            hwXponDeviceOtdrServerIpAddress           IpAddress,
            hwXponDeviceOtdrProtocol                  INTEGER,
            hwXponDeviceOtdrUserName                  OCTET STRING,
            hwXponDeviceOtdrPassword                  OCTET STRING,
            hwXponDeviceOtdrFilePath                  OCTET STRING,
            hwXponDeviceOtdrTestFilterOrder           INTEGER
            }

        hwXponDeviceOtdrTestOper OBJECT-TYPE
            SYNTAX INTEGER 
                {
                 start(1),
                 stop(2),
                 invalid(-1)      
                }
            MAX-ACCESS read-write
            STATUS current
            DESCRIPTION
                "OTDR test operation of a port.
                 Options: 
                 1. start(1)                - Indicates that the OTDR test is started on the port.
                 2. stop(2)                 - Indicates that the OTDR test is stopped on the port.
                 3. invalid(-1)             - Indicates that the query fails or no information is detected.
                "
            ::= { hwXponDeviceOtdrTestEntry 1 }

        hwXponDeviceOtdrTestStatus OBJECT-TYPE
            SYNTAX INTEGER 
                {
                 untested(1),
                 testing(2),
                 testFinish(3)
                }
            MAX-ACCESS read-only
            STATUS current
            DESCRIPTION
                "The state of OTDR test.
                 Options: 
                 1. untested (1)                - Indicates that the OTDR test is not performed for the port.
                 2. testing (2)                 - Indicates that the OTDR test is being performed for the port.
                 3. testFinish (3)              - Indicates that the OTDR test is complete.
                "
             ::= { hwXponDeviceOtdrTestEntry 2 }
             
        hwXponDeviceOtdrTestResult OBJECT-TYPE
            SYNTAX  Integer32
            MAX-ACCESS read-only
            STATUS current
            DESCRIPTION
                "This object indicates the result of OTDR test.
                 Options:
                 1. Success(1)                   - Indicates that the OTDR test successfully.
                 2. FtpFail(2)                   - Indicates that the result file of OTDR test upload failed.
                 3. BoardFail(3)                 - Indicates that the board is faulty during the test.
                 4. OpticalModuleFail(4)         - Indicates that the optical module is faulty during the test.
                 5. PortShutdown(5)              - Indicates that the port is shutdown during the test.
                 6. SystemSwitchOver(6)          - Indicates that the system switchover occurs during the test.
                 7. BoardloadFail(7)             - Indicates that the result file of OTDR test upload to mainboard failed.
                 8. BoardTypeBswitch(8)          - Indicates that the board switch over for TYPE B.
                 9. unknow(240)                  - Indicates that an unknown error occurs during the test.
                 10. invalid(-1)                 - Indicates that the query fails or no information is detected.
                "
            ::= { hwXponDeviceOtdrTestEntry 3 }    
                            
        hwXponDeviceOtdrTestWave OBJECT-TYPE
            SYNTAX INTEGER 
                {
                 upWave(1),
                 downWave(2),
                 all(3),
                 independant(4),
                 invalid(-1)
                }                  
            MAX-ACCESS read-write
            STATUS current
            DESCRIPTION
                "Test wave for the OTDR test.
                 Options:
                 1.upWave(1)                   - Indicates that the upstream wavelength is selected for the OTDR test.
                 2.downWave(2)                 - Indicates that the downstream wavelength is selected for the OTDR test.
                 3.all(3)                      - Indicates that both the upstream and downstream wavelengths are selected for the OTDR test.
                 4.independant(4)              - Indicates that the independent wavelength is selected for the OTDR test
                 5.invalid(-1)                 - Indicates that the query fails or no information is detected.
                 Default:downWave(2).
                "
            ::= { hwXponDeviceOtdrTestEntry 4 }

        hwXponDeviceOtdrTestPulseWidth OBJECT-TYPE
            SYNTAX Integer32
            UNITS  "0.01ns"
            MAX-ACCESS read-write
            STATUS current
            DESCRIPTION
                "Pulse width of test signals.
                 Unit: 0.01ns
                 The value of this node can be -1 indicates that query fails or no information is detected.
                 Default:2500.
                "
            ::= { hwXponDeviceOtdrTestEntry 5 }
                
        hwXponDeviceOtdrClockRate OBJECT-TYPE
            SYNTAX INTEGER 
                {
                 fortyMHz(1),
                 eightyMHz(2),
                 invalid(-1)
                }
            MAX-ACCESS read-only
            STATUS current
            DESCRIPTION
                "Clock rate of the OTDR test.
                 Options:
                 1.fortyMHz(1)                      - Indicates that the clock rate of the OTDR test is 40 MHz, at which, the system works in the low power consumption mode.
                 2.eightyMHz(2)                     - Indicates that the clock rate of the OTDR test is 80 MHz, at which, the system works in the high resolution mode.
                 3.invalid(-1)                      - Indicates that the query fails or no information is detected.
                 The clock rate is determined by hardware.
                "
            ::= { hwXponDeviceOtdrTestEntry 6 }
                
        hwXponDeviceOtdrTestSignalType OBJECT-TYPE
            SYNTAX INTEGER
                {
                 singlePulse(1),
                 singlePnSequence(2),
                 singleGrayCodeSequence(3),
                 consecutivePnSequence(4),
                 consecutiveGrayCodeSequence(5),
                 invalid(-1)
                }
            MAX-ACCESS read-write
            STATUS current
            DESCRIPTION
                "Type of sent OTDR test signals.
                 Options: 
                 1.singlePulse(1)                       - Indicates single pulse
                 2.singlePnSequence(2)                  - Indicates single PN sequence.
                 3.singleGrayCodeSequence(3)            - Indicates single gray code sequence.
                 4.consecutivePnSequence(4)             - Indicates consecutive PN sequence.
                 5.consecutiveGrayCodeSequence(5)       - Indicates consecutive gray code sequence.
                 6.invalid(-1)                          - Indicates that the query fails or no information is detected.
                 Default: consecutiveGrayCodeSequence(5).
                "
            ::= { hwXponDeviceOtdrTestEntry 7 }
                
        hwXponDeviceOtdrTestFreq OBJECT-TYPE
            SYNTAX INTEGER
                {
                 doubleFclk(1),
                 fclk(2),
                 halfFclk(3),
                 quarterFclk(4),
                 eighthFclk(5),
                 invalid(-1)
                }
            MAX-ACCESS read-write
            STATUS current
            DESCRIPTION
                "Sampling frequency of the OTDR test; Fclk indicates the clock frequency.
                 Options: 
                 1.doubleFclk(1)                   - Indicates that the sampling frequency of OTDR test is 2 x Fclk.
                 2.fclk(2)                         - Indicates that the sampling frequency of OTDR test is Fclk.
                 3.halfFclk(3)                     - Indicates that the sampling frequency of OTDR test is 1/2 x Fclk.
                 4.quarterFclk(4)                  - Indicates that the sampling frequency of OTDR test is 1/4 x Fclk.
                 5.eighthFclk(5)                   - Indicates that the sampling frequency of OTDR test is 1/8 x Fclk.
                 6.invalid(-1)                     - Indicates that the query fails or no information is detected.
                 Default:quarterFclk(4).
                "
            ::= { hwXponDeviceOtdrTestEntry 8 }
            
         hwXponDeviceOtdrTestFilterSwitch OBJECT-TYPE
            SYNTAX INTEGER
                {
                 enable(1),
                 disable(2),
                 invalid(-1)
                }
            MAX-ACCESS read-write
            STATUS current
            DESCRIPTION
                "Enable status of the OTDR FIR filter.
                 Options: 
                 1.enable(1)                   - Indicates that the OTDR FIR filter is enabled.
                 2.disable(2)                  - Indicates that the OTDR FIR filter is disabled.
                 3.invalid(-1)                 - Indicates that the query fails or no information is detected.
                 Default:enable(1).
                "
            ::= { hwXponDeviceOtdrTestEntry 9 }
            
         hwXponDeviceOtdrTestFilterMode OBJECT-TYPE
            SYNTAX INTEGER
                {
                 systemDefault(1),
                 issuedParameters(2),
                 invalid(-1)
                }
            MAX-ACCESS read-write
            STATUS current
            DESCRIPTION
                "Parameter configuration principle of the FIR filter.
                 Options: 
                 1.systemDefault(1)                   - Indicates that the system default parameters are used for the FIR filter.
                 2.issuedParameters(2)                - Indicates that the issued parameters are used for the FIR filter.
                 3.invalid(-1)                        - Indicates that the query fails or no information is detected.
                 Default:systemDefault(1).
                "
            ::= { hwXponDeviceOtdrTestEntry 10 } 
       
         hwXponDeviceOtdrTestFilterPara OBJECT-TYPE
            SYNTAX OCTET STRING 
            MAX-ACCESS read-write
            STATUS current
            DESCRIPTION
                "Parameters of the FIR filter.
                 If the parameter of hwXponDeviceOtdrTestFilterMode is set to the issued parameter,
                 this parameter is forwarded to the OTDR chip.
                 The first character of this node represents the number of parameters. 
                 Starting from the second character, these characters represent parameters.
                 Every four characters (32 bits) from left to right represent a parameter.
                 If a parameter is set with invalid value FFFFFFFF, its default value will be issued. Default values of parameters are as follows: 
                 0x00C5AC58,0x0208F564,0x049C37F2,0x090BF767,0x0F72A0E4,0x17065730,0x1E03A4E2,0x224243C2.
                "
            ::= { hwXponDeviceOtdrTestEntry 11 }  
            
         hwXponDeviceOtdrTestAverageTime OBJECT-TYPE
            SYNTAX INTEGER
                {
                 thirtySeconds(1),
                 oneMinute(2),
                 twoMinutes(3),
                 threeeMinutes(4),
                 sixMinutes(5),
                 thirtyMinutes(6),
                 invalid(-1)                
                }
            MAX-ACCESS read-write
            STATUS current
            DESCRIPTION
                "Average sampling times for OTDR test.
                 Options: 
                 1.thirtySeconds(1)                 - Indicates that the OTDR test is executed every 30 seconds.               
                 2.oneMinute(2)                     - Indicates that the OTDR test is executed every 1 minute.
                 3.twoMinutes(3)                    - Indicates that the OTDR test is executed every 2 minutes.
                 4.threeeMinutes(4)                 - Indicates that the OTDR test is executed every 3 minutes.
                 5.sixMinutes(5)                    - Indicates that the OTDR test is executed every 6 minutes.
                 6.thirtyMinutes(6)                 - Indicates that the OTDR test is executed every 30 minutes.
                 7.invalid(-1)                      - Indicates that the query fails or no information is detected.
                 Only test time is issued for this node, and the test times are calculated by the board. 
                 The board queries the test status of the optical module after the test time elapses.
                 If the test is complete, the board reads the data. 
                 Otherwise, the board will retry to query the test status of the optical module for three times.
                 If the test is always not complete, the test will be canceled, and a failure message will be returned.
                 Default:thirtySeconds(1).
                "
            ::= { hwXponDeviceOtdrTestEntry 12 }    
            
         hwXponDeviceOtdrTestOpticalFibreLength OBJECT-TYPE
            SYNTAX Integer32
            MAX-ACCESS read-write
            STATUS current
            DESCRIPTION
                "Length of the optical fiber to be tested.
                 Options: 
                 1.(1)                  - Indicates that the length of the optical fiber to be tested is 5 km.
                 2.(2)                  - Indicates that the length of the optical fiber to be tested is 10 km.
                 3.(3)                  - Indicates that the length of the optical fiber to be tested is 20 km.
                 4.(4)                  - Indicates that the length of the optical fiber to be tested is 30 km.
                 5.(5)                  - Indicates that the length of the optical fiber to be tested is 40 km.
                 6.(6)                  - Indicates that the length of the optical fiber to be tested is 80 km.
                 7.(-1)                 - Indicates that the query fails or no information is detected.
                 The length of the optical fiber to be tested is displayed as the value selected by the user. 
                 However, the actual length equals the value selected by the user plus 10 km in background processing.
                 Default:4(30km).
                "
            ::= { hwXponDeviceOtdrTestEntry 13 } 
                
         hwXponDeviceOtdrTestDownPowerUsage OBJECT-TYPE
            SYNTAX Integer32
            MAX-ACCESS read-write
            STATUS current
            DESCRIPTION
                "Modulation depth of downstream test signals
                 Currently, this value can be set to 10, 20, 30, 40, 50 and 100.
                 which indicates that the modulation depth is 10%, 20%, 30%, 40%, 50% and 100%.
                 The vlaue of this node can be -1 indicates that query fails or no information is detected.
                 Default:10
                "
            ::= { hwXponDeviceOtdrTestEntry 14 }     
            
         hwXponDeviceOtdrUpTestMode OBJECT-TYPE
            SYNTAX INTEGER
                {
                 onlineTest(1),
                 quickTest(2),
                 invalid(-1)
                }
            MAX-ACCESS read-write
            STATUS current
            DESCRIPTION
                "Upstream test mode.
                 Options: 
                 1.onlineTest(1)                   - Indicates that the upstream test mode is online test.
                 2.quickTest(2)                    - Indicates that the upstream test mode is quick test.
                 3.invalid(-1)                     - Indicates that the query fails or no information is detected.
                 Based on the selected test mode, the OLT can determine, 
                 work out the regularity of sending Trig signals and configure the optical module.
                 Currently, this node cannot be configured.
                "
            ::= { hwXponDeviceOtdrTestEntry 15 }  
      
         hwXponDeviceOtdrServerIpAddress OBJECT-TYPE
            SYNTAX      IpAddress
            MAX-ACCESS   read-write
            STATUS       current
            DESCRIPTION
                "The destination IP address of the OTDR.
                 The vlaue of this node can be FFFFFFFF indicates that query fails or no information is detected.
                " 
            ::= { hwXponDeviceOtdrTestEntry 16 }  
            
         hwXponDeviceOtdrProtocol OBJECT-TYPE
            SYNTAX INTEGER
                {
                 ftp(1),
                 tftp(2),
                 sftp(3),
                 invalid(-1)
                }
            MAX-ACCESS read-write
            STATUS current
            DESCRIPTION
                "Transfer protocol of test result.
                 Options: 
                 1.ftp(1)                   - Indicates that the test result file transfer mode is ftp.
                 2.tftp(2)                  - Indicates that the test result file transfer mode is tftp.
                 3.sftp(3)                  - Indicates that the test result file transfer mode is sftp.
                 4.invalid(-1)              - Indicates that the query fails or no information is detected.
                 Default:ftp(1).
                "
            ::= { hwXponDeviceOtdrTestEntry 17 }               
                  
        hwXponDeviceOtdrUserName OBJECT-TYPE
            SYNTAX OCTET STRING (SIZE (0..64))
            MAX-ACCESS read-write
            STATUS current
            DESCRIPTION
                "The user name of OTDR test.
                "
            ::= { hwXponDeviceOtdrTestEntry 18 }
                
        hwXponDeviceOtdrPassword OBJECT-TYPE
            SYNTAX OCTET STRING (SIZE (0..64))
            MAX-ACCESS read-write
            STATUS current
            DESCRIPTION
                "The password of OTDR test.
                "
            ::= { hwXponDeviceOtdrTestEntry 19 } 
           
        hwXponDeviceOtdrFilePath OBJECT-TYPE
            SYNTAX OCTET STRING (SIZE (0..256))
            MAX-ACCESS read-write
            STATUS current
            DESCRIPTION
                "The file path of OTDR test.
                "
            ::= { hwXponDeviceOtdrTestEntry 20 }   
                     
        hwXponDeviceOtdrTestFilterOrder OBJECT-TYPE
            SYNTAX INTEGER
                {
                 fifteenOrder(1),
                 sixteenOrder(2),
                 invalid(-1)
                }
            MAX-ACCESS read-write
            STATUS current
            DESCRIPTION
                "Value of the FIR filter order.
                 Options: 
                 1.fifteenOrder(1)                   - Indicates that the FIR filter order is fifteen.
                 2.sixteenOrder(2)                   - Indicates that the FIR filter order is sixteen.
                 3.invalid(-1)                       - Indicates that the query fails or no information is detected.
                 Default:fifteenOrder(1).
                "
            ::= { hwXponDeviceOtdrTestEntry 21 }    
                                                  
-- hwXponDeviceOtdrTestTable  end                 

 --Table hwXponOpticsDdmInfoExTable
        hwXponOpticsDdmInfoExTable OBJECT-TYPE
            SYNTAX SEQUENCE OF HwXponOpticsDdmInfoExEntry 
            MAX-ACCESS not-accessible
            STATUS current
            DESCRIPTION
                "This table supports the query of the information about the optical transceiver.
                 The index of this table is ifIndex.
                 "
            ::= { hwXponCommonControlObjects 22 }

        hwXponOpticsDdmInfoExEntry OBJECT-TYPE
            SYNTAX HwXponOpticsDdmInfoExEntry
            MAX-ACCESS not-accessible
            STATUS current
            DESCRIPTION
                "This table supports the query of the information about the optical transceiver.
                 The index of this entry is ifIndex.
                "
            INDEX { ifIndex }
            ::= { hwXponOpticsDdmInfoExTable 1 }
                
        HwXponOpticsDdmInfoExEntry ::=
            SEQUENCE { 
                     hwXponOpticsDdmInfoExTemperatureHighAlarmThreshold          Integer32,
                     hwXponOpticsDdmInfoExTemperatureLowAlarmThreshold           Integer32,
                     hwXponOpticsDdmInfoExTemperatureHighWarningThreshold        Integer32,
                     hwXponOpticsDdmInfoExTemperatureLowWarningThreshold         Integer32,
                     hwXponOpticsDdmInfoExSupplyVoltageHighAlarmThreshold        Integer32,
                     hwXponOpticsDdmInfoExSupplyVoltageLowAlarmThreshold         Integer32,
                     hwXponOpticsDdmInfoExSupplyVoltageHighWarningThreshold      Integer32,
                     hwXponOpticsDdmInfoExSupplyVoltageLowWarningThreshold       Integer32, 
                     hwXponOpticsDdmInfoExTxBiasCurrentHighAlarmThreshold        Integer32,
                     hwXponOpticsDdmInfoExTxBiasCurrentLowAlarmThreshold         Integer32,
                     hwXponOpticsDdmInfoExTxBiasCurrentHighWarningThreshold      Integer32,
                     hwXponOpticsDdmInfoExTxBiasCurrentLowWarningThreshold       Integer32,
                     hwXponOpticsDdmInfoExTxPowerHighAlarmThreshold              Integer32,
                     hwXponOpticsDdmInfoExTxPowerLowAlarmThreshold               Integer32,
                     hwXponOpticsDdmInfoExTxPowerHighWarningThreshold            Integer32,
                     hwXponOpticsDdmInfoExTxPowerLowWarningThreshold             Integer32,
                     hwXponOpticsDdmInfoExRxPowerHighAlarmThreshold              Integer32,
                     hwXponOpticsDdmInfoExRxPowerLowAlarmThreshold               Integer32,
                     hwXponOpticsDdmInfoExRxPowerHighWarningThreshold            Integer32,
                     hwXponOpticsDdmInfoExRxPowerLowWarningThreshold             Integer32,
                     hwXponOpticsDdmInfoEx10GTxBiasCurrent                       Integer32,
                     hwXponOpticsDdmInfoEx10GTxBiasCurrentHighAlarmThreshold     Integer32,
                     hwXponOpticsDdmInfoEx10GTxBiasCurrentLowAlarmThreshold      Integer32,
                     hwXponOpticsDdmInfoEx10GTxBiasCurrentHighWarningThreshold   Integer32,
                     hwXponOpticsDdmInfoEx10GTxBiasCurrentLowWarningThreshold    Integer32,
                     hwXponOpticsDdmInfoEx10GTxPower                             Integer32,
                     hwXponOpticsDdmInfoEx10GTxPowerHighAlarmThreshold           Integer32,
                     hwXponOpticsDdmInfoEx10GTxPowerLowAlarmThreshold            Integer32,
                     hwXponOpticsDdmInfoEx10GTxPowerHighWarningThreshold         Integer32,
                     hwXponOpticsDdmInfoEx10GTxPowerLowWarningThreshold          Integer32,
                     hwXponOpticsDdmInfoExCatvRxPowerHighAlarmThreshold          Integer32,                     
                     hwXponOpticsDdmInfoExCatvRxPowerLowAlarmThreshold           Integer32,
                     hwXponOpticsDdmInfoExModuleType                             INTEGER,
                     hwXponOpticsDdmInfoExSubType                                INTEGER,
                     hwXponOpticsDdmInfoExPrecision                              Integer32,
                     hwXponOpticsDdmInfoExEncapsulationType                      INTEGER,
                     hwXponOpticsDdmInfoExVendorPN                               OCTET STRING,
                     hwXponOpticsDdmInfoExUsedType                               INTEGER
            }

        hwXponOpticsDdmInfoExTemperatureHighAlarmThreshold OBJECT-TYPE
            SYNTAX   Integer32
            UNITS       "0.000001 C(centigrade)"
            MAX-ACCESS  read-only
            STATUS      current
            DESCRIPTION
                "Upper alarm threshold of the temperature. 
                 Unit: 0.000001 C(centigrade)
                 Options:
                 1. invalid(0x7FFFFFFF)      - Indicates that the query fails or no information is detected
                "
            ::= { hwXponOpticsDdmInfoExEntry  1 }

        hwXponOpticsDdmInfoExTemperatureLowAlarmThreshold OBJECT-TYPE
            SYNTAX   Integer32
            UNITS       "0.000001 C(centigrade)"
            MAX-ACCESS  read-only
            STATUS      current
            DESCRIPTION
                "Lower alarm threshold of the temperature. 
                 Unit: 0.000001 C(centigrade) 
                 Options:
                 1. invalid(0x7FFFFFFF)      - Indicates that the query fails or no information is detected
                "
            ::= { hwXponOpticsDdmInfoExEntry  2 }

        hwXponOpticsDdmInfoExTemperatureHighWarningThreshold OBJECT-TYPE
            SYNTAX   Integer32
            UNITS       "0.000001 C(centigrade)"
            MAX-ACCESS  read-only
            STATUS      current
            DESCRIPTION
                "Upper warning threshold of the temperature. 
                 Unit: 0.000001 C(centigrade) 
                 Options:
                 1. invalid(0x7FFFFFFF)      - Indicates that the query fails or no information is detected
                "
            ::= { hwXponOpticsDdmInfoExEntry  3 }

        hwXponOpticsDdmInfoExTemperatureLowWarningThreshold OBJECT-TYPE
            SYNTAX   Integer32
            UNITS       "0.000001 C(centigrade)"
            MAX-ACCESS  read-only
            STATUS      current
            DESCRIPTION
                "Lower warning threshold of the temperature. 
                 Unit: 0.000001 C(centigrade)
                 Options:
                 1. invalid(0x7FFFFFFF)      - Indicates that the query fails or no information is detected
                "
            ::= { hwXponOpticsDdmInfoExEntry  4 }

        hwXponOpticsDdmInfoExSupplyVoltageHighAlarmThreshold OBJECT-TYPE
            SYNTAX   Integer32
            UNITS       "0.000001V"
            MAX-ACCESS  read-only
            STATUS      current
            DESCRIPTION
                "Upper alarm threshold of the voltage. 
                 Unit: 0.000001V
                 Options:
                 1. invalid(0x7FFFFFFF)      - Indicates that the query fails or no information is detected
                "
            ::= { hwXponOpticsDdmInfoExEntry  5 }

        hwXponOpticsDdmInfoExSupplyVoltageLowAlarmThreshold OBJECT-TYPE
            SYNTAX   Integer32
            UNITS       "0.000001V"
            MAX-ACCESS  read-only
            STATUS      current
            DESCRIPTION
                "Lower alarm threshold of the voltage. 
                 Unit: 0.000001V
                 Options:
                 1. invalid(0x7FFFFFFF)      - Indicates that the query fails or no information is detected
                "
            ::= { hwXponOpticsDdmInfoExEntry  6 }

        hwXponOpticsDdmInfoExSupplyVoltageHighWarningThreshold OBJECT-TYPE
            SYNTAX   Integer32
            UNITS       "0.000001V"
            MAX-ACCESS  read-only
            STATUS      current
            DESCRIPTION
                "Upper warning threshold of the voltage.
                 Unit: 0.000001V
                 Options:
                 1. invalid(0x7FFFFFFF)      - Indicates that the query fails or no information is detected
                "
            ::= { hwXponOpticsDdmInfoExEntry  7 }

        hwXponOpticsDdmInfoExSupplyVoltageLowWarningThreshold OBJECT-TYPE
            SYNTAX   Integer32
            UNITS       "0.000001V"
            MAX-ACCESS  read-only
            STATUS      current
            DESCRIPTION
                "Lower warning threshold of the voltage. 
                 Unit: 0.000001V
                 Options:
                 1. invalid(0x7FFFFFFF)      - Indicates that the query fails or no information is detected
                "
            ::= { hwXponOpticsDdmInfoExEntry  8 }

        hwXponOpticsDdmInfoExTxBiasCurrentHighAlarmThreshold OBJECT-TYPE
            SYNTAX   Integer32
            UNITS       "0.000001A"
            MAX-ACCESS  read-only
            STATUS      current
            DESCRIPTION
                "Upper alarm threshold of the bias current. 
                 Unit: 0.000001A 
                 Options:
                 1. invalid(-1)      - Indicates that the query fails or no information is detected
                "
            ::= { hwXponOpticsDdmInfoExEntry  9 }

        hwXponOpticsDdmInfoExTxBiasCurrentLowAlarmThreshold OBJECT-TYPE
            SYNTAX   Integer32
            UNITS       "0.000001A"
            MAX-ACCESS  read-only
            STATUS      current
            DESCRIPTION
                "Lower alarm threshold of the bias current. 
                 Unit: 0.000001A
                 Options:
                 1. invalid(-1)      - Indicates that the query fails or no information is detected
                "
            ::= { hwXponOpticsDdmInfoExEntry  10 }

        hwXponOpticsDdmInfoExTxBiasCurrentHighWarningThreshold OBJECT-TYPE
            SYNTAX   Integer32
            UNITS       "0.000001A"
            MAX-ACCESS  read-only
            STATUS      current
            DESCRIPTION
                "Upper warning threshold of the bias current. 
                 Unit: 0.000001A
                 Options:
                 1. invalid(-1)      - Indicates that the query fails or no information is detected
                "
            ::= { hwXponOpticsDdmInfoExEntry  11 }

        hwXponOpticsDdmInfoExTxBiasCurrentLowWarningThreshold OBJECT-TYPE
            SYNTAX   Integer32
            UNITS       "0.000001A"
            MAX-ACCESS  read-only
            STATUS      current
            DESCRIPTION
                "Lower warning threshold of the bias current. 
                 Unit: 0.000001A 
                 Options:
                 1. invalid(-1)      - Indicates that the query fails or no information is detected
                "
            ::= { hwXponOpticsDdmInfoExEntry  12 }

        hwXponOpticsDdmInfoExTxPowerHighAlarmThreshold OBJECT-TYPE
            SYNTAX   Integer32
            UNITS       "0.000001dBm"
            MAX-ACCESS  read-only
            STATUS      current
            DESCRIPTION
                "Upper alarm threshold of the Tx power. 
                 Unit: 0.000001dBm
                 Options:
                 1. invalid(0x7FFFFFFF)      - Indicates that the query fails or no information is detected
                "
            ::= { hwXponOpticsDdmInfoExEntry  13 }

        hwXponOpticsDdmInfoExTxPowerLowAlarmThreshold OBJECT-TYPE
            SYNTAX   Integer32
            UNITS       "0.000001dBm"
            MAX-ACCESS  read-only
            STATUS      current
            DESCRIPTION
                "Lower alarm threshold of the Tx power. 
                 Unit: 0.000001dBm
                 Options:
                 1. invalid(0x7FFFFFFF)      - Indicates that the query fails or no information is detected
                "
            ::= { hwXponOpticsDdmInfoExEntry  14 }

        hwXponOpticsDdmInfoExTxPowerHighWarningThreshold OBJECT-TYPE
            SYNTAX   Integer32
            UNITS       "0.000001dBm"
            MAX-ACCESS  read-only
            STATUS      current
            DESCRIPTION
                "Upper warning threshold of the Tx power. 
                 Unit: 0.000001dBm
                 Options:
                 1. invalid(0x7FFFFFFF)      - Indicates that the query fails or no information is detected
                "
            ::= { hwXponOpticsDdmInfoExEntry  15 }

        hwXponOpticsDdmInfoExTxPowerLowWarningThreshold OBJECT-TYPE
            SYNTAX   Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected
                "
            ::= { hwXponOpticsDdmInfoExEntry  16 }

        hwXponOpticsDdmInfoExRxPowerHighAlarmThreshold   OBJECT-TYPE
            SYNTAX      Integer32
            UNITS       "0.000001dBm"
            MAX-ACCESS  read-only
            STATUS      current
            DESCRIPTION
                "Upper alarm threshold of the Rx power. 
                 Unit: 0.000001dBm
                 Options:
                 1. invalid(0x7FFFFFFF)      - Indicates that the query fails or no information is detected                 
                "
            ::= { hwXponOpticsDdmInfoExEntry  17 }

        hwXponOpticsDdmInfoExRxPowerLowAlarmThreshold OBJECT-TYPE
            SYNTAX   Integer32
            UNITS       "0.000001dBm"
            MAX-ACCESS  read-only
            STATUS      current
            DESCRIPTION
                "Lower alarm threshold of the Rx power. 
                 Unit: 0.000001dBm
                 Options:
                 1. invalid(0x7FFFFFFF)      - Indicates that the query fails or no information is detected                 
                "
            ::= { hwXponOpticsDdmInfoExEntry  18 }

        hwXponOpticsDdmInfoExRxPowerHighWarningThreshold OBJECT-TYPE
            SYNTAX   Integer32
            UNITS       "0.000001dBm"
            MAX-ACCESS  read-only
            STATUS      current
            DESCRIPTION
                "Upper warning threshold of the Rx power. 
                 Unit: 0.000001dBm
                 Options:
                 1. invalid(0x7FFFFFFF)      - Indicates that the query fails or no information is detected                 
                "
            ::= { hwXponOpticsDdmInfoExEntry  19 }

        hwXponOpticsDdmInfoExRxPowerLowWarningThreshold OBJECT-TYPE
            SYNTAX   Integer32
            UNITS       "0.000001dBm"
            MAX-ACCESS  read-only
            STATUS      current
            DESCRIPTION
                "Lower warning threshold of the Rx power. 
                 Unit: 0.000001dBm   
                 Options:
                 1. invalid(0x7FFFFFFF)      - Indicates that the query fails or no information is detected                 
                "
            ::= { hwXponOpticsDdmInfoExEntry  20 }
            
        hwXponOpticsDdmInfoEx10GTxBiasCurrent OBJECT-TYPE
            SYNTAX      Integer32
            UNITS       "0.000001A"
            MAX-ACCESS  read-only
            STATUS      current
            DESCRIPTION
                "Current of the 10G EPON optical transceiver. 
                 Unit: 0.000001A
                 Options:
                 1. invalid(-1)      - Indicates that the query fails or no information is detected
                "
            ::= { hwXponOpticsDdmInfoExEntry  21 }

        hwXponOpticsDdmInfoEx10GTxBiasCurrentHighAlarmThreshold OBJECT-TYPE
            SYNTAX   Integer32
            UNITS       "0.000001A"
            MAX-ACCESS  read-only
            STATUS      current
            DESCRIPTION
                "Upper alarm threshold of the 10G EPON optical transceiver bias current. 
                 Unit: 0.000001A 
                 Options:
                 1. invalid(-1)      - Indicates that the query fails or no information is detected
                "
            ::= { hwXponOpticsDdmInfoExEntry  22 }

        hwXponOpticsDdmInfoEx10GTxBiasCurrentLowAlarmThreshold OBJECT-TYPE
            SYNTAX   Integer32
            UNITS       "0.000001A"
            MAX-ACCESS  read-only
            STATUS      current
            DESCRIPTION
                "Lower alarm threshold of the 10G EPON optical transceiver bias current. 
                 Unit: 0.000001A
                 Options:
                 1. invalid(-1)      - Indicates that the query fails or no information is detected
                "
            ::= { hwXponOpticsDdmInfoExEntry  23 }

        hwXponOpticsDdmInfoEx10GTxBiasCurrentHighWarningThreshold OBJECT-TYPE
            SYNTAX   Integer32
            UNITS       "0.000001A"
            MAX-ACCESS  read-only
            STATUS      current
            DESCRIPTION
                "Upper warning threshold of the 10G EPON optical transceiver bias current. 
                 Unit: 0.000001A
                 Options:
                 1. invalid(-1)      - Indicates that the query fails or no information is detected
                "
            ::= { hwXponOpticsDdmInfoExEntry  24 }

        hwXponOpticsDdmInfoEx10GTxBiasCurrentLowWarningThreshold OBJECT-TYPE
            SYNTAX   Integer32
            UNITS       "0.000001A"
            MAX-ACCESS  read-only
            STATUS      current
            DESCRIPTION
                "Lower warning threshold of the 10G EPON optical transceiver bias current. 
                 Unit: 0.000001A 
                 Options:
                 1. invalid(-1)      - Indicates that the query fails or no information is detected
                "
            ::= { hwXponOpticsDdmInfoExEntry  25 }    
            
        hwXponOpticsDdmInfoEx10GTxPower OBJECT-TYPE
            SYNTAX      Integer32
            UNITS       "0.01dBm"
            MAX-ACCESS  read-only
            STATUS      current
            DESCRIPTION
                "Tx optical power of the 10G EPON optical transceiver. 
                 Unit: 0.01dBm
                 Options:
                 1. invalid(0x7FFFFFFF)      - Indicates that the query fails or no information is detected
                "
            ::= { hwXponOpticsDdmInfoExEntry  26 }            

        hwXponOpticsDdmInfoEx10GTxPowerHighAlarmThreshold OBJECT-TYPE
            SYNTAX   Integer32
            UNITS       "0.000001dBm"
            MAX-ACCESS  read-only
            STATUS      current
            DESCRIPTION
                "Upper alarm threshold of the 10G EPON optical transceiver Tx power. 
                 Unit: 0.000001dBm
                 Options:
                 1. invalid(0x7FFFFFFF)      - Indicates that the query fails or no information is detected
                "
            ::= { hwXponOpticsDdmInfoExEntry  27 }

        hwXponOpticsDdmInfoEx10GTxPowerLowAlarmThreshold OBJECT-TYPE
            SYNTAX   Integer32
            UNITS       "0.000001dBm"
            MAX-ACCESS  read-only
            STATUS      current
            DESCRIPTION
                "Lower alarm threshold of the 10G EPON optical transceiver Tx power. 
                 Unit: 0.000001dBm
                 Options:
                 1. invalid(0x7FFFFFFF)      - Indicates that the query fails or no information is detected
                "
            ::= { hwXponOpticsDdmInfoExEntry  28 }

        hwXponOpticsDdmInfoEx10GTxPowerHighWarningThreshold OBJECT-TYPE
            SYNTAX   Integer32
            UNITS       "0.000001dBm"
            MAX-ACCESS  read-only
            STATUS      current
            DESCRIPTION
                "Upper warning threshold of the 10G EPON optical transceiver Tx power. 
                 Unit: 0.000001dBm
                 Options:
                 1. invalid(0x7FFFFFFF)      - Indicates that the query fails or no information is detected
                "
            ::= { hwXponOpticsDdmInfoExEntry  29 }

        hwXponOpticsDdmInfoEx10GTxPowerLowWarningThreshold OBJECT-TYPE
            SYNTAX   Integer32
            UNITS       "0.000001dBm"
            MAX-ACCESS  read-only
            STATUS      current
            DESCRIPTION
                "Lower warning threshold of the 10G EPON optical transceiver Tx power.
                 Unit: 0.000001dBm
                 Options:
                 1. invalid(0x7FFFFFFF)      - Indicates that the query fails or no information is detected
                "
            ::= { hwXponOpticsDdmInfoExEntry  30 }
                    
         hwXponOpticsDdmInfoExCatvRxPowerHighAlarmThreshold OBJECT-TYPE
            SYNTAX      Integer32
            UNITS       "0.000001dBm"
            MAX-ACCESS  read-only
            STATUS      current
            DESCRIPTION
                "Upper AlarmThreshold threshold of the CATV Rx power.
                 Unit: 0.000001dBm
                 Options:
                 1. invalid(0x7FFFFFFF)      - Indicates that the query fails or no information is detected
                "
            ::= { hwXponOpticsDdmInfoExEntry  31 } 

        hwXponOpticsDdmInfoExCatvRxPowerLowAlarmThreshold OBJECT-TYPE
            SYNTAX      Integer32
            UNITS       "0.000001dBm"
            MAX-ACCESS  read-only
            STATUS      current
            DESCRIPTION
                "Lower AlarmThreshold threshold of the CATV Rx power.
                 Unit: 0.000001dBm
                 Options:
                 1. invalid(0x7FFFFFFF)      - Indicates that the query fails or no information is detected
                "
            ::= { hwXponOpticsDdmInfoExEntry  32 }            
            
        hwXponOpticsDdmInfoExModuleType OBJECT-TYPE
            SYNTAX INTEGER
            {
                gpon(1),
                epon(2),
                epon10g(3),
                gpon10g(4),
                wdmpon(5),
                hybridpon(6),
                gponepon(7),
                unknown(8),
                xgspon(9),
                gponandxgpon(10), 
                gponandxgspon(11),
                twdmpon(15),
                invalid(-1)
            }
            MAX-ACCESS read-only
            STATUS current
            DESCRIPTION
            "Options:
             1. gpon(1)          - GPON
             2. epon(2)          - EPON
             3. epon10g(3)       - 10G EPON
             4. gpon10g(4)       - 10G GPON
             5. wdmpon(5)        - WDM PON
             6. hybridpon(6)     - hybrid PON
             7. gponepon(7)      - GPON/EPON 
             8. unknown(8)       - Unknown
             9. xgspon(9)        - XGS-PON
             10.gponandxgpon(10) - GPON+XG-PON
             11.gponandxgspon(11)- GPON+XGS-PON
             12.twdmpon(15)      - TWDM-PON
             13.invalid(-1)      - Indicates that the query fails or no information is detected
            "
            ::= { hwXponOpticsDdmInfoExEntry  33 } 
            
        hwXponOpticsDdmInfoExSubType OBJECT-TYPE
            SYNTAX INTEGER
            {
                classbplus(1),
                classcplus(2),
                classb(3),
                classcplusplus(4),
                classd(5),
                n2a(33),
                n2b(34),
                n1(35),
                e1(36),
                e2a(37),
                e2b(38),
                d1(40),
                d2(41),
                n2(42),
                e2(43),
                px20(65),
                px20plus(66),
                px20plusplus(67),
                pr30(97),
                pr20(98),
                prx30(99),
                prx20(100),
                prx40(101),
                pr40(102),
                prx30e(103),
                prx40e(104),
                pr30plus(105),
                classbPlusAndPx20Plus(129),
                classbAndPx20(130),
                unknown(145),
                invalid(-1)
            }
            MAX-ACCESS read-only
            STATUS current
            DESCRIPTION
            "Options:
             1.  classbplus(1)              - CLASS B+
             2.  classcplus(2)              - CLASS C+
             3.  classb(3)                  - CLASS B
             4.  classcplusplus(4)          - CLASS C++
             5.  classd(5)                  - CLASS D
             6.  n2a(33)                    - N2a  
             7.  n2b(34)                    - N2b
             8.  n1(35)                     - N1
             9.  e1(36)                     - E1
             10.  e2a(37)                    - N2a
             11. e2b(38)                    - N2b
             12. d1(40)                     - D1
             13. d2(41)                     - D2
             14. n2(42)                     - N2
             15. e2(43)                     - E2
             16. px20(65)                   - PX20
             17. px20plus(66)               - PX20+
             18. px20plusplus(67)           - PX20++
             19. pr30(97)                   - PR30
             20. pr20(98)                   - PR20
             21. prx30(99)                  - PRX30
             22. prx20(100)                 - PRX20
             23. prx40(101)                 - PRX40  
             24. pr40(102)                  - PR40
             25. prx30e(103)                - PRX30-E
             26. prx40e(104)                - PRX40-E
             27. pr30plus(105)              - PR30+
             28. classbPlusAndPx20Plus(129) - GPON CLASS B+/EPON PX20+
             29. classbAndPx20(130)         - GPON CLASS B/EPON PX20
             30. unknown(145)               - Unknown
             31. invalid(-1)                - Indicates that the query fails or no information is detected
            "
            ::= { hwXponOpticsDdmInfoExEntry  34 } 
            
        hwXponOpticsDdmInfoExPrecision OBJECT-TYPE
            SYNTAX      Integer32
            UNITS       "0.1dBm"
            MAX-ACCESS  read-only
            STATUS      current
            DESCRIPTION
                "This object indicates the precision of optical power. 
                 Unit: 0.1dBm
                 Options:
                 1. invalid(-1)      - Indicates that the query fails or no information is detected
                "
            ::= { hwXponOpticsDdmInfoExEntry  35 } 
      
        hwXponOpticsDdmInfoExEncapsulationType OBJECT-TYPE
            SYNTAX INTEGER
            {
                sff2x5(1),
                sff2x10(2),
                sfp(3),
                xfp(4),
                lxfp(5),
                bosaonboard(6),
                unknown(7),   
                sfpplus(8),
                invalid(-1)
            }
            MAX-ACCESS read-only
            STATUS current
            DESCRIPTION
            "Options:
             1. sff2x5(1)               - SFF 2x5
             2. sff2x10(2)              - SFF 2x10
             3. sfp(3)                  - SFP
             4. xfp(4)                  - XFP
             5. lxfp(5)                 - LXFP
             6. bosaonboard(6)          - BOSA ON BOARD  
             7. unknown(7)              - Unknown      
             8. sfpplus(8)              - SFP+
             9. invalid(-1)             - Indicates that the query fails or no information is detected
            "
            ::= { hwXponOpticsDdmInfoExEntry  36 } 
            
        hwXponOpticsDdmInfoExVendorPN OBJECT-TYPE
            SYNTAX OCTET STRING (SIZE (0..17))
            MAX-ACCESS read-only
            STATUS current
            DESCRIPTION
                "This object indicates the part number."
            ::= { hwXponOpticsDdmInfoExEntry  37 } 
                    
        hwXponOpticsDdmInfoExUsedType OBJECT-TYPE
            SYNTAX INTEGER {
                olt(1),
                onu(3),
                catvtriplex(4), 
                unknown(5),
                invalid(-1)
            }
            MAX-ACCESS read-only
            STATUS current
            DESCRIPTION
                "This object indicates the application scenario of the optical transceiver.
                 Options:
                 1. olt(1)                 - OLT
                 2. onu(3)                 - ONU
                 3. catvtriplex(4)         - CATV TriPlex
                 4. unknown(5)             - Unknown
                 5. invalid(-1)            - Indicates that the query fails or no information is detected
                "
            ::= { hwXponOpticsDdmInfoExEntry  38 }                                
                                                              
-- hwXponOpticsDdmInfoExTable  end        
--Table hwXponOpticsParameterRangeTable  begin
        hwXponOpticsParameterRangeTable OBJECT-TYPE
            SYNTAX SEQUENCE OF HwXponOpticsParameterRangeEntry
            MAX-ACCESS not-accessible
            STATUS     current
            DESCRIPTION
                "The xpon optics parameter range table. This table is used to query range of the optics parameter.
                 The indexes of this table are hwXponOpticalModuleType, hwXponOpticalModuleSubType, hwXponOpticalModuleOltOntType, and hwXponOpticalModuleBandwidthType.
                "
            ::= { hwXponCommonControlObjects 23 }

        hwXponOpticsParameterRangeEntry OBJECT-TYPE
            SYNTAX HwXponOpticsParameterRangeEntry
            MAX-ACCESS not-accessible
            STATUS     current
            DESCRIPTION
                "The xpon optics parameter range table. This table is used to query range of the optics parameter.
                 The indexes of this entry are hwXponOpticalModuleType, hwXponOpticalModuleSubType, hwXponOpticalModuleOltOntType, and hwXponOpticalModuleBandwidthType.
                "
            INDEX       { hwXponOpticalModuleType, hwXponOpticalModuleSubType, hwXponOpticalModuleOltOntType, hwXponOpticalModuleBandwidthType }
            ::= { hwXponOpticsParameterRangeTable 1 }

        HwXponOpticsParameterRangeEntry ::=
            SEQUENCE
                { 
                hwXponOpticalModuleType                  INTEGER,
                hwXponOpticalModuleSubType               Integer32,
                hwXponOpticalModuleOltOntType            INTEGER,
                hwXponOpticalModuleBandwidthType         INTEGER,
                hwXponOpticalModuleRxPowerValidValueMax  Integer32,
                hwXponOpticalModuleRxPowerValidValueMin  Integer32
                }

        hwXponOpticalModuleType OBJECT-TYPE
            SYNTAX INTEGER
                {
                gpon(2),
                epon(3),
                tengepon(4),
                xgpon(5),
                wdmpon(6),
                mixpon(7),
                gponepondoublemode(8)
                }
            MAX-ACCESS not-accessible
            STATUS current
            DESCRIPTION
                "This object indicates the xpon optical module type.
                 Options:
                 1. gpon(2)                - gpon type.
                 2. epon(3)                - epon type.
                 3. tengepon(4)            - 10gepon type.
                 4. xgpon(5)               - xgpon type.
                 5. wdmpon(6)              - wdmpon type.
                 6. mixpon(7)              - mixpon type.
                 7. gponepondoublemode(8)  - gponepondoublemode type.
                "
            ::= { hwXponOpticsParameterRangeEntry 1 }

        hwXponOpticalModuleSubType OBJECT-TYPE
            SYNTAX Integer32
            MAX-ACCESS not-accessible
            STATUS current
            DESCRIPTION
                "The xpon optical module sub type.
                GPON:0x2 - CLASS B+,
                     0x3 - CLASS C+,
                     0x4 - CLASS B,
                     0x5 - CLASS C++,
                     0x6 - CLASS D,
                EPON:0x2 - PX20,
                     0x3 - PX20+,
                     0x4 - PX20++,
                10GEPON:0x2 - PR30,
                        0x3 - PR20,
                        0x4 - PRX30,
                        0x5 - PRX20,
                        0x6 - PRX40,
                        0x7 - PR40,
                        0x8 - PRX30E,
                        0x9 - PRX40E,
                        0xa - PR30PLUS,
                XG-PON:0x2 to 0x5 - reserved,
                       0x6        - N2a,
                       0x7        - N2b,
                       0x8        - N1,
                       0x9        - E1,
                       0xA        - E2a,
                       0xB        - E2b,
                       0xC        - D1,
                       0xD        - D2,
                Gpon and Epon double mode: 0x2 - double mode, compatible with GPON CLASS B+ and EPON PX20+."
            ::= { hwXponOpticsParameterRangeEntry 2 }    

        hwXponOpticalModuleOltOntType OBJECT-TYPE
            SYNTAX INTEGER
                {
                olt(2),
                onu(4)
                }
            MAX-ACCESS not-accessible
            STATUS current
            DESCRIPTION
                "This object indicates the xpon optical module olt ont type.
                 Options:
                 1. olt(2)                 - olt type.
                 2. onu(4)                 - onu type.
                "
            ::= { hwXponOpticsParameterRangeEntry 3 }

        hwXponOpticalModuleBandwidthType OBJECT-TYPE
            SYNTAX INTEGER
                {
                bw1g(1),
                bw10g(2)
                }
            MAX-ACCESS not-accessible
            STATUS current
            DESCRIPTION
                "This object indicates the xpon optical module bandwidth type.
                 Options:
                 1. bw1g(1)               - bw1g type.
                 2. bw10g(2)              - bw10g type.
                "
            ::= { hwXponOpticsParameterRangeEntry 4 }

         hwXponOpticalModuleRxPowerValidValueMax OBJECT-TYPE
            SYNTAX Integer32
            MAX-ACCESS read-only
            STATUS current
            DESCRIPTION
                "The xpon optical module Rx power maximum valid value, units of 0.01 dBm."
            ::= { hwXponOpticsParameterRangeEntry 5 }
 
         hwXponOpticalModuleRxPowerValidValueMin OBJECT-TYPE
            SYNTAX Integer32
            MAX-ACCESS read-only
            STATUS current
            DESCRIPTION
                "The xpon optical module Rx power minimum valid value, units of 0.01 dBm."
            ::= { hwXponOpticsParameterRangeEntry 6 }                                               
--Table hwXponOpticsParameterRangeTable  end 

--Table hwGponInteroperModeConfigTable
        hwGponInteroperModeConfigTable OBJECT-TYPE
            SYNTAX SEQUENCE OF HwGponInteroperModeConfigEntry
            MAX-ACCESS not-accessible
            STATUS     current
            DESCRIPTION
                "This table is used to configure the interoperability mode of the ONT.
                 The indexes of this table are hwGponInteroperModeOntVenderIDInfoIndex, hwGponInteroperModeOntEquipmentIDInfoIndex and hwGponInteroperModeOntSoftwareVersionInfoIndex.
                "
            ::= { hwXponCommonControlObjects 24 }

        hwGponInteroperModeConfigEntry OBJECT-TYPE
            SYNTAX HwGponInteroperModeConfigEntry
            MAX-ACCESS not-accessible
            STATUS     current
            DESCRIPTION
                "This table is used to configure the interoperability mode of the ONT.
                 The indexes of this entry are hwGponInteroperModeOntVenderIDInfoIndex, hwGponInteroperModeOntEquipmentIDInfoIndex and hwGponInteroperModeOntSoftwareVersionInfoIndex.
                "
            INDEX       { hwGponInteroperModeOntVenderIDInfoIndex, hwGponInteroperModeOntEquipmentIDInfoIndex, hwGponInteroperModeOntSoftwareVersionInfoIndex }
            ::= { hwGponInteroperModeConfigTable 1 }
            
        HwGponInteroperModeConfigEntry ::=
            SEQUENCE
                {
                hwGponInteroperModeOntVenderIDInfoIndex           OCTET STRING,
                hwGponInteroperModeOntEquipmentIDInfoIndex        OCTET STRING,
                hwGponInteroperModeOntSoftwareVersionInfoIndex    OCTET STRING,
                hwGponInteroperModeSwitch                         INTEGER,
                hwGponInteroperModeOntMutlicastAuthModeSwitch     INTEGER,
                hwGponInteroperModeActiveMode                     INTEGER,
                hwGponInteroperModeConfigRowStatus                RowStatus,
                hwGponInteroperModeOntWanConfigMode               INTEGER,
                hwGponInteroperModeOntVlanTagOperMode             INTEGER,
                hwGponInteroperModeAniMVlanFilter                 INTEGER
                }
                
        hwGponInteroperModeOntVenderIDInfoIndex OBJECT-TYPE
            SYNTAX OCTET STRING (SIZE (1..4))
            MAX-ACCESS   not-accessible
            STATUS       current
            DESCRIPTION
                "This object indicates the vender ID of the ONT.
                "
            ::= { hwGponInteroperModeConfigEntry 1 }
            
        hwGponInteroperModeOntEquipmentIDInfoIndex OBJECT-TYPE
            SYNTAX OCTET STRING (SIZE (1..20))
            MAX-ACCESS   not-accessible
            STATUS       current
            DESCRIPTION
                "This object indicates the equipment ID of the ONT.
                 0 indicates that the equipment ID of the ONT is not specified.
                "
            ::= { hwGponInteroperModeConfigEntry 2 }
            
        hwGponInteroperModeOntSoftwareVersionInfoIndex OBJECT-TYPE
            SYNTAX OCTET STRING (SIZE (1..14))
            MAX-ACCESS   not-accessible
            STATUS       current
            DESCRIPTION
                "This object indicates the software version of the ONT.
                 0 indicates that the software version of the ONT is not specified.
                "
            ::= { hwGponInteroperModeConfigEntry 3 }
        
        hwGponInteroperModeSwitch OBJECT-TYPE
            SYNTAX INTEGER
                {
                ituT(1),
                ctc(2),
                ericV1(3),
                ericV2(4),
                ituTG984(5),
                ituTG988(6),
                cuc(7),
                cmcc(8),
                eci(9),
                mode1(10),
                mode2(11),
                mode2V2(12),
                mode3(13),
                mode4(14),
                mode2V3(15),
                mode2V4(16),
                mode5(17),
                eciV2(18),
                mode1V2(19)
                }
            MAX-ACCESS read-write
            STATUS current
            DESCRIPTION
                "The switch mode of ONT interoperability.
                 Options:
                 1. ituT(1)       - The switch mode of gpon ONT interoperability is ituT
                 2. ctc(2)        - The switch mode of gpon ONT interoperability is ctc
                 3. ericV1(3)     - The switch mode of gpon ONT interoperability is ericV1
                 4. ericV2(4)     - The switch mode of gpon ONT interoperability is ericV2
                 5. ituTG984(5)   - The switch mode of gpon ONT interoperability is ituTG984
                 6. ituTG988(6)   - The switch mode of gpon ONT interoperability is ituTG988  
                 7. cuc(7)        - The switch mode of gpon ONT interoperability is cuc
                 8. cmcc(8)       - The switch mode of gpon ONT interoperability is cmcc
                 9. eci(9)        - The switch mode of gpon ONT interoperability is eci
                 10. mode1(10)    - The switch mode of gpon ONT interoperability is mode1 
                 11. mode2(11)    - The switch mode of gpon ONT interoperability is mode2
                 12. mode2V2(12)  - The switch mode of gpon ONT interoperability is mode2V2 
                 13. mode3(13)    - The switch mode of gpon ONT interoperability is mode3   
                 14. mode4(14)    - The switch mode of gpon ONT interoperability is mode4 
                 15. mode2V3(15)  - The switch mode of gpon ONT interoperability is mode2V3
                 16. mode2V4(16)  - The switch mode of gpon ONT interoperability is mode2V4
                 17. mode5(17)    - The switch mode of gpon ONT interoperability is mode5
                 18. eciV2(18)    - The switch mode of gpon ONT interoperability is eciV2 
                 19. mode1V2(19)  - The switch mode of gpon ONT interoperability is mode1V2
                "
            ::= { hwGponInteroperModeConfigEntry 4 }

        hwGponInteroperModeOntMutlicastAuthModeSwitch OBJECT-TYPE
            SYNTAX INTEGER
                {
                ontControl(1),
                oltControl(2)
                }
            MAX-ACCESS read-write
            STATUS current
            DESCRIPTION
                "The switch mode of gpon ONT multicast authentication.
                 Options:
                 1. ontControl(1)  - The switch mode of gpon ONT multicast authentication is ont-control
                 2. oltControl(2)  - The switch mode of gpon ONT multicast authentication is olt-control
                "
            ::= { hwGponInteroperModeConfigEntry 5 }
            
        hwGponInteroperModeActiveMode OBJECT-TYPE
            SYNTAX INTEGER
                {
                immediate(1),
                nextStartup(2),
                invalid(-1)
                }
            MAX-ACCESS read-write
            STATUS current
            DESCRIPTION
                "The active mode of gpon ONT interoperability mode.
                 Options:
                 1. immediate(1)     - Indicates that the ONT takes effect immediately
                 2. nextStartup(2)  - Indicates that the ONT takes effect after next startup
                 3. invalid(-1)      - Indicates that the query fails or no information is detected
                "
            ::= { hwGponInteroperModeConfigEntry 6 }
            
        hwGponInteroperModeConfigRowStatus OBJECT-TYPE
            SYNTAX RowStatus
            MAX-ACCESS read-create
            STATUS current
            DESCRIPTION
                "The hwGponInteroperModeConfigRowStatus is used to create a new row
                 or delete an existing row in this table.
                 Options:
                 1. createAndGo(4) -create a new instance of a conceptual row 
                 2. destroy(6)     -delete the instances associated with an existing conceptual row
                "
            ::= { hwGponInteroperModeConfigEntry 7 }

        hwGponInteroperModeOntWanConfigMode OBJECT-TYPE
            SYNTAX INTEGER
                {
                setAfterCreate(1),
                setByCreate(2)
                }
            MAX-ACCESS read-write
            STATUS current
            DESCRIPTION
                "The mode of gpon ont wan config mode.
                 Options:
                 1. setAfterCreate(1)  - The mode of gpon wan config mode is set-after-create                  
                 2. setByCreate(2)     - The mode of gpon wan config mode is set-by-create
                "
            ::= { hwGponInteroperModeConfigEntry 8 }
             
        hwGponInteroperModeOntVlanTagOperMode OBJECT-TYPE
            SYNTAX INTEGER
                {
                modifyExternalTag(1),
                modifySingleTag(2)
                }
            MAX-ACCESS read-write
            STATUS current
            DESCRIPTION
                "The mode of gpon ont vlan tag operation mode.
                 Options:
                 1. modifyExternalTag(1)  - The mode of gpon vlan tag operation mode is modify-external-tag   
                 2. modifySingleTag(2)    - The mode of gpon vlan tag operation mode is modify-single-tag,this is the default mode.                               
                "
            ::= { hwGponInteroperModeConfigEntry 9 }
            
        hwGponInteroperModeAniMVlanFilter  OBJECT-TYPE
            SYNTAX  INTEGER
              {
                  default(0),
                  enable(1),
                  disable(2)
              }
            MAX-ACCESS read-write
            STATUS current
            DESCRIPTION
                "Indicates the mode of multicast VLAN filtering on the GPON ONT ANI side.
                 Options: 
                 1. default(0) -Indicates the default system behavior.                 
                 2. enable(1)  -Creates the multicast VLAN tagging filter data entity on the ANI side and issues the multicast VLAN to this entity. 
                 3. disable(2) -Do not create the multicast VLAN tagging filter data entity on the ANI side or issue the multicast VLAN to this entity.
                 The default value is default(0).
                "
            ::= { hwGponInteroperModeConfigEntry 10 } 
                         
--Table hwGponInteroperModeConfigTable end

--Table hwXponOltOpticsModuleExtInfoTable
        hwXponOltOpticsModuleExtInfoTable OBJECT-TYPE
            SYNTAX SEQUENCE OF HwXponOltOpticsModuleExtInfoEntry
            MAX-ACCESS not-accessible
            STATUS     current
            DESCRIPTION
                "This table is used to query the information about the optical transceiver.
                 The index of this table is ifIndex.
                "
            ::= { hwXponCommonControlObjects 25 }

        hwXponOltOpticsModuleExtInfoEntry OBJECT-TYPE
            SYNTAX HwXponOltOpticsModuleExtInfoEntry
            MAX-ACCESS not-accessible
            STATUS     current
            DESCRIPTION
                "This table is used to query the information about the optical transceiver.
                 The index of this entry is ifIndex.
                "
            INDEX       { ifIndex }
            ::= { hwXponOltOpticsModuleExtInfoTable 1 }
            
        HwXponOltOpticsModuleExtInfoEntry ::=
            SEQUENCE {
                hwXponOltOpticsModuleInfoRateIdentifier           INTEGER,
                hwXponOltOpticsModuleInfoLength50MicronOM3        Integer32,
                hwXponOltOpticsModuleInfoCcBaseState              INTEGER,
                hwXponOltOpticsModuleInfoCcExtState               INTEGER
            }
                
        hwXponOltOpticsModuleInfoRateIdentifier OBJECT-TYPE
            SYNTAX INTEGER {
                unspecified (1),               
                rateId4g2g1gRateSelectAs0As1(2),
                rateId8g4g2gRxRateSelect (3),   
                rateId8g4g2gTxRateSelect (4),   
                rateId8g4g2gRxTxRateSelect (5),
                rateId16g8g4gRxRateSelect (6),  
                rateId16g8g4gRxTxRateSelect (7),
                invalid (-1)                        
            }
            MAX-ACCESS read-only
            STATUS current
            DESCRIPTION
                "This object indicates the type of rate select functionality.
                 Options:
                 1. unspecified (1)                    - Unspecified
                 2. rateId4g2g1gRateSelectAs0As1(2)    - 4/2/1G Rate_Select & AS0/AS1
                 3. rateId8g4g2gRxRateSelect (3)       - 8/4/2G Rx Rate_Select only
                 4. rateId8g4g2gTxRateSelect (4)       - 8/4/2G Tx Rate_Select only
                 5. rateId8g4g2gRxTxRateSelect (5)     - 8/4/2G Independent Rx & Tx Rate_select
                 6. rateId16g8g4gRxRateSelect (6)      - 16/8/4G Rx Rate_select only
                 7. rateId16g8g4gRxTxRateSelect (7)    - 16/8/4G Independent Rx, Tx Rate_select
                 8. invalid (-1)                       - Indicates that the query fails or no information is detected
                "
            ::= { hwXponOltOpticsModuleExtInfoEntry 1 }

        hwXponOltOpticsModuleInfoLength50MicronOM3 OBJECT-TYPE
            SYNTAX Integer32
            MAX-ACCESS read-only
            STATUS current
            DESCRIPTION
                "This object indicates the link length supported for 50 um OM3 fiber, units of 10 m."
            ::= { hwXponOltOpticsModuleExtInfoEntry 2 }
          
        hwXponOltOpticsModuleInfoCcBaseState OBJECT-TYPE
            SYNTAX INTEGER {
                correct (1), 
                incorrect(2),
                invalid (-1)    
            }
            MAX-ACCESS read-only
            STATUS current
            DESCRIPTION
                "This object indicates the CC_BASE match state.
                 Options:
                 1. correct (1)             - Correct
                 2. incorrect(2)            - Incorrect
                 3. invalid (-1)            - Indicates that the query fails or no information is detected
                "
            ::= { hwXponOltOpticsModuleExtInfoEntry 3 }          
            
        hwXponOltOpticsModuleInfoCcExtState OBJECT-TYPE
            SYNTAX INTEGER {
                correct (1), 
                incorrect(2),
                invalid (-1)    
            }
            MAX-ACCESS read-only
            STATUS current
            DESCRIPTION
                "This object indicates the CC_EXT match state.
                 Options:
                 1. correct (1)             - Correct
                 2. incorrect(2)            - Incorrect
                 3. invalid (-1)            - Indicates that the query fails or no information is detected
                "
            ::= { hwXponOltOpticsModuleExtInfoEntry 4 } 
                                      
--Table hwXponOltOpticsModuleExtInfoTable end 

--Table hwGponOntPortServiceCfgTable
        hwGponOntPortServiceCfgTable OBJECT-TYPE
            SYNTAX SEQUENCE OF HwGponOntPortServiceCfgEntry
            MAX-ACCESS not-accessible
            STATUS     current
            DESCRIPTION
                "This table is used to configure the service parameter of the ONT port.
                 The indexes of this table are ifIndex, hwXponOntIndex, hwGponOntifType and hwGponOntifPort.
                "
            ::= { hwXponCommonControlObjects 26 }

        hwGponOntPortServiceCfgEntry OBJECT-TYPE
            SYNTAX HwGponOntPortServiceCfgEntry
            MAX-ACCESS not-accessible
            STATUS     current
            DESCRIPTION
                "This table is used to configure the service parameter of the ONT port.
                 The indexes of this entry are ifIndex, hwXponOntIndex, hwGponOntifType and hwGponOntifPort.
                "
            INDEX { ifIndex, hwXponOntIndex, hwGponOntifType, hwGponOntifPort }
            ::= { hwGponOntPortServiceCfgTable 1 }
            
        HwGponOntPortServiceCfgEntry ::=
            SEQUENCE
                {
                hwGponOntPortNativeVlan            Integer32,
                hwGponOntPortNativeVlanPriority    Integer32,
                hwGponOntPortIgmpForwardMode       INTEGER,
                hwGponOntPortCfgQinqMode           INTEGER
                }
                
        hwGponOntPortNativeVlan OBJECT-TYPE
            SYNTAX     Integer32 (-1|0..4095)
            MAX-ACCESS    read-write
            STATUS      current
            DESCRIPTION
                "This object indicates the native VLAN of the port.
                "
            ::= { hwGponOntPortServiceCfgEntry 1 }
            
        hwGponOntPortNativeVlanPriority OBJECT-TYPE
            SYNTAX     Integer32 (-1|0..7)
            MAX-ACCESS    read-write
            STATUS      current
            DESCRIPTION
                "This object indicates the native VLAN priority of the port.
                "
            ::= { hwGponOntPortServiceCfgEntry 2 }
            
        hwGponOntPortIgmpForwardMode OBJECT-TYPE
            SYNTAX    INTEGER{
                disable(1),
                enable(2),
                invalid (-1)
                }
            MAX-ACCESS  read-write
            STATUS      current
            DESCRIPTION
                "The object is used to enable or disable the switch of ONT port IGMP forward mode.
                Options:
                1. disable(1)     - Disable the switch of ONT port IGMP forward mode
                2. enable(2)      - Enable the switch of ONT port IGMP forward mode
                3. invalid(-1)    - Indicates that the query fails or no information is detected
                "
            ::= { hwGponOntPortServiceCfgEntry 3 }
            
        hwGponOntPortCfgQinqMode OBJECT-TYPE
            SYNTAX    INTEGER{
                disable(1),
                enable(2),
                unconcern(254)
                }
            MAX-ACCESS  read-write
            STATUS      current
            DESCRIPTION
                "The object is used to enable or disable the switch of ONT port QinQ transparent transmission mode..
                Options:
                1. disable(1)     - Disable the switch of ONT port QinQ transparent transmission mode
                2. enable(2)      - Enable the switch of ONT port QinQ transparent transmission mode
                3. unconcern(254) - Unconcern QinQ transparent transmission mode
                The default value is unconcern(254)
                "
            ::= { hwGponOntPortServiceCfgEntry 4 }
  --Table hwGponOntPortServiceCfgTable end
  
  --Table hwXponDeviceOntNoAuthConfigTable
        hwXponDeviceOntNoAuthConfigTable OBJECT-TYPE
            SYNTAX SEQUENCE OF HwXponDeviceOntNoAuthConfigEntry
            MAX-ACCESS not-accessible
            STATUS     current
            DESCRIPTION
                "The hwXponDeviceOntNoAuthConfigTable is used to configure the type of ONT to be no authentication.
                 The indexes of this table are hwXponDeviceOntAccessType and hwXponDeviceOntModel.
                "
            ::= { hwXponCommonControlObjects 27 }

        hwXponDeviceOntNoAuthConfigEntry OBJECT-TYPE
            SYNTAX HwXponDeviceOntNoAuthConfigEntry
            MAX-ACCESS not-accessible
            STATUS current
            DESCRIPTION
                "The hwXponDeviceOntNoAuthConfigTable is used to configure the type of ONT to be no authentication.
                 The indexes of this entry are hwXponDeviceOntAccessType and hwXponDeviceOntModel.
                "
            INDEX       { hwXponDeviceOntAccessType, hwXponDeviceOntModel }
            ::= { hwXponDeviceOntNoAuthConfigTable 1 }

        HwXponDeviceOntNoAuthConfigEntry ::=
            SEQUENCE
                {
                hwXponDeviceOntAccessType              INTEGER,
                hwXponDeviceOntModel                   OCTET STRING,
                hwXponDeviceOntNoAuthRowStatus         RowStatus
                }
                
        hwXponDeviceOntAccessType OBJECT-TYPE
            SYNTAX INTEGER {
                           gpon(1),
                           epon(2)
                           }
            MAX-ACCESS    not-accessible
            STATUS      current
            DESCRIPTION
                "This object indicates the ONT access type.
                 Options:
                 1. gpon(1) - The ONT access type is GPON
                 2. epon(2) - The ONT access type is EPON
                "
            ::= { hwXponDeviceOntNoAuthConfigEntry 1 }

        hwXponDeviceOntModel  OBJECT-TYPE
            SYNTAX OCTET STRING (SIZE (1..20))
            MAX-ACCESS   not-accessible
            STATUS       current
            DESCRIPTION
                "This object indicates the ONT model."
            ::= { hwXponDeviceOntNoAuthConfigEntry 2 }

        hwXponDeviceOntNoAuthRowStatus OBJECT-TYPE
            SYNTAX     RowStatus
            MAX-ACCESS    read-create
            STATUS current
            DESCRIPTION
                "This object is used to create a new row or to modify or delete an existing row in this table.
                 Options:
                 1. createAndGo(4) -create a new instance of a conceptual row 
                 2. destroy(6)     -delete the instances associated with an existing conceptual row
                "
            ::= { hwXponDeviceOntNoAuthConfigEntry 3 }
            
  --Table hwXponDeviceOntNoAuthConfigTable end       
       
  --Table hwGponPortInfoTable
        hwGponPortInfoTable OBJECT-TYPE
            SYNTAX     SEQUENCE OF HwGponPortInfoEntry
            MAX-ACCESS not-accessible
            STATUS     current
            DESCRIPTION
                "GPON port Info table. This table is used to query the GPON/XG-PON port information.
                 The index of this table is ifIndex.
                "
            ::= { hwXponCommonControlObjects 28 }

        hwGponPortInfoEntry OBJECT-TYPE
            SYNTAX     HwGponPortInfoEntry
            MAX-ACCESS not-accessible
            STATUS     current
            DESCRIPTION
                "GPON port Info table. This table is used to query the GPON/XG-PON port information.
                 The index of this entry is ifIndex.
                "
            INDEX       { ifIndex }
            ::= { hwGponPortInfoTable 1 }

        HwGponPortInfoEntry  ::=
            SEQUENCE
                {
                hwGponPortMulticastEncryptState      INTEGER, 
                hwGponPortInfoAvailableBwFor2dot5G   Integer32,
                hwGponPortInfoAvailableBwFor10G      Integer32,
				hwGponPortRunFlexMode 				INTEGER	
                }    
                        
        hwGponPortMulticastEncryptState OBJECT-TYPE
            SYNTAX      INTEGER
                {
                off(1),
                on(2),
                invalid(-1)
                }
            MAX-ACCESS  read-only
            STATUS      current
            DESCRIPTION
                "Query the Multicast GEM Port encypt switch.
                 Options:
                 1. off(1)         - The Multicast GEM Port encypt switch is not encrypted
                 2. on(2)          - The Multicast GEM Port encypt switch is encrypted
                 3. invalid(-1)    - Indicates that the query fails or no information is detected
                "
            ::= { hwGponPortInfoEntry  1 } 
	    
        hwGponPortInfoAvailableBwFor2dot5G OBJECT-TYPE
            SYNTAX Integer32
            MAX-ACCESS read-only
            STATUS current
            DESCRIPTION
                "This object indicates the available bandwidth for the XG-PON port.
                 Unit: Kbps.
		         The value (-1) indicates that the query fails or no information is detected.
                "
            ::= { hwGponPortInfoEntry  2 }    
            
        hwGponPortInfoAvailableBwFor10G OBJECT-TYPE
            SYNTAX Integer32
            MAX-ACCESS read-only
            STATUS current
            DESCRIPTION
                "This object indicates the available bandwidth for the XGS-PON port.
                 Unit: Kbps.
		         The value (-1) indicates that the query fails or no information is detected.
                "
            ::= { hwGponPortInfoEntry  3 }
	    
		hwGponPortRunFlexMode OBJECT-TYPE
            SYNTAX  INTEGER {
               unusable(1),	
               gpon(2),
               xgpon(3),
               xgspon(4),
               xgComboAuto(5),
               xgComboWdm(6),
               xgsComboAuto(7), 
               xgsComboWdm(8),
               twdmpon(9),
               invalid(-1)
            }
            MAX-ACCESS read-only
            STATUS current
            DESCRIPTION
                "This object indicates the flex mode of COMBO-PON port.
				 Options: 
				 1. unusable(1)           -Indicates that the flex mode is unusable.
				 2. gpon(2)               -Indicates that the flex mode is Gpon.
				 3. xgpon(3)              -Indicates that the flex mode is XG-Pon.
				 4. xgspon(4)             -Indicates that the flex mode is XGS-Pon.
				 5. xgComboAuto(5)        -Indicates that the flex mode is XG/G Combo auto Pon.
				 6. xgComboWdm(6)         -Indicates that the flex mode is XG/G Combo wdm Pon.   
				 7. xgsComboAuto(7)       -Indicates that the flex mode is XGS/G Combo auto Pon.
				 8. xgsComboWdm(8)        -Indicates that the flex mode is XGS/G Combo wdm Pon.
				 9. twdmpon(9)            -Indicates that the flex mode is TWDM-PON
				 10. invalid(-1)          -Indicates that the query fails or no information is detect.
				"
          ::= { hwGponPortInfoEntry 4 }
  --Table hwGponPortInfoTable end

  --Table hwEponInteroperModeConfigTable
        hwEponInteroperModeConfigTable OBJECT-TYPE
            SYNTAX SEQUENCE OF HwEponInteroperModeConfigEntry
            MAX-ACCESS not-accessible
            STATUS     current
            DESCRIPTION
                "This table is used to configure the interoperability mode of the EPON ONT.
                 The indexes of this table are hwEponInteroperModeOntVendorIDInfoIndex, hwEponInteroperModeOntModelInfoIndex and hwEponInteroperModeOntSoftwareVersionInfoIndex.
                "
            ::= { hwXponCommonControlObjects 29 }

        hwEponInteroperModeConfigEntry OBJECT-TYPE
            SYNTAX HwEponInteroperModeConfigEntry
            MAX-ACCESS not-accessible
            STATUS     current
            DESCRIPTION
                "This table is used to configure the interoperability mode of the EPON ONT.
                 The indexes of this entry are hwEponInteroperModeOntVendorIDInfoIndex, hwEponInteroperModeOntModelInfoIndex and hwEponInteroperModeOntSoftwareVersionInfoIndex.
                "
            INDEX       { hwEponInteroperModeOntVendorIDInfoIndex, hwEponInteroperModeOntModelInfoIndex, hwEponInteroperModeOntSoftwareVersionInfoIndex }
            ::= { hwEponInteroperModeConfigTable 1 }
            
        HwEponInteroperModeConfigEntry ::=
            SEQUENCE {
                hwEponInteroperModeOntVendorIDInfoIndex           OCTET STRING,
                hwEponInteroperModeOntModelInfoIndex              OCTET STRING,
                hwEponInteroperModeOntSoftwareVersionInfoIndex    OCTET STRING,
                hwEponInteroperModeStandard                       INTEGER,
                hwEponInteroperModeActiveMode                     INTEGER,
                hwEponInteroperModeConfigRowStatus                RowStatus,
                hwEponInteroperModeStandardVersion                Integer32
            }
                
        hwEponInteroperModeOntVendorIDInfoIndex OBJECT-TYPE
            SYNTAX OCTET STRING (SIZE (1..4))
            MAX-ACCESS   not-accessible
            STATUS       current
            DESCRIPTION
                "This object indicates the vender ID of the ONT.
                "
            ::= { hwEponInteroperModeConfigEntry 1 }
            
        hwEponInteroperModeOntModelInfoIndex OBJECT-TYPE 
            SYNTAX OCTET STRING (SIZE (1..20))
            MAX-ACCESS   not-accessible
            STATUS       current
            DESCRIPTION
                "This object indicates the ont model of the ONT.
                  indicates that the ont model of the ONT is not specified.
                "
            ::= { hwEponInteroperModeConfigEntry 2 }
            
        hwEponInteroperModeOntSoftwareVersionInfoIndex OBJECT-TYPE
            SYNTAX OCTET STRING (SIZE (1..16))
            MAX-ACCESS   not-accessible
            STATUS       current
            DESCRIPTION
                "This object indicates the software version of the ONT.
                 0 indicates that the software version of the ONT is not specified.
                "
            ::= { hwEponInteroperModeConfigEntry 3 }
        
        hwEponInteroperModeStandard OBJECT-TYPE
            SYNTAX INTEGER
                {
                ctc(1),
                cuc(2)
                }
            MAX-ACCESS read-write
            STATUS current
            DESCRIPTION
                "The mode standard of epon ONT interoperability.
                 Options:
                 1. ctc(1)	- The mode standard of epon ONT interoperability is ctc
                 2. cuc(2)	- The mode standard of epon ONT interoperability is cuc
                "
            ::= { hwEponInteroperModeConfigEntry 4 }
            
        hwEponInteroperModeActiveMode OBJECT-TYPE
            SYNTAX INTEGER {
                immediate(1),
                nextStartup(2),
                invalid(-1)
            }
            MAX-ACCESS read-write
            STATUS current
            DESCRIPTION
                "The active mode of epon ONT interoperability mode.
                 Options:
                 1. immediate(1)     - Indicates that the ONT takes effect immediately
                 2. nextStartup(2)  - Indicates that the ONT takes effect after next startup
                 3. invalid(-1)      - Indicates that the query fails or no information is detected
                "
            ::= { hwEponInteroperModeConfigEntry 5 }
            
        hwEponInteroperModeConfigRowStatus OBJECT-TYPE
            SYNTAX RowStatus
            MAX-ACCESS read-create
            STATUS current
            DESCRIPTION
                "The hwEponInteroperModeConfigRowStatus is used to create a new row
                 or delete an existing row in this table.
                 Options:
                 1. createAndGo(4) -create a new instance of a conceptual row 
                 2. destroy(6)     -delete the instances associated with an existing conceptual row
                "
            ::= { hwEponInteroperModeConfigEntry 6 }        
            
        hwEponInteroperModeStandardVersion OBJECT-TYPE
            SYNTAX Integer32 (0..254)
            MAX-ACCESS read-write
            STATUS current
            DESCRIPTION
                "This object indicates the oui version of the ONT.
                 0 indicates that the oui version of the ONT is not specified.
                 0x21 indicates that the oui version of the ONT is 2.1.     
                "
            ::= { hwEponInteroperModeConfigEntry 7 }

  --Table hwEponInteroperModeConfigTable end

  --Table hwXponUnconfiguredRogueOntTable
        hwXponUnconfiguredRogueOntTable OBJECT-TYPE
            SYNTAX  SEQUENCE OF HwXponUnconfiguredRogueOntEntry
            MAX-ACCESS  not-accessible
            STATUS  current
            DESCRIPTION
                "This table is used to query the information about rogue ONTs that is not added.
                 The index of this table is a combination of ifIndex and hwXponUnconfiguredRogueOntIndex.
                "
            ::= { hwXponCommonControlObjects 30 }
  
        hwXponUnconfiguredRogueOntEntry OBJECT-TYPE
            SYNTAX  HwXponUnconfiguredRogueOntEntry
            MAX-ACCESS  not-accessible
            STATUS  current
            DESCRIPTION
                "This table is used to query the information about rogue ONTs that is not added.
                 The index of this entry is a combination of ifIndex and hwXponUnconfiguredRogueOntIndex.
                "
            INDEX  { ifIndex, hwXponUnconfiguredRogueOntIndex }
            ::= { hwXponUnconfiguredRogueOntTable 1 }
  
        HwXponUnconfiguredRogueOntEntry ::=
            SEQUENCE {
                hwXponUnconfiguredRogueOntIndex              Integer32,
                hwXponUnconfiguredRogueOntIdentifier         OCTET STRING
            }

        hwXponUnconfiguredRogueOntIndex OBJECT-TYPE
            SYNTAX      Integer32
            MAX-ACCESS  not-accessible
            STATUS      current
            DESCRIPTION
                "The index of the rogue ONTs which is not added."
            ::= { hwXponUnconfiguredRogueOntEntry 1 }
 
        hwXponUnconfiguredRogueOntIdentifier OBJECT-TYPE
            SYNTAX     OCTET STRING  (SIZE (8))
            MAX-ACCESS  read-only
            STATUS     current
            DESCRIPTION
                "This object indicates the identifier of rogue ONTs that is not added."
            ::= { hwXponUnconfiguredRogueOntEntry 2 }
            
  --Table hwXponUnconfiguredRogueOntTable end
  
  --Table hwXponOntPortConfigTable
        hwXponOntPortConfigTable OBJECT-TYPE
            SYNTAX  SEQUENCE OF HwXponOntPortConfigEntry
            MAX-ACCESS  not-accessible
            STATUS  current
            DESCRIPTION
                "This table is used to configure the mac learning switch of teh ont port.
                 The indexes of this table are ifIndex, hwXponOntIndex, hwXponOntPhyType and hwXponOntPhyIndex.
                "
            ::= { hwXponCommonControlObjects 31 }
  
        hwXponOntPortConfigEntry OBJECT-TYPE
            SYNTAX  HwXponOntPortConfigEntry
            MAX-ACCESS  not-accessible
            STATUS  current
            DESCRIPTION
                "This table is used to configure the mac learning switch of teh ont port.
                 The indexes of this entry are ifIndex, hwXponOntIndex, hwXponOntPhyType and hwXponOntPhyIndex.
                "
            INDEX  { ifIndex, hwXponOntIndex, hwXponOntPhyType, hwXponOntPhyIndex }
            ::= { hwXponOntPortConfigTable 1 }
  
        HwXponOntPortConfigEntry ::=
            SEQUENCE {
                hwXponOntPhyType        INTEGER,
                hwXponOntPhyIndex       Integer32,
                hwXponOntPortCfgMacLearningSwitch INTEGER,
                hwXponOntPortCfgRouteSwitch       INTEGER,
                hwXponOntPortCfgL2IsolateSwitch   INTEGER
            } 
            
        hwXponOntPhyType OBJECT-TYPE
            SYNTAX INTEGER {
               t1(13),
               e1(14),
               fe(24),
               ge(34),
               vdsl(37),
               moca(46),
               eth(47),
               iphost(50)
            }
            MAX-ACCESS  not-accessible
            STATUS      current
            DESCRIPTION
                "The ONT port type.
                 Options:
                 1. t1(13)             - T1
                 2. e1(14)             - E1
                 3. fe(24)             - FE
                 4. ge(34)             - GE
                 5. vdsl(37)           - VDSL
                 6. moca(46)           - MOCA
                 7. eth(47)            - ETH
                 8. iphost(50)         - IPHOST
                "
            ::= { hwXponOntPortConfigEntry 1 }
 
        hwXponOntPhyIndex OBJECT-TYPE
            SYNTAX      Integer32
            MAX-ACCESS  not-accessible
            STATUS      current
            DESCRIPTION
                "The ONT port ID."
            ::= { hwXponOntPortConfigEntry 2 }        
            
        hwXponOntPortCfgMacLearningSwitch OBJECT-TYPE
            SYNTAX     INTEGER {
               enable(1),
               disable(2),
               invalid(-1)
            }
            MAX-ACCESS  read-write
            STATUS      current
            DESCRIPTION
                "This object is used to configure the mac learning switch of teh ont port.
                 Options:
                 1. enable(1)       - Indicates that the switch is enabled
                 2. disable(2)      - Indicates that the switch is disabled
                 3. invalid(-1)     - Indicates that the query fails or no information is detected
                "
            ::= { hwXponOntPortConfigEntry 3 }
            
        hwXponOntPortCfgRouteSwitch OBJECT-TYPE
            SYNTAX    INTEGER 
            {
               unconcern(0),
               enable(1),
               disable(2),
               invalid(-1)
            }
            MAX-ACCESS  read-write
            STATUS      current
            DESCRIPTION
                "This object is used to configure the route switch of ont port.
                 Options:
                 1. unconcern(0)    - Indicates that the switch is unconcern
                 2. enable(1)       - Indicates that the switch is enabled
                 3. disable(2)      - Indicates that the switch is disabled                
                "
            ::= { hwXponOntPortConfigEntry 4 }
			
        hwXponOntPortCfgL2IsolateSwitch OBJECT-TYPE
            SYNTAX    INTEGER 
            {
               unconcern(0),
               enable(1),
               disable(2),
			   invalid(-1)
            }
            MAX-ACCESS  read-write
            STATUS      current
            DESCRIPTION
                "This object is used to configure Layer 2 isolation for a GPON ONT port.
				 The default value is unconcern(0).
                 Options:
                 1. unconcern(0)    - Indicates that the switch is unconcern
                 2. enable(1)       - Indicates that the switch is enabled
                 3. disable(2)      - Indicates that the switch is disabled 
				 4. invalid(-1)     - Indicates that the query fails or no information is detected
                "
            ::= { hwXponOntPortConfigEntry 5 }			
            
  --Table hwXponOntPortConfigTable end
  
  --Table hwXponOntPortStaticMacTable
        hwXponOntPortStaticMacTable OBJECT-TYPE
            SYNTAX  SEQUENCE OF HwXponOntPortStaticMacEntry
            MAX-ACCESS  not-accessible
            STATUS  current
            DESCRIPTION
                "This table is used to configure the static mac address and vlan of the ONT port.
                 The indexes of this table are ifIndex, hwXponOntIndex, hwXponOntPhyType, hwXponOntPhyIndex and hwXponStaticMacIndex.
                "
            ::= { hwXponCommonControlObjects 32 }
  
        hwXponOntPortStaticMacEntry OBJECT-TYPE
            SYNTAX  HwXponOntPortStaticMacEntry
            MAX-ACCESS  not-accessible
            STATUS  current
            DESCRIPTION
                "This table is used to configure the static mac address and vlan of the ONT port.
                 The indexes of this entry are ifIndex, hwXponOntIndex, hwXponOntPhyType, hwXponOntPhyIndex and hwXponStaticMacIndex.
                "
            INDEX  { ifIndex, hwXponOntIndex, hwXponOntPhyType, hwXponOntPhyIndex, hwXponStaticMacIndex }
            ::= { hwXponOntPortStaticMacTable 1 }
  
        HwXponOntPortStaticMacEntry ::=
            SEQUENCE {                
                hwXponStaticMacIndex        Integer32,
                hwXponStaticMacVlanID       Integer32,
                hwXponStaticMacMacAddr      MacAddress,
                hwXponStaticMacRowStatus    RowStatus
            }
            
        hwXponStaticMacIndex OBJECT-TYPE
            SYNTAX      Integer32
            MAX-ACCESS  not-accessible
            STATUS      current
            DESCRIPTION
                "Indicates the index of a static MAC address. The index is used by the software for recording an entry."
            ::= { hwXponOntPortStaticMacEntry 1 }    
            
        hwXponStaticMacVlanID OBJECT-TYPE
            SYNTAX 	Integer32(1..4094)
	    MAX-ACCESS  read-write
	    STATUS 	current
	    DESCRIPTION
	            "The VLAN ID."
            ::= { hwXponOntPortStaticMacEntry 2 }
            
        hwXponStaticMacMacAddr OBJECT-TYPE
            SYNTAX      MacAddress
            MAX-ACCESS  read-write
            STATUS      current
            DESCRIPTION
                "Static MAC address of the ONT port."
            ::= { hwXponOntPortStaticMacEntry 3 }  
            
        hwXponStaticMacRowStatus OBJECT-TYPE
            SYNTAX RowStatus
            MAX-ACCESS read-create
            STATUS current
            DESCRIPTION
                "The hwStaticMacRowStatus is used to create a new row
                 or delete an existing row in this table.
                 Options:
                 1. createAndGo(4) -create a new instance of a conceptual row 
                 2. destroy(6)     -delete the instances associated with an existing conceptual row
                "
            ::= { hwXponOntPortStaticMacEntry 4 }
            
  --Table hwXponOntPortStaticMacTable end  
  
  --Table hwXponOntLoadInfoTable
        hwXponOntLoadInfoTable OBJECT-TYPE
            SYNTAX  SEQUENCE OF HwXponOntLoadInfoEntry
            MAX-ACCESS  not-accessible
            STATUS  current
            DESCRIPTION
                "This table is used to load the ONT file.
                 The indexes of this table are ifIndex, hwXponOntNewIndex.
                "
            ::= { hwXponCommonControlObjects 33 }
  
        hwXponOntLoadInfoEntry OBJECT-TYPE
            SYNTAX  HwXponOntLoadInfoEntry
            MAX-ACCESS  not-accessible
            STATUS  current
            DESCRIPTION
                "This table is used to load the ONT file.
                 The indexes of this entry are ifIndex, hwXponOntNewIndex.
                "
            INDEX  { ifIndex, hwXponOntNewIndex }
            ::= { hwXponOntLoadInfoTable 1 }
  
        HwXponOntLoadInfoEntry ::=
            SEQUENCE {
                hwXponOntNewIndex                   Integer32,                              	
                hwXponOntLoadInfoAppFragmentNum     Integer32,
                hwXponOntLoadInfoAppCurrFragment    Integer32
            } 
             
        hwXponOntNewIndex   OBJECT-TYPE
            SYNTAX       Integer32
            MAX-ACCESS   not-accessible
            STATUS       current
            DESCRIPTION
                "ONT ID, range: 0-254."
            ::= { hwXponOntLoadInfoEntry 1 }
                      
        hwXponOntLoadInfoAppFragmentNum OBJECT-TYPE 
            SYNTAX       Integer32 
            MAX-ACCESS   read-only 
            STATUS       current 
            DESCRIPTION 
                "Indicates the fragment num of of the app load for ONT. 
                 The value (-1) indicates that the fragment num is the invalid value. 
                " 
            ::= { hwXponOntLoadInfoEntry 2 } 
                 
        hwXponOntLoadInfoAppCurrFragment OBJECT-TYPE 
            SYNTAX       Integer32 
            MAX-ACCESS   read-only 
            STATUS       current 
            DESCRIPTION 
                "Indicates the current fragment index of of the app load for ONT, range: 1~hwXponOntLoadInfoAppFragmentNum.
                 The value (-1) indicates that the fragment index is the invalid value. 
                " 
            ::= { hwXponOntLoadInfoEntry 3 } 
            
  --Table hwXponOntLoadInfoTable end
  
  --Table hwXponOpticalDdmProfileReferenceTable
        hwXponOpticalDdmProfileReferenceTable OBJECT-TYPE
            SYNTAX SEQUENCE OF HwXponOpticalDdmProfileReferenceEntry 
            MAX-ACCESS not-accessible
            STATUS current
            DESCRIPTION
                "This table supports the query of the reference thresholds about the optical transceiver.
                 The indexes of this table are hwXponOpticalUseType, hwXponOpticalGradeType, hwXponOpticalType and hwXponOpticalSubType.
                 "
            ::= { hwXponCommonControlObjects 34 }

        hwXponOpticalDdmProfileReferenceEntry OBJECT-TYPE
            SYNTAX HwXponOpticalDdmProfileReferenceEntry
            MAX-ACCESS not-accessible
            STATUS current
            DESCRIPTION
                "This table supports the query of the reference thresholds about the optical transceiver.
                 The indexes of this entry are hwXponOpticalUseType, hwXponOpticalGradeType, hwXponOpticalType and hwXponOpticalSubType.
                "
            INDEX { hwXponOpticalUseType, hwXponOpticalGradeType, hwXponOpticalType, hwXponOpticalSubType }
            ::= { hwXponOpticalDdmProfileReferenceTable 1 }
                
        HwXponOpticalDdmProfileReferenceEntry ::=
            SEQUENCE { 
                     hwXponOpticalUseType                       INTEGER,
                     hwXponOpticalGradeType                     INTEGER,
                     hwXponOpticalType                          INTEGER,                     
                     hwXponOpticalSubType                       INTEGER,
                     hwXponOpticalTxAlarmUpper                  Integer32,
                     hwXponOpticalTxAlarmLower                  Integer32,
                     hwXponOpticalTxWarnUpper                   Integer32,
                     hwXponOpticalTxWarnLower                   Integer32,
                     hwXponOpticalRxAlarmUpper                  Integer32,
                     hwXponOpticalRxAlarmLower                  Integer32,
                     hwXponOpticalRxWarnUpper                   Integer32,
                     hwXponOpticalRxWarnLower                   Integer32,
                     hwXponOpticalTxBiasCurrentAlarmUpper       Integer32,
                     hwXponOpticalTxBiasCurrentAlarmLower       Integer32,
                     hwXponOpticalTxBiasCurrentWarnUpper        Integer32,
                     hwXponOpticalTxBiasCurrentWarnLower        Integer32,
                     hwXponOpticalSupplyVoltageAlarmUpper       Integer32,
                     hwXponOpticalSupplyVoltageAlarmLower       Integer32,
                     hwXponOpticalSupplyVoltageWarnUpper        Integer32,
                     hwXponOpticalSupplyVoltageWarnLower        Integer32,
                     hwXponOpticalTemperatureAlarmUpper         Integer32,
                     hwXponOpticalTemperatureAlarmLower         Integer32,
                     hwXponOpticalTemperatureWarnUpper          Integer32,
                     hwXponOpticalTemperatureWarnLower          Integer32,
                     hwXponOptical10GTxAlarmUpper               Integer32,
                     hwXponOptical10GTxAlarmLower               Integer32,
                     hwXponOptical10GTxWarnUpper                Integer32,
                     hwXponOptical10GTxWarnLower                Integer32,
                     hwXponOptical10GTxBiasCurrentAlarmUpper    Integer32,
                     hwXponOptical10GTxBiasCurrentAlarmLower    Integer32,
                     hwXponOptical10GTxBiasCurrentWarnUpper     Integer32,
                     hwXponOptical10GTxBiasCurrentWarnLower     Integer32
            }
			
        hwXponOpticalUseType OBJECT-TYPE
            SYNTAX INTEGER {
                olt(1),
                onu(3),
                catvtriplex(4), 
                unknown(5)
            }
			MAX-ACCESS not-accessible
            STATUS current
            DESCRIPTION
                "This object indicates the application scenario of the optical transceiver.
                 Options:
                 1. olt(1)                 - OLT
                 2. onu(3)                 - ONU
                 3. catvtriplex(4)         - CATV TriPlex
                 4. unknown(5)             - Unknown                 
                "
            ::= { hwXponOpticalDdmProfileReferenceEntry  1 }
			
        hwXponOpticalGradeType OBJECT-TYPE
            SYNTAX INTEGER {                
                commercial(1),
                industrial(2)
            }
            MAX-ACCESS not-accessible
            STATUS current
            DESCRIPTION
                "This object indicates the grade of the optical transceiver.
                 Options:                 
                 1. commercial(1)          - Commercial grade
                 2. industrial(2)          - Industrial grade                 
                "
            ::= { hwXponOpticalDdmProfileReferenceEntry  2 }
		
        hwXponOpticalType OBJECT-TYPE
            SYNTAX INTEGER {
                gpon(1),
                epon(2),
                epon10g(3),
                xgpon(4),
                wdmpon(5),
                hybridpon(6),
                gponepon(7),
                unknown(8),
                xgspon(9),
                xgcombopon(10),
                xgscombopon(11)
            }
            MAX-ACCESS not-accessible
            STATUS current
            DESCRIPTION
            "Options:
             1. gpon(1)          - GPON
             2. epon(2)          - EPON
             3. epon10g(3)       - 10G EPON
             4. xgpon(4)         - Asymmetric XG-PON
             5. wdmpon(5)        - WDM PON
             6. hybridpon(6)     - hybrid PON
             7. gponepon(7)      - GPON/EPON 
             8. unknown(8)       - Unknown
             9. xgspon(9)        - XGS-PON
             10. xgcombopon(10)  - XGPON+GPON
             11. xgscombopon(11) - XGSPON+GPON
            "
            ::= { hwXponOpticalDdmProfileReferenceEntry  3 }		       
			
        hwXponOpticalSubType OBJECT-TYPE
            SYNTAX INTEGER
            {
                classbplus(1),
                classcplus(2),
                classb(3),
                classcplusplus(4),
                classd(5),
                n2a(33),
                n2b(34),
                n1(35),
                e1(36),
                e2a(37),
                d1(40),
                d2(41),
                n2(42),
                e2(43),
                px20(65),
                px20plus(66),
                px20plusplus(67),
                pr30(97),
                pr20(98),
                prx30(99),
                prx20(100),
                pr40(101),
                prx40(102),
                pr30plus(103),
                classbPlusAndPx20Plus(129),
                classbAndPx20(130),
                unknown(145)
            }
            MAX-ACCESS not-accessible
            STATUS current
            DESCRIPTION
                "Options:
                1.  classbplus(1)              - CLASS B+
                2.  classcplus(2)              - CLASS C+
                3.  classb(3)                  - CLASS B
                4.  classcplusplus(4)          - CLASS C++
                5.  classd(5)                  - CLASS D
                6.  n2a(33)                    - N2a  
                7.  n2b(34)                    - N2b
                8.  n1(35)                     - N1
                9.  e1(36)                     - E1
                10. e2a(37)                    - E2a
                11. d1(40)                     - D1
                12. d2(41)                     - D2
                13. n2(42)                     - N2
                14. e2(43)                     - E2
                15. px20(65)                   - PX20
                16. px20plus(66)               - PX20+
                17. px20plusplus(67)           - PX20++
                18. pr30(97)                   - PR30
                19. pr20(98)                   - PR20
                20. prx30(99)                  - PRX30
                21. prx20(100)                 - PRX20
                22. pr40(101)                  - PR40
                23. prx40(102)                 - PRX40
                24. pr30plus(103)              - PR30+
                25. classbPlusAndPx20Plus(129) - GPON CLASS B+/EPON PX20+
                26. classbAndPx20(130)         - GPON CLASS B/EPON PX20
                27. unknown(145)               - Unknown
                "
            ::= { hwXponOpticalDdmProfileReferenceEntry  4 }
			
        hwXponOpticalTxAlarmUpper OBJECT-TYPE
            SYNTAX   Integer32
            UNITS       "0.000001dBm"
            MAX-ACCESS  read-only
            STATUS      current
            DESCRIPTION
                "Upper alarm threshold of the Tx power. 
                 Unit: 0.000001dBm
                 Options:
                 1. invalid(0x7FFFFFFF)      - Indicates that the query fails or no information is detected
                "
            ::= { hwXponOpticalDdmProfileReferenceEntry  5 }
			
        hwXponOpticalTxAlarmLower OBJECT-TYPE
            SYNTAX   Integer32
            UNITS       "0.000001dBm"
            MAX-ACCESS  read-only
            STATUS      current
            DESCRIPTION
                "Lower alarm threshold of the Tx power. 
                 Unit: 0.000001dBm
                 Options:
                 1. invalid(0x7FFFFFFF)      - Indicates that the query fails or no information is detected
                "
            ::= { hwXponOpticalDdmProfileReferenceEntry  6 }
			
        hwXponOpticalTxWarnUpper OBJECT-TYPE
            SYNTAX   Integer32
            UNITS       "0.000001dBm"
            MAX-ACCESS  read-only
            STATUS      current
            DESCRIPTION
                "Upper warning threshold of the Tx power. 
                 Unit: 0.000001dBm
                 Options:
                 1. invalid(0x7FFFFFFF)      - Indicates that the query fails or no information is detected
                "
            ::= { hwXponOpticalDdmProfileReferenceEntry  7 }
			
        hwXponOpticalTxWarnLower OBJECT-TYPE
            SYNTAX   Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected
                "
            ::= { hwXponOpticalDdmProfileReferenceEntry  8 }
			
        hwXponOpticalRxAlarmUpper OBJECT-TYPE
            SYNTAX      Integer32
            UNITS       "0.000001dBm"
            MAX-ACCESS  read-only
            STATUS      current
            DESCRIPTION
                "Upper alarm threshold of the Rx power. 
                 Unit: 0.000001dBm
                 Options:
                 1. invalid(0x7FFFFFFF)      - Indicates that the query fails or no information is detected                 
                "
            ::= { hwXponOpticalDdmProfileReferenceEntry  9 }
			
        hwXponOpticalRxAlarmLower OBJECT-TYPE
            SYNTAX   Integer32
            UNITS       "0.000001dBm"
            MAX-ACCESS  read-only
            STATUS      current
            DESCRIPTION
                "Lower alarm threshold of the Rx power. 
                 Unit: 0.000001dBm
                 Options:
                 1. invalid(0x7FFFFFFF)      - Indicates that the query fails or no information is detected                 
                "
            ::= { hwXponOpticalDdmProfileReferenceEntry  10 }
			
        hwXponOpticalRxWarnUpper OBJECT-TYPE
            SYNTAX   Integer32
            UNITS       "0.000001dBm"
            MAX-ACCESS  read-only
            STATUS      current
            DESCRIPTION
                "Upper warning threshold of the Rx power. 
                 Unit: 0.000001dBm
                 Options:
                 1. invalid(0x7FFFFFFF)      - Indicates that the query fails or no information is detected                 
                "
            ::= { hwXponOpticalDdmProfileReferenceEntry  11 }
			
        hwXponOpticalRxWarnLower OBJECT-TYPE
            SYNTAX   Integer32
            UNITS       "0.000001dBm"
            MAX-ACCESS  read-only
            STATUS      current
            DESCRIPTION
                "Lower warning threshold of the Rx power. 
                 Unit: 0.000001dBm   
                 Options:
                 1. invalid(0x7FFFFFFF)      - Indicates that the query fails or no information is detected                 
                "
            ::= { hwXponOpticalDdmProfileReferenceEntry  12 }
			
        hwXponOpticalTxBiasCurrentAlarmUpper OBJECT-TYPE
            SYNTAX   Integer32
            UNITS       "0.000001A"
            MAX-ACCESS  read-only
            STATUS      current
            DESCRIPTION
                "Upper alarm threshold of the bias current. 
                 Unit: 0.000001A 
                 Options:
                 1. invalid(-1)      - Indicates that the query fails or no information is detected
                "
            ::= { hwXponOpticalDdmProfileReferenceEntry  13 }
			
        hwXponOpticalTxBiasCurrentAlarmLower OBJECT-TYPE
            SYNTAX   Integer32
            UNITS       "0.000001A"
            MAX-ACCESS  read-only
            STATUS      current
            DESCRIPTION
                "Lower alarm threshold of the bias current. 
                 Unit: 0.000001A
                 Options:
                 1. invalid(-1)      - Indicates that the query fails or no information is detected
                "
            ::= { hwXponOpticalDdmProfileReferenceEntry  14 }
			
        hwXponOpticalTxBiasCurrentWarnUpper OBJECT-TYPE
            SYNTAX   Integer32
            UNITS       "0.000001A"
            MAX-ACCESS  read-only
            STATUS      current
            DESCRIPTION
                "Upper warning threshold of the bias current. 
                 Unit: 0.000001A
                 Options:
                 1. invalid(-1)      - Indicates that the query fails or no information is detected
                "
            ::= { hwXponOpticalDdmProfileReferenceEntry  15 }
			
        hwXponOpticalTxBiasCurrentWarnLower OBJECT-TYPE
            SYNTAX   Integer32
            UNITS       "0.000001A"
            MAX-ACCESS  read-only
            STATUS      current
            DESCRIPTION
                "Lower warning threshold of the bias current. 
                 Unit: 0.000001A 
                 Options:
                 1. invalid(-1)      - Indicates that the query fails or no information is detected
                "
            ::= { hwXponOpticalDdmProfileReferenceEntry  16 }
			
        hwXponOpticalSupplyVoltageAlarmUpper OBJECT-TYPE
            SYNTAX   Integer32
            UNITS       "0.000001V"
            MAX-ACCESS  read-only
            STATUS      current
            DESCRIPTION
                "Upper alarm threshold of the voltage. 
                 Unit: 0.000001V
                 Options:
                 1. invalid(0x7FFFFFFF)      - Indicates that the query fails or no information is detected
                "
            ::= { hwXponOpticalDdmProfileReferenceEntry  17 }
			
        hwXponOpticalSupplyVoltageAlarmLower OBJECT-TYPE
            SYNTAX   Integer32
            UNITS       "0.000001V"
            MAX-ACCESS  read-only
            STATUS      current
            DESCRIPTION
                "Lower alarm threshold of the voltage. 
                 Unit: 0.000001V
                 Options:
                 1. invalid(0x7FFFFFFF)      - Indicates that the query fails or no information is detected
                "
            ::= { hwXponOpticalDdmProfileReferenceEntry  18 }
			
        hwXponOpticalSupplyVoltageWarnUpper OBJECT-TYPE
            SYNTAX   Integer32
            UNITS       "0.000001V"
            MAX-ACCESS  read-only
            STATUS      current
            DESCRIPTION
                "Upper warning threshold of the voltage.
                 Unit: 0.000001V
                 Options:
                 1. invalid(0x7FFFFFFF)      - Indicates that the query fails or no information is detected
                "
            ::= { hwXponOpticalDdmProfileReferenceEntry  19 }
			
        hwXponOpticalSupplyVoltageWarnLower OBJECT-TYPE
            SYNTAX   Integer32
            UNITS       "0.000001V"
            MAX-ACCESS  read-only
            STATUS      current
            DESCRIPTION
                "Lower warning threshold of the voltage. 
                 Unit: 0.000001V
                 Options:
                 1. invalid(0x7FFFFFFF)      - Indicates that the query fails or no information is detected
                "
            ::= { hwXponOpticalDdmProfileReferenceEntry  20 }
			
        hwXponOpticalTemperatureAlarmUpper OBJECT-TYPE
            SYNTAX   Integer32
            UNITS       "0.000001 C(centigrade)"
            MAX-ACCESS  read-only
            STATUS      current
            DESCRIPTION
                "Upper alarm threshold of the temperature. 
                 Unit: 0.000001 C(centigrade)
                 Options:
                 1. invalid(0x7FFFFFFF)      - Indicates that the query fails or no information is detected
                "
            ::= { hwXponOpticalDdmProfileReferenceEntry  21 }
			
        hwXponOpticalTemperatureAlarmLower OBJECT-TYPE
            SYNTAX   Integer32
            UNITS       "0.000001 C(centigrade)"
            MAX-ACCESS  read-only
            STATUS      current
            DESCRIPTION
                "Lower alarm threshold of the temperature. 
                 Unit: 0.000001 C(centigrade) 
                 Options:
                 1. invalid(0x7FFFFFFF)      - Indicates that the query fails or no information is detected
                "
            ::= { hwXponOpticalDdmProfileReferenceEntry  22 }
			
        hwXponOpticalTemperatureWarnUpper OBJECT-TYPE
            SYNTAX   Integer32
            UNITS       "0.000001 C(centigrade)"
            MAX-ACCESS  read-only
            STATUS      current
            DESCRIPTION
                "Upper warning threshold of the temperature. 
                 Unit: 0.000001 C(centigrade) 
                 Options:
                 1. invalid(0x7FFFFFFF)      - Indicates that the query fails or no information is detected
                "
            ::= { hwXponOpticalDdmProfileReferenceEntry  23 }
			
        hwXponOpticalTemperatureWarnLower OBJECT-TYPE
            SYNTAX   Integer32
            UNITS       "0.000001 C(centigrade)"
            MAX-ACCESS  read-only
            STATUS      current
            DESCRIPTION
                "Lower warning threshold of the temperature. 
                 Unit: 0.000001 C(centigrade)
                 Options:
                 1. invalid(0x7FFFFFFF)      - Indicates that the query fails or no information is detected
                "
            ::= { hwXponOpticalDdmProfileReferenceEntry  24 }	

        hwXponOptical10GTxAlarmUpper OBJECT-TYPE
            SYNTAX   Integer32
            UNITS       "0.000001dBm"
            MAX-ACCESS  read-only
            STATUS      current
            DESCRIPTION
                "Upper alarm threshold of the 10G xPON optical transceiver Tx power. 
                 Unit: 0.000001dBm
                 Options:
                 1. invalid(0x7FFFFFFF)      - Indicates that the query fails or no information is detected
                "
            ::= { hwXponOpticalDdmProfileReferenceEntry  25 }

        hwXponOptical10GTxAlarmLower OBJECT-TYPE
            SYNTAX   Integer32
            UNITS       "0.000001dBm"
            MAX-ACCESS  read-only
            STATUS      current
            DESCRIPTION
                "Lower alarm threshold of the 10G xPON optical transceiver Tx power. 
                 Unit: 0.000001dBm
                 Options:
                 1. invalid(0x7FFFFFFF)      - Indicates that the query fails or no information is detected
                "
            ::= { hwXponOpticalDdmProfileReferenceEntry  26 }

        hwXponOptical10GTxWarnUpper OBJECT-TYPE
            SYNTAX   Integer32
            UNITS       "0.000001dBm"
            MAX-ACCESS  read-only
            STATUS      current
            DESCRIPTION
                "Upper warning threshold of the 10G xPON optical transceiver Tx power. 
                 Unit: 0.000001dBm
                 Options:
                 1. invalid(0x7FFFFFFF)      - Indicates that the query fails or no information is detected
                "
            ::= { hwXponOpticalDdmProfileReferenceEntry  27 }

        hwXponOptical10GTxWarnLower OBJECT-TYPE
            SYNTAX   Integer32
            UNITS       "0.000001dBm"
            MAX-ACCESS  read-only
            STATUS      current
            DESCRIPTION
                "Lower warning threshold of the 10G xPON optical transceiver Tx power.
                 Unit: 0.000001dBm
                 Options:
                 1. invalid(0x7FFFFFFF)      - Indicates that the query fails or no information is detected
                "
            ::= { hwXponOpticalDdmProfileReferenceEntry  28 }
                       
        hwXponOptical10GTxBiasCurrentAlarmUpper OBJECT-TYPE
            SYNTAX   Integer32
            UNITS       "0.000001A"
            MAX-ACCESS  read-only
            STATUS      current
            DESCRIPTION
                "Upper alarm threshold of the 10G xPON optical transceiver bias current. 
                 Unit: 0.000001A 
                 Options:
                 1. invalid(-1)      - Indicates that the query fails or no information is detected
                "
            ::= { hwXponOpticalDdmProfileReferenceEntry  29 }

        hwXponOptical10GTxBiasCurrentAlarmLower OBJECT-TYPE
            SYNTAX   Integer32
            UNITS       "0.000001A"
            MAX-ACCESS  read-only
            STATUS      current
            DESCRIPTION
                "Lower alarm threshold of the 10G xPON optical transceiver bias current. 
                 Unit: 0.000001A
                 Options:
                 1. invalid(-1)      - Indicates that the query fails or no information is detected
                "
            ::= { hwXponOpticalDdmProfileReferenceEntry  30 }

        hwXponOptical10GTxBiasCurrentWarnUpper OBJECT-TYPE
            SYNTAX   Integer32
            UNITS       "0.000001A"
            MAX-ACCESS  read-only
            STATUS      current
            DESCRIPTION
                "Upper warning threshold of the 10G xPON optical transceiver bias current. 
                 Unit: 0.000001A
                 Options:
                 1. invalid(-1)      - Indicates that the query fails or no information is detected
                "
            ::= { hwXponOpticalDdmProfileReferenceEntry  31 }

        hwXponOptical10GTxBiasCurrentWarnLower OBJECT-TYPE
            SYNTAX   Integer32
            UNITS       "0.000001A"
            MAX-ACCESS  read-only
            STATUS      current
            DESCRIPTION
                "Lower warning threshold of the 10G xPON optical transceiver bias current. 
                 Unit: 0.000001A 
                 Options:
                 1. invalid(-1)      - Indicates that the query fails or no information is detected
                "
            ::= { hwXponOpticalDdmProfileReferenceEntry  32 }
			
  -- hwXponOpticalDdmProfileReferenceTable  end 		
  
  --Table hwXponOntPortVlanExtConfigTable
        hwXponOntPortVlanExtConfigTable OBJECT-TYPE
            SYNTAX  SEQUENCE OF HwXponOntPortVlanExtConfigEntry
            MAX-ACCESS  not-accessible
            STATUS  current
            DESCRIPTION
                "This table is used to configure the vlan config mode and downstream operation mode of ont port.
                 The indexes of this table are ifIndex, hwXponOntIndex, hwXponOntPortVlanExtConfigPhyType and
                 hwXponOntPortVlanExtConfigPhyIndex.
                "
            ::= { hwXponCommonControlObjects 35 }
  
        hwXponOntPortVlanExtConfigEntry OBJECT-TYPE
            SYNTAX  HwXponOntPortVlanExtConfigEntry
            MAX-ACCESS  not-accessible
            STATUS  current
            DESCRIPTION
                "This table is used to configure the vlan config mode and downstream operation mode of ont port.
                 The indexes of this entry are ifIndex, hwXponOntIndex, hwXponOntPortVlanExtConfigPhyType and
                 hwXponOntPortVlanExtConfigPhyIndex.
                "
            INDEX  { ifIndex, hwXponOntIndex, hwXponOntPortVlanExtConfigPhyType, hwXponOntPortVlanExtConfigPhyIndex }
            ::= { hwXponOntPortVlanExtConfigTable 1 }
  
        HwXponOntPortVlanExtConfigEntry ::=
            SEQUENCE {
                hwXponOntPortVlanExtConfigPhyType        INTEGER,
                hwXponOntPortVlanExtConfigPhyIndex       Integer32,
                hwXponOntPortVlanConfigMode              INTEGER,
                hwXponOntPortVlanDownstreamOperMode      INTEGER
            } 
            
        hwXponOntPortVlanExtConfigPhyType OBJECT-TYPE
            SYNTAX INTEGER {
               wifi(40),
               eth(47),
               ippath(61)
            }
            MAX-ACCESS  not-accessible
            STATUS      current
            DESCRIPTION
                "The ONT port type.
                 Options:
                 1. wifi(40)           - WiFi
                 2. eth(47)            - ETH
                 3. ippath(61)         - IPPATH
                "
            ::= { hwXponOntPortVlanExtConfigEntry 1 }
 
        hwXponOntPortVlanExtConfigPhyIndex OBJECT-TYPE
            SYNTAX      Integer32
            MAX-ACCESS  not-accessible
            STATUS      current
            DESCRIPTION
                "The ONT port ID."
            ::= { hwXponOntPortVlanExtConfigEntry 2 }        
            
        hwXponOntPortVlanConfigMode OBJECT-TYPE
            SYNTAX     INTEGER {
               extended(1),
               unconcern(3),
               invalid(-1)
            }
            MAX-ACCESS  read-write
            STATUS      current
            DESCRIPTION
                "This object is used to configure vlan config mode of ont port.
                 The configuration takes effect only when the ONT is in mode1 (interoperability mode).
                 Options:
                 1. extended(1)     - Indicates that the vlan config mode is extended mode
                 2. unconcern(3)    - Indicates that the vlan config mode is unconcern
                 3. invalid(-1)     - Indicates that the query fails or no information is detected
                 The default value is unconcern(3)
                "
            ::= { hwXponOntPortVlanExtConfigEntry 3 }
            
        hwXponOntPortVlanDownstreamOperMode OBJECT-TYPE
            SYNTAX    INTEGER 
            {
               transparentMatch(1),
               untagMatch(2),
               unconcern(3),
               invalid(-1)
            }
            MAX-ACCESS  read-write
            STATUS      current
            DESCRIPTION
                "This object is used to configure the vlan downstream operation mode of ont port.
                 The configuration takes effect only when the ONT is in mode1 (interoperability mode).
                 Options:
                 1. transparentMatch(1) - Indicates to process the VLAN tag of the downstream packets and transparent the packets with matched VLAN tag
                 2. untagMatch(2)       - Indicates to process the VLAN tag of the downstream packets and untag the packets with matched VLAN tag
                 3. unconcern(3)        - Indicates that the vlan downstream operation mode is unconcern
                 4. invalid(-1)         - Indicates that the query fails or no information is detected       
                 The default value is unconcern(3)     
                "
            ::= { hwXponOntPortVlanExtConfigEntry 4 }
            
  --Table hwXponOntPortVlanExtConfigTable end
  
  --Table hwXponOntPortVlanDiscardTable
        hwXponOntPortVlanDiscardTable OBJECT-TYPE
            SYNTAX  SEQUENCE OF HwXponOntPortVlanDiscardEntry
            MAX-ACCESS  not-accessible
            STATUS  current
            DESCRIPTION
                "This table is used to configure the vlan discard mode of ont port.
                 The indexes of this table are ifIndex, hwXponOntIndex, hwXponOntPortVlanDiscardPhyType and
                 hwXponOntPortVlanDiscardPhyIndex.
                "
            ::= { hwXponCommonControlObjects 36 }
  
        hwXponOntPortVlanDiscardEntry OBJECT-TYPE
            SYNTAX  HwXponOntPortVlanDiscardEntry
            MAX-ACCESS  not-accessible
            STATUS  current
            DESCRIPTION
                "This table is used to configure the vlan discard mode of ont port.
                 The indexes of this entry are ifIndex, hwXponOntIndex, hwXponOntPortVlanDiscardPhyType and
                 hwXponOntPortVlanDiscardPhyIndex.
                "
            INDEX  { ifIndex, hwXponOntIndex, hwXponOntPortVlanDiscardPhyType, hwXponOntPortVlanDiscardPhyIndex }
            ::= { hwXponOntPortVlanDiscardTable 1 }
  
        HwXponOntPortVlanDiscardEntry ::=
            SEQUENCE {
                hwXponOntPortVlanDiscardPhyType        INTEGER,
                hwXponOntPortVlanDiscardPhyIndex       Integer32,
                hwXponOntPortVlanDiscardMode           INTEGER
            } 
            
        hwXponOntPortVlanDiscardPhyType OBJECT-TYPE
            SYNTAX INTEGER {
               wifi(40),
               eth(47),
               iphost(50),
               ippath(61)
            }
            MAX-ACCESS  not-accessible
            STATUS      current
            DESCRIPTION
                "The ONT port type.
                 Options:
                 1. wifi(40)           - WiFi
                 2. eth(47)            - ETH
                 3. iphost(50)         - IPHOST
                 4. ippath(61)         - IPPATH
                "
            ::= { hwXponOntPortVlanDiscardEntry 1 }
 
        hwXponOntPortVlanDiscardPhyIndex OBJECT-TYPE
            SYNTAX      Integer32
            MAX-ACCESS  not-accessible
            STATUS      current
            DESCRIPTION
                "The ONT port ID."
            ::= { hwXponOntPortVlanDiscardEntry 2 }        
            
        hwXponOntPortVlanDiscardMode OBJECT-TYPE
            SYNTAX     INTEGER {
               untagged(1),
               tagged(2),
               none(3),
               unconcern(7),
               invalid(-1)
            }
            MAX-ACCESS  read-write
            STATUS      current
            DESCRIPTION
                "This object is used to configure vlan config mode of ont port.
                 The configuration takes effect only when the ONT is in mode1 (interoperability mode).
                 Options:
                 1. untagged(1)     - Indicates that the vlan discard mode is untagged
                 2. tagged(2)       - Indicates that the vlan discard mode is tagged
                 3. none(3)         - Indicates that the vlan discard mode is none
                 4. unconcern(7)    - Indicates that the vlan discard mode is unconcern
                 5. invalid(-1)     - Indicates that the query fails or no information is detected
                 The default value is unconcern(7)
                "
            ::= { hwXponOntPortVlanDiscardEntry 3 }
 
  --Table hwXponOntPortVlanDiscardTable end
  --Table hwGponBoardWorkModeTable
  
        hwGponBoardWorkModeTable OBJECT-TYPE
            SYNTAX  SEQUENCE OF HwGponBoardWorkModeEntry
            MAX-ACCESS  not-accessible
            STATUS  current
            DESCRIPTION
                "This table is used to configure the board work mode of GPON board.
                 The indexes of this table are hwFrameIndex and hwSlotIndex.
                "
            ::= { hwXponCommonControlObjects 37 }
  
        hwGponBoardWorkModeEntry OBJECT-TYPE
            SYNTAX  HwGponBoardWorkModeEntry
            MAX-ACCESS  not-accessible
            STATUS  current
            DESCRIPTION
                "This table is used to configure the board work mode of GPON board.
                 The indexes of this entry are hwFrameIndex and hwSlotIndex.
                "
            INDEX  { hwFrameIndex, hwSlotIndex }
            ::= { hwGponBoardWorkModeTable 1 }
  
        HwGponBoardWorkModeEntry ::=
            SEQUENCE {
                hwGponBoardWorkMode           INTEGER
            } 
            
        hwGponBoardWorkMode OBJECT-TYPE
            SYNTAX INTEGER {
               gpon(1),
               xgpon(2),
               xgspon(3),
               twdmpon(4),
               adapt(5),
               invalid(-1)
            }
            MAX-ACCESS  read-write
            STATUS      current
            DESCRIPTION
                "The GPON board work mode.
                 Options:
                 1. gpon(1)            - GPON work mode
                 2. xgpon(2)           - XGPON work mode
                 3. xgspon(3)          - XGSPON work mode
                 4. twdmpon(4)         - TWDMPON work mode
                 5. adapt(5)           - Adapt work mode
                 6. invalid(-1)        - Invalid work mode
                 Only board H901TWED/H902TWHD/H901FLHF can support to set board work mode currently.
                 The valid options of H901TWED/H902TWHD board are xgspon(3) and twdmpon(4), and the default value is xgspon(3).
                 The valid options of H901FLHF board are twdmpon(4) and adapt(5), and the default value is adapt(5).
                "
            ::= { hwGponBoardWorkModeEntry 1 } 
            
  --Table hwGponBoardWorkModeTable end                    
  
  --Table hwXponPortVsResourceTable
        hwXponPortVsResourceTable OBJECT-TYPE
            SYNTAX SEQUENCE OF HwXponPortVsResourceEntry
            MAX-ACCESS not-accessible
            STATUS     current
            DESCRIPTION
                "This table is used to config the resource about ports in virtual system.
                 The indexes of this table are ifIndex and hwXponPortVsId.
                "
            ::= { hwXponCommonControlObjects 38 }

        hwXponPortVsResourceEntry OBJECT-TYPE
            SYNTAX HwXponPortVsResourceEntry
            MAX-ACCESS not-accessible
            STATUS current
            DESCRIPTION
                "This table is used to config the resource about ports in virtual system.
                 The indexes of this entry are ifIndex and hwXponPortVsId.
                "
            INDEX       { ifIndex, hwXponPortVsId }
            ::= { hwXponPortVsResourceTable 1 }

        HwXponPortVsResourceEntry ::=
            SEQUENCE
                {
                hwXponPortVsId                      Integer32,
                hwXponPortVsMaxOntCount             Integer32,
                hwXponPortVsMaxGuaranteedBandwidth  Integer32,
                hwXponPortVsLeftGuaranteedBandwidth Integer32
                }

        hwXponPortVsId   OBJECT-TYPE
            SYNTAX Integer32
            MAX-ACCESS   not-accessible
            STATUS       current
            DESCRIPTION
                "This object indicates the indexes of virtual system,range: 1-3.
                 The invalid value is -1.
                "
            ::= { hwXponPortVsResourceEntry 1}
            
        hwXponPortVsMaxOntCount OBJECT-TYPE
            SYNTAX  Integer32
            MAX-ACCESS read-write
            STATUS current
            DESCRIPTION
                "This object indicates the maximum ONT number of port in virtual system,range: 1-256.
                 The default value is -1.
                 If the value of hwXponPortVsMaxOntCount is set to -1, the limitation will be canceled.
                "
          ::= { hwXponPortVsResourceEntry 2 }
          
        hwXponPortVsMaxGuaranteedBandwidth OBJECT-TYPE
            SYNTAX  Integer32
            UNITS   "kbps"
            MAX-ACCESS read-write
            STATUS current
            DESCRIPTION
                "This object indicates the maximum guaranteed bandwidth in virtual system, the value must be greater than or equal to 128 but cannot be larger than 10000000.
                 Unit: kbps
		 The default value is -1.
                 If the value of hwXponPortVsMaxGuaranteedBandwidth is set to -1, the limitation will be canceled.
                "
          ::= { hwXponPortVsResourceEntry 3 }
          
        hwXponPortVsLeftGuaranteedBandwidth OBJECT-TYPE
            SYNTAX  Integer32
            UNITS   "kbps"
            MAX-ACCESS read-only
            STATUS current
            DESCRIPTION
                "This object indicates the left guaranteed bandwidth of a PON port in virtual system.
                 Unit: kbps
		 The invalid value is -1.
                "
          ::= { hwXponPortVsResourceEntry 4 }
          
  --Table hwXponPortVsResourceTable end
  --Table hwGponTwdmChannelGroupTable
        hwGponTwdmChannelGroupTable OBJECT-TYPE
            SYNTAX SEQUENCE OF HwGponTwdmChannelGroupEntry 
            MAX-ACCESS not-accessible
            STATUS current
            DESCRIPTION
                "This table supports the TWDM PON channel group.
                 The index of this table is hwGponTwdmChannelGroupId.
                 "
            ::= { hwXponCommonControlObjects 39 }

        hwGponTwdmChannelGroupEntry OBJECT-TYPE
            SYNTAX HwGponTwdmChannelGroupEntry
            MAX-ACCESS not-accessible
            STATUS current
            DESCRIPTION
                "This table supports the TWDM PON channel group.
                 The index of this entry is hwGponTwdmChannelGroupId.
                "
            INDEX { hwGponTwdmChannelGroupId }
            ::= { hwGponTwdmChannelGroupTable 1 }
                
        HwGponTwdmChannelGroupEntry ::=
            SEQUENCE { 
                     hwGponTwdmChannelGroupId                       Integer32,
                     hwGponTwdmChannelGroupWorkMode                 INTEGER,
                     hwGponTwdmChannelGroupMaxChannelNumber         Integer32,                     
                     hwGponTwdmChannelGroupSelectPolicy             INTEGER,
                     hwGponTwdmChannelGroupState                    INTEGER,
                     hwGponTwdmChannelGroupDescription              OCTET STRING,
                     hwGponTwdmChannelGroupRowStatus                RowStatus
            }
            
        hwGponTwdmChannelGroupId OBJECT-TYPE
            SYNTAX     Integer32
	    MAX-ACCESS not-accessible
            STATUS current
            DESCRIPTION
                "This object indicates the ID number of channel group.              
                "
            ::= { hwGponTwdmChannelGroupEntry  1 }
            			
        hwGponTwdmChannelGroupWorkMode OBJECT-TYPE
            SYNTAX INTEGER {
                static(1),
                dynamic(2),
                invalid(-1)
            }
	    MAX-ACCESS read-write
            STATUS current
            DESCRIPTION
                "This object indicates the work mode of channel group.
                 Options:
                 1. static(1)              - static mode
                 2. dynamic(2)             - dynamic mode
                 3. invalid(-1)            - invalid value                 
                "
            ::= { hwGponTwdmChannelGroupEntry  2 }	
            
        hwGponTwdmChannelGroupMaxChannelNumber OBJECT-TYPE
            SYNTAX     Integer32(2..8)
	    MAX-ACCESS read-write
            STATUS current
            DESCRIPTION
                "This object indicates the maximum channel number of channel group,
                 and only can set value when create a channel group, the default value is 4.             
                "
            ::= { hwGponTwdmChannelGroupEntry  3 } 
            
        hwGponTwdmChannelGroupSelectPolicy OBJECT-TYPE
            SYNTAX INTEGER {
                payAsGrow(1),
                sharing(2),
                invalid(-1)
            }
	    MAX-ACCESS read-write
            STATUS current
            DESCRIPTION
                "This object indicates the policy of channel group.
                 Options:
                 1. payAsGrow(1)           - pay as grow
                 2. sharing(2)             - sharing
                 3. invalid(-1)            - invalid value                 
                "
            ::= { hwGponTwdmChannelGroupEntry  4 }                
            
        hwGponTwdmChannelGroupState OBJECT-TYPE
            SYNTAX INTEGER {
                online(1),
                offline(2),
                invalid(-1)
            }
	    MAX-ACCESS read-only
            STATUS current
            DESCRIPTION
                "This object indicates the state of channel group.
                 Options:
                 1. online(1)              - online
                 2. offline(2)             - offline
                 3. invalid(-1)            - invalid value                 
                "
            ::= { hwGponTwdmChannelGroupEntry  5 }        
            
        hwGponTwdmChannelGroupDescription OBJECT-TYPE
            SYNTAX      OCTET STRING (SIZE (0..128))
            MAX-ACCESS  read-write
            STATUS current
            DESCRIPTION
                "This object indicates the description of channel group.             
                "
            ::= { hwGponTwdmChannelGroupEntry  6 }    
            
        hwGponTwdmChannelGroupRowStatus OBJECT-TYPE
            SYNTAX        RowStatus
            MAX-ACCESS    read-create
            STATUS        current
            DESCRIPTION
                "Row status. This object is used to differentiate the
                 creation, modification and deletion operations for an object.
                 Options:
                 1. active(1)      -indicates that the conceptual row is available for use by the managed device
                 2. createAndGo(4) -create a new instance of a conceptual row 
                 3. destroy(6)     -delete the instances associated with an existing conceptual row
                "
            ::= { hwGponTwdmChannelGroupEntry  7 }                                                                                       		 			
  -- hwGponTwdmChannelGroupTable  end 
  
  --Table hwGponTwdmChannelMemberTable
        hwGponTwdmChannelMemberTable OBJECT-TYPE
            SYNTAX SEQUENCE OF HwGponTwdmChannelMemberEntry 
            MAX-ACCESS not-accessible
            STATUS current
            DESCRIPTION
                "This table supports the TWDM PON channel group member.
                 The indexes of this table are hwGponTwdmChannelGroupId, hwGponTwdmChannelMemberIndex.
                 "
            ::= { hwXponCommonControlObjects 40 }

        hwGponTwdmChannelMemberEntry OBJECT-TYPE
            SYNTAX HwGponTwdmChannelMemberEntry
            MAX-ACCESS not-accessible
            STATUS current
            DESCRIPTION
                "This table supports the TWDM PON channel group member.
                 The indexes of this entry are hwGponTwdmChannelGroupId, hwGponTwdmChannelMemberIndex.
                "
            INDEX { hwGponTwdmChannelGroupId, hwGponTwdmChannelMemberIndex }
            ::= { hwGponTwdmChannelMemberTable 1 }
                
        HwGponTwdmChannelMemberEntry ::=
            SEQUENCE { 
                     hwGponTwdmChannelMemberIndex                   Integer32,
                     hwGponTwdmChannelMemberRole                    INTEGER,
                     hwGponTwdmChannelMemberRowStatus               RowStatus
            }
            
        hwGponTwdmChannelMemberIndex OBJECT-TYPE
            SYNTAX     Integer32
	    MAX-ACCESS not-accessible
            STATUS current
            DESCRIPTION
                "This object indicates the index of channel group member.              
                "
            ::= { hwGponTwdmChannelMemberEntry  1 } 
         
        hwGponTwdmChannelMemberRole OBJECT-TYPE
            SYNTAX INTEGER {
                master(1),
                slave(2),
                invalid(-1)
            }
	    MAX-ACCESS read-write
            STATUS current
            DESCRIPTION
                "This object indicates the role of channel group member.
                 Options:
                 1. master(1)              - master
                 2. slave(2)               - slave
                 3. invalid(-1)            - invalid value                 
                "
            ::= { hwGponTwdmChannelMemberEntry  2 }        
            
        hwGponTwdmChannelMemberRowStatus OBJECT-TYPE
            SYNTAX        RowStatus
            MAX-ACCESS    read-create
            STATUS        current
            DESCRIPTION
                "Row status. This object is used to differentiate the
                 creation, modification and deletion operations for an object.
                 Options:
                 1. active(1)      -indicates that the conceptual row is available for use by the managed device
                 2. createAndGo(4) -create a new instance of a conceptual row 
                 3. destroy(6)     -delete the instances associated with an existing conceptual row
                "
            ::= { hwGponTwdmChannelMemberEntry  3 }           
  -- hwGponTwdmChannelMemberTable  end

  --Table hwXponPortChannelMaxRateInfoTable
        hwXponPortChannelMaxRateInfoTable OBJECT-TYPE
            SYNTAX SEQUENCE OF HwXponPortChannelMaxRateInfoEntry 
            MAX-ACCESS not-accessible
            STATUS current
            DESCRIPTION
                "This table supports to get the port second-level peak rate.
                 The indexes of this table are ifIndex, hwXponPortChannelIndex, hwXponPortChannelRateDirection.
                 "
            ::= { hwXponCommonControlObjects 41 }

        hwXponPortChannelMaxRateInfoEntry OBJECT-TYPE
            SYNTAX HwXponPortChannelMaxRateInfoEntry
            MAX-ACCESS not-accessible
            STATUS current
            DESCRIPTION
                "This table supports to get the port second-level peak rate.
                 The indexes of this entry are ifIndex, hwXponPortChannelIndex, hwXponPortChannelRateDirection.
                "
            INDEX { ifIndex, hwXponPortChannelIndex, hwXponPortChannelRateDirection }
            ::= { hwXponPortChannelMaxRateInfoTable 1 }
                
        HwXponPortChannelMaxRateInfoEntry ::=
            SEQUENCE { 
                     hwXponPortChannelIndex      Integer32,
                     hwXponPortChannelRateDirection     INTEGER,
                     hwXponPortChannelPhysicalRate      Integer32,
                     hwXponPortChannelMaxRate           Integer32,
                     hwXponPortChannelBandwidthUsage    Integer32,
                     hwXponPortChannelMaxTime           DateAndTime
            }
            
        hwXponPortChannelIndex OBJECT-TYPE
            SYNTAX     Integer32
	    MAX-ACCESS not-accessible
            STATUS current
            DESCRIPTION
                "This object indicates the index of channel, start from 0.              
                "
            ::= { hwXponPortChannelMaxRateInfoEntry  1 }
            			
        hwXponPortChannelRateDirection OBJECT-TYPE
            SYNTAX INTEGER {
                upstream(1),
                downstream(2),
                invalid(-1)
            }
	    MAX-ACCESS not-accessible
            STATUS current
            DESCRIPTION
                "This object indicates the direction of port rate.
                 Options:
                 1. upstream(1)         - upstream direction
                 2. downstream(2)       - downstream direction
                 3. invalid(-1)         - invalid value                 
                "
            ::= { hwXponPortChannelMaxRateInfoEntry  2 }	
                        
        hwXponPortChannelPhysicalRate OBJECT-TYPE
            SYNTAX  Integer32
            UNITS   "kbps"
            MAX-ACCESS read-only
            STATUS current
            DESCRIPTION
                "This object indicates the maximum rate of the corresponding channel.
                 Unit: kbps
		 The invalid value is -1.
                "
          ::= { hwXponPortChannelMaxRateInfoEntry 3 }    
                  
        hwXponPortChannelMaxRate OBJECT-TYPE
            SYNTAX  Integer32
            UNITS   "kbps"
            MAX-ACCESS read-only
            STATUS current
            DESCRIPTION
                "Indicates the peak rate at the second level within a collection period, in the unit of kbit/s.
		 The invalid value is -1.
                "
          ::= { hwXponPortChannelMaxRateInfoEntry 4 }                      

        hwXponPortChannelBandwidthUsage OBJECT-TYPE
            SYNTAX  Integer32 (-1 | 0..10000)
            MAX-ACCESS read-only
            STATUS current
            DESCRIPTION
                "Indicates the bandwidth usage corresponding to peak rate at the second level, units of 0.01%.
		 The invalid value is -1.
                "
          ::= { hwXponPortChannelMaxRateInfoEntry 5 }  
                 
        hwXponPortChannelMaxTime OBJECT-TYPE
            SYNTAX     DateAndTime
            MAX-ACCESS  read-only
            STATUS     current
            DESCRIPTION
                "Indicates the moment when rate at the second level reaches the peak value.
                 Format: xxxx (year)-xx(month)-xx(day) xx(hour):xx(min):xx(second)+time zone, character string type.
		 The format is as follows:
		 2000-03-12 11:59:14+08:00
		 A null character string is returned when this leaf is not supported."
            ::= { hwXponPortChannelMaxRateInfoEntry 6 }  
  -- hwXponPortChannelMaxRateInfoTable  end

  --  Table hwXponDeviceOntPotsPortStateTable
        hwXponDeviceOntPotsPortStateTable OBJECT-TYPE
            SYNTAX SEQUENCE OF HwXponDeviceOntPotsPortStateEntry
            MAX-ACCESS not-accessible
            STATUS current
            DESCRIPTION
                "This table is used to query the state of ONT POTS port.
                 The indexes of this table are ifIndex, hwXponOntIndex and hwXponDeviceOntPotsPortId.
                "
            ::= { hwXponCommonControlObjects 42 }
            
        hwXponDeviceOntPotsPortStateEntry OBJECT-TYPE
            SYNTAX HwXponDeviceOntPotsPortStateEntry
            MAX-ACCESS not-accessible
            STATUS current
            DESCRIPTION
                "This table is used to query the state of ONT POTS port.
                 The indexes of this entry are ifIndex, hwXponOntIndex and hwXponDeviceOntPotsPortId.
                "
            INDEX { ifIndex, hwXponOntIndex, hwXponDeviceOntPotsPortId}
            ::= { hwXponDeviceOntPotsPortStateTable 1 }
            
        HwXponDeviceOntPotsPortStateEntry ::=
            SEQUENCE {
            hwXponDeviceOntPotsPortId                                  Integer32,
            hwXponDeviceOntPotsPortPTPSrvState                         INTEGER,
            hwXponDeviceOntPotsPortPTPAdminState                       INTEGER, 
            hwXponDeviceOntPotsPortPTPHookState                        INTEGER,
            hwXponDeviceOntPotsPortCTPSrvState                         INTEGER,
            hwXponDeviceOntPotsPortCTPSrvType                          INTEGER,
            hwXponDeviceOntPotsPortCTPSrvCode                          INTEGER
            }
            
         hwXponDeviceOntPotsPortId OBJECT-TYPE
            SYNTAX      Integer32
            MAX-ACCESS  not-accessible
            STATUS      current
            DESCRIPTION
                "ONT POTS port ID."
            ::= { hwXponDeviceOntPotsPortStateEntry  1 }
            
         hwXponDeviceOntPotsPortPTPSrvState OBJECT-TYPE
            SYNTAX      INTEGER
                {
                normal (1),
                fail (2),
                invalidState (-1)
                }
            MAX-ACCESS  read-only
            STATUS      current
             DESCRIPTION
                "ONT POTS port physics running state.
                 Options:
                 1. normal(1)        - Normal state
                 2. fail(2)          - Fail state
                 3. invalidState(-1) - Returned in case of query failure or error
                "
            ::= { hwXponDeviceOntPotsPortStateEntry  2 }
            
         hwXponDeviceOntPotsPortPTPAdminState OBJECT-TYPE
            SYNTAX      INTEGER
                {
                lock (1),
                unlock (2),
                shutDown (3),
                invalidState (-1)
                }
            MAX-ACCESS  read-only
            STATUS      current
            DESCRIPTION
                "ONT POTS port physics admin state.
                 Options:
                 1. lock(1)           - All user functions of this circuit pack are blocked, and alarm for this managed entity
                                       are no longer generated
                 2. unlock(2)         - Unlock state, all user functions of this circuit pack are normal
                 3. shutDown(3)       - POTS UNI administrative state is shutdown
                 4. invalidState(-1)  - This value is return when can't query or have some errors in query
                "
            ::= { hwXponDeviceOntPotsPortStateEntry  3 }
            
         hwXponDeviceOntPotsPortPTPHookState OBJECT-TYPE
            SYNTAX      INTEGER
                {
                onHook (1),
                offHook (2),
                invalidState (-1)
                }
            MAX-ACCESS  read-only
            STATUS      current
            DESCRIPTION
                   "ONT POTS port physics hook state.
                    Options:
                    1. onHook(1)        - ONT POTS port physics is onHook
                    2. offHook(2)       - ONT POTS port physics is offHook
                    3. invalidState(-1) - Returned in case of query failure or error
                   "
            ::= { hwXponDeviceOntPotsPortStateEntry  4 }
            
         hwXponDeviceOntPotsPortCTPSrvState OBJECT-TYPE
            SYNTAX      INTEGER
                {
                noneOrinitial (1),
                registered (2),
                inSession (3),
                failedRegistration (4),
                failedInvite (5),
                portNotconfigured (6),
                configDone (7),
                failedRegistrationBecauseOfIcmpError(8),
                failedRegistrationBecauseOfFailedTcp(9),
                failedRegistrationBecauseOfFailedAuthentication(10),
                failedRegistrationBecauseOfTimeout(11),
                failedRegistrationBecauseOfServerFailCode(12),
                failedInviteBecauseOfIcmpError(13),
                failedInviteBecauseOfFailedTcp(14),
                failedInviteBecauseOfFailedAuthentication(15),
                failedInviteBecauseOfTimeout(16),
                failedInviteBecauseOfServerFailCode(17),
                disabledBySwitch(18),
                endLocal(19),
                endRemote(20) ,
                endAuto(21) ,
                normal(22),
                invalidState (-1)
                }
            MAX-ACCESS  read-only
            STATUS      current
            DESCRIPTION
                "ONT POTS port service running state.
                 Options:
                 1. noneOrinitial(1)      - None or initial state
                 2. registered(2)         - Registered state
                 3. inSession(3)          - In session
                 4. failedRegistration(4) - Failed in registration
                 5. failedInvite(5)       - Failed in invite
                 6. portNotconfigured(6)  - Port doesn't configure
                 7. configDone(7)         - Config has been done
                 8. failedRegistrationBecauseOfIcmpError(8)      - Failed in registration because of ICMP errors
                 9. failedRegistrationBecauseOfFailedTcp(9)      - Failed in registration because of TCP errors
                 10. failedRegistrationBecauseOfFailedAuthentication(10)      - Failed in registration because of authentication failure
                 11. failedRegistrationBecauseOfTimeout(11)      - Failed in registration because of timeout
                 12. failedRegistrationBecauseOfServerFailCode(12)      - Failed in registration because of server errors
                 13. failedInviteBecauseOfIcmpError(13)      - Failed to initiate a session because of ICMP errors
                 14. failedInviteBecauseOfFailedTcp(14)      - Failed to initiate a session because of TCP errors
                 15. failedInviteBecauseOfFailedAuthentication(15)      - Failed to initiate a session because of authentication failure
                 16. failedInviteBecauseOfTimeout(16)      - Failed to initiate a session because of timeout
                 17. failedInviteBecauseOfServerFailCode(17)      - Failed to initiate a session because of server errors
                 18. disabledBySwitch(18)      - The service port is prohibited by the call server
                 19. endLocal(19)      - Services are terminated at local because the user disables the port
                 20. endRemote(20)      - Services are terminated at the remote end because the MGC issues commands
                 21. endAuto(21)      - Services are terminated automatically because of MGC faults
                 22. normal(22)      - Services are normal
                 23. invalidState(-1)      - Returned in case of query failure or error
                "
            ::= { hwXponDeviceOntPotsPortStateEntry  5 }
            
         hwXponDeviceOntPotsPortCTPSrvType OBJECT-TYPE
            SYNTAX   INTEGER
                {
                idleOrnone (1),
                twoWay (2),
                threeWay (3),
                fax (4),
                telem (5),
                conference (6),
                invalidType (-1)
                }
            MAX-ACCESS  read-only
            STATUS      current
            DESCRIPTION
                "ONT POTS port service type.
                 Options:
                 1. idleOrnone(1)       - Idle or none type
                 2. twoWay(2)           - Two way type
                 3. threeWay(3)         - Three way type
                 4. fax(4)              - Fax type
                 5. telem(5)            - Telem type
                 6. conference(6)       - Conference type
                 7. invalidType(-1)     - Invalid type
                "
            ::= { hwXponDeviceOntPotsPortStateEntry  6 }
            
         hwXponDeviceOntPotsPortCTPSrvCode OBJECT-TYPE
            SYNTAX      INTEGER
                {
                pcmu (1),
                reserved1 (2),
                reserved2 (3),
                gsm (4),
                g723 (5),
                dvi4ClockRate8000 (6),
                dvi4ClockRate16000 (7),
                lpc (8),
                pcma (9),
                g722 (10),
                l16TwoChannels  (11),
                l16OneChannel (12),
                qcelp (13),
                cn (14),
                mpa (15),
                g728 (16),
                dvi4ClockRate11025 (17),
                dvi4ClockRate22050 (18),
                g729 (19),
                t38(20),
                g711a(21),
                g711u(22),
                g726(23),
                invalidCode (-1)
                }
            MAX-ACCESS  read-only
            STATUS      current
            DESCRIPTION
                "ONT POTS port code mode.
                 Options:
                 1.  pcmu(1)                - Audio data is encoded as eight bits per sample, after logarithmic scaling PCMU denotes mu-law scaling.
                 2.  reserved1(2)           - Reserved.
                 3.  reserved2(3)           - Reserved.
                 4.  gsm(4)                 - GSM denotes the European GSM 06.10 standard for full-rate
                                            - speech transcoding, ETS 300 961, which is based on RPE/LTP (residual pulse
                                            - excitation/long term prediction) coding at a rate of 13 kb/.
                 5.  g723(5)                - Dual-rate speech coder for multimedia communications transmitting at 5.3 and 6.3 kbit/s.
                 6.  dvi4ClockRate8000(6)   - DVI4 uses an adaptive delta pulse code modulation (ADPCM) encoding scheme that was
                                            - specified by the Interactive Multimedia Association (IMA) as the IMA ADPCM wave type,
                                            - and the clock rate is 8000HZ.
                 7.  dvi4ClockRate16000(7)  - DVI4 uses an adaptive delta pulse code modulation (ADPCM) encoding scheme that was
                                            - specified by the Interactive Multimedia Association (IMA) as the IMA ADPCM wave type, and the clock rate is 16000HZ.
                 8.  lpc(8)                 - LPC designates an experimental linear predictive encoding contributed by Ron Frederick,
                                            - which is based on an implementation written by Ron Zuckerman posted to the Usenet group comp.
                 9.  pcma(9)                - Audio data is encoded as eight bits per sample, after logarithmic scaling. PCMA denotes A-law scaling.
                 10. g722(10)               - 7 kHz audio-coding within 64 kbit/s.
                 11. l16TwoChannels(11)     - Two channel encoding.
                 12. l16OneChannel(12)      - One channel encoding.
                 13. qcelp(13)              - QCELP CODEC compresses each 20 milliseconds of 8,000 Hz.
                 14. cn(14)                 - Comfort Noise.
                 15. mpa(15)                - MPA denotes MPEG-1 or MPEG-2 audio encapsulated as elementary streams.
                 16. g728(16)               - Coding of speech at 16 kbit/s using low-delay code excited linear prediction.
                 17. dvi4ClockRate11025(17) - DVI4 uses an adaptive delta pulse code modulation (ADPCM) encoding scheme that was specified
                                            - by the Interactive Multimedia Association (IMA) as the IMA ADPCM wave type, and the clock rate is 11025HZ.
                 18. dvi4ClockRate22050(18) - DVI4 uses an adaptive delta pulse code modulation (ADPCM) encoding  scheme that was specified
                                            - by the Interactive Multimedia Association (IMA) as the IMA ADPCM wave type, and the clock rate is 11025HZ.
                 19. g729(19)               - Coding of speech at 8 kbit/s using conjugate structure-algebraic code excited linear prediction.
                 20. t38(20)                - T.38 is used by the IFP peer to verify message alignment. It is identified by an ASN.1 Application tag.
                 21. g711a(21),             - G.711A.
                 22. g711u(22),             - G.711U.
                 23. g726(23),              - G.726.
                 24. invalidCode(-1)        - Invalid code.
                "
            ::= { hwXponDeviceOntPotsPortStateEntry  7 }
            
  --hwXponDeviceOntPotsPortStateTable end

  --Table hwGponPortConfigInfoTable
        hwGponPortConfigInfoTable OBJECT-TYPE
            SYNTAX     SEQUENCE OF HwGponPortConfigInfoEntry
            MAX-ACCESS not-accessible
            STATUS     current
            DESCRIPTION
                "The hwGponPortConfigInfoTable is used to query the information about ports.
                 The index of this table is ifIndex.
                "
            ::= { hwXponCommonControlObjects 43 }

        hwGponPortConfigInfoEntry OBJECT-TYPE
            SYNTAX     HwGponPortConfigInfoEntry
            MAX-ACCESS not-accessible
            STATUS     current
            DESCRIPTION
                "The hwGponPortConfigInfoTable is used to query the information about ports.
                 The index of this entry is ifIndex.
                "
            INDEX       { ifIndex }
            ::= { hwGponPortConfigInfoTable 1 }

        HwGponPortConfigInfoEntry  ::=
            SEQUENCE
                {
                hwGponPortConfigInfoLeftBwFor2dot5G      Integer32,
                hwGponPortConfigInfoLeftBwFor10G         Integer32
                }    
                        
        hwGponPortConfigInfoLeftBwFor2dot5G OBJECT-TYPE
            SYNTAX  Integer32
            MAX-ACCESS  read-only
            STATUS  current
            DESCRIPTION
                "This object indicates the remaining bandwidth of the XGS-PON port or the combo PON port for the ONT with upstream rate 2.5 Gbps. Unit:kbps.
                 The value (-1) indicates that the query fails or no information is detected.
                "
            ::= { hwGponPortConfigInfoEntry 1 }
        
        hwGponPortConfigInfoLeftBwFor10G OBJECT-TYPE
            SYNTAX  Integer32
            MAX-ACCESS  read-only
            STATUS  current
            DESCRIPTION
                "This object indicates the remaining bandwidth of the XGS-PON port or the combo PON port for the ONT with upstream rate 10 Gbps. Unit:kbps.
                 The value (-1) indicates that the query fails or no information is detected.
                "
            ::= { hwGponPortConfigInfoEntry 2 }
  --Table hwGponPortConfigInfoTable end
  
 --Table hwXponOntAutoPingTable
        hwXponOntAutoPingTable OBJECT-TYPE
            SYNTAX SEQUENCE OF HwXponOntAutoPingEntry
            MAX-ACCESS not-accessible
            STATUS     current
            DESCRIPTION
                "The hwXponOntAutoPingTable is used to start ont auto ping test and query result.
                 The indexes of this table are ifIndex and hwXponOntIndex.
                "
            ::= { hwXponCommonControlObjects 44 }

        hwXponOntAutoPingEntry OBJECT-TYPE
            SYNTAX HwXponOntAutoPingEntry
            MAX-ACCESS not-accessible
            STATUS current
            DESCRIPTION
                "The hwXponOntAutoPingTable is used to start ont auto ping test and query result.
                 The indexes of this Entry are ifIndex and hwXponOntIndex.
                "
            INDEX     { ifIndex, hwXponOntIndex }
            ::= { hwXponOntAutoPingTable 1 }

        HwXponOntAutoPingEntry ::=
            SEQUENCE
            {
            hwXponOntAutoPingStart                      INTEGER,
            hwXponOntAutoPingResultCode                 INTEGER,
            hwXponOntAutoPingResultContent         OCTET STRING,
            hwXponOntAutoPingClearResult                INTEGER
            }

        hwXponOntAutoPingStart OBJECT-TYPE
            SYNTAX      INTEGER
	    {
            start(1),
            invalid(-1)
            }
            MAX-ACCESS  read-write
            STATUS      current
            DESCRIPTION
                "The object is used to start the ont auto ping test.
                 options:
                 1.start(1)       - Starts the ont auto ping test.
                 2.invalid(-1)    - Indicates that no information is detected.
                 "
            ::= { hwXponOntAutoPingEntry 1 }

        hwXponOntAutoPingResultCode OBJECT-TYPE
            SYNTAX      INTEGER
	        {
	        success(0),
	        offline(1),
	        notsupport(2),
	        onterror(3),
	        nowan(4),
	        invalid(-1)
	        }
            MAX-ACCESS  read-only
            STATUS      current
            DESCRIPTION
                "Indicates the result of ont auto ping test.
                 Options:
                 1.success(0)       - Indicates the ont auto ping test complete.
                 2.offline(1)       - Indicates the ont is not online. 
                 3.notsupport(2)    - Indicates the ont doesn't support this operation.
                 4.onterror(3)      - Indicates the ont process error.
                 5.nowan(4)         - Indicates that no wan ports exist on the ont.
                 6.invalid(-1)      - Indicates that no information is detected.
                "
            ::= { hwXponOntAutoPingEntry 2 }

       hwXponOntAutoPingResultContent OBJECT-TYPE
            SYNTAX     OCTET STRING (SIZE(0..800)) 
            MAX-ACCESS read-only
            STATUS     current
            DESCRIPTION
                "This object indicates the information about ont auto ping results.
                 This object consists of type, length, WAN name, IPv4 connection status, IPv4 ping result for gateway,
                 IPv4 ping result for DNS, IPv6 connection status, IPv6 ping result for gateway, IPv6 ping result for DNS.  
                 The format of this object is as follows:
                 --------------------------------------------------------------------------------------
                 |field          |field length |                  field description                   |
                 --------------------------------------------------------------------------------------
                 |type           |1            |1: type  1                                            |  
                 --------------------------------------------------------------------------------------
                 |len            |2            |total length of the following content                 |    
                 --------------------------------------------------------------------------------------
                 |WAN name       |32           |WAN name                                              | 
                 --------------------------------------------------------------------------------------
                 |IPv4 Connection|1            |IPv4 status      0:unconfigured                       |
                 |Status         |             |Description:     1:connecting                         | 
                 |               |             |                 2:connected                          |
                 |               |             |                 3:pending                            |
                 |               |             |                 4:disconnecting                      |
                 |               |             |                 5:disconnected                       |
                 --------------------------------------------------------------------------------------                 
                 |IPv6 Connection|1            |IPv6 status      0:invalid                            |
                 |Status         |             |Description:     1:connecting                         |
                 |               |             |                 2:connected                          |
                 |               |             |                 3:pending                            |
                 |               |             |                 4:disconnecting                      |
                 |               |             |                 5:disconnected                       |
                 |               |             |                 6:unknown                            |             
                 -------------------------------------------------------------------------------------- 
                 | IPv4 ping     |1            |ping  gateway    0:success                            |
                 | result for    |             |result           1:fail                               |
                 | gateway       |             |Description:     2:not support                        |
                 -------------------------------------------------------------------------------------- 
                 | IPv6 ping     |1            |ping  gateway    0:success                            |
                 | result for    |             |result           1:fail                               |
                 | gateway       |             |Description:     2:not support                        |          
                 --------------------------------------------------------------------------------------
                 | IPv4 ping     |1            |ping  DNS        0:success                            |
                 | result for    |             |result           1:fail                               |
                 | DNS           |             |Description:     2:not support                        |
                 -------------------------------------------------------------------------------------- 
                 | IPv6 ping     |1            |ping  DNS        0:success                            |
                 | result for    |             |result           1:fail                               |
                 | DNS           |             |Description:     2:not support                        |
                 --------------------------------------------------------------------------------------
                "
            ::= { hwXponOntAutoPingEntry  3 }
        hwXponOntAutoPingClearResult OBJECT-TYPE
            SYNTAX      INTEGER
            {
            clear(1),
            invalid(-1)
            }
            MAX-ACCESS  read-write
            STATUS      current 
            DESCRIPTION
                "The object is used to clear the ont auto ping test.
                Options:
                1.clear(1)        - Clear ont auto ping test result.
                2.invalid(-1)     - Indicates the invalid value.               
                "
            ::= { hwXponOntAutoPingEntry 4 }

  --hwXponOntAutoPingTable end 
  
  --Table hwXponPortAutoPingTable
   hwXponPortAutoPingTable OBJECT-TYPE
            SYNTAX SEQUENCE OF HwXponPortAutoPingEntry
            MAX-ACCESS not-accessible
            STATUS     current
            DESCRIPTION
                "The hwXponPortAutoPingTable is used to start auto ping test for all onts under port.
                 The indexes of this table are ifIndex.
                "
            ::= { hwXponCommonControlObjects 45 }

        hwXponPortAutoPingEntry OBJECT-TYPE
            SYNTAX HwXponPortAutoPingEntry
            MAX-ACCESS not-accessible
            STATUS current
            DESCRIPTION
                "The hwXponPortAutoPingTable is used to start auto ping test for all onts under port.
                 The indexes of this Entry are ifIndex.
                "
            INDEX       { ifIndex }
            ::= { hwXponPortAutoPingTable 1 }

        HwXponPortAutoPingEntry ::=
            SEQUENCE
            {
     		hwXponPortAutoPingStart        INTEGER,
     		hwXponPortAutoPingClearResult  INTEGER
            } 
				           
        hwXponPortAutoPingStart OBJECT-TYPE
            SYNTAX      INTEGER
	    {
            start(1),
            invalid(-1)
            }
	    MAX-ACCESS  read-write
            STATUS      current 
            DESCRIPTION
                "The object is used to start the port auto ping test.
                options:
                1.start(1)        - Starts the port auto ping test.
                2.invalid(-1)     - Indicates that no information is detected.               
                "
            ::= { hwXponPortAutoPingEntry 1 }
        hwXponPortAutoPingClearResult OBJECT-TYPE
            SYNTAX      INTEGER
            {
            clear(1),
            invalid(-1)
            }
	    MAX-ACCESS  read-write
            STATUS      current 
            DESCRIPTION
                "The object is used to clear the port auto ping test.
                Options:
                1.clear(1)        - Clear port auto ping test result.
                2.invalid(-1)     - Indicates the invalid value.               
                "
            ::= { hwXponPortAutoPingEntry 2 }

  --hwXponPortAutoPingTable end

  --Table hwXponDeviceGetOntInfoByAuthInfoTable
        hwXponDeviceGetOntInfoByAuthInfoTable OBJECT-TYPE
            SYNTAX  SEQUENCE OF HwXponDeviceGetOntInfoByAuthInfoEntry
            MAX-ACCESS  not-accessible
            STATUS  current
            DESCRIPTION
                "This table is used to get ONT information by ONT authentication information.
                 If multiple ONTs match authentication information, only the first one is obtained.
                 The indexes of this table are hwXponDeviceOntAuthMethod and hwXponDeviceOntAuthInfo.
                "
            ::= { hwXponCommonControlObjects 46 }
  
        hwXponDeviceGetOntInfoByAuthInfoEntry OBJECT-TYPE
            SYNTAX  HwXponDeviceGetOntInfoByAuthInfoEntry
            MAX-ACCESS  not-accessible
            STATUS  current
            DESCRIPTION
                "This table is used to get ONT information by ONT authentication information.
                 If multiple ONTs match authentication information, only the first one is obtained.
                 The indexes of this entry are hwXponDeviceOntAuthMethod and hwXponDeviceOntAuthInfo.
                "
            INDEX  { hwXponDeviceOntAuthMethod, hwXponDeviceOntAuthInfo }
            ::= { hwXponDeviceGetOntInfoByAuthInfoTable 1 }
  
        HwXponDeviceGetOntInfoByAuthInfoEntry ::=
            SEQUENCE
                {
                hwXponDeviceOntAuthMethod                 INTEGER,
                hwXponDeviceOntAuthInfo                   OCTET STRING,
                hwXponDeviceGetOntIfindex                 Integer32,
                hwXponDeviceGetOntIndex                   Integer32
                }
                
        hwXponDeviceOntAuthMethod OBJECT-TYPE
            SYNTAX INTEGER 
            {
                password(1)
            }
            MAX-ACCESS    not-accessible
            STATUS      current
            DESCRIPTION
                "This object indicates the ONT authentication mode.
                 Options:
                 1. password(1) - The ONT authentication type is password
                "
            ::= { hwXponDeviceGetOntInfoByAuthInfoEntry 1 }

        hwXponDeviceOntAuthInfo  OBJECT-TYPE
            SYNTAX OCTET STRING (SIZE (1..36))
            MAX-ACCESS   not-accessible
            STATUS       current
            DESCRIPTION
                "This object indicates the ONT authentication information."
            ::= { hwXponDeviceGetOntInfoByAuthInfoEntry 2 }

        hwXponDeviceGetOntIfindex OBJECT-TYPE
            SYNTAX      Integer32
            MAX-ACCESS  read-only
            STATUS      current
            DESCRIPTION
                "This object is the ifindex of the ONT.
                "
            ::= { hwXponDeviceGetOntInfoByAuthInfoEntry 3 }

        hwXponDeviceGetOntIndex OBJECT-TYPE
            SYNTAX      Integer32
            MAX-ACCESS  read-only
            STATUS      current
            DESCRIPTION
                "This object is the index of the ONT.
                "
            ::= { hwXponDeviceGetOntInfoByAuthInfoEntry 4 }
                        
  --Table hwXponDeviceGetOntInfoByAuthInfoTable end
  
  --Table hwXponOntOpticalDdmInfoHistoryTable
       hwXponOntOpticalDdmInfoHistoryTable OBJECT-TYPE
            SYNTAX SEQUENCE OF HwXponOntOpticalDdmInfoHistoryEntry
            MAX-ACCESS not-accessible
            STATUS current
            DESCRIPTION
                "This table is the ont optical Ddm infomation history.
                 The indexes of this table are ifIndex hwXponOntIndex and hwXponOntOpticalDdmInfoRecordIndex.
                "
            ::= { hwXponCommonControlObjects 47 }
            
        hwXponOntOpticalDdmInfoHistoryEntry OBJECT-TYPE
            SYNTAX HwXponOntOpticalDdmInfoHistoryEntry
            MAX-ACCESS not-accessible
            STATUS current
            DESCRIPTION
                "This table is the ont optical Ddm infomation history.
                 The indexes of this table are ifIndex hwXponOntIndex and hwXponOntOpticalDdmInfoRecordIndex.
                "
            INDEX { ifIndex, hwXponOntIndex, hwXponOntOpticalDdmInfoRecordIndex }
            ::= { hwXponOntOpticalDdmInfoHistoryTable 1 }
            
        HwXponOntOpticalDdmInfoHistoryEntry ::=
            SEQUENCE {
                hwXponOntOpticalDdmInfoRecordIndex                           Integer32,
                hwXponOntOpticalDdmInfoRecordStartTime                       DateAndTime,
                hwXponOntOpticalDdmInfoRecordEndTime                         DateAndTime, 
                hwXponOntOpticalDdmOntRxPowerMax                             Integer32,
                hwXponOntOpticalDdmOntRxPowerMin                             Integer32,
                hwXponOntOpticalDdmOltRxPowerMax                             Integer32,
                hwXponOntOpticalDdmOltRxPowerMin                             Integer32
            }

	 hwXponOntOpticalDdmInfoRecordIndex OBJECT-TYPE
            SYNTAX      Integer32 (0..23)
            MAX-ACCESS  not-accessible
            STATUS      current
            DESCRIPTION
                "ONT optical Ddm infomation ID."
            ::= { hwXponOntOpticalDdmInfoHistoryEntry  1 }
	 
	 hwXponOntOpticalDdmInfoRecordStartTime OBJECT-TYPE
            SYNTAX      DateAndTime
            MAX-ACCESS  read-only
            STATUS      current
            DESCRIPTION
                "The start time for ONT optical info .
                "
            ::= { hwXponOntOpticalDdmInfoHistoryEntry  2 }
	    
	 hwXponOntOpticalDdmInfoRecordEndTime OBJECT-TYPE
            SYNTAX      DateAndTime
            MAX-ACCESS  read-only
            STATUS      current
            DESCRIPTION
                "The end time for ONT optical info .
                "
            ::= { hwXponOntOpticalDdmInfoHistoryEntry  3 }
	    
	 hwXponOntOpticalDdmOntRxPowerMax OBJECT-TYPE
            SYNTAX      Integer32
	    UNITS       "0.01dBm"
            MAX-ACCESS  read-only
            STATUS      current
            DESCRIPTION
                "The max receiving power of the optical module, unit 0.01dBm.
                "
            ::= { hwXponOntOpticalDdmInfoHistoryEntry  4 }
	    
	 hwXponOntOpticalDdmOntRxPowerMin OBJECT-TYPE
            SYNTAX      Integer32
	    UNITS       "0.01dBm"
            MAX-ACCESS  read-only
            STATUS      current
            DESCRIPTION
                "The min receiving power of the optical module, unit 0.01dBm.
                "
            ::= { hwXponOntOpticalDdmInfoHistoryEntry  5 }
	    
	 hwXponOntOpticalDdmOltRxPowerMax OBJECT-TYPE
            SYNTAX      Integer32
	    UNITS       "0.01dBm"
            MAX-ACCESS  read-only
            STATUS      current
            DESCRIPTION
                "The max ONT optical power received on the OLT, unit 0.01dBm.
                "
            ::= { hwXponOntOpticalDdmInfoHistoryEntry  6 }
     
     hwXponOntOpticalDdmOltRxPowerMin OBJECT-TYPE
            SYNTAX      Integer32
	    UNITS       "0.01dBm"
            MAX-ACCESS  read-only
            STATUS      current
            DESCRIPTION
                "The min ONT optical power received on the OLT, unit 0.01dBm.
                "
            ::= { hwXponOntOpticalDdmInfoHistoryEntry  7 }
	    
  --hwXponOntEthernetPortOpticalDdmInfoTable end            

  --Table hwXponPortOpticConfigTable
        hwXponPortOpticConfigTable OBJECT-TYPE
            SYNTAX SEQUENCE OF HwXponPortOpticConfigEntry
            MAX-ACCESS not-accessible
            STATUS     current
            DESCRIPTION
                "This table is used to configure the optical module information state.
                 The index of this table is ifIndex. 
                "
            ::= { hwXponCommonControlObjects 48 }

        hwXponPortOpticConfigEntry OBJECT-TYPE
            SYNTAX HwXponPortOpticConfigEntry
            MAX-ACCESS not-accessible
            STATUS     current
            DESCRIPTION
                "This table is used to configure the optical module information state.
                 The index of this entry is ifIndex. 
                "
            INDEX       { ifIndex }
            ::= { hwXponPortOpticConfigTable 1 }
            
        HwXponPortOpticConfigEntry ::=
            SEQUENCE {
                hwXponPortOpticVenderIDInfo  OCTET STRING,
                hwXponPortOpticVenderSNInfo  OCTET STRING,
                hwXponPortOpticState      INTEGER
                }
                            
        hwXponPortOpticVenderIDInfo  OBJECT-TYPE
            SYNTAX OCTET STRING (SIZE (1..4))
            MAX-ACCESS read-write
            STATUS       current
            DESCRIPTION
                "This object indicates the vender ID of the optical module.
                "
            ::= { hwXponPortOpticConfigEntry 1 }
            
        hwXponPortOpticVenderSNInfo  OBJECT-TYPE 
            SYNTAX OCTET STRING (SIZE (1..16))
            MAX-ACCESS   read-write
            STATUS       current
            DESCRIPTION
                " This object indicates the vender SN of the optical module.
                "
            ::= { hwXponPortOpticConfigEntry 2 }
            
        hwXponPortOpticState      OBJECT-TYPE
            SYNTAX INTEGER
                {
                normal(1),
                conflict(2)
                }
            MAX-ACCESS read-write
            STATUS current
            DESCRIPTION
                "The state of optical module.
                 Options:
                 1. normal(1)	- The optical module information state is normal
                 2. conflict(2)	- The optical module information state is conflict
                "
            ::= { hwXponPortOpticConfigEntry 3 }
  --Table hwXponPortOpticConfigTable end
  
  --Table hwXponPortOpticListTable
        hwXponPortOpticListTable OBJECT-TYPE
            SYNTAX  SEQUENCE OF HwXponPortOpticListEntry
            MAX-ACCESS  not-accessible
            STATUS  current
            DESCRIPTION
                "This table is used to get optical module list.
                 The indexe of this table is hwXponPortOpticListType.
                "
            ::= { hwXponCommonControlObjects 49 }
  
        hwXponPortOpticListEntry OBJECT-TYPE
            SYNTAX  HwXponPortOpticListEntry
            MAX-ACCESS  not-accessible
            STATUS  current
            DESCRIPTION
                " This table is used to get optical module list.
                 The indexe of this table is hwXponPortOpticListType.
                "
            INDEX  { hwXponPortOpticListType }
            ::= { hwXponPortOpticListTable 1 }
  
        HwXponPortOpticListEntry::=
            SEQUENCE
                {
                hwXponPortOpticListType  INTEGER,
                hwXponPortOpticListNum   Integer32,
                hwXponPortOpticList      OCTET STRING
                }
                
        hwXponPortOpticListType OBJECT-TYPE
            SYNTAX INTEGER 
            {
                normal(1)
            }
            MAX-ACCESS    not-accessible
            STATUS      current
            DESCRIPTION
                "This object indicates the optical module list mode.
                 Options:
                 1. normal(1) - The optical module list mode is normal
                "
            ::= { hwXponPortOpticListEntry 1 }

        hwXponPortOpticListNum  OBJECT-TYPE
            SYNTAX      Integer32
            MAX-ACCESS  read-only
            STATUS      current
            DESCRIPTION
                "This object is the number of the optical module list."
            ::= { hwXponPortOpticListEntry 2 }

        hwXponPortOpticList      OBJECT-TYPE
            SYNTAX OCTET STRING (SIZE (0..8192))
            MAX-ACCESS  read-only
            STATUS      current
            DESCRIPTION
                "This object is the optical module list, and each optical module takes 20 bytes, include 
                 venderID(4 bytes), venderSN(16 bytes) and the most number of optical module is 256.
                "
            ::= { hwXponPortOpticListEntry 3 }
 
  --Table hwXponPortOpticListTable end
    --Table hwGponBoardFlexLicenseTable
	   hwGponBoardFlexLicenseTable OBJECT-TYPE
		   SYNTAX     SEQUENCE OF HwGponBoardFlexLicenseEntry
		   MAX-ACCESS not-accessible
		   STATUS     current
		   DESCRIPTION
			   "Indicates the flex license info of the board.
				The index of this table is hwFrameIndex and hwSlotIndex."
		   ::= { hwXponCommonControlObjects 50 }
	   
	   hwGponBoardFlexLicenseEntry OBJECT-TYPE
		   SYNTAX     HwGponBoardFlexLicenseEntry
		   MAX-ACCESS not-accessible
		   STATUS     current
		   DESCRIPTION
			   "Indicates the flex license info of the board.
				The index of this entry is  hwFrameIndex and hwSlotIndex."
		   INDEX { hwFrameIndex, hwSlotIndex }
		   ::= { hwGponBoardFlexLicenseTable 1 }
	   
	   HwGponBoardFlexLicenseEntry ::= 
		  SEQUENCE {
		   hwXponBoardFlexLvl1PortLicenseNum   Unsigned32,                                 
		   hwXponBoardFlexLvl2PortLicenseNum   Unsigned32,
		   hwXponBoardFlexLvl3PortLicenseNum   Unsigned32
	   }  

       hwXponBoardFlexLvl1PortLicenseNum OBJECT-TYPE
				SYNTAX Unsigned32          
				MAX-ACCESS read-only
				STATUS current			
				DESCRIPTION
				"
   				Indicates the number of flex2.0 pon ports board Gpon mode. 
   				"
         		::= { hwGponBoardFlexLicenseEntry  1 }    
         
       hwXponBoardFlexLvl2PortLicenseNum OBJECT-TYPE
				SYNTAX Unsigned32          
				MAX-ACCESS read-only
				STATUS current			
				DESCRIPTION
				"
   				Indicates the number of flex2.0 pon ports board 10G Gpon(XG/XGS/Combo) mode. 
   				"
         		::= { hwGponBoardFlexLicenseEntry  2 }
         
       hwXponBoardFlexLvl3PortLicenseNum OBJECT-TYPE
				SYNTAX Unsigned32          
				MAX-ACCESS read-only
				STATUS current			
				DESCRIPTION
				"
   				 Indicates the number of flex2.0 pon board using TWDM PON mode. 
   				"
         		::= { hwGponBoardFlexLicenseEntry  3 }

  --hwGponBoardFlexLicenseTable end 

    --Table hwXponOntDIDOTable
        hwXponOntDIDOTable OBJECT-TYPE
            SYNTAX     SEQUENCE OF HwXponOntDIDOEntry
            MAX-ACCESS not-accessible
            STATUS     current
            DESCRIPTION
                "Indicates the DI/DO state of the ONT and control the switch of the ONT DI Trap Reporting.
                 The index of this table is ifIndex and hwXponOntIndex.
                "
            ::= { hwXponCommonControlObjects 51 }

        hwXponOntDIDOEntry OBJECT-TYPE
            SYNTAX     HwXponOntDIDOEntry
            MAX-ACCESS not-accessible
            STATUS     current
            DESCRIPTION
                "Indicates the DI/DO state of the ONT and control the switch of the ONT DI Trap Reporting.
                 The index of this entry is  ifIndex and hwXponOntIndex.
                "
            INDEX { ifIndex,  hwXponOntIndex }
            ::= { hwXponOntDIDOTable 1 }

        HwXponOntDIDOEntry ::=
            SEQUENCE {
            hwXponOntDITrapSwitch   INTEGER,
            hwXponOntDIState   OCTET STRING,
            hwXponOntDOState   OCTET STRING
            }

        hwXponOntDITrapSwitch OBJECT-TYPE
            SYNTAX INTEGER
            {
                enable(1),
                disable(2),
                invalid(-1)
            }
            MAX-ACCESS read-write
            STATUS current
            DESCRIPTION
            "
            The switch value of ONT DI Trap Reporting.
            Options:
            1. enable(1)         - The switch value of ONT DI Trap Reporting is enable.
            2. disable(2)        - The switch value of ONT DI Trap Reporting is disable.
            3. invalid(-1)        - Indicates that the query fails or no information is detected.
            The default value is enable(1).
            "
            ::= { hwXponOntDIDOEntry  1 }

        hwXponOntDIState OBJECT-TYPE
            SYNTAX OCTET STRING (SIZE (0..255))
            MAX-ACCESS read-only
            STATUS current
            DESCRIPTION
            "
            When query the ONT DI status, returns the status of all DI ports at a time.
            The first byte indicates the number of ports (0~127).
            Each two byte indicates the state of a port, with the first byte indicating the port index and the second byte indicating the DI state.
            Port index (1 Byte);
            Port status (1 Byte): 0- low level, 1- high level. 
            "
            ::= { hwXponOntDIDOEntry  2 }

        hwXponOntDOState OBJECT-TYPE
            SYNTAX OCTET STRING (SIZE (0..255))
            MAX-ACCESS read-only
            STATUS current
            DESCRIPTION
            "
            When query the ONT DO status, returns the status of all DO ports at a time.
            The first byte indicates the number of ports (0~127). 
            Each two byte indicates the state of a port, with the first byte indicating the port index and the second byte indicating the DO state.
            Port index (1 Byte);
            Port status (1 Byte): 0- low level, 1- high level.
            "
           ::= { hwXponOntDIDOEntry  3 }
    --hwXponOntDIDOTable end

  --Table hwGponDevicePotsPortStatisticTable
        hwGponDevicePotsPortStatisticTable OBJECT-TYPE
            SYNTAX      SEQUENCE OF HwGponDevicePotsPortStatisticEntry
            MAX-ACCESS  not-accessible
            STATUS      current
            DESCRIPTION
                "VOIP perform monitor statistic table. This table is used to query Pots
                 port statistic.
                 The indexes of this table are ifIndex, hwGponDeviceOntObjIndex and
                 hwGponDeviceOntPhyIndex.
                "
            ::= { hwXponCommonStatisticObjects 1 }

        hwGponDevicePotsPortStatisticEntry OBJECT-TYPE
            SYNTAX      HwGponDevicePotsPortStatisticEntry
            MAX-ACCESS  not-accessible
            STATUS      current
            DESCRIPTION
                "VOIP perform monitor statistic table. This table is used to query Pots
                 port statistic.
                 The indexes of this entry are ifIndex, hwGponDeviceOntObjIndex and
                 hwGponDeviceOntPhyIndex.
                "
            INDEX
                {
                ifIndex,
                hwGponDeviceOntObjIndex,
                hwGponDeviceOntPhyIndex
                }
            ::= { hwGponDevicePotsPortStatisticTable 1 }

        HwGponDevicePotsPortStatisticEntry ::=
            SEQUENCE
                {
                hwGponDeviceOntPhyIndex                       Integer32,
                hwGponDevicePotsStatisticRtpError             Gauge32,
                hwGponDevicePotsStatisticPacketLoss           Gauge32,
                hwGponDevicePotsPortMaxJitter                 Gauge32,
                hwGponDevicePotsPortMaxTimeRTCP               Gauge32,
                hwGponDevicePotsStatisticUnderFlowBuff        Gauge32,
                hwGponDevicePotsStatisticOverFlowBuff         Gauge32,
                hwGponDevicePotsStatisticCallSetupFails       Gauge32,
                hwGponDevicePotsPortCallSetupTimer            Gauge32,
                hwGponDevicePotsStatisticCallTerminateFails   Gauge32,
                hwGponDevicePotsStatisticAnalogPortRelease    Gauge32,
                hwGponDevicePotsPortAnalogPortOffHookTimer    Gauge32
                }

        hwGponDeviceOntPhyIndex OBJECT-TYPE
            SYNTAX      Integer32
            MAX-ACCESS  not-accessible
            STATUS      current
            DESCRIPTION
                "Port index of the ONT."
            ::={ hwGponDevicePotsPortStatisticEntry 1 }

        hwGponDevicePotsStatisticRtpError OBJECT-TYPE
            SYNTAX      Gauge32
            MAX-ACCESS  read-only
            STATUS      current
            DESCRIPTION
                "The statistic of RTP packet errors."
            ::={ hwGponDevicePotsPortStatisticEntry 2 }

        hwGponDevicePotsStatisticPacketLoss OBJECT-TYPE
            SYNTAX      Gauge32
            MAX-ACCESS  read-only
            STATUS      current
            DESCRIPTION
                "The statistic of the fraction of packets lost."
            ::={ hwGponDevicePotsPortStatisticEntry 3 }

        hwGponDevicePotsPortMaxJitter OBJECT-TYPE
            SYNTAX      Gauge32
            MAX-ACCESS  read-only
            STATUS      current
            DESCRIPTION
                "The maximum jitter identified during the measured interval."
            ::={ hwGponDevicePotsPortStatisticEntry 4 }

        hwGponDevicePotsPortMaxTimeRTCP OBJECT-TYPE
            SYNTAX      Gauge32
            MAX-ACCESS  read-only
            STATUS      current
            DESCRIPTION
                "The maximum time between RTCP packets."
            ::={ hwGponDevicePotsPortStatisticEntry 5 }

        hwGponDevicePotsStatisticUnderFlowBuff OBJECT-TYPE
            SYNTAX      Gauge32
            MAX-ACCESS  read-only
            STATUS      current
            DESCRIPTION
                "The statistic of times the reassembly buffer underflows."
            ::={ hwGponDevicePotsPortStatisticEntry 6 }

        hwGponDevicePotsStatisticOverFlowBuff OBJECT-TYPE
            SYNTAX      Gauge32
            MAX-ACCESS  read-only
            STATUS      current
            DESCRIPTION
                "The statistic of times the reassembly buffer overflows."
            ::={ hwGponDevicePotsPortStatisticEntry 7 }

        hwGponDevicePotsStatisticCallSetupFails OBJECT-TYPE
            SYNTAX      Gauge32
            MAX-ACCESS  read-only
            STATUS      current
            DESCRIPTION
                "The statistic of call setup failures."
            ::={ hwGponDevicePotsPortStatisticEntry 8}

        hwGponDevicePotsPortCallSetupTimer OBJECT-TYPE
            SYNTAX      Gauge32
            MAX-ACCESS  read-only
            STATUS      current
            DESCRIPTION
                "The longest duration of a single call setup detected during this interval."
            ::={ hwGponDevicePotsPortStatisticEntry 9 }

        hwGponDevicePotsStatisticCallTerminateFails OBJECT-TYPE
            SYNTAX      Gauge32
            MAX-ACCESS  read-only
            STATUS      current
            DESCRIPTION
                "The statistic of calls that were terminated with cause."
            ::={ hwGponDevicePotsPortStatisticEntry 10 }

        hwGponDevicePotsStatisticAnalogPortRelease OBJECT-TYPE
            SYNTAX      Gauge32
            MAX-ACCESS  read-only
            STATUS      current
            DESCRIPTION
                "The statistic of analog port releases without dialling detected."
            ::={ hwGponDevicePotsPortStatisticEntry 11 }

        hwGponDevicePotsPortAnalogPortOffHookTimer OBJECT-TYPE
            SYNTAX      Gauge32
            MAX-ACCESS  read-only
            STATUS      current
            DESCRIPTION
                "The longest period of a single off-hook detected on the analog port."
            ::={ hwGponDevicePotsPortStatisticEntry 12 }

  --Table hwGponOntPerfCurr15MinDataTable
        hwGponOntPerfCurr15MinDataTable OBJECT-TYPE
            SYNTAX      SEQUENCE OF HwGponOntPerfCurr15MinDataEntry
            MAX-ACCESS  not-accessible
            STATUS      current
            DESCRIPTION
                "Ont performance monitor statistic table. This table is used to query ont
                 statistic in the current 15 minutes. The indexes of this table are 
                 ifIndex and hwXponOntIndex.
                "
            ::= { hwXponCommonStatisticObjects 2 }

        hwGponOntPerfCurr15MinDataEntry OBJECT-TYPE
            SYNTAX      HwGponOntPerfCurr15MinDataEntry
            MAX-ACCESS  not-accessible
            STATUS      current
            DESCRIPTION
                "Ont performance monitor statistic table. This table is used to query ont 
                 statistic in the current 15 minutes. The indexes of this entry are 
                 ifIndex and hwXponOntIndex.
                "
            INDEX
                {
                ifIndex,
                hwXponOntIndex
                }
            ::= { hwGponOntPerfCurr15MinDataTable 1 }

        HwGponOntPerfCurr15MinDataEntry ::=
            SEQUENCE
                {
                hwGponOntPerfCurr15MinFecCorrectByte            Integer32,
                hwGponOntPerfCurr15MinFecCorrectCodeWords       Integer32,
                hwGponOntPerfCurr15MinFecUncorrectCodeWords     Integer32,
                hwGponOntPerfCurr15MinFecTotalCodeWords         Integer32,
                hwGponOntPerfCurr15MinFecSeconds                Integer32,
                hwGponOntPerfCurr15MinRangingTimeCount          Counter64,
                hwGponOntPerfCurr15MinTransmittedGemFrames      Counter64,
                hwGponOntPerfCurr15MinXgemKeyErrorCount         Counter64,
                hwGponOntPerfCurr15MinXgemHecErrorCount         Counter64 
                }

        hwGponOntPerfCurr15MinFecCorrectByte OBJECT-TYPE
            SYNTAX      Integer32
            MAX-ACCESS  read-only
            STATUS      current
            DESCRIPTION
                "Count of bytes that were corrected by 
                the FEC function in the current 15 minutes."
            ::={ hwGponOntPerfCurr15MinDataEntry 1 }

        hwGponOntPerfCurr15MinFecCorrectCodeWords OBJECT-TYPE
            SYNTAX      Integer32
            MAX-ACCESS  read-only
            STATUS      current
            DESCRIPTION
                "Count of code words that were corrected by the FEC 
                function in the current 15 minutes."
            ::={ hwGponOntPerfCurr15MinDataEntry 2 }

        hwGponOntPerfCurr15MinFecUncorrectCodeWords OBJECT-TYPE
            SYNTAX      Integer32
            MAX-ACCESS  read-only
            STATUS      current
            DESCRIPTION
                "Count of code words that were not corrected by the FEC function 
                in the current 15 minutes."
            ::={ hwGponOntPerfCurr15MinDataEntry 3 }

        hwGponOntPerfCurr15MinFecTotalCodeWords  OBJECT-TYPE
            SYNTAX      Integer32
            MAX-ACCESS  read-only
            STATUS      current
            DESCRIPTION
                "Count of total received code words in the current 15 minutes."
            ::={ hwGponOntPerfCurr15MinDataEntry 4 }

        hwGponOntPerfCurr15MinFecSeconds OBJECT-TYPE
            SYNTAX      Integer32
            MAX-ACCESS  read-only
            STATUS      current
            DESCRIPTION
                "Count of seconds in the current 15 minutes, when there 
                was a forward error correction anomaly."
            ::={ hwGponOntPerfCurr15MinDataEntry 5 }   
            
        hwGponOntPerfCurr15MinRangingTimeCount OBJECT-TYPE
            SYNTAX      Counter64
            MAX-ACCESS  read-only
            STATUS      current
            DESCRIPTION
                "Count of rangingtime in the current 15 minutes."
            ::={ hwGponOntPerfCurr15MinDataEntry 6 }
            
        hwGponOntPerfCurr15MinTransmittedGemFrames OBJECT-TYPE
            SYNTAX      Counter64
            MAX-ACCESS  read-only
            STATUS      current
            DESCRIPTION
                "Count of transmitted XGEM frames in the current 15 minutes."
            ::={ hwGponOntPerfCurr15MinDataEntry 7 }
            
        hwGponOntPerfCurr15MinXgemKeyErrorCount OBJECT-TYPE
            SYNTAX      Counter64
            MAX-ACCESS  read-only
            STATUS      current
            DESCRIPTION
                "Count of XGEM key errors in the current 15 minutes."
            ::={ hwGponOntPerfCurr15MinDataEntry 8 }   
            
        hwGponOntPerfCurr15MinXgemHecErrorCount OBJECT-TYPE
            SYNTAX      Counter64
            MAX-ACCESS  read-only
            STATUS      current
            DESCRIPTION
                "Count of XGEM hec error in the current 15 minutes."
            ::={ hwGponOntPerfCurr15MinDataEntry 9 }

  --Table hwGponOntPerfHis15MinTable
        hwGponOntPerfHis15MinTable OBJECT-TYPE
            SYNTAX      SEQUENCE OF HwGponOntPerfHis15MinEntry
            MAX-ACCESS  not-accessible
            STATUS      current
            DESCRIPTION
                "Ont performance monitor statistic table. This table is used to query ont
                 statistic. The indexes of this table are ifIndex, hwXponOntIndex and 
                 hwGponOntPerfHis15MinNumber.
                "
            ::= { hwXponCommonStatisticObjects 3 }

        hwGponOntPerfHis15MinEntry OBJECT-TYPE
            SYNTAX      HwGponOntPerfHis15MinEntry
            MAX-ACCESS  not-accessible
            STATUS      current
            DESCRIPTION
                "Ont performance monitor statistic table. This table is used to query ont 
                 statistic. The indexes of this entry are ifIndex,hwXponOntIndex and 
                 hwGponOntPerfHis15MinNumber.
                "
            INDEX
                {
                ifIndex,
                hwXponOntIndex,
                hwGponOntPerfHis15MinNumber
                }
            ::= { hwGponOntPerfHis15MinTable 1 }

        HwGponOntPerfHis15MinEntry ::=
            SEQUENCE
                {     
                hwGponOntPerfHis15MinNumber                     Unsigned32,
                hwGponOntPerfHis15MinFecCorrectByte             Integer32,
                hwGponOntPerfHis15MinFecCorrectCodeWords        Integer32,
                hwGponOntPerfHis15MinFecUncorrectCodeWords      Integer32,
                hwGponOntPerfHis15MinFecTotalCodeWords          Integer32,
                hwGponOntPerfHis15MinFecSeconds                 Integer32,
                hwGponOntPerfHis15MinRangingTimeCount           Counter64,
                hwGponOntPerfHis15MinTransmittedGemFrames       Counter64,
                hwGponOntPerfHis15MinXgemKeyErrorCount          Counter64,
                hwGponOntPerfHis15MinXgemHecErrorCount          Counter64
                                }        

        hwGponOntPerfHis15MinNumber OBJECT-TYPE
            SYNTAX      Unsigned32 (1)
            MAX-ACCESS  not-accessible
            STATUS      current
            DESCRIPTION
                "Performance data interval number 1 is the most recent previous 
                15 minutes interval. Rang:1."
            ::={ hwGponOntPerfHis15MinEntry 1 }
            
        hwGponOntPerfHis15MinFecCorrectByte OBJECT-TYPE
            SYNTAX      Integer32
            MAX-ACCESS  read-only
            STATUS      current
            DESCRIPTION
                "Count of bytes that were corrected by 
                the FEC function in this interval."
            ::={ hwGponOntPerfHis15MinEntry 2 }

        hwGponOntPerfHis15MinFecCorrectCodeWords OBJECT-TYPE
            SYNTAX      Integer32
            MAX-ACCESS  read-only
            STATUS      current
            DESCRIPTION
                "Count of code words that were corrected by the FEC 
                 function in this interval.
                 -1 indicates the invalid value.
                "
            ::={ hwGponOntPerfHis15MinEntry 3 }

        hwGponOntPerfHis15MinFecUncorrectCodeWords OBJECT-TYPE
            SYNTAX      Integer32
            MAX-ACCESS  read-only
            STATUS      current
            DESCRIPTION
                "Count of code words that were not corrected by the FEC 
                function in this interval.
                -1 indicates the invalid value.
                "
            ::={ hwGponOntPerfHis15MinEntry 4}

        hwGponOntPerfHis15MinFecTotalCodeWords OBJECT-TYPE
            SYNTAX      Integer32
            MAX-ACCESS  read-only
            STATUS      current
            DESCRIPTION
                "Count of total received code words in this interval.
                 -1 indicates the invalid value.
                "
            ::={ hwGponOntPerfHis15MinEntry 5 }

        hwGponOntPerfHis15MinFecSeconds OBJECT-TYPE
            SYNTAX      Integer32
            MAX-ACCESS  read-only
            STATUS      current
            DESCRIPTION
                "Count of seconds during this interval, when there 
                was a forward error correction anomaly."
            ::={ hwGponOntPerfHis15MinEntry 6 }   
            
        hwGponOntPerfHis15MinRangingTimeCount OBJECT-TYPE
            SYNTAX      Counter64
            MAX-ACCESS  read-only
            STATUS      current
            DESCRIPTION
                "Count of rangingtime in this interval."
            ::={ hwGponOntPerfHis15MinEntry 7 }
            
        hwGponOntPerfHis15MinTransmittedGemFrames OBJECT-TYPE
            SYNTAX      Counter64
            MAX-ACCESS  read-only
            STATUS      current
            DESCRIPTION
                "Count of transmitted XGEM frames in this interval."
            ::={ hwGponOntPerfHis15MinEntry 8 }
            
        hwGponOntPerfHis15MinXgemKeyErrorCount OBJECT-TYPE
            SYNTAX      Counter64
            MAX-ACCESS  read-only
            STATUS      current
            DESCRIPTION
                "Count of XGEM key errors in this interval."
            ::={ hwGponOntPerfHis15MinEntry 9 }   
            
        hwGponOntPerfHis15MinXgemHecErrorCount OBJECT-TYPE
            SYNTAX      Counter64
            MAX-ACCESS  read-only
            STATUS      current
            DESCRIPTION
                "Count of XGEM hec error in this interval."
            ::={ hwGponOntPerfHis15MinEntry 10 }
            
       --Table hwGponOntIphostStatsTable
        hwGponOntIphostStatsTable OBJECT-TYPE
            SYNTAX      SEQUENCE OF HwGponOntIphostStatsEntry
            MAX-ACCESS  not-accessible
            STATUS      current
            DESCRIPTION
                "The ONT IPHOST port statistics table.
                 The index of this table is a combination of ifIndex,
                 hwGponDeviceOntObjIndex.
                "
            ::= { hwXponCommonStatisticObjects 4 }
            
        hwGponOntIphostStatsEntry OBJECT-TYPE
            SYNTAX      HwGponOntIphostStatsEntry
            MAX-ACCESS  not-accessible
            STATUS      current
            DESCRIPTION
                "The ONT IPHOST port statistics table.
                 The index of this entry is a combination of ifIndex,
                 hwGponDeviceOntObjIndex.
                "
            INDEX
                {
                ifIndex,
                hwGponDeviceOntObjIndex
                }
            ::= { hwGponOntIphostStatsTable 1 }

        HwGponOntIphostStatsEntry ::=
            SEQUENCE
                {     
                hwGponOntIphostEthernetStatisticRecvOctets                    Counter64,
                hwGponOntIphostEthernetStatisticRecvPkts                      Counter64,
                hwGponOntIphostEthernetStatisticRecvMulticastPkts             Counter64,
                hwGponOntIphostEthernetStatisticRecvBroadcastPkts             Counter64,                                              
                hwGponOntIphostEthernetStatisticRecvPkts64Octets              Counter64,
                hwGponOntIphostEthernetStatisticRecvPkts65to127Octets         Counter64,
                hwGponOntIphostEthernetStatisticRecvPkts128to255Octets        Counter64,
                hwGponOntIphostEthernetStatisticRecvPkts256to511Octets        Counter64,
                hwGponOntIphostEthernetStatisticRecvPkts512to1023Octets       Counter64,
                hwGponOntIphostEthernetStatisticRecvPkts1024to1518Octets      Counter64,
                hwGponOntIphostEthernetStatisticRecvPktsOversize              Counter64,
                hwGponOntIphostEthernetStatisticRecvPktsUndersize             Counter64,
                hwGponOntIphostEthernetStatisticRecvFCSErrors                 Counter64,
                hwGponOntIphostEthernetStatisticRecvDropEvents                Counter64,                                         
                hwGponOntIphostEthernetStatisticSendOctets                    Counter64,
                hwGponOntIphostEthernetStatisticSendPkts                      Counter64,
                hwGponOntIphostEthernetStatisticMulticastSendPkts             Counter64,
                hwGponOntIphostEthernetStatisticSendBroadcastPkts             Counter64,                                           
                hwGponOntIphostEthernetStatisticSendPkts64Octets              Counter64,
                hwGponOntIphostEthernetStatisticSendPkts65to127Octets         Counter64,
                hwGponOntIphostEthernetStatisticSendPkts128to255Octets        Counter64,
                hwGponOntIphostEthernetStatisticSendPkts256to511Octets        Counter64,
                hwGponOntIphostEthernetStatisticSendPkts512to1023Octets       Counter64,
                hwGponOntIphostEthernetStatisticSendPkts1024to1518Octets      Counter64,
                hwGponOntIphostEthernetStatisticSendPktsOversize              Counter64,
                hwGponOntIphostEthernetStatisticForwardDropEvents             Counter64,
                hwGponOntIphostEthernetStatisticClear                         INTEGER
                }    
                    
       hwGponOntIphostEthernetStatisticRecvOctets OBJECT-TYPE
            SYNTAX Counter64
            MAX-ACCESS read-only
            STATUS current
            DESCRIPTION
                "This object indicates the received bytes."
            ::= { hwGponOntIphostStatsEntry 1 }
            
        hwGponOntIphostEthernetStatisticRecvPkts OBJECT-TYPE
            SYNTAX Counter64
            MAX-ACCESS read-only
            STATUS current
            DESCRIPTION
                "This object indicates the received frames."
            ::= { hwGponOntIphostStatsEntry 2 }   
      
       hwGponOntIphostEthernetStatisticRecvMulticastPkts OBJECT-TYPE
            SYNTAX Counter64
            MAX-ACCESS read-only
            STATUS current
            DESCRIPTION
                "This object indicates the received multicast frames."
            ::= { hwGponOntIphostStatsEntry 3 }
            
       hwGponOntIphostEthernetStatisticRecvBroadcastPkts OBJECT-TYPE
            SYNTAX Counter64
            MAX-ACCESS read-only
            STATUS current
            DESCRIPTION
                "This object indicates the received broadcast frames."
            ::= { hwGponOntIphostStatsEntry 4 }
            
         hwGponOntIphostEthernetStatisticRecvPkts64Octets OBJECT-TYPE
            SYNTAX Counter64
            MAX-ACCESS read-only
            STATUS current
            DESCRIPTION
                "This object indicates the received 64-octet frames"
            ::= { hwGponOntIphostStatsEntry 5 }  
            
      hwGponOntIphostEthernetStatisticRecvPkts65to127Octets OBJECT-TYPE
            SYNTAX Counter64
            MAX-ACCESS read-only
            STATUS current
            DESCRIPTION
                "This object indicates the received 65~127-octet frames"
            ::= { hwGponOntIphostStatsEntry 6 }

      hwGponOntIphostEthernetStatisticRecvPkts128to255Octets OBJECT-TYPE
            SYNTAX Counter64
            MAX-ACCESS read-only
            STATUS current
            DESCRIPTION
                "This object indicates the received 128~255-octet frames"
            ::= { hwGponOntIphostStatsEntry 7 }

        hwGponOntIphostEthernetStatisticRecvPkts256to511Octets OBJECT-TYPE
            SYNTAX Counter64
            MAX-ACCESS read-only
            STATUS current
            DESCRIPTION
                "This object indicates the received 256~511-octet frames."
            ::= { hwGponOntIphostStatsEntry 8 }

        hwGponOntIphostEthernetStatisticRecvPkts512to1023Octets OBJECT-TYPE
            SYNTAX Counter64
            MAX-ACCESS read-only
            STATUS current
            DESCRIPTION
                "This object indicates the received 512~1023-octet frames."
            ::= { hwGponOntIphostStatsEntry 9 }

        hwGponOntIphostEthernetStatisticRecvPkts1024to1518Octets OBJECT-TYPE
            SYNTAX Counter64
            MAX-ACCESS read-only
            STATUS current
            DESCRIPTION
                "This object indicates the received 1024~1518-octet frames."
            ::= { hwGponOntIphostStatsEntry 10 }
            
        hwGponOntIphostEthernetStatisticRecvPktsOversize OBJECT-TYPE
            SYNTAX Counter64
            MAX-ACCESS read-only
            STATUS current
            DESCRIPTION
                "This object indicates the received oversize frames."
            ::= { hwGponOntIphostStatsEntry 11 }

         hwGponOntIphostEthernetStatisticRecvPktsUndersize OBJECT-TYPE
            SYNTAX Counter64
            MAX-ACCESS read-only
            STATUS current
            DESCRIPTION
                "This object indicates the received undersize frames."
            ::= { hwGponOntIphostStatsEntry 12 }
          
          hwGponOntIphostEthernetStatisticRecvFCSErrors  OBJECT-TYPE
            SYNTAX Counter64
            MAX-ACCESS read-only
            STATUS current
            DESCRIPTION
                "This object indicates the received FCS error frames."
            ::= { hwGponOntIphostStatsEntry 13 }
            
          hwGponOntIphostEthernetStatisticRecvDropEvents  OBJECT-TYPE
            SYNTAX Counter64
            MAX-ACCESS read-only
            STATUS current
            DESCRIPTION
                "This object indicates the received drop events."
            ::= { hwGponOntIphostStatsEntry 14 }
            
            hwGponOntIphostEthernetStatisticSendOctets OBJECT-TYPE
            SYNTAX Counter64
            MAX-ACCESS read-only
            STATUS current
            DESCRIPTION
                "This object indicates the sent bytes."
            ::= { hwGponOntIphostStatsEntry 15 }

        hwGponOntIphostEthernetStatisticSendPkts OBJECT-TYPE
            SYNTAX Counter64
            MAX-ACCESS read-only
            STATUS current
            DESCRIPTION
                "This object indicates the sent frames."
            ::= { hwGponOntIphostStatsEntry 16 }
        
        hwGponOntIphostEthernetStatisticMulticastSendPkts OBJECT-TYPE
            SYNTAX Counter64
            MAX-ACCESS read-only
            STATUS current
            DESCRIPTION
                "This object indicates the sent multicast frames."
            ::= { hwGponOntIphostStatsEntry 17 }
            
       hwGponOntIphostEthernetStatisticSendBroadcastPkts OBJECT-TYPE
            SYNTAX Counter64
            MAX-ACCESS read-only
            STATUS current
            DESCRIPTION
                "This object indicates the sent broadcast frames."
            ::= { hwGponOntIphostStatsEntry 18 }
            
          hwGponOntIphostEthernetStatisticSendPkts64Octets OBJECT-TYPE
            SYNTAX Counter64
            MAX-ACCESS read-only
            STATUS current
            DESCRIPTION
                "This object indicates the sent 64-octet frames"
            ::= { hwGponOntIphostStatsEntry 19 }

        hwGponOntIphostEthernetStatisticSendPkts65to127Octets OBJECT-TYPE
            SYNTAX Counter64
            MAX-ACCESS read-only
            STATUS current
            DESCRIPTION
                "This object indicates the sent 65~127-octet frames"
            ::= { hwGponOntIphostStatsEntry 20 }

        hwGponOntIphostEthernetStatisticSendPkts128to255Octets OBJECT-TYPE
            SYNTAX Counter64
            MAX-ACCESS read-only
            STATUS current
            DESCRIPTION
                "This object indicates the sent 128~255-octet frames"
            ::= { hwGponOntIphostStatsEntry 21 }

        hwGponOntIphostEthernetStatisticSendPkts256to511Octets OBJECT-TYPE
            SYNTAX Counter64
            MAX-ACCESS read-only
            STATUS current
            DESCRIPTION
                "This object indicates the sent 256~511-octet frames."
            ::= { hwGponOntIphostStatsEntry 22 }

        hwGponOntIphostEthernetStatisticSendPkts512to1023Octets OBJECT-TYPE
            SYNTAX Counter64
            MAX-ACCESS read-only
            STATUS current
            DESCRIPTION
                "This object indicates the sent 512~1023-octet frames."
            ::= { hwGponOntIphostStatsEntry 23}

         hwGponOntIphostEthernetStatisticSendPkts1024to1518Octets OBJECT-TYPE
            SYNTAX Counter64
            MAX-ACCESS read-only
            STATUS current
            DESCRIPTION
                "This object indicates the sent 1024~1518-octet frames."
            ::= { hwGponOntIphostStatsEntry 24 }
            
        hwGponOntIphostEthernetStatisticSendPktsOversize OBJECT-TYPE
            SYNTAX Counter64
            MAX-ACCESS read-only
            STATUS current
            DESCRIPTION
                "This object indicates the sent oversize frames."
            ::= { hwGponOntIphostStatsEntry 25 }
  
        hwGponOntIphostEthernetStatisticForwardDropEvents OBJECT-TYPE
            SYNTAX Counter64
            MAX-ACCESS read-only
            STATUS current
            DESCRIPTION
                "This object indicates the sent drop events."
            ::= { hwGponOntIphostStatsEntry 26}           
        
        hwGponOntIphostEthernetStatisticClear  OBJECT-TYPE
            SYNTAX INTEGER{
                clear(1),
                invalid(-1)
            }
            MAX-ACCESS read-write
            STATUS current
            DESCRIPTION
                "This object is used to clear the statistics.
                 Options:
                 1. clear(1)                     - Indicates that clear the statistics
                 2. invalid(-1)                 - Indicates that the query fails or no information is detected
                "
            ::= { hwGponOntIphostStatsEntry 60 }           

  --Table hwGponOntPerfEverbeforeDataTable
        hwGponOntPerfEverbeforeDataTable OBJECT-TYPE
            SYNTAX      SEQUENCE OF HwGponOntPerfEverbeforeDataEntry
            MAX-ACCESS  not-accessible
            STATUS      current
            DESCRIPTION
                "Ont performance monitor statistic table. This table is used to query ont 
                 ever before statistic. 
                 The indexes of this table are a combination of ifIndex and hwXponOntIndex.
                " 
             ::= { hwXponCommonStatisticObjects 5 }

        hwGponOntPerfEverbeforeDataEntry OBJECT-TYPE
            SYNTAX      HwGponOntPerfEverbeforeDataEntry
            MAX-ACCESS  not-accessible
            STATUS      current
            DESCRIPTION
                "Ont performance monitor statistic table. This table is used to query ont 
                 ever before statistic. 
                 The indexes of this entry are a combination of ifIndex and hwXponOntIndex.
                " 
            INDEX
                {
                ifIndex,
                hwXponOntIndex
                }
            ::= { hwGponOntPerfEverbeforeDataTable 1 }  
            HwGponOntPerfEverbeforeDataEntry ::=
                        SEQUENCE
                {      
                hwGponOntEverbeforeDownFrameFecCorrectedBytes           Counter64,
                hwGponOntEverbeforeDownFrameFecCorrectedCodeWords       Counter64,
                hwGponOntEverbeforeDownFrameFecUncorrectableCodeWords   Counter64,
                hwGponOntEverbeforeDownFrameTotalRecCodeWords           Counter64,
                hwGponOntEverbeforeDownFrameFecSeconds                  Counter64,
                hwGponOntEverbeforeRangingTimeCount                     Counter64,
                hwGponOntEverbeforeTransmittedGemFrames                 Counter64,
                hwGponOntEverbeforeXgemKeyErrorCount                    Counter64,
                hwGponOntEverbeforeXgemHecErrorCount                    Counter64
                } 
            hwGponOntEverbeforeDownFrameFecCorrectedBytes OBJECT-TYPE
            SYNTAX      Counter64 
            MAX-ACCESS  read-only
            STATUS      current
            DESCRIPTION
            "Count of bytes that were corrected by 
            the FEC function ever before"
            ::={ hwGponOntPerfEverbeforeDataEntry 1 }  
            
        hwGponOntEverbeforeDownFrameFecCorrectedCodeWords OBJECT-TYPE
            SYNTAX      Counter64
            MAX-ACCESS  read-only
            STATUS      current
            DESCRIPTION
                "Count of code words that were corrected by the FEC 
                function ever before."
            ::={ hwGponOntPerfEverbeforeDataEntry 2 }

        hwGponOntEverbeforeDownFrameFecUncorrectableCodeWords OBJECT-TYPE
            SYNTAX      Counter64
            MAX-ACCESS  read-only
            STATUS      current
            DESCRIPTION
                "Count of code words that were not corrected by the FEC 
                function ever before."
            ::={ hwGponOntPerfEverbeforeDataEntry 3}

        hwGponOntEverbeforeDownFrameTotalRecCodeWords OBJECT-TYPE
            SYNTAX      Counter64
            MAX-ACCESS  read-only
            STATUS      current
            DESCRIPTION
                "Count of total received code words ever before."
            ::={ hwGponOntPerfEverbeforeDataEntry 4 }

        hwGponOntEverbeforeDownFrameFecSeconds OBJECT-TYPE
            SYNTAX      Counter64
            MAX-ACCESS  read-only
            STATUS      current
            DESCRIPTION
                "Count of seconds ever before, when there 
                was a forward error correction anomaly."
            ::={ hwGponOntPerfEverbeforeDataEntry 5 }   
            
        hwGponOntEverbeforeRangingTimeCount OBJECT-TYPE
            SYNTAX      Counter64
            MAX-ACCESS  read-only
            STATUS      current
            DESCRIPTION
                "Count of rangingtime ever before."
            ::={ hwGponOntPerfEverbeforeDataEntry 6 }
            
        hwGponOntEverbeforeTransmittedGemFrames OBJECT-TYPE
            SYNTAX      Counter64
            MAX-ACCESS  read-only
            STATUS      current
            DESCRIPTION
                "Count of transmitted XGEM frames ever before."
            ::={ hwGponOntPerfEverbeforeDataEntry 7 }
            
        hwGponOntEverbeforeXgemKeyErrorCount OBJECT-TYPE
            SYNTAX      Counter64
            MAX-ACCESS  read-only
            STATUS      current
            DESCRIPTION
                "Count of XGEM key errors ever before."
            ::={ hwGponOntPerfEverbeforeDataEntry 8 }   
            
        hwGponOntEverbeforeXgemHecErrorCount OBJECT-TYPE
            SYNTAX      Counter64
            MAX-ACCESS  read-only
            STATUS      current
            DESCRIPTION
                "Count of XGEM hec error ever before."
            ::={ hwGponOntPerfEverbeforeDataEntry 9 }
            
    --Table hw10GponOltOpticsModuleInformationTable
        hw10GponOltOpticsModuleInformationTable OBJECT-TYPE
            SYNTAX SEQUENCE OF Hw10GponOltOpticsModuleInformationEntry
            MAX-ACCESS not-accessible
            STATUS     current
            DESCRIPTION
                "This table is used to query the information about the optical transceiver.
                 The index of this table is ifIndex."     
            ::= { hwXponCommonStatisticObjects 6 }
        
        hw10GponOltOpticsModuleInformationEntry OBJECT-TYPE
            SYNTAX Hw10GponOltOpticsModuleInformationEntry
            MAX-ACCESS not-accessible
            STATUS current
            DESCRIPTION
                "This table is used to query the information about the optical transceiver.
                 The index of this entry is ifIndex.
                "
            INDEX       { ifIndex }
            ::= { hw10GponOltOpticsModuleInformationTable 1 }
            
        Hw10GponOltOpticsModuleInformationEntry ::=
         SEQUENCE
                {
                hw10GponOltOpticsModuleInfoIdentifier                               INTEGER,
                hw10GponOltOpticsModuleInfoExtCLEICode                              INTEGER,
                hw10GponOltOpticsModuleInfoExtTXRefClock                            INTEGER,
                hw10GponOltOpticsModuleInfoExtCDRFunc                               INTEGER,
                hw10GponOltOpticsModuleInfoExtPowerLevel                            INTEGER,
                hw10GponOltOpticsModuleInfoConnector                                INTEGER,
                hw10GponOltOpticsModuleInfoEncodingRZ                               INTEGER,
                hw10GponOltOpticsModuleInfoEncodingNRZ                              INTEGER,
                hw10GponOltOpticsModuleInfoEncoding8B10B                            INTEGER,
                hw10GponOltOpticsModuleInfoEncoding64B                              INTEGER,
                hw10GponOltOpticsModuleInfoBrMin                                    Integer32,
                hw10GponOltOpticsModuleInfoBrMax                                    Integer32,
                hw10GponOltOpticsModuleInfoSupportLenSMF                            Integer32,
                hw10GponOltOpticsModuleInfoSupportLenE50um                          Integer32,
                hw10GponOltOpticsModuleInfoSupportLen50um                           Integer32,
                hw10GponOltOpticsModuleInfoSupportLen62p5um                         Integer32,
                hw10GponOltOpticsModuleInfoSupportLenCopper                         Integer32,
                hw10GponOltOpticsModuleInfoTransmitterSupport                       INTEGER,
                hw10GponOltOpticsModuleInfoDetector                                 INTEGER,
                hw10GponOltOpticsModuleInfoCooledTransmitterDevice                  INTEGER,
                hw10GponOltOpticsModuleInfoWavelengthControl                        INTEGER,
                hw10GponOltOpticsModuleInfoTransmitterTechnologySupport             INTEGER,
                hw10GponOltOpticsModuleInfoVendorName                               OCTET STRING,
                hw10GponOltOpticsModuleInfoSupportXFIMode                           INTEGER,
                hw10GponOltOpticsModuleInfoSupportLinesideMode                      INTEGER,
                hw10GponOltOpticsModuleInfoMaxBitRateSupportedByCDR                 INTEGER,
                hw10GponOltOpticsModuleInfoVendorOUI                                Integer32,
                hw10GponOltOpticsModuleInfoVendorPN                                 OCTET STRING,
                hw10GponOltOpticsModuleInfoVendorRev                                OCTET STRING,
                hw10GponOltOpticsModuleInfoF51                                      Integer32,
                hw10GponOltOpticsModuleInfoWaveTolerance                            Integer32,
                hw10GponOltOpticsModuleInfoMaxCaseTemperature                       Integer32,
                hw10GponOltOpticsModuleInfoCcbase                                   Integer32,
                hw10GponOltOpticsModuleInfoMaxDissipation                           Integer32,
                hw10GponOltOpticsModuleInfoMaxDissipationPowerDownMode              Integer32,
                hw10GponOltOpticsModuleInfoMaximum5P0VSupply                        Integer32,
                hw10GponOltOpticsModuleInfoMaximum3P3VSupply                        Integer32,
                hw10GponOltOpticsModuleInfoMaximum1P8VSupply                        Integer32,
                hw10GponOltOpticsModuleInfoMaximum5P2VSupply                        Integer32,
                hw10GponOltOpticsModuleInfoVendorSN                                 OCTET STRING,
                hw10GponOltOpticsModuleInfoDateCode                                 OCTET STRING,
                hw10GponOltOpticsModuleInfoDiagnoMonitorPowerMeasure                INTEGER,
                hw10GponOltOpticsModuleInfoDiagnoMonitorTypeFECBER                  INTEGER,
                hw10GponOltOpticsModuleInfoEnhancedOptions                          Integer32,
                hw10GponOltOpticsModuleInfoAuxInputOne                              INTEGER,
                hw10GponOltOpticsModuleInfoAuxInputTwo                              INTEGER,
                hw10GponOltOpticsModuleInfoCCEXT                                    Integer32,
                hw10GponOltOpticsModuleInfoWavelengthFor2d5G                        Integer32,
                hw10GponOltOpticsModuleInfoWavelengthFor1d25G                       Integer32,
                hw10GponOltOpticsModuleInfoVendorSpecific                           OCTET STRING,
                hw10GponOltOpticsModuleXponType                                     INTEGER,
                hw10GponOltOpticsModuleXponSubType                                  INTEGER,
                hw10GponOltOpticsModuleXponUsedType                                 INTEGER,
                hw10GponOltOpticsModuleXponEncapsulationType                        INTEGER,
                hw10GponOltOpticsModuleXponTemperatureLevel                         INTEGER,
                hw10GponOltOpticsModuleXponOPMprecision                             INTEGER,
                hw10GponOltOpticsModuleInfoCcBaseState                              INTEGER,
                hw10GponOltOpticsModuleInfoCcExtState                               INTEGER,
                hw10GponOltOpticsModuleInfoWaveLength                               Integer32,
                hw10GponOltOpticsModuleComboMode                                    INTEGER,
                hw10GponOltOpticsModuleInfoPartNum                                  OCTET STRING
                }
                
        hw10GponOltOpticsModuleInfoIdentifier OBJECT-TYPE
          SYNTAX INTEGER {
              unknown(0), 
              gbic(1), 
              solderedToMotherBoard(2),
              sfp(3), 
              pin300XBI(4), 
              xenpak(5), 
              xfp(6), 
              xff(7), 
              xfep(8), 
              xpak(9), 
              x2(10),  
              sfpplus(11),
              invalid(-1)
            }
          MAX-ACCESS read-only
          STATUS current
          DESCRIPTION
              "This object indicates the type of serial transceiver.
               Options:
               1. unknown(0)                      - Unknown or unspecified
               2. gbic(1)                         - GBIC
               3. solderedToMotherBoard(2)        - Module soldered to motherboard
               4. sfp(3)                          - SFP
               5. pin300XBI(4)                    - PIN300XBI
               6. xenpak(5)                       - XENPAK
               7. xfp(6)                          - XFP
               8. xff(7)                          - XFF
               9. xfep(8)                         - XFEP
               10. xpak(9)                        - XPAK
               11. x2(10)                         - X2  
               12. sfpplus(11)                    - SFP+
               13. invalid(-1)                    - Indicates that the query fails or no information is detected
               "
          ::= { hw10GponOltOpticsModuleInformationEntry 1 }
            
          hw10GponOltOpticsModuleInfoExtCLEICode OBJECT-TYPE
              SYNTAX INTEGER {
                  nonExtCLEICode(0), 
                  extCLEICode(1),
                  invalid(-1)
              }
            MAX-ACCESS read-only
            STATUS current
            DESCRIPTION
                "This object indicates the extclei code.
                 Options:
                 1. nonExtCLEICode(0)                - No CLEI code present in Table 02h
                 2. extCLEICode(1)                   - CLEI code present in Table 02h 
                 3. invalid(-1)                      - Indicates that the query fails or no information is detected
                "
            ::= { hw10GponOltOpticsModuleInformationEntry 2 }
            
          hw10GponOltOpticsModuleInfoExtTXRefClock OBJECT-TYPE
              SYNTAX INTEGER {
                        nonExtTXRefClock(0), 
                  extTXRefClock(1),
                  invalid(-1)
              }
            MAX-ACCESS read-only
            STATUS current
            DESCRIPTION
            "This object indicates the txref clock.
             Options:
             1. nonExtTXRefClock(0)              - TX Ref Clock Input Not Required
             2. extTXRefClock(1)                 - TX Ref Clock Input Required 
             3. invalid(-1)                      - Indicates that the query fails or no information is detected                
             "
          ::= { hw10GponOltOpticsModuleInformationEntry 3 }
            
          hw10GponOltOpticsModuleInfoExtCDRFunc OBJECT-TYPE
              SYNTAX INTEGER {
                        nonExtCDRFunc(0),
                       extCDRFunc(1),
                       invalid(-1)
              }
            MAX-ACCESS read-only
            STATUS current
            DESCRIPTION
            "This object indicates the CDR function.
             Options:
             1. nonExtCDRFunc(0)               - Non-CDR version of XFP
             2. extCDRFunc(1)                  - Module with CDR function 
             3. invalid(-1)                    - Indicates that the query fails or no information is detected                
            "
          ::= { hw10GponOltOpticsModuleInformationEntry 4 }
            
          hw10GponOltOpticsModuleInfoExtPowerLevel OBJECT-TYPE
              SYNTAX INTEGER {
                      extPowerLevel1(0), 
                extPowerLevel2(1), 
                extPowerLevel3(2), 
                extPowerLevel4(3), 
                invalid(-1)
              }
            MAX-ACCESS read-only
            STATUS current
            DESCRIPTION
            "This object indicates the power level.
             Options:
             1. extPowerLevel1(0)               - Power Level 1 Module (1.5 W max. power dissipation.)
             2. extPowerLevel2(1)               - Power Level 2 Module (2.5W Max) 
             3. extPowerLevel3(2)               - Power Level 3 Module (3.5W max. power dissipation.)
             4. extPowerLevel4(3)               - Power Level 4 Module (>3.5W max. power dissipation.) 
             5. invalid(-1)                     - Indicates that the query fails or no information is detected                
             "
          ::= { hw10GponOltOpticsModuleInformationEntry 5 }
            
          hw10GponOltOpticsModuleInfoConnector OBJECT-TYPE
              SYNTAX INTEGER {
                      unknown(1), 
                sc(2), 
                style1Connector(3), 
                style2Connector(4), 
                bnctnc(5) ,
                channelCoaxial(6), 
                fiberJack(7), 
                lc(8) ,
                mtrj(9), 
                mu(10), 
                sg(11), 
                opticalPigtail(12), 
                hssdc(13), 
                copperPigtail(14), 
                invalid(-1)
              }
            MAX-ACCESS read-only
            STATUS current
            DESCRIPTION
            "
               This object indicates the code for connector type.
               Options:
               1.  unknown(1)                - Unknown
               2.  sc(2)                     - SC
               3.  style1Connector(3)        - Fibre Channel Style 1 copper connector
               4.  style2Connector(4)        - Fibre Channel Style 2 copper connector
               5.  bnctnc(5)                 - BNC/TNC
               6.  channelCoaxial(6)         - Fibre Channel coaxial headers
               7.  fiberJack(7)              - FiberJack
               8.  lc(8)                     - LC
               9.  mtrj(9)                   - MT-RJ
               10. mu(10)                    - MU
               11. sg(11)                    - SG
               12. opticalPigtail(12)        - Optical pigtail
               13. hssdc(13)                 - HSSDC II
               14. copperPigtail(14)         - Copper Pigtail
               15. invalid(-1)               - Indicates that the query fails or no information is detected
            "
          ::= { hw10GponOltOpticsModuleInformationEntry 6 }
            
          hw10GponOltOpticsModuleInfoEncodingRZ OBJECT-TYPE
              SYNTAX INTEGER {
                      nonEncodingRZ(0), 
                  encodingRZ(1),
                  invalid(-1)
              }
            MAX-ACCESS read-only
            STATUS current
            DESCRIPTION
            "This object indicates the EncodingRZ.
             Options:
             1. nonEncodingRZ(0)             - Encoding Don't Support RZ
             2. encodingRZ(1)                - Encoding Support RZ 
             3. invalid(-1)                  - Indicates that the query fails or no information is detected                
            "
          ::= { hw10GponOltOpticsModuleInformationEntry 7 }
            
          hw10GponOltOpticsModuleInfoEncodingNRZ OBJECT-TYPE
              SYNTAX INTEGER {
                      nonEncodingNRZ(0), 
                  encodingNRZ(1),
                  invalid(-1)
              }
            MAX-ACCESS read-only
            STATUS current
            DESCRIPTION
            "This object indicates the EncodingNRZ.
             Options:
             1. nonEncodingNRZ(0)       - Encoding Don't Support NRZ
             2. encodingNRZ(1)          - Encoding Support NRZ 
             3. invalid(-1)             - Indicates that the query fails or no information is detected                
            "
          ::= { hw10GponOltOpticsModuleInformationEntry 8 }
            
          hw10GponOltOpticsModuleInfoEncoding8B10B OBJECT-TYPE
              SYNTAX INTEGER {
                      nonEncoding8B10B(0), 
                  encoding8B10B(1),
                  invalid(-1)
              }
            MAX-ACCESS read-only
            STATUS current
            DESCRIPTION
            "This object indicates the Encoding8B10B.
             Options:
             1. nonEncoding8B10B(0)          - Encoding Don't Support 8B10B
             2. encoding8B10B(1)             - Encoding Support 8B10B
             3. invalid(-1)                  - Indicates that the query fails or no information is detected                
            "
          ::= { hw10GponOltOpticsModuleInformationEntry 9 }
            
          hw10GponOltOpticsModuleInfoEncoding64B OBJECT-TYPE
              SYNTAX INTEGER {
                      nonEncoding64B(0), 
                  encoding64B(1),
                  invalid(-1) 
              }
            MAX-ACCESS read-only
            STATUS current
            DESCRIPTION
            "This object indicates the Encoding64B.
             Options:
             1. nonEncoding64B(0)          - Encoding Don't Support 64B/66B
             2. encoding64B(1)             - Encoding Support 64B/66B 
             3. invalid(-1)                - Indicates that the query fails or no information is detected                
            "
          ::= { hw10GponOltOpticsModuleInformationEntry 10 }
            
          hw10GponOltOpticsModuleInfoBrMin OBJECT-TYPE
              SYNTAX Integer32
            MAX-ACCESS read-only
            STATUS current
            DESCRIPTION
            "
                Minimum bit rate, units of 100 MBits/s
            "
          ::= { hw10GponOltOpticsModuleInformationEntry 11 }
          
          hw10GponOltOpticsModuleInfoBrMax OBJECT-TYPE
              SYNTAX Integer32
            MAX-ACCESS read-only
            STATUS current
            DESCRIPTION
            "
                Maximum bit rate, units of 100 MBits/s
            "
          ::= { hw10GponOltOpticsModuleInformationEntry 12 }
          
          hw10GponOltOpticsModuleInfoSupportLenSMF OBJECT-TYPE
              SYNTAX Integer32
            MAX-ACCESS read-only
            STATUS current
            DESCRIPTION
            "
                Link length supported for SMF fiber in km 
            "
          ::= { hw10GponOltOpticsModuleInformationEntry 13 }
          
          hw10GponOltOpticsModuleInfoSupportLenE50um OBJECT-TYPE
              SYNTAX Integer32
            MAX-ACCESS read-only
            STATUS current
            DESCRIPTION
            "
                Link length supported for EBW 50/125 um fiber, units of 2 m
            "
          ::= { hw10GponOltOpticsModuleInformationEntry 14 }
          
          hw10GponOltOpticsModuleInfoSupportLen50um OBJECT-TYPE
              SYNTAX Integer32
            MAX-ACCESS read-only
            STATUS current
            DESCRIPTION
            "
                Link length supported for 50/125 um fiber, units of 1 m 
            "
          ::= { hw10GponOltOpticsModuleInformationEntry 15 }
          
          hw10GponOltOpticsModuleInfoSupportLen62p5um OBJECT-TYPE
              SYNTAX Integer32
            MAX-ACCESS read-only
            STATUS current
            DESCRIPTION
            "
                Link length supported for 62.5/125 um fiber, units of 1 m
            "
          ::= { hw10GponOltOpticsModuleInformationEntry 16 }
          
          hw10GponOltOpticsModuleInfoSupportLenCopper OBJECT-TYPE
              SYNTAX Integer32
            MAX-ACCESS read-only
            STATUS current
            DESCRIPTION
            "
                Link length supported for copper, units of 1m
            "
          ::= { hw10GponOltOpticsModuleInformationEntry 17 }
            
          hw10GponOltOpticsModuleInfoTransmitterSupport OBJECT-TYPE
              SYNTAX INTEGER {
                      nonTunable(0),
                     tunable(1),
                     invalid(-1) 
              }
            MAX-ACCESS read-only
            STATUS current
            DESCRIPTION
                "This object indicates the transmitter support.
                 Options:
                 1. nonTunable(0)      - Transmitter Not Support Tunable
                 2. tunable(1)         - Transmitter Support Tunable 
                 3. invalid(-1)        - Indicates that the query fails or no information is detected                
                "
            ::= { hw10GponOltOpticsModuleInformationEntry 18 }
            
          hw10GponOltOpticsModuleInfoDetector OBJECT-TYPE
              SYNTAX INTEGER {
                      pin(0),
                apd(1),
                invalid(-1) 
              }
            MAX-ACCESS read-only
            STATUS current
            DESCRIPTION
                "This object indicates the transmitter support.
                 Options:
                 1. pin(0)              - PIN
                 2. apd(1)              - APD 
                 3. invalid(-1)         - Indicates that the query fails or no information is detected                
                "
            ::= { hw10GponOltOpticsModuleInformationEntry 19 }
            
          hw10GponOltOpticsModuleInfoCooledTransmitterDevice OBJECT-TYPE
              SYNTAX INTEGER {
                      nonSupport(0),
                     support(1),
                     invalid(-1) 
              }
            MAX-ACCESS read-only
            STATUS current
            DESCRIPTION
                "This object indicates the wavelength control.
                 Options:
                 1. nonSupport(0)       - Wavelength control NonSupport
                 2. support(1)          - Wavelength control Support 
                 3. invalid(-1)         - Indicates that the query fails or no information is detected                
                "
            ::= { hw10GponOltOpticsModuleInformationEntry 20 }
            
          hw10GponOltOpticsModuleInfoWavelengthControl OBJECT-TYPE
              SYNTAX INTEGER {
                      nonSupport(0),
                    support(1),
                    invalid(-1) 
              }
            MAX-ACCESS read-only
            STATUS current
            DESCRIPTION
                "This object indicates the cooled transmitter device.
                 Options:
                 1. nonSupport(0)         - Cooled transmitter device NonSupport
                 2. support(1)            - Cooled transmitter device Support 
                 3. invalid(-1)           - Indicates that the query fails or no information is detected                
                "
          ::= { hw10GponOltOpticsModuleInformationEntry 21 }
            
          hw10GponOltOpticsModuleInfoTransmitterTechnologySupport OBJECT-TYPE
              SYNTAX INTEGER {
                      vCSEL850(0),
                     vCSEL1310(1),
                vCSEL1550(2),
                fP1310(3),
                dFB1310(4),
                dFB1550(5),
                eML1310(6),
                eML1550(7),
                cOPPER(8),
                invalid(-1) 
              }
            MAX-ACCESS read-only
            STATUS current
            DESCRIPTION
                "This object indicates the transmitter technology support.
                 Options:
                 1. vCSEL850(0)          - vCSEL850
                 2. vCSEL1310(1)         - vCSEL1310 
                 3. vCSEL1550(2)         - vCSEL1550
                 4. fP1310(3)            - fP1310
                 5. dFB1310(4)           - dFB1310
                 6. dFB1550(5)           - dFB1550 
                 7. eML1310(6)           - eML1310
                 8. eML1550(7)           - eML1550         
                 9. cOPPER(8)            - cOPPER         
                 10. invalid(-1)         - Indicates that the query fails or no information is detected                
                "
          ::= { hw10GponOltOpticsModuleInformationEntry 22 }
          
          hw10GponOltOpticsModuleInfoVendorName OBJECT-TYPE
            SYNTAX OCTET STRING (SIZE (0..17))
            MAX-ACCESS read-only
            STATUS current
            DESCRIPTION
                "This object indicates the SFP vendor name (ASCII)."
            ::= { hw10GponOltOpticsModuleInformationEntry 23 }
          
          hw10GponOltOpticsModuleInfoSupportXFIMode OBJECT-TYPE
              SYNTAX INTEGER {
                      nonSupportXFIMode(0),
                     supportXFIMode(1),
                invalid(-1) 
              }
            MAX-ACCESS read-only
            STATUS current
            DESCRIPTION
                "This object indicates the XFI mode.
                 Options:
                 1. nonSupportXFIMode(0)      - Don't Support XFI Loopback Mode
                 2. supportXFIMode(1)         - XFI Loopback Mode Supported
                 3. invalid(-1)               - Indicates that the query fails or no information is detected                
                "
          ::= { hw10GponOltOpticsModuleInformationEntry 24 }
            
          hw10GponOltOpticsModuleInfoSupportLinesideMode OBJECT-TYPE
              SYNTAX INTEGER {
                      nonSupportLinesideMode(0),
                     supportLinesideMode(1),
                invalid(-1) 
              }
            MAX-ACCESS read-only
            STATUS current
            DESCRIPTION
                "This object indicates the XFI mode.
                 Options:
                 1. nonSupportLinesideMode(0)     - Don't Support Lineside Loopback Mode
                 2. supportLinesideMode(1)        - Lineside Loopback Mode Supported 
                 3. invalid(-1)                   - Indicates that the query fails or no information is detected                
                "
          ::= { hw10GponOltOpticsModuleInformationEntry 25 }
            
          hw10GponOltOpticsModuleInfoMaxBitRateSupportedByCDR OBJECT-TYPE
              SYNTAX INTEGER {
                      cdrNosupport(0),
                    maxBitRateSupportedByCDR11p1(1),
                    maxBitRateSupportedByCDR10p7(3),
                    maxBitRateSupportedByCDR10p5(7),
                    maxBitRateSupportedByCDR10p3(15),
                    maxBitRateSupportedByCDR9p95(31),
                    invalid(-1) 
              }
            MAX-ACCESS read-only
            STATUS current
            DESCRIPTION
                "This object indicates the max bit rate by CDR.
                 Options:
                 1. cdrNosupport(0)                       - CDR not support
                 2. maxBitRateSupportedByCDR11p1(1)       - CDR support for 11.1 Gb/s 
                 3. maxBitRateSupportedByCDR10p7(3)       - CDR support for 10.7 Gb/s
                 4. maxBitRateSupportedByCDR10p5(7)       - CDR support for 10.5 Gb/s 
                 5. maxBitRateSupportedByCDR10p3(15)      - CDR support for 10.3 Gb/s                
                 6. maxBitRateSupportedByCDR9p95(31)      - CDR support for 9.95 Gb/s        
                 7. invalid(-1)                           - Indicates that the query fails or no information is detected                
                "
            ::= { hw10GponOltOpticsModuleInformationEntry 26 }
            
          hw10GponOltOpticsModuleInfoVendorOUI OBJECT-TYPE
              SYNTAX Integer32
            MAX-ACCESS read-only
            STATUS current
            DESCRIPTION
               "This object indicates the Vendor OUI."
          ::= { hw10GponOltOpticsModuleInformationEntry 27 }
            
          hw10GponOltOpticsModuleInfoVendorPN OBJECT-TYPE
            SYNTAX OCTET STRING (SIZE (0..17))
            MAX-ACCESS read-only
            STATUS current
            DESCRIPTION
                "This object indicates the Vendor PN."
          ::= { hw10GponOltOpticsModuleInformationEntry 28 }

        hw10GponOltOpticsModuleInfoVendorRev OBJECT-TYPE
            SYNTAX OCTET STRING (SIZE (0..17))
            MAX-ACCESS read-only
            STATUS current
            DESCRIPTION
               "This object indicates the Vendor rev."
          ::= { hw10GponOltOpticsModuleInformationEntry 29 }
          
        hw10GponOltOpticsModuleInfoF51 OBJECT-TYPE
            SYNTAX Integer32
            MAX-ACCESS read-only
            STATUS current
            DESCRIPTION
                "This object indicates the Wavelength."
          ::= { hw10GponOltOpticsModuleInformationEntry 30 }        
            
          hw10GponOltOpticsModuleInfoWaveTolerance OBJECT-TYPE
              SYNTAX Integer32
            MAX-ACCESS read-only
            STATUS current
            DESCRIPTION
               "This object indicates the Wavelength."
          ::= { hw10GponOltOpticsModuleInformationEntry 31 }
            
          hw10GponOltOpticsModuleInfoMaxCaseTemperature OBJECT-TYPE
              SYNTAX Integer32
            MAX-ACCESS read-only
            STATUS current
            DESCRIPTION
               "This object indicates the Maximum Case Temperature in Degrees C."
          ::= { hw10GponOltOpticsModuleInformationEntry 32 }
            
          hw10GponOltOpticsModuleInfoCcbase OBJECT-TYPE
              SYNTAX Integer32
            MAX-ACCESS read-only
            STATUS current
            DESCRIPTION
               "This object indicates the Cc_base."
          ::= { hw10GponOltOpticsModuleInformationEntry 33 }
            
          hw10GponOltOpticsModuleInfoMaxDissipation OBJECT-TYPE
              SYNTAX Integer32
            MAX-ACCESS read-only
            STATUS current
            DESCRIPTION
               "This object indicates the Maximum Power Dissipation."
          ::= { hw10GponOltOpticsModuleInformationEntry 34 }
            
          hw10GponOltOpticsModuleInfoMaxDissipationPowerDownMode OBJECT-TYPE
              SYNTAX Integer32
            MAX-ACCESS read-only
            STATUS current
            DESCRIPTION
               "This object indicates the Maximum Total Power Dissipation in Power Down Mode."
          ::= { hw10GponOltOpticsModuleInformationEntry 35 }
            
          hw10GponOltOpticsModuleInfoMaximum5P0VSupply OBJECT-TYPE
              SYNTAX Integer32
            MAX-ACCESS read-only
            STATUS current
            DESCRIPTION
               "This object indicates the Maximum current required by +5V Supply."
          ::= { hw10GponOltOpticsModuleInformationEntry 36 }
            
          hw10GponOltOpticsModuleInfoMaximum3P3VSupply OBJECT-TYPE
              SYNTAX Integer32
            MAX-ACCESS read-only
            STATUS current
            DESCRIPTION
               "This object indicates the Maximum current required by +3.3V Supply."
          ::= { hw10GponOltOpticsModuleInformationEntry 37 }
            
          hw10GponOltOpticsModuleInfoMaximum1P8VSupply OBJECT-TYPE
              SYNTAX Integer32
            MAX-ACCESS read-only
            STATUS current
            DESCRIPTION
               "This object indicates the Maximum current required by +1.8V Supply."
          ::= { hw10GponOltOpticsModuleInformationEntry 38 }
            
          hw10GponOltOpticsModuleInfoMaximum5P2VSupply OBJECT-TYPE
              SYNTAX Integer32
            MAX-ACCESS read-only
            STATUS current
            DESCRIPTION
               "This object indicates the Maximum current required by -5.2V Supply."
          ::= { hw10GponOltOpticsModuleInformationEntry 39 }
            
          hw10GponOltOpticsModuleInfoVendorSN OBJECT-TYPE
              SYNTAX OCTET STRING (SIZE (0..17))
            MAX-ACCESS read-only
            STATUS current
            DESCRIPTION
               "This object indicates the Vendor SN."
          ::= { hw10GponOltOpticsModuleInformationEntry 40 } 
          
        hw10GponOltOpticsModuleInfoDateCode OBJECT-TYPE
            SYNTAX OCTET STRING (SIZE (0..9))
            MAX-ACCESS read-only
            STATUS current
            DESCRIPTION
               "This object indicates the Date code."
          ::= { hw10GponOltOpticsModuleInformationEntry 41 }
          
        hw10GponOltOpticsModuleInfoDiagnoMonitorPowerMeasure OBJECT-TYPE
            SYNTAX INTEGER {
                      supportOMA(0),
                     supportAveragePower(1), 
                     invalid(-1)
              }
            MAX-ACCESS read-only
            STATUS current
            DESCRIPTION
               "This object indicates the Received power measurement type.
                Options:
                1. supportOMA(0)               - OMA
                2. supportAveragePower(1)      - Average Power 
                3. invalid(-1)                 - Indicates that the query fails or no information is detected                
               "
          ::= { hw10GponOltOpticsModuleInformationEntry 42 }
            
          hw10GponOltOpticsModuleInfoDiagnoMonitorTypeFECBER OBJECT-TYPE
              SYNTAX INTEGER {
                      nonSupportBER(0),
                     supportBER(1),
                     invalid(-1) 
              }
            MAX-ACCESS read-only
            STATUS current
            DESCRIPTION
               "This object indicates the Module Respond to FEC BER.
                Options:
                1. nonSupportBER(0)         - No BER Support
                2. supportBER(1)            - BER Support 
                3. invalid(-1)              - Indicates that the query fails or no information is detected                
               "
          ::= { hw10GponOltOpticsModuleInformationEntry 43 }
            
          hw10GponOltOpticsModuleInfoEnhancedOptions OBJECT-TYPE
              SYNTAX Integer32 
            MAX-ACCESS read-only
            STATUS current
            DESCRIPTION
                "Indicates which optional enhanced features are implemented.
                 bit                Description of Enhanced Options
                  7                  -Module Supports Optional VPS
                  6                  -Optional Soft TX_DISABLE implemented
                  5                  -Optional Soft P_down implemented
                  4                  -Supports VPS LV regulator mode
                  3                  -Supports VPS bypassed regulator Mode
                  2                  -Active FEC control functions implemented
                  1                  -Wavelength tunability implemented
                  0                  -Optional CMU Support Mode 
                  invalid(-1)        -Indicates that the query fails or no information is detected                
               "
          ::= { hw10GponOltOpticsModuleInformationEntry 44 }
            
            hw10GponOltOpticsModuleInfoAuxInputOne OBJECT-TYPE
              SYNTAX INTEGER {
                   auxInputType1(0),
                   auxInputType2(1),
                   auxInputType3(2),
                   auxInputType4(3),
                   auxInputType5(4),
                   auxInputType6(5),
                   auxInputType7(6),
                   auxInputType8(7),
                   auxInputType9(8),
                   auxInputType10(9),
                   auxInputType11(10),
                   auxInputType14(13),
                   auxInputType15(14),
                   auxInputType16(15),
                   invalid(-1) 
              }
            MAX-ACCESS read-only
            STATUS current
            DESCRIPTION
                "This object indicates the optics Aux Input One.
                 Options:
                 1. auxInputType1(0)          - Auxiliary monitoring not implemented
                 2. auxInputType2(1)          - APD Bias Voltage 
                 3. auxInputType3(2)          - 1G Tx Bias Current                
                 4. auxInputType4(3)          - TEC Current (mA)
                 5. auxInputType5(4)          - Laser Temperature 
                 6. auxInputType6(5)          - Laser Wavelength                
                 7. auxInputType7(6)          - +5V Supply Voltage
                 8. auxInputType8(7)          - 1G Tx Power 
                 9. auxInputType9(8)          - +1.8V Supply Voltage                
                 10. auxInputType10(9)        - -5.2V Supply Voltage 
                 11. auxInputType11(10)       - +5V Supply Current                
                 12. auxInputType14(13)       - +3.3V Supply Current
                 13. auxInputType15(14)       - +1.8V Supply Current 
                 14. auxInputType16(15)       - -5.2V Supply Current                
                 15. invalid(-1)              - Indicates that the query fails or no information is detected                
                "
            ::= { hw10GponOltOpticsModuleInformationEntry 45 }
            
          hw10GponOltOpticsModuleInfoAuxInputTwo OBJECT-TYPE
              SYNTAX INTEGER {
                   auxInputType1(0),
                   auxInputType2(1),
                   auxInputType3(2),
                   auxInputType4(3),
                   auxInputType5(4),
                   auxInputType6(5),
                   auxInputType7(6),
                   auxInputType8(7),
                   auxInputType9(8),
                   auxInputType10(9),
                   auxInputType11(10),
                   auxInputType14(13),
                   auxInputType15(14),
                   auxInputType16(15),
                   invalid(-1) 
              }
            MAX-ACCESS read-only
            STATUS current
            DESCRIPTION
                "This object indicates the optics Aux Input One.
                 Options:
                 1. auxInputType1(0)          - Auxiliary monitoring not implemented
                 2. auxInputType2(1)          - APD Bias Voltage 
                 3. auxInputType3(2)          - 1G Tx Bias Current                
                 4. auxInputType4(3)          - TEC Current (mA)
                 5. auxInputType5(4)          - Laser Temperature 
                 6. auxInputType6(5)          - Laser Wavelength                
                 7. auxInputType7(6)          - +5V Supply Voltage
                 8. auxInputType8(7)          - 1G Tx Power 
                 9. auxInputType9(8)          - +1.8V Supply Voltage                
                 10. auxInputType10(9)        - -5.2V Supply Voltage 
                 11. auxInputType11(10)       - +5V Supply Current                
                 12. auxInputType14(13)       - +3.3V Supply Current
                 13. auxInputType15(14)       - +1.8V Supply Current 
                 14. auxInputType16(15)       - -5.2V Supply Current                
                 15. invalid(-1)              - Indicates that the query fails or no information is detected                
                "
            ::= { hw10GponOltOpticsModuleInformationEntry 46 }
            
          hw10GponOltOpticsModuleInfoCCEXT OBJECT-TYPE
              SYNTAX Integer32
            MAX-ACCESS read-only
            STATUS current
            DESCRIPTION
                "This object indicates the CC_EXT ."
          ::= { hw10GponOltOpticsModuleInformationEntry 47 }
            
          hw10GponOltOpticsModuleInfoWavelengthFor2d5G OBJECT-TYPE
              SYNTAX Integer32
            MAX-ACCESS read-only
            STATUS current
            DESCRIPTION
                "This object indicates the Wavelength for 2.5G."
          ::= { hw10GponOltOpticsModuleInformationEntry 48 }
            
          hw10GponOltOpticsModuleInfoWavelengthFor1d25G OBJECT-TYPE
              SYNTAX Integer32
            MAX-ACCESS read-only
            STATUS current
            DESCRIPTION
                "This object indicates the Wavelength for 1.25G."
          ::= { hw10GponOltOpticsModuleInformationEntry 49 }
            
          hw10GponOltOpticsModuleInfoVendorSpecific OBJECT-TYPE
              SYNTAX OCTET STRING (SIZE (0..33))
            MAX-ACCESS read-only
            STATUS current
            DESCRIPTION
                "This object indicates the Vendor specific."
          ::= { hw10GponOltOpticsModuleInformationEntry 50 }
          
        hw10GponOltOpticsModuleXponType OBJECT-TYPE
            SYNTAX INTEGER 
                  {
                  unknown(1),
                  gpon(2),
                  epon(3),
                  epon10g(4),
                  xgpon(5),
                  wdmpon(6),
                  hybridpon(7),
                  gponOrEpon(8),
                  xgspon(9),
                  gponandxgpon(10),
                  gponandxgspon(11),
                  twdmpon(15),
                  invalid(-1)
                  }
            MAX-ACCESS read-only
            STATUS current
            DESCRIPTION
                "This object indicates the module type.
                 Options:
                 1. unknown(1)            - Unknown
                 2. gpon(2)               - GPON 
                 3. epon(3)               - EPON                
                 4. epon10g(4)            - 10G EPON
                 5. xgpon(5)              - XG-PON 
                 6. wdmpon(6)             - WDM PON                
                 7. hybridpon(7)          - Hybrid PON
                 8. gponOrEpon(8)         - GPON/EPON 
                 9. xgspon(9)             - XGS-PON
                 10. gponandxgpon(10)     - GPON+XG-PON
                 11. gponandxgspon(11)    - GPON+XGS-PON
                 12. twdmpon(15)          - TWDM-PON
                 13. invalid(-1)          - Indicates that the query fails or no information is detected                
               "
          ::= { hw10GponOltOpticsModuleInformationEntry 51 }
            
          hw10GponOltOpticsModuleXponSubType OBJECT-TYPE
              SYNTAX INTEGER {
                unknown(1), 
                classbplus(101), 
                classcplus(102), 
                classb(103), 
                classcplusplus(104),
                classd(105),
                px20(201), 
                px20plus(202), 
                px20plusplus(203),
                pr30(301), 
                pr20(302), 
                prx30(303), 
                prx20(304), 
                prx40(305),
                pr40(306),
                prx30e(307), 
                prx40e(308),
                pr30plus(309),
                n2a(405), 
                n2b(406), 
                n1(407), 
                e1(408),
                e2a(409),
                e2b(410),
                d1(411),
                d2(412),
                n2(413),
                e2(414),
                classbPlusAndPx20Plus(501),
                classbAndPx20(502),
                invalid(-1)
              }
            MAX-ACCESS read-only
            STATUS current
            DESCRIPTION
                "This object indicates the sub module type.
                 Options:
                 1. unknown(1)                 - Unknown
                 2. classbplus(101)            - CLASS B+
                 3. classcplus(102)            - CLASS C+
                 4. classb(103)                - CLASS B
                 5. classcplusplus(104)        - CLASS C++
                 6. classcd(105)        - CLASS D
                 7. px20(201)                  - PX20
                 8. px20plus(202)              - PX20+
                 9. px20plusplus(203)          - PX20++
                 10. pr30(301)                  - PR30
                 11.pr20(302)                  - PR20
                 12.prx30(303)                 - PRX30
                 13.prx20(304)                 - PRX20
                 14.prx40(305)                 - PRX40  
                 15.pr40(306)                  - PR40
                 16.prx30e(307)                - PRX30-E
                 17.prx40e(308)                - PRX40-E
                 18.pr30plus(309)              - PR30+
                 19.n2a(405)                   - N2a 
                 20.n2b(406)                   - N2b
                 21.n1(407)                    - N1    
                 22.e1(408)                    - E1 
                 23.e2a(409)                   - E2a
                 24.e2b(410)                   - E2b
                 25.d1(411)                    - D1
                 26.d2(412)                    - D2
                 27.n2(413)                    - N2
                 28.e2(414)                    - E2			
                 29.classbPlusAndPx20Plus(501) - GPON CLASS B+/EPON PX20+
                 30.classbAndPx20(502)         - GPON CLASS B/EPON PX20	 
                 31.invalid(-1)                - Indicates that the query fails or no information is detected
                "
          ::= { hw10GponOltOpticsModuleInformationEntry 52 }
            
          hw10GponOltOpticsModuleXponUsedType OBJECT-TYPE
              SYNTAX INTEGER {
                      unknown(1), 
                olt(2), 
                ont(3), 
                onu(4), 
                catvtriplex(5), 				
                invalid(-1) 
              }
            MAX-ACCESS read-only
            STATUS current
            DESCRIPTION
                "This object indicates the application scenario of the optical transceiver.
                 Options:
                 1. unknown(1)        - Unknown
                 2. olt(2)            - OLT
                 3. ont(3)            - ONT
                 4. onu(4)            - ONU
                 5. catvtriplex(5)    - CATV TriPlex				 
                 6. invalid(-1)       - Indicates that the query fails or no information is detected
                "
          ::= { hw10GponOltOpticsModuleInformationEntry 53 }
            
          hw10GponOltOpticsModuleXponEncapsulationType OBJECT-TYPE
              SYNTAX INTEGER {
                      unknown(1), 
                  sff2x5(2), 
                  sff2x10(3), 
                  sfp(4), 
                  xfp(5), 
                  lxfp(6), 
                  bosaonboard(7),    
                  sfpplus(8),
                  invalid(-1) 
              }
            MAX-ACCESS read-only
            STATUS current
            DESCRIPTION
                "This object indicates the encapsulation information about the optical transceiver.
                 Options:
                 1. unknown(1)        - Unknown
                 2. sff2x5(2)         - SFF 2x5
                 3. sff2x10(3)        - SFF 2x10
                 4. sfp(4)            - SFP
                 5. xfp(5)            - XFP
                 6. lxfp(6)           - LXFP
                 7. bosaonboard(7)    - BOSA ON BOARD           
                 8. sfpplus(8)        - SFP+
                 9. invalid(-1)       - Indicates that the query fails or no information is detected
                "
          ::= { hw10GponOltOpticsModuleInformationEntry 54 }
            
          hw10GponOltOpticsModuleXponTemperatureLevel OBJECT-TYPE
              SYNTAX INTEGER {
                      unknown(1),
                commercial(2),
                industry(3),
                expandTemperature(4),
                invalid(-1)
              }
            MAX-ACCESS read-only
            STATUS current
            DESCRIPTION
                "This object indicates the application scenario of the optical transceiver.
                 Options:
                 1. unknown(1)              - Unknown
                 2. commercial(2)           - commercial
                 3. industry(3)             - industry
                 4. expandTemperature(4)    - expand temperature
                 5. invalid(-1)             - Indicates that the query fails or no information is detected
                "
          ::= { hw10GponOltOpticsModuleInformationEntry 55 }
            
          hw10GponOltOpticsModuleXponOPMprecision OBJECT-TYPE
              SYNTAX INTEGER {
                      unknown(1),
                db3(2),
                db1(3),
                invalid(-1) 
              }
            MAX-ACCESS read-only
            STATUS current
            DESCRIPTION
                "This object indicates the OPM precision.
                 Options:
                 1. unknown(1)        - Unknown
                 2. db3(2)            - 3db
                 3. db1(3)            - 1db
                 4. invalid(-1)       - Indicates that the query fails or no information is detected
                "
          ::= { hw10GponOltOpticsModuleInformationEntry 56 }
            
            hw10GponOltOpticsModuleInfoCcBaseState OBJECT-TYPE
            SYNTAX INTEGER {
                correct (1), 
                incorrect(2),
                invalid (-1)    
            }
            MAX-ACCESS read-only
            STATUS current
            DESCRIPTION
                "This object indicates the CC_BASE match state.
                 Options:
                 1. correct (1)             - Correct
                 2. incorrect(2)            - Incorrect
                 3. invalid (-1)            - Indicates that the query fails or no information is detected
                "
            ::= { hw10GponOltOpticsModuleInformationEntry 57 }          
            
        hw10GponOltOpticsModuleInfoCcExtState OBJECT-TYPE
            SYNTAX INTEGER {
                correct (1), 
                incorrect(2),
                invalid (-1)    
            }
            MAX-ACCESS read-only
            STATUS current
            DESCRIPTION
                "This object indicates the CC_EXT match state.
                 Options:
                 1. correct (1)             - Correct
                 2. incorrect(2)            - Incorrect
                 3. invalid (-1)            - Indicates that the query fails or no information is detected
                "
            ::= { hw10GponOltOpticsModuleInformationEntry 58 } 
            
        hw10GponOltOpticsModuleInfoWaveLength OBJECT-TYPE
            SYNTAX Integer32
            MAX-ACCESS read-only
            STATUS current
            DESCRIPTION
                "This object indicates the Wavelength, unit:0.01nm."
          ::= { hw10GponOltOpticsModuleInformationEntry 59 }  
        
        hw10GponOltOpticsModuleComboMode OBJECT-TYPE
            SYNTAX INTEGER {
                wdm (1), 
                tdm (2),
                invalid (-1)    
            }
            MAX-ACCESS read-only
            STATUS current
            DESCRIPTION
                "This object indicates the ComboMode.
                 Options:
                 1. wdm (1)                 - wavelength division
                 2. tdm(2)                  - time division
                 3. invalid (-1)            - Indicates that the query fails or no information is detected
                "
          ::= { hw10GponOltOpticsModuleInformationEntry 60 }  
            
          hw10GponOltOpticsModuleInfoPartNum OBJECT-TYPE
            SYNTAX OCTET STRING (SIZE (0..16))
            MAX-ACCESS read-only
            STATUS current
            DESCRIPTION
               "Indicate the part number of a optical module provided by Huawei."
          ::= { hw10GponOltOpticsModuleInformationEntry 61 } 

          --Table hwGponCommonOntStatisticTable  
        hwGponCommonOntStatisticTable OBJECT-TYPE
            SYNTAX SEQUENCE OF HwGponCommonOntStatisticEntry
            MAX-ACCESS not-accessible      
            STATUS     current
            DESCRIPTION
                "This table is used to query the information about the priority queue alarm.
                 The indexes of this table are ifIndex and hwXponOntIndex."     
            ::= { hwXponCommonStatisticObjects 7 }
        
        hwGponCommonOntStatisticEntry OBJECT-TYPE
            SYNTAX HwGponCommonOntStatisticEntry
            MAX-ACCESS not-accessible
            STATUS current
            DESCRIPTION
                "This table is used to query the information about the priority queue alarm.
                 The indexes of this entry are ifIndex and hwXponOntIndex."
            INDEX       
            { 
            ifIndex,
            hwXponOntIndex
            }
            ::= { hwGponCommonOntStatisticTable 1 }
            
        HwGponCommonOntStatisticEntry ::=
         SEQUENCE
                {
                    hwXponOntUpstreamPQDiscardedBytesAlarmCount                  OCTET STRING,
                    hwXponOntDownstreamPQDiscardedBytesAlarmCount                  OCTET STRING,
                    hwXponOntPQDiscardedBytesAlarmCountClear                     INTEGER
                }
                
        hwXponOntUpstreamPQDiscardedBytesAlarmCount OBJECT-TYPE
            SYNTAX OCTET STRING (SIZE (0..8192))
            MAX-ACCESS read-only
            STATUS current
            DESCRIPTION
                "This object indicates the number of the upstream priority queue alarm due to buffer overflow.
                 One record uses 6 bytes : T-CONT index(1byte)+PQ number(1byte)+alarm number(4bytes)."
          ::= { hwGponCommonOntStatisticEntry 1 }
            
        hwXponOntDownstreamPQDiscardedBytesAlarmCount OBJECT-TYPE
            SYNTAX OCTET STRING (SIZE (0..1280))
            MAX-ACCESS read-only
            STATUS current
            DESCRIPTION
                "This object indicates the number of the downstream priority queue alarm due to buffer overflow.
                 One record uses 8 bytes : port type(1byte)+port index(1byte)+reserve(1byte)+PQ number(1byte)+alarm number(4byte)."
          ::= { hwGponCommonOntStatisticEntry 2 }
            
        hwXponOntPQDiscardedBytesAlarmCountClear  OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwGponCommonOntStatisticEntry 3 }

      --Table hwXponOntStatProbeConfigTable  
        hwXponOntStatProbeConfigTable OBJECT-TYPE
            SYNTAX SEQUENCE OF HwXponOntStatProbeConfigEntry
            MAX-ACCESS not-accessible      
            STATUS     current
            DESCRIPTION
                "This table is used to configure statistical probe.
                  The indexes of this table are ifIndex, hwXponOntIndex and hwXponOntStatProbeConfigIndex."     
            ::= { hwXponCommonStatisticObjects 8 }
        
        hwXponOntStatProbeConfigEntry OBJECT-TYPE
            SYNTAX HwXponOntStatProbeConfigEntry
            MAX-ACCESS not-accessible
            STATUS current
            DESCRIPTION
                "This table is used to configure statistical probe.
                  The indexes of this entry are ifIndex, hwXponOntIndex and hwXponOntStatProbeConfigIndex."
            INDEX       
            { 
                ifIndex,
                hwXponOntIndex,
                hwXponOntStatProbeConfigIndex
            }
            ::= { hwXponOntStatProbeConfigTable 1 }
            
        HwXponOntStatProbeConfigEntry ::=
         SEQUENCE
                {
                    hwXponOntStatProbeConfigIndex        Integer32,
                    hwXponOntStatProbeConfigType         INTEGER,
                    hwXponOntStatProbeConfigParameter    OCTET STRING,
                    hwXponOntStatProbeConfigRowStatus    RowStatus
                }
                
        hwXponOntStatProbeConfigIndex  OBJECT-TYPE
            SYNTAX       Integer32
            MAX-ACCESS   not-accessible
            STATUS       current
            DESCRIPTION
                "Index of the statistical probe. Range: 1-2147483647, and -1. 
                 Value -1 must be issued when this index is configured. Then, the device allocates actual index to the NMS."
            ::= { hwXponOntStatProbeConfigEntry 1}
                
        hwXponOntStatProbeConfigType  OBJECT-TYPE
            SYNTAX     INTEGER{
                vlanBased(1),
                gemPortBased(2),
                multicastGemPortBased(3),
                invalid(-1)
            }
            MAX-ACCESS   read-write
            STATUS      current
            DESCRIPTION
                "This object Indicates the type of statistic probe.
                 Options:
                 1. vlanBased(1)                    - Indicates that the statistics are collected by ONT port, VLAN and VLAN priority.
                 2. gemPortBased(2)                 - Indicates that the statistics are collected by GEM port.
                 3. multicastGemPortBased(3)        - Indicates that the statistics are collected by Multicast GEM port.
                 4. invalid(-1)                     - Indicates that the query fails or no information is detected.
                "
            ::= { hwXponOntStatProbeConfigEntry 2 }
            
        hwXponOntStatProbeConfigParameter OBJECT-TYPE
            SYNTAX      OCTET STRING (SIZE (0..128))
            MAX-ACCESS read-write
            STATUS current
            DESCRIPTION
                "This node indicates the detailed configurations of the statistical probe.
                 If the type of the probe is vlanBased, the format of this node is 'AABBCCCCDD'.
                 AA: Indicates the hexadecimal value of the ONT port type, VDSL(37),ETH(47) and IPHOST(50) is valid.
                 BB: Indicates the hexadecimal value of an ONT port.
                 CCCC: Indicates the hexadecimal value of a VLAN.
                 DD: Indicates the hexadecimal value of the VLAN priority. 'FF' identifies all VLAN priorities, indicating that the VLAN priority is not configured. 
                 If the type of the probe is gemPortBased, the format of this node is 'AAAA'.
                 AAAA: Indicates the hexadecimal value of GEM port ID for distributing-mode or GEM index for profile-mode.
                 If the type of the probe is multicastGemPortBased, the content of this node is null string, doesn't need this parameter.
                 For example, to configure probe with ONT ETH port 1, VLAN 1000, all VLAN priorities, issue '2F0103E8FF'."
            ::= { hwXponOntStatProbeConfigEntry 3}
            
        hwXponOntStatProbeConfigRowStatus OBJECT-TYPE
              SYNTAX RowStatus
              MAX-ACCESS read-create
              STATUS current
              DESCRIPTION
                  "this object is used to create a new row or to modify or delete an existing row in this table.
                   Options:
                   1. createAndGo(4) -create a new instance of a conceptual row 
                   2. destroy(6)     -delete the instances associated with an existing conceptual row
                  "
              ::= { hwXponOntStatProbeConfigEntry 4 }
              
      --Table hwXponOntProbeStatTable  
        hwXponOntProbeStatTable OBJECT-TYPE
            SYNTAX SEQUENCE OF HwXponOntProbeStatEntry
            MAX-ACCESS not-accessible      
            STATUS     current
            DESCRIPTION
                "This table is used to query probe statistics.
                  The indexes of this table are ifIndex, hwXponOntIndex and hwXponOntStatProbeConfigIndex."     
            ::= { hwXponCommonStatisticObjects 9 }
        
        hwXponOntProbeStatEntry OBJECT-TYPE
            SYNTAX HwXponOntProbeStatEntry
            MAX-ACCESS not-accessible
            STATUS current
            DESCRIPTION
                "This table is used to query probe statistics.
                  The indexes of this entry are ifIndex, hwXponOntIndex and hwXponOntStatProbeConfigIndex."
            INDEX       
            { 
                ifIndex,
                hwXponOntIndex,
                hwXponOntStatProbeConfigIndex
            }
            ::= { hwXponOntProbeStatTable 1 }
            
        HwXponOntProbeStatEntry ::=
         SEQUENCE
                {
                    hwXponOntProbeStatResult       Integer32,
                    hwXponOntProbeStatRecvBytes    Counter64,
                    hwXponOntProbeStatRecvFrames   Counter64,
                    hwXponOntProbeStatSendBytes    Counter64,
                    hwXponOntProbeStatSendFrames   Counter64,
                    hwXponOntProbeStatClear        INTEGER
                }
                
        hwXponOntProbeStatResult  OBJECT-TYPE
            SYNTAX     Integer32
            MAX-ACCESS   read-only
            STATUS      current
            DESCRIPTION
                "This node identifies the result of queried probe statistics.
                 Value 0 indicates that probe statistics are queried successfully.
                "
            ::= { hwXponOntProbeStatEntry 1 }
            
        hwXponOntProbeStatRecvBytes OBJECT-TYPE
            SYNTAX      Counter64 
            MAX-ACCESS  read-only
            STATUS      current
            DESCRIPTION
            "This object indicates the received bytes.
            "
            ::={ hwXponOntProbeStatEntry 2 }
            
        hwXponOntProbeStatRecvFrames OBJECT-TYPE
            SYNTAX      Counter64 
            MAX-ACCESS  read-only
            STATUS      current
            DESCRIPTION
            "This object indicates the received frames.
            "
            ::={ hwXponOntProbeStatEntry 3 }
            
        hwXponOntProbeStatSendBytes OBJECT-TYPE
            SYNTAX      Counter64 
            MAX-ACCESS  read-only
            STATUS      current
            DESCRIPTION
            "This object indicates the sent bytes.
            "
            ::={ hwXponOntProbeStatEntry 4 }
            
        hwXponOntProbeStatSendFrames OBJECT-TYPE
            SYNTAX      Counter64 
            MAX-ACCESS  read-only
            STATUS      current
            DESCRIPTION
            "This object indicates the sent frames.
            "
            ::={ hwXponOntProbeStatEntry 5 }
            
        hwXponOntProbeStatClear  OBJECT-TYPE
            SYNTAX     INTEGER{
                clear(1),
                invalid(-1)
            }
            MAX-ACCESS   read-write
            STATUS      current
            DESCRIPTION
                "This node is used to clear probe statistics.
                 Options:
                 1. clear(1)                    - Indicates that clear probe statistics.
                 2. invalid(-1)                 - Indicates that the query fails or no information is detected.
                "
            ::= { hwXponOntProbeStatEntry 6 }
            
       hwGponOntMulticastGemPortStatisticTable OBJECT-TYPE
            SYNTAX  SEQUENCE OF HwGponOntMulticastGemPortStatisticEntry
            MAX-ACCESS not-accessible
            STATUS current
            DESCRIPTION
                "The ONT Multicast GEM Port statistics table.
                 The index of this table is a combination of ifIndex and
                 hwXponOntIndex.
                "
            ::= { hwXponCommonStatisticObjects 10 }

        hwGponOntMulticastGemPortStatisticEntry OBJECT-TYPE
            SYNTAX HwGponOntMulticastGemPortStatisticEntry
            MAX-ACCESS not-accessible
            STATUS current
            DESCRIPTION
                "The ONT Multicast GEM Port statistics table.
                 The index of this entry is a combination of ifIndex and
                 hwXponOntIndex.
                "
            INDEX { ifIndex, hwXponOntIndex }
            ::= { hwGponOntMulticastGemPortStatisticTable 1 }

        HwGponOntMulticastGemPortStatisticEntry ::=
            SEQUENCE {
                hwGponOntMulticastGemPortStatisticRecvLostFrames         Counter64,
                hwGponOntMulticastGemPortStatisticRecvMisinsertedFrames  Counter64,
                hwGponOntMulticastGemPortStatisticRecvFrames             Counter64,
                hwGponOntMulticastGemPortStatisticRecvBlocks             Counter64,
                hwGponOntMulticastGemPortStatisticSendBlocks             Counter64,
                hwGponOntMulticastGemPortStatisticImpairedBlocks         Counter64, 
                hwGponOntMulticastGemPortStatisticSendGemFrames          Counter64, 
                hwGponOntMulticastGemPortStatisticClear                  INTEGER
            }

        hwGponOntMulticastGemPortStatisticRecvLostFrames OBJECT-TYPE
            SYNTAX Counter64
            MAX-ACCESS read-only
            STATUS current
            DESCRIPTION
                "This object indicates the loss of frames."
            ::= { hwGponOntMulticastGemPortStatisticEntry 1 }

        hwGponOntMulticastGemPortStatisticRecvMisinsertedFrames OBJECT-TYPE
            SYNTAX Counter64
            MAX-ACCESS read-only
            STATUS current
            DESCRIPTION
                "This object indicates the misinserted frames."
            ::= { hwGponOntMulticastGemPortStatisticEntry 2 }

        hwGponOntMulticastGemPortStatisticRecvFrames OBJECT-TYPE
            SYNTAX Counter64
            MAX-ACCESS read-only
            STATUS current
            DESCRIPTION
                "This object indicates the received frames."
            ::= { hwGponOntMulticastGemPortStatisticEntry 3 }

        hwGponOntMulticastGemPortStatisticRecvBlocks OBJECT-TYPE
            SYNTAX Counter64
            MAX-ACCESS read-only
            STATUS current
            DESCRIPTION
                "This object indicates the received blocks."
            ::= { hwGponOntMulticastGemPortStatisticEntry 4 }

        hwGponOntMulticastGemPortStatisticSendBlocks OBJECT-TYPE
            SYNTAX Counter64
            MAX-ACCESS read-only
            STATUS current
            DESCRIPTION
                "This object indicates the sent blocks."
            ::= { hwGponOntMulticastGemPortStatisticEntry 5 }

        hwGponOntMulticastGemPortStatisticImpairedBlocks OBJECT-TYPE
            SYNTAX Counter64
            MAX-ACCESS read-only
            STATUS current
            DESCRIPTION
                "This object indicates the number of received impaired data blocks."
            ::= { hwGponOntMulticastGemPortStatisticEntry 6 }   
            
        hwGponOntMulticastGemPortStatisticSendGemFrames OBJECT-TYPE
            SYNTAX Counter64
            MAX-ACCESS read-only
            STATUS current
            DESCRIPTION
               "This object indicates the number of transmitted GEM frames."
               ::= { hwGponOntMulticastGemPortStatisticEntry 7 }

        hwGponOntMulticastGemPortStatisticClear OBJECT-TYPE
            SYNTAX INTEGER{
                clear(1),
                invalid(-1)
            }
            MAX-ACCESS read-write
            STATUS current
            DESCRIPTION
                "This object is used to clear the statistics.
                 Options:
                 1. clear(1)                    - Indicates that clear the statistics
                 2. invalid(-1)                 - Indicates that the query fails or no information is detected
                "
            ::= { hwGponOntMulticastGemPortStatisticEntry 20 }
            
      --Table hwGponOntTdmPortPerf15MinTable  
        hwGponOntTdmPortPerf15MinTable OBJECT-TYPE
            SYNTAX SEQUENCE OF HwGponOntTdmPortPerf15MinEntry
            MAX-ACCESS not-accessible      
            STATUS     current
            DESCRIPTION
                "This table is used to query ONT TDM port statistics in history 15 minutes.
                  The indexes of this table are ifIndex, hwXponOntIndex, hwGponDeviceOntPhyIndex and hwGponOntTdmPortPerf15minIntervalNum."     
            ::= { hwXponCommonStatisticObjects 11 }
        
        hwGponOntTdmPortPerf15MinEntry OBJECT-TYPE
            SYNTAX HwGponOntTdmPortPerf15MinEntry
            MAX-ACCESS not-accessible
            STATUS current
            DESCRIPTION
                "This table is used to query ONT TDM port statistics in history 15 minutes.
                  The indexes of this entry are ifIndex, hwXponOntIndex, hwGponDeviceOntPhyIndex and hwGponOntTdmPortPerf15minIntervalNum."
            INDEX       
            { 
                ifIndex,
                hwXponOntIndex,
                hwGponDeviceOntPhyIndex,
                hwGponOntTdmPortPerf15minIntervalNum
            }
            ::= { hwGponOntTdmPortPerf15MinTable 1 }
            
        HwGponOntTdmPortPerf15MinEntry ::=
         SEQUENCE
                {
                    hwGponOntTdmPortPerf15minIntervalNum  Integer32,
                    hwGponOntTdmPortPerf15minES    Gauge32,
                    hwGponOntTdmPortPerf15minSES   Gauge32,
                    hwGponOntTdmPortPerf15minUAS   Gauge32,
                    hwGponOntTdmPortPerf15minEFS   Gauge32
                }
                
        hwGponOntTdmPortPerf15minIntervalNum OBJECT-TYPE
            SYNTAX     Integer32
            MAX-ACCESS   not-accessible
            STATUS      current
            DESCRIPTION
                "This object indicates the history 15 minutes interval number. 
                 value 0 indicates current 15 minutes interval.
                "
            ::= { hwGponOntTdmPortPerf15MinEntry 1 }
            
        hwGponOntTdmPortPerf15minES OBJECT-TYPE
            SYNTAX      Gauge32 
            MAX-ACCESS  read-only
            STATUS      current
            DESCRIPTION
            "This object indicates the statistic of the errored seconds.
             -1 indicates the invalid value.
            "
            ::={ hwGponOntTdmPortPerf15MinEntry 2 }
            
        hwGponOntTdmPortPerf15minSES OBJECT-TYPE
            SYNTAX      Gauge32 
            MAX-ACCESS  read-only
            STATUS      current
            DESCRIPTION
            "This object indicates the statistic of the serverly erroeds.
             -1 indicates the invalid value.
            "
            ::={ hwGponOntTdmPortPerf15MinEntry 3 }
            
        hwGponOntTdmPortPerf15minUAS OBJECT-TYPE
            SYNTAX      Gauge32 
            MAX-ACCESS  read-only
            STATUS      current
            DESCRIPTION
            "This object indicates the statistic of the unavailable seconds.
             -1 indicates the invalid value.
            "
            ::={ hwGponOntTdmPortPerf15MinEntry 4}
            
        hwGponOntTdmPortPerf15minEFS OBJECT-TYPE
            SYNTAX      Gauge32 
            MAX-ACCESS  read-only
            STATUS      current
            DESCRIPTION
            "This object indicates the statistic of the error free seconds.
             -1 indicates the invalid value.
            "
            ::={ hwGponOntTdmPortPerf15MinEntry 5 }
			
	  --Table hwGponDevicePotsPortHis15MinStatisticTable
        hwGponDevicePotsPortHis15MinStatisticTable OBJECT-TYPE
            SYNTAX      SEQUENCE OF HwGponDevicePotsPortHis15MinStatisticEntry
            MAX-ACCESS  not-accessible
            STATUS      current
            DESCRIPTION
                "VOIP perform monitor statistic table. This table is used to query Pots
                 port statistic.
                 The indexes of this table are ifIndex, hwGponDeviceOntObjIndex and
                 hwGponDeviceOntPhyIndex.
                "
            ::= { hwXponCommonStatisticObjects 12 }

        hwGponDevicePotsPortHis15MinStatisticEntry OBJECT-TYPE
            SYNTAX      HwGponDevicePotsPortHis15MinStatisticEntry
            MAX-ACCESS  not-accessible
            STATUS      current
            DESCRIPTION
                "VOIP perform monitor statistic table. This table is used to query Pots
                 port statistic.
                 The indexes of this entry are ifIndex, hwGponDeviceOntObjIndex and
                 hwGponDeviceOntPhyIndex.
                "
            INDEX
                {
                ifIndex,
                hwGponDeviceOntObjIndex,
                hwGponDeviceOntPhyIndex
                }
            ::= { hwGponDevicePotsPortHis15MinStatisticTable 1 }

        HwGponDevicePotsPortHis15MinStatisticEntry ::=
            SEQUENCE
                {
	            hwGponDevicePotsPortHis15MinNumber		              Gauge32,
                hwGponDevicePotsHis15MinStatisticRtpError             Gauge32,
                hwGponDevicePotsHis15MinStatisticPacketLoss           Gauge32,
                hwGponDevicePotsPortHis15MinMaxJitter                 Gauge32,
                hwGponDevicePotsPortHis15MinMaxTimeRTCP               Gauge32,
                hwGponDevicePotsHis15MinStatisticUnderFlowBuff        Gauge32,
                hwGponDevicePotsHis15MinStatisticOverFlowBuff         Gauge32,
                hwGponDevicePotsHis15MinStatisticCallSetupFails       Gauge32,
                hwGponDevicePotsPortHis15MinCallSetupTimer            Gauge32,
                hwGponDevicePotsHis15MinStatisticCallTerminateFails   Gauge32,
                hwGponDevicePotsHis15MinStatisticAnalogPortRelease    Gauge32,
                hwGponDevicePotsPortHis15MinAnalogPortOffHookTimer    Gauge32
                }
				
        hwGponDevicePotsPortHis15MinNumber OBJECT-TYPE
            SYNTAX      Gauge32
            MAX-ACCESS  read-only
            STATUS      current
            DESCRIPTION
                "Statistic data interval number 1 is the most recent previous 
				15 minutes interval. Rang:1."
            ::={ hwGponDevicePotsPortHis15MinStatisticEntry 1 }
			
		hwGponDevicePotsHis15MinStatisticRtpError OBJECT-TYPE
            SYNTAX      Gauge32
            MAX-ACCESS  read-only
            STATUS      current
            DESCRIPTION
                "The statistic of RTP packet errors."
            ::={ hwGponDevicePotsPortHis15MinStatisticEntry 2 }

        hwGponDevicePotsHis15MinStatisticPacketLoss OBJECT-TYPE
            SYNTAX      Gauge32
            MAX-ACCESS  read-only
            STATUS      current
            DESCRIPTION
                "The statistic of the fraction of packets lost."
            ::={ hwGponDevicePotsPortHis15MinStatisticEntry 3 }

        hwGponDevicePotsPortHis15MinMaxJitter OBJECT-TYPE
            SYNTAX      Gauge32
            MAX-ACCESS  read-only
            STATUS      current
            DESCRIPTION
                "The maximum jitter identified during the measured interval."
            ::={ hwGponDevicePotsPortHis15MinStatisticEntry 4 }

        hwGponDevicePotsPortHis15MinMaxTimeRTCP OBJECT-TYPE
            SYNTAX      Gauge32
            MAX-ACCESS  read-only
            STATUS      current
            DESCRIPTION
                "The maximum time between RTCP packets."
            ::={ hwGponDevicePotsPortHis15MinStatisticEntry 5 }

        hwGponDevicePotsHis15MinStatisticUnderFlowBuff OBJECT-TYPE
            SYNTAX      Gauge32
            MAX-ACCESS  read-only
            STATUS      current
            DESCRIPTION
                "The statistic of times the reassembly buffer underflows."
            ::={ hwGponDevicePotsPortHis15MinStatisticEntry 6 }

        hwGponDevicePotsHis15MinStatisticOverFlowBuff OBJECT-TYPE
            SYNTAX      Gauge32
            MAX-ACCESS  read-only
            STATUS      current
            DESCRIPTION
                "The statistic of times the reassembly buffer overflows."
            ::={ hwGponDevicePotsPortHis15MinStatisticEntry 7 }

        hwGponDevicePotsHis15MinStatisticCallSetupFails OBJECT-TYPE
            SYNTAX      Gauge32
            MAX-ACCESS  read-only
            STATUS      current
            DESCRIPTION
                "The statistic of call setup failures."
            ::={ hwGponDevicePotsPortHis15MinStatisticEntry 8 }

        hwGponDevicePotsPortHis15MinCallSetupTimer OBJECT-TYPE
            SYNTAX      Gauge32
            MAX-ACCESS  read-only
            STATUS      current
            DESCRIPTION
                "The longest duration of a single call setup detected during this interval."
            ::={ hwGponDevicePotsPortHis15MinStatisticEntry 9 }

        hwGponDevicePotsHis15MinStatisticCallTerminateFails OBJECT-TYPE
            SYNTAX      Gauge32
            MAX-ACCESS  read-only
            STATUS      current
            DESCRIPTION
                "The statistic of calls that were terminated with cause."
            ::={ hwGponDevicePotsPortHis15MinStatisticEntry 10 }

        hwGponDevicePotsHis15MinStatisticAnalogPortRelease OBJECT-TYPE
            SYNTAX      Gauge32
            MAX-ACCESS  read-only
            STATUS      current
            DESCRIPTION
                "The statistic of analog port releases without dialling detected."
            ::={ hwGponDevicePotsPortHis15MinStatisticEntry 11 }

        hwGponDevicePotsPortHis15MinAnalogPortOffHookTimer OBJECT-TYPE
            SYNTAX      Gauge32
            MAX-ACCESS  read-only
            STATUS      current
            DESCRIPTION
                "The longest period of a single off-hook detected on the analog port."
            ::={ hwGponDevicePotsPortHis15MinStatisticEntry 12 }
            
       --Table hwXponOntPortEthernetStatsTable  
        hwXponOntPortEthernetStatsTable OBJECT-TYPE
            SYNTAX SEQUENCE OF HwXponOntPortEthernetStatsEntry
            MAX-ACCESS not-accessible      
            STATUS     current
            DESCRIPTION
                "The ONT port statistics table.
                  The indexes of this table are ifIndex, hwXponOntIndex, hwGponOntifType and hwGponOntifPort."     
            ::= { hwXponCommonStatisticObjects 13 }
        
        hwXponOntPortEthernetStatsEntry OBJECT-TYPE
            SYNTAX HwXponOntPortEthernetStatsEntry
            MAX-ACCESS not-accessible
            STATUS current
            DESCRIPTION
                "The ONT port statistics table.
                  The indexes of this entry are ifIndex, hwXponOntIndex, hwGponOntifType and hwGponOntifPort."
            INDEX       
            { 
                ifIndex,
                hwXponOntIndex,
                hwGponOntifType,
                hwGponOntifPort
            }
            ::= { hwXponOntPortEthernetStatsTable 1 }
            
        HwXponOntPortEthernetStatsEntry ::=
         SEQUENCE
                {
                    hwXponOntPortEthernetStatisticRecvOctets                Counter64,
                    hwXponOntPortEthernetStatisticRecvPkts                  Counter64,
                    hwXponOntPortEthernetStatisticRecvBroadcastPkts         Counter64,
                    hwXponOntPortEthernetStatisticRecvMulticastPkts         Counter64,
                    hwXponOntPortEthernetStatisticRecvPkts64Octets          Counter64,
                    hwXponOntPortEthernetStatisticRecvPkts65to127Octets     Counter64,
                    hwXponOntPortEthernetStatisticRecvPkts128to255Octets    Counter64,
                    hwXponOntPortEthernetStatisticRecvPkts256to511Octets    Counter64,
                    hwXponOntPortEthernetStatisticRecvPkts512to1023Octets   Counter64,
                    hwXponOntPortEthernetStatisticRecvPkts1024to1518Octets  Counter64,
                    hwXponOntPortEthernetStatisticRecvPktsOversize          Counter64,
                    hwXponOntPortEthernetStatisticRecvPktsUndersize         Counter64,
                    hwXponOntPortEthernetStatisticRecvFCSErrors             Counter64,
                    hwXponOntPortEthernetStatisticRecvDropEvents            Counter64,
                    hwXponOntPortEthernetStatisticSendOctets                Counter64,
                    hwXponOntPortEthernetStatisticSendPkts                  Counter64,
                    hwXponOntPortEthernetStatisticSendBroadcastPkts         Counter64,
                    hwXponOntPortEthernetStatisticSendMulticastPkts         Counter64,
                    hwXponOntPortEthernetStatisticSendPkts64Octets          Counter64,
                    hwXponOntPortEthernetStatisticSendPkts65to127Octets     Counter64,
                    hwXponOntPortEthernetStatisticSendPkts128to255Octets    Counter64,
                    hwXponOntPortEthernetStatisticSendPkts256to511Octets    Counter64,
                    hwXponOntPortEthernetStatisticSendPkts512to1023Octets   Counter64,
                    hwXponOntPortEthernetStatisticSendPkts1024to1518Octets  Counter64,
                    hwXponOntPortEthernetStatisticSendPktsOversize          Counter64,
                    hwXponOntPortEthernetStatisticForwardDropEvents         Counter64,
                    hwXponOntPortEthernetStatisticClear                     INTEGER
                }
                
        hwXponOntPortEthernetStatisticRecvOctets OBJECT-TYPE
            SYNTAX Counter64
            MAX-ACCESS read-only
            STATUS current
            DESCRIPTION
                "This object indicates the received bytes."
            ::= { hwXponOntPortEthernetStatsEntry 1 }

        hwXponOntPortEthernetStatisticRecvPkts OBJECT-TYPE
            SYNTAX Counter64
            MAX-ACCESS read-only
            STATUS current
            DESCRIPTION
                "This object indicates the received frames."
            ::= { hwXponOntPortEthernetStatsEntry 2 }
            
        hwXponOntPortEthernetStatisticRecvBroadcastPkts OBJECT-TYPE
            SYNTAX Counter64
            MAX-ACCESS read-only
            STATUS current
            DESCRIPTION
                "This object indicates the received broadcast frames."
            ::= { hwXponOntPortEthernetStatsEntry 3 }

        hwXponOntPortEthernetStatisticRecvMulticastPkts OBJECT-TYPE
            SYNTAX Counter64
            MAX-ACCESS read-only
            STATUS current
            DESCRIPTION
                "This object indicates the received multicast frames."
            ::= { hwXponOntPortEthernetStatsEntry 4 }

        hwXponOntPortEthernetStatisticRecvPkts64Octets OBJECT-TYPE
            SYNTAX Counter64
            MAX-ACCESS read-only
            STATUS current
            DESCRIPTION
                "This object indicates the received 64-octet frames"
            ::= { hwXponOntPortEthernetStatsEntry 5 }

        hwXponOntPortEthernetStatisticRecvPkts65to127Octets OBJECT-TYPE
            SYNTAX Counter64
            MAX-ACCESS read-only
            STATUS current
            DESCRIPTION
                "This object indicates the received 65~127-octet frames"
            ::= { hwXponOntPortEthernetStatsEntry 6 }

        hwXponOntPortEthernetStatisticRecvPkts128to255Octets OBJECT-TYPE
            SYNTAX Counter64
            MAX-ACCESS read-only
            STATUS current
            DESCRIPTION
                "This object indicates the received 128~255-octet frames"
            ::= { hwXponOntPortEthernetStatsEntry 7 }

        hwXponOntPortEthernetStatisticRecvPkts256to511Octets OBJECT-TYPE
            SYNTAX Counter64
            MAX-ACCESS read-only
            STATUS current
            DESCRIPTION
                "This object indicates the received 256~511-octet frames."
            ::= { hwXponOntPortEthernetStatsEntry 8 }

        hwXponOntPortEthernetStatisticRecvPkts512to1023Octets OBJECT-TYPE
            SYNTAX Counter64
            MAX-ACCESS read-only
            STATUS current
            DESCRIPTION
                "This object indicates the received 512~1023-octet frames."
            ::= { hwXponOntPortEthernetStatsEntry 9 }

        hwXponOntPortEthernetStatisticRecvPkts1024to1518Octets OBJECT-TYPE
            SYNTAX Counter64
            MAX-ACCESS read-only
            STATUS current
            DESCRIPTION
                "This object indicates the received 1024~1518-octet frames."
            ::= { hwXponOntPortEthernetStatsEntry 10 }
            
        hwXponOntPortEthernetStatisticRecvPktsOversize OBJECT-TYPE
            SYNTAX Counter64
            MAX-ACCESS read-only
            STATUS current
            DESCRIPTION
                "This object indicates the received oversize frames."
            ::= { hwXponOntPortEthernetStatsEntry 11 }
            
        hwXponOntPortEthernetStatisticRecvPktsUndersize OBJECT-TYPE
            SYNTAX Counter64
            MAX-ACCESS read-only
            STATUS current
            DESCRIPTION
                "This object indicates the received undersize frames."
            ::= { hwXponOntPortEthernetStatsEntry 12 }

        hwXponOntPortEthernetStatisticRecvFCSErrors  OBJECT-TYPE
            SYNTAX Counter64
            MAX-ACCESS read-only
            STATUS current
            DESCRIPTION
                "This object indicates the received FCS error frames."
            ::= { hwXponOntPortEthernetStatsEntry 13 }
            
        hwXponOntPortEthernetStatisticRecvDropEvents  OBJECT-TYPE
            SYNTAX Counter64
            MAX-ACCESS read-only
            STATUS current
            DESCRIPTION
                "This object indicates the received drop events."
            ::= { hwXponOntPortEthernetStatsEntry 14 }

        hwXponOntPortEthernetStatisticSendOctets  OBJECT-TYPE
            SYNTAX Counter64
            MAX-ACCESS read-only
            STATUS current
            DESCRIPTION
                "This object indicates the send drop bytes."
            ::= { hwXponOntPortEthernetStatsEntry 15 }

        hwXponOntPortEthernetStatisticSendPkts  OBJECT-TYPE
            SYNTAX Counter64
            MAX-ACCESS read-only
            STATUS current
            DESCRIPTION
                "This object indicates the send frames."
            ::= { hwXponOntPortEthernetStatsEntry 16 }

        hwXponOntPortEthernetStatisticSendBroadcastPkts  OBJECT-TYPE
            SYNTAX Counter64
            MAX-ACCESS read-only
            STATUS current
            DESCRIPTION
                "This object indicates the sent broadcast frames."
            ::= { hwXponOntPortEthernetStatsEntry 17 }

                hwXponOntPortEthernetStatisticSendMulticastPkts  OBJECT-TYPE
            SYNTAX Counter64
            MAX-ACCESS read-only
            STATUS current
            DESCRIPTION
                "This object indicates the sent multicast frames."
            ::= { hwXponOntPortEthernetStatsEntry 18 }
            
         hwXponOntPortEthernetStatisticSendPkts64Octets  OBJECT-TYPE
            SYNTAX Counter64
            MAX-ACCESS read-only
            STATUS current
            DESCRIPTION
                "This object indicates the sent 64-octet frames."
            ::= { hwXponOntPortEthernetStatsEntry 19 }            
            
         hwXponOntPortEthernetStatisticSendPkts65to127Octets  OBJECT-TYPE
            SYNTAX Counter64
            MAX-ACCESS read-only
            STATUS current
            DESCRIPTION
                "This object indicates the sent 65~127-octet frames."
            ::= { hwXponOntPortEthernetStatsEntry 20 }            
            
        hwXponOntPortEthernetStatisticSendPkts128to255Octets  OBJECT-TYPE
            SYNTAX Counter64
            MAX-ACCESS read-only
            STATUS current
            DESCRIPTION
                "This object indicates the sent 128~255-octet frames."
            ::= { hwXponOntPortEthernetStatsEntry 21}
            
         hwXponOntPortEthernetStatisticSendPkts256to511Octets   OBJECT-TYPE
            SYNTAX Counter64
            MAX-ACCESS read-only
            STATUS current
            DESCRIPTION
                "This object indicates the sent 256~511-octet frames."
            ::= { hwXponOntPortEthernetStatsEntry 22 }
            
      hwXponOntPortEthernetStatisticSendPkts512to1023Octets   OBJECT-TYPE
            SYNTAX Counter64
            MAX-ACCESS read-only
            STATUS current
            DESCRIPTION
                "This object indicates the sent 512~1023-octet frames."
            ::= { hwXponOntPortEthernetStatsEntry 23 }
            
      hwXponOntPortEthernetStatisticSendPkts1024to1518Octets   OBJECT-TYPE
            SYNTAX Counter64
            MAX-ACCESS read-only
            STATUS current
            DESCRIPTION
                "This object indicates the sent 1024~1518-octet frames."
            ::= { hwXponOntPortEthernetStatsEntry 24 }      
       
       hwXponOntPortEthernetStatisticSendPktsOversize    OBJECT-TYPE
            SYNTAX Counter64
            MAX-ACCESS read-only
            STATUS current
            DESCRIPTION
                "This object indicates the sent oversize frames."
            ::= { hwXponOntPortEthernetStatsEntry 25 }
            
       hwXponOntPortEthernetStatisticForwardDropEvents  OBJECT-TYPE
            SYNTAX Counter64
            MAX-ACCESS read-only
            STATUS current
            DESCRIPTION
                "This object indicates the sent drop events."
            ::= { hwXponOntPortEthernetStatsEntry 26 }
             
       hwXponOntPortEthernetStatisticClear   OBJECT-TYPE
            SYNTAX INTEGER{
                clear(1),
                invalid(-1)
            }
            MAX-ACCESS read-write
            STATUS current
            DESCRIPTION
                "This object is used to clear the statistics.
                 Options:
                 1. clear(1)       - Indicates that clear the statistics
                 2. invalid(-1)    - Indicates that the query fails or no information is detected
                "
            ::= { hwXponOntPortEthernetStatsEntry 27 }  
      
       --Table hwXponOntPowerReductionStatisticTable  
        hwXponOntPowerReductionStatisticTable OBJECT-TYPE
            SYNTAX SEQUENCE OF HwXponOntPowerReductionStatisticEntry
            MAX-ACCESS not-accessible      
            STATUS     current
            DESCRIPTION
                "This table is used to query the information about the ONT power reduction statistics. 
                 It is only used for defining GPON management common MIB objects for both profile-mode and distributing-mode.
                 The indexes of this table are ifIndex and hwXponOntIndex."     
            ::= { hwXponCommonStatisticObjects 14 }
        
        hwXponOntPowerReductionStatisticEntry OBJECT-TYPE
            SYNTAX HwXponOntPowerReductionStatisticEntry
            MAX-ACCESS not-accessible
            STATUS current
            DESCRIPTION
                "This table is used to query the information about the ONT power reduction statistics. 
                 It is only used for defining GPON management common MIB objects for both profile-mode and distributing-mode.
                 The indexes of this entry are ifIndex and hwXponOntIndex."  
            INDEX       
            { 
            ifIndex,
            hwXponOntIndex
            }
            ::= { hwXponOntPowerReductionStatisticTable 1 }
            
        HwXponOntPowerReductionStatisticEntry ::=
         SEQUENCE
                {
                    hwXponOntPowerReductionDozeTime                              Counter64,
                    hwXponOntPowerReductionCyclicSleepTime                       Counter64,
                    hwXponOntPowerReductionWatchfulSleepTime                     Counter64,
                    hwXponOntPowerReductionEnergySaved                           Counter64,
                    hwXponOntPowerReductionCountClear                            INTEGER                   
                    
                }
                
       hwXponOntPowerReductionDozeTime    OBJECT-TYPE
           SYNTAX       Counter64
           MAX-ACCESS read-only
           STATUS current    
           DESCRIPTION
                "This object indicates the total doze time of power reduction ONT since its statistics have been cleared last time.
                 It is defined as an 64-bit integer whose unit is 'S'(Second)."
          ::= { hwXponOntPowerReductionStatisticEntry 1 }
          
       hwXponOntPowerReductionCyclicSleepTime    OBJECT-TYPE
           SYNTAX       Counter64
           MAX-ACCESS read-only
           STATUS current    
           DESCRIPTION
                "This object indicates the total cyclic sleep time of power reduction ONT since its statistics have been cleared last time.
                 It is defined as an 64-bit integer whose unit is 'S'(Second)."
          ::= { hwXponOntPowerReductionStatisticEntry 2 } 
          
       hwXponOntPowerReductionWatchfulSleepTime    OBJECT-TYPE
           SYNTAX       Counter64
           MAX-ACCESS read-only
           STATUS current    
           DESCRIPTION
                "This object indicates the total watchful sleep time of power reduction ONT since its statistics have been cleared last time.
                It is defined as an 64-bit integer whose unit is 'S'(Second)."

          ::= { hwXponOntPowerReductionStatisticEntry 3 } 
       
       hwXponOntPowerReductionEnergySaved    OBJECT-TYPE
           SYNTAX       Counter64
           MAX-ACCESS read-only
           STATUS current    
           DESCRIPTION
                "This object indicates the total energy saved for power reduction ONT since its statistics have been cleared last time.
                It is defined as an 64-bit integer whose unit is 'J'(standard energy unit)."

          ::= { hwXponOntPowerReductionStatisticEntry 4 }
         
       hwXponOntPowerReductionCountClear  OBJECT-TYPE
            SYNTAX     INTEGER{
                clear (1),
                invalid (-1) 
            }
            MAX-ACCESS   read-write
            STATUS      current
            DESCRIPTION
                "This object is used to clear the statistics.
                 Options:
                 1. clear(1)                    - Indicates that clear the  power reduction statistics
                 2. invalid(-1)                 - Indicates that the query fails or no information is detected
                "
            ::= { hwXponOntPowerReductionStatisticEntry 5 } 
   
      --Table hwGponPortTrafficStatisticTable  
       hwGponPortTrafficStatisticTable OBJECT-TYPE
            SYNTAX SEQUENCE OF HwGponPortTrafficStatisticEntry
            MAX-ACCESS not-accessible      
            STATUS     current
            DESCRIPTION
                "This table is used to query the information about the traffic congestion statistics. 
                 The indexes of this table are ifIndex and hwGponPortTrafficStatisticIndex."     
            ::= { hwXponCommonStatisticObjects 15 }
	    
        hwGponPortTrafficStatisticEntry OBJECT-TYPE
            SYNTAX HwGponPortTrafficStatisticEntry
            MAX-ACCESS not-accessible
            STATUS current
            DESCRIPTION
                "This table is used to query the information about the traffic congestion statistics. 
                 The indexes of this entry are ifIndex and hwGponPortTrafficStatisticIndex."  
            INDEX
            { 
            ifIndex,
            hwGponPortTrafficStatisticIndex
            }
            ::= { hwGponPortTrafficStatisticTable 1 }
	    
        HwGponPortTrafficStatisticEntry ::=
         SEQUENCE
                {
                    hwGponPortTrafficStatisticIndex                        Integer32,
                    hwGponPortTrafficStatisticUpstreamRate                 Integer32,                  
                    hwGponPortTrafficStatisticDownstreamRate               Integer32,    
                    hwGponPortTrafficStatisticUpstreamCongestionTimes      Integer32, 
                    hwGponPortTrafficStatisticDownstreamCongestionTimes    Integer32
                }
		
        hwGponPortTrafficStatisticIndex  OBJECT-TYPE
            SYNTAX       Integer32
            MAX-ACCESS   not-accessible
            STATUS       current
            DESCRIPTION
                "Index of the traffic congestion statistics. Range: 0-1. 
                 Value 0 query current period traffic congestion statistics
                 Value 1 query last period traffic congestion statistics."
            ::= { hwGponPortTrafficStatisticEntry 1}        
	    
        hwGponPortTrafficStatisticUpstreamRate    OBJECT-TYPE
            SYNTAX       Integer32
            MAX-ACCESS read-only
            STATUS current    
            DESCRIPTION
                 "This object indicates the received average rate of this port.
                  It is defined as an 32-bit integer whose unit is 'kbps'."
           ::= { hwGponPortTrafficStatisticEntry 2 }
	   
        hwGponPortTrafficStatisticDownstreamRate    OBJECT-TYPE
            SYNTAX       Integer32
            MAX-ACCESS read-only
            STATUS current    
            DESCRIPTION
                 "This object indicates the transmitted average rate of this port.
                  It is defined as an 32-bit integer whose unit is 'kbps'."
           ::= { hwGponPortTrafficStatisticEntry 3 }
	   
        hwGponPortTrafficStatisticUpstreamCongestionTimes    OBJECT-TYPE
            SYNTAX       Integer32
            MAX-ACCESS read-only
            STATUS current    
            DESCRIPTION
                 "This object indicates the Upstream congestion period number."
           ::= { hwGponPortTrafficStatisticEntry 4 }  
	   
        hwGponPortTrafficStatisticDownstreamCongestionTimes    OBJECT-TYPE
            SYNTAX       Integer32
            MAX-ACCESS read-only
            STATUS current    
            DESCRIPTION
                 "This object indicates the Downstream congestion period number."
           ::= { hwGponPortTrafficStatisticEntry 5 }     
      --hwGponPortTrafficStatisticTable   end  	
      
      -- Table: hwGponComboOltEthernetStatisticTable
        hwGponComboOltEthernetStatisticTable OBJECT-TYPE
            SYNTAX     SEQUENCE OF HwGponComboOltEthernetStatisticEntry
            MAX-ACCESS not-accessible
            STATUS     current
            DESCRIPTION
                "This table is the Combo PON port ether statistics table. 
                 The indexes of this table are ifIndex and hwGponComboOltEthernetStatisticChannelID."
            ::= { hwXponCommonStatisticObjects 16 }    
            
        hwGponComboOltEthernetStatisticEntry OBJECT-TYPE
            SYNTAX     HwGponComboOltEthernetStatisticEntry
            MAX-ACCESS not-accessible
            STATUS     current
            DESCRIPTION
                "This table is the Combo PON port ether statistics table. 
                 The indexes of this entry  are ifIndex and hwGponComboOltEthernetStatisticChannelID."
            INDEX       { ifIndex, hwGponComboOltEthernetStatisticChannelID }
            ::= { hwGponComboOltEthernetStatisticTable 1 }   
            
        HwGponComboOltEthernetStatisticEntry ::=
            SEQUENCE { 
                hwGponComboOltEthernetStatisticChannelID                      INTEGER,
                hwGponComboOltEthernetStatisticReceivedPakts                  Counter64,
                hwGponComboOltEthernetStatisticSendPakts                      Counter64,
                hwGponComboOltEthernetStatisticDropPakts                      Counter64,
                hwGponComboOltEthernetStatisticReceivedTotalPakts             Counter64,
                hwGponComboOltEthernetStatisticReceivedBroadcastPakts         Counter64,
                hwGponComboOltEthernetStatisticReceivedMulticastPakts         Counter64,
                hwGponComboOltEthernetStatisticReceivedUnicastPakts           Counter64,
                hwGponComboOltEthernetStatisticReceivedLen64Bytes             Counter64,
                hwGponComboOltEthernetStatisticReceivedLen65To127Bytes        Counter64,
                hwGponComboOltEthernetStatisticReceivedLen128To255Bytes       Counter64,
                hwGponComboOltEthernetStatisticReceivedLen256To511Bytes       Counter64,
                hwGponComboOltEthernetStatisticReceivedLen512To1023Bytes      Counter64,
                hwGponComboOltEthernetStatisticReceivedLen1024To1518Bytes     Counter64,
                hwGponComboOltEthernetStatisticReceivedLenMore1518Bytes       Counter64,
                hwGponComboOltEthernetStatisticReceivedBytes                  Counter64,
                hwGponComboOltEthernetStatisticReceivedTooLongPakts           Counter64,
                hwGponComboOltEthernetStatisticReceivedTooShortPakts          Counter64,
                hwGponComboOltEthernetStatisticReceivedCRCErrPakts            Counter64,
                hwGponComboOltEthernetStatisticSendTotalPakts                 Counter64,
                hwGponComboOltEthernetStatisticSendBroadcastPakts             Counter64,
                hwGponComboOltEthernetStatisticSendMulticastPakts             Counter64,
                hwGponComboOltEthernetStatisticSendUnicastPakts               Counter64,
                hwGponComboOltEthernetStatisticSendLen64Bytes                 Counter64,
                hwGponComboOltEthernetStatisticSendLen65To127Bytes            Counter64,
                hwGponComboOltEthernetStatisticSendLen128To255Bytes           Counter64,
                hwGponComboOltEthernetStatisticSendLen256To511Bytes           Counter64,
                hwGponComboOltEthernetStatisticSendLen512To1023Bytes          Counter64,
                hwGponComboOltEthernetStatisticSendLen1024To1518Bytes         Counter64,
                hwGponComboOltEthernetStatisticSendLenMore1518Bytes           Counter64,
                hwGponComboOltEthernetStatisticSendBytes                      Counter64,
                hwGponComboOltEthernetStatisticSendMulticastBytes             Counter64
            }                           
            
        hwGponComboOltEthernetStatisticChannelID OBJECT-TYPE
            SYNTAX  INTEGER
              {                      
                  gpon(1),
                  xgpon(2)
              } 
           MAX-ACCESS  not-accessible
           STATUS      current
           DESCRIPTION
                   "This object indicates the channel of the Combo PON port.
                    Options:
                    1. gpon(1)      - Indicates that the channel of the Combo PON port is GPON.
                    2. xgpon(2)     - Indicates that the channel of the Combo PON port is XG-PON.                                                                              
                   "
           ::= { hwGponComboOltEthernetStatisticEntry 1 }    
           
        hwGponComboOltEthernetStatisticReceivedPakts  OBJECT-TYPE
            SYNTAX     Counter64
            MAX-ACCESS   read-only
            STATUS      current
            DESCRIPTION
                "This object indicates the received frames."
            ::= { hwGponComboOltEthernetStatisticEntry 2 }  
            
        hwGponComboOltEthernetStatisticSendPakts  OBJECT-TYPE
            SYNTAX     Counter64
            MAX-ACCESS   read-only
            STATUS      current
            DESCRIPTION
                "This object indicates the sent frames."
            ::= { hwGponComboOltEthernetStatisticEntry 3 }  
            
        hwGponComboOltEthernetStatisticDropPakts  OBJECT-TYPE
            SYNTAX     Counter64
            MAX-ACCESS   read-only
            STATUS      current
            DESCRIPTION
                "This object indicates the number of Ethernet frames, including oversized frames,
                 undersized frames, and CRC failures.
                "
            ::= { hwGponComboOltEthernetStatisticEntry 4 } 
            
        hwGponComboOltEthernetStatisticReceivedTotalPakts  OBJECT-TYPE
            SYNTAX     Counter64
            MAX-ACCESS   read-only
            STATUS      current
            DESCRIPTION
                "This object indicates the received GEM frames."
            ::= { hwGponComboOltEthernetStatisticEntry 5 }  
            
        hwGponComboOltEthernetStatisticReceivedBroadcastPakts  OBJECT-TYPE
            SYNTAX     Counter64
            MAX-ACCESS   read-only
            STATUS      current
            DESCRIPTION
                "This object indicates the received broadcast frames."
            ::= { hwGponComboOltEthernetStatisticEntry 6 }  
            
        hwGponComboOltEthernetStatisticReceivedMulticastPakts  OBJECT-TYPE
            SYNTAX     Counter64
            MAX-ACCESS   read-only
            STATUS      current
            DESCRIPTION
                "This object indicates the received multicast frames."
            ::= { hwGponComboOltEthernetStatisticEntry 7 }   
            
        hwGponComboOltEthernetStatisticReceivedUnicastPakts  OBJECT-TYPE
            SYNTAX     Counter64
            MAX-ACCESS   read-only
            STATUS      current
            DESCRIPTION
                "This object indicates the received unicast frames."
            ::= { hwGponComboOltEthernetStatisticEntry 8 } 
            
        hwGponComboOltEthernetStatisticReceivedLen64Bytes    OBJECT-TYPE
            SYNTAX     Counter64
            MAX-ACCESS   read-only
            STATUS      current
            DESCRIPTION
                "This object indicates the received 64-octet frames."
            ::= { hwGponComboOltEthernetStatisticEntry 9 }    
            
        hwGponComboOltEthernetStatisticReceivedLen65To127Bytes    OBJECT-TYPE
            SYNTAX     Counter64
            MAX-ACCESS   read-only
            STATUS      current
            DESCRIPTION
                "This object indicates the received 65~127-octet frames."
            ::= { hwGponComboOltEthernetStatisticEntry 10 }  
            
        hwGponComboOltEthernetStatisticReceivedLen128To255Bytes    OBJECT-TYPE
            SYNTAX     Counter64
            MAX-ACCESS   read-only
            STATUS      current
            DESCRIPTION
                "This object indicates the received 128~255-octet frames."
            ::= { hwGponComboOltEthernetStatisticEntry 11 }   
            
        hwGponComboOltEthernetStatisticReceivedLen256To511Bytes    OBJECT-TYPE
            SYNTAX     Counter64
            MAX-ACCESS   read-only
            STATUS      current
            DESCRIPTION
                "This object indicates the received 256~511-octet frames."
            ::= { hwGponComboOltEthernetStatisticEntry 12 }     
            
        hwGponComboOltEthernetStatisticReceivedLen512To1023Bytes    OBJECT-TYPE
            SYNTAX     Counter64
            MAX-ACCESS   read-only
            STATUS      current
            DESCRIPTION
                "This object indicates the received 512~1023-octet frames."
            ::= { hwGponComboOltEthernetStatisticEntry 13 }   
            
        hwGponComboOltEthernetStatisticReceivedLen1024To1518Bytes    OBJECT-TYPE
            SYNTAX     Counter64
            MAX-ACCESS   read-only
            STATUS      current
            DESCRIPTION
                "This object indicates the received 1024~1518-octet frames."
            ::= { hwGponComboOltEthernetStatisticEntry 14 }  
            
        hwGponComboOltEthernetStatisticReceivedLenMore1518Bytes    OBJECT-TYPE
            SYNTAX     Counter64
            MAX-ACCESS   read-only
            STATUS      current
            DESCRIPTION
                "This object indicates the received over 1518-octet frames."
            ::= { hwGponComboOltEthernetStatisticEntry 15 }   
            
        hwGponComboOltEthernetStatisticReceivedBytes    OBJECT-TYPE
            SYNTAX     Counter64
            MAX-ACCESS   read-only
            STATUS      current
            DESCRIPTION
                "This object indicates the received octets."
            ::= { hwGponComboOltEthernetStatisticEntry 16 }  
            
        hwGponComboOltEthernetStatisticReceivedTooLongPakts    OBJECT-TYPE
            SYNTAX     Counter64
            MAX-ACCESS   read-only
            STATUS      current
            DESCRIPTION
                "This object indicates the received oversize frames."
            ::= { hwGponComboOltEthernetStatisticEntry 17 }   
            
        hwGponComboOltEthernetStatisticReceivedTooShortPakts    OBJECT-TYPE
            SYNTAX     Counter64
            MAX-ACCESS   read-only
            STATUS      current
            DESCRIPTION
                "This object indicates the received undersize frames."
            ::= { hwGponComboOltEthernetStatisticEntry 18 }  
            
        hwGponComboOltEthernetStatisticReceivedCRCErrPakts    OBJECT-TYPE
            SYNTAX     Counter64
            MAX-ACCESS   read-only
            STATUS      current
            DESCRIPTION
                "This object indicates the received error frames."
            ::= { hwGponComboOltEthernetStatisticEntry 19 }  
            
        hwGponComboOltEthernetStatisticSendTotalPakts    OBJECT-TYPE
            SYNTAX     Counter64
            MAX-ACCESS   read-only
            STATUS      current
            DESCRIPTION
                "This object indicates the send GEM frames."
            ::= { hwGponComboOltEthernetStatisticEntry 20 }   
            
        hwGponComboOltEthernetStatisticSendBroadcastPakts    OBJECT-TYPE
            SYNTAX     Counter64
            MAX-ACCESS   read-only
            STATUS      current
            DESCRIPTION
                "This object indicates the send broadcast frames."
            ::= { hwGponComboOltEthernetStatisticEntry 21 }  
            
        hwGponComboOltEthernetStatisticSendMulticastPakts    OBJECT-TYPE
            SYNTAX     Counter64
            MAX-ACCESS   read-only
            STATUS      current
            DESCRIPTION
                "This object indicates the send multicast frames."
            ::= { hwGponComboOltEthernetStatisticEntry 22 } 
            
        hwGponComboOltEthernetStatisticSendUnicastPakts    OBJECT-TYPE
            SYNTAX     Counter64
            MAX-ACCESS   read-only
            STATUS      current
            DESCRIPTION
                "This object indicates the send unicast frames."
            ::= { hwGponComboOltEthernetStatisticEntry 23 } 
            
        hwGponComboOltEthernetStatisticSendLen64Bytes    OBJECT-TYPE
            SYNTAX     Counter64
            MAX-ACCESS   read-only
            STATUS      current
            DESCRIPTION
                "This object indicates the sent 64-octet frames."
            ::= { hwGponComboOltEthernetStatisticEntry 24 } 
            
        hwGponComboOltEthernetStatisticSendLen65To127Bytes    OBJECT-TYPE
            SYNTAX     Counter64
            MAX-ACCESS   read-only
            STATUS      current
            DESCRIPTION
                "This object indicates the sent 65~127-octet frames."
            ::= { hwGponComboOltEthernetStatisticEntry 25 }  
            
        hwGponComboOltEthernetStatisticSendLen128To255Bytes    OBJECT-TYPE
            SYNTAX     Counter64
            MAX-ACCESS   read-only
            STATUS      current
            DESCRIPTION
                "This object indicates the sent 128~255-octet frames."
            ::= { hwGponComboOltEthernetStatisticEntry 26 } 
            
        hwGponComboOltEthernetStatisticSendLen256To511Bytes    OBJECT-TYPE
            SYNTAX     Counter64
            MAX-ACCESS   read-only
            STATUS      current
            DESCRIPTION
                "This object indicates the sent 256~511-octet frames."
            ::= { hwGponComboOltEthernetStatisticEntry 27 } 
            
        hwGponComboOltEthernetStatisticSendLen512To1023Bytes    OBJECT-TYPE
            SYNTAX     Counter64
            MAX-ACCESS   read-only
            STATUS      current
            DESCRIPTION
                "This object indicates the sent 512~1023-octet frames."
            ::= { hwGponComboOltEthernetStatisticEntry 28 }  
            
        hwGponComboOltEthernetStatisticSendLen1024To1518Bytes    OBJECT-TYPE
            SYNTAX     Counter64
            MAX-ACCESS   read-only
            STATUS      current
            DESCRIPTION
                "This object indicates the sent 1024~1518-octet frames."
            ::= { hwGponComboOltEthernetStatisticEntry 29 } 
            
        hwGponComboOltEthernetStatisticSendLenMore1518Bytes    OBJECT-TYPE
            SYNTAX     Counter64
            MAX-ACCESS   read-only
            STATUS      current
            DESCRIPTION
                "This object indicates the sent over 1518-octet frames."
            ::= { hwGponComboOltEthernetStatisticEntry 30 }
            
        hwGponComboOltEthernetStatisticSendBytes    OBJECT-TYPE
            SYNTAX     Counter64
            MAX-ACCESS   read-only
            STATUS      current
            DESCRIPTION
                "This object indicates the sent octets."
            ::= { hwGponComboOltEthernetStatisticEntry 31 }  
            
        hwGponComboOltEthernetStatisticSendMulticastBytes    OBJECT-TYPE
            SYNTAX     Counter64
            MAX-ACCESS   read-only
            STATUS      current
            DESCRIPTION
                "This object indicates the sent multicast bytes."
            ::= { hwGponComboOltEthernetStatisticEntry 32 }   
            
   -- hwGponComboOltEthernetStatisticTable end   
   
   -- Table: hwGponComboOltGemStatisticTable
        hwGponComboOltGemStatisticTable OBJECT-TYPE
            SYNTAX     SEQUENCE OF HwGponComboOltGemStatisticEntry
            MAX-ACCESS not-accessible
            STATUS     current
            DESCRIPTION
                "This table is the Combo PON port GEM frame statistics table.
                 The indexes of this table are ifIndex and hwGponComboOltGemStatisticChannelID.
                "
            ::= { hwXponCommonStatisticObjects 17 }  
            
        hwGponComboOltGemStatisticEntry OBJECT-TYPE
            SYNTAX     HwGponComboOltGemStatisticEntry
            MAX-ACCESS not-accessible
            STATUS     current
            DESCRIPTION
                "This table is the Combo PON port GEM frame statistics table.
                 The indexes of this entry are ifIndex and hwGponComboOltGemStatisticChannelID.
                "
            INDEX       { ifIndex, hwGponComboOltGemStatisticChannelID }
            ::= { hwGponComboOltGemStatisticTable 1 }  
            
        HwGponComboOltGemStatisticEntry ::=
            SEQUENCE { 
                hwGponComboOltGemStatisticChannelID            INTEGER,
                hwGponComboOltGemStatisticReceivedFrames       Counter64,
                hwGponComboOltGemStatisticReceivedOMCIPackts   Counter64,
                hwGponComboOltGemStatisticReceivedPLOAMPackts  Counter64,
                hwGponComboOltGemStatisticReceivedIdlePackts   Counter64,
                hwGponComboOltGemStatisticSendFrames           Counter64,
                hwGponComboOltGemStatisticSendOMCIPackts       Counter64,
                hwGponComboOltGemStatisticSendPLOAMPackts      Counter64,
                hwGponComboOltGemStatisticSendIdlePackts       Counter64
            }                        
            
        hwGponComboOltGemStatisticChannelID OBJECT-TYPE
            SYNTAX  INTEGER
              {                      
                  gpon(1),
                  xgpon(2)
              } 
           MAX-ACCESS  not-accessible
           STATUS      current
           DESCRIPTION
                   "This object indicates the channel of the Combo PON port.
                    Options:
                    1. gpon(1)      - Indicates that the channel of the Combo PON port is GPON.
                    2. xgpon(2)     - Indicates that the channel of the Combo PON port is XG-PON.                                                                              
                   "
           ::= { hwGponComboOltGemStatisticEntry 1 }  
           
        hwGponComboOltGemStatisticReceivedFrames  OBJECT-TYPE
            SYNTAX     Counter64
            MAX-ACCESS   read-only
            STATUS      current
            DESCRIPTION
                "This object indicates the received GEM frames."
            ::= { hwGponComboOltGemStatisticEntry 2 }  
            
        hwGponComboOltGemStatisticReceivedOMCIPackts  OBJECT-TYPE
            SYNTAX     Counter64
            MAX-ACCESS   read-only
            STATUS      current
            DESCRIPTION
                "This object indicates the recived OMCI frames."
            ::= { hwGponComboOltGemStatisticEntry 3 } 
            
        hwGponComboOltGemStatisticReceivedPLOAMPackts  OBJECT-TYPE
            SYNTAX     Counter64
            MAX-ACCESS   read-only
            STATUS      current
            DESCRIPTION
                "This object indicates the recived PLOAM frames."
            ::= { hwGponComboOltGemStatisticEntry 4 } 
            
        hwGponComboOltGemStatisticReceivedIdlePackts  OBJECT-TYPE
            SYNTAX     Counter64
            MAX-ACCESS   read-only
            STATUS      current
            DESCRIPTION
                "This object indicates the recived IDLE frames."
            ::= { hwGponComboOltGemStatisticEntry 5 } 
            
        hwGponComboOltGemStatisticSendFrames  OBJECT-TYPE
            SYNTAX     Counter64
            MAX-ACCESS   read-only
            STATUS      current
            DESCRIPTION
                "This object indicates the sent GEM frames."
            ::= { hwGponComboOltGemStatisticEntry 6 }   
            
        hwGponComboOltGemStatisticSendOMCIPackts  OBJECT-TYPE
            SYNTAX     Counter64
            MAX-ACCESS   read-only
            STATUS      current
            DESCRIPTION
                "This object indicates the sent OMCI frames."
            ::= { hwGponComboOltGemStatisticEntry 7 }   
            
        hwGponComboOltGemStatisticSendPLOAMPackts  OBJECT-TYPE
            SYNTAX     Counter64
            MAX-ACCESS   read-only
            STATUS      current
            DESCRIPTION
                "This object indicates the sent PLOAM frames."
            ::= { hwGponComboOltGemStatisticEntry 8 }    
            
        hwGponComboOltGemStatisticSendIdlePackts    OBJECT-TYPE
            SYNTAX     Counter64
            MAX-ACCESS   read-only
            STATUS      current
            DESCRIPTION
                "This object indicates the sent IDLE frames."
            ::= { hwGponComboOltGemStatisticEntry 9 }  
            
    -- hwGponComboOltGemStatisticTable end  
    
    -- Table: hwOltGponComboPortInfoTable
        hwOltGponComboPortInfoTable OBJECT-TYPE
            SYNTAX     SEQUENCE OF HwOltGponComboPortInfoEntry
            MAX-ACCESS not-accessible
            STATUS     current
            DESCRIPTION
                "The Combo PON port information table.
                 The index of this table is ifIndex and hwOltGponComboPortChannelID.
                "
            ::= { hwXponCommonStatisticObjects 18 } 
            
        hwOltGponComboPortInfoEntry OBJECT-TYPE
            SYNTAX     HwOltGponComboPortInfoEntry
            MAX-ACCESS not-accessible
            STATUS     current
            DESCRIPTION
                "The Combo PON port information table.
                 The index of this entry is ifIndex and hwOltGponComboPortChannelID.
                "
            INDEX       { ifIndex, hwOltGponComboPortChannelID }
            ::= { hwOltGponComboPortInfoTable 1 }  
            
        HwOltGponComboPortInfoEntry ::=
            SEQUENCE { 
                hwOltGponComboPortChannelID               INTEGER,                
                hwOltGponComboPortOpticModuleStatus       INTEGER
            }
        hwOltGponComboPortChannelID OBJECT-TYPE
            SYNTAX  INTEGER
              {                      
                  gpon(1),
                  xgpon(2)
              } 
           MAX-ACCESS  not-accessible
           STATUS      current
           DESCRIPTION
                   "This object indicates the channel of the Combo PON port.
                    Options:
                    1. gpon(1)      - Indicates that the channel of the Combo PON port is GPON.
                    2. xgpon(2)     - Indicates that the channel of the Combo PON port is XG-PON.                                                                              
                   "
           ::= { hwOltGponComboPortInfoEntry 1 }   
           
        hwOltGponComboPortOpticModuleStatus  OBJECT-TYPE
            SYNTAX  INTEGER
              {                      
                  online(1),
                  offline(2),
                  invalid(-1)
              } 
           MAX-ACCESS  read-only
           STATUS      current
           DESCRIPTION
                   "This object indicates the status of the Combo PON port optical module.
                    Options:
                    1. online(1)      - Indicates that the status of the Combo PON port optical module is online.
                    2. offline(2)     - Indicates that the status of the Combo PON port optical module is offline. 
                    3. invalid(-1)    - Indicates that the query fails or no information is detected.                                                                          
                   "
           ::= { hwOltGponComboPortInfoEntry 2 } 
           
    -- hwOltGponComboPortInfoTable end       
    
    --  Table hwXponOntRegAndAuthStatTable     
           hwXponOntRegAndAuthStatTable OBJECT-TYPE
	            SYNTAX     SEQUENCE OF HwXponOntRegAndAuthStatEntry
	            MAX-ACCESS not-accessible
	            STATUS     current
	            DESCRIPTION
	                "This table is indicates the ONT registration and authentication statistics. 
	                 The indexes of this table are ifIndex and hwXponOntIndex.
	                "
	            ::= { hwXponCommonStatisticObjects 19 }  
	            
	        hwXponOntRegAndAuthStatEntry OBJECT-TYPE
	            SYNTAX     HwXponOntRegAndAuthStatEntry
	            MAX-ACCESS not-accessible
	            STATUS     current
	            DESCRIPTION
	                "This table is indicates the ONT registration and authentication statistics. 
	                 The indexes of this entry are ifIndex and hwXponOntIndex.
	                "
	            INDEX       { ifIndex, hwXponOntIndex }
	            ::= { hwXponOntRegAndAuthStatTable 1 }    
	            
	        HwXponOntRegAndAuthStatEntry ::=
	            SEQUENCE {
	                hwXponOntRegAndAuthStatRegisterAcceptedCounter     Counter64,     
	                hwXponOntRegAndAuthStatRegisterRejectedCounter     Counter64,
	                hwXponOntRegAndAuthStatAuthAcceptedCounter         Counter64,
	                hwXponOntRegAndAuthStatAuthRejectedCounter         Counter64,
	                hwXponOntRegAndAuthStatChallengedCounter           Counter64
	            }
	            
	        hwXponOntRegAndAuthStatRegisterAcceptedCounter  OBJECT-TYPE
	            SYNTAX     Counter64
	            MAX-ACCESS   read-only
	            STATUS      current
	            DESCRIPTION
	                "This object indicates the registration accepted counter.
			-1 indicates the invalid value."
	            ::= { hwXponOntRegAndAuthStatEntry 1 }      
	            
	        hwXponOntRegAndAuthStatRegisterRejectedCounter  OBJECT-TYPE
	            SYNTAX     Counter64
	            MAX-ACCESS   read-only
	            STATUS      current
	            DESCRIPTION
	                "This object indicates the registration rejected counter.
			-1 indicates the invalid value."
	            ::= { hwXponOntRegAndAuthStatEntry 2 }   
	            
	        hwXponOntRegAndAuthStatAuthAcceptedCounter  OBJECT-TYPE
	            SYNTAX     Counter64
	            MAX-ACCESS   read-only
	            STATUS      current
	            DESCRIPTION
	                "This object indicates the authentification accepted counter.
			-1 indicates the invalid value."
	            ::= { hwXponOntRegAndAuthStatEntry 3 }      
	            
	        hwXponOntRegAndAuthStatAuthRejectedCounter  OBJECT-TYPE
	            SYNTAX     Counter64
	            MAX-ACCESS   read-only
	            STATUS      current
	            DESCRIPTION
	                "This object indicates the authentification rejected counter.
			-1 indicates the invalid value."
	            ::= { hwXponOntRegAndAuthStatEntry 4 }  
	            
	        hwXponOntRegAndAuthStatChallengedCounter  OBJECT-TYPE
	            SYNTAX     Counter64
	            MAX-ACCESS   read-only
	            STATUS      current
	            DESCRIPTION
	                "This object indicates the authentification challenged counter.
			-1 indicates the invalid value."
	            ::= { hwXponOntRegAndAuthStatEntry 5 }

    --hwXponOntRegAndAuthStatTable end  
    
    -- Table: hwXponPortTrafficStatisticTable
        hwXponPortTrafficStatisticTable OBJECT-TYPE
            SYNTAX     SEQUENCE OF HwXponPortTrafficStatisticEntry
            MAX-ACCESS not-accessible
            STATUS     current
            DESCRIPTION
                "This table is used to query statistics about upstream and downstream rates of a PON port.
                 The index of this table is ifIndex.
                "
            ::= { hwXponCommonStatisticObjects 20 } 
            
        hwXponPortTrafficStatisticEntry OBJECT-TYPE
            SYNTAX     HwXponPortTrafficStatisticEntry
            MAX-ACCESS not-accessible
            STATUS     current
            DESCRIPTION
                "This table is used to query statistics about upstream and downstream rates of a PON port. 
                 The index of this entry is ifIndex. 
                "
            INDEX       { ifIndex }
            ::= { hwXponPortTrafficStatisticTable 1 }  
            
        HwXponPortTrafficStatisticEntry ::=
            SEQUENCE { 
		hwXponPortTrafficStatisticCurrentUpstreamRate      Integer32,                
		hwXponPortTrafficStatisticCurrentDownstreamRate    Integer32,
		hwXponPortTrafficStatisticUp1GChannelRate      Integer32,                
		hwXponPortTrafficStatisticUp1GChannelBandwidthUsage    Integer32,
		hwXponPortTrafficStatisticUp1GChannelUnicastRate      Integer32,                
		hwXponPortTrafficStatisticUp1GChannelMulticastRate    Integer32,
		hwXponPortTrafficStatisticUp1GChannelBroadcastRate      Integer32,                
		hwXponPortTrafficStatisticUp10GChannelRate    Integer32,
		hwXponPortTrafficStatisticUp10GChannelBandwidthUsage      Integer32,                
		hwXponPortTrafficStatisticUp10GChannelUnicastRate    Integer32,
		hwXponPortTrafficStatisticUp10GChannelMulticastRate      Integer32,                
		hwXponPortTrafficStatisticUp10GChannelBroadcastRate    Integer32,
		hwXponPortTrafficStatisticDown1GChannelRate      Integer32,                
		hwXponPortTrafficStatisticDown1GChannelBandwidthUsage    Integer32,
		hwXponPortTrafficStatisticDown1GChannelUnicastRate    Integer32,
		hwXponPortTrafficStatisticDown1GChannelMulticastRate    Integer32,
		hwXponPortTrafficStatisticDown1GChannelBroadcastRate    Integer32,
		hwXponPortTrafficStatisticDown10GChannelRate    Integer32,
		hwXponPortTrafficStatisticDown10GChannelBandwidthUsage    Integer32,
		hwXponPortTrafficStatisticDown10GChannelUnicastRate    Integer32,
		hwXponPortTrafficStatisticDown10GChannelMulticastRate    Integer32,
		hwXponPortTrafficStatisticDown10GChannelBroadcastRate    Integer32,
		hwXponPortTrafficStatisticUp2GChannelRate    Integer32,
		hwXponPortTrafficStatisticUp2GChannelBandwidthUsage    Integer32,
		hwXponPortTrafficStatisticUp2GChannelUnicastRate    Integer32,
		hwXponPortTrafficStatisticUp2GChannelMulticastRate    Integer32,
		hwXponPortTrafficStatisticUp2GChannelBroadcastRate    Integer32			
            }
        hwXponPortTrafficStatisticCurrentUpstreamRate OBJECT-TYPE
            SYNTAX     Integer32
            MAX-ACCESS read-only
            STATUS     current
            DESCRIPTION
                   "This object indicates the current Rx rate of a port, in the unit of kbit/s. 
                   "
           ::= { hwXponPortTrafficStatisticEntry 1 }   
           
        hwXponPortTrafficStatisticCurrentDownstreamRate  OBJECT-TYPE
            SYNTAX     Integer32
            MAX-ACCESS read-only
            STATUS     current
            DESCRIPTION
                   "This object indicates the current Tx rate of a port, in the unit of kbit/s.
                   "
           ::= { hwXponPortTrafficStatisticEntry 2 } 
		   
        hwXponPortTrafficStatisticUp1GChannelRate  OBJECT-TYPE
            SYNTAX     Integer32
            MAX-ACCESS read-only
            STATUS     current
            DESCRIPTION
                   "This object indicates the current Rx rate of 1G channel in the unit of kbit/s. 
				   "
           ::= { hwXponPortTrafficStatisticEntry 3 } 
		
        hwXponPortTrafficStatisticUp1GChannelBandwidthUsage  OBJECT-TYPE
            SYNTAX     Integer32
            MAX-ACCESS read-only
            STATUS     current
            DESCRIPTION
                   "This object indicates the current upstream bandwidth usage of 1G channel in the unit of 1%. 
				   "
           ::= { hwXponPortTrafficStatisticEntry 4 }
		
        hwXponPortTrafficStatisticUp1GChannelUnicastRate  OBJECT-TYPE
            SYNTAX     Integer32
            MAX-ACCESS read-only
            STATUS     current
            DESCRIPTION
                   "This object indicates the current Rx unicast rate of 1G channel in the unit of kbit/s. 
				   "
           ::= { hwXponPortTrafficStatisticEntry 5 }		
         
        hwXponPortTrafficStatisticUp1GChannelMulticastRate  OBJECT-TYPE
            SYNTAX     Integer32
            MAX-ACCESS read-only
            STATUS     current
            DESCRIPTION
                   "This object indicates the current Rx multicast rate of 1G channel in the unit of kbit/s. 
				   "
           ::= { hwXponPortTrafficStatisticEntry 6 }

        hwXponPortTrafficStatisticUp1GChannelBroadcastRate  OBJECT-TYPE
            SYNTAX     Integer32
            MAX-ACCESS read-only
            STATUS     current
            DESCRIPTION
                   "This object indicates the current Rx boardcast rate of 1G channel in the unit of kbit/s. 
				   "
           ::= { hwXponPortTrafficStatisticEntry 7 }

        hwXponPortTrafficStatisticUp10GChannelRate  OBJECT-TYPE
            SYNTAX     Integer32
            MAX-ACCESS read-only
            STATUS     current
            DESCRIPTION
                   "This object indicates the current Rx rate of 10G(or 2.5G in xgpon)  channel in the unit of kbit/s. 
				   "
           ::= { hwXponPortTrafficStatisticEntry 8 }

        hwXponPortTrafficStatisticUp10GChannelBandwidthUsage  OBJECT-TYPE
            SYNTAX     Integer32
            MAX-ACCESS read-only
            STATUS     current
            DESCRIPTION
                   "This object indicates the current upstream bandwidth usage of 10G(or 2.5G in xgpon)  channel in the unit of 1%. 
				   "
           ::= { hwXponPortTrafficStatisticEntry 9 }

        hwXponPortTrafficStatisticUp10GChannelUnicastRate  OBJECT-TYPE
            SYNTAX     Integer32
            MAX-ACCESS read-only
            STATUS     current
            DESCRIPTION
                   "This object indicates the current Rx unicast rate of 10G(or 2.5G in xgpon)  channel in the unit of kbit/s. 
				   "
           ::= { hwXponPortTrafficStatisticEntry 10 }

        hwXponPortTrafficStatisticUp10GChannelMulticastRate  OBJECT-TYPE
            SYNTAX     Integer32
            MAX-ACCESS read-only
            STATUS     current
            DESCRIPTION
                   "This object indicates the current Rx multicast rate of 10G(or 2.5G in xgpon)  channel in the unit of kbit/s. 
				   "
           ::= { hwXponPortTrafficStatisticEntry 11 }

        hwXponPortTrafficStatisticUp10GChannelBroadcastRate  OBJECT-TYPE
            SYNTAX     Integer32
            MAX-ACCESS read-only
            STATUS     current
            DESCRIPTION
                   "This object indicates the current Rx boardcast rate of 10G(or 2.5G in xgpon)  channel in the unit of kbit/s. 
				   "
           ::= { hwXponPortTrafficStatisticEntry 12 }
		
        hwXponPortTrafficStatisticDown1GChannelRate  OBJECT-TYPE
            SYNTAX     Integer32
            MAX-ACCESS read-only
            STATUS     current
            DESCRIPTION
                   "This object indicates the current Tx rate of 1G(or 2.5G in gpon) channel in the unit of kbit/s. 
				   "
           ::= { hwXponPortTrafficStatisticEntry 13 }
		   
        hwXponPortTrafficStatisticDown1GChannelBandwidthUsage  OBJECT-TYPE
            SYNTAX     Integer32
            MAX-ACCESS read-only
            STATUS     current
            DESCRIPTION
                   "This object indicates the current downstream bandwidth usage of 1G(or 2.5G in gpon) channel in the unit of 1%. 
				   "
           ::= { hwXponPortTrafficStatisticEntry 14 }

        hwXponPortTrafficStatisticDown1GChannelUnicastRate  OBJECT-TYPE
            SYNTAX     Integer32
            MAX-ACCESS read-only
            STATUS     current
            DESCRIPTION
                   "This object indicates the current Tx unicast rate of 1G(or 2.5G in gpon) channel in the unit of kbit/s. 
				   "
           ::= { hwXponPortTrafficStatisticEntry 15 }

        hwXponPortTrafficStatisticDown1GChannelMulticastRate  OBJECT-TYPE
            SYNTAX     Integer32
            MAX-ACCESS read-only
            STATUS     current
            DESCRIPTION
                   "This object indicates the current Tx multicast rate of 1G(or 2.5G in gpon) channel in the unit of kbit/s. 
				   "
           ::= { hwXponPortTrafficStatisticEntry 16 }

        hwXponPortTrafficStatisticDown1GChannelBroadcastRate  OBJECT-TYPE
            SYNTAX     Integer32
            MAX-ACCESS read-only
            STATUS     current
            DESCRIPTION
                   "This object indicates the current Tx boardcast rate of 1G(or 2.5G in gpon) channel in the unit of kbit/s. 
				   "
           ::= { hwXponPortTrafficStatisticEntry 17 }

        hwXponPortTrafficStatisticDown10GChannelRate  OBJECT-TYPE
            SYNTAX     Integer32
            MAX-ACCESS read-only
            STATUS     current
            DESCRIPTION
                   "This object indicates the current Tx rate of 10G channel in the unit of kbit/s. 
				   "
           ::= { hwXponPortTrafficStatisticEntry 18 }

        hwXponPortTrafficStatisticDown10GChannelBandwidthUsage  OBJECT-TYPE
            SYNTAX     Integer32
            MAX-ACCESS read-only
            STATUS     current
            DESCRIPTION
                   "This object indicates the current downstream bandwidth usage of 10G(or 2.5G in xgpon)  channel in the unit of 1%. 
				   "
           ::= { hwXponPortTrafficStatisticEntry 19 }

        hwXponPortTrafficStatisticDown10GChannelUnicastRate  OBJECT-TYPE
            SYNTAX     Integer32
            MAX-ACCESS read-only
            STATUS     current
            DESCRIPTION
                   "This object indicates the current Tx unicast rate of 10G channel in the unit of kbit/s. 
				   "
           ::= { hwXponPortTrafficStatisticEntry 20 }

        hwXponPortTrafficStatisticDown10GChannelMulticastRate  OBJECT-TYPE
            SYNTAX     Integer32
            MAX-ACCESS read-only
            STATUS     current
            DESCRIPTION
                   "This object indicates the current Tx multicast rate of 10G channel in the unit of kbit/s. 
				   "
           ::= { hwXponPortTrafficStatisticEntry 21 } 

        hwXponPortTrafficStatisticDown10GChannelBroadcastRate  OBJECT-TYPE
            SYNTAX     Integer32
            MAX-ACCESS read-only
            STATUS     current
            DESCRIPTION
                   "This object indicates the current Tx boardcast rate of 10G channel in the unit of kbit/s. 
				   "
           ::= { hwXponPortTrafficStatisticEntry 22 } 
	   
        hwXponPortTrafficStatisticUp2GChannelRate  OBJECT-TYPE
            SYNTAX     Integer32
            MAX-ACCESS read-only
            STATUS     current
            DESCRIPTION
                   "This object indicates the current Rx rate of 1G channel in the unit of kbit/s. 
				   "
           ::= { hwXponPortTrafficStatisticEntry 23 } 
		   
        hwXponPortTrafficStatisticUp2GChannelBandwidthUsage  OBJECT-TYPE
            SYNTAX     Integer32
            MAX-ACCESS read-only
            STATUS     current
            DESCRIPTION
                   "This object indicates the current upstream bandwidth usage of 1G channel in the unit of 1%.. 
				   "
           ::= { hwXponPortTrafficStatisticEntry 24 } 
		   
        hwXponPortTrafficStatisticUp2GChannelUnicastRate  OBJECT-TYPE
            SYNTAX     Integer32
            MAX-ACCESS read-only
            STATUS     current
            DESCRIPTION
                   "This object indicates the current Rx unicast rate of 1G channel in the unit of kbit/s. 
				   "
           ::= { hwXponPortTrafficStatisticEntry 25 } 
	   
        hwXponPortTrafficStatisticUp2GChannelMulticastRate  OBJECT-TYPE
            SYNTAX     Integer32
            MAX-ACCESS read-only
            STATUS     current
            DESCRIPTION
                   "This object indicates the current Rx multicast rate of 1G channel in the unit of kbit/s. 
				   "
           ::= { hwXponPortTrafficStatisticEntry 26 } 
	   
        hwXponPortTrafficStatisticUp2GChannelBroadcastRate  OBJECT-TYPE
            SYNTAX     Integer32
            MAX-ACCESS read-only
            STATUS     current
            DESCRIPTION
                   "This object indicates the current Rx boardcast rate of 1G channel in the unit of kbit/s. 
				   "
           ::= { hwXponPortTrafficStatisticEntry 27 }    
		
    -- hwXponPortTrafficStatisticTable end

    -- Table: hwXponOntQueueStatisticTable
        hwXponOntQueueStatisticTable OBJECT-TYPE
            SYNTAX     SEQUENCE OF HwXponOntQueueStatisticEntry
            MAX-ACCESS not-accessible
            STATUS     current
            DESCRIPTION
                "This table is used to query statistics about priority queue of ONT.
                 The index of this table is ifIndex, hwXponOntIndex, hwXponOntQueueStatisticType, hwXponOntQueueStatisticIndex and hwXponOntQueueStatisticQueueId.
                "
            ::= { hwXponCommonStatisticObjects 21 } 
            
        hwXponOntQueueStatisticEntry OBJECT-TYPE
            SYNTAX     HwXponOntQueueStatisticEntry
            MAX-ACCESS not-accessible
            STATUS     current
            DESCRIPTION
                "This table is used to query statistics about priority queue of ONT.
                 The index of this table is ifIndex, hwXponOntIndex, hwXponOntQueueStatisticType, hwXponOntQueueStatisticIndex and hwXponOntQueueStatisticQueueId.
                "
            INDEX       { ifIndex, hwXponOntIndex,  hwXponOntQueueStatisticType, hwXponOntQueueStatisticIndex, hwXponOntQueueStatisticQueueId }
            ::= { hwXponOntQueueStatisticTable 1 }  
            
        HwXponOntQueueStatisticEntry ::=
            SEQUENCE { 
                hwXponOntQueueStatisticType           INTEGER,                
                hwXponOntQueueStatisticIndex          Integer32,
                hwXponOntQueueStatisticQueueId        Integer32,
                hwXponOntQueueStatisticPassedNumber   Counter64,
                hwXponOntQueueStatisticDroppedNumber  Counter64,
                hwXponOntQueueStatisticPassedBytes    Counter64
            }

        hwXponOntQueueStatisticType OBJECT-TYPE
            SYNTAX INTEGER
            {
              tcont(1),
              llid(2),
              eth(3),
              wifi(4)
            }
            MAX-ACCESS not-accessible
            STATUS     current
            DESCRIPTION
                "This object indicates the type of statistics object.
                 Options:
                 1. tcont(1) - Indicates that the statistics object is the T-CONT of GPON ONT
                 2. llid(2)  - Indicates that the statistics object is the LLID of EPON ONT
                 3. eth(3)   - Indicates that the statistics object is the ETH port of ONT
                 4. wifi(4)  - Indicates that the statistics object is the WIFI port of ONT 
                "
           ::= { hwXponOntQueueStatisticEntry 1 }

        hwXponOntQueueStatisticIndex  OBJECT-TYPE
            SYNTAX     Integer32
            MAX-ACCESS not-accessible
            STATUS     current
            DESCRIPTION
                   "This object indicates the index of statistics object.
                     1. When hwXponOntQueueStatisticIfType is tcont(1), the value is the T-CONT ID
                     2. When hwXponOntQueueStatisticIfType is llid(2), the value must be -1
                     3. When hwXponOntQueueStatisticIfType is eth(3), the value is the ETH port ID
                     4. When hwXponOntQueueStatisticIfType is wifi(4), this object Indicates the WIFI frequency band, 1 indicates 2.4G, 2 indicates 5G
                   "
           ::= { hwXponOntQueueStatisticEntry 2 }

        hwXponOntQueueStatisticQueueId  OBJECT-TYPE
         SYNTAX      Integer32 (0..7)
         MAX-ACCESS  not-accessible
         STATUS current
         DESCRIPTION
             "Indicates a specified queue ID.
              Range: 0-7
              The queues are real queues (errors are prompted when there are actually four queues on a ONT).
             "
           ::= { hwXponOntQueueStatisticEntry 3 } 

        hwXponOntQueueStatisticPassedNumber OBJECT-TYPE
            SYNTAX      Counter64
            MAX-ACCESS  read-only
            STATUS      current
            DESCRIPTION
                "Indicates the number of pass-through packets. 
                 After a packet is sent, the statistics of pass-through packets are increased by 1 if the packet passes."
            ::={ hwXponOntQueueStatisticEntry 4 }

        hwXponOntQueueStatisticDroppedNumber OBJECT-TYPE
            SYNTAX      Counter64
            MAX-ACCESS  read-only
            STATUS      current
            DESCRIPTION
                "Indicates the number of dropped packets. 
                 After a packet is sent, the statistics of dropped packets are increased by 1 if the packet fails to pass."
            ::={ hwXponOntQueueStatisticEntry 5 }

        hwXponOntQueueStatisticPassedBytes OBJECT-TYPE
            SYNTAX      Counter64
            MAX-ACCESS  read-only
            STATUS      current
            DESCRIPTION
                "Indicates the number of pass-through bytes. 
                 After a byte is sent, the statistics of pass-through bytes are increased by 1 if the byte passes."
            ::={ hwXponOntQueueStatisticEntry 6 }

    -- hwXponOntQueueStatisticTable end

    -- Table: hwXponOntQueueStatisticControlTable
        hwXponOntQueueStatisticControlTable OBJECT-TYPE
            SYNTAX     SEQUENCE OF HwXponOntQueueStatisticControlEntry
            MAX-ACCESS not-accessible
            STATUS     current
            DESCRIPTION
                "This table is used to clear statistics about priority queue of ONT.
                 The index of this table is ifIndex, hwXponOntIndex, hwXponOntQueueStatisticControlType and hwXponOntQueueStatisticControlIndex.
                "
            ::= { hwXponCommonStatisticObjects 22 }
            
        hwXponOntQueueStatisticControlEntry OBJECT-TYPE
            SYNTAX     HwXponOntQueueStatisticControlEntry
            MAX-ACCESS not-accessible
            STATUS     current
            DESCRIPTION
                "This table is used to clear statistics about priority queue of ONT.
                 The index of this table is ifIndex, hwXponOntIndex, hwXponOntQueueStatisticControlType and hwXponOntQueueStatisticControlIndex.
                "
            INDEX       { ifIndex, hwXponOntIndex,  hwXponOntQueueStatisticControlType, hwXponOntQueueStatisticControlIndex }
            ::= { hwXponOntQueueStatisticControlTable 1 }  
            
        HwXponOntQueueStatisticControlEntry ::=
            SEQUENCE { 
                hwXponOntQueueStatisticControlType      INTEGER,
                hwXponOntQueueStatisticControlIndex     Integer32,
                hwXponOntQueueStatisticControlClear     INTEGER
            }

        hwXponOntQueueStatisticControlType OBJECT-TYPE
            SYNTAX INTEGER
              {
              tcont(1),
              llid(2),
              eth(3),
              wifi(4)
              }
            MAX-ACCESS not-accessible
            STATUS     current
            DESCRIPTION
                "This object indicates the type of statistics object.
                 Options:
                 1. tcont(1) - Indicates that the statistics object is the T-CONT of GPON ONT
                 2. llid(2)  - Indicates that the statistics object is the LLID of EPON ONT
                 3. eth(3)   - Indicates that the statistics object is the ETH port of ONT
                 4. wifi(4)  - Indicates that the statistics object is the WIFI port of ONT 
                "
           ::= { hwXponOntQueueStatisticControlEntry 1 }

        hwXponOntQueueStatisticControlIndex  OBJECT-TYPE
            SYNTAX     Integer32
            MAX-ACCESS not-accessible
            STATUS     current
            DESCRIPTION
                   "This object indicates the index of statistics object.
                     1. When hwXponOntQueueStatisticIfType is tcont(1), the value is the T-CONT ID
                     2. When hwXponOntQueueStatisticIfType is llid(2), the value must be -1
                     3. When hwXponOntQueueStatisticIfType is eth(3), the value is the ETH port ID
                     4. When hwXponOntQueueStatisticIfType is wifi(4), the value must be -1
                   "
           ::= { hwXponOntQueueStatisticControlEntry 2 }

        hwXponOntQueueStatisticControlClear  OBJECT-TYPE
            SYNTAX INTEGER
              {
              clear(1),
              invalid(-1)
              }
         MAX-ACCESS  read-write
         STATUS current
         DESCRIPTION
             "Indicates a specified queue ID.
              1. clear(1)       - In the set operation, clear the statistics information
              2. invalid(-1)    - In the get operation, the invalid value -1 is returned.
             "
           ::= { hwXponOntQueueStatisticControlEntry 3 } 

    -- hwXponOntQueueStatisticControlTable end

    --hwGponDeviceCommonGlobalObjects   begin
        hwGponDeviceChangePasswordIntervalTime OBJECT-TYPE
            SYNTAX     Gauge32 (0 | 5..1440 | 65535)
            UNITS      "minutes"
            MAX-ACCESS read-write
            STATUS     current
            DESCRIPTION
                "The interval time of ONT's password renew, 0 means no update, 65535 means no
                 configration data.
                 Unit: minutes
                "
            ::= { hwGponDeviceCommonGlobalObjects 1 }

        hwGponDeviceTcontAutoCombineSwitch  OBJECT-TYPE
            SYNTAX  INTEGER
              {
                  enable(1),
                  disable(2)
              }
            MAX-ACCESS read-write
            STATUS current
            DESCRIPTION
                "The switch value of T-CONT auto-combine.
                 Options:
                 1. enable(1)  - The switch value of T-CONT auto-combine is enable
                 2. disable(2) - The switch value of T-CONT auto-combine is disable
                "
            ::= { hwGponDeviceCommonGlobalObjects 2 }
            
         hwGponOntInteroperabilityMode   OBJECT-TYPE
            SYNTAX  INTEGER
              {
                  ituT(1),
                  ctc(2),
                  ericV1(3),
                  ericV2(4),
                  ituTG984(5),
                  ituTG988(6),
                  cuc(7),
                  cmcc(8),
                  eci(9),
                  mode1(10),
                  mode2(11),
                  mode2V2(12),
                  mode3(13),
                  mode4(14),
                  mode2V3(15),
                  mode2V4(16),
                  mode5(17),
                  eciV2(18),
                  mode1V2(19)
              }
            MAX-ACCESS read-write
            STATUS current
            DESCRIPTION
                "The switch mode of gpon ont interoperability.
                 Options:
                 1. ituT(1)         - The switch mode of gpon ont interoperability is ituT
                 2. ctc(2)          - The switch mode of gpon ont interoperability is ctc
                 3. ericV1(3)       - The switch mode of gpon ont interoperability is ericV1
                 4. ericV2(4)       - The switch mode of gpon ont interoperability is ericV2
                 5. ituTG984(5)     - The switch mode of gpon ont interoperability is ituTG984
                 6. ituTG988(6)     - The switch mode of gpon ont interoperability is ituTG988  
                 7. cuc(7)          - The switch mode of gpon ont interoperability is cuc
                 8. cmcc(8)         - The switch mode of gpon ont interoperability is cmcc
                 9. eci(9)          - The switch mode of gpon ont interoperability is eci
                 10.mode1(10)       - The switch mode of gpon ont interoperability is mode1
                 11.mode2(11)       - The switch mode of gpon ont interoperability is mode2
                 12.mode2V2(12)     - The switch mode of gpon ont interoperability is mode2V2
                 13.mode3(13)       - The switch mode of gpon ont interoperability is mode3   
                 14.mode4(14)       - The switch mode of gpon ont interoperability is mode4 
                 15.mode2V3(15)     - The switch mode of gpon ont interoperability is mode2V3
                 16.mode2V4(16)     - The switch mode of gpon ont interoperability is mode2V4
                 17.mode5(17)       - The switch mode of gpon ont interoperability is mode5
                 18.eciV2(18)       - The switch mode of gpon ont interoperability is eciV2 
                 19.mode1V2(19)     - The switch mode of gpon ont interoperability is mode1V2
                "
            ::= { hwGponDeviceCommonGlobalObjects 3 }  
            
        hwGponDeviceOntDefaultLineProfName  OBJECT-TYPE
            SYNTAX      OCTET STRING (SIZE (0..32))
            MAX-ACCESS  read-only
            STATUS      current
            DESCRIPTION
                "This object indicates the name of the default line profile that is bound to the ONT."
            ::= { hwGponDeviceCommonGlobalObjects 4 }

        hwGponDeviceOntDefaultSrvProfName  OBJECT-TYPE
            SYNTAX      OCTET STRING (SIZE (0..32))
            MAX-ACCESS  read-only
            STATUS      current
            DESCRIPTION
                "This object indicates the name of the default service profile that is bound to the ONT."
            ::= { hwGponDeviceCommonGlobalObjects 5 }
           
       hwGponOntMutlicastAuthMode   OBJECT-TYPE
            SYNTAX  INTEGER
              {
                  ontControl(1),
                  oltControl(2)
              }
            MAX-ACCESS read-write
            STATUS current
            DESCRIPTION
                "The mode of gpon ont multicast authentication.
                 Options:
                 1. ontControl(1)  - The mode of gpon multicast authentication is ont-control
                 2. oltControl(2)  - The mode of gpon multicast authentication is olt-control
                "
            ::= { hwGponDeviceCommonGlobalObjects 6 }       
                      
       hwGponOnuTcontPriorityQueuePriorityReverse   OBJECT-TYPE
            SYNTAX  INTEGER
              {                  
                  enable(1),
                  disable(2)
              }
            MAX-ACCESS read-write
            STATUS current
            DESCRIPTION
                "The priority reverse switch of gpon ont priority queue.
                 Options:
                 1. enable(1)  - The priority reverse switch is enable
                 2. disable(2)   - The priority reverse switch is disable
                "
            ::= { hwGponDeviceCommonGlobalObjects 7 }
              
       hwGponOntInteroperModeActiveMode   OBJECT-TYPE
            SYNTAX  INTEGER
              {                  
                  immediate(1),
                  nextStartup(2),
                  invalid(-1)
              }
            MAX-ACCESS read-write
            STATUS current
            DESCRIPTION
                 "The active mode of gpon ONT interoperability mode.
                 Options:
                 1. immediate(1)     - Indicates that the ONT takes effect immediately
                 2. nextStartup(2)  - Indicates that the ONT takes effect after next startup
                 3. invalid(-1)      - Indicates that the query fails or no information is detected
                 "
            ::= { hwGponDeviceCommonGlobalObjects 8 }         

       hwGponDeviceTcontAutoCreateSwitch  OBJECT-TYPE
            SYNTAX  INTEGER
              {
                  enable(1),
                  disable(2)
              }
            MAX-ACCESS read-write
            STATUS current
            DESCRIPTION
                "The switch value of T-CONT auto-create.
                 Options:
                 1. enable(1)  - The switch value of T-CONT auto-create is enable
                 2. disable(2) - The switch value of T-CONT auto-create is disable
                 The default value is disable(2)
                "
            ::= { hwGponDeviceCommonGlobalObjects 9 }       
            
       hwGponOntPriorityQueueMappingPolicySwitch  OBJECT-TYPE
            SYNTAX  INTEGER
              {
                  gemMap(1),
                  cosMap(2)
              }
            MAX-ACCESS read-write
            STATUS current
            DESCRIPTION
                "The switch value of GPON ONT priority queue mapping policy.
                 Options:
                 1. gemMap(1)  - GPON ONT priority queue mapping policy is gemMap
                 2. cosMap(2)  - GPON ONT priority queue mapping policy is cosMap
                 The default value is gemMap(1)
                "
            ::= { hwGponDeviceCommonGlobalObjects 10 } 

       hwGponDeviceXgMulticastGemportId  OBJECT-TYPE
            SYNTAX Integer32
            MAX-ACCESS read-write
            STATUS current
            DESCRIPTION
                "The GEM port ID for XG-PON multicast service, ranging from 65439 to 65534.
                 The default value is 65534.
                "
            ::= { hwGponDeviceCommonGlobalObjects 11 } 
            
       hwGponOntWanConfigMode   OBJECT-TYPE
            SYNTAX  INTEGER
              {
                  setAfterCreate(1),
                  setByCreate(2)
              }
            MAX-ACCESS read-write
            STATUS current
            DESCRIPTION
                "The mode of gpon ont wan config mode.
                 Options:
                 1. setAfterCreate(1)  - The mode of gpon wan config mode is set-after-create   
                 2. setByCreate(2)     - The mode of gpon wan config mode is set-by-create                               
                "
            ::= { hwGponDeviceCommonGlobalObjects 12 }              
                
         hwGponDeviceAntiDosPloamSwitch  OBJECT-TYPE
            SYNTAX  INTEGER
              {
                  enable(1),
                  disable(2)
              }
            MAX-ACCESS read-write
            STATUS current
            DESCRIPTION
                "The switch value of anti-dos PLOAM.
                 Options:
                 1. enable(1)  - The switch value of anti-dos PLOAM is enable
                 2. disable(2) - The switch value of anti-dos PLOAM is disable
                 The default value is disable(2)
                "
            ::= { hwGponDeviceCommonGlobalObjects 13 }
            
        hwGponOntHomeGatewayConfigMethod  OBJECT-TYPE
            SYNTAX  INTEGER
              {
                  xml(1),
                  omci(2)
              }
            MAX-ACCESS read-write
            STATUS current
            DESCRIPTION
                "The config method of home gateway.
                 Options:
                 1. xml(1)  - The config method of home gateway is xml.
                 2. omci(2) - The config method of home gateway is omci.
                "
            ::= { hwGponDeviceCommonGlobalObjects 14}    
            
        hwGponDeviceSnOutPutFormatPolicy  OBJECT-TYPE
            SYNTAX  INTEGER
              {
                  default(1),
                  vendorPrefix(2)
              }
            MAX-ACCESS read-write
            STATUS current
            DESCRIPTION
                "The output format of SN.
                 Options:
                 1. default(1)        - The output format of SN is default
                 2. vendorPrefix(2)   - The output format of SN is vendor-prefix
                 The default value is default(1)                
                "
            ::= { hwGponDeviceCommonGlobalObjects 15}
            
        hwGponDeviceOmciBandwidthCompensateSwitch  OBJECT-TYPE
            SYNTAX  INTEGER
              {
                  enable(1),
                  disable(2),
                  invalid(-1)
              }
            MAX-ACCESS read-write
            STATUS current
            DESCRIPTION
                "The switch value of omci bandwidth compensate.
                 Options:
                 1. enable(1)   - The switch value of omci bandwidth compensate is enable
                 2. disable(2)  - The switch value of omci bandwidth compensate is disable
                 3. invalid(-1) - The switch value of omci bandwidth compensate is invalid
                 The default value is disable(2)               
                "
            ::= { hwGponDeviceCommonGlobalObjects 16}  
            
        hwGponOntVlanTagOperMode   OBJECT-TYPE
            SYNTAX  INTEGER
              {
                  modifyExternalTag(1),
                  modifySingleTag(2)
              }
            MAX-ACCESS read-write
            STATUS current
            DESCRIPTION
                "The mode of gpon ont vlan tag operation mode.
                 Options:
                 1. modifyExternalTag(1)  - The mode of gpon vlan tag operation mode is modify-external-tag   
                 2. modifySingleTag(2)    - The mode of gpon vlan tag operation mode is modify-single-tag,this is the default mode.                               
                "
            ::= { hwGponDeviceCommonGlobalObjects 17 } 
                                      
        hwGponOntAniMVlanFilter  OBJECT-TYPE
            SYNTAX  INTEGER
              {
                  default(0),
                  enable(1),
                  disable(2)
              }
            MAX-ACCESS read-write
            STATUS current
            DESCRIPTION
                "Indicates the mode of multicast VLAN filtering on the GPON ONT ANI side.
                 Options: 
                 1. default(0) -Indicates the default system behavior.                 
                 2. enable(1)  -Creates the multicast VLAN tagging filter data entity on the ANI side and issues the multicast VLAN to this entity. 
                 3. disable(2) -Do not create the multicast VLAN tagging filter data entity on the ANI side or issue the multicast VLAN to this entity.
                 The default value is default(0).
                "
            ::= { hwGponDeviceCommonGlobalObjects 18}  

        hwGponOntQueueMapQueue0ID OBJECT-TYPE
            SYNTAX      Integer32 (0..3 | 255)
            MAX-ACCESS  read-write
            STATUS      current
            DESCRIPTION
                "Configures the rule of mapping the GPON ONT virtual queue to actual queue. 
                 Note the leaves hwGponOntQueueMapQueue0ID to hwGponOntQueueMapQueue7ID must be configured concurrently. Otherwise, the OLT reports an error.  
                 1. queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
            ::= { hwGponDeviceCommonGlobalObjects 19}
            
        hwGponOntQueueMapQueue1ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
            ::= { hwGponDeviceCommonGlobalObjects 20}

        hwGponOntQueueMapQueue2ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
            ::= { hwGponDeviceCommonGlobalObjects 21}
            
        hwGponOntQueueMapQueue3ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
            ::= { hwGponDeviceCommonGlobalObjects 22}
            
        hwGponOntQueueMapQueue4ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
            ::= { hwGponDeviceCommonGlobalObjects 23}
            
        hwGponOntQueueMapQueue5ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "

            ::= { hwGponDeviceCommonGlobalObjects 24}
            
        hwGponOntQueueMapQueue6ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
           ::= { hwGponDeviceCommonGlobalObjects 25}
            
        hwGponOntQueueMapQueue7ID OBJECT-TYPE
            SYNTAX      Integer32 (0..3 | 255)
            MAX-ACCESS  read-write
            STATUS      current
            DESCRIPTION
                 "Configures the rule of mapping the GPON ONT virtual queue to actual queue. 
                  Note the leaves hwGponOntQueueMapQueue0ID to hwGponOntQueueMapQueue7ID must be configured concurrently. Otherwise, the OLT reports an error.  
                 1. Queue0-id to queue7-id are IDs mapping virtual queues to actual ONT queues. 
                    The value range is 0-3. The current OMCI protocol supports scenarios of 4 queues and 8 queues. 
                    If the ONT has 8 queues, this configuration does not take effect. If the ONT has 4 queues, this configuration takes effect.  
                 2. This operation affects services of all online ONUs.  
                 3. Queue0-id to queue7-id configured by running this command must start from 0 and are configured in ascending order.  
                 4. The 8 queues must completely map to 4 queues, that is, values 0-3 must be configured.  
                 
                 Options: 
                    0..3. Indicates IDs of actual ONT queues. 
                    0xff. Indicates configuration deletion. 
                "
           ::= { hwGponDeviceCommonGlobalObjects 26}
           
         hwGponDeviceGemPortEncryptMode     OBJECT-TYPE
            SYNTAX INTEGER {
                on(1),
                off(2)
            }
            MAX-ACCESS read-write
            STATUS current
            DESCRIPTION
                "This object indicates the automatic allocation gemport encrypt mode.
                 Options:
                 1. on(1)      - Indicates that the automatic allocation gemport encrypt mode is on
                 2. off(2)     - Indicates that the automatic allocation gemport encrypt mode is off
                 The default value is off(2).
                "
            ::= { hwGponDeviceCommonGlobalObjects 27 }  
						
        hwGponDeviceOntLOOCiAlarmThreshold OBJECT-TYPE
            SYNTAX Integer32 (1..100)
            MAX-ACCESS read-write
            STATUS  current
            DESCRIPTION
                "This object indicates the GPON LOOCi alarm  generation threshold, in times.
                 The restoration threshold must be lower than the generation threshold.
                 The default value is 100."
            ::= { hwGponDeviceCommonGlobalObjects 28 }

        hwGponDeviceOntLOOCiAlarmRestoreThreshold OBJECT-TYPE
            SYNTAX Integer32 (0..99)
            MAX-ACCESS read-write
            STATUS  current
            DESCRIPTION
                "This object indicates the GPON LOOCi alarm restoration threshold, in times.
                 The restoration threshold must be lower than the generation threshold.
                 The default value is 0."
            ::= { hwGponDeviceCommonGlobalObjects 29 }

        hwGponDeviceOntLOOCiAlarmMonitorPeriod OBJECT-TYPE
            SYNTAX Integer32 (60..900)
            MAX-ACCESS read-write
            STATUS  current
            DESCRIPTION
                "This object indicates GPON LOOCi alarm monitoring period, in seconds.
                 The default value is 900."
            ::= { hwGponDeviceCommonGlobalObjects 30 }		
                                                                
  --hwGponDeviceCommonGlobalObjects   end   

  --hwEponDeviceCommonGlobalObjects   begin            
         hwEponInteroperModeGlobalStandard       OBJECT-TYPE
            SYNTAX  INTEGER
              {
                  ctc(1),
                  cuc(2)
              }
            MAX-ACCESS read-write
            STATUS current
            DESCRIPTION
                "The switch mode of epon ont interoperability.
                 Options:
                 1. ctc(1)      - The mode standard of epon ont interoperability is ctc  
                 2. cuc(2)      - The mode standard of epon ont interoperability is cuc
                "
            ::= { hwEponDeviceCommonGlobalObjects 1 }  
              
       hwEponInteroperModeGlobalActiveMode       OBJECT-TYPE
            SYNTAX  INTEGER
              {                  
                  immediate(1),
                  nextStartup(2),
                  invalid(-1)
              }
            MAX-ACCESS read-write
            STATUS current
            DESCRIPTION
                 "The active mode of epon ONT interoperability mode.
                 Options:
                 1. immediate(1)     - Indicates that the epon ONT takes effect immediately
                 2. nextStartup(2)  - Indicates that the epon ONT takes effect after next startup
                 3. invalid(-1)      - Indicates that the query fails or no information is detected
                 "
            ::= { hwEponDeviceCommonGlobalObjects 2 }  
            
       hwEponInteroperModeGlobalStandardVersion  OBJECT-TYPE
            SYNTAX Integer32 (0..254) 
            MAX-ACCESS read-write
            STATUS current
            DESCRIPTION
                "This object indicates the oui version of epon ONT interoperability.
                 0 indicates that the oui version of epon ONT interoperability is not specified.
                 0x21 indicates that the oui version of epon ONT interoperability 2.1.        
                "
            ::= { hwEponDeviceCommonGlobalObjects 3 }                 
                        
  --hwEponDeviceCommonGlobalObjects   end 

  --hwXponDeviceCommonGlobalObjects   begin 
        hwXponDeviceLosAlarmControlState  OBJECT-TYPE
            SYNTAX  INTEGER {
                enable(1),
                disable(2)
            }
            MAX-ACCESS read-write
            STATUS current
            DESCRIPTION
                   "The object is used to open or close the switch of the advanced los alarm.
                   Options:
                   1.enable(1)     - Open the switch of the advanced los alarm
                   2.disable(2)    - Close the switch of the advanced los alarm
                   The default value is disable(2).
                   "
            ::= { hwXponDeviceCommonGlobalObjects 1 }

        hwXponCommonOntCatvDefaultState OBJECT-TYPE
            SYNTAX     INTEGER {
                on(1),
                off(2),
                invalid(-1)
            }
            MAX-ACCESS read-write
            STATUS current
            DESCRIPTION
                "This object is used to set the default status of ONT CATV ports.
                 Options:
                 1. on(1)             - The default status of ONT CATV ports is on
                 2. off(2)            - The default status of ONT CATV ports is off
                 3. invalid(-1)       - Indicates that the query fails
                "
            ::= { hwXponDeviceCommonGlobalObjects 2 }
            
        hwXponDeviceGroupPowerOffControlState OBJECT-TYPE
            SYNTAX     INTEGER {
                enable(1),
                disable(2)
            }
            MAX-ACCESS read-write
            STATUS current
            DESCRIPTION
                "This object is used to open or close the group power off report switch.
                 Options:
                 1.enable(1)     - Open the group power off report switch      
                 2.disable(2)    - Close the group power off report switch
                 The default value is disable(2)
                "
            ::= { hwXponDeviceCommonGlobalObjects 3 }
               
        hwXponDeviceAutofindConflictCheckSwitch OBJECT-TYPE
            SYNTAX INTEGER {
                enable(1),
                disable(2)
            }
            MAX-ACCESS read-write
            STATUS current
            DESCRIPTION
                "This object is used to open or close the ONT autofind conflict-check switch.
                 Options:
                 1.enable(1)     - Open the switch of the ONT autofind conflict-check
                 2.disable(2)    - Close the switch of the ONT autofind conflict-check
                 The default value is disable(2)
                "
            ::= { hwXponDeviceCommonGlobalObjects 4 }
            
        hwXponDeviceModifyBoundProfileSwitch  OBJECT-TYPE
            SYNTAX  INTEGER {
                enable(1),
                disable(2),
                invalid(-1)
            }
            MAX-ACCESS read-write
            STATUS current
            DESCRIPTION
                   "This object is used to enable or disable the bound profile modification switch.
                   Options:
                   1.enable(1)     - Enable to modify bound profile
                   2.disable(2)    - Disable to modify bound profile
                   3.invalid(-1)   - Indicates that the query fails
                   The default value is enable(1).
                   "
            ::= { hwXponDeviceCommonGlobalObjects 5 }
            
        hwXponDeviceAlarmClearOnShutdown  OBJECT-TYPE
            SYNTAX  INTEGER {
                enable(1),
                disable(2)
            }
            MAX-ACCESS read-write
            STATUS current
            DESCRIPTION
                   "The object is used to set whether clear active alarm on shutdown object.
                   Options:
                   1.enable(1)     - Open the switch, clear active alarm on shutdown object
                   2.disable(2)    - Close the switch, does not clear active alarm on shutdown object
                   The default value is disable(2).
                   "
            ::= { hwXponDeviceCommonGlobalObjects 6 }
            
        hwXponDeviceSuppressInitialAlarmState  OBJECT-TYPE
            SYNTAX  INTEGER {
                enable(1),
                disable(2),
                enableexceptopticalalarm(3)
            }
            MAX-ACCESS read-write
            STATUS current
            DESCRIPTION
                   "The object is used to set whether suppress initial alarm.
                   Options:
                   1.enable(1)                    - Open the switch, suppress initial alarm state
                   2.disable(2)                   - Close the switch, does not suppress initial alarm state
                   3.enableexceptopticalalarm(3)  - Suppress other alarms, does not suppress optical module
                   The default value is enable(1).
                   "
            ::= { hwXponDeviceCommonGlobalObjects 7 }
            
        hwXponDeviceAllowDifferentRangeSwitch  OBJECT-TYPE
            SYNTAX  INTEGER {
                enable(1),
                disable(2)
            }
            MAX-ACCESS read-write
            STATUS current
            DESCRIPTION
                   "This object is used to enable or disable the switch of allowing protect group member ports have different distances.
                   Options:
                   1.enable(1)     - Enable the switch of allowing protect group member ports have different distances
                   2.disable(2)    - Disable the switch of allowing protect group member ports have different distances
                   The default value is disable(2).
                   "
            ::= { hwXponDeviceCommonGlobalObjects 8 }

        hwXponOntInteroperabilityFileVersion  OBJECT-TYPE
            SYNTAX  OCTET STRING (SIZE(9))
            MAX-ACCESS read-only
            STATUS current
            DESCRIPTION
                   "This object is used to query the version of the ont interoperability file.
                   The value of this node:
                   Year(2byte)         : 65535-invalid
                   Month(1byte)        : 255-invalid
                   Day(1byte)          : 255-invalid
                   Hour(1byte)         : 255-invalid
                   Minute(1byte)       : 255-invalid
                   Second(1byte)       : 255-invalid
                   CrcCode(2byte)      : The CRC value of ont interoperability file.
                   "
            ::= { hwXponDeviceCommonGlobalObjects 9 }
            
        hwXponDeviceOperatorCheckSwitch  OBJECT-TYPE
            SYNTAX  INTEGER {
                enable(1),
                disable(2)
            }
            MAX-ACCESS read-write
            STATUS current
            DESCRIPTION
                   "The object is used to set operator check switch.
                   Options:
                   1.enable(1)     - Open the switch
                   2.disable(2)    - Close the switch
                   The default value is disable(2).
                   "
            ::= { hwXponDeviceCommonGlobalObjects 10 }    
        hwXponDeviceOperatorCheckCode  OBJECT-TYPE
            SYNTAX      OCTET STRING (SIZE(0..16))
            MAX-ACCESS read-write
            STATUS current
            DESCRIPTION
                   "The object is used to set operator check code."
            ::= { hwXponDeviceCommonGlobalObjects 11 }  
        hwXponDeviceOperatorCheckHistoryCodeMaxNumber  OBJECT-TYPE
            SYNTAX Integer32
            MAX-ACCESS read-write
            STATUS current
            DESCRIPTION
                   "The object is used to set max number of operator check history code.
                    range: 0-11."
            ::= { hwXponDeviceCommonGlobalObjects 12 }   
        hwXponDeviceOperatorCheckHistoryCodeClear  OBJECT-TYPE
            SYNTAX      OCTET STRING (SIZE(0..16)) 
            MAX-ACCESS read-write
            STATUS current
            DESCRIPTION
                   "The object is used to clear operator check history code."
            ::= { hwXponDeviceCommonGlobalObjects 13 } 
	    
        hwXponCommonDeviceOntPowerReductionSwitch OBJECT-TYPE
            SYNTAX  INTEGER{
                enable (1),
                disable (2)
            }
            MAX-ACCESS read-write
            STATUS current
            DESCRIPTION
                "This object is used to open or close the ONT global  switch.
                 Options:   
                 1.enable(1)      - Open the switch of the ONT power reduction. 
                 2.disable(2)     - Close the switch of the ONT power reduction.
                 The default value is disable(2)
                "
            ::= { hwXponDeviceCommonGlobalObjects 14 } 
	    
		hwXponDeviceAntiWeakLightRogueSwitch OBJECT-TYPE
            SYNTAX  INTEGER{
                enable (1),
                disable (2)
            }
            MAX-ACCESS read-write
            STATUS current
            DESCRIPTION
                "This object is used to enable or disable the function of anti-rogue ONTs that transmit weak optical signals.
                 Options:   
                 1.enable(1)      - Enable the function of anti-rogue ONTs that transmit weak optical signals. 
                 2.disable(2)     - Disable the function of anti-rogue ONTs that transmit weak optical signals.
                 The default value is disable(2)
                "
            ::= { hwXponDeviceCommonGlobalObjects 15 }    

        hwXponDeviceOntUserMulticastProcess  OBJECT-TYPE
            SYNTAX  INTEGER {
                forward(1),
                discard(2)
            }
            MAX-ACCESS read-write
            STATUS  current
            DESCRIPTION
                "This object indicates the processing mode of the ONT user-side multicast packet.
                 Options:
                 1.forward(1)        - Indicates the forward processing mode.
                 2.discard(2)        - Indicates the discard processing mode.
                 The default value is forward(1).
                "
            ::= { hwXponDeviceCommonGlobalObjects 16 }     
                            
        hwXponDevicePortFaultCheckSwitch  OBJECT-TYPE
            SYNTAX  INTEGER {
                enable(1),
                disable(2)
            }
            MAX-ACCESS read-write
            STATUS  current
            DESCRIPTION
                "This object indicates the switch value of PON fault check.
                 Options:
                 1.enable(1)        - The switch value of PON fault check is enable.
                 2.disable(2)       - The switch value of PON fault check is disable.
                 The default value is disable(2).
                "
            ::= { hwXponDeviceCommonGlobalObjects 17 }  
                            
        hwXponDeviceRogueOntSelfDetectSwitch  OBJECT-TYPE
            SYNTAX  INTEGER {
                enable(1),
                disable(2),
		unconcern(3)
            }
            MAX-ACCESS read-write
            STATUS  current
            DESCRIPTION
                "This object indicates the self-detected switch of rogue ONTs.
                 Options:
                 1.enable(1)        - The self-detected switch of rogue ONTs is enable. 
                 2.disable(2)       - The self-detected switch of rogue ONTs is disable.
		 3.unconcern(3)     - The self-detected switch of rogue ONTs is unconcern.
                 The default value is unconcern(3).
                "
            ::= { hwXponDeviceCommonGlobalObjects 18 } 

        hwXponDeviceOntOfflineMonitorSwitch  OBJECT-TYPE
            SYNTAX  INTEGER {
                enable(1),
                disable(2)
            }
            MAX-ACCESS read-write
            STATUS  current
            DESCRIPTION
                "This object indicates the switch value of ONTs offline monitoring.
                 Options:
                 1.enable(1)        - The switch of ONTs offline monitoring is enable. 
                 2.disable(2)       - The switch of ONTs offline monitoring is disable.
                 The default value is disable(2).
                "
            ::= { hwXponDeviceCommonGlobalObjects 19 }	

        hwXponDeviceOntOfflineMonitorAlarmThresholdRatio  OBJECT-TYPE
            SYNTAX Integer32 (0..100)
            MAX-ACCESS read-write
            STATUS  current
            DESCRIPTION
                "This object indicates the ratio of ONTS offline monitoring alarm generation threshold.
                 The restoration threshold must be higher than the generation threshold.
                 The default value is 70."
            ::= { hwXponDeviceCommonGlobalObjects 20 }

        hwXponDeviceOntOfflineMonitorRestoreThresholdRatio  OBJECT-TYPE
            SYNTAX Integer32 (0..100)
            MAX-ACCESS read-write
            STATUS  current
            DESCRIPTION
                "This object indicates the ratio of ONTS offline monitoring alarm restoration threshold.
                 The restoration threshold must be higher than the generation threshold.
                 The default value is 80."
            ::= { hwXponDeviceCommonGlobalObjects 21 }   
                   
        hwXponDeviceTypeBLosAlarmControlState  OBJECT-TYPE
            SYNTAX  INTEGER {
                enable(1),
                disable(2)
            }
            MAX-ACCESS read-write
            STATUS current
            DESCRIPTION
                   "The object is used to open or close the switch of the los alarm for the standby port in the Type B protect group.
                   Options:
                   1.enable(1)     - Open the switch of the los alarm for the standby port in the Type B protect group
                   2.disable(2)    - Close the switch of the los alarm for the standby port in the Type B protect group
                   The default value is disable(2).
                   "
            ::= { hwXponDeviceCommonGlobalObjects 22 }
			
	hwXponDeviceOltOpticalAlarmAutoMonitorSwitch  OBJECT-TYPE
            SYNTAX  INTEGER {
                disable(2),
                opticalThreshold(11),
                standardThreshold(12),
                invalid(-1)
            }
            MAX-ACCESS read-write
            STATUS current
            DESCRIPTION
                   "The object is used to configure automatic monitoring on OLT optical alarm, the function will be disabled when the PON port is bound to optical alarm profile.
                   Options:
                   1. disable(2)    - The function is disabled
                   2. opticalThreshold (11)    - The function is enabled, the optical threshold is read from the optical module, which is defined by the manufacturer
                   3. standardThreshold(12)    - The function is enabled, the alarm threshold is defined by the standard threshold
                   4. invalid(-1)       - Indicates that the query fails or no information is detected
                   The default value is disable(2).
                   "
            ::= { hwXponDeviceCommonGlobalObjects 23 }
			
	hwXponDeviceOntOpticalAlarmAutoMonitorSwitch  OBJECT-TYPE
            SYNTAX  INTEGER {
                disable(2),
                opticalThreshold(11),
                standardThreshold(12),
                invalid(-1)
            }
            MAX-ACCESS read-write
            STATUS current
            DESCRIPTION
                   "The object is used to configure automatic monitoring on ONT optical alarm, the function will be disabled when the ONT is bound to optical alarm profile.
                   Options:
                   1. disable(2)      - The function is disabled
                   2. opticalThreshold (11)    - The function is enabled, the optical threshold is read from the optical module, which is defined by the manufacturer
                   3. standardThreshold(12)    - The function is enabled, the alarm threshold is defined by the standard threshold
                   4. invalid(-1)       - Indicates that the query fails or no information is detected
                   The default value is disable(2).
                   "
            ::= { hwXponDeviceCommonGlobalObjects 24 }
	    
        hwXponDeviceVsOntIdAllocPolicy  OBJECT-TYPE
            SYNTAX  INTEGER {
                global(1),
                independent(2)
            }
            MAX-ACCESS read-write
            STATUS  current
            DESCRIPTION
                "This object indicates the ONT ID alloc policy of virtual system.
                 Options:
                 1.global(1)         - The ONT ID alloc policy is global. 
                 2.independent(2)    - The ONT ID alloc policy is independent.
                 The default value is independent(2).
                "
            ::= { hwXponDeviceCommonGlobalObjects 25 }

        hwXponDeviceOntLowBandwidthUsageMonitorSwitch  OBJECT-TYPE
            SYNTAX  INTEGER {
                enable(1),
                disable(2)
            }
            MAX-ACCESS read-write
            STATUS current
            DESCRIPTION
                   "This object is used to enable or disable monitoring on ONT abnormal bandwidth request.
                   Options:
                   1.enable(1)     - Enable monitoring on ONT abnormal bandwidth request
                   2.disable(2)    - Disable monitoring on ONT abnormal bandwidth request
                   The default value is enable(1).
                   "
            ::= { hwXponDeviceCommonGlobalObjects 26 }   
        
        hwXponDeviceAntiRogueOamOntAutoIsolateMode  OBJECT-TYPE
            SYNTAX  INTEGER {
                deactivate(1),
                reset(2),
                disable(3)
            }
            MAX-ACCESS read-write
            STATUS current
            DESCRIPTION
                   "This object indicates the anti-rogueont isolation mode for OAM management mode ONT, it is used for EPON ONT.
                   Options:
                   1.deactivate(1)     - Indicates that the isolation mode is deactivate.
                   2.reset(2)          - Indicates that the isolation mode is reset. 
                   3.disable(3)        - Indicates that the isolation mode is disable.
                   The default value is disable(3).
                   "
            ::= { hwXponDeviceCommonGlobalObjects 27 }    
       
       hwXponDeviceAntiRogueSnmpOntAutoIsolateMode  OBJECT-TYPE
            SYNTAX  INTEGER {
                deactivate(1),
                reset(2),
                disable(3)
            }
            MAX-ACCESS read-write
            STATUS current
            DESCRIPTION
                   "This object indicates the anti-rogueont isolation mode for SNMP management mode ONT,it is used for EPON MxU.
                   Options:
                   1.deactivate(1)     - Indicates that the isolation mode is deactivate.
                   2.reset(2)          - Indicates that the isolation mode is reset. 
                   3.disable(3)        - Indicates that the isolation mode is disable.
                   The default value is disable(3).
                   "
            ::= { hwXponDeviceCommonGlobalObjects 28 }  
	    
       hwXponDeviceOntOpticalDdmQuickQuerySwitch  OBJECT-TYPE
            SYNTAX  INTEGER {
                disable(1),
                enable(2),
	        invalidState(-1)
            }
            MAX-ACCESS read-write
            STATUS current
            DESCRIPTION
                   "This object is used to enable or disable fast query of DDM parameters of an ONT optical module.		   
                   Options:
                   1.disable(1)           - Indicates that fast query of DDM parameters of an ONT optical module is disabled.
                   2.enable(2)            - Indicates that fast query of DDM parameters of an ONT optical module is enabled.
	           3.invalidState(-1)     - Indicates that the query fails or no information is detected.
                   The default value is disable(1).
                   "
            ::= { hwXponDeviceCommonGlobalObjects 29 } 
            
       hwXponDeviceAutoRecoverySwitch   OBJECT-TYPE
            SYNTAX  INTEGER {
                enable(1),
                disable(2)
            }
            MAX-ACCESS read-write
            STATUS current
            DESCRIPTION
                "This object indicates the xPON auto recovery switch.
                 Options:
                 1. enable(1)     - Indicates that the xPON auto recovery switch is enable
                 2. disable (2)   - Indicates that the xPON auto recovery switch is disable
                 The default value is enable(1).
                 "
            ::= { hwXponDeviceCommonGlobalObjects 30 }  
                                                                                  
	hwXponDeviceAuthConflictCheckBySnSwitch  OBJECT-TYPE
            SYNTAX  INTEGER {
                enable(1),
                disable(2)
            }
            MAX-ACCESS read-write
            STATUS current
            DESCRIPTION
                   "This object indicates the switch value of ONT authentication conflict check by SN.		   
                   Options:
                   1.enable(1)            - Indicates that the switch value of ONT authentication conflict check by SN is enable,ONT unique SN in system.
                   2.disable(2)           - Indicates that the switch value of ONT authentication conflict check by SN is disable, ONT unique SN in port.    
                   The default value is enable(1).
                   "
            ::= { hwXponDeviceCommonGlobalObjects 31 }  
	hwXponDeviceAuthConflictCheckByLoidSwitch  OBJECT-TYPE
            SYNTAX  INTEGER {
                enable(1),
                disable(2)
            }
            MAX-ACCESS read-write
            STATUS current
            DESCRIPTION
                   "This object indicates the switch value of ONT authentication conflict check by LOID.		   
                   Options:
                   1.enable(1)            - Indicates that the switch value of ONT authentication conflict check by LOID is enable,ONT unique LOID in system.
                   2.disable(2)           - Indicates that the switch value of ONT authentication conflict check by LOID is disable, ONT unique LOID in port.    
                   The default value is enable(1).
                   "
            ::= { hwXponDeviceCommonGlobalObjects 32 } 
  hwXponDeviceOperatorCheckVersion  OBJECT-TYPE
            SYNTAX  INTEGER {
                version1(1),
                version2(2)
            }
            MAX-ACCESS read-write
            STATUS current
            DESCRIPTION
                   "The object is used to set operator check version
                   Options:
                   1.version1(1),     - set operator check version1
                   2.version2(2),     - set operator check version2
                   The default value is version1(1).
                   "
            ::= { hwXponDeviceCommonGlobalObjects 33 }
  hwXponDeviceAutoFindAdditionalNoticeTimes OBJECT-TYPE
            SYNTAX Integer32 (0..10)
            MAX-ACCESS read-write
            STATUS current
            DESCRIPTION
                "The object indicates the times of sending auto-found ONT additional notices. 
				The value ranges from 0 to 10. If this parameter is set to 0, the auto found ONT additional notice function is disabled. 
				This node must be set together with the hwXponDeviceAutoFindAdditionalNoticeDistanceTime node. 
                "               
            ::= { hwXponDeviceCommonGlobalObjects 34 }
  hwXponDeviceAutoFindAdditionalNoticeDistanceTime OBJECT-TYPE
            SYNTAX Integer32 (255 | 30..100)
            MAX-ACCESS read-write
            STATUS current
            DESCRIPTION
                "The object indicates the interval for sending auto-found ONT additional notices. 
				The value ranges from 30s to 100s. 
				This node must be set together with the hwXponDeviceAutoFindAdditionalNoticeDistanceTime node. 
				If the function of sending auto-found ONT additional notices is disabled, this node is set to 255 which is an invalid value."
            ::= { hwXponDeviceCommonGlobalObjects 35 }
  hwXponDeviceOpticalModuleAlarmControlSwitch   OBJECT-TYPE
            SYNTAX  INTEGER {
                enable(1),
                disable(2)
            }
            MAX-ACCESS read-write
            STATUS current
            DESCRIPTION
                "The object is used to decide whether initial optical module alarm should be reported or suppressed when a port is shut down.
                Options:
                1.enable(1)  - When a port is shut down, no alarm will be reported if we plug-out the optical module.  
                2.disable(2) - When a port is shut down, plug-out the optical module, alarm will be reported;
                               But if there's no optical module at the beginning, no alarm will be reported.  
                The default value is enable(1)."
            ::= { hwXponDeviceCommonGlobalObjects 36 }  

  hwXponDeviceOpticalTraceabilitySwitch   OBJECT-TYPE
            SYNTAX INTEGER {
                enable(1),
                disable(2)
            }
            MAX-ACCESS read-write
            STATUS current
            DESCRIPTION
                "This object indicates the optical traceability switch.
                 Options:
                 1. enable(1)    - Indicates that the optical traceability switch is enable
                 2. disable(2)   - Indicates that the optical traceability switch is disable
                 The default value is disable(2).
                "
            ::= { hwXponDeviceCommonGlobalObjects 37 }   
            	
  hwXponDeviceLosAlarmControlDyingGaspONTNumberRatio OBJECT-TYPE
            SYNTAX Integer32 (0..100)
            MAX-ACCESS read-write
            STATUS current
            DESCRIPTION
                "The object is used to set threshold number ratio of Dyinggasp ONT number to send LOS alarm, the unit is %. 
		 The value 0 indicates that the ratio is unconcern to send LOS alarm. The default value is 0.
                "              
            ::= { hwXponDeviceCommonGlobalObjects 38 }   

  hwXponDeviceLosAlarmControlDyingGaspONTTime OBJECT-TYPE
            SYNTAX Integer32 (6..600)
            MAX-ACCESS read-write
            STATUS current
            DESCRIPTION
                "The object is used to set threshold time of Dyinggasp ONT to send LOS alarm, the unit is s. 
		 The default value is 6s.  
                "              
            ::= { hwXponDeviceCommonGlobalObjects 39 }   
            
  hwXponDeviceTotalONTNumber OBJECT-TYPE
            SYNTAX Integer32 
            MAX-ACCESS read-only
            STATUS current
            DESCRIPTION
                "The object is used to get the total number of ONT in the OLT device.  
                "              
            ::= { hwXponDeviceCommonGlobalObjects 40 }   

  hwXponDeviceTotalOnlineONTNumber OBJECT-TYPE
            SYNTAX Integer32 
            MAX-ACCESS read-only
            STATUS current
            DESCRIPTION
                "The object is used to get the total number of online ONT in the OLT device. 
                "              
            ::= { hwXponDeviceCommonGlobalObjects 41 }   
            
  hwXponDeviceTotalOfflineONTNumber OBJECT-TYPE
            SYNTAX Integer32 
            MAX-ACCESS read-only
            STATUS current
            DESCRIPTION
                "The object is used to get the total number of offline ONT in the OLT device.  
                "              
            ::= { hwXponDeviceCommonGlobalObjects 42 }   
                                    
  --hwXponDeviceCommonGlobalObjects   end
  
  --Table hwXponOntAlarmPolicyTable
        hwXponOntAlarmPolicyTable OBJECT-TYPE
            SYNTAX SEQUENCE OF HwXponOntAlarmPolicyEntry
            MAX-ACCESS not-accessible
            STATUS     current
            DESCRIPTION
                "The hwXponOntAlarmPolicyTable is used to config the ONT alarm policy profile.
                 The index of this table is hwXponOntAlarmPolicyNameIndex.
                "
            ::= { hwXponDeviceCommonProfileObjects 1 }

        hwXponOntAlarmPolicyEntry OBJECT-TYPE
            SYNTAX HwXponOntAlarmPolicyEntry
            MAX-ACCESS not-accessible
            STATUS current
            DESCRIPTION
                "The hwXponOntAlarmPolicyTable is used to config the ONT alarm policy profile.
                 The index of this entry is hwXponOntAlarmPolicyNameIndex.
                "
            INDEX       { IMPLIED hwXponOntAlarmPolicyNameIndex }
            ::= { hwXponOntAlarmPolicyTable 1 }

        HwXponOntAlarmPolicyEntry ::=
            SEQUENCE
                {
                hwXponOntAlarmPolicyNameIndex                OCTET STRING,
                hwXponOntAlarmPolicyBindNum                  Integer32,
                hwXponOntAlarmPolicyFilterAlarmNum           Integer32,
                hwXponOntAlarmPolicyFilterAlarmList          OCTET STRING,
                hwXponOntAlarmPolicyUnFilterAlarmNum         Integer32,
                hwXponOntAlarmPolicyUnFilterAlarmList        OCTET STRING,
                hwXponOntAlarmPolicyRowStatus                RowStatus,
                hwXponOntAlarmPolicyAppendPolicyName         INTEGER,
                hwXponOntAlarmPolicyAppendIpAddress          INTEGER,
                hwXponOntAlarmPolicyAppendMac                INTEGER,
                hwXponOntAlarmPolicyAppendSn                 INTEGER,
                hwXponOntAlarmPolicyAppendLoid               INTEGER
                }

        hwXponOntAlarmPolicyNameIndex  OBJECT-TYPE
            SYNTAX OCTET STRING (SIZE (1..32))
            MAX-ACCESS   not-accessible
            STATUS       current
            DESCRIPTION
                "This object indicates the ONT alarm policy profile name index."
            ::= { hwXponOntAlarmPolicyEntry 1 }

        hwXponOntAlarmPolicyBindNum OBJECT-TYPE
            SYNTAX Integer32
            MAX-ACCESS read-only
            STATUS current
            DESCRIPTION
                "This object indicates the number of ONT bound with alarm policy profile."
            ::= { hwXponOntAlarmPolicyEntry 2 }

        hwXponOntAlarmPolicyFilterAlarmNum OBJECT-TYPE
            SYNTAX Integer32 (0..100)
            MAX-ACCESS read-write
            STATUS current
            DESCRIPTION
                "This object indicates the number of filtered alarm of the alarm policy profile."
            ::= { hwXponOntAlarmPolicyEntry 3 }
            
        hwXponOntAlarmPolicyFilterAlarmList OBJECT-TYPE
            SYNTAX OCTET STRING (SIZE (0..400))
            MAX-ACCESS read-write
            STATUS current
            DESCRIPTION
                "This object indicates the filtered alarm list of the alarm policy profile,and each alarm ID takes 4 bytes."
            ::= { hwXponOntAlarmPolicyEntry 4 }
            
        hwXponOntAlarmPolicyUnFilterAlarmNum OBJECT-TYPE
            SYNTAX Integer32 (0..100)
            MAX-ACCESS read-write
            STATUS current
            DESCRIPTION
                "This object indicates the number of unfiltered alarm of the alarm policy profile."
            ::= { hwXponOntAlarmPolicyEntry 5 }
       
        hwXponOntAlarmPolicyUnFilterAlarmList OBJECT-TYPE
            SYNTAX OCTET STRING (SIZE (0..400))
            MAX-ACCESS read-write
            STATUS current
            DESCRIPTION
                "This object indicates the unfiltered alarm list of the alarm policy profile,and each alarm ID takes 4 bytes."
            ::= { hwXponOntAlarmPolicyEntry 6 }
            
        hwXponOntAlarmPolicyRowStatus OBJECT-TYPE
            SYNTAX RowStatus
            MAX-ACCESS read-create
            STATUS current
            DESCRIPTION
                "The hwXponOntAlarmPolicyRowStatus is used to create a new row
                 or to modify or delete an existing row in this table.
                 Options:
                 1. createAndGo(4) -create a new instance of a conceptual row 
                 2. destroy(6)     -delete the instances associated with an existing conceptual row
                "
            ::= { hwXponOntAlarmPolicyEntry 7 }

        hwXponOntAlarmPolicyAppendPolicyName  OBJECT-TYPE
            SYNTAX  INTEGER {
                enable(1),
                disable(2)
            }
            MAX-ACCESS read-write
            STATUS current
            DESCRIPTION
                   "This object indicates if the ONT alarm appends ONT alarm policy profile name.
                    Options:
                    1.enable(1)     - The ONT alarm appends  ONT alarm policy profile name..
                    2.disable(2)    - The ONT alarm does not append  ONT alarm policy profile name..
                    The default value is enable(1).
                   "
            ::= { hwXponOntAlarmPolicyEntry 8 }

        hwXponOntAlarmPolicyAppendIpAddress  OBJECT-TYPE
            SYNTAX  INTEGER {
                enable(1),
                disable(2)
            }
            MAX-ACCESS read-write
            STATUS current
            DESCRIPTION
                   "This object indicates if the ONT alarm appends IP address.
                    Options:
                    1.enable(1)     - The ONT alarm appends IP address.
                    2.disable(2)    - The ONT alarm does not append IP address.
                    The default value is disable(2).
                   "
            ::= { hwXponOntAlarmPolicyEntry 9 }

        hwXponOntAlarmPolicyAppendMac  OBJECT-TYPE
            SYNTAX  INTEGER {
                enable(1),
                disable(2)
            }
            MAX-ACCESS read-write
            STATUS current
            DESCRIPTION
                   "This object indicates if the ONT alarm appends MAC.
                    Options:
                    1.enable(1)     - The ONT alarm appends MAC.
                    2.disable(2)    - The ONT alarm does not append MAC.
                    The default value is disable(2).
                   "
            ::= { hwXponOntAlarmPolicyEntry 10 }

        hwXponOntAlarmPolicyAppendSn  OBJECT-TYPE
            SYNTAX  INTEGER {
                enable(1),
                disable(2)
            }
            MAX-ACCESS read-write
            STATUS current
            DESCRIPTION
                   "This object indicates if the ONT alarm appends SN.
                    Options:
                    1.enable(1)     - The ONT alarm appends SN.
                    2.disable(2)    - The ONT alarm does not append SN.
                    The default value is disable(2).
                   "
            ::= { hwXponOntAlarmPolicyEntry 11}

        hwXponOntAlarmPolicyAppendLoid  OBJECT-TYPE
            SYNTAX  INTEGER {
                enable(1),
                disable(2)
            }
            MAX-ACCESS read-write
            STATUS current
            DESCRIPTION
                   "This object indicates if the ONT alarm appends LOID.
                    Options:
                    1.enable(1)     - The ONT alarm appends LOID.
                    2.disable(2)    - The ONT alarm does not append LOID.
                    The default value is disable(2).
                   "
            ::= { hwXponOntAlarmPolicyEntry 12 }
            
  --Table hwXponDeviceOntPowerSheddingProfileTable  begin  
        hwXponDeviceOntPowerSheddingProfileTable OBJECT-TYPE
            SYNTAX SEQUENCE OF HwXponDeviceOntPowerSheddingProfileEntry
            MAX-ACCESS not-accessible
            STATUS     current
            DESCRIPTION
                "The hwXponDeviceOntPowerSheddingProfileTable is used to config the ONT power shedding profile.
                 The index of this table is hwXponDeviceOntPowerSheddingProfileNameIndex.
                "
            ::= { hwXponDeviceCommonProfileObjects 2 }

        hwXponDeviceOntPowerSheddingProfileEntry OBJECT-TYPE
            SYNTAX HwXponDeviceOntPowerSheddingProfileEntry
            MAX-ACCESS not-accessible
            STATUS current
            DESCRIPTION
                "The hwXponDeviceOntPowerSheddingProfileTable is used to config the ONT power shedding profile.
                 The index of this entry is hwXponDeviceOntPowerSheddingProfileNameIndex.
                "
            INDEX       { IMPLIED hwXponDeviceOntPowerSheddingProfileNameIndex }
            ::= { hwXponDeviceOntPowerSheddingProfileTable 1 }

        HwXponDeviceOntPowerSheddingProfileEntry ::=
            SEQUENCE
                {
                hwXponDeviceOntPowerSheddingProfileNameIndex                OCTET STRING,
                hwXponDeviceOntPowerSheddingProfileBindNum                  Integer32,
                hwXponDeviceOntPowerSheddingIntervalClassData               Integer32,
                hwXponDeviceOntPowerSheddingIntervalClassVoice              Integer32,
                hwXponDeviceOntPowerSheddingIntervalClassVideoOverlay       Integer32,
                hwXponDeviceOntPowerSheddingIntervalClassVideoReturn        Integer32,
                hwXponDeviceOntPowerSheddingIntervalClassAtm                Integer32,
                hwXponDeviceOntPowerSheddingIntervalClassDsl                Integer32,
                hwXponDeviceOntPowerSheddingIntervalClassCes                Integer32,
                hwXponDeviceOntPowerSheddingIntervalClassFrame              Integer32,
                hwXponDeviceOntPowerSheddingIntervalClassSdhSonet           Integer32,
                hwXponDeviceOntPowerSheddingRestoreInterval                 Integer32,
                hwXponDeviceOntPowerSheddingProfileRowStatus                RowStatus
                }
                
        hwXponDeviceOntPowerSheddingProfileNameIndex  OBJECT-TYPE
            SYNTAX OCTET STRING (SIZE (1..32))
            MAX-ACCESS   not-accessible
            STATUS       current
            DESCRIPTION
                "This object indicates the ONT power shedding profile name index."
            ::= { hwXponDeviceOntPowerSheddingProfileEntry 1 }

        hwXponDeviceOntPowerSheddingProfileBindNum OBJECT-TYPE
            SYNTAX Integer32
            MAX-ACCESS read-only
            STATUS current
            DESCRIPTION
                "This object indicates the number of ONT bound with power shedding profile."
            ::= { hwXponDeviceOntPowerSheddingProfileEntry 2 }
            
        hwXponDeviceOntPowerSheddingIntervalClassData OBJECT-TYPE
            SYNTAX Integer32 (0..65535)
            MAX-ACCESS read-write
            STATUS current
            DESCRIPTION
                "This object indicates the power shedding interval of data class service.
                 Options:
                 1: disables power shedding(0) 
                 2: enables immediate power shed(1)
                 3. 2-65535       - Indicates the time, in seconds, to keep the service active after AC failure before shutting them down and shedding power.                
                "
            ::= { hwXponDeviceOntPowerSheddingProfileEntry 3 }
       
        hwXponDeviceOntPowerSheddingIntervalClassVoice OBJECT-TYPE
            SYNTAX Integer32 (0..65535)
            MAX-ACCESS read-write
            STATUS current
            DESCRIPTION
                "This object indicates the power shedding interval of voice class service.
                 Options:
                 1: disables power shedding(0) 
                 2: enables immediate power shed(1)
                 3. 2-65535       - Indicates the time, in seconds, to keep the service active after AC failure before shutting them down and shedding power.                
                "
            ::= { hwXponDeviceOntPowerSheddingProfileEntry 4 }
            
        hwXponDeviceOntPowerSheddingIntervalClassVideoOverlay OBJECT-TYPE
            SYNTAX Integer32 (0..65535)
            MAX-ACCESS read-write
            STATUS current
            DESCRIPTION
                "This object indicates the power shedding interval of video overlay class service.
                 Options:
                 1: disables power shedding(0) 
                 2: enables immediate power shed(1)
                 3. 2-65535       - Indicates the time, in seconds, to keep the service active after AC failure before shutting them down and shedding power.                
                "
            ::= { hwXponDeviceOntPowerSheddingProfileEntry 5 }
            
        hwXponDeviceOntPowerSheddingIntervalClassVideoReturn OBJECT-TYPE
            SYNTAX Integer32 (0..65535)
            MAX-ACCESS read-write
            STATUS current
            DESCRIPTION
                "This object indicates the power shedding interval of video return class service.
                 Options:
                 1: disables power shedding(0) 
                 2: enables immediate power shed(1)
                 3. 2-65535       - Indicates the time, in seconds, to keep the service active after AC failure before shutting them down and shedding power.                
                "
            ::= { hwXponDeviceOntPowerSheddingProfileEntry 6 }            

        hwXponDeviceOntPowerSheddingIntervalClassDsl OBJECT-TYPE
            SYNTAX Integer32 (0..65535)
            MAX-ACCESS read-write
            STATUS current
            DESCRIPTION
                "This object indicates the power shedding interval of DSL class service.
                 Options:
                 1: disables power shedding(0) 
                 2: enables immediate power shed(1)
                 3. 2-65535       - Indicates the time, in seconds, to keep the service active after AC failure before shutting them down and shedding power.                
                "
            ::= { hwXponDeviceOntPowerSheddingProfileEntry 7 }  
            
        hwXponDeviceOntPowerSheddingIntervalClassAtm OBJECT-TYPE
            SYNTAX Integer32 (0..65535)
            MAX-ACCESS read-write
            STATUS current
            DESCRIPTION
                "This object indicates the power shedding interval of ATM class service.
                 Options:
                 1: disables power shedding(0) 
                 2: enables immediate power shed(1)
                 3. 2-65535       - Indicates the time, in seconds, to keep the service active after AC failure before shutting them down and shedding power.                
                "
            ::= { hwXponDeviceOntPowerSheddingProfileEntry 8 }
       
        hwXponDeviceOntPowerSheddingIntervalClassCes OBJECT-TYPE
            SYNTAX Integer32 (0..65535)
            MAX-ACCESS read-write
            STATUS current
            DESCRIPTION
                "This object indicates the power shedding interval of CES class service.
                 Options:
                 1: disables power shedding(0) 
                 2: enables immediate power shed(1)
                 3. 2-65535       - Indicates the time, in seconds, to keep the service active after AC failure before shutting them down and shedding power.                
                "
            ::= { hwXponDeviceOntPowerSheddingProfileEntry 9 }
            
        hwXponDeviceOntPowerSheddingIntervalClassFrame OBJECT-TYPE
            SYNTAX Integer32 (0..65535)
            MAX-ACCESS read-write
            STATUS current
            DESCRIPTION
                "This object indicates the power shedding interval of frame class service.
                 Options:
                 1: disables power shedding(0) 
                 2: enables immediate power shed(1)
                 3. 2-65535       - Indicates the time, in seconds, to keep the service active after AC failure before shutting them down and shedding power.                
                "
            ::= { hwXponDeviceOntPowerSheddingProfileEntry 10 }
            
        hwXponDeviceOntPowerSheddingIntervalClassSdhSonet OBJECT-TYPE
            SYNTAX Integer32 (0..65535)
            MAX-ACCESS read-write
            STATUS current
            DESCRIPTION
                "This object indicates the power shedding interval of sdh-sonet class service.
                 Options:
                 1: disables power shedding(0) 
                 2: enables immediate power shed(1)
                 3. 2-65535       - Indicates the time, in seconds, to keep the service active after AC failure before shutting them down and shedding power.                
                "
            ::= { hwXponDeviceOntPowerSheddingProfileEntry 11 }            

        hwXponDeviceOntPowerSheddingRestoreInterval OBJECT-TYPE
            SYNTAX Integer32 (0..65535)
            MAX-ACCESS read-write
            STATUS current
            DESCRIPTION
                "This object indicates the time delay, in seconds, before resetting the power-shedding timers after full power restoration."
            ::= { hwXponDeviceOntPowerSheddingProfileEntry 12 }  
             
        hwXponDeviceOntPowerSheddingProfileRowStatus OBJECT-TYPE
            SYNTAX RowStatus
            MAX-ACCESS read-create
            STATUS current
            DESCRIPTION
                "The hwXponDeviceOntPowerSheddingProfileRowStatus is used to create a new row or to modify or delete an existing row in this table.
                 Options:
                 1. createAndGo(4) -create a new instance of a conceptual row 
                 2. destroy(6)     -delete the instances associated with an existing conceptual row 
                "
            ::= { hwXponDeviceOntPowerSheddingProfileEntry 13 }            
                                    
  --Table hwXponDeviceOntPowerSheddingProfileTable  end
  
  --Table hwXponOntTr069ServerProfileTable 
        hwXponOntTr069ServerProfileTable OBJECT-TYPE
            SYNTAX     SEQUENCE OF HwXponOntTr069ServerProfileEntry
            MAX-ACCESS not-accessible
            STATUS     current
            DESCRIPTION
                "This table is used to create, delete or modify the tr069 server profile.
                 The index of this table is hwXponOntTr069ServerProfileName.          
                "
            ::= { hwXponDeviceCommonProfileObjects 3 }
                
        hwXponOntTr069ServerProfileEntry OBJECT-TYPE
            SYNTAX     HwXponOntTr069ServerProfileEntry
            MAX-ACCESS not-accessible
            STATUS     current
            DESCRIPTION
                "This table is used to create, delete or modify the tr069 server profile.
                 The index of this entry is hwXponOntTr069ServerProfileName.          
                "
            INDEX       { IMPLIED hwXponOntTr069ServerProfileName }
            ::= { hwXponOntTr069ServerProfileTable 1 }

        HwXponOntTr069ServerProfileEntry ::=
            SEQUENCE {
                hwXponOntTr069ServerProfileName                     OCTET STRING,
                hwXponOntTr069ServerProfileBindTimes                Integer32,
                hwXponOntTr069ServerProfileUrl                      OCTET STRING,
                hwXponOntTr069ServerProfileUserName                 OCTET STRING,
                hwXponOntTr069ServerProfilePassword                 OCTET STRING,
                hwXponOntTr069ServerProfileRealm                    OCTET STRING,
                hwXponOntTr069ServerProfileRowStatus                RowStatus
            }
            
        hwXponOntTr069ServerProfileName OBJECT-TYPE
            SYNTAX   OCTET STRING (SIZE (1..32))
            MAX-ACCESS  not-accessible
            STATUS      current
            DESCRIPTION
                "This object indicates the tr069-server-profile name."
            ::= { hwXponOntTr069ServerProfileEntry 1 }
            
        hwXponOntTr069ServerProfileBindTimes OBJECT-TYPE
            SYNTAX   Integer32
            MAX-ACCESS  read-only
            STATUS      current
            DESCRIPTION
                "This object indicates the number of ONT bound with tr069-server-profile."
            ::= { hwXponOntTr069ServerProfileEntry 2 }

        hwXponOntTr069ServerProfileUrl OBJECT-TYPE
            SYNTAX   OCTET STRING (SIZE (1..63))
            MAX-ACCESS  read-write
            STATUS      current
            DESCRIPTION
                "This object indicates the server URL.
                 For example: you can set the value of the leaf like 'www.huawei.com'."
            ::= { hwXponOntTr069ServerProfileEntry 3 }

        hwXponOntTr069ServerProfileUserName OBJECT-TYPE
            SYNTAX   OCTET STRING (SIZE (0..50))
            MAX-ACCESS  read-write
            STATUS      current
            DESCRIPTION
                "This object indicates the user name."
            ::= { hwXponOntTr069ServerProfileEntry 4 }

        hwXponOntTr069ServerProfilePassword OBJECT-TYPE
            SYNTAX   OCTET STRING (SIZE (0..25))
            MAX-ACCESS  read-write
            STATUS      current
            DESCRIPTION
                "This object indicates the user password."
            ::= { hwXponOntTr069ServerProfileEntry 5 }
        
        hwXponOntTr069ServerProfileRealm OBJECT-TYPE
            SYNTAX   OCTET STRING (SIZE (0..24))
            MAX-ACCESS  read-write
            STATUS      current
            DESCRIPTION
                "This object indicates the server realm."
            ::= { hwXponOntTr069ServerProfileEntry 6 }
                 
        hwXponOntTr069ServerProfileRowStatus OBJECT-TYPE
            SYNTAX   RowStatus
            MAX-ACCESS  read-create
            STATUS      current
            DESCRIPTION
                "TRow status. This object is used to differentiate the creation, modification and deletion operations for an object.
                 Options:
                 1. createAndGo(4) -create a new instance of a conceptual row 
                 2. destroy(6)     -delete the instances associated with an existing conceptual row
                "
            ::= { hwXponOntTr069ServerProfileEntry 7 }
-- hwXponOntTr069ServerProfileTable  end

  --Table hwXponOntAlarmPolicyAlarmTable 
        hwXponOntAlarmPolicyAlarmTable OBJECT-TYPE
            SYNTAX     SEQUENCE OF HwXponOntAlarmPolicyAlarmEntry
            MAX-ACCESS not-accessible
            STATUS     current
            DESCRIPTION
                "This table is used to set the ONT alarm level.
                 The index of this table is hwXponOntAlarmPolicyCfgNameIndex and hwXponOntAlarmPolicyAlarmId.
                "
            ::= { hwXponDeviceCommonProfileObjects 4 }
                
        hwXponOntAlarmPolicyAlarmEntry OBJECT-TYPE
            SYNTAX     HwXponOntAlarmPolicyAlarmEntry
            MAX-ACCESS not-accessible
            STATUS     current
            DESCRIPTION
                "This table is used to set the ONT alarm level.
                 The index of this entry is hwXponOntAlarmPolicyCfgNameIndex and hwXponOntAlarmPolicyAlarmId.
                "
            INDEX    { hwXponOntAlarmPolicyCfgNameIndex, hwXponOntAlarmPolicyAlarmId }
            ::= { hwXponOntAlarmPolicyAlarmTable 1 }

        HwXponOntAlarmPolicyAlarmEntry ::=
            SEQUENCE {
                hwXponOntAlarmPolicyCfgNameIndex           OCTET STRING,
                hwXponOntAlarmPolicyAlarmId                Integer32,
                hwXponOntAlarmPolicyAlarmLevel             INTEGER
            }
            
        hwXponOntAlarmPolicyCfgNameIndex  OBJECT-TYPE
            SYNTAX OCTET STRING (SIZE (1..32))
            MAX-ACCESS   not-accessible
            STATUS       current
            DESCRIPTION
                "This object indicates the ONT alarm policy profile name index."
            ::= { hwXponOntAlarmPolicyAlarmEntry 1 }

        hwXponOntAlarmPolicyAlarmId OBJECT-TYPE
            SYNTAX   Integer32
            MAX-ACCESS  not-accessible
            STATUS      current
            DESCRIPTION
                "This object indicates the ONT alarm ID."
            ::= { hwXponOntAlarmPolicyAlarmEntry 2 }
            
        hwXponOntAlarmPolicyAlarmLevel OBJECT-TYPE
            SYNTAX   INTEGER {
                critical(1),
                major(2),
                minor(3),
                warning(4),
                unconcern(-1)
            }
            MAX-ACCESS  read-write
            STATUS      current
            DESCRIPTION
                "This object indicates the ONT alarm level.
                 Options:
                 1. critical(1)             - The ONT alarm level is critical.
                 2. major(2)                - The ONT alarm level is major.
                 3. minor(3)                - The ONT alarm level is minor.
                 4. warning(4)              - The ONT alarm level is warning.
                 5. unconcern(-1)           - The ONT alarm severity is unconcerned in the ONT alarm policy profile.
                 The default value is unconcern(-1).
                "
            ::= { hwXponOntAlarmPolicyAlarmEntry 3 }
-- hwXponOntAlarmPolicyAlarmTable  end

  --Table hwXponOntFtpServerProfileTable 
        hwXponOntFtpServerProfileTable OBJECT-TYPE
            SYNTAX     SEQUENCE OF HwXponOntFtpServerProfileEntry
            MAX-ACCESS not-accessible
            STATUS     current
            DESCRIPTION
                "This table is used to create, delete or modify the FTP server profile.
                 The index of this table is hwXponOntFtpServerProfileNameIndex.          
                "
            ::= { hwXponDeviceCommonProfileObjects 5 }
            
        hwXponOntFtpServerProfileEntry OBJECT-TYPE
            SYNTAX     HwXponOntFtpServerProfileEntry
            MAX-ACCESS not-accessible
            STATUS     current
            DESCRIPTION
                "This table is used to create, delete or modify the FTP server profile.
                 The index of this entry is hwXponOntFtpServerProfileNameIndex.          
                "
            INDEX    { IMPLIED hwXponOntFtpServerProfileNameIndex }
            ::= { hwXponOntFtpServerProfileTable 1 }
            
        HwXponOntFtpServerProfileEntry ::=
            SEQUENCE {
                hwXponOntFtpServerProfileNameIndex        OCTET STRING,
                hwXponOntFtpServerProfileAddress          OCTET STRING,
                hwXponOntFtpServerProfilePort             Integer32,
                hwXponOntFtpServerProfileUserName         OCTET STRING,
                hwXponOntFtpServerProfilePassword         OCTET STRING,
                hwXponOntFtpServerProfileRowStatus        RowStatus
            }
            
        hwXponOntFtpServerProfileNameIndex OBJECT-TYPE
            SYNTAX OCTET STRING (SIZE (1..15))
            MAX-ACCESS not-accessible
            STATUS current
            DESCRIPTION
                "This object indicates the name of FTP server profile."
            ::= { hwXponOntFtpServerProfileEntry 1 }
        
        hwXponOntFtpServerProfileAddress OBJECT-TYPE
            SYNTAX OCTET STRING (SIZE (1..63))
            MAX-ACCESS read-write
            STATUS current
            DESCRIPTION
                "This object indicates the address of FTP server profile.
                the format of string should be like ftp://127.0.0.1 or ftps://127.0.0.1
                "
            ::= { hwXponOntFtpServerProfileEntry 2 }
            
        hwXponOntFtpServerProfilePort OBJECT-TYPE
           SYNTAX      Integer32 (0..65535)
           MAX-ACCESS  read-write
           STATUS      current
           DESCRIPTION
                   "This object indicates the port of FTP server profile.
                   The default value is 21."
           ::= { hwXponOntFtpServerProfileEntry 3 }
           
        hwXponOntFtpServerProfileUserName OBJECT-TYPE
            SYNTAX OCTET STRING (SIZE (0..15))
            MAX-ACCESS read-write
            STATUS current
            DESCRIPTION
                "This object indicates the user name of FTP server."
            ::= { hwXponOntFtpServerProfileEntry 4 }
            
        hwXponOntFtpServerProfilePassword OBJECT-TYPE
            SYNTAX OCTET STRING (SIZE (0..15))
            MAX-ACCESS read-write
            STATUS current
            DESCRIPTION
                "This object indicates the password of FTP server."
            ::= { hwXponOntFtpServerProfileEntry 5 }
        
        hwXponOntFtpServerProfileRowStatus OBJECT-TYPE
           SYNTAX RowStatus
           MAX-ACCESS read-create
           STATUS current
           DESCRIPTION
               "The hwXponOntFtpServerProfileRowStatus is used to create a new row
                 or to modify or to delete an existing row in this table.
                 Options:
                 1. createAndGo(4) -create a new instance of a conceptual row 
                 2. destroy(6)     -delete the instances associated with an existing conceptual row
                "
           ::= { hwXponOntFtpServerProfileEntry 6 }
            
  --hwXponOntFtpServerProfileTable end

  --Table hwXponDeviceOntPowerReductionProfileTable 
        hwXponDeviceOntPowerReductionProfileTable OBJECT-TYPE
            SYNTAX     SEQUENCE OF HwXponDeviceOntPowerReductionProfileEntry
            MAX-ACCESS not-accessible
            STATUS     current
            DESCRIPTION
                "This table is used to create, delete, or modify the power reduction profile.
                 It can contain 32 power reduction profiles in total.Power reduction profile is a kind of profile that can be bound
                 to one or more ONT(s) at the same time and it specify how and when the ONT(s) perform power reduction function. 
                 The index of this table is hwXponDeviceOntPowerReductionProfileNameIndex.          
                "
            ::= { hwXponDeviceCommonProfileObjects 6 }
            
        hwXponDeviceOntPowerReductionProfileEntry OBJECT-TYPE
            SYNTAX     HwXponDeviceOntPowerReductionProfileEntry
            MAX-ACCESS not-accessible
            STATUS     current
            DESCRIPTION
                "This table is used to create, delete, or modify the power reduction profile.
                 It can contain 32 power reduction profiles in total.Power reduction profile is a kind of profile that can be bound
                 to one or more ONT(s) at the same time and it specify how and when the ONT(s) perform power reduction function. 
                 The index of this entry is hwXponDeviceOntPowerReductionProfileNameIndex.          
                "
            INDEX    { IMPLIED hwXponDeviceOntPowerReductionProfileNameIndex }
            ::= { hwXponDeviceOntPowerReductionProfileTable 1 }
            
        HwXponDeviceOntPowerReductionProfileEntry ::=
            SEQUENCE {
                hwXponDeviceOntPowerReductionProfileNameIndex         OCTET STRING,
                hwXponDeviceOntPowerReductionProfileBindNum           Integer32,
                hwXponDeviceOntPowerReductionMode                     INTEGER,
                hwXponDeviceOntPowerReductionSleepInterval            Integer32, 
                hwXponDeviceOntPowerReductionAwakeInterval            Integer32, 
                hwXponDeviceOntPowerReductionEnterInterval            Integer32, 
                hwXponDeviceOntPowerReductionUpstreamEnterRate        Integer32,  
                hwXponDeviceOntPowerReductionDownstreamEnterRate      Integer32,
                hwXponDeviceOntPowerReductionExitInterval             Integer32, 
                hwXponDeviceOntPowerReductionUpstreamExitRate         Integer32,
                hwXponDeviceOntPowerReductionDownstreamExitRate       Integer32,
                hwXponDeviceOntPowerReductionUpstreamExitBurstRate    Integer32, 
                hwXponDeviceOntPowerReductionDownstreamExitBurstRate  Integer32,  
                hwXponDeviceOntPowerReductionTimeRange                INTEGER, 
                hwXponDeviceOntPowerReductionEnableDayofWeek          Integer32,
                hwXponDeviceOntPowerReductionStartTime                OCTET STRING,
                hwXponDeviceOntPowerReductionEndTime                  OCTET STRING,
                hwXponDeviceOntPowerReductionProfileRowStatus         RowStatus
            }
                       
        hwXponDeviceOntPowerReductionProfileNameIndex OBJECT-TYPE
            SYNTAX OCTET STRING (SIZE (1..32))
            MAX-ACCESS not-accessible
            STATUS current
            DESCRIPTION
                "This object indicates the name of the power reduction profile."
            ::= { hwXponDeviceOntPowerReductionProfileEntry 1 }
         
        hwXponDeviceOntPowerReductionProfileBindNum OBJECT-TYPE
            SYNTAX  Integer32
            MAX-ACCESS read-only
            STATUS current
            DESCRIPTION
                "This object indicates the number of ONTs bound with power reduction profile."
            ::= { hwXponDeviceOntPowerReductionProfileEntry 2 } 
            
        hwXponDeviceOntPowerReductionMode OBJECT-TYPE
            SYNTAX  INTEGER{
                 disable (1),
                 doze    (2),
                 cyclicSleep (3),
                 watchfulSleep (4),
                 auto (5)
            }
            MAX-ACCESS read-write
            STATUS current
            DESCRIPTION
                "This object indicates the power reduction mode of this profile. 
                Options:
                 1.disable(1)        -disable mode:disable power reduction function for this profile,then ONTs bound to this profile will run normally without power-reduction..
                 2.doze(2)           -doze mode:when in a LowPower state (the Asleep state) in this mode the ONT receiver remains active, ONT can receive downstream traffic,but it will deactivate its transmitter periodicly ,at this time it can't send its upstream traffic.
                 3.cyclicSleep(3)    -cyclic sleep mode:when in a LowPower state (the Asleep state) in this mode, the ONT receiver is inactive;the ONT cannot receive downstream traffic. its transmitter is also inactive,so it can't send its upstream traffic.
                 4.watchfulSleep(4)  -watchful sleep mode:when in a LowPower state (the Watch state) in this mode, the ONT periodically checks the downstream traffic for wakeup indications from the OLT.
                 5.auto(5)           -auto negotiation mode:Indicates that ONT can select one of the power reduction modes above that it can support to perform power reduction.
                 The default value is disable(1).
                 "
            ::= { hwXponDeviceOntPowerReductionProfileEntry 3 } 
            
        hwXponDeviceOntPowerReductionSleepInterval OBJECT-TYPE
            SYNTAX  Integer32
            MAX-ACCESS read-write
            STATUS current
            DESCRIPTION
                "Indicateas the time that ONT stays in a LowPower status in power reduction state periodicly.
                 The valid value range is 1--500ms
                 The default value is 200ms "
            ::= { hwXponDeviceOntPowerReductionProfileEntry 4 } 
            
        hwXponDeviceOntPowerReductionAwakeInterval OBJECT-TYPE
            SYNTAX  Integer32
            MAX-ACCESS read-write
            STATUS current
            DESCRIPTION
                "Indicateas the time that ONT stays in awake status in power reduction state periodicly
                 The valid value range is 1--100ms
                 The default value is 20ms "
            ::= { hwXponDeviceOntPowerReductionProfileEntry 5 }
            
        hwXponDeviceOntPowerReductionEnterInterval OBJECT-TYPE
            SYNTAX  Integer32
            MAX-ACCESS read-write
            STATUS current
            DESCRIPTION
                "Indicates the time interval that ONT needs to enter power reduction state,during this time,the ONT will check if it can enter power reduction state.
                 The valid value range is 1--900s
                 The default value is 300s "
            ::= { hwXponDeviceOntPowerReductionProfileEntry 6 }
                                                               
        hwXponDeviceOntPowerReductionUpstreamEnterRate OBJECT-TYPE
            SYNTAX  Integer32
            MAX-ACCESS read-write
            STATUS current
            DESCRIPTION
                "Indicates the upstream rate threshold that ONT needs to enter power reduction state,during enter-interval time,if its upstream rate is continuously lower then this
                 threshold,then the ONT will enter power reduction state if it is bound to power reduction profile and meets other conditions. 
                 The valid value range is 1--100pps
                 The default value is 3pps"
            ::= { hwXponDeviceOntPowerReductionProfileEntry 7 }    
            
        hwXponDeviceOntPowerReductionDownstreamEnterRate OBJECT-TYPE
            SYNTAX  Integer32
            MAX-ACCESS read-write
            STATUS current
            DESCRIPTION
                "Indicates the downstream rate threshold that ONT needs to enter power reduction state,during enter-interval time,if its downstream rate is continuously lower then this
                 threshold,then the ONT will enter power reduction state if it is bound to power reduction profile and meets other conditions.
                The valid value range is 1--100pps
                The default value is 3pps"
            ::= { hwXponDeviceOntPowerReductionProfileEntry 8 }                                                
                                                               
        hwXponDeviceOntPowerReductionExitInterval OBJECT-TYPE
            SYNTAX  Integer32
            MAX-ACCESS read-write
            STATUS current
            DESCRIPTION
                "Indicates the time interval that ONT needs to exit power reduction state,during this time,the ONT will check if it need to exit power reduction state.
                 The valid value range is 1--60s
                 The default value is 3s"
            ::= { hwXponDeviceOntPowerReductionProfileEntry 9 }                                                       
                                                                 
        hwXponDeviceOntPowerReductionUpstreamExitRate OBJECT-TYPE
            SYNTAX  Integer32
            MAX-ACCESS read-write
            STATUS current
            DESCRIPTION
                "Indicates the upstream rate threshold that ONT needs to exit power reduction state,during exit-interval time,if its upstream rate is continuously higher then this
                 threshold,then the ONT will exit power reduction state if it is bound to power reduction profile and meets other conditions. 
                 The valid value range is 1--100pps
                 The default value is 3pps"
            ::= { hwXponDeviceOntPowerReductionProfileEntry 10 } 
            
        hwXponDeviceOntPowerReductionDownstreamExitRate OBJECT-TYPE
            SYNTAX  Integer32
            MAX-ACCESS read-write
            STATUS current
            DESCRIPTION
                "Indicates the downstream rate threshold that ONT needs to exit power reduction state. during exit-interval time,if its downstream rate is continuously higher then this
                 threshold,then the ONT will exit power reduction state if it is bound to power reduction profile and meets other conditions. 
                 The valid value range is 1--100pps
                 The default value is 3pps"
            ::= { hwXponDeviceOntPowerReductionProfileEntry 11 }  
            
         hwXponDeviceOntPowerReductionUpstreamExitBurstRate OBJECT-TYPE
            SYNTAX  Integer32
            MAX-ACCESS read-write
            STATUS current
            DESCRIPTION
                "Indicates the upstream burst rate threshold that ONT needs to exit power reduction state. during exit-interval time,if its upstream burst rate is  higher then this
                 threshold,then the ONT will exit power reduction state if it is bound to power reduction profile and meets other conditions. 
                 The valid value range is 2--100pps
                 The default value is 10pps"
            ::= { hwXponDeviceOntPowerReductionProfileEntry 12 }
            
         hwXponDeviceOntPowerReductionDownstreamExitBurstRate OBJECT-TYPE
            SYNTAX  Integer32
            MAX-ACCESS read-write
            STATUS current
            DESCRIPTION
                "Indicates the downstream burst rate threshold that ONT needs to exit power reduction state. during exit-interval time,if its downstream burst rate is  higher then this
                 threshold,then the ONT will exit power reduction state if it is bound to power reduction profile and meets other conditions.
                 The valid value range is 2--100pps
                 The default value is 10pps"
            ::= { hwXponDeviceOntPowerReductionProfileEntry 13 }
            
         hwXponDeviceOntPowerReductionTimeRange OBJECT-TYPE
            SYNTAX  INTEGER{
                 all (1),
                 specific (2)
             }
            MAX-ACCESS read-write
            STATUS current
            DESCRIPTION
                "Indicates the time range that the ONT can be in power reduction state,in the specific time range,if the ONT meets the conditions need to enter power reduction state,
                 it will perform power reduction function.other leaves following this leaf are used to specify this time range. 
                 Options:
                 1.all(1)        -the whole time range from 00 :00 to 24:00 every day.
                 2.specific(2)   -specific time range. 
                 The default value is all (1).
                 "
            ::= { hwXponDeviceOntPowerReductionProfileEntry 14 }    
            
          hwXponDeviceOntPowerReductionEnableDayofWeek OBJECT-TYPE
            SYNTAX  Integer32
            MAX-ACCESS read-write
            STATUS current
            DESCRIPTION
                "The values are as follows: 
                 Sunday: 0x01
                 Monday: 0x02
                 Tuesday: 0x04
                 Wednesday: 0x08
                 Thursday: 0x10
                 Friday: 0x20
                 Saturday: 0x40 
                 If the value is set to Sunday and Monday,  perform the | operation to the values of Sunday and Monday, 
                 and the value is 0x03, and so on.
                 "
            ::= { hwXponDeviceOntPowerReductionProfileEntry 15}
           
          hwXponDeviceOntPowerReductionStartTime OBJECT-TYPE
            SYNTAX OCTET STRING (SIZE (2))
            MAX-ACCESS read-write
            STATUS current
            DESCRIPTION
                "Indicates the start time of a periodic time range,example:0x08 0x1E means 08:30"
            ::= { hwXponDeviceOntPowerReductionProfileEntry 16}
            
          hwXponDeviceOntPowerReductionEndTime OBJECT-TYPE
            SYNTAX OCTET STRING (SIZE (2))
            MAX-ACCESS read-write
            STATUS current
            DESCRIPTION
                "Indicates the end time of a periodic time range,example:0x08 0x1E means 08:30"
            ::= { hwXponDeviceOntPowerReductionProfileEntry 17}
            
          hwXponDeviceOntPowerReductionProfileRowStatus OBJECT-TYPE
            SYNTAX RowStatus
            MAX-ACCESS read-create
            STATUS current
            DESCRIPTION
                "The hwXponDeviceOntPowerReductionProfileRowStatus is used to create a new row
                 or to modify or to delete an existing row in this table.
                 Options:
                 1. createAndGo(4) -create a new instance of a conceptual row 
                 2. destroy(6)     -delete the instances associated with an existing conceptual row 
                "
            ::= { hwXponDeviceOntPowerReductionProfileEntry 18}
                                                            
  --hwXponDeviceOntPowerReductionProfileTable end         
  
  --Table hwXponOntEthPortPoeConfigTable 
        hwXponOntEthPortPoeConfigTable OBJECT-TYPE
            SYNTAX     SEQUENCE OF HwXponOntEthPortPoeConfigEntry
            MAX-ACCESS not-accessible
            STATUS     current
            DESCRIPTION
                "This table is used to set the PoE configuration of the ONT Ethernet port.
                 The indexes of this table are ifIndex, hwXponOntIndex and hwXponOntEthPortId.
                "
            ::= { hwXponDeviceCommonProfileObjects 7 }
            
        hwXponOntEthPortPoeConfigEntry OBJECT-TYPE
            SYNTAX     HwXponOntEthPortPoeConfigEntry
            MAX-ACCESS not-accessible
            STATUS     current
            DESCRIPTION
                "This table is used to set the PoE configuration of the ONT Ethernet port.
                 The indexes of this entry are ifIndex, hwXponOntIndex and hwXponOntEthPortId.          
                "
            INDEX    { ifIndex, hwXponOntIndex, hwXponOntEthPortId }
            ::= { hwXponOntEthPortPoeConfigTable 1 }
            
        HwXponOntEthPortPoeConfigEntry ::=
            SEQUENCE {
                hwXponOntEthPortId                  Integer32,
                hwXponOntEthPortPoeSwitch           INTEGER,
                hwXponOntEthPortPoeMode             INTEGER,
                hwXponOntEthPortPoePriority         INTEGER,
                hwXponOntEthPortPoePowerClass       INTEGER,
		hwXponOntEthPortPoeMaxPowerValue    Integer32,
                hwXponOntEthPortPoeForcePowerSwitch INTEGER
            }
              
        hwXponOntEthPortId OBJECT-TYPE
            SYNTAX      Integer32
            MAX-ACCESS  not-accessible
            STATUS      current
            DESCRIPTION
                "ONT ETH port ID."
            ::= { hwXponOntEthPortPoeConfigEntry 1 }
                                   
        hwXponOntEthPortPoeSwitch OBJECT-TYPE
            SYNTAX  INTEGER
              {                  
                  enable(1),
                  disable(2),
                  unconcern(3)
              } 
           MAX-ACCESS  read-write
           STATUS      current
           DESCRIPTION
                   "This object indicates the power supply switch of the ONT Ethernet port.
                    Options:
                    1. enable(1)    - Indicates that the power supply switch of the ONT Ethernet port is enabled.
                    2. disable(2)   - Indicates that the power supply switch of the ONT Ethernet port is disabled.
                    3. unconcern(3) - Indicates that the power supply switch of the ONT Ethernet port is unconcerned.
                    The default value is unconcern(3).                                        
                   "
           ::= { hwXponOntEthPortPoeConfigEntry 2 }
           
        hwXponOntEthPortPoeMode OBJECT-TYPE
            SYNTAX  INTEGER
              {                  
                  signal(1),
                  spare(2),
		  unconcern(255)
              }
            MAX-ACCESS read-write
            STATUS current
            DESCRIPTION
                "This object indicates the power supply mode of the ONT Ethernet port.
                 Options:
                 1. signal(1)    - Indicates that the power supply mode of the ONT Ethernet port is the signal line pair.
                 2. spare(2)     - Indicates that the power supply mode of the ONT Ethernet port is the spare line pair.
		 3. unconcern(255) - Indicates that the power supply mode of the ONT Ethernet port is unconcerned.
                 The default value is signal(1).                                                         
                "
            ::= { hwXponOntEthPortPoeConfigEntry 3 }
            
        hwXponOntEthPortPoePriority OBJECT-TYPE
            SYNTAX  INTEGER
              {                  
                  critical(1),
                  high(2),
                  low(3)
              }
            MAX-ACCESS read-write
            STATUS current
            DESCRIPTION
                "This object indicates the power supply priority of the ONT Ethernet port.
                 Options:
                 1. critical(1)  - Indicates that the power supply of the ONT Ethernet port is of the highest priority.
                 2. high(2)      - Indicates that the power supply priority of the ONT Ethernet port is high.
                 3. low(3)       - Indicates that the power supply priority of the ONT Ethernet port is low.
                 The default value is high(2).
                "                 
            ::= { hwXponOntEthPortPoeConfigEntry 4 }
        
        hwXponOntEthPortPoePowerClass OBJECT-TYPE
            SYNTAX  INTEGER
              {                  
                  default(1),
                  class0(2),
                  class1(3),
                  class2(4),
                  class3(5),
                  class4(6),
		  invalid(-1)
              }
           MAX-ACCESS read-write
           STATUS current
           DESCRIPTION
               "This object indicates the power supply classification of the ONT Ethernet port.
                Options:
                1. default(1) - Indicates the default power supply classification of the ONT Ethernet port according to the classification of the PD.
                2. class0(2)  - Indicates the power supply classification of the ONT Ethernet port is class0.
                3. class1(3)  - Indicates the power supply classification of the ONT Ethernet port is class1.
                4. class2(4)  - Indicates the power supply classification of the ONT Ethernet port is class2.
                5. class3(5)  - Indicates the power supply classification of the ONT Ethernet port is class3.
                6. class4(6)  - Indicates the power supply classification of the ONT Ethernet port is class4.
		7. invalid(-1)  - Indicates the power supply classification of the ONT Ethernet port is invalid.				
                The default value is default(1).                                        
               "
           ::= { hwXponOntEthPortPoeConfigEntry 5 }
		   
	hwXponOntEthPortPoeMaxPowerValue OBJECT-TYPE
            SYNTAX Integer32 (-1 | 100..65535)
            MAX-ACCESS read-write
            STATUS current
            DESCRIPTION
                "This object indicates the max power of the ONT Ethernet port, the unit is 10mW.
                 The invalid value is -1.                                                        
                "
            ::= { hwXponOntEthPortPoeConfigEntry 6 }
			
	hwXponOntEthPortPoeForcePowerSwitch OBJECT-TYPE
            SYNTAX  INTEGER
              {                  
                  disable(1),
                  enable(2),
				  invalid(-1)
              }
            MAX-ACCESS read-write
            STATUS current
            DESCRIPTION
                "This object indicates the force power switch of the ONT Ethernet port.
                 Options:
                 1. disable(1)    - Indicates that the force power switch of the ONT Ethernet port is disabled.
                 2. enable(2)     - Indicates that the force power switch of the ONT Ethernet port is enabled.
				 3. invalid(-1)   - Indicates that the force power switch of the ONT Ethernet port is invalid.				 
                 The default value is disable(1).                                                         
                "
            ::= { hwXponOntEthPortPoeConfigEntry 7 }
                       
  --hwXponOntEthPortPoeConfigTable end
       
  --Table hwXponOntEthPortPoeStatusTable 
        hwXponOntEthPortPoeStatusTable OBJECT-TYPE
            SYNTAX     SEQUENCE OF HwXponOntEthPortPoeStatusEntry
            MAX-ACCESS not-accessible
            STATUS     current
            DESCRIPTION
                "This table is used to query the PoE stauts of the ONT Ethernet port.
                 The indexes of this table are ifIndex, hwXponOntIndex and hwXponOntEthPortId.
                "
            ::= { hwXponDeviceCommonProfileObjects 8 }
            
        hwXponOntEthPortPoeStatusEntry OBJECT-TYPE
            SYNTAX     HwXponOntEthPortPoeStatusEntry
            MAX-ACCESS not-accessible
            STATUS     current
            DESCRIPTION
                "This table is used to query the PoE stauts of the ONT Ethernet port.
                 The indexes of this entry are ifIndex, hwXponOntIndex and hwXponOntEthPortId.          
                "
            INDEX    { ifIndex, hwXponOntIndex, hwXponOntEthPortId }
            ::= { hwXponOntEthPortPoeStatusTable 1 }
            
        HwXponOntEthPortPoeStatusEntry ::=
            SEQUENCE {
                hwXponOntEthPortPoePowerSupplyCapability          INTEGER,
                hwXponOntEthPortPoePowerDetectionStatus           INTEGER,
                hwXponOntEthPortPoePowerClassificationStatus      INTEGER,
                hwXponOntEthPortPoeInvalidSignatureCounter        Counter64,
                hwXponOntEthPortPoePowerDeniedCounter             Counter64,
                hwXponOntEthPortPoeOverloadCounter                Counter64,
                hwXponOntEthPortPoeShortCounter                   Counter64,
                hwXponOntEthPortPoeMpsAbsentCounter               Counter64,
		hwXponOntEthPortPoeStatusOutPutPowerCurrentValue  Integer32,
		hwXponOntEthPortPoeStatusOutPutPowerAverageValue  Integer32,
                hwXponOntEthPortPoeStatusOutPutPowerPeakValue     Integer32
            }
                       
        hwXponOntEthPortPoePowerSupplyCapability OBJECT-TYPE
            SYNTAX  INTEGER
              { 
                  capable(1),
                  incapable(2),
                  invalid(-1)
              }
           MAX-ACCESS  read-only
           STATUS      current
           DESCRIPTION
                   "This object indicates the power supply capability of the ONT Ethernet port.
                    Options:
                    1. capable(1)    - Indicates that the ONT Ethernet port can supply power to the PD.
                    2. incapable(2)  - Indicates that the ONT Ethernet port can not supply power to the PD. 
                    3. invalid(-1)   - Indicates that the query fails or no information is detected.
                   "
           ::= { hwXponOntEthPortPoeStatusEntry 1 }
           
        hwXponOntEthPortPoePowerDetectionStatus OBJECT-TYPE
            SYNTAX  INTEGER
              {                  
                  noneed(1),
                  searching(2),
                  delivering(3),
                  forced(4),
                  fault(5),
                  specificFault(6),
                  invalid(-1)
              }
            MAX-ACCESS read-only
            STATUS current
            DESCRIPTION
                "This object indicates the power detection status of the ONT Ethernet port.
                 Options:
                 1. noneed(1)         - Indicates that the ONT Ethernet port does not need to supply power to the PD.
                 2. searching(2)      - Indicates that the ONT Ethernet port is in the power supply searching state.
                 3. delivering(3)     - Indicates that the ONT Ethernet port is in the power supply delivering state.
                 4. forced(4)         - Indicates that the ONT Ethernet port is in the forced power supply state.  
                 5. fault(5)          - Indicates that the ONT Ethernet port is in the forced power supply failure state.
                 6. specificFault(6)  - Indicates that the ONT Ethernet port is in the power supply failure state because the PD does not meet the current power supply conditions. 
                 7. invalid(-1)       - Indicates that the query fails or no information is detected.
                "
            ::= { hwXponOntEthPortPoeStatusEntry 2 }
            
        hwXponOntEthPortPoePowerClassificationStatus OBJECT-TYPE
            SYNTAX  INTEGER
              {                  
                  undefined(1),
                  class0(2),
                  class1(3),
                  class2(4),
                  class3(5),
                  class4(6),
                  invalid(-1)
              }
            MAX-ACCESS read-only
            STATUS current
            DESCRIPTION
                "This object indicates the power supply classification of the ONT Ethernet port.
                 Options:
                 1. undefined(1)  - Indicates that the actual power classification of the PD is undefined or the PD does not support the feature.
                 2. class0(2)   - Indicates that the actual power classification of the PD is class 0. 
                 3. class1(3)   - Indicates that the actual power classification of the PD is class 1.
                 4. class2(4)   - Indicates that the actual power classification of the PD is class 2.  
                 5. class3(5)   - Indicates that the actual power classification of the PD is class 3.
                 6. class4(6)   - Indicates that the actual power classification of the PD is class 4.
                 7. invalid(-1) - Indicates that the query fails or no information is detected.                 
                " 
            ::= { hwXponOntEthPortPoeStatusEntry 3 }
        
        hwXponOntEthPortPoeInvalidSignatureCounter OBJECT-TYPE
           SYNTAX Counter64
           MAX-ACCESS read-only
           STATUS current
           DESCRIPTION
               "This object indicates the invalid signature statistics of the ONT Ethernet port.
               "
           ::= { hwXponOntEthPortPoeStatusEntry 4 }
           
        hwXponOntEthPortPoePowerDeniedCounter OBJECT-TYPE
           SYNTAX Counter64
           MAX-ACCESS read-only
           STATUS current
           DESCRIPTION
               "This object indicates the statistics of the ONT Ethernet port which refused to supply power to the PD.    
               "
           ::= { hwXponOntEthPortPoeStatusEntry 5 }  
           
        hwXponOntEthPortPoeOverloadCounter OBJECT-TYPE
           SYNTAX Counter64
           MAX-ACCESS read-only
           STATUS current
           DESCRIPTION
               "This object indicates the power overload statistics of ONT Ethernet port.
               "
           ::= { hwXponOntEthPortPoeStatusEntry 6 }    
           
        hwXponOntEthPortPoeShortCounter OBJECT-TYPE
           SYNTAX Counter64
           MAX-ACCESS read-only
           STATUS current
           DESCRIPTION
               "This object indicates the current overload statistics of the ONT Ethernet port.
               "
           ::= { hwXponOntEthPortPoeStatusEntry 7 }    
           
        hwXponOntEthPortPoeMpsAbsentCounter OBJECT-TYPE
           SYNTAX Counter64
           MAX-ACCESS read-only
           STATUS current
           DESCRIPTION
               "This object indicates the disconnected statistics of the ONT Ethernet port.
               "
           ::= { hwXponOntEthPortPoeStatusEntry 8 } 
		   
	hwXponOntEthPortPoeStatusOutPutPowerCurrentValue OBJECT-TYPE
            SYNTAX Integer32
            MAX-ACCESS read-only
            STATUS current
            DESCRIPTION
                "This object indicates the current power of the ONT Ethernet port.
                 The unit is mW.                                                         
                "
            ::= { hwXponOntEthPortPoeStatusEntry 9 }
			
	hwXponOntEthPortPoeStatusOutPutPowerAverageValue OBJECT-TYPE
            SYNTAX Integer32
            MAX-ACCESS read-only
            STATUS current
            DESCRIPTION
                "This object indicates the average power of the ONT Ethernet port.
                 The unit is mW.                                                         
                "
            ::= { hwXponOntEthPortPoeStatusEntry 10 }
			
	hwXponOntEthPortPoeStatusOutPutPowerPeakValue OBJECT-TYPE
            SYNTAX Integer32
            MAX-ACCESS read-only
            STATUS current
            DESCRIPTION
                "This object indicates the peek power of the ONT Ethernet port.
                 The unit is mW.                                                         
                "
            ::= { hwXponOntEthPortPoeStatusEntry 11 }
            
  --hwXponOntEthPortPoeStatusTable end
  
--  Table hwXponTrafficAlarmProfileTable
        hwXponTrafficAlarmProfileTable OBJECT-TYPE
            SYNTAX SEQUENCE OF HwXponTrafficAlarmProfileEntry
            MAX-ACCESS not-accessible
            STATUS current
            DESCRIPTION
                "This is the traffic alarm profile infomation table.
                 The index of this table is hwXponTrafficAlarmProfileNameIndex.
                "
            ::= { hwXponDeviceCommonProfileObjects 9 }
            
        hwXponTrafficAlarmProfileEntry OBJECT-TYPE
            SYNTAX HwXponTrafficAlarmProfileEntry
            MAX-ACCESS not-accessible
            STATUS current
            DESCRIPTION
                "This is the traffic alarm profile infomation table.
                 The index of this entry is hwXponTrafficAlarmProfileNameIndex.
                "
            INDEX { IMPLIED hwXponTrafficAlarmProfileNameIndex}
            ::= { hwXponTrafficAlarmProfileTable 1 }
            
        HwXponTrafficAlarmProfileEntry ::=
            SEQUENCE {
                hwXponTrafficAlarmProfileNameIndex                    OCTET STRING,
                hwXponTrafficAlarmProfileBindNum                      Integer32,
                hwXponTrafficAlarmProfileDetectInterval               Integer32,
                hwXponTrafficAlarmProfileDetectTimes                  Integer32,
                hwXponTrafficAlarmProfileAlarmDetectTimes             Integer32,
                hwXponTrafficAlarmProfileWarningDetectTimes           Integer32,
                hwXponTrafficAlarmProfileUpRatioThreshold             Integer32,
                hwXponTrafficAlarmProfileDownRatioThreshold           Integer32,
                hwXponTrafficAlarmProfileRowStatus                    RowStatus
            }
            
        hwXponTrafficAlarmProfileNameIndex OBJECT-TYPE
            SYNTAX OCTET STRING (SIZE(1..32))
            MAX-ACCESS not-accessible
            STATUS current
            DESCRIPTION
                "This object indicates the traffic alarm profile name index."
            ::= { hwXponTrafficAlarmProfileEntry 1 }
            
        hwXponTrafficAlarmProfileBindNum OBJECT-TYPE
            SYNTAX Integer32
            MAX-ACCESS read-only
            STATUS current
            DESCRIPTION
                "This object indicates the traffic alarm profile binding times."
            ::= { hwXponTrafficAlarmProfileEntry 2 }
            
        hwXponTrafficAlarmProfileDetectInterval OBJECT-TYPE
            SYNTAX Integer32 (1..300)
            MAX-ACCESS read-write
            STATUS current
            DESCRIPTION
                "This object indicates the traffic congestion detection interval.
                 It is defined as an 32-bit integer whose unit is 's'(second)"
            ::= { hwXponTrafficAlarmProfileEntry 3 }

        hwXponTrafficAlarmProfileDetectTimes OBJECT-TYPE
            SYNTAX Integer32 (1..900)
            MAX-ACCESS read-write
            STATUS current
            DESCRIPTION
                "This object indicates the traffic congestion detection times."
            ::= { hwXponTrafficAlarmProfileEntry 4 }
            
        hwXponTrafficAlarmProfileAlarmDetectTimes OBJECT-TYPE
            SYNTAX Integer32 (0..900)
            MAX-ACCESS read-write
            STATUS current
            DESCRIPTION
                "This object indicates the alarm threshold of the congestion detection."
            ::= { hwXponTrafficAlarmProfileEntry 5 }
            
        hwXponTrafficAlarmProfileWarningDetectTimes OBJECT-TYPE
            SYNTAX Integer32 (0..900)
            MAX-ACCESS read-write
            STATUS current
            DESCRIPTION
                "This object indicates the warning threshold of the congestion detection."
            ::= { hwXponTrafficAlarmProfileEntry 6 }
            
        hwXponTrafficAlarmProfileUpRatioThreshold OBJECT-TYPE
            SYNTAX Integer32 (1..100)
            MAX-ACCESS read-write
            STATUS current
            DESCRIPTION
                "This object indicates the ratio of upstream congestion threshold."
            ::= { hwXponTrafficAlarmProfileEntry 7 }
            
        hwXponTrafficAlarmProfileDownRatioThreshold OBJECT-TYPE
            SYNTAX Integer32 (1..100)
            MAX-ACCESS read-write
            STATUS current
            DESCRIPTION
                "This object indicates the ratio of downstream congestion threshold."
            ::= { hwXponTrafficAlarmProfileEntry 8 }
            
        hwXponTrafficAlarmProfileRowStatus OBJECT-TYPE
            SYNTAX RowStatus
            MAX-ACCESS read-create
            STATUS current
            DESCRIPTION
                "The hwXponTrafficAlarmProfileRowStatus is used to create a new row
                 or to modify or delete an existing row in this table.
                 Options:
                 1. createAndGo(4) -create a new instance of a conceptual row 
                 2. destroy(6)     -delete the instances associated with an existing conceptual row
                "
            ::= { hwXponTrafficAlarmProfileEntry 9 }
	    
  --hwXponTrafficAlarmProfileTable end
  
--  Table hwXponOntWanProfileTable
        hwXponOntWanProfileTable OBJECT-TYPE
            SYNTAX SEQUENCE OF HwXponOntWanProfileEntry
            MAX-ACCESS not-accessible
            STATUS current
            DESCRIPTION
                "This is the ONT wan profile infomation table.
                 The index of this table is hwXponOntWanProfileNameIndex.
                "
            ::= { hwXponDeviceCommonProfileObjects 10 }
            
        hwXponOntWanProfileEntry OBJECT-TYPE
            SYNTAX HwXponOntWanProfileEntry
            MAX-ACCESS not-accessible
            STATUS current
            DESCRIPTION
                "This is the ONT wan profile infomation table.
                 The index of this entry is hwXponOntWanProfileNameIndex.
                "
            INDEX { IMPLIED hwXponOntWanProfileNameIndex}
            ::= { hwXponOntWanProfileTable 1 }
            
        HwXponOntWanProfileEntry ::=
            SEQUENCE {
                hwXponOntWanProfileNameIndex                    OCTET STRING,
                hwXponOntWanProfileBindNum                      Integer32,
                hwXponOntWanProfileConnectionType               INTEGER,
                hwXponOntWanProfileNatSwitch                    INTEGER,       
                hwXponOntWanProfileRowStatus                    RowStatus
            }
            
        hwXponOntWanProfileNameIndex OBJECT-TYPE
            SYNTAX OCTET STRING (SIZE(1..32))
            MAX-ACCESS not-accessible
            STATUS current
            DESCRIPTION
                "This object indicates the ont wan profile name index."
            ::= { hwXponOntWanProfileEntry 1 }
            
        hwXponOntWanProfileBindNum OBJECT-TYPE
            SYNTAX Integer32
            MAX-ACCESS read-only
            STATUS current
            DESCRIPTION
                "This object indicates the number of ont bound with wan profile."
            ::= { hwXponOntWanProfileEntry 2 }
        
        hwXponOntWanProfileConnectionType OBJECT-TYPE
            SYNTAX  INTEGER
              {                  
                  route(1),
                  bridge(2)
              } 
           MAX-ACCESS  read-write
           STATUS      current
           DESCRIPTION
                   "This object indicates the connection type of  ONT wan.
                    Options:
                    1. route(1)    - Indicates that the connection type  of  ont wan  is route.
                    2. bridge(2)   - Indicates that the connection type  of  ont wan  is bridge.                   
                    The default value is route(1).                                        
                   "
           ::= { hwXponOntWanProfileEntry 3 }
           
        hwXponOntWanProfileNatSwitch OBJECT-TYPE
            SYNTAX  INTEGER
              {                      
                  enable(1),
                  disable(2)
              } 
           MAX-ACCESS  read-write
           STATUS      current
           DESCRIPTION
                   "This object indicates the NAT switch of  ont wan.
                    Options:
                    1. enable(1)    - Indicates that the NAT switch  of  ont wan  is enable.
                    2. disable(2)   - Indicates that the NAT switch  of  ont wan  is disable.                  
                    The default value is disable(2).                                        
                   "
           ::= { hwXponOntWanProfileEntry 4 }
           
         hwXponOntWanProfileRowStatus OBJECT-TYPE
            SYNTAX RowStatus       
            MAX-ACCESS read-create
            STATUS current
            DESCRIPTION
                "The hwXponOntWanProfileRowStatus is used to create a new row
                 or to modify or delete an existing row in this table.
                 Options:
                 1. createAndGo(4) -create a new instance of a conceptual row 
                 2. destroy(6)     -delete the instances associated with an existing conceptual row
                "
            ::= { hwXponOntWanProfileEntry 5 }
	    
  --hwXponOntWanProfileTable end  
  
--  Table hwXponOntPolicyRouteProfileTable
        hwXponOntPolicyRouteProfileTable OBJECT-TYPE
            SYNTAX SEQUENCE OF HwXponOntPolicyRouteProfileEntry
            MAX-ACCESS not-accessible
            STATUS current
            DESCRIPTION
                "This is the ont policy route profile infomation table.
                 The index of this table is hwXponOntPolicyRouteProfileNameIndex.
                "
            ::= { hwXponDeviceCommonProfileObjects 11 }
            
        hwXponOntPolicyRouteProfileEntry OBJECT-TYPE
            SYNTAX HwXponOntPolicyRouteProfileEntry
            MAX-ACCESS not-accessible
            STATUS current
            DESCRIPTION
                "This is the ont policy route profile infomation table.
                 The index of this entry is hwXponOntPolicyRouteProfileNameIndex.
                "
            INDEX { IMPLIED hwXponOntPolicyRouteProfileNameIndex}
            ::= { hwXponOntPolicyRouteProfileTable 1 }
            
        HwXponOntPolicyRouteProfileEntry ::=
            SEQUENCE {
                hwXponOntPolicyRouteProfileNameIndex                    OCTET STRING,
                hwXponOntPolicyRouteProfileBindNum                      Integer32,     
                hwXponOntPolicyRouteProfileRowStatus                    RowStatus
            }
            
        hwXponOntPolicyRouteProfileNameIndex OBJECT-TYPE
            SYNTAX OCTET STRING (SIZE(1..32))
            MAX-ACCESS not-accessible
            STATUS current
            DESCRIPTION
                "This object indicates the ont policy route profile index."
            ::= { hwXponOntPolicyRouteProfileEntry 1 } 
            
        hwXponOntPolicyRouteProfileBindNum OBJECT-TYPE
            SYNTAX Integer32
            MAX-ACCESS read-only
            STATUS current
            DESCRIPTION
                "This object indicates the number of ont bound with policy route profile."
            ::= { hwXponOntPolicyRouteProfileEntry 2 } 
            
         hwXponOntPolicyRouteProfileRowStatus OBJECT-TYPE
            SYNTAX RowStatus            
            MAX-ACCESS read-create
            STATUS current
            DESCRIPTION
                "The hwXponOntPolicyRouteProfileRowStatus is used to create a new row
                 or to modify or delete an existing row in this table.
                 Options:
                 1. createAndGo(4) -create a new instance of a conceptual row 
                 2. destroy(6)     -delete the instances associated with an existing conceptual row
                "
            ::= { hwXponOntPolicyRouteProfileEntry 3 }                       
                       
  --hwXponOntPolicyRouteProfileTable end 

--  Table hwXponOntPolicyRouteProfilePortCfgTable
        hwXponOntPolicyRouteProfilePortCfgTable OBJECT-TYPE
            SYNTAX SEQUENCE OF HwXponOntPolicyRouteProfilePortCfgEntry
            MAX-ACCESS not-accessible
            STATUS current
            DESCRIPTION
                "This is the ont policy route profile port configuration infomation table.
                 The index of this table is hwXponOntPolicyRouteProfilePortCfgProfNameIndex.
                "
            ::= { hwXponDeviceCommonProfileObjects 12 }
            
        hwXponOntPolicyRouteProfilePortCfgEntry OBJECT-TYPE
            SYNTAX HwXponOntPolicyRouteProfilePortCfgEntry
            MAX-ACCESS not-accessible
            STATUS current
            DESCRIPTION
                "This is the ont policy route profile port configuration infomation table.
                 The index of this entry is hwXponOntPolicyRouteProfilePortCfgProfNameIndex.
                "
            INDEX { hwXponOntPolicyRouteProfilePortCfgProfNameIndex, hwXponOntPolicyRouteProfilePortCfgIndex}
            ::= { hwXponOntPolicyRouteProfilePortCfgTable 1 }
            
        HwXponOntPolicyRouteProfilePortCfgEntry ::=
            SEQUENCE {
                hwXponOntPolicyRouteProfilePortCfgProfNameIndex                    OCTET STRING,
                hwXponOntPolicyRouteProfilePortCfgIndex                            Integer32, 
                hwXponOntPolicyRouteProfilePortCfgWanIndex                         Integer32,
                hwXponOntPolicyRouteProfilePortCfgEthPortBitMap                    Integer32,
                hwXponOntPolicyRouteProfilePortCfgWlanPortBitMap                   Integer32,
                hwXponOntPolicyRouteProfilePortCfgRowStatus                        RowStatus
            }
            
        hwXponOntPolicyRouteProfilePortCfgProfNameIndex OBJECT-TYPE
            SYNTAX OCTET STRING (SIZE(1..32))
            MAX-ACCESS not-accessible
            STATUS current
            DESCRIPTION
                "This object indicates the ont policy route profile index."
            ::= { hwXponOntPolicyRouteProfilePortCfgEntry 1 } 
            
        hwXponOntPolicyRouteProfilePortCfgIndex OBJECT-TYPE
            SYNTAX Integer32
            MAX-ACCESS read-write
            STATUS current
            DESCRIPTION
                "This object indicates the policy route rule index."
            ::= { hwXponOntPolicyRouteProfilePortCfgEntry 2 } 
            
        hwXponOntPolicyRouteProfilePortCfgWanIndex OBJECT-TYPE
            SYNTAX Integer32
            MAX-ACCESS read-write
            STATUS current
            DESCRIPTION
                "This object indicates the index of wan appointed by ont policy route."
            ::= { hwXponOntPolicyRouteProfilePortCfgEntry 3}  
            
        hwXponOntPolicyRouteProfilePortCfgEthPortBitMap OBJECT-TYPE
            SYNTAX Integer32
            MAX-ACCESS read-write
            STATUS current
            DESCRIPTION
                "This object indicates the mask of ethport using the policy route rule."
            ::= { hwXponOntPolicyRouteProfilePortCfgEntry 4}  
            
        hwXponOntPolicyRouteProfilePortCfgWlanPortBitMap OBJECT-TYPE
            SYNTAX Integer32
            MAX-ACCESS read-write
            STATUS current
            DESCRIPTION
                "This object indicates the mask of wan using the policy route rule."
            ::= { hwXponOntPolicyRouteProfilePortCfgEntry 5}         
            
        hwXponOntPolicyRouteProfilePortCfgRowStatus OBJECT-TYPE
            SYNTAX RowStatus        
            MAX-ACCESS read-create
            STATUS current
            DESCRIPTION
                "The hwXponOntPolicyRouteProfilePortCfgRowStatus is used to create a new row
                 or to modify or delete an existing row in this table.
                 Options:
                 1. createAndGo(4) -create a new instance of a conceptual row 
                 2. destroy(6)     -delete the instances associated with an existing conceptual row
                "
            ::= { hwXponOntPolicyRouteProfilePortCfgEntry 6}                       
                       
  --hwXponOntPolicyRouteProfilePortCfgTable end    

--  Table hwXponOntEthernetPortOpticalStaticInfoTable
        hwXponOntEthernetPortOpticalStaticInfoTable OBJECT-TYPE
            SYNTAX SEQUENCE OF HwXponOntEthernetPortOpticalStaticInfoEntry
            MAX-ACCESS not-accessible
            STATUS current
            DESCRIPTION
                "This table is the ont ethernet port optical static infomation.
                 The indexes of this table are ifIndex hwXponOntIndex and hwXponOntEthPortId.
                "
            ::= { hwXponDeviceCommonProfileObjects 13 }
            
        hwXponOntEthernetPortOpticalStaticInfoEntry OBJECT-TYPE
            SYNTAX HwXponOntEthernetPortOpticalStaticInfoEntry
            MAX-ACCESS not-accessible
            STATUS current
            DESCRIPTION
                "This table is the ont ethernet port optical static infomation.
                 The indexes of this entry are ifIndex hwXponOntIndex and hwXponOntEthPortId.
                "
            INDEX { ifIndex, hwXponOntIndex, hwXponOntEthPortId}
            ::= { hwXponOntEthernetPortOpticalStaticInfoTable 1 }
            
        HwXponOntEthernetPortOpticalStaticInfoEntry ::=
            SEQUENCE {
                hwXponOntEthernetPortOpticalIdentifier                             INTEGER,
                hwXponOntEthernetPortOpticalExtID                                  INTEGER,
                hwXponOntEthernetPortOpticalConnector                              INTEGER,
                hwXponOntEthernetPortOpticalVendorName                             OCTET STRING,
                hwXponOntEthernetPortOpticalVendorRev                              OCTET STRING,
                hwXponOntEthernetPortOpticalVendorPN                               OCTET STRING,
                hwXponOntEthernetPortOpticalVendorSN                               OCTET STRING,
                hwXponOntEthernetPortOpticalDateCode                               OCTET STRING,                
                hwXponOntEthernetPortOpticalSFF8472Compliance                      INTEGER,
                hwXponOntEthernetPortOptical10GEComplianceCodes			   INTEGER,
                hwXponOntEthernetPortOpticalGEComplianceCodes                      INTEGER,
                hwXponOntEthernetPortOpticalSpeed                                  INTEGER,
                hwXponOntEthernetPortOpticalLength9Micronkm                        Integer32,  
                hwXponOntEthernetPortOpticalLength9Micron                          Integer32,                
                hwXponOntEthernetPortOpticalLength50Micron                         Integer32,  
                hwXponOntEthernetPortOpticalLength62Micron5                        Integer32,  
                hwXponOntEthernetPortOpticalLengthCopper                           Integer32,  
                hwXponOntEthernetPortOpticalWaveLength                             Integer32,  
                hwXponOntEthernetPortOpticalBrNominal                              Integer32,  
                hwXponOntEthernetPortOpticalBrMax                                  Integer32,  
                hwXponOntEthernetPortOpticalBrMin                                  Integer32,  
                hwXponOntEthernetPortOpticalCcBase                                 Integer32,  
                hwXponOntEthernetPortOpticalCcExt                                  Integer32
            }
	    
        hwXponOntEthernetPortOpticalIdentifier OBJECT-TYPE
           SYNTAX  INTEGER
              {                      
                unknown(1), 
                gbic(2), 
                solderedToMotherboard(3), 
                sfp(4), 
                pin300XBI(5), 
                xenpak(6), 
                xfp(7), 
                xff(8), 
                xfpe(9), 
                xpak(10), 
                x2(11), 
                dwdmSfp(12), 
                qSfp(13),
                invalid(-1)
              } 
           MAX-ACCESS read-only
           STATUS      current
           DESCRIPTION
                 " Indicate the identifier of optical module.
                  Options:
		  1. unknown(1)                 -unknown the identifier of optical module
		  2. gbic(2)                    -the identifier of optical module is gbic
		  3. solderedToMotherboard(3)   -the identifier of optical module is solderedToMotherboard
		  4. sfp(4)                     -the identifier of optical module is sfp
		  5. pin300XBI(5)               -the identifier of optical module is pin300XBI
		  6. xenpak(6)                  -the identifier of optical module is xenpak
		  7. xfp(7)                     -the identifier of optical module is xfp
		  8. xff(8)                     -the identifier of optical module is xff
		  9. xfpe(9)                    -the identifier of optical module is xfpe
		  10. xpak(10)                  -the identifier of optical module is xpak
		  11. x2(11)                    -the identifier of optical module is x2
		  12. dwdmSfp(12)               -the identifier of optical module is DWDM-SFP
		  13. qSfp(13)                  -the identifier of optical module is QSFP                                      
                  14. invalid(-1) - Indicates that the query fails or no information is detected.
                  "
            ::= { hwXponOntEthernetPortOpticalStaticInfoEntry 1}   
	        
	hwXponOntEthernetPortOpticalExtID OBJECT-TYPE
           SYNTAX  INTEGER
              {                      
                  notSpecifiedOrNotCompliant(1), 
		  moddef1(2), 
		  moddef2(3), 
		  moddef3(4), 
		  bySerialIDOnly(5), 
		  moddef5(6), 
		  moddef6(7), 
		  moddef7(8), 
		  invalid(-1)
              } 
           MAX-ACCESS read-only
           STATUS      current
           DESCRIPTION
                 "Indicate the extended type of optical module. 
                  Options:
		  1. notSpecifiedOrNotCompliant(1)  -the extended type of optical module is notSpecifiedOrNotCompliant
		  2. moddef1(2)                     -the extended type of optical module is moddef1
		  3. moddef2(3)                     -the extended type of optical module is moddef2
		  4. moddef3(4)                     -the extended type of optical module is moddef3
		  5. bySerialIDOnly(5)              -the extended type of optical module is bySerialIDOnly
		  6. moddef5(6)                     -the extended type of optical module is moddef5
		  7. moddef6(7)                     -the extended type of optical module is moddef6
		  8. moddef7(8)                     -the extended type of optical module is moddef7
                  9. invalid(-1) - Indicates that the query fails or no information is detected.
                  "
            ::= { hwXponOntEthernetPortOpticalStaticInfoEntry 2}  
	     	    
	hwXponOntEthernetPortOpticalConnector OBJECT-TYPE
           SYNTAX  INTEGER
              {                      
                unknown(1), 
	        sc(2), 
		copperConnector1(3), 
		copperConnector2(4), 
		bnctnc(5), 
		coaxialHeaders(6), 
		fiberJack(7), 
		lc(8),
		mtrj(9), 
		mu(10), 
		sg(11), 
		opticalPigtail(12), 
		hssdcii(13), 
		copperPigtail(14), 
		vendorSpecific(15), 
		mpoParallelOptic(16), 
		rj45(17),
		invalid(-1)
              } 
           MAX-ACCESS read-only
           STATUS      current
           DESCRIPTION
                 "Indicate the type of optical module connector. 
                  Options:
                  1. unknown(1)            -unknown the type of optical module connector.
		  2. sc(2)                 -the type of optical module connector is sc.
		  3. copperConnector1(3)   -the type of optical module connector is copperConnector1.
		  4. copperConnector2(4)   -the type of optical module connector is copperConnector2.
		  5. bnctnc(5)             -the type of optical module connector is bnctnc.
		  6. coaxialHeaders(6)     -the type of optical module connector is coaxialHeaders.
		  7. fiberJack(7)          -the type of optical module connector is fiberJack.
		  8. lc(8)                 -the type of optical module connector is lc.
		  9. mtrj(9)               -the type of optical module connector is mtrj.
		  10. mu(10)               -the type of optical module connector is mu.
		  11. sg(11)               -the type of optical module connector is sg.
		  12. opticalPigtail(12)   -the type of optical module connector is opticalPigtail.
		  13. hssdcii(13)          -the type of optical module connector is hssdcii.
		  14. copperPigtail(14)    -the type of optical module connector is copperPigtail.
		  15. vendorSpecific(15)   -the type of optical module connector is vendorSpecific.
		  16. mpoParallelOptic(16) -the type of optical module connector is mpo parallel optic.
		  17. rj45(17)             -the type of optical module connector is RJ45.
                  18. invalid(-1) - Indicates that the query fails or no information is detected
                  "
            ::= { hwXponOntEthernetPortOpticalStaticInfoEntry 3}   
	    	    
        hwXponOntEthernetPortOpticalVendorName OBJECT-TYPE
            SYNTAX   OCTET STRING (SIZE (0..17))
            MAX-ACCESS read-only
            STATUS      current
            DESCRIPTION
                "Indicate the vendor name of a optical module."
            ::= { hwXponOntEthernetPortOpticalStaticInfoEntry 4}  
	    
	 hwXponOntEthernetPortOpticalVendorRev OBJECT-TYPE
            SYNTAX   OCTET STRING (SIZE (0..5))
            MAX-ACCESS read-only
            STATUS      current
            DESCRIPTION
                "Indicate the revision level for part number provided by vendor."
            ::= { hwXponOntEthernetPortOpticalStaticInfoEntry 5}  
	    
	 hwXponOntEthernetPortOpticalVendorPN OBJECT-TYPE
            SYNTAX   OCTET STRING (SIZE (0..17))
            MAX-ACCESS read-only
            STATUS      current
            DESCRIPTION
                "Indicate the part number of a optical module provided by vendor."
            ::= { hwXponOntEthernetPortOpticalStaticInfoEntry 6}  
	    
	 hwXponOntEthernetPortOpticalVendorSN OBJECT-TYPE
            SYNTAX   OCTET STRING (SIZE (0..17))
            MAX-ACCESS read-only
            STATUS      current
            DESCRIPTION
                "The serial number of a optical module provided by vendor."
            ::= { hwXponOntEthernetPortOpticalStaticInfoEntry 7}  
	    
	 hwXponOntEthernetPortOpticalDateCode OBJECT-TYPE
            SYNTAX   OCTET STRING (SIZE (0..9))
            MAX-ACCESS read-only
            STATUS      current
            DESCRIPTION
                "The date code of a optical module."
            ::= { hwXponOntEthernetPortOpticalStaticInfoEntry 8} 
	    
	hwXponOntEthernetPortOpticalSFF8472Compliance OBJECT-TYPE
           SYNTAX  INTEGER
              {                      
                  undefined(1), 
                  includesSFF8472V93(2), 
                  includesSFF8472V95(3), 
                  includesSFF8472V102(4), 
                  includesSFF8472V104(5), 
                  includesSFF8472V110(6), 
                  invalid(-1) 
              } 
           MAX-ACCESS read-only
           STATUS      current
           DESCRIPTION
                 "Indicate the SFF-8472 standard.
                  Options:
		    1. undefined(1)            -not included or undefined.
		    2. includesSFF8472V93(2)   -includes functionality described in SFF-8472 Rev 9.3.
		    3. includesSFF8472V95(3)   -includes functionality described in SFF-8472 Rev 9.5.
		    4. includesSFF8472V102(4)  -includes functionality described in SFF-8472 Rev 10.2.
		    5. includesSFF8472V104(5)  -includes functionality described in SFF-8472 Rev 10.4.
		    6. includesSFF8472V110(6)  -includes functionality described in SFF-8472 Rev 11.0.
		    7. invalid(-1)             -Indicates that the query fails or no information is detected  
                  "
            ::= { hwXponOntEthernetPortOpticalStaticInfoEntry 9} 
            
         hwXponOntEthernetPortOptical10GEComplianceCodes OBJECT-TYPE
           SYNTAX  INTEGER
              {                                        
                  en10GBASELRM(1), 
                  en10GBASELR(2), 
                  en10GBASESR(3), 
                  en10GBASEER(4), 
                  invalid(-1) 
              } 
           MAX-ACCESS read-only
           STATUS      current
           DESCRIPTION
                 "Indicate the 10G ethernet transceiver type.
                  Options:
		    1. en10GBASELRM(1)           -Ethernet transceiver type is 10GBASE-LRM
		    2. en10GBASELR(2)            -Ethernet transceiver type is 10GBASE-LR
		    3. en10GBASESR(3)            -Ethernet transceiver type is 10GBASE-SR
		    4. en10GBASEER(4)            -Ethernet transceiver type is 10GBASE-ER
		    5. invalid(-1)               -Indicates that the query fails or no information is detected
                  "
            ::= { hwXponOntEthernetPortOpticalStaticInfoEntry 10} 
            
           hwXponOntEthernetPortOpticalGEComplianceCodes OBJECT-TYPE
           SYNTAX  INTEGER
              {                      
                  en1000BASET(1), 
                  en1000BASECX(2), 
                  en1000BASELX(3), 
                  en1000BASESX(4), 
                  enMULTILX(5), 
                  en100BASELX(6), 
                  en100BASEFX(7), 
                  en1000BASEBX(8), 
                  en1000BASEPX(9), 
                  en100BASEBX(10), 
                  en1000BASEZX(11), 
                  invalid(-1) 
              } 
           MAX-ACCESS read-only
           STATUS      current
           DESCRIPTION
                 "Indicate the 1G ethernet transceiver type.
                  Options:
		    1. en1000BASET(1)              -Ethernet transceiver type is 1000BASE-T
		    2. en1000BASECX(2)             -Ethernet transceiver type is 1000BASE-CX
		    3. en1000BASELX(3)             -Ethernet transceiver type is 1000BASE-LX
		    4. en1000BASESX(4)             -Ethernet transceiver type is 1000BASE-SX
		    5. enMULTILX(5)                -Ethernet transceiver type is 100BASE-LX&1000BASE-LX
		    6. en100BASELX(6)              -Ethernet transceiver type is 100BASE-LX
		    7. en100BASEFX(7)              -Ethernet transceiver type is 100BASE-FX
		    8. en1000BASEBX(8)             -Ethernet transceiver type is 1000BASE-BX
		    9. en1000BASEPX(9)             -Ethernet transceiver type is 1000BASE-PX
		    10. en100BASEBX(10)            -Ethernet transceiver type is 100BASE-BX
                    11. en1000BASEZX(11)           -Ethernet transceiver type is 1000BASE-ZX
                    12. invalid(-1)                -Indicates that the query fails or no information is detected
                  "
            ::= { hwXponOntEthernetPortOpticalStaticInfoEntry 11} 
            
         hwXponOntEthernetPortOpticalSpeed OBJECT-TYPE
           SYNTAX  INTEGER
              {                      
                  speed400MBytesPerSec(1), 
                  speed200MBytesPerSec(2), 
                  speed100MBytesPerSec(3), 
                  speed800MBytesPerSec(4), 
                  speed1200MBytesPerSec(5), 
                  speed1600MBytesPerSec(6), 
                  invalid(-1) 
              } 
           MAX-ACCESS read-only
           STATUS      current
           DESCRIPTION
                 "Indicate the fibre Channel speed.
                  Options:
		    1. speed400MBytesPerSec(1)    -fibre channel speed is 400 MBytes/s  
		    2. speed200MBytesPerSec(2)    -fibre channel speed is 200 MBytes/s  
		    3. speed100MBytesPerSec(3)    -fibre channel speed is 100 MBytes/s  
		    4. speed800MBytesPerSec(4)    -fibre channel speed is 800 MBytes/s  
		    5. speed1200MBytesPerSec(5)   -fibre channel speed is 1200 MBytes/s  
		    6. speed1600MBytesPerSec(6)   -fibre channel speed is 1600 MBytes/s  
		    7. invalid(-1)                -Indicates that the query fails or no information is detected
                  "
            ::= { hwXponOntEthernetPortOpticalStaticInfoEntry 12} 
            
          hwXponOntEthernetPortOpticalLength9Micronkm OBJECT-TYPE
            SYNTAX      Integer32
	    UNITS       "km"
            MAX-ACCESS  read-only
            STATUS      current
            DESCRIPTION
                "Indicate the link length that is supported by the transceiver while operating in compliance 
                 with the applicable standards using 9 micron Single-mode Fiber.
	 	 0-255: The maximum value is 255, which means that the transceiver supports a link length 
                 greater than 254 km. Unit: km
                 Invalid(-1)                - Indicates that the query fails or no information is detected
                "
            ::= { hwXponOntEthernetPortOpticalStaticInfoEntry  13 }
            
         hwXponOntEthernetPortOpticalLength9Micron OBJECT-TYPE
            SYNTAX      Integer32
	    UNITS       "1m"
            MAX-ACCESS  read-only
            STATUS      current
            DESCRIPTION
                "Indicate the link length that is supported by the transceiver while operating in
		 compliance with the applicable standards using 9 micron Single-mode Fiber.
		 0~255:The maximum value is 255, which means that the transceiver supports a link length 
		 greater than 25.4 km.  Unit: 1m
		 Invalid(-1)                - Indicates that the query fails or no information is detected
                "
            ::= { hwXponOntEthernetPortOpticalStaticInfoEntry  14 }
          
          hwXponOntEthernetPortOpticalLength50Micron OBJECT-TYPE
            SYNTAX      Integer32
	    UNITS       "10m"
            MAX-ACCESS  read-only
            STATUS      current
            DESCRIPTION
                "Indicate link length that is supported by the transceiver while operating in
		 compliance with applicable standards using 50 micron multi-mode OM2 [500MHz*km] 
		 fiber.
		 0~255:The maximum value is 255, which means that the transceiver supports a link
	         length greater than 2.54 km.  Unit: 10m
		 Invalid(-1)                - Indicates that the query fails or no information is detected
                "
            ::= { hwXponOntEthernetPortOpticalStaticInfoEntry  15 }
            
          hwXponOntEthernetPortOpticalLength62Micron5 OBJECT-TYPE
            SYNTAX      Integer32
	    UNITS       "10m"
            MAX-ACCESS  read-only
            STATUS      current
            DESCRIPTION
                " Indicate link length that is supported by the transceiver while operating in
		  compliance with applicable standards using 62.5 micron multi-mode OM1 [200 MHz*km] 
		  fiber.
		  0~255: The maximum value is 255, which means that the transceiver supports a link length 
		  greater than 2.54 km.
		  Unit: 10m
		  Invalid(-1)                - Indicates that the query fails or no information is detected
                "
            ::= { hwXponOntEthernetPortOpticalStaticInfoEntry  16 }
            
          hwXponOntEthernetPortOpticalLengthCopper OBJECT-TYPE
            SYNTAX      Integer32
	    UNITS       "1m"
            MAX-ACCESS  read-only
            STATUS      current
            DESCRIPTION
                "Indicate Link length supported for copper.
		 Unit: 1m
		 Invalid(-1)                - Indicates that the query fails or no information is detected
                "
            ::= { hwXponOntEthernetPortOpticalStaticInfoEntry  17 }
            
          hwXponOntEthernetPortOpticalWaveLength OBJECT-TYPE
            SYNTAX      Integer32
	    UNITS       "1nm"
            MAX-ACCESS  read-only
            STATUS      current
            DESCRIPTION
                "The laser wavelength.
		 Unit: 1nm
		 Invalid(-1)                - Indicates that the query fails or no information is detected
                "
            ::= { hwXponOntEthernetPortOpticalStaticInfoEntry  18 }
            
          hwXponOntEthernetPortOpticalBrNominal OBJECT-TYPE
            SYNTAX      Integer32
	    UNITS       "100 MBits/sec"
            MAX-ACCESS  read-only
            STATUS      current
            DESCRIPTION
                "Indicate Nominal bit rate.
		 Unit: 100 MBits/sec
		 Invalid(-1)                - Indicates that the query fails or no information is detected
                "
            ::= { hwXponOntEthernetPortOpticalStaticInfoEntry  19 }
            
          hwXponOntEthernetPortOpticalBrMax OBJECT-TYPE
            SYNTAX      Integer32
            MAX-ACCESS  read-only
            STATUS      current
            DESCRIPTION
                "The upper bit rate margin.
		 Invalid(-1)                - Indicates that the query fails or no information is detected
                "
            ::= { hwXponOntEthernetPortOpticalStaticInfoEntry  20 }
            
          hwXponOntEthernetPortOpticalBrMin OBJECT-TYPE
            SYNTAX      Integer32
            MAX-ACCESS  read-only
            STATUS      current
            DESCRIPTION
                "The lower bit rate margin.
		 Invalid(-1)                - Indicates that the query fails or no information is detected
                "
            ::= { hwXponOntEthernetPortOpticalStaticInfoEntry  21 }
            
          hwXponOntEthernetPortOpticalCcBase OBJECT-TYPE
            SYNTAX      Integer32
            MAX-ACCESS  read-only
            STATUS      current
            DESCRIPTION
                "The check code for the base ID fields.
		 Invalid(-1)                - Indicates that the query fails or no information is detected
                "
            ::= { hwXponOntEthernetPortOpticalStaticInfoEntry  22 }
            
          hwXponOntEthernetPortOpticalCcExt OBJECT-TYPE
            SYNTAX      Integer32
            MAX-ACCESS  read-only
            STATUS      current
            DESCRIPTION
                "The check code for the extended ID fields.
		 Invalid(-1)                - Indicates that the query fails or no information is detected
                "
            ::= { hwXponOntEthernetPortOpticalStaticInfoEntry  23 }
  --hwXponOntEthernetPortOpticalStaticInfoTable end

--  Table hwXponOntEthernetPortOpticalDdmInfoTable
        hwXponOntEthernetPortOpticalDdmInfoTable OBJECT-TYPE
            SYNTAX SEQUENCE OF HwXponOntEthernetPortOpticalDdmInfoEntry
            MAX-ACCESS not-accessible
            STATUS current
            DESCRIPTION
                "This table is the ont ethernet port optical Ddm infomation.
                 The indexes of this table are ifIndex hwXponOntIndex and hwXponOntEthPortId.
                "
            ::= { hwXponDeviceCommonProfileObjects 14 }
            
        hwXponOntEthernetPortOpticalDdmInfoEntry OBJECT-TYPE
            SYNTAX HwXponOntEthernetPortOpticalDdmInfoEntry
            MAX-ACCESS not-accessible
            STATUS current
            DESCRIPTION
                "This table is the ont ethernet port optical Ddm infomation.
                 The indexes of this entry are ifIndex hwXponOntIndex and hwXponOntEthPortId.
                "
            INDEX { ifIndex, hwXponOntIndex, hwXponOntEthPortId}
            ::= { hwXponOntEthernetPortOpticalDdmInfoTable 1 }
            
        HwXponOntEthernetPortOpticalDdmInfoEntry ::=
            SEQUENCE {
                hwXponOntEthernetPortOpticalDdmTemperature                         Integer32,
                hwXponOntEthernetPortOpticalDdmBiasCurrent                         Integer32, 
                hwXponOntEthernetPortOpticalDdmTxPower                             Integer32,
                hwXponOntEthernetPortOpticalDdmRxPower                             Integer32,
                hwXponOntEthernetPortOpticalDdmVoltage                             Integer32
            }

	 hwXponOntEthernetPortOpticalDdmTemperature OBJECT-TYPE
            SYNTAX      Integer32
	    UNITS       "C"
            MAX-ACCESS  read-only
            STATUS      current
            DESCRIPTION
                "The temperature of the optical module.
		 Unit: unit C(centigrade)
                "
            ::= { hwXponOntEthernetPortOpticalDdmInfoEntry  1 }
	    
	 hwXponOntEthernetPortOpticalDdmBiasCurrent OBJECT-TYPE
            SYNTAX      Integer32
	    UNITS       "mA"
            MAX-ACCESS  read-only
            STATUS      current
            DESCRIPTION
                "The Bias Current of the optical module.
	 	 Unit: mA
                "
            ::= { hwXponOntEthernetPortOpticalDdmInfoEntry  2 }
	    
	 hwXponOntEthernetPortOpticalDdmTxPower OBJECT-TYPE
            SYNTAX      Integer32
	    UNITS       "0.01dBm"
            MAX-ACCESS  read-only
            STATUS      current
            DESCRIPTION
                "The transmitting power of the optical module.
		 Unit: 0.01dBm
                "
            ::= { hwXponOntEthernetPortOpticalDdmInfoEntry  3 }
	    
	 hwXponOntEthernetPortOpticalDdmRxPower OBJECT-TYPE
            SYNTAX      Integer32
	    UNITS       "0.01dBm"
            MAX-ACCESS  read-only
            STATUS      current
            DESCRIPTION
                "The receiving power of the optical module.
		 Unit: 0.01dBm
                "
            ::= { hwXponOntEthernetPortOpticalDdmInfoEntry  4 }
	    
	 hwXponOntEthernetPortOpticalDdmVoltage OBJECT-TYPE
            SYNTAX      Integer32
	    UNITS       "mV"
            MAX-ACCESS  read-only
            STATUS      current
            DESCRIPTION
                "The power feed voltage of the optical module.
		 Unit: mV
                "
            ::= { hwXponOntEthernetPortOpticalDdmInfoEntry  5 }
	    
  --hwXponOntEthernetPortOpticalDdmInfoTable end
  
        END
