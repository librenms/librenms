CONEL-INFO-MIB DEFINITIONS ::= BEGIN

IMPORTS
			enterprises
				FROM RFC1155-SMI
			OBJECT-TYPE
				FROM RFC-1212;

conel			OBJECT IDENTIFIER ::= { enterprises 30140 }

info			OBJECT IDENTIFIER ::= { conel 6 }

infoProduct		OBJECT-TYPE
			SYNTAX	OCTET STRING
			ACCESS	read-only
			STATUS	current
			::= { info 1 }

infoFirmware		OBJECT-TYPE
			SYNTAX	OCTET STRING
			ACCESS	read-only
			STATUS	current
			::= { info 2 }

infoSN			OBJECT-TYPE
			SYNTAX	OCTET STRING
			ACCESS	read-only
			STATUS	current
			::= { info 3 }

infoIMEI		OBJECT-TYPE
			SYNTAX	OCTET STRING
			ACCESS	read-only
			STATUS	current
			::= { info 4 }

infoESN			OBJECT-TYPE
			SYNTAX	OCTET STRING
			ACCESS	read-only
			STATUS	current
			::= { info 5 }

infoMEID		OBJECT-TYPE
			SYNTAX	OCTET STRING
			ACCESS	read-only
			STATUS	current
			::= { info 6 }

infoICCID		OBJECT-TYPE
			SYNTAX	OCTET STRING
			ACCESS	read-only
			STATUS	current
			::= { info 7 }

infoIMSI		OBJECT-TYPE
			SYNTAX	OCTET STRING
			ACCESS	read-only
			STATUS	current
			::= { info 8 }

info2IMEI		OBJECT-TYPE
			SYNTAX	OCTET STRING
			ACCESS	read-only
			STATUS	current
			::= { info 104 }

info2ESN		OBJECT-TYPE
			SYNTAX	OCTET STRING
			ACCESS	read-only
			STATUS	current
			::= { info 105 }

info2MEID		OBJECT-TYPE
			SYNTAX	OCTET STRING
			ACCESS	read-only
			STATUS	current
			::= { info 106 }

info2ICCID		OBJECT-TYPE
			SYNTAX	OCTET STRING
			ACCESS	read-only
			STATUS	current
			::= { info 107 }

info2IMSI		OBJECT-TYPE
			SYNTAX	OCTET STRING
			ACCESS	read-only
			STATUS	current
			::= { info 108 }

END
