FAST-ETHERNET-MIB DEFINITIONS ::= BEGIN

        --  fast-ethernet-mib The cabletron fast ethernet MIB
        --  Revision:   01.02.01
        --  Date: November 19, 1996 

        --  Cabletron Systems, Inc.
        --  35 Industrial Way, P.O. Box 5005
        --  Rochester, NH 03867-0505
        --  (603) 332-9400
        --  support@ctron.com

        --  This module provides authoritative definitions for Cabletron's
        --  enterprise-specific connection MIB.
        --
        --  This module will be extended, as needed.
        --

        --  Cabletron Systems reserves the right to make changes in 
        --  specification and other information contained in this document 
        --  without prior notice.  The reader should consult Cabletron Systems
        --  to determine whether any such changes have been made.
        --
        --  In no event shall Cabletron Systems be liable for any incidental, 
        --  indirect, special, or consequential damages whatsoever (including 
        --  but not limited to lost profits) arising out of or related to this
        --  document or the information contained in it, even if Cabletron
        --  Systems has been advised of, known, or should have known, the 
        --  possibility of such damages.
        --
        --  Cabletron grants vendors, end-users, and other interested parties
        --  a non-exclusive license to use this Specification in connection
        --  with the management of Cabletron products.

        --  Copyright August 95 Cabletron Systems


        IMPORTS
                OBJECT-TYPE
                        FROM    RFC-1212
                ctFastEthernet                  -- 1.3.6.1.4.1.52.4.1.2.9
                        FROM    CTRON-MIB-NAMES;

ctFastEthernetCtl               OBJECT IDENTIFIER ::= { ctFastEthernet 1 }
ctMMACFENBCfg                   OBJECT IDENTIFIER ::= { ctFastEthernet 2 }


ctFastEthernetCtlTable  OBJECT-TYPE
SYNTAX  SEQUENCE OF CtFastEthernetCtlEntry
ACCESS  not-accessible
STATUS  mandatory
DESCRIPTION
        "Provides a list of definitions and control objects over 100Base-X
        ports."
::= { ctFastEthernetCtl 1 }

ctFastEthernetCtlEntry  OBJECT-TYPE
SYNTAX  CtFastEthernetCtlEntry
ACCESS  not-accessible
STATUS  mandatory
DESCRIPTION
        "Defines a particular entry containing objects pertaining to
        definition and control over 100Base-X ports."
INDEX { ctFastEthernetCtlInterface, ctFastEthernetCtlPortGroup,
         ctFastEthernetCtlPort }
::= { ctFastEthernetCtlTable 1 }

CtFastEthernetCtlEntry ::= SEQUENCE {
        ctFastEthernetCtlInterface                      INTEGER,
        ctFastEthernetCtlPortGroup                      INTEGER,
        ctFastEthernetCtlPort                           INTEGER,
        ctFastEthernetLocalTechnologyAbility            INTEGER,
        ctFastEthernetCurrentOperationalMode            INTEGER,
        ctFastEthernetAdvertisedTechnologyAbility       INTEGER,
        ctFastEthernetReceivedTechnologyAbility         INTEGER
        }

ctFastEthernetCtlInterface      OBJECT-TYPE
SYNTAX  INTEGER
ACCESS  read-only
STATUS  mandatory
DESCRIPTION
        "The interface for which this fast ethernet information pertains."
::= { ctFastEthernetCtlEntry 1 }

ctFastEthernetCtlPortGroup      OBJECT-TYPE
SYNTAX  INTEGER
ACCESS  read-only
STATUS  mandatory
DESCRIPTION
        "The port group for which this fast ethernet information
        pertains."
::= { ctFastEthernetCtlEntry 2 }

ctFastEthernetCtlPort   OBJECT-TYPE
SYNTAX  INTEGER
ACCESS  read-only
STATUS  mandatory
DESCRIPTION
        "The physical port for which this fast ethernet information pertains."
::= { ctFastEthernetCtlEntry 3 }


 
ctFastEthernetLocalTechnologyAbility OBJECT-TYPE
SYNTAX  INTEGER  (1..1023)
ACCESS  read-only
STATUS  mandatory
DESCRIPTION
        "This indicates the technology ability of the local hardware.
        The value of this object is the logical OR of all supported 
        technologies.  Where each technology is given the values below:

          other(1)                      Undefined, or ability not known
          Auto-Negotiation(2)           Auto-Negotiation
          10BASE-T(8)                   10BASE-T
          10BASE-TFD(16)                Full duplex 10BASE-T
          100BASE-TX(32)                100BASE-TX  
          100BASE-TXFD(64)              Full Duplex 100BASE-TX
          100BASE-T4(128)               100BASE-T4 
          100BASE-FX(256)               100BASE-FX
          100BASE-FXFD(512)             Full Duplex 100Base-FX

        For example a port which supported 100Base-TX(32), 100Base-TXFD(64),
        and Auto-Negotiation(2) would have a value of 98(32 + 64 + 2)."
::= { ctFastEthernetCtlEntry 4 }


ctFastEthernetCurrentOperationalMode OBJECT-TYPE
SYNTAX  INTEGER (1..1023)
ACCESS  read-write
STATUS  mandatory
DESCRIPTION
        "Indicates the current operational mode of this port.
        The value of this object is the logical OR of current opertational
        mode and how we arrived at that mode, whether it be by 
        Auto-Negotiation(2), Manual-Config(4) or default.
        Where each mode is given the values below:

          other(1)                      Initializing or no link, ability unknown
          Auto-Negotiation(2)           Auto-Negotiation/Parallel Detection
          Manual-Config(4)              Manually Configured
          10BASE-T(8)                   10BASE-T
          10BASE-TFD(16)                Full duplex 10BASE-T
          100BASE-TX(32)                100BASE-TX  
          100BASE-TXFD(64)              Full Duplex 100BASE-TX
          100BASE-T4(128)               100BASE-T4
          100Base-FX(256)               100Base-FX
          100Base-FXFD(512)             Full Duplex 100Base-FX

        For example, a port operating at 100Base-TX(32) achieved through 
        Auto-Negotiation(2) would have a value of 34(32 + 2).
        If the port was manually configured(4) for 100Base-TX(32) this object 
        would have a value of 36(32 + 4).

        Values written to this object are limited to values read from
        ctFastEthernetLocalTechnologyAbility, with the addition of
        Manual-Config(4) but excluding other(1).  Therefore if 
        ctFastEthernetLocalTechnologyAbility has a value of 98 writing a 
        value of 256 would result in an error.  That is to say 100Base-FX 
        is not supported on this port.

        A set to a value of Auto-Negotiation(2) will result in
        auto-negotiation being enabled and will cause link re-negotiation.
        Note: this re-negotiation will in every case cause temporary link loss 
        during the link re-negotiation. Any other set with Auto-Negotiation(2)
        included will result in an error since you can not force an operational
        mode and auto-negotiation at the same time.

        A set to a value of Manual-Config(4) will result in auto-negotiation
        being disabled but the port staying at its current operational mode
        until device reset/power down at which time the port will come up
        in default mode. A subsequent read will indicate only the current
        operational mode achieved by default means.

        A set to any other value (port is being manually configured) must
        reflect a single ability.  For example writing a value of 68 would
        result in auto-negotiation being disabled and the port being manually
        configured(4) for 100Base-TXFD(64).  However a write of 100 would
        result in an error."
        ::= { ctFastEthernetCtlEntry 5 }



ctFastEthernetAdvertisedTechnologyAbility OBJECT-TYPE
SYNTAX  INTEGER   (1..1023)
ACCESS  read-write
STATUS  mandatory
DESCRIPTION
        "Indicates the advertised ability of the local hardware, but only
        becomes active on ports that have auto-negotiation enabled.  

        For example a port which will advertise 100Base-TX(32) and
        100Base-TXFD(64) ablilities would have a value of 96(32 + 64). A port
        that does not support auto-negotiation will be read as other(1).

        Values written to this object are limited to values read from
        ctFastEthernetLocalTechnologyAbility, excluding other(1) and
        Auto-Negotiation(2).  Therefore if ctFastEthernetLocalTechnologyAbility
        has a value of 98 writing a value of 128 would result in an error.  That
        is to say 100Base-T4 is not supported on this port. Furthermore, if
        ctFastEthernetLocalTechnologyAbility has a value that does not include
        Auto-Negotiation(2), writing any value will result in an error. That is
        to say that this port does not support Auto-Negotiation and therefore
        does not support ctFastEthernetAdvertisedTechnologyAbility.

        A successful set operation will result in immediate link re-negotiation
        if ctFastEthernetCurrentOperationalMode has a value that includes 
        Auto-Negotiation(2)(meaning Auto-negotiation is enabled). 

        Note: this re-negotiation will in every case cause temporary link loss 
        during the link re-negotiation.  If set to a value that is incompatible 
        with ctFastEthernetReceivedTechnologyAbility, link negotiation will not 
        be successful and will cause permanent link loss."
::= { ctFastEthernetCtlEntry 6 }

ctFastEthernetReceivedTechnologyAbility OBJECT-TYPE
SYNTAX  INTEGER  (1..1023)
ACCESS  read-only
STATUS  mandatory
DESCRIPTION
        "Indicates the advertised ability of the remote hardware, or link
        partner.  The value of this object is the logical OR of all supported 
        technologies.  Where each technology is given the values below:

          other(1)                      Undefined
          Auto-Negotiation(2)           Auto-Negotiation/Parallel Detection
          Not-Detected(4)               Link Partner does not support Auto-Negotiation
          10BASE-T(8)                   10BASE-T
          10BASE-TFD(16)                Full duplex 10BASE-T
          100BASE-TX(32)                100BASE-TX as defined in clause 25
          100BASE-TXFD(64)              Full Duplex 100BASE-TX
          100BASE-T4(128)               100BASE-T4 as defined in clause 23
          100Base-FX(256)               100Base-FX
          100Base-FXFD(512)             Full Duplex 100Base-FX

        For example a port which supports 100Base-TX(32), 100Base-TXFD(64),
        would have a value of 98(32 + 64 + Auto-Negotiation(2)).

        A read should always include Auto-Negotiation(2), unless the link
        partner does not support auto-negotiation, at which time the value
        will be Not-Detected(4) or auto-negotiation is disabled(or not
        supported) for this port at which time the value will be other(1)." 
::= { ctFastEthernetCtlEntry 7 }


ctFastEthernetCtlTableNumEntries OBJECT-TYPE
    SYNTAX INTEGER
    ACCESS read-only
    STATUS mandatory
    DESCRIPTION
        "The number of entries in the ctFastEthernetCtl Table."
    ::= { ctFastEthernetCtl 2 }
 

-- The ctMMACFENBCfg group is an optional group, this group configures
-- ports in regards to the MMAC Fast Ethernet Network Bus.
--
-- If the ctMMACFENBCfg group is implemnted all objects within
-- the group must be implemented.

ctMMACFENBCfgTable  OBJECT-TYPE
SYNTAX  SEQUENCE OF CtMMACFENBCfgEntry
ACCESS  not-accessible
STATUS  mandatory
DESCRIPTION
        "A table defining the capabilities of each port
        in regards to the MMAC Fast Ethernet Network Bus."
::= { ctMMACFENBCfg 1 }

ctMMACFENBCfgEntry  OBJECT-TYPE
SYNTAX  CtMMACFENBCfgEntry
ACCESS  not-accessible
STATUS  mandatory
DESCRIPTION
        "defines a particular entry containing port configuration 
        information." 
INDEX { ctMMACFENBCfgInterface, ctMMACFENBCfgPortGroup,
         ctMMACFENBCfgPort }
::= { ctMMACFENBCfgTable 1 }
 
CtMMACFENBCfgEntry ::= SEQUENCE {
        ctMMACFENBCfgInterface                      INTEGER,
        ctMMACFENBCfgPortGroup                      INTEGER,
        ctMMACFENBCfgPort                           INTEGER,
        ctMMACFENBOperCapabilities                  INTEGER,
        ctMMACFENBAdminCapabilities                 INTEGER
        }
 

ctMMACFENBCfgInterface      OBJECT-TYPE
SYNTAX  INTEGER
ACCESS  read-only
STATUS  mandatory
DESCRIPTION
        "The interface for which this MMAC FENB information pertains."
::= { ctMMACFENBCfgEntry 1 }
 
ctMMACFENBCfgPortGroup      OBJECT-TYPE
SYNTAX  INTEGER
ACCESS  read-only
STATUS  mandatory
DESCRIPTION
        "The port group for which this MMAC FENB information pertains."
::= { ctMMACFENBCfgEntry 2 }
 
ctMMACFENBCfgPort   OBJECT-TYPE
SYNTAX  INTEGER
ACCESS  read-only
STATUS  mandatory
DESCRIPTION
        "The physical port for which this MMAC FENB information pertains."
::= { ctMMACFENBCfgEntry 3 }
 
 
ctMMACFENBOperCapabilities OBJECT-TYPE
SYNTAX  INTEGER  (1..63)
ACCESS  read-only
STATUS  mandatory
DESCRIPTION
        "This value indicates the current capabilities of this port.
 
                (1)  Other
                (2)  MMAC A Channel
                (4)  MMAC FENB 1 (FENB= Fast Ethernet Network Bus)
                (8)  MMAC FENB 2
                (16) MMAC FENB 3
                (32) Front Panel

        The value of this object is the logical OR of all supported
        capabilities."
::= { ctMMACFENBCfgEntry 4 }
 
ctMMACFENBAdminCapabilities OBJECT-TYPE
SYNTAX  INTEGER (1..63)
ACCESS  read-write
STATUS  mandatory
DESCRIPTION
        "This value indicates the desired operational capabilities of 
        this port. 
 
                (1)  Other
                (2)  MMAC A Channel
                (4)  MMAC FENB 1 (FENB= Fast Ethernet Network Bus)
                (8)  MMAC FENB 2
                (16) MMAC FENB 3
                (32) Front Panel"

::= { ctMMACFENBCfgEntry 5 }

END
