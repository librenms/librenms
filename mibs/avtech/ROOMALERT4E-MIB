--
--defines ROOMALERT4E-MIB for SNMP agent extension of Room Alert 4E
--Contents:	Global Registration Module
--		Room Alert OIDs - Enterprise 20916
--Version:	4.2.4
--Date:		15 February 2019
--Developed By: AVTECH Software, Inc.

--
--Copyright (c) 2019 AVTECH Software, Inc.
--

ROOMALERT4E-MIB DEFINITIONS ::= BEGIN


IMPORTS
	enterprises, IpAddress, Counter, TimeTicks
		FROM RFC1155-SMI
	OBJECT-TYPE
		FROM RFC-1212
	TRAP-TYPE
		FROM RFC-1215;


avtech      OBJECT IDENTIFIER ::= { enterprises 20916 }
products      OBJECT IDENTIFIER ::= { avtech 1 }
roomalert4E      OBJECT IDENTIFIER ::= { products 6 }
sensors       OBJECT IDENTIFIER ::= { roomalert4E 1 }
signaltower		OBJECT IDENTIFIER ::= { roomalert4E 2 }
traps	      OBJECT IDENTIFIER ::= { roomalert4E 3 }
internal   OBJECT IDENTIFIER ::= { sensors 1 }
temperature   OBJECT IDENTIFIER ::= { internal 1 }
label	OBJECT IDENTIFIER ::= { internal 2 }
digital   OBJECT IDENTIFIER ::= { sensors 2 }
digital-sen1   OBJECT IDENTIFIER ::= { digital 1 }
digital-sen2   OBJECT IDENTIFIER ::= { digital 2 }
switch   OBJECT IDENTIFIER ::= { sensors 3 }


-- Room Alert 4E MIB
-- Parameters


internal-tempf OBJECT-TYPE
	SYNTAX  	INTEGER(0..65535)
	ACCESS		read-only
	STATUS		mandatory
	DESCRIPTION	"The internal temperature reading in Fahrenheit."
::= { temperature 1 }

internal-tempc OBJECT-TYPE
	SYNTAX  	INTEGER(0..65535)
	ACCESS		read-only
	STATUS		mandatory
	DESCRIPTION	"The internal temperature reading in Celsius."
::= { temperature 2 }

internal-label OBJECT-TYPE
	SYNTAX		OCTET STRING
	ACCESS		read-only
	STATUS		mandatory
	DESCRIPTION "The label of this sensor"
::= { label 1 }

digital-sen1-1 OBJECT-TYPE
	SYNTAX  	INTEGER(0..65535)
	ACCESS		read-only
	STATUS		mandatory
	DESCRIPTION	"If this sensor is a Temperature, Temp/Humidity, Temp/Analog, or Temp/Active Power sensor, this value represents the current temperature in Celsius."
::= { digital-sen1 1 }

digital-sen1-2 OBJECT-TYPE
	SYNTAX  	INTEGER(0..65535)
	ACCESS		read-only
	STATUS		mandatory
	DESCRIPTION	"If this sensor is a Temperature, Temp/Humidity, Temp/Analog, or Temp/Active Power sensor, this value represents the current temperature in Fahrenheit."
::= { digital-sen1 2 }

digital-sen1-3 OBJECT-TYPE
	SYNTAX  	INTEGER(0..65535)
	ACCESS		read-only
	STATUS		mandatory
	DESCRIPTION	"If this sensor is a Temp/Humidity sensor, this value represents the current relative humidity in % Relative Humidity. If this sensor is a Temp/Analog sensor, this value represents the current Voltage reading. If this is a Temp/Active Power sensor, this value represents the current power state (1=Power Detected, 0=No Power Detected)."
::= { digital-sen1 3 }

digital-sen1-4 OBJECT-TYPE
	SYNTAX  	INTEGER(0..65535)
	ACCESS		read-only
	STATUS		mandatory
	DESCRIPTION	"If this sensor is a Temp/Humidity sensor, this value represents the current heat index in Fahrenheit. If this sensor is a Temp/Analog sensor, this value represents the current custom reading."
::= { digital-sen1 4 }

digital-sen1-5 OBJECT-TYPE
	SYNTAX  	INTEGER(0..65535)
	ACCESS		read-only
	STATUS		mandatory
	DESCRIPTION	"If this sensor is a Temp/Humidity sensor, this value represents the current heat index in Celsius."
::= { digital-sen1 5 }

digital-sen1-6 OBJECT-TYPE
	SYNTAX  	INTEGER(0..65535)
	ACCESS		read-only
	STATUS		mandatory
	DESCRIPTION	"If this sensor is a Temp/Humidity sensor, this value represents the current dew point in Celsius."
::= { digital-sen1 6 }

digital-sen1-7 OBJECT-TYPE
	SYNTAX  	INTEGER(0..65535)
	ACCESS		read-only
	STATUS		mandatory
	DESCRIPTION	"If this sensor is a Temp/Humidity sensor, this value represents the current dew point in Fahrenheit."
::= { digital-sen1 7 }

digital-sen1-label OBJECT-TYPE
	SYNTAX		OCTET STRING
	ACCESS		read-only
	STATUS		mandatory
	DESCRIPTION "The label of this sensor"
::= {digital-sen1 8}

digital-sen2-1 OBJECT-TYPE
	SYNTAX  	INTEGER(0..65535)
	ACCESS		read-only
	STATUS		mandatory
	DESCRIPTION	"If this sensor is a Temperature, Temp/Humidity, Temp/Analog, or Temp/Active Power sensor, this value represents the current temperature in Celsius."
::= { digital-sen2 1 }

digital-sen2-2 OBJECT-TYPE
	SYNTAX  	INTEGER(0..65535)
	ACCESS		read-only
	STATUS		mandatory
	DESCRIPTION	"If this sensor is a Temperature, Temp/Humidity, Temp/Analog, or Temp/Active Power sensor, this value represents the current temperature in Fahrenheit."
::= { digital-sen2 2 }

digital-sen2-3 OBJECT-TYPE
	SYNTAX  	INTEGER(0..65535)
	ACCESS		read-only
	STATUS		mandatory
	DESCRIPTION	"If this sensor is a Temp/Humidity sensor, this value represents the current relative humidity in % Relative Humidity. If this sensor is a Temp/Analog sensor, this value represents the current Voltage reading. If this is a Temp/Active Power sensor, this value represents the current power state (1=Power Detected, 0=No Power Detected)."
::= { digital-sen2 3 }

digital-sen2-4 OBJECT-TYPE
	SYNTAX  	INTEGER(0..65535)
	ACCESS		read-only
	STATUS		mandatory
	DESCRIPTION	"If this sensor is a Temp/Humidity sensor, this value represents the current heat index in Fahrenheit. If this sensor is a Temp/Analog sensor, this value represents the current custom reading."
::= { digital-sen2 4 }

digital-sen2-5 OBJECT-TYPE
	SYNTAX  	INTEGER(0..65535)
	ACCESS		read-only
	STATUS		mandatory
	DESCRIPTION	"If this sensor is a Temp/Humidity sensor, this value represents the current heat index in Celsius."
::= { digital-sen2 5 }

digital-sen2-6 OBJECT-TYPE
	SYNTAX  	INTEGER(0..65535)
	ACCESS		read-only
	STATUS		mandatory
	DESCRIPTION	"If this sensor is a Temp/Humidity sensor, this value represents the current dew point in Celsius."
::= { digital-sen2 6 }

digital-sen2-7 OBJECT-TYPE
	SYNTAX  	INTEGER(0..65535)
	ACCESS		read-only
	STATUS		mandatory
	DESCRIPTION	"If this sensor is a Temp/Humidity sensor, this value represents the current dew point in Fahrenheit."
::= { digital-sen2 7 }

digital-sen2-label OBJECT-TYPE
	SYNTAX		OCTET STRING
	ACCESS		read-only
	STATUS		mandatory
	DESCRIPTION "The label of this sensor"
::= {digital-sen2 8}

switch-sen1 OBJECT-TYPE
	SYNTAX  	INTEGER(0..1)
	ACCESS		read-only
	STATUS		mandatory
	DESCRIPTION	"The reading for the switch sensor 1 (0 = OPEN, 1 = CLOSED)."
::= { switch 1 }

switch-label OBJECT-TYPE
	SYNTAX		OCTET STRING
	ACCESS		read-only
	STATUS		mandatory
	DESCRIPTION "The label for the switch sensor"
::= { switch 2 }

red-led OBJECT-TYPE
	SYNTAX  	INTEGER(0..1)
	ACCESS		read-write
	STATUS		mandatory
	DESCRIPTION	"The status of this Light Tower element (0 = OFF, 1 = ON)."
::= { signaltower 1 }

amber-led OBJECT-TYPE
	SYNTAX  	INTEGER(0..1)
	ACCESS		read-write
	STATUS		mandatory
	DESCRIPTION	"The status of this Light Tower element (0 = OFF, 1 = ON)."
::= { signaltower 2 }

green-led OBJECT-TYPE
	SYNTAX  	INTEGER(0..1)
	ACCESS		read-write
	STATUS		mandatory
	DESCRIPTION	"The status of this Light Tower element (0 = OFF, 1 = ON)."
::= { signaltower 3 }

blue-led OBJECT-TYPE
	SYNTAX  	INTEGER(0..1)
	ACCESS		read-write
	STATUS		mandatory
	DESCRIPTION	"The status of this Light Tower element (0 = OFF, 1 = ON)."
::= { signaltower 4 }

white-led OBJECT-TYPE
	SYNTAX  	INTEGER(0..1)
	ACCESS		read-write
	STATUS		mandatory
	DESCRIPTION	"The status of this Light Tower element (0 = OFF, 1 = ON)."
::= { signaltower 5 }

alarm1 OBJECT-TYPE
	SYNTAX  	INTEGER(0..1)
	ACCESS		read-write
	STATUS		mandatory
	DESCRIPTION	"The status of this Light Tower element (0 = OFF, 1 = ON)."
::= { signaltower 6 }

alarm2 OBJECT-TYPE
	SYNTAX  	INTEGER(0..1)
	ACCESS		read-write
	STATUS		mandatory
	DESCRIPTION	"The status of this Light Tower element (0 = OFF, 1 = ON)."
::= { signaltower 7 }

alarmmessage OBJECT-TYPE
	SYNTAX  	OCTET STRING
	ACCESS		read-only
	STATUS		mandatory
	DESCRIPTION	"Last Alarm Message"
::= { traps 1 }


-- roomalert4E TRAPS

room-alert-4e-snmp-trap TRAP-TYPE
	ENTERPRISE	roomalert4E
	VARIABLES	{ alarmmessage }
	DESCRIPTION	"A room-alert-4e-snmp-trap indicates that an alarm
			condition has occurred on the sensor indicated
			by the alarmmessage variable."
::= 2
END
