--
-- EDFA-oa-MIB.mib
-- MIB generated by MG-SOFT Visual MIB Builder Version 6.0  Build 88
-- Wednesday, November 08, 2017 at 10:55:00
--

	EDFA-oa-MIB DEFINITIONS ::= BEGIN
 
		IMPORTS
			OBJECT-TYPE			
				FROM SNMPv2-SMI;
	
	
--
-- Node definitions
--
	
-- 1.3.6.1.4.1.34592
--		edfa OBJECT IDENTIFIER ::= { enterprises 34592 }
			eponeoc MODULE-IDENTITY 
			LAST-UPDATED "201005271056Z"		-- May 27, 2010 at 10:56 GMT
			ORGANIZATION 
				"epon eoc factory."
			CONTACT-INFO 
				" "
			DESCRIPTION 
				"epon eoc common mib module"
			::= { enterprises 34592 }
		
		-- 1.3.6.1.4.1.34592.1
		ipProduct OBJECT-IDENTITY
			STATUS current
			DESCRIPTION 
				"Defines the base identifier containing the definition of ip products line.
				"
			::= { eponeoc 1 }

		
-- 1.3.6.1.4.1.34592.1.1
		mediaConverter OBJECT-IDENTITY
			STATUS current
			DESCRIPTION 
				"Defines the base identifier for the subtree
				supported by media converter line products.
				"
			::= { ipProduct 1 }

		
-- 1.3.6.1.4.1.34592.1.5
		edfa OBJECT-IDENTITY
			STATUS current
			DESCRIPTION 
				"Defines the base identifier for the subtree
				supported by smartCPE Switch line products.
				"
			::= { ipProduct 5 }
			
-- 1.3.6.1.4.1.34592.1.5.1
		oaEDFAAlarmRangeTable OBJECT-TYPE
			SYNTAX SEQUENCE OF OaEDFAAlarmRangeEntry
			MAX-ACCESS not-accessible
			STATUS current
			DESCRIPTION
				"Description."
			::= { edfa 1 }

		
-- 1.3.6.1.4.1.34592.1.5.1.1
		oaEDFAAlarmRangeEntry OBJECT-TYPE
			SYNTAX OaEDFAAlarmRangeEntry
			MAX-ACCESS not-accessible
			STATUS current
			DESCRIPTION
				"Description."
			INDEX { oaEDFAAlarmRangeIndex }
			::= { oaEDFAAlarmRangeTable 1 }

		
		OaEDFAAlarmRangeEntry ::=
			SEQUENCE { 
				oaEDFAAlarmRangeIndex
					INTEGER,
				oaEDFAAlarmRangeDecr
					OCTET STRING,
				oaEDFAAlarmRangeHIHItoHI
					INTEGER,
				oaEDFAAlarmRangeHIHItoLO
					INTEGER,
				oaEDFAAlarmRangeHItoHI
					INTEGER,
				oaEDFAAlarmRangeHItoLO
					INTEGER,
				oaEDFAAlarmRangeLOtoHI
					INTEGER,
				oaEDFAAlarmRangeLOtoLO
					INTEGER,
				oaEDFAAlarmRangeLOLOtoHI
					INTEGER,
				oaEDFAAlarmRangeLOLOtoLO
					INTEGER,
				oaEDFAAlarmRangeDDtoHI
					INTEGER,
				oaEDFAAlarmRangeDDtoLO
					INTEGER
			 }

-- 1.3.6.1.4.1.34592.1.5.1.1.1
		oaEDFAAlarmRangeIndex OBJECT-TYPE
			SYNTAX INTEGER (1..12)
			MAX-ACCESS read-only
			STATUS current
			DESCRIPTION
				"Description."
			::= { oaEDFAAlarmRangeEntry 1 }

		
-- 1.3.6.1.4.1.34592.1.5.1.1.2
		oaEDFAAlarmRangeDecr OBJECT-TYPE
			SYNTAX DisplayString
			MAX-ACCESS read-only
			STATUS mandatory
			DESCRIPTION
				"Description."
			::= { oaEDFAAlarmRangeEntry 2 }

		
-- 1.3.6.1.4.1.34592.1.5.1.1.3
		oaEDFAAlarmRangeHIHItoHI OBJECT-TYPE
			SYNTAX INTEGER
			MAX-ACCESS read-only
			STATUS current
			DESCRIPTION
				"Description."
			::= { oaEDFAAlarmRangeEntry 3 }

		
-- 1.3.6.1.4.1.34592.1.5.1.1.4
		oaEDFAAlarmRangeHIHItoLO OBJECT-TYPE
			SYNTAX INTEGER
			MAX-ACCESS read-only
			STATUS current
			DESCRIPTION
				"Description."
			::= { oaEDFAAlarmRangeEntry 4 }

		
-- 1.3.6.1.4.1.34592.1.5.1.1.5
		oaEDFAAlarmRangeHItoHI OBJECT-TYPE
			SYNTAX INTEGER
			MAX-ACCESS read-only
			STATUS current
			DESCRIPTION
				"Description."
			::= { oaEDFAAlarmRangeEntry 5 }

		
-- 1.3.6.1.4.1.34592.1.5.1.1.6
		oaEDFAAlarmRangeHItoLO OBJECT-TYPE
			SYNTAX INTEGER
			MAX-ACCESS read-only
			STATUS current
			DESCRIPTION
				"Description."
			::= { oaEDFAAlarmRangeEntry 6 }

		
-- 1.3.6.1.4.1.34592.1.5.1.1.7
		oaEDFAAlarmRangeLOtoHI OBJECT-TYPE
			SYNTAX INTEGER
			MAX-ACCESS read-only
			STATUS current
			DESCRIPTION
				"Description."
			::= { oaEDFAAlarmRangeEntry 7 }

		
-- 1.3.6.1.4.1.34592.1.5.1.1.8
		oaEDFAAlarmRangeLOtoLO OBJECT-TYPE
			SYNTAX INTEGER
			MAX-ACCESS read-only
			STATUS current
			DESCRIPTION
				"Description."
			::= { oaEDFAAlarmRangeEntry 8 }

		
-- 1.3.6.1.4.1.34592.1.5.1.1.9
		oaEDFAAlarmRangeLOLOtoHI OBJECT-TYPE
			SYNTAX INTEGER
			MAX-ACCESS read-only
			STATUS current
			DESCRIPTION
				"Description."
			::= { oaEDFAAlarmRangeEntry 9 }

		
-- 1.3.6.1.4.1.34592.1.5.1.1.10
		oaEDFAAlarmRangeLOLOtoLO OBJECT-TYPE
			SYNTAX INTEGER
			MAX-ACCESS read-only
			STATUS current
			DESCRIPTION
				"Description."
			::= { oaEDFAAlarmRangeEntry 10 }

		
-- 1.3.6.1.4.1.34592.1.5.1.1.11
		oaEDFAAlarmRangeDDtoHI OBJECT-TYPE
			SYNTAX INTEGER
			MAX-ACCESS read-only
			STATUS current
			DESCRIPTION
				"Description."
			::= { oaEDFAAlarmRangeEntry 11 }

		
-- 1.3.6.1.4.1.34592.1.5.1.1.12
		oaEDFAAlarmRangeDDtoLO OBJECT-TYPE
			SYNTAX INTEGER
			MAX-ACCESS read-only
			STATUS current
			DESCRIPTION
				"Description."
			::= { oaEDFAAlarmRangeEntry 12 }

		
	
	END

--
-- EDFA-oa-MIB.mib
--
