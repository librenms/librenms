--
-- VENDOR-COMMON-MIB.my
-- MIB generated by MG-SOFT Visual MIB Builder Version 6.0  Build 88
-- Tuesday, Dec 25, 2017 at 15:03:49
--

	VENDOR-COMMON-MIB DEFINITIONS ::= BEGIN
 
		IMPORTS
			enterprises, MODULE-IDENTITY, OBJECT-IDENTITY			
				FROM SNMPv2-SMI			
			TEXTUAL-CONVENTION			
				FROM SNMPv2-TC;
	
	
-- 1.3.6.1.4.1.34592
		vendor MODULE-IDENTITY 
			LAST-UPDATED "201005271056Z"		-- May 27, 2010 at 10:56 GMT
			ORGANIZATION 
				"vendor."
			CONTACT-INFO 
				" "
			DESCRIPTION 
				"vendor common mib module"
			::= { enterprises 34592 }

		
	
--
-- Textual conventions
--
	
--  Textual conventions
-- 
-- Textual conventions
-- 
		OperSwitch ::= TEXTUAL-CONVENTION
			STATUS current
			DESCRIPTION 
				"Device function operation switch type"
			SYNTAX INTEGER
				{
				enable(1),
				disable(2)
				}

		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}

		DataDirection ::= TEXTUAL-CONVENTION
			STATUS current
			DESCRIPTION 
				"A data channel normally have two direction, up and down"
			SYNTAX INTEGER
				{
				upstream(1),
				downstream(2)
				}

		DeviceOperation ::= TEXTUAL-CONVENTION
			STATUS current
			DESCRIPTION 
				"This type defines an operate action aggregate"
			SYNTAX INTEGER
				{
				reset(2),
				default(3),
				saveConfig(4),
				restore(5),
				delete(6)
				}

		LedStatus ::= TEXTUAL-CONVENTION
			STATUS current
			DESCRIPTION 
				"Led status"
			SYNTAX INTEGER
				{
				on(1),
				off(2),
				blink(3)
				}

		DeviceType ::= TEXTUAL-CONVENTION
			STATUS current
			DESCRIPTION 
				"Device type convention. Define all PBB device type value.
				
				----------------------------------
				| family | series | class | type |
				----------------------------------
				   8b        8b      8b      8b
				
				refer to document <pducuct type defines>"
			SYNTAX INTEGER
				{
				epon(16842752),
				chassis(16843009),
				olt(16843265),
				pon(16843521),
				pon1(16909057),
				epon1u(17105153),
				olt1(17105409),
				pon2(17105665),
				onu4db(16974081),
				onu4db1(16974082),
				onu4db2(16974083),
				onu8db(16974084),
				onu4d(16974085),
				onu1d(16974086),
				onu1dg(16974087),
				onu2dg(16974088),
				onu2dgm(16974095),
				onu4dgm(16974094),
				onu4dp(16974089),
				onu3dm(16974090),
				onu4d1(16974091),
				onu2dm(16974092),
				onu4d2p(16974337),
				onu4d2pp(16974338),
				onu4d1r(16974593),
				onu4d1rp(16974594),
				onu4d2p1r(16974849),
				onu4d2p1r1(17040129),
				onu4d2p1rp(16974850),
				onu24d(17039617)
				}

	
--
-- Node definitions
--
	
-- 1.3.6.1.4.1.34592.1
		ipProduct OBJECT-IDENTITY
			STATUS current
			DESCRIPTION 
				"Defines the base identifier containing the definition of ip products line.
				"
			::= { vendor 1 }

		
-- 1.3.6.1.4.1.34592.1.1
		mediaConverter OBJECT-IDENTITY
			STATUS current
			DESCRIPTION 
				"Defines the base identifier for the subtree
				supported by media converter line products.
				"
			::= { ipProduct 1 }

		
-- 1.3.6.1.4.1.34592.1.2
		switch OBJECT-IDENTITY
			STATUS current
			DESCRIPTION 
				"Defines the base identifier for the subtree
				supported by smartCPE Switch line products.
				"
			::= { ipProduct 2 }

		
-- 1.3.6.1.4.1.34592.1.3
		pon OBJECT-IDENTITY
			STATUS current
			DESCRIPTION 
				" "
			::= { ipProduct 3 }

		
-- 1.3.6.1.4.1.34592.1.4
		eoc OBJECT-IDENTITY
			STATUS current
			DESCRIPTION 
				" "
			::= { ipProduct 4 }

		
	
	END

--
-- EPON-EOC-MIB.my
--
