--
-- NSCRTV-EPONEOC-MOD-EOC-MIB.my
-- MIB generated by MG-SOFT Visual MIB Builder Version 4.0 Build 349
-- Monday, July 13, 2009 at 10:59:26
--

        NSCRTV-EPONEOC-MOD-EOC-MIB DEFINITIONS ::= BEGIN
 
                IMPORTS
                        DisplayString                   
                                FROM RFC1213-MIB                        
                        TimeTicks, IpAddress, Counter32, Counter64, OBJECT-TYPE, NOTIFICATION-TYPE                 
                                FROM SNMPv2-SMI                 
                        spidcom
                                FROM SPIDCOM-MIB
                        MacAddress, RowStatus                   
                                FROM SNMPv2-TC;


eoc MODULE-IDENTITY
        LAST-UPDATED "200908180000Z"
        ORGANIZATION "SPiDCOM"
        CONTACT-INFO
                "SPiDCOM"
        DESCRIPTION
                "Description"
        REVISION "200908180000Z"
        DESCRIPTION
                ""
        ::= { spidcom 3 }

        
                org     OBJECT IDENTIFIER
                ::=  {  iso  3  }

        dod     OBJECT IDENTIFIER
                ::=  {  org  6  }

        internet        OBJECT IDENTIFIER
                ::=  {  dod  1  }

        private OBJECT IDENTIFIER
                ::=  {  internet  4  }

        enterprises     OBJECT IDENTIFIER
                ::=  {  private  1  }

        eoc     OBJECT IDENTIFIER
                ::=  {  spidcom  3  }

        nscrtvEocTree     OBJECT IDENTIFIER
                ::=  {  eoc  1  }
        
--
-- Node definitions
--
        
                -- 1.3.6.1.4.1.17409.2.4.1
                modEoCCLTAdminGroup OBJECT IDENTIFIER ::= { nscrtvEocTree 1 }

                
                -- 1.3.6.1.4.1.17409.2.4.1.1
                modEoCCLTDevInfoGroup OBJECT IDENTIFIER ::= { modEoCCLTAdminGroup 1 }

                
                -- 1.3.6.1.4.1.17409.2.4.1.1.1
                modEoCCLTAdminLogicalID OBJECT-TYPE
                        SYNTAX DisplayString (SIZE (0..40))
                        MAX-ACCESS read-write
                        STATUS current
                        DESCRIPTION ""
                        ::= { modEoCCLTDevInfoGroup 1 }

                
                -- 1.3.6.1.4.1.17409.2.4.1.1.2
                modEoCCLTAdminTechProject OBJECT-TYPE
                        SYNTAX DisplayString (SIZE (0..255))
                        MAX-ACCESS read-only
                        STATUS current
                        DESCRIPTION ""
                        ::= { modEoCCLTDevInfoGroup 2 }

                
                -- 1.3.6.1.4.1.17409.2.4.1.1.3
                modEoCCLTAdminManufactoryInfo OBJECT-TYPE
                        SYNTAX DisplayString (SIZE (0..255))
                        MAX-ACCESS read-only
                        STATUS current
                        DESCRIPTION ""
                        ::= { modEoCCLTDevInfoGroup 3 }

                
                -- 1.3.6.1.4.1.17409.2.4.1.1.4
                modEoCCLTAdminModelNumber OBJECT-TYPE
                        SYNTAX DisplayString (SIZE (0..255))
                        MAX-ACCESS read-only
                        STATUS current
                        DESCRIPTION ""
                        ::= { modEoCCLTDevInfoGroup 4 }

                
                -- 1.3.6.1.4.1.17409.2.4.1.1.5
                modEoCCLTAdminSerialNumber OBJECT-TYPE
                        SYNTAX DisplayString (SIZE (0..255))
                        MAX-ACCESS read-only
                        STATUS current
                        DESCRIPTION ""
                        ::= { modEoCCLTDevInfoGroup 5 }

                
                -- 1.3.6.1.4.1.17409.2.4.1.1.6
                modEoCCLTAdminSoftwareVersion OBJECT-TYPE
                        SYNTAX DisplayString (SIZE (0..255))
                        MAX-ACCESS read-only
                        STATUS current
                        DESCRIPTION ""
                        ::= { modEoCCLTDevInfoGroup 6 }

                
                -- 1.3.6.1.4.1.17409.2.4.1.1.7
                modEoCCLTAdminHardwareVersion OBJECT-TYPE
                        SYNTAX DisplayString (SIZE (0..255))
                        MAX-ACCESS read-only
                        STATUS current
                        DESCRIPTION ""
                        ::= { modEoCCLTDevInfoGroup 7 }

                
                -- 1.3.6.1.4.1.17409.2.4.1.1.8
                modEoCCLTAdminVendorSpecialInfo OBJECT-TYPE
                        SYNTAX DisplayString (SIZE (0..255))
                        MAX-ACCESS read-only
                        STATUS current
                        DESCRIPTION ""
                        ::= { modEoCCLTDevInfoGroup 8 }

                
                -- 1.3.6.1.4.1.17409.2.4.1.2
                modEoCCLTNetworkAttrGroup OBJECT IDENTIFIER ::= { modEoCCLTAdminGroup 2 }

                
                -- 1.3.6.1.4.1.17409.2.4.1.2.1
                modEoCCLTAdminMACAddress OBJECT-TYPE
                        SYNTAX MacAddress
                        MAX-ACCESS read-only
                        STATUS current
                        DESCRIPTION ""
                        ::= { modEoCCLTNetworkAttrGroup 1 }

                
                -- 1.3.6.1.4.1.17409.2.4.1.2.2
                modEoCCLTAdminIPMode OBJECT-TYPE
                        SYNTAX INTEGER
                                {
                                static(0),
                                dynamic(1)
                                }
                        MAX-ACCESS read-write
                        STATUS current
                        DESCRIPTION ""
                        ::= { modEoCCLTNetworkAttrGroup 2 }

                
                -- 1.3.6.1.4.1.17409.2.4.1.2.3
                modEoCCLTAdminIPAddress OBJECT-TYPE
                        SYNTAX IpAddress
                        MAX-ACCESS read-write
                        STATUS current
                        DESCRIPTION ""
                        ::= { modEoCCLTNetworkAttrGroup 3 }

                
                -- 1.3.6.1.4.1.17409.2.4.1.2.4
                modEoCCLTAdminIPMask OBJECT-TYPE
                        SYNTAX IpAddress
                        MAX-ACCESS read-write
                        STATUS current
                        DESCRIPTION ""
                        ::= { modEoCCLTNetworkAttrGroup 4 }

                
                -- 1.3.6.1.4.1.17409.2.4.1.2.5
                modEoCCLTAdminIPGateway OBJECT-TYPE
                        SYNTAX IpAddress
                        MAX-ACCESS read-write
                        STATUS current
                        DESCRIPTION ""
                        ::= { modEoCCLTNetworkAttrGroup 5 }

                
                -- 1.3.6.1.4.1.17409.2.4.1.2.6
                modEoCCLTAdminEMSIPAddress OBJECT-TYPE
                        SYNTAX IpAddress
                        MAX-ACCESS read-write
                        STATUS current
                        DESCRIPTION ""
                        ::= { modEoCCLTNetworkAttrGroup 6 }

                
                -- 1.3.6.1.4.1.17409.2.4.1.3
                modEoCCLTDevStatusGroup OBJECT IDENTIFIER ::= { modEoCCLTAdminGroup 3 }

                
                -- 1.3.6.1.4.1.17409.2.4.1.3.1
                modEoCCLTAdminAlarmDetectionControl OBJECT-TYPE
                        SYNTAX INTEGER
                                {
                                detectionDisabled(1),
                                detectionEnabled(2),
                                detectionEnabledAndRegenerate(3)
                                }
                        MAX-ACCESS read-write
                        STATUS current
                        DESCRIPTION ""
                        ::= { modEoCCLTDevStatusGroup 1 }

                
                -- 1.3.6.1.4.1.17409.2.4.1.3.2
                modEoCCLTAdminStatus OBJECT-TYPE
                        SYNTAX OCTET STRING (SIZE (1))
                        MAX-ACCESS read-only
                        STATUS current
                        DESCRIPTION ""
                        ::= { modEoCCLTDevStatusGroup 2 }

                
                -- 1.3.6.1.4.1.17409.2.4.1.3.3
                modEoCCLTAdminInternalTemperature OBJECT-TYPE
                        SYNTAX INTEGER (-128..127)
                        UNITS "°C"
                        MAX-ACCESS read-only
                        STATUS current
                        DESCRIPTION ""
                        ::= { modEoCCLTDevStatusGroup 3 }

                
                -- 1.3.6.1.4.1.17409.2.4.1.3.4
                modEoCCLTAdminTamperStatus OBJECT-TYPE
                        SYNTAX INTEGER
                                {
                                intact(1),
                                compromised(2)
                                }
                        MAX-ACCESS read-only
                        STATUS current
                        DESCRIPTION ""
                        ::= { modEoCCLTDevStatusGroup 4 }

                
                -- 1.3.6.1.4.1.17409.2.4.1.3.5
                modEoCCLTAdminDateAndTime OBJECT-TYPE
                        SYNTAX TimeTicks
                        MAX-ACCESS read-write
                        STATUS current
                        DESCRIPTION ""
                        ::= { modEoCCLTDevStatusGroup 5 }

                
                -- 1.3.6.1.4.1.17409.2.4.1.3.6
                modEoCCLTAdminReset OBJECT-TYPE
                        SYNTAX INTEGER { reset(1) }
                        MAX-ACCESS read-write
                        STATUS current
                        DESCRIPTION ""
                        ::= { modEoCCLTDevStatusGroup 6 }

                
                -- 1.3.6.1.4.1.17409.2.4.1.3.7
                modEoCCLTAdminResetCause OBJECT-TYPE
                        SYNTAX INTEGER
                                {
                                other(1),
                                powerup(2),
                                command(3),
                                watchdog(4),
                                craft(5)
                                }
                        MAX-ACCESS read-only
                        STATUS current
                        DESCRIPTION ""
                        ::= { modEoCCLTDevStatusGroup 7 }

                
                -- 1.3.6.1.4.1.17409.2.4.1.3.8
                modEoCCLTAdminConfigurationSaving OBJECT-TYPE
                        SYNTAX INTEGER { save(1) }
                        MAX-ACCESS read-write
                        STATUS current
                        DESCRIPTION ""
                        ::= { modEoCCLTDevStatusGroup 8 }

                
                -- 1.3.6.1.4.1.17409.2.4.1.3.9
                modEoCCLTAdminConfigurationResult OBJECT-TYPE
                        SYNTAX INTEGER
                                {
                                none(0),
                                save(1),
                                failed(2)
                                }
                        MAX-ACCESS read-only
                        STATUS current
                        DESCRIPTION ""
                        ::= { modEoCCLTDevStatusGroup 9 }

                
                -- 1.3.6.1.4.1.17409.2.4.1.4
                modEoCCLTSNMPSettingGroup OBJECT IDENTIFIER ::= { modEoCCLTAdminGroup 4 }

                
                -- 1.3.6.1.4.1.17409.2.4.1.4.1
                modEoCCLTAdminVarBindings OBJECT-TYPE
                        SYNTAX INTEGER
                        MAX-ACCESS read-write
                        STATUS current
                        DESCRIPTION ""
                        ::= { modEoCCLTSNMPSettingGroup 1 }

                
                -- 1.3.6.1.4.1.17409.2.4.1.4.2
                modEoCCLTAdminSNMPVersion OBJECT-TYPE
                        SYNTAX INTEGER
                        MAX-ACCESS read-only
                        STATUS current
                        DESCRIPTION ""
                        ::= { modEoCCLTSNMPSettingGroup 2 }

                
                -- 1.3.6.1.4.1.17409.2.4.1.4.3
                modEoCCLTAdminSNMPCommunity OBJECT-TYPE
                        SYNTAX INTEGER
                        MAX-ACCESS read-only
                        STATUS current
                        DESCRIPTION ""
                        ::= { modEoCCLTSNMPSettingGroup 3 }

                
                -- 1.3.6.1.4.1.17409.2.4.1.5
                modEoCCLTOtherAdminGroup OBJECT IDENTIFIER ::= { modEoCCLTAdminGroup 5 }

                
                -- 1.3.6.1.4.1.17409.2.4.1.5.1
                modEoCCLTAdminLinkTopoChange OBJECT-TYPE
                        SYNTAX INTEGER
                                {
                                no-change(0),
                                change(1)
                                }
                        MAX-ACCESS read-only
                        STATUS current
                        DESCRIPTION ""
                        ::= { modEoCCLTOtherAdminGroup 1 }

                
                -- 1.3.6.1.4.1.17409.2.4.1.5.2
                modEoCCLTAdminAppropriativeOID OBJECT-TYPE
                        SYNTAX OBJECT IDENTIFIER
                        MAX-ACCESS read-write
                        STATUS current
                        DESCRIPTION ""
                        ::= { modEoCCLTOtherAdminGroup 2 }

                
                -- 1.3.6.1.4.1.17409.2.4.2
                modEoCMasterRFGroup OBJECT IDENTIFIER ::= { nscrtvEocTree 2 }

                
                -- 1.3.6.1.4.1.17409.2.4.2.1
                modEoCMasterRFTable OBJECT-TYPE
                        SYNTAX SEQUENCE OF ModEoCMasterRFEntry
                        MAX-ACCESS not-accessible
                        STATUS current
                        DESCRIPTION ""
                        ::= { modEoCMasterRFGroup 1 }

                
                -- 1.3.6.1.4.1.17409.2.4.2.1.1
                modEoCMasterRFEntry OBJECT-TYPE
                        SYNTAX ModEoCMasterRFEntry
                        MAX-ACCESS not-accessible
                        STATUS current
                        DESCRIPTION ""
                        INDEX { modEoCMasterRFIndex }
                        ::= { modEoCMasterRFTable 1 }

                
                ModEoCMasterRFEntry ::=
                        SEQUENCE { 
                                modEoCMasterRFIndex
                                        INTEGER,
                                modEoCMasterRFLinkMaximum
                                        INTEGER,
                                modEoCMasterRFMasterOutputLevel
                                        INTEGER,
                                modEoCMasterRFDownstreamStartFreq
                                        INTEGER,
                                modEoCMasterRFDownstreamStopFreq
                                        INTEGER,
                                modEoCMasterRFUpstreamStartFreq
                                        INTEGER,
                                modEoCMasterRFUpstreamStopFreq
                                        INTEGER
                         }

                -- 1.3.6.1.4.1.17409.2.4.2.1.1.1
                modEoCMasterRFIndex OBJECT-TYPE
                        SYNTAX INTEGER (0..20)
                        MAX-ACCESS read-only
                        STATUS current
                        DESCRIPTION ""
                        ::= { modEoCMasterRFEntry 1 }

                
                -- 1.3.6.1.4.1.17409.2.4.2.1.1.2
                modEoCMasterRFLinkMaximum OBJECT-TYPE
                        SYNTAX INTEGER (0..512)
                        MAX-ACCESS read-only
                        STATUS current
                        DESCRIPTION ""
                        ::= { modEoCMasterRFEntry 2 }

                
                -- 1.3.6.1.4.1.17409.2.4.2.1.1.3
                modEoCMasterRFMasterOutputLevel OBJECT-TYPE
                        SYNTAX INTEGER (103..129)
                        UNITS "dBuV"
                        MAX-ACCESS read-write
                        STATUS current
                        DESCRIPTION ""
                        ::= { modEoCMasterRFEntry 3 }

                
                -- 1.3.6.1.4.1.17409.2.4.2.1.1.4
                modEoCMasterRFDownstreamStartFreq OBJECT-TYPE
                        SYNTAX INTEGER (0..1000000000)
                        UNITS "kHz"
                        MAX-ACCESS read-only
                        STATUS current
                        DESCRIPTION ""
                        ::= { modEoCMasterRFEntry 4 }

                
                -- 1.3.6.1.4.1.17409.2.4.2.1.1.5
                modEoCMasterRFDownstreamStopFreq OBJECT-TYPE
                        SYNTAX INTEGER (0..1000000000)
                        UNITS "kHz"
                        MAX-ACCESS read-only
                        STATUS current
                        DESCRIPTION ""
                        ::= { modEoCMasterRFEntry 5 }

                
                -- 1.3.6.1.4.1.17409.2.4.2.1.1.6
                modEoCMasterRFUpstreamStartFreq OBJECT-TYPE
                        SYNTAX INTEGER (0..1000000000)
                        UNITS "kHz"
                        MAX-ACCESS read-only
                        STATUS current
                        DESCRIPTION ""
                        ::= { modEoCMasterRFEntry 6 }

                
                -- 1.3.6.1.4.1.17409.2.4.2.1.1.7
                modEoCMasterRFUpstreamStopFreq OBJECT-TYPE
                        SYNTAX INTEGER (0..1000000000)
                        UNITS "kHz"
                        MAX-ACCESS read-only
                        STATUS current
                        DESCRIPTION ""
                        ::= { modEoCMasterRFEntry 7 }

                
                -- 1.3.6.1.4.1.17409.2.4.3
                modEoCMasterMACGroup OBJECT IDENTIFIER ::= { nscrtvEocTree 3 }

                
                -- 1.3.6.1.4.1.17409.2.4.3.1
                modEoCMasterMACVlanTable OBJECT-TYPE
                        SYNTAX SEQUENCE OF ModEoCMasterMACVlanEntry
                        MAX-ACCESS not-accessible
                        STATUS current
                        DESCRIPTION ""
                        ::= { modEoCMasterMACGroup 1 }

                
                -- 1.3.6.1.4.1.17409.2.4.3.1.1
                modEoCMasterMACVlanEntry OBJECT-TYPE
                        SYNTAX ModEoCMasterMACVlanEntry
                        MAX-ACCESS not-accessible
                        STATUS current
                        DESCRIPTION ""
                        INDEX { modEoCMasterMACVlanIndex }
                        ::= { modEoCMasterMACVlanTable 1 }

                
                ModEoCMasterMACVlanEntry ::=
                        SEQUENCE { 
                                modEoCMasterMACVlanIndex
                                        INTEGER,
                                modEoCMasterMACVlanEN
                                        INTEGER,
                                modEoCMasterMACAdminVlanID
                                        INTEGER
                         }

                -- 1.3.6.1.4.1.17409.2.4.3.1.1.1
                modEoCMasterMACVlanIndex OBJECT-TYPE
                        SYNTAX INTEGER (0..20)
                        MAX-ACCESS read-only
                        STATUS current
                        DESCRIPTION ""
                        ::= { modEoCMasterMACVlanEntry 1 }

                
                -- 1.3.6.1.4.1.17409.2.4.3.1.1.2
                modEoCMasterMACVlanEN OBJECT-TYPE
                        SYNTAX INTEGER
                                {
                                disable(0),
                                enable(1)
                                }
                        MAX-ACCESS read-write
                        STATUS current
                        DESCRIPTION ""
                        ::= { modEoCMasterMACVlanEntry 2 }

                
                -- 1.3.6.1.4.1.17409.2.4.3.1.1.3
                modEoCMasterMACAdminVlanID OBJECT-TYPE
                        SYNTAX INTEGER (0..4095)
                        MAX-ACCESS read-write
                        STATUS current
                        DESCRIPTION ""
                        ::= { modEoCMasterMACVlanEntry 3 }

                
                -- 1.3.6.1.4.1.17409.2.4.3.2
                modEoCMasterMACBroadcastTable OBJECT-TYPE
                        SYNTAX SEQUENCE OF ModEoCMasterMACBroadcastEntry
                        MAX-ACCESS not-accessible
                        STATUS current
                        DESCRIPTION ""
                        ::= { modEoCMasterMACGroup 2 }

                
                -- 1.3.6.1.4.1.17409.2.4.3.2.1
                modEoCMasterMACBroadcastEntry OBJECT-TYPE
                        SYNTAX ModEoCMasterMACBroadcastEntry
                        MAX-ACCESS not-accessible
                        STATUS current
                        DESCRIPTION ""
                        INDEX { modEoCMasterMACBroadcastIndex }
                        ::= { modEoCMasterMACBroadcastTable 1 }

                
                ModEoCMasterMACBroadcastEntry ::=
                        SEQUENCE { 
                                modEoCMasterMACBroadcastIndex
                                        INTEGER,
                                modEoCMasterMACBroadcastRestrictionEN
                                        INTEGER,
                                modEoCMasterMACBroadcastRestriction
                                        INTEGER,
                                modEoCMasterMACUnknowRestrictionEN
                                        INTEGER,
                                modEoCMasterMACUnknowRestriction
                                        INTEGER
                         }

                -- 1.3.6.1.4.1.17409.2.4.3.2.1.1
                modEoCMasterMACBroadcastIndex OBJECT-TYPE
                        SYNTAX INTEGER (0..20)
                        MAX-ACCESS read-only
                        STATUS current
                        DESCRIPTION ""
                        ::= { modEoCMasterMACBroadcastEntry 1 }

                
                -- 1.3.6.1.4.1.17409.2.4.3.2.1.2
                modEoCMasterMACBroadcastRestrictionEN OBJECT-TYPE
                        SYNTAX INTEGER
                                {
                                disable(0),
                                enable(1)
                                }
                        MAX-ACCESS read-write
                        STATUS current
                        DESCRIPTION ""
                        ::= { modEoCMasterMACBroadcastEntry 2 }

                
                -- 1.3.6.1.4.1.17409.2.4.3.2.1.3
                modEoCMasterMACBroadcastRestriction OBJECT-TYPE
                        SYNTAX INTEGER
                        UNITS "kbps"
                        MAX-ACCESS read-write
                        STATUS current
                        DESCRIPTION ""
                        ::= { modEoCMasterMACBroadcastEntry 3 }

                
                -- 1.3.6.1.4.1.17409.2.4.3.2.1.4
                modEoCMasterMACUnknowRestrictionEN OBJECT-TYPE
                        SYNTAX INTEGER
                                {
                                disable(0),
                                enable(1)
                                }
                        MAX-ACCESS read-write
                        STATUS current
                        DESCRIPTION ""
                        ::= { modEoCMasterMACBroadcastEntry 4 }

                
                -- 1.3.6.1.4.1.17409.2.4.3.2.1.5
                modEoCMasterMACUnknowRestriction OBJECT-TYPE
                        SYNTAX INTEGER
                        UNITS "kbps"
                        MAX-ACCESS read-write
                        STATUS current
                        DESCRIPTION ""
                        ::= { modEoCMasterMACBroadcastEntry 5 }

                
                -- 1.3.6.1.4.1.17409.2.4.3.3
                modEoCMasterMACCNUIsolationTable OBJECT-TYPE
                        SYNTAX SEQUENCE OF ModEoCMasterMACCNUIsolationEntry
                        MAX-ACCESS not-accessible
                        STATUS current
                        DESCRIPTION ""
                        ::= { modEoCMasterMACGroup 3 }

                
                -- 1.3.6.1.4.1.17409.2.4.3.3.1
                modEoCMasterMACCNUIsolationEntry OBJECT-TYPE
                        SYNTAX ModEoCMasterMACCNUIsolationEntry
                        MAX-ACCESS not-accessible
                        STATUS current
                        DESCRIPTION ""
                        INDEX { modEoCMasterMACCNUIsolationIndex }
                        ::= { modEoCMasterMACCNUIsolationTable 1 }

                
                ModEoCMasterMACCNUIsolationEntry ::=
                        SEQUENCE { 
                                modEoCMasterMACCNUIsolationIndex
                                        INTEGER,
                                modEoCMasterMACCNUIsolationEN
                                        INTEGER
                         }

                -- 1.3.6.1.4.1.17409.2.4.3.3.1.1
                modEoCMasterMACCNUIsolationIndex OBJECT-TYPE
                        SYNTAX INTEGER (0..20)
                        MAX-ACCESS read-only
                        STATUS current
                        DESCRIPTION ""
                        ::= { modEoCMasterMACCNUIsolationEntry 1 }

                
                -- 1.3.6.1.4.1.17409.2.4.3.3.1.2
                modEoCMasterMACCNUIsolationEN OBJECT-TYPE
                        SYNTAX INTEGER
                                {
                                disable(0),
                                enable(1)
                                }
                        MAX-ACCESS read-write
                        STATUS current
                        DESCRIPTION ""
                        ::= { modEoCMasterMACCNUIsolationEntry 2 }

                
                -- 1.3.6.1.4.1.17409.2.4.3.4
                modEoCOnlineMasterTable OBJECT-TYPE
                        SYNTAX SEQUENCE OF ModEoCOnlineMasterEntry
                        MAX-ACCESS not-accessible
                        STATUS current
                        DESCRIPTION ""
                        ::= { modEoCMasterMACGroup 4 }

                
                -- 1.3.6.1.4.1.17409.2.4.3.4.1
                modEoCOnlineMasterEntry OBJECT-TYPE
                        SYNTAX ModEoCOnlineMasterEntry
                        MAX-ACCESS not-accessible
                        STATUS current
                        DESCRIPTION ""
                        INDEX { modOnlineMasterIndex }
                        ::= { modEoCOnlineMasterTable 1 }

                
                ModEoCOnlineMasterEntry ::=
                        SEQUENCE { 
                                modOnlineMasterIndex
                                        INTEGER,
                                modOnlineMasterMACAddress
                                        MacAddress,
                                modOnlineMasterModelNumber
                                        DisplayString,
                                modOnlineMasterSoftwareVersion
                                        DisplayString,
                                modOnlineMasterReset
                                        INTEGER,
                                modEoCCLTUpLinkBroadcastFrameSendIntervalBeforeAck
                                        INTEGER,
                                modEoCCLTUpLinkBroadcastFrameSendIntervalAfterAck
                                        INTEGER,
                                modOnlineMasterUpLinkDeviceMACAddress
                                        MacAddress,
                                modOnlineMasterUpLinkDevicePortNumber
                                        INTEGER,
                                modOnlineMasterConfigurationSaving
                                        INTEGER,
                                modOnlineMasterConfigurationResult
                                        INTEGER
                         }

                -- 1.3.6.1.4.1.17409.2.4.3.4.1.1
                modOnlineMasterIndex OBJECT-TYPE
                        SYNTAX INTEGER (0..20)
                        MAX-ACCESS read-only
                        STATUS current
                        DESCRIPTION ""
                        ::= { modEoCOnlineMasterEntry 1 }

                
                -- 1.3.6.1.4.1.17409.2.4.3.4.1.2
                modOnlineMasterMACAddress OBJECT-TYPE
                        SYNTAX MacAddress
                        MAX-ACCESS read-only
                        STATUS current
                        DESCRIPTION ""
                        ::= { modEoCOnlineMasterEntry 2 }

                
                -- 1.3.6.1.4.1.17409.2.4.3.4.1.3
                modOnlineMasterModelNumber OBJECT-TYPE
                        SYNTAX DisplayString (SIZE (0..255))
                        MAX-ACCESS read-only
                        STATUS current
                        DESCRIPTION ""
                        ::= { modEoCOnlineMasterEntry 3 }

                
                -- 1.3.6.1.4.1.17409.2.4.3.4.1.4
                modOnlineMasterSoftwareVersion OBJECT-TYPE
                        SYNTAX DisplayString (SIZE (0..255))
                        MAX-ACCESS read-only
                        STATUS current
                        DESCRIPTION ""
                        ::= { modEoCOnlineMasterEntry 4 }

                
                -- 1.3.6.1.4.1.17409.2.4.3.4.1.5
                modOnlineMasterReset OBJECT-TYPE
                        SYNTAX INTEGER { reset(1) }
                        MAX-ACCESS read-write
                        STATUS current
                        DESCRIPTION ""
                        ::= { modEoCOnlineMasterEntry 5 }

                
                -- 1.3.6.1.4.1.17409.2.4.3.4.1.6
                modEoCCLTUpLinkBroadcastFrameSendIntervalBeforeAck OBJECT-TYPE
                        SYNTAX INTEGER
                        UNITS "s"
                        MAX-ACCESS read-write
                        STATUS current
                        DESCRIPTION ""
                        ::= { modEoCOnlineMasterEntry 6 }

                
                -- 1.3.6.1.4.1.17409.2.4.3.4.1.7
                modEoCCLTUpLinkBroadcastFrameSendIntervalAfterAck OBJECT-TYPE
                        SYNTAX INTEGER
                        UNITS "s"
                        MAX-ACCESS read-write
                        STATUS current
                        DESCRIPTION ""
                        ::= { modEoCOnlineMasterEntry 7 }

                
                -- 1.3.6.1.4.1.17409.2.4.3.4.1.8
                modOnlineMasterUpLinkDeviceMACAddress OBJECT-TYPE
                        SYNTAX MacAddress
                        MAX-ACCESS read-write
                        STATUS current
                        DESCRIPTION ""
                        ::= { modEoCOnlineMasterEntry 8 }

                
                -- 1.3.6.1.4.1.17409.2.4.3.4.1.9
                modOnlineMasterUpLinkDevicePortNumber OBJECT-TYPE
                        SYNTAX INTEGER (0..65535)
                        MAX-ACCESS read-write
                        STATUS current
                        DESCRIPTION ""
                        ::= { modEoCOnlineMasterEntry 9 }

                
                -- 1.3.6.1.4.1.17409.2.4.3.4.1.10
                modOnlineMasterConfigurationSaving OBJECT-TYPE
                        SYNTAX INTEGER { save(1) }
                        MAX-ACCESS read-write
                        STATUS current
                        DESCRIPTION ""
                        ::= { modEoCOnlineMasterEntry 10 }

                
                -- 1.3.6.1.4.1.17409.2.4.3.4.1.11
                modOnlineMasterConfigurationResult OBJECT-TYPE
                        SYNTAX INTEGER
                                {
                                none(0),
                                save(1),
                                failed(2)
                                }
                        MAX-ACCESS read-only
                        STATUS current
                        DESCRIPTION ""
                        ::= { modEoCOnlineMasterEntry 11 }

                
                -- 1.3.6.1.4.1.17409.2.4.4
                modEoCSoftwareUpgradeGroup OBJECT IDENTIFIER ::= { nscrtvEocTree 4 }

                
                -- 1.3.6.1.4.1.17409.2.4.4.1
                modEoCSoftwaretUpgradeServerIP OBJECT-TYPE
                        SYNTAX IpAddress
                        MAX-ACCESS read-write
                        STATUS current
                        DESCRIPTION ""
                        ::= { modEoCSoftwareUpgradeGroup 1 }

                
                -- 1.3.6.1.4.1.17409.2.4.4.2
                modEoCSoftwareUpgradeServerPort OBJECT-TYPE
                        SYNTAX INTEGER (0..65535)
                        MAX-ACCESS read-write
                        STATUS current
                        DESCRIPTION ""
                        ::= { modEoCSoftwareUpgradeGroup 2 }

                
                -- 1.3.6.1.4.1.17409.2.4.4.3
                modEoCSoftwareUpgradeLogin OBJECT-TYPE
                        SYNTAX DisplayString (SIZE (1..255))
                        MAX-ACCESS read-write
                        STATUS current
                        DESCRIPTION ""
                        ::= { modEoCSoftwareUpgradeGroup 3 }

                
                -- 1.3.6.1.4.1.17409.2.4.4.4
                modEoCSoftwareUpgradePassWord OBJECT-TYPE
                        SYNTAX DisplayString (SIZE (1..255))
                        MAX-ACCESS read-write
                        STATUS current
                        DESCRIPTION ""
                        ::= { modEoCSoftwareUpgradeGroup 4 }

                
                -- 1.3.6.1.4.1.17409.2.4.4.5
                modEoCSoftwareUpgradeTable OBJECT-TYPE
                        SYNTAX SEQUENCE OF ModEoCSoftwareUpgradeEntry
                        MAX-ACCESS not-accessible
                        STATUS current
                        DESCRIPTION ""
                        ::= { modEoCSoftwareUpgradeGroup 5 }

                
                -- 1.3.6.1.4.1.17409.2.4.4.5.1
                modEoCSoftwareUpgradeEntry OBJECT-TYPE
                        SYNTAX ModEoCSoftwareUpgradeEntry
                        MAX-ACCESS not-accessible
                        STATUS current
                        DESCRIPTION ""
                        INDEX { modEoCSoftwareUpgradeMasterIndex, modEoCSoftwareUpgradeCNUIndex }
                        ::= { modEoCSoftwareUpgradeTable 1 }

                
                ModEoCSoftwareUpgradeEntry ::=
                        SEQUENCE { 
                                modEoCSoftwareUpgradeMasterIndex
                                        INTEGER,
                                modEoCSoftwareUpgradeCNUIndex
                                        INTEGER,
                                modEoCSoftwareUpgradeMACAddress
                                        MacAddress,
                                modEoCSoftwareUpgradeDevType
                                        INTEGER,
                                modEoCSoftwareUpgradeFileName
                                        OCTET STRING,
                                modEoCSoftwareUpgradeProceed
                                        INTEGER,
                                modEoCSoftwareUpgradeResult
                                        INTEGER
                         }

                -- 1.3.6.1.4.1.17409.2.4.4.5.1.1
                modEoCSoftwareUpgradeMasterIndex OBJECT-TYPE
                        SYNTAX INTEGER (0..20)
                        MAX-ACCESS read-only
                        STATUS current
                        DESCRIPTION ""
                        ::= { modEoCSoftwareUpgradeEntry 1 }

                
                -- 1.3.6.1.4.1.17409.2.4.4.5.1.2
                modEoCSoftwareUpgradeCNUIndex OBJECT-TYPE
                        SYNTAX INTEGER (0..10240)
                        MAX-ACCESS read-only
                        STATUS current
                        DESCRIPTION ""
                        ::= { modEoCSoftwareUpgradeEntry 2 }

                
                -- 1.3.6.1.4.1.17409.2.4.4.5.1.3
                modEoCSoftwareUpgradeMACAddress OBJECT-TYPE
                        SYNTAX MacAddress
                        MAX-ACCESS read-write
                        STATUS current
                        DESCRIPTION ""
                        ::= { modEoCSoftwareUpgradeEntry 3 }

                
                -- 1.3.6.1.4.1.17409.2.4.4.5.1.4
                modEoCSoftwareUpgradeDevType OBJECT-TYPE
                        SYNTAX INTEGER
                                {
                                clt(1),
                                master(2),
                                cnu(3),
                                other(4)
                                }
                        MAX-ACCESS read-write
                        STATUS current
                        DESCRIPTION ""
                        ::= { modEoCSoftwareUpgradeEntry 4 }

                
                -- 1.3.6.1.4.1.17409.2.4.4.5.1.5
                modEoCSoftwareUpgradeFileName OBJECT-TYPE
                        SYNTAX OCTET STRING (SIZE (1..255))
                        MAX-ACCESS read-write
                        STATUS current
                        DESCRIPTION ""
                        ::= { modEoCSoftwareUpgradeEntry 5 }

                
                -- 1.3.6.1.4.1.17409.2.4.4.5.1.6
                modEoCSoftwareUpgradeProceed OBJECT-TYPE
                        SYNTAX INTEGER
                                {
                                download(1),
                                upload(2),
                                update(3)
                                }
                        MAX-ACCESS read-write
                        STATUS current
                        DESCRIPTION ""
                        ::= { modEoCSoftwareUpgradeEntry 6 }

                
                -- 1.3.6.1.4.1.17409.2.4.4.5.1.7
                modEoCSoftwareUpgradeResult OBJECT-TYPE
                        SYNTAX INTEGER
                                {
                                none(0),
                                running(1),
                                successful(2),
                                failed(3)
                                }
                        MAX-ACCESS read-only
                        STATUS current
                        DESCRIPTION ""
                        ::= { modEoCSoftwareUpgradeEntry 7 }

                
                -- 1.3.6.1.4.1.17409.2.4.5
                modEoCCNUGroup OBJECT IDENTIFIER ::= { nscrtvEocTree 5 }

                
                -- 1.3.6.1.4.1.17409.2.4.5.1
                modEoCCNUWhiteList OBJECT IDENTIFIER ::= { modEoCCNUGroup 1 }

                
                -- 1.3.6.1.4.1.17409.2.4.5.1.1
                modEoCCNUWhiteListAmountLimitation OBJECT-TYPE
                        SYNTAX INTEGER (0..10240)
                        MAX-ACCESS read-write
                        STATUS current
                        DESCRIPTION ""
                        ::= { modEoCCNUWhiteList 1 }

                
                -- 1.3.6.1.4.1.17409.2.4.5.1.2
                modEoCCNUWhiteListRegisteredAmount OBJECT-TYPE
                        SYNTAX INTEGER (0..10240)
                        MAX-ACCESS read-only
                        STATUS current
                        DESCRIPTION ""
                        ::= { modEoCCNUWhiteList 2 }

                
                -- 1.3.6.1.4.1.17409.2.4.5.1.3
                modEoCCNUWhiteListAllRFOutputLevel OBJECT-TYPE
                        SYNTAX INTEGER (103..129)
                        UNITS "dBuv"
                        MAX-ACCESS read-write
                        STATUS current
                        DESCRIPTION ""
                        ::= { modEoCCNUWhiteList 3 }

                
                -- 1.3.6.1.4.1.17409.2.4.5.1.4
                modEoCCNUWhiteListAllExtMACLimitation OBJECT-TYPE
                        SYNTAX INTEGER
                        MAX-ACCESS read-write
                        STATUS current
                        DESCRIPTION ""
                        ::= { modEoCCNUWhiteList 4 }

                
                -- 1.3.6.1.4.1.17409.2.4.5.1.5
                modEoCCNUWhiteListPhyRateGate OBJECT-TYPE
                        SYNTAX INTEGER
                        UNITS "Mbps"
                        MAX-ACCESS read-write
                        STATUS current
                        DESCRIPTION ""
                        ::= { modEoCCNUWhiteList 5 }

                
                -- 1.3.6.1.4.1.17409.2.4.5.1.6
                modEoCCNUWhiteListTable OBJECT-TYPE
                        SYNTAX SEQUENCE OF ModEoCCNUWhiteListEntry
                        MAX-ACCESS not-accessible
                        STATUS current
                        DESCRIPTION ""
                        ::= { modEoCCNUWhiteList 6 }

                
                -- 1.3.6.1.4.1.17409.2.4.5.1.6.1
                modEoCCNUWhiteListEntry OBJECT-TYPE
                        SYNTAX ModEoCCNUWhiteListEntry
                        MAX-ACCESS not-accessible
                        STATUS current
                        DESCRIPTION ""
                        INDEX { modEoCCNUWhiteListIndex }
                        ::= { modEoCCNUWhiteListTable 1 }

                
                ModEoCCNUWhiteListEntry ::=
                        SEQUENCE { 
                                modEoCCNUWhiteListIndex
                                        INTEGER,
                                modEoCCNUWhiteListMACAddress
                                        MacAddress,
                                modEoCCNUWhiteListAuthorization
                                        INTEGER,
                                modEoCCNUWhiteListRFOutputLevel
                                        INTEGER,
                                modEoCCNUWhiteListAutoUpgradeEN
                                        INTEGER,
                                modEoCCNUWhiteListRegisterOnlineState
                                        INTEGER,
                                modEoCCNUWhiteListStartTime
                                        TimeTicks,
                                modEoCCNUWhiteListEndTime
                                        TimeTicks,
                                modEoCCNUWhiteListRowStatus
                                        RowStatus
                         }

                -- 1.3.6.1.4.1.17409.2.4.5.1.6.1.1
                modEoCCNUWhiteListIndex OBJECT-TYPE
                        SYNTAX INTEGER (0..10240)
                        MAX-ACCESS read-only
                        STATUS current
                        DESCRIPTION ""
                        ::= { modEoCCNUWhiteListEntry 1 }

                
                -- 1.3.6.1.4.1.17409.2.4.5.1.6.1.2
                modEoCCNUWhiteListMACAddress OBJECT-TYPE
                        SYNTAX MacAddress
                        MAX-ACCESS read-write
                        STATUS current
                        DESCRIPTION ""
                        ::= { modEoCCNUWhiteListEntry 2 }

                
                -- 1.3.6.1.4.1.17409.2.4.5.1.6.1.3
                modEoCCNUWhiteListAuthorization OBJECT-TYPE
                        SYNTAX INTEGER
                                {
                                not-authorized(0),
                                authorized(1)
                                }
                        MAX-ACCESS read-write
                        STATUS current
                        DESCRIPTION ""
                        ::= { modEoCCNUWhiteListEntry 3 }

                
                -- 1.3.6.1.4.1.17409.2.4.5.1.6.1.4
                modEoCCNUWhiteListRFOutputLevel OBJECT-TYPE
                        SYNTAX INTEGER (103..129)
                        UNITS "dBuV"
                        MAX-ACCESS read-write
                        STATUS current
                        DESCRIPTION ""
                        ::= { modEoCCNUWhiteListEntry 4 }

                
                -- 1.3.6.1.4.1.17409.2.4.5.1.6.1.5
                modEoCCNUWhiteListAutoUpgradeEN OBJECT-TYPE
                        SYNTAX INTEGER
                                {
                                disable(0),
                                enable(1)
                                }
                        MAX-ACCESS read-write
                        STATUS current
                        DESCRIPTION ""
                        ::= { modEoCCNUWhiteListEntry 5 }

                
                -- 1.3.6.1.4.1.17409.2.4.5.1.6.1.6
                modEoCCNUWhiteListRegisterOnlineState OBJECT-TYPE
                        SYNTAX INTEGER
                                {
                                offline(0),
                                online(1)
                                }
                        MAX-ACCESS read-only
                        STATUS current
                        DESCRIPTION ""
                        ::= { modEoCCNUWhiteListEntry 6 }

                
                -- 1.3.6.1.4.1.17409.2.4.5.1.6.1.7
                modEoCCNUWhiteListStartTime OBJECT-TYPE
                        SYNTAX TimeTicks
                        MAX-ACCESS read-write
                        STATUS current
                        DESCRIPTION ""
                        ::= { modEoCCNUWhiteListEntry 7 }

                
                -- 1.3.6.1.4.1.17409.2.4.5.1.6.1.8
                modEoCCNUWhiteListEndTime OBJECT-TYPE
                        SYNTAX TimeTicks
                        MAX-ACCESS read-write
                        STATUS current
                        DESCRIPTION ""
                        ::= { modEoCCNUWhiteListEntry 8 }

                
                -- 1.3.6.1.4.1.17409.2.4.5.1.6.1.9
                modEoCCNUWhiteListRowStatus OBJECT-TYPE
                        SYNTAX RowStatus
                        MAX-ACCESS read-create
                        STATUS current
                        DESCRIPTION ""
                        ::= { modEoCCNUWhiteListEntry 9 }

                
                -- 1.3.6.1.4.1.17409.2.4.5.2
                modEoCCNUOnline OBJECT IDENTIFIER ::= { modEoCCNUGroup 2 }

                
                -- 1.3.6.1.4.1.17409.2.4.5.2.1
                modEoCCNUOnlineAllReset OBJECT-TYPE
                        SYNTAX INTEGER { reset(1) }
                        MAX-ACCESS read-write
                        STATUS current
                        DESCRIPTION ""
                        ::= { modEoCCNUOnline 1 }

                
                -- 1.3.6.1.4.1.17409.2.4.5.2.2
                modEoCCNUOnlineCurrentAmount OBJECT-TYPE
                        SYNTAX INTEGER (0..10240)
                        MAX-ACCESS read-only
                        STATUS current
                        DESCRIPTION ""
                        ::= { modEoCCNUOnline 2 }

                
                -- 1.3.6.1.4.1.17409.2.4.5.2.3
                modEoCCNUOnlineAmountLimitation OBJECT-TYPE
                        SYNTAX INTEGER (0..10240)
                        MAX-ACCESS read-write
                        STATUS current
                        DESCRIPTION ""
                        ::= { modEoCCNUOnline 3 }

                
                -- 1.3.6.1.4.1.17409.2.4.5.2.4
                modEoCCNUOnlineTable OBJECT-TYPE
                        SYNTAX SEQUENCE OF ModEoCCNUOnlineEntry
                        MAX-ACCESS not-accessible
                        STATUS current
                        DESCRIPTION ""
                        ::= { modEoCCNUOnline 4 }

                
                -- 1.3.6.1.4.1.17409.2.4.5.2.4.1
                modEoCCNUOnlineEntry OBJECT-TYPE
                        SYNTAX ModEoCCNUOnlineEntry
                        MAX-ACCESS not-accessible
                        STATUS current
                        DESCRIPTION ""
                        INDEX { modEoCCNUOnlineMasterIndex, modEoCCNUOnlineIndex }
                        ::= { modEoCCNUOnlineTable 1 }

                
                ModEoCCNUOnlineEntry ::=
                        SEQUENCE { 
                                modEoCCNUOnlineMasterIndex
                                        INTEGER,
                                modEoCCNUOnlineIndex
                                        INTEGER,
                                modEoCCNUOnlineMACAddress
                                        MacAddress,
                                modEoCCNUOnlineModelNumber
                                        DisplayString,
                                modEoCCNUOnlinePortAmount
                                        INTEGER,
                                modEoCCNUOnlineAuthorizationState
                                        INTEGER,
                                modEoCCNUOnlineSoftwareVersion
                                        DisplayString,
                                modEoCCNUOnlineReset
                                        INTEGER,
                                modEoCCNUOnlineRFDownstreamAttenuation
                                        INTEGER,
                                modEoCCNUOnlineRFUpstreamAttenuation
                                        INTEGER,
                                modEoCCNUOnlineRFDownstreamQuality
                                        INTEGER,
                                modEoCCNUOnlineRFUpstreamQuality
                                        INTEGER,
                                modEoCCNUOnlinePhyDownstreamRate
                                        INTEGER,
                                modEoCCNUOnlinePhyUpstreamRate
                                        INTEGER,
                                modCNUOnlineConfigurationSaving
                                        INTEGER,
                                modCNUOnlineConfigurationResult
                                        INTEGER
                         }

                -- 1.3.6.1.4.1.17409.2.4.5.2.4.1.1
                modEoCCNUOnlineMasterIndex OBJECT-TYPE
                        SYNTAX INTEGER (0..20)
                        MAX-ACCESS read-only
                        STATUS current
                        DESCRIPTION ""
                        ::= { modEoCCNUOnlineEntry 1 }

                
                -- 1.3.6.1.4.1.17409.2.4.5.2.4.1.2
                modEoCCNUOnlineIndex OBJECT-TYPE
                        SYNTAX INTEGER (0..10240)
                        MAX-ACCESS read-only
                        STATUS current
                        DESCRIPTION ""
                        ::= { modEoCCNUOnlineEntry 2 }

                
                -- 1.3.6.1.4.1.17409.2.4.5.2.4.1.3
                modEoCCNUOnlineMACAddress OBJECT-TYPE
                        SYNTAX MacAddress
                        MAX-ACCESS read-only
                        STATUS current
                        DESCRIPTION ""
                        ::= { modEoCCNUOnlineEntry 3 }

                
                -- 1.3.6.1.4.1.17409.2.4.5.2.4.1.4
                modEoCCNUOnlineModelNumber OBJECT-TYPE
                        SYNTAX DisplayString (SIZE (0..255))
                        MAX-ACCESS read-only
                        STATUS current
                        DESCRIPTION ""
                        ::= { modEoCCNUOnlineEntry 4 }

                
                -- 1.3.6.1.4.1.17409.2.4.5.2.4.1.5
                modEoCCNUOnlinePortAmount OBJECT-TYPE
                        SYNTAX INTEGER
                        MAX-ACCESS read-only
                        STATUS current
                        DESCRIPTION ""
                        ::= { modEoCCNUOnlineEntry 5 }

                
                -- 1.3.6.1.4.1.17409.2.4.5.2.4.1.6
                modEoCCNUOnlineAuthorizationState OBJECT-TYPE
                        SYNTAX INTEGER
                                {
                                not-authorized(0),
                                authorized(1)
                                }
                        MAX-ACCESS read-only
                        STATUS current
                        DESCRIPTION ""
                        ::= { modEoCCNUOnlineEntry 6 }

                
                -- 1.3.6.1.4.1.17409.2.4.5.2.4.1.7
                modEoCCNUOnlineSoftwareVersion OBJECT-TYPE
                        SYNTAX DisplayString (SIZE (0..255))
                        MAX-ACCESS read-only
                        STATUS current
                        DESCRIPTION ""
                        ::= { modEoCCNUOnlineEntry 7 }

                
                -- 1.3.6.1.4.1.17409.2.4.5.2.4.1.8
                modEoCCNUOnlineReset OBJECT-TYPE
                        SYNTAX INTEGER { reset(1) }
                        MAX-ACCESS read-write
                        STATUS current
                        DESCRIPTION ""
                        ::= { modEoCCNUOnlineEntry 8 }

                
                -- 1.3.6.1.4.1.17409.2.4.5.2.4.1.9
                modEoCCNUOnlineRFDownstreamAttenuation OBJECT-TYPE
                        SYNTAX INTEGER (0..127)
                        UNITS "dB"
                        MAX-ACCESS read-only
                        STATUS current
                        DESCRIPTION ""
                        ::= { modEoCCNUOnlineEntry 9 }

                
                -- 1.3.6.1.4.1.17409.2.4.5.2.4.1.10
                modEoCCNUOnlineRFUpstreamAttenuation OBJECT-TYPE
                        SYNTAX INTEGER (0..127)
                        UNITS "dB"
                        MAX-ACCESS read-only
                        STATUS current
                        DESCRIPTION ""
                        ::= { modEoCCNUOnlineEntry 10 }

                
                -- 1.3.6.1.4.1.17409.2.4.5.2.4.1.11
                modEoCCNUOnlineRFDownstreamQuality OBJECT-TYPE
                        SYNTAX INTEGER (0..100)
                        MAX-ACCESS read-only
                        STATUS current
                        DESCRIPTION ""
                        ::= { modEoCCNUOnlineEntry 11 }

                
                -- 1.3.6.1.4.1.17409.2.4.5.2.4.1.12
                modEoCCNUOnlineRFUpstreamQuality OBJECT-TYPE
                        SYNTAX INTEGER (0..100)
                        MAX-ACCESS read-only
                        STATUS current
                        DESCRIPTION ""
                        ::= { modEoCCNUOnlineEntry 12 }

                
                -- 1.3.6.1.4.1.17409.2.4.5.2.4.1.13
                modEoCCNUOnlinePhyDownstreamRate OBJECT-TYPE
                        SYNTAX INTEGER
                        UNITS "Mbps"
                        MAX-ACCESS read-only
                        STATUS current
                        DESCRIPTION ""
                        ::= { modEoCCNUOnlineEntry 13 }

                
                -- 1.3.6.1.4.1.17409.2.4.5.2.4.1.14
                modEoCCNUOnlinePhyUpstreamRate OBJECT-TYPE
                        SYNTAX INTEGER
                        UNITS "Mbps"
                        MAX-ACCESS read-only
                        STATUS current
                        DESCRIPTION ""
                        ::= { modEoCCNUOnlineEntry 14 }

                
                -- 1.3.6.1.4.1.17409.2.4.5.2.4.1.15
                modCNUOnlineConfigurationSaving OBJECT-TYPE
                        SYNTAX INTEGER { save(1) }
                        MAX-ACCESS read-write
                        STATUS current
                        DESCRIPTION ""
                        ::= { modEoCCNUOnlineEntry 15 }

                
                -- 1.3.6.1.4.1.17409.2.4.5.2.4.1.16
                modCNUOnlineConfigurationResult OBJECT-TYPE
                        SYNTAX INTEGER
                                {
                                none(0),
                                save(1),
                                failed(2)
                                }
                        MAX-ACCESS read-only
                        STATUS current
                        DESCRIPTION ""
                        ::= { modEoCCNUOnlineEntry 16 }

                
                -- 1.3.6.1.4.1.17409.2.4.5.3
                modEoCCNUService OBJECT IDENTIFIER ::= { modEoCCNUGroup 3 }

                
                -- 1.3.6.1.4.1.17409.2.4.5.3.1
                modEoCCNUServiceType OBJECT-TYPE
                        SYNTAX INTEGER
                        		{
                        		none(0),
                        		svcvid(1),
                        		svcprio(2),
                        		svctos(3),
                        		svcnb(4)
                        		}
                        MAX-ACCESS read-write
                        STATUS current
                        DESCRIPTION ""
                        ::= { modEoCCNUService 1 }

                
                -- 1.3.6.1.4.1.17409.2.4.5.3.2
                modEoCCNUServiceAmountLimitation OBJECT-TYPE
                        SYNTAX INTEGER
                        MAX-ACCESS read-write
                        STATUS current
                        DESCRIPTION ""
                        ::= { modEoCCNUService 2 }

                
                -- 1.3.6.1.4.1.17409.2.4.5.3.3
                modEoCCNUServiceTable OBJECT-TYPE
                        SYNTAX SEQUENCE OF ModEoCCNUServiceEntry
                        MAX-ACCESS not-accessible
                        STATUS current
                        DESCRIPTION ""
                        ::= { modEoCCNUService 3 }

                
                -- 1.3.6.1.4.1.17409.2.4.5.3.3.1
                modEoCCNUServiceEntry OBJECT-TYPE
                        SYNTAX ModEoCCNUServiceEntry
                        MAX-ACCESS not-accessible
                        STATUS current
                        DESCRIPTION ""
                        INDEX { modEoCCNUServiceIndex }
                        ::= { modEoCCNUServiceTable 1 }

                
                ModEoCCNUServiceEntry ::=
                        SEQUENCE { 
                                modEoCCNUServiceIndex
                                        INTEGER,
                                modEoCCNUServiceName
                                        DisplayString,
                                modEoCCNUServiceMatchingValue
                                        INTEGER,
                                modEoCCNUServiceQOSPrio
                                        INTEGER,
                                modEoCCNUServiceDBADownstreamPIR
                                        INTEGER,
                                modEoCCNUServiceDBAUpstreamPIR
                                        INTEGER,
                                modEoCCNUServiceDBADownstreamCIR
                                        INTEGER,
                                modEoCCNUServiceDBAUpstreamCIR
                                        INTEGER,
                                modEoCCNUServiceMaxLatency
                                        INTEGER,
                                modEoCCNUServiceRowStatus
                                        RowStatus
                         }

                -- 1.3.6.1.4.1.17409.2.4.5.3.3.1.1
                modEoCCNUServiceIndex OBJECT-TYPE
                        SYNTAX INTEGER (1..255)
                        MAX-ACCESS read-only
                        STATUS current
                        DESCRIPTION ""
                        ::= { modEoCCNUServiceEntry 1 }

                
                -- 1.3.6.1.4.1.17409.2.4.5.3.3.1.2
                modEoCCNUServiceName OBJECT-TYPE
                        SYNTAX DisplayString (SIZE (0..255))
                        MAX-ACCESS read-write
                        STATUS current
                        DESCRIPTION ""
                        ::= { modEoCCNUServiceEntry 2 }

                
                -- 1.3.6.1.4.1.17409.2.4.5.3.3.1.3
                modEoCCNUServiceMatchingValue OBJECT-TYPE
                        SYNTAX INTEGER
                        MAX-ACCESS read-write
                        STATUS current
                        DESCRIPTION ""
                        ::= { modEoCCNUServiceEntry 3 }

                
                -- 1.3.6.1.4.1.17409.2.4.5.3.3.1.4
                modEoCCNUServiceQOSPrio OBJECT-TYPE
                        SYNTAX INTEGER (0..7)
                        MAX-ACCESS read-write
                        STATUS current
                        DESCRIPTION ""
                        ::= { modEoCCNUServiceEntry 4 }

                
                -- 1.3.6.1.4.1.17409.2.4.5.3.3.1.5
                modEoCCNUServiceDBADownstreamPIR OBJECT-TYPE
                        SYNTAX INTEGER
                        UNITS "kbps"
                        MAX-ACCESS read-write
                        STATUS current
                        DESCRIPTION ""
                        ::= { modEoCCNUServiceEntry 5 }

                
                -- 1.3.6.1.4.1.17409.2.4.5.3.3.1.6
                modEoCCNUServiceDBAUpstreamPIR OBJECT-TYPE
                        SYNTAX INTEGER
                        UNITS "kbps"
                        MAX-ACCESS read-write
                        STATUS current
                        DESCRIPTION ""
                        ::= { modEoCCNUServiceEntry 6 }

                
                -- 1.3.6.1.4.1.17409.2.4.5.3.3.1.7
                modEoCCNUServiceDBADownstreamCIR OBJECT-TYPE
                        SYNTAX INTEGER
                        UNITS "kbps"
                        MAX-ACCESS read-write
                        STATUS current
                        DESCRIPTION ""
                        ::= { modEoCCNUServiceEntry 7 }

                
                -- 1.3.6.1.4.1.17409.2.4.5.3.3.1.8
                modEoCCNUServiceDBAUpstreamCIR OBJECT-TYPE
                        SYNTAX INTEGER
                        UNITS "kbps"
                        MAX-ACCESS read-write
                        STATUS current
                        DESCRIPTION ""
                        ::= { modEoCCNUServiceEntry 8 }

                
                -- 1.3.6.1.4.1.17409.2.4.5.3.3.1.9
                modEoCCNUServiceMaxLatency OBJECT-TYPE
                        SYNTAX INTEGER
                        MAX-ACCESS read-write
                        STATUS current
                        DESCRIPTION ""
                        ::= { modEoCCNUServiceEntry 9 }

                
                -- 1.3.6.1.4.1.17409.2.4.5.3.3.1.10
                modEoCCNUServiceRowStatus OBJECT-TYPE
                        SYNTAX RowStatus
                        MAX-ACCESS read-create
                        STATUS current
                        DESCRIPTION ""
                        ::= { modEoCCNUServiceEntry 10 }

                
                -- 1.3.6.1.4.1.17409.2.4.5.4
                modEoCCNUPort OBJECT IDENTIFIER ::= { modEoCCNUGroup 4 }

                
                -- 1.3.6.1.4.1.17409.2.4.5.4.1
                modEoCCNUPortPerCNULimitation OBJECT-TYPE
                        SYNTAX INTEGER
                        MAX-ACCESS read-write
                        STATUS current
                        DESCRIPTION ""
                        ::= { modEoCCNUPort 1 }

                
                -- 1.3.6.1.4.1.17409.2.4.5.4.2
                modEoCCNUPortAmountLimitation OBJECT-TYPE
                        SYNTAX INTEGER
                        MAX-ACCESS read-write
                        STATUS current
                        DESCRIPTION ""
                        ::= { modEoCCNUPort 2 }

                
                -- 1.3.6.1.4.1.17409.2.4.5.4.3
                modEoCCNUPortTable OBJECT-TYPE
                        SYNTAX SEQUENCE OF ModEoCCNUPortEntry
                        MAX-ACCESS not-accessible
                        STATUS current
                        DESCRIPTION ""
                        ::= { modEoCCNUPort 3 }

                
                -- 1.3.6.1.4.1.17409.2.4.5.4.3.1
                modEoCCNUPortEntry OBJECT-TYPE
                        SYNTAX ModEoCCNUPortEntry
                        MAX-ACCESS not-accessible
                        STATUS current
                        DESCRIPTION ""
                        INDEX { modEoCCNUPortMasterIndex, modEoCCNUPortCNUIndex, modEoCCNUPortIndex }
                        ::= { modEoCCNUPortTable 1 }

                
                ModEoCCNUPortEntry ::=
                        SEQUENCE { 
                                modEoCCNUPortMasterIndex
                                        INTEGER,
                                modEoCCNUPortCNUIndex
                                        INTEGER,
                                modEoCCNUPortIndex
                                        INTEGER,
                                modEoCCNUPortEN
                                        INTEGER,
                                modEoCCNUPortService
                                        INTEGER,
                                modEoCCNUPortVLANTagEN
                                        INTEGER,
                                modEoCCNUPortVLANMarkID
                                        INTEGER
                         }

                -- 1.3.6.1.4.1.17409.2.4.5.4.3.1.1
                modEoCCNUPortMasterIndex OBJECT-TYPE
                        SYNTAX INTEGER (0..20)
                        MAX-ACCESS read-only
                        STATUS current
                        DESCRIPTION ""
                        ::= { modEoCCNUPortEntry 1 }

                
                -- 1.3.6.1.4.1.17409.2.4.5.4.3.1.2
                modEoCCNUPortCNUIndex OBJECT-TYPE
                        SYNTAX INTEGER (0..10240)
                        MAX-ACCESS read-only
                        STATUS current
                        DESCRIPTION ""
                        ::= { modEoCCNUPortEntry 2 }

                
                -- 1.3.6.1.4.1.17409.2.4.5.4.3.1.3
                modEoCCNUPortIndex OBJECT-TYPE
                        SYNTAX INTEGER
                        MAX-ACCESS read-only
                        STATUS current
                        DESCRIPTION ""
                        ::= { modEoCCNUPortEntry 3 }

                
                -- 1.3.6.1.4.1.17409.2.4.5.4.3.1.4
                modEoCCNUPortEN OBJECT-TYPE
                        SYNTAX INTEGER
                                {
                                disable(0),
                                enable(1)
                                }
                        MAX-ACCESS read-write
                        STATUS current
                        DESCRIPTION ""
                        ::= { modEoCCNUPortEntry 4 }

                
                -- 1.3.6.1.4.1.17409.2.4.5.4.3.1.5
                modEoCCNUPortService OBJECT-TYPE
                        SYNTAX INTEGER
                        MAX-ACCESS read-write
                        STATUS current
                        DESCRIPTION ""
                        ::= { modEoCCNUPortEntry 5 }

                
                -- 1.3.6.1.4.1.17409.2.4.5.4.3.1.6
                modEoCCNUPortVLANTagEN OBJECT-TYPE
                        SYNTAX INTEGER
                                {
                                disable(0),
                                enable(1)
                                }
                        MAX-ACCESS read-write
                        STATUS current
                        DESCRIPTION ""
                        ::= { modEoCCNUPortEntry 6 }

                
                -- 1.3.6.1.4.1.17409.2.4.5.4.3.1.7
                modEoCCNUPortVLANMarkID OBJECT-TYPE
                        SYNTAX INTEGER (0..4095)
                        MAX-ACCESS read-write
                        STATUS current
                        DESCRIPTION ""
                        ::= { modEoCCNUPortEntry 7 }

                
                -- 1.3.6.1.4.1.17409.2.4.6
                modEoCStatisticGroup OBJECT IDENTIFIER ::= { nscrtvEocTree 6 }

                
                -- 1.3.6.1.4.1.17409.2.4.6.1
                modEoCCNURealTimeStatisticTable OBJECT-TYPE
                        SYNTAX SEQUENCE OF ModEoCCNURealTimeStatisticEntry
                        MAX-ACCESS not-accessible
                        STATUS current
                        DESCRIPTION ""
                        ::= { modEoCStatisticGroup 1 }

                
                -- 1.3.6.1.4.1.17409.2.4.6.1.1
                modEoCCNURealTimeStatisticEntry OBJECT-TYPE
                        SYNTAX ModEoCCNURealTimeStatisticEntry
                        MAX-ACCESS not-accessible
                        STATUS current
                        DESCRIPTION ""
                        INDEX { modEoCCNURealTimeStatisticMasterIndex, modEoCCNURealTimeStatisticCNUIndex }
                        ::= { modEoCCNURealTimeStatisticTable 1 }

                
                ModEoCCNURealTimeStatisticEntry ::=
                        SEQUENCE { 
                                modEoCCNURealTimeStatisticMasterIndex
                                        INTEGER,
                                modEoCCNURealTimeStatisticCNUIndex
                                        INTEGER,
                                modEoCCNURealTimeStatisticTxPkt
                                        Counter32,
                                modEoCCNURealTimeStatisticRxPkt
                                        Counter32,
                                modEoCCNURealTimeStatisticTxByte
                                        Counter64,
                                modEoCCNURealTimeStatisticRxByte
                                        Counter64,
                                modEoCCNURealTimeStatisticTxBcast
                                        Counter32,
                                modEoCCNURealTimeStatisticRxBcast
                                        Counter32,
                                modEoCCNURealTimeStatisticTxMcast
                                        Counter32,
                                modEoCCNURealTimeStatisticRxMcast
                                        Counter32,
                                modEoCCNURealTimeStatisticRxCrc
                                        Counter32,
                                modEoCCNURealTimeStatisticTxShort
                                        Counter32,
                                modEoCCNURealTimeStatisticRxShort
                                        Counter32,
                                modEoCCNURealTimeStatisticTxDropped
                                        Counter32,
                                modEoCCNURealTimeStatisticRxDropped
                                        Counter32,
                                modEoCCNURealTimeStatisticAveragePre-FEC
                                        Counter32,
                                modEoCCNURealTimeStatisticReset
                                        INTEGER
                         }

                -- 1.3.6.1.4.1.17409.2.4.6.1.1.1
                modEoCCNURealTimeStatisticMasterIndex OBJECT-TYPE
                        SYNTAX INTEGER (0..20)
                        MAX-ACCESS read-only
                        STATUS current
                        DESCRIPTION ""
                        ::= { modEoCCNURealTimeStatisticEntry 1 }

                
                -- 1.3.6.1.4.1.17409.2.4.6.1.1.2
                modEoCCNURealTimeStatisticCNUIndex OBJECT-TYPE
                        SYNTAX INTEGER (0..10240)
                        MAX-ACCESS read-only
                        STATUS current
                        DESCRIPTION ""
                        ::= { modEoCCNURealTimeStatisticEntry 2 }

                
                -- 1.3.6.1.4.1.17409.2.4.6.1.1.3
                modEoCCNURealTimeStatisticTxPkt OBJECT-TYPE
                        SYNTAX Counter32
                        MAX-ACCESS read-only
                        STATUS current
                        DESCRIPTION ""
                        ::= { modEoCCNURealTimeStatisticEntry 3 }

                
                -- 1.3.6.1.4.1.17409.2.4.6.1.1.4
                modEoCCNURealTimeStatisticRxPkt OBJECT-TYPE
                        SYNTAX Counter32
                        MAX-ACCESS read-only
                        STATUS current
                        DESCRIPTION ""
                        ::= { modEoCCNURealTimeStatisticEntry 4 }

                
                -- 1.3.6.1.4.1.17409.2.4.6.1.1.5
                modEoCCNURealTimeStatisticTxByte OBJECT-TYPE
                        SYNTAX Counter64
                        MAX-ACCESS read-only
                        STATUS current
                        DESCRIPTION ""
                        ::= { modEoCCNURealTimeStatisticEntry 5 }

                
                -- 1.3.6.1.4.1.17409.2.4.6.1.1.6
                modEoCCNURealTimeStatisticRxByte OBJECT-TYPE
                        SYNTAX Counter64
                        MAX-ACCESS read-only
                        STATUS current
                        DESCRIPTION ""
                        ::= { modEoCCNURealTimeStatisticEntry 6 }

                
                -- 1.3.6.1.4.1.17409.2.4.6.1.1.7
                modEoCCNURealTimeStatisticTxBcast OBJECT-TYPE
                        SYNTAX Counter32
                        MAX-ACCESS read-only
                        STATUS current
                        DESCRIPTION ""
                        ::= { modEoCCNURealTimeStatisticEntry 7 }

                
                -- 1.3.6.1.4.1.17409.2.4.6.1.1.8
                modEoCCNURealTimeStatisticRxBcast OBJECT-TYPE
                        SYNTAX Counter32
                        MAX-ACCESS read-only
                        STATUS current
                        DESCRIPTION ""
                        ::= { modEoCCNURealTimeStatisticEntry 8 }

                
                -- 1.3.6.1.4.1.17409.2.4.6.1.1.9
                modEoCCNURealTimeStatisticTxMcast OBJECT-TYPE
                        SYNTAX Counter32
                        MAX-ACCESS read-only
                        STATUS current
                        DESCRIPTION ""
                        ::= { modEoCCNURealTimeStatisticEntry 9 }

                
                -- 1.3.6.1.4.1.17409.2.4.6.1.1.10
                modEoCCNURealTimeStatisticRxMcast OBJECT-TYPE
                        SYNTAX Counter32
                        MAX-ACCESS read-only
                        STATUS current
                        DESCRIPTION ""
                        ::= { modEoCCNURealTimeStatisticEntry 10 }

                
                -- 1.3.6.1.4.1.17409.2.4.6.1.1.11
                modEoCCNURealTimeStatisticRxCrc OBJECT-TYPE
                        SYNTAX Counter32
                        MAX-ACCESS read-only
                        STATUS current
                        DESCRIPTION ""
                        ::= { modEoCCNURealTimeStatisticEntry 11 }

                
                -- 1.3.6.1.4.1.17409.2.4.6.1.1.12
                modEoCCNURealTimeStatisticTxShort OBJECT-TYPE
                        SYNTAX Counter32
                        MAX-ACCESS read-only
                        STATUS current
                        DESCRIPTION ""
                        ::= { modEoCCNURealTimeStatisticEntry 12 }

                
                -- 1.3.6.1.4.1.17409.2.4.6.1.1.13
                modEoCCNURealTimeStatisticRxShort OBJECT-TYPE
                        SYNTAX Counter32
                        MAX-ACCESS read-only
                        STATUS current
                        DESCRIPTION ""
                        ::= { modEoCCNURealTimeStatisticEntry 13 }

                
                -- 1.3.6.1.4.1.17409.2.4.6.1.1.14
                modEoCCNURealTimeStatisticTxDropped OBJECT-TYPE
                        SYNTAX Counter32
                        MAX-ACCESS read-only
                        STATUS current
                        DESCRIPTION ""
                        ::= { modEoCCNURealTimeStatisticEntry 14 }

                
                -- 1.3.6.1.4.1.17409.2.4.6.1.1.15
                modEoCCNURealTimeStatisticRxDropped OBJECT-TYPE
                        SYNTAX Counter32
                        MAX-ACCESS read-only
                        STATUS current
                        DESCRIPTION ""
                        ::= { modEoCCNURealTimeStatisticEntry 15 }

                
                -- 1.3.6.1.4.1.17409.2.4.6.1.1.16
                modEoCCNURealTimeStatisticAveragePre-FEC OBJECT-TYPE
                        SYNTAX Counter32
                        MAX-ACCESS read-only
                        STATUS current
                        DESCRIPTION ""
                        ::= { modEoCCNURealTimeStatisticEntry 16 }

                
                -- 1.3.6.1.4.1.17409.2.4.6.1.1.17
                modEoCCNURealTimeStatisticReset OBJECT-TYPE
                        SYNTAX INTEGER
                                {
                                none(0),
                                clear(1)
                                }
                        MAX-ACCESS read-write
                        STATUS current
                        DESCRIPTION ""
                        ::= { modEoCCNURealTimeStatisticEntry 17 }

                
                -- 1.3.6.1.4.1.17409.2.4.7
                modEoCIGMPSnoopingGroup OBJECT IDENTIFIER ::= { nscrtvEocTree 7 }

                
                -- 1.3.6.1.4.1.17409.2.4.7.1
                modEoCIGMPSnoopingTable OBJECT-TYPE
                        SYNTAX SEQUENCE OF ModEoCIGMPSnoopingEntry
                        MAX-ACCESS not-accessible
                        STATUS current
                        DESCRIPTION ""
                        ::= { modEoCIGMPSnoopingGroup 1 }

                
                -- 1.3.6.1.4.1.17409.2.4.7.1.1
                modEoCIGMPSnoopingEntry OBJECT-TYPE
                        SYNTAX ModEoCIGMPSnoopingEntry
                        MAX-ACCESS not-accessible
                        STATUS current
                        DESCRIPTION ""
                        INDEX { modEoCIGMPSnoopingMasterIndex, modEoCIGMPSnoopingCNUIndex }
                        ::= { modEoCIGMPSnoopingTable 1 }

                
                ModEoCIGMPSnoopingEntry ::=
                        SEQUENCE { 
                                modEoCIGMPSnoopingMasterIndex
                                        INTEGER,
                                modEoCIGMPSnoopingCNUIndex
                                        INTEGER,
                                modEoCIGMPSnoopingDevMACAddress
                                        MacAddress,
                                modEoCIGMPSnoopingEN
                                        INTEGER
                         }

                -- 1.3.6.1.4.1.17409.2.4.7.1.1.1
                modEoCIGMPSnoopingMasterIndex OBJECT-TYPE
                        SYNTAX INTEGER (0..20)
                        MAX-ACCESS read-only
                        STATUS current
                        DESCRIPTION ""
                        ::= { modEoCIGMPSnoopingEntry 1 }

                
                -- 1.3.6.1.4.1.17409.2.4.7.1.1.2
                modEoCIGMPSnoopingCNUIndex OBJECT-TYPE
                        SYNTAX INTEGER (0..10240)
                        MAX-ACCESS read-only
                        STATUS current
                        DESCRIPTION ""
                        ::= { modEoCIGMPSnoopingEntry 2 }

                
                -- 1.3.6.1.4.1.17409.2.4.7.1.1.3
                modEoCIGMPSnoopingDevMACAddress OBJECT-TYPE
                        SYNTAX MacAddress
                        MAX-ACCESS read-write
                        STATUS current
                        DESCRIPTION ""
                        ::= { modEoCIGMPSnoopingEntry 3 }

                
                -- 1.3.6.1.4.1.17409.2.4.7.1.1.4
                modEoCIGMPSnoopingEN OBJECT-TYPE
                        SYNTAX INTEGER
                                {
                                disable(0),
                                enable(1)
                                }
                        MAX-ACCESS read-write
                        STATUS current
                        DESCRIPTION ""
                        ::= { modEoCIGMPSnoopingEntry 4 }

                
                -- 1.3.6.1.4.1.17409.2.4.8
                modEoCTrapGroup OBJECT IDENTIFIER ::= { nscrtvEocTree 8 }

                
                -- 1.3.6.1.4.1.17409.2.4.8.1
                modEoCTrapMaxTimes OBJECT-TYPE
                        SYNTAX INTEGER (1..255)
                        MAX-ACCESS read-write
                        STATUS current
                        DESCRIPTION ""
                        ::= { modEoCTrapGroup 1 }

                
                -- 1.3.6.1.4.1.17409.2.4.8.2
                modEoCTrapMinInterval OBJECT-TYPE
                        SYNTAX INTEGER
                        UNITS "s"
                        MAX-ACCESS read-write
                        STATUS current
                        DESCRIPTION ""
                        ::= { modEoCTrapGroup 2 }

                
                -- 1.3.6.1.4.1.17409.2.4.8.3
                modEoCTrapMaxInterval OBJECT-TYPE
                        SYNTAX INTEGER
                        UNITS "s"
                        MAX-ACCESS read-write
                        STATUS current
                        DESCRIPTION ""
                        ::= { modEoCTrapGroup 3 }

                
                -- 1.3.6.1.4.1.17409.2.4.8.4
                modEoCTrapAck OBJECT-TYPE
                        SYNTAX INTEGER (0..1)
                        MAX-ACCESS read-write
                        STATUS current
                        DESCRIPTION ""
                        ::= { modEoCTrapGroup 4 }

                
                -- 1.3.6.1.4.1.17409.2.4.8.5
                modEoCTrapTable OBJECT-TYPE
                        SYNTAX SEQUENCE OF ModEoCTrapEntry
                        MAX-ACCESS not-accessible
                        STATUS current
                        DESCRIPTION ""
                        ::= { modEoCTrapGroup 5 }

                
                -- 1.3.6.1.4.1.17409.2.4.8.5.1
                modEoCTrapEntry OBJECT-TYPE
                        SYNTAX ModEoCTrapEntry
                        MAX-ACCESS not-accessible
                        STATUS current
                        DESCRIPTION ""
                        INDEX { modEoCTrapIndex }
                        ::= { modEoCTrapTable 1 }

                
                ModEoCTrapEntry ::=
                        SEQUENCE { 
                                modEoCTrapIndex
                                        INTEGER,
                                modEoCTrapIP
                                        IpAddress,
                                modEoCTrapCommunity
                                        DisplayString,
                                modEoCTrapStatus
                                        INTEGER,
                                modEoCTrapRowStatus
                                        RowStatus
                         }

                -- 1.3.6.1.4.1.17409.2.4.8.5.1.1
                modEoCTrapIndex OBJECT-TYPE
                        SYNTAX INTEGER (1..16)
                        MAX-ACCESS read-only
                        STATUS current
                        DESCRIPTION ""
                        ::= { modEoCTrapEntry 1 }

                
                -- 1.3.6.1.4.1.17409.2.4.8.5.1.2
                modEoCTrapIP OBJECT-TYPE
                        SYNTAX IpAddress
                        MAX-ACCESS read-write
                        STATUS current
                        DESCRIPTION ""
                        ::= { modEoCTrapEntry 2 }

                
                -- 1.3.6.1.4.1.17409.2.4.8.5.1.3
                modEoCTrapCommunity OBJECT-TYPE
                        SYNTAX DisplayString
                        MAX-ACCESS read-only
                        STATUS current
                        DESCRIPTION ""
                        ::= { modEoCTrapEntry 3 }

                
                -- 1.3.6.1.4.1.17409.2.4.8.5.1.4
                modEoCTrapStatus OBJECT-TYPE
                        SYNTAX INTEGER (1..16)
                        MAX-ACCESS read-only
                        STATUS current
                        DESCRIPTION ""
                        ::= { modEoCTrapEntry 4 }

                
                -- 1.3.6.1.4.1.17409.2.4.8.5.1.5
                modEoCTrapRowStatus OBJECT-TYPE
                        SYNTAX RowStatus
                        MAX-ACCESS read-create
                        STATUS current
                        DESCRIPTION ""
                        ::= { modEoCTrapEntry 5 }

                
                -- 1.3.6.1.4.1.17409.2.4.8.6
                modEoCTrapSubObjects OBJECT IDENTIFIER ::= { modEoCTrapGroup 6 }

                
                -- 1.3.6.1.4.1.17409.2.4.8.6.1
                modEoCTrapTime OBJECT-TYPE
                        SYNTAX TimeTicks
                        MAX-ACCESS read-only
                        STATUS current
                        DESCRIPTION ""
                        ::= { modEoCTrapSubObjects 1 }

                
                -- 1.3.6.1.4.1.17409.2.4.8.6.2
                modEoCTrapSourceID OBJECT-TYPE
                        SYNTAX INTEGER
                        MAX-ACCESS read-only
                        STATUS current
                        DESCRIPTION ""
                        ::= { modEoCTrapSubObjects 2 }

                
                -- 1.3.6.1.4.1.17409.2.4.8.6.3
                modEoCTrapCode OBJECT-TYPE
                        SYNTAX OCTET STRING (SIZE (8))
                        MAX-ACCESS read-only
                        STATUS current
                        DESCRIPTION ""
                        ::= { modEoCTrapSubObjects 3 }

                
                -- 1.3.6.1.4.1.17409.2.4.8.6.4
                modEoCTrapSeverity OBJECT-TYPE
                        SYNTAX INTEGER
                                {
                                unknown(0),
                                critical(1),
                                major(2),
                                minor(3),
                                warning(4)
                                }
                        MAX-ACCESS read-only
                        STATUS current
                        DESCRIPTION ""
                        ::= { modEoCTrapSubObjects 4 }

                
                -- 1.3.6.1.4.1.17409.2.4.8.6.5
                modEoCTrapValue OBJECT-TYPE
                        SYNTAX OCTET STRING (SIZE (0..64))
                        MAX-ACCESS read-only
                        STATUS current
                        DESCRIPTION ""
                        ::= { modEoCTrapSubObjects 5 }

                
                -- 1.3.6.1.4.1.17409.2.4.8.7
                modEoCTrapObjects OBJECT IDENTIFIER ::= { modEoCTrapGroup 7 }

                
                -- 1.3.6.1.4.1.17409.2.4.8.7.1
                modEoCTrapNotification NOTIFICATION-TYPE
                        OBJECTS { modEoCTrapTime, modEoCTrapSourceID, modEoCTrapCode, modEoCTrapSeverity, modEoCTrapValue
                                 }
                        STATUS current
                        DESCRIPTION "" 
                        ::= { modEoCTrapObjects 1 }

                
        
        END

--
-- NSCRTV-EPONEOC-MOD-EOC-MIB.my
--
