--
-- ALARM-MIB.my
-- MIB generated by MG-SOFT Visual MIB Builder Version 4.0 Build 349
-- Friday, November 21, 2003 at 15:00:38
--

	SPIDCOM-ALARM-MIB DEFINITIONS ::= BEGIN

		IMPORTS
			neMibAlarm
			    FROM NE-ALARM-MIB
			OBJECT-GROUP, NOTIFICATION-GROUP
				FROM SNMPv2-CONF
			Integer32, Unsigned32, Counter32, TimeTicks, IpAddress, OBJECT-TYPE, MODULE-IDENTITY, NOTIFICATION-TYPE
				FROM SNMPv2-SMI
			DisplayString, DateAndTime, TEXTUAL-CONVENTION
				FROM SNMPv2-TC;


		-- 1.3.6.1.4.1.22764.2.1
		neAlarm MODULE-IDENTITY
			LAST-UPDATED "200207151330Z"		-- July 15, 2002 at 13:30 GMT
			ORGANIZATION
				"SPiDCOM"

			CONTACT-INFO
				" TO BE SPECIFIED BY SPiDCOM
				"
			DESCRIPTION
				"Definition of the MIB tree structure
				to manage the Alarm Monitoring."
			::= { neMibAlarm 1 }



--
-- Textual conventions
--

		ItuAlarmProbableCause ::= TEXTUAL-CONVENTION
			STATUS current
			DESCRIPTION
				"ItuAlarmProbableCause is the probable cause according the ITU X.733."
			SYNTAX INTEGER
				{
				other(1),
				adapterError(2),
				applicationSubsystemFailure(3),
				bandwidthReduced(4),
				callEstablishmentError(5),
				communicationsProtocolError(6),
				communicationsSubsystemFailure(7),
				configurationOrCustomizationError(8),
				congestion(9),
				corruptData(10),
				cpuCyclesLimitExceeded(11),
				dataSetOrModemError(12),
				degradedSignal(13),
				dteDceInterfaceError(14),
				enclosureDoorOpen(15),
				equipmentMalfunction(16),
				excessiveVibration(17),
				fileError(18),
				fireDetected(19),
				floodDetected(20),
				framingError(21),
				heatingVentCoolingSystemProblem(22),
				humidityUnacceptable(23),
				inputOutputDeviceError(24),
				inputDeviceError(25),
				lanError(26),
				leakDetected(27),
				localNodeTransmissionError(28),
				lossOfFrame(29),
				lossOfSignal(30),
				materialSupplyExhausted(31),
				multiplexerProblem(32),
				outOfMemory(33),
				ouputDeviceError(34),
				performanceDegraded(35),
				powerProblem(36),
				pressureUnacceptable(37),
				processorProblem(38),
				pumpFailure(39),
				queueSizeExceeded(40),
				receiveFailure(41),
				receiverFailure(42),
				remoteNodeTransmissionError(43),
				resourceAtOrNearingCapacity(44),
				responseTimeExecessive(45),
				retransmissionRateExcessive(46),
				softwareError(47),
				softwareProgramAbnormallyTerminated(48),
				softwareProgramError(49),
				storageCapacityProblem(50),
				temperatureUnacceptable(51),
				thresholdCrossed(52),
				timingProblem(53),
				toxicLeakDetected(54),
				transmitFailure(55),
				transmitterFailure(56),
				underlyingResourceUnavailable(57),
				versionMismatch(58),
				authenticationFailure(59),
				breachOfConfidentiality(60),
				cableTamper(61),
				delayedInformation(62),
				denialOfService(63),
				duplicateInformation(64),
				informationMissing(65),
				informationModificationDetected(66),
				informationOutOfSequence(67),
				intrusionDetection(68),
				keyExpired(69),
				nonRepudiationFailure(70),
				outOfHoursActivity(71),
				outOfService(72),
				proceduralError(73),
				unauthorizedAccessAttempt(74),
				unexpectedInformation(75)
				}

		ItuAlarmType ::= TEXTUAL-CONVENTION
			STATUS current
			DESCRIPTION
				"ItuAlarmType is the alarm type according the ITU X.733."
			SYNTAX INTEGER
				{
				other(1),
				communicationsAlarm(2),
				qualityOfServiceAlarm(3),
				processingErrorAlarm(4),
				equipmentAlarm(5),
				environmentalAlarm(6),
				integrityViolation(7),
				operationalViolation(8),
				physicalViolation(9),
				securityServiceOrMechanismViolation(10),
				timeDomainViolation(11)
				}

		NeAlarmPhoto ::= TEXTUAL-CONVENTION
			STATUS current
			DESCRIPTION
				"Description."
			SYNTAX INTEGER { takePhoto(1) }



		NeTrapFilter ::= TEXTUAL-CONVENTION
			STATUS current
			DESCRIPTION
				"Filtertype used for control of traps by manager.
				If trapFilterOn, the agent sends non traps."
			SYNTAX INTEGER
				{
				trapFilterOff(0),
				trapFilterOn(1)
				}


--
-- Node definitions
--

		-- 1.3.6.1.4.1.22764.2.1.1
		neAlarmTable OBJECT-TYPE
			SYNTAX SEQUENCE OF NeAlarmEntry
			MAX-ACCESS not-accessible
			STATUS current
			DESCRIPTION
				"neAlarmTable represents all the possible alarms on the NE,
				stating the probable cause, the alarm type and the perceived
				severity as per [X.733].
				Note that each entry is significant until neAlarmIsApplicable
				is applicable(1).
				Entries should never be removed unless the NE they refer to
				disconnected NEs.
				To invalidate an entry the Agent sets neAlarmIsApplicable to
				notApplicable(0). before invalidating the entry, the agent
				sets the neAlarmPerceivedSeverity to cleared."
			::= { neAlarm 1 }


		-- 1.3.6.1.4.1.22764.2.1.1.1
		neAlarmEntry OBJECT-TYPE
			SYNTAX NeAlarmEntry
			MAX-ACCESS not-accessible
			STATUS current
			DESCRIPTION
				"neAlarmMibEntry: an entry in neAlarmMibTable.
				"
			INDEX { neAlarmIndex }
			::= { neAlarmTable 1 }


		NeAlarmEntry ::=
			SEQUENCE {
				neAlarmIndex
					Unsigned32,
				neAlarmAdditionalText
					DisplayString,
				neAlarmProbableCause
					ItuAlarmProbableCause,
				neAlarmDescription
					DisplayString,
				neAlarmType
					ItuAlarmType,
				neAlarmManagedObject
					DisplayString,
				neAlarmStatus
					INTEGER,
				neAlarmAlreadyPresent
					INTEGER,
				neAlarmTimeStamp
					TimeTicks
			 }

		-- 1.3.6.1.4.1.22764.2.1.1.1.1
		neAlarmIndex OBJECT-TYPE
			SYNTAX Unsigned32
			MAX-ACCESS read-only
			STATUS current
			DESCRIPTION
				"neAlarmIndex is a unique identifier for an alarm on a given type of NE.
				The association between the alarmIndex and the alarm for the type of NE
				is described in the NE MIB.
				For example for the SRA L it is in the NETVIEWER SRAL 16X2 MIB.
				"
			::= { neAlarmEntry 1 }


		-- 1.3.6.1.4.1.22764.2.1.1.1.2
		neAlarmAdditionalText OBJECT-TYPE
			SYNTAX DisplayString
			MAX-ACCESS read-only
			STATUS current
			DESCRIPTION
				"neAlarmDescription is a brief description of a given alarm.
				E.g. Tributary 1 Card Fail."
			::= { neAlarmEntry 2 }


		-- 1.3.6.1.4.1.22764.2.1.1.1.3
		neAlarmProbableCause OBJECT-TYPE
			SYNTAX ItuAlarmProbableCause
			MAX-ACCESS read-only
			STATUS current
			DESCRIPTION
				"neAlarmProbablecause represents the probable cause values for
				the alarms as per [X.733].
				"
			::= { neAlarmEntry 3 }


		-- 1.3.6.1.4.1.22764.2.1.1.1.4
		neAlarmDescription OBJECT-TYPE
			SYNTAX DisplayString
			MAX-ACCESS read-only
			STATUS current
			DESCRIPTION
				"neAlarmDescription represents a description of the Alarm, as per [X.733]
				"
			::= { neAlarmEntry 4 }


		-- 1.3.6.1.4.1.22764.2.1.1.1.5
		neAlarmType OBJECT-TYPE
			SYNTAX ItuAlarmType
			MAX-ACCESS read-only
			STATUS current
			DESCRIPTION
				"neAlarmType represents the event type values for
				the alarms as per [X.733].
				"
			::= { neAlarmEntry 5 }


		-- 1.3.6.1.4.1.22764.2.1.1.1.6
		neAlarmManagedObject OBJECT-TYPE
			SYNTAX DisplayString
			MAX-ACCESS read-only
			STATUS current
			DESCRIPTION
				"neAlarmManagedObject represents the managed Object
				values for the alarms.
				"
			::= { neAlarmEntry 6 }


		-- 1.3.6.1.4.1.22764.2.1.1.1.7
		neAlarmStatus OBJECT-TYPE
			SYNTAX INTEGER
				{
				active(1),
				inactive(2),
				terminate(3)
				}
			MAX-ACCESS read-write
			STATUS current
			DESCRIPTION
				"If neAlarmStatus is active(1) the current alarm is active
				for the NE.
				If neAlarmStatus is inactive(2), the current alarm is inactive
				(normality) for the NE.
				If neAlarmStatus is notAffected(3), the current alarm is not
				significant for the NE."
			::= { neAlarmEntry 7 }


		-- 1.3.6.1.4.1.22764.2.1.1.1.8
		neAlarmAlreadyPresent OBJECT-TYPE
			SYNTAX INTEGER
				{
				false(0),
				true(1)
				}
			MAX-ACCESS read-only
			STATUS current
			DESCRIPTION
				"This field could be use to know if alarm already there.
				"
			::= { neAlarmEntry 8 }


		-- 1.3.6.1.4.1.22764.2.1.1.1.9
		neAlarmTimeStamp OBJECT-TYPE
			SYNTAX TimeTicks
			MAX-ACCESS read-only
			STATUS current
			DESCRIPTION
				"The alarm timestamp."
			::= { neAlarmEntry 9 }


		-- 1.3.6.1.4.1.22764.2.1.2
		neAlarmActiveLastTrapIndex OBJECT-TYPE
			SYNTAX Unsigned32
			MAX-ACCESS read-only
			STATUS current
			DESCRIPTION
				"This is the Alarm Index sent for which the last trap was sent
				"
			::= { neAlarm 2 }


		-- 1.3.6.1.4.1.22764.2.1.3
		neClearTerminatedAlarms OBJECT-TYPE
			SYNTAX Integer32 (1)
			MAX-ACCESS read-write
			STATUS current
			DESCRIPTION
				"When the manager sets this object, the agent deletes
				its alarms which status is terminated
				"
			::= { neAlarm 3 }



		-- 1.3.6.1.4.1.22764.2.1.4
		neAlarmActivePhoto OBJECT-TYPE
			SYNTAX Integer32 (1)
			MAX-ACCESS read-write
			STATUS current
			DESCRIPTION
				"When the manager sets this object, the agent sends all
				the active alarms from neAlarmtable to the manager.
				"
			::= { neAlarm 4 }


		-- 1.3.6.1.4.1.22764.2.1.10
		neAlarmTrap OBJECT IDENTIFIER ::= { neAlarm 10 }



		-- 1.3.6.1.4.1.22764.2.1.10.2
		neAlarmTrapCounter OBJECT-TYPE
			SYNTAX Counter32
			MAX-ACCESS read-only
			STATUS current
			DESCRIPTION
				"This object counts only the traps sent under node
				neAlarmTrap."
			::= { neAlarmTrap 2 }


		-- 1.3.6.1.4.1.22764.2.1.10.3
		neAlarmTrapFilter OBJECT-TYPE
			SYNTAX NeTrapFilter
			MAX-ACCESS read-write
			STATUS current
			DESCRIPTION
				"If trapFilterOn, the agent sends no traps under
				node neAlarmTrap. "
			::= { neAlarmTrap 3 }


		-- 1.3.6.1.4.1.22764.2.1.10.4
		neAlarmTrapDestiIp OBJECT-TYPE
			SYNTAX IpAddress
			MAX-ACCESS read-write
			STATUS current
			DESCRIPTION
				"The @IP where traps are sent"
			::= { neAlarmTrap 4 }


		-- 1.3.6.1.4.1.22764.2.1.10.5
		neAlarmTrapDestiPort OBJECT-TYPE
			SYNTAX Unsigned32
			MAX-ACCESS read-write
			STATUS current
			DESCRIPTION
				"The UDP port where traps are sent"
			::= { neAlarmTrap 5 }


		-- 1.3.6.1.4.1.22764.2.1.11
		neAlarmGroup OBJECT-GROUP
			OBJECTS { neAlarmIndex, neAlarmAdditionalText, neAlarmProbableCause, neAlarmDescription, neAlarmType,
					  neAlarmManagedObject, neAlarmAlreadyPresent, neAlarmTimeStamp, neAlarmStatus
					}
			STATUS current
			DESCRIPTION
				"The objects you can find in this MIB."
			::= { neAlarm 11 }


		-- 1.3.6.1.4.1.22764.2.1.12
		--neAlarmMibNotificationGroup NOTIFICATION-GROUP
		--	NOTIFICATIONS { neAlarmChangeNotification }
		--	STATUS current
		--	DESCRIPTION
		--		"Description."
		--	::= { neAlarm 12 }


		-- 1.3.6.1.4.1.22764.2.1.13
		neAlarmActiveGroup OBJECT-GROUP
			OBJECTS { neAlarmActiveLastTrapIndex, neAlarmActivePhoto, neAlarmTrapFilter, neAlarmTrapDestiIp,
					  neAlarmTrapDestiPort, neAlarmTrapCounter, neClearTerminatedAlarms
					}
			STATUS current
			DESCRIPTION
				"The object regarding active alarms"
			::= { neAlarm 13 }



	END

--
-- SPIDCOM-ALARM-MIB.my
--
