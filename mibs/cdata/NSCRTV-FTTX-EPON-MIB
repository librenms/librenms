--
-- NSCRTV-FTTX-EPON-MIB.my
-- MIB generated by MG-SOFT Visual MIB Builder Version 6.0  Build 88
-- Tuesday, March 15, 2016 at 13:56:51
--

	NSCRTV-FTTX-EPON-MIB DEFINITIONS ::= BEGIN
 
		IMPORTS
			BridgeId, Timeout			
				FROM BRIDGE-MIB			
			enterprises, TimeTicks, IpAddress, Unsigned32, Gauge32, 
			Counter32, Counter64, BITS, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;
	
	
	
--
-- Textual conventions
--
	
		EponAlarmInstance ::= TEXTUAL-CONVENTION
			STATUS current
			DESCRIPTION 
				"
				Alarm instance, which define the detailed management object
				reported the alarm. For example, OLT device 1, slot 2, port 3
				reports a port down alarm.
				It is represents in OCTET STRING format.
				1. The first four OCTET has same definition as EponDeviceIndex TC.
				2. The fifth OCTET is the slot definition of ONU, which shall 
				   have same definition as last byte definition in EponCardIndex
				   TC.
				3. The sixth OCTET is the UNI port ID of ONU, which is similar to
				   EponPortIndex TC.
				4. The seventh and eighth OCTETS are reserved and shall be set to 
				   0 at any time, and shall be ignored by maangement system.        
				For example,        
				0x01 02 03 04 05 06 00 00, represents OLT device 1, slot 2, port 3, 
				ONU logical ID 4, slot 5 UNI port 6 of the connected ONU.        
				"
			SYNTAX OCTET STRING (SIZE (8))

		EponAlarmCode ::= TEXTUAL-CONVENTION
			STATUS current
			DESCRIPTION 
				"Alarm codes, uniquely indentifies each kind of alarm.
				Refer to EPON alarm definition table"
			SYNTAX INTEGER (1..65535)

		EponSeverityType ::= TEXTUAL-CONVENTION
			STATUS current
			DESCRIPTION 
				"
				"
			SYNTAX INTEGER
				{
				critical(1),
				major(2),
				minor(3),
				warning(4),
				info(5),
				clear(6)
				}

		TAddress ::= TEXTUAL-CONVENTION
			STATUS current
			DESCRIPTION 
				"
				First four octets sames definition of IpAddress, stands for NMS IP address
				The last four octets same definition of INTEGER, stands for trap UDP port "
			SYNTAX OCTET STRING (SIZE (8))

		EponCardIndex ::= TEXTUAL-CONVENTION
			STATUS current
			DESCRIPTION 
				"                
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For trunk, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a trunk
				"
			SYNTAX Unsigned32

		EponPortIndex ::= TEXTUAL-CONVENTION
			STATUS current
			DESCRIPTION 
				"
				Epon        
				The device port number shall start from 1. Nunber 0 had specific meaning, stands
				for portIndex is meaningless, for the situation defined.
				"
			SYNTAX INTEGER (0..2147483647)

		EponDeviceIndex ::= TEXTUAL-CONVENTION
			STATUS current
			DESCRIPTION 
				"        
				Olt device-8bit OLT Card-8bit Pon port-8bit OnuNUM-8bit        
				Note: 
				----        
				1. OLT device must not be 0.        
				2. Card here shall confirm the last byte definition of EponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				ONU UNI, OLT device, trunk.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				ONU UNI    - Same as OLT ONU ID
				OLT device   - Set card, pon port and OnuNUM to 0
				Trunk    - Card to 0x3F, pon port to trunk ID, OnuNUM to 0
				         Olt device to corresponding ONU device       
				"
			SYNTAX Unsigned32

		AutoNegotiationTechAbility ::= TEXTUAL-CONVENTION
			STATUS current
			DESCRIPTION 
				"Technology ability of auto negotiation. Refer to 
				clause 30.6.1.1.5 of IEEE 802.3 2005 edition"
			SYNTAX BITS
				{
				tenBaseTFullDuplex(1),
				tenBaseTHalfDuplex(2),
				hundredBaseTFullDuplex(3),
				hundredBaseTHalfDuplex(4),
				thousandBaseTFullDuplex(5),
				thousandBaseTHalfDuplex(6),
				thousandBaseXFullDuplex(7),
				thousandBaseXHalfDuplex(8),
				fdxPause(9),
				fdxApause(10),
				fdxSpause(11),
				fdxBpause(12)
				}

		EponStats15MinRecordType ::= TEXTUAL-CONVENTION
			STATUS current
			DESCRIPTION 
				" "
			SYNTAX INTEGER (0..96)

		EponStats24HourRecordType ::= TEXTUAL-CONVENTION
			STATUS current
			DESCRIPTION 
				" "
			SYNTAX INTEGER (0..30)

		EponStatsThresholdType ::= TEXTUAL-CONVENTION
			STATUS current
			DESCRIPTION 
				"
				1-  InOctets                 
				2 InPkts                   
				3 InBroadcastPkts          
				4 InMulticastPkts          
				5 InPkts64Octets           
				6 InPkts65to127Octets      
				7 InPkts128to255Octets     
				8 InPkts256to511Octets     
				9 InPkts512to1023Octets    
				10  InPkts1024to1518Octets 
				11  InPkts1519to1522Octets 
				12  InUndersizePkts        
				13  InOversizePkts         
				14  InFragments            
				15  InMpcpFrames           
				16  InMpcpOctets           
				17  InOAMFrames            
				18  InOAMOctets            
				19  InCRCErrorPkts         
				20  InDropEvents           
				21  InJabbers              
				22  InCollision            
				23  OutOctets              
				24  OutPkts                
				25  OutBroadcastPkts       
				26  OutMulticastPkts       
				27  OutPkts64Octets        
				28  OutPkts65to127Octets   
				29  OutPkts128to255Octets  
				30  OutPkts256to511Octets  
				31  OutPkts512to1023Octets 
				32  OutPkts1024to1518Octets
				33  OutPkts1519o1522Octets 
				34  OutUndersizePkts       
				35  OutOversizePkts        
				36  OutFragments           
				37  OutMpcpFrames          
				38  OutMpcpOctets          
				39  OutOAMFrames           
				40  OutOAMOctets           
				41  OutCRCErrorPkts        
				42  OutDropEvents          
				43  OutJabbers             
				44  OutCollision
				50  Temperature
				51  Voltage
				52  TXPower
				53  RXPower
				
				
				Note:
				----------------------------------------------------------------
				1. For 50 Temperature, this parameter shall only applied to
				   a. Slot level, for each service/switch/management card, for
				      chassis-based system.
				   b. Node-level, for fixed box.
				2. For 50 Temperature, shall be applied to both OLT and ONU
				3. For 50 Temperature, since no 15-min performance data collection
				   are required, system shall ensure the temperature polling interval
				   no less than 5 seconds. The alarm shall be only generated when the
				   threshold is acrossed for three continuous intervals, and shall be 
				   cleared, when the threshold is not accrossed any more, for three 
				   continous intervals.
				"
			SYNTAX INTEGER (1..1024)

	
--
-- Node definitions
--
	
		-- 1.3.6.1.4.1.17409
		nscrtvRoot OBJECT IDENTIFIER ::= { enterprises 17409 }

		
--  DESCRIPTION
-- "nscrtvRootMIB"
		-- 1.3.6.1.4.1.17409.1
		nscrtvHFCemsTree OBJECT IDENTIFIER ::= { nscrtvRoot 1 }

		
		-- 1.3.6.1.4.1.17409.2
		nscrtvEponEocTree OBJECT IDENTIFIER ::= { nscrtvRoot 2 }

		
--  DESCRIPTION
-- "nscrtvEponEocTreeEPONEoCMIB,"
-- "EPONEoCMIB"
		-- 1.3.6.1.4.1.17409.2.1
		propertyIdent OBJECT IDENTIFIER ::= { nscrtvEponEocTree 1 }

		
--      DESCRIPTION
-- "(Property)MIB"
		-- 1.3.6.1.4.1.17409.2.2
		alarmsIdent OBJECT IDENTIFIER ::= { nscrtvEponEocTree 2 }

		
--      DESCRIPTION
-- "OpticalTransmission MIB"
		-- 1.3.6.1.4.1.17409.2.2.11
		eponAlarmTree OBJECT IDENTIFIER ::= { alarmsIdent 11 }

		
		-- 1.3.6.1.4.1.17409.2.2.11.1
		eponTrapObjectGroup OBJECT IDENTIFIER ::= { eponAlarmTree 1 }

		
-- ------------------------------------------------------------------------------
-- AlarmManagementObjects[](1.3.6.1.4.1.17409.2.2.11)
-- ------------------------------------------------------------------------------ 
		-- 1.3.6.1.4.1.17409.2.2.11.1.1
		eponNotifications OBJECT IDENTIFIER ::= { eponTrapObjectGroup 1 }

		
		-- 1.3.6.1.4.1.17409.2.2.11.1.1.1
		eponAlarmNotification NOTIFICATION-TYPE
			OBJECTS { eponTrapSequenceNumber, eponTrapOccurTime, eponTrapCode, eponTrapInstance, eponTrapSeverity, 
				eponTrapCorrelationId, eponTrapAdditionalText }
			STATUS current
			DESCRIPTION 
				"Alarm TRAP definition"
			::= { eponNotifications 1 }

		
		-- 1.3.6.1.4.1.17409.2.2.11.1.1.2
		eponEventNotification NOTIFICATION-TYPE
			OBJECTS { eponTrapSequenceNumber, eponTrapOccurTime, eponTrapCode, eponTrapInstance, eponTrapAdditionalText
				 }
			STATUS current
			DESCRIPTION 
				"Event TRAP definition"
			::= { eponNotifications 2 }

		
		-- 1.3.6.1.4.1.17409.2.2.11.1.2
		eponTrapObjects OBJECT IDENTIFIER ::= { eponTrapObjectGroup 2 }

		
		-- 1.3.6.1.4.1.17409.2.2.11.1.2.1
		eponTrapInstance OBJECT-TYPE
			SYNTAX EponAlarmInstance
			MAX-ACCESS accessible-for-notify
			STATUS current
			DESCRIPTION
				"Alarm instance, indicates the detailed managed object, which
				detects faults.
				"
			::= { eponTrapObjects 1 }

		
		-- 1.3.6.1.4.1.17409.2.2.11.1.2.2
		eponTrapCorrelationId OBJECT-TYPE
			SYNTAX Unsigned32
			MAX-ACCESS accessible-for-notify
			STATUS current
			DESCRIPTION
				"The unique sequence number for the alarm to be cleared, for alarm clearing. 
				Set to 0 for alarm reporting"
			::= { eponTrapObjects 2 }

		
		-- 1.3.6.1.4.1.17409.2.2.11.1.2.3
		eponTrapAdditionalText OBJECT-TYPE
			SYNTAX OCTET STRING (SIZE (0..256))
			MAX-ACCESS accessible-for-notify
			STATUS current
			DESCRIPTION
				"Additional info to the alarm, for further desciption of the
				alarm. The format of it shall be related to each kind alarm
				defined in alarm reference table"
			::= { eponTrapObjects 3 }

		
		-- 1.3.6.1.4.1.17409.2.2.11.1.2.4
		eponTrapCode OBJECT-TYPE
			SYNTAX EponAlarmCode
			MAX-ACCESS accessible-for-notify
			STATUS current
			DESCRIPTION
				"
				C"
			::= { eponTrapObjects 4 }

		
		-- 1.3.6.1.4.1.17409.2.2.11.1.2.5
		eponTrapSeverity OBJECT-TYPE
			SYNTAX EponSeverityType
			MAX-ACCESS accessible-for-notify
			STATUS current
			DESCRIPTION
				"
				"
			::= { eponTrapObjects 5 }

		
		-- 1.3.6.1.4.1.17409.2.2.11.1.2.6
		eponTrapOccurTime OBJECT-TYPE
			SYNTAX DateAndTime
			MAX-ACCESS accessible-for-notify
			STATUS current
			DESCRIPTION
				"
				"
			::= { eponTrapObjects 6 }

		
		-- 1.3.6.1.4.1.17409.2.2.11.1.2.7
		eponTrapSequenceNumber OBJECT-TYPE
			SYNTAX Unsigned32
			MAX-ACCESS accessible-for-notify
			STATUS current
			DESCRIPTION
				"
				A unique sequence number for each trap generated by node. The sequence 
				number shall be reset to 1 when node restarts.         
				The alarm sequence number shall be independent of the event sequence 
				number. Each shall be self-governed.
				
				--------------------------------------------------------------------------------            
				The sequence ID of alarm shall be assigned from the order of transmitting 
				trap to the NMS, instead of the order of alarm occurance. Therefore the NMS 
				will receive the continuous sequence ID.
				    
				1.  When device is in active/standby mode, sequence ID shall be synchronized 
				  between active and standby control module.
				2.  When control module switchover takes place, the current sequence ID shall 
				  keep the synchronized value.
				3.  When device restarts, sequence ID shall start from 1.
				4.  It shall be increased per alarm trap including both alarm raising and clear.
				5.  Non-zero value shall be used. When reaches the maximum number, it shall 
				roll back to 1.          
				
				--------------------------------------------------------------------------------        
				The sequence ID of event shall be assigned from the order of transmitting 
				trap to the NMS. Therefore the NMS will receive the continuous sequence ID.            
				1.  When device is in active/standby mode, sequence ID shall be synchronized 
				  between active and standby control module.
				2.  When control module switchover takes place, the current sequence ID shall 
				  keep the synchronized value.
				3.  When device restarts, sequence ID shall start from 1.
				4.  It shall be increased per event trap.
				5.  Non-zero value shall be used. When reaches the maximum number, it shall 
				roll back to 1.        
				"
			::= { eponTrapObjects 7 }

		
		-- 1.3.6.1.4.1.17409.2.2.11.2
		eponAlarmObjGroup OBJECT IDENTIFIER ::= { eponAlarmTree 2 }

		
		-- 1.3.6.1.4.1.17409.2.2.11.2.1
		activeAlarmTable OBJECT-TYPE
			SYNTAX SEQUENCE OF ActiveAlarmEntry
			MAX-ACCESS not-accessible
			STATUS current
			DESCRIPTION
				"Active alarm table
				
				The device shall maintain this table, to maintain all outstanding 
				(not cleared) alarms generated by the device, including:
				1. Not hit device local alarm filter. That means had been reported to
				   trap receiver (NMS or EMS)
				2. Hit local alarm filter. That means not trap is reported to trap receiver
				   for the alarm.
				
				The device shall maintain two numbers:
				1. Alarm sequence number: As described in eponTrapSequenceNumber, it is initially
				   set to 1 when device restarts, increases per trap reported to trap receiver,
				   and rollover to 1 once it reaches the maximum value. 
				   From NMS's view, traps received from a nodes will be consecutive, by identifying 
				   the alarm sequence number carried in alarm trap. If breaks, means some trap 
				   may be lost, since packet loss between NMS and NE. 
				2. Alarm raising number: This is maintained by NE internally and does not intend for
				   being acknowledged by external manage system. It is designed to uniquely indentify
				   each alarm raised by NE, excluding duplicates. Once one alarm raised, despite 
				   whether it is hit by alarm filter, NE shall assign a raising number to it. So, it
				   major functionality is to uniquely identify alarms hit NE local alarm filter, since 
				   this kindly alarm will not be reported to NMS, and hence no alarm sequence number
				   is assigned to it.
				   It is initially  set to 1 when device restarts, increases per alarm generation (
				   excluding duplicates), and rollover to 1 once it reaches the maximum value. 
				
				FUNCTION DESCRIPTION OF ACTIVE ALARM TABLE:         
				ALARM RAISING
				----------------------        
				1. When NE detects one fault and associates to one kind of alarm, it shall check whether
				   there is same alarm in active alarm table, which is indexed by alarm code and alarm
				   instance. If hits, it means duplicates, update the corresponding entry of the table.
				   Otherwise,
				2. The alarm is not a duplicate. Assign an alarm raising number. Check whether the
				alarm hits local alarm filters. If hits, set alarm sequence number to 0.
				   Create an entry into active alarm table. Otherwise,
				3. Assign an alarm sequence number to the alarm. Create an entry into active alarm
				table. Report the alarm trap to all trap receivers.
				   
				ALARM CLEARING
				----------------------        
				1. When NE detects one fault is cleared and associates to one kind of alarm, it shall 
				   check whether there is corresponding alarm in active alarm table, which is indexed
				by alarm code and alarm instance. If no hit, escape this clear event. Upon a hit,
				if the alarm sequence number is 0, move the active alarm entry to history alarm
				table and update the corresponding fields. At this case, historyAlarmCorrelationId
				and historyAlarmSeqNum will be set to 0.
				   Otherwise,
				2. Assign an alarm sequence number to the clear trap. Report the alarm clear trap to 
				   all trap receivers. Move the active alarm entry to history alarm table and update 
				   the corresponding fields. At this case, activeAlarmSeqNum shall be copied to 
				   historyAlarmCorrelationId, and historyAlarmSeqNum shall be set to the new alarm
				   sequence number for the clear trap.
				
				ALARM SYNCHRONIZATION BETWEEN NE AND NMS
				---------------------------------------------        
				1. Once NMS finds the alarm sequence number in reported alarm traps is not continuous,
				   it will walk active or history alarm table of the NE for the lost seuqence number.
				"
			::= { eponAlarmObjGroup 1 }

		
		-- 1.3.6.1.4.1.17409.2.2.11.2.1.1
		activeAlarmEntry OBJECT-TYPE
			SYNTAX ActiveAlarmEntry
			MAX-ACCESS not-accessible
			STATUS current
			DESCRIPTION			" "
			INDEX { activeAlarmSeqNum, activeAlarmRaisingNumber }
			::= { activeAlarmTable 1 }

		
		ActiveAlarmEntry ::=
			SEQUENCE { 
				activeAlarmSeqNum
					Unsigned32,
				activeAlarmCode
					EponAlarmCode,
				activeAlarmInstance
					EponAlarmInstance,
				activeAlarmSeverity
					EponSeverityType,
				activeAlarmRaisingNumber
					Unsigned32,
				activeAlarmFirstOccurTime
					DateAndTime,
				activeAlarmLastOccurTime
					DateAndTime,
				activeAlarmRepeats
					Counter32,
				activeAlarmConfirm
					TruthValue,
				activeAlarmAdditionalText
					OCTET STRING
			 }

		-- 1.3.6.1.4.1.17409.2.2.11.2.1.1.1
		activeAlarmSeqNum OBJECT-TYPE
			SYNTAX Unsigned32 (1..4294967295)
			MAX-ACCESS not-accessible
			STATUS current
			DESCRIPTION
				"Alarm sequence number
				
				The definition refered to the description of activeAlarmTable"
			::= { activeAlarmEntry 1 }

		
		-- 1.3.6.1.4.1.17409.2.2.11.2.1.1.2
		activeAlarmCode OBJECT-TYPE
			SYNTAX EponAlarmCode
			MAX-ACCESS read-only
			STATUS current
			DESCRIPTION
				"
				C
				"
			::= { activeAlarmEntry 2 }

		
		-- 1.3.6.1.4.1.17409.2.2.11.2.1.1.3
		activeAlarmInstance OBJECT-TYPE
			SYNTAX EponAlarmInstance
			MAX-ACCESS read-only
			STATUS current
			DESCRIPTION
				"Alarm instance, indicates the detailed managed object"
			::= { activeAlarmEntry 3 }

		
		-- 1.3.6.1.4.1.17409.2.2.11.2.1.1.4
		activeAlarmSeverity OBJECT-TYPE
			SYNTAX EponSeverityType
			MAX-ACCESS read-only
			STATUS current
			DESCRIPTION
				"
				"
			::= { activeAlarmEntry 4 }

		
		-- 1.3.6.1.4.1.17409.2.2.11.2.1.1.5
		activeAlarmRaisingNumber OBJECT-TYPE
			SYNTAX Unsigned32 (1..4294967295)
			MAX-ACCESS not-accessible
			STATUS current
			DESCRIPTION
				"Alarm raising number.        
				The definition refered to the description of activeAlarmTable"
			::= { activeAlarmEntry 5 }

		
		-- 1.3.6.1.4.1.17409.2.2.11.2.1.1.6
		activeAlarmFirstOccurTime OBJECT-TYPE
			SYNTAX DateAndTime
			MAX-ACCESS read-only
			STATUS current
			DESCRIPTION
				"
				        
				The time stamp when alarm occurs, which triggered to create the 
				active alarm entry."
			::= { activeAlarmEntry 6 }

		
		-- 1.3.6.1.4.1.17409.2.2.11.2.1.1.7
		activeAlarmLastOccurTime OBJECT-TYPE
			SYNTAX DateAndTime
			MAX-ACCESS read-only
			STATUS current
			DESCRIPTION
				"
				The time stamp when alarm occurs, where the alarm is duplicated 
				with existed active alarm entry, and it was the latest one. "
			::= { activeAlarmEntry 7 }

		
		-- 1.3.6.1.4.1.17409.2.2.11.2.1.1.8
		activeAlarmRepeats OBJECT-TYPE
			SYNTAX Counter32
			MAX-ACCESS read-only
			STATUS current
			DESCRIPTION
				"Number of repeated alarms for this active alarm entry"
			::= { activeAlarmEntry 8 }

		
		-- 1.3.6.1.4.1.17409.2.2.11.2.1.1.9
		activeAlarmConfirm OBJECT-TYPE
			SYNTAX TruthValue
			MAX-ACCESS read-write
			STATUS current
			DESCRIPTION
				"
				        
				Node shall not clear an active alarm, upon the confirmation 
				of the active alarm, but just mark an acknowledged status.
				
				An alarm will only be cleared once the clear condition hits."
			::= { activeAlarmEntry 9 }

		
		-- 1.3.6.1.4.1.17409.2.2.11.2.1.1.10
		activeAlarmAdditionalText OBJECT-TYPE
			SYNTAX OCTET STRING (SIZE (0..256))
			MAX-ACCESS read-only
			STATUS current
			DESCRIPTION
				"Additional info to the alarm, for further desciption of the
				alarm. The format of it shall be related to each kind alarm
				defined in alarm reference table"
			::= { activeAlarmEntry 10 }

		
		-- 1.3.6.1.4.1.17409.2.2.11.2.2
		historyAlarmTable OBJECT-TYPE
			SYNTAX SEQUENCE OF HistoryAlarmEntry
			MAX-ACCESS not-accessible
			STATUS current
			DESCRIPTION
				"History alarm table.        
				The device shall maintain this table, to maintain all cleared 
				alarms generated by the device, including:        
				1. Not hit device local alarm filter. That means had been reported to
				   trap receiver (NMS or EMS)
				2. Hit local alarm filter. That means not trap is reported to trap receiver
				   for the alarm.        
				The number of history alarm enteries in the table could be device-specific.
				However, it is recommended no less than 200 entries.        
				The detailed function definition refers to that given in description of
				activeAlarmTable.
				"
			::= { eponAlarmObjGroup 2 }

		
		-- 1.3.6.1.4.1.17409.2.2.11.2.2.1
		historyAlarmEntry OBJECT-TYPE
			SYNTAX HistoryAlarmEntry
			MAX-ACCESS not-accessible
			STATUS current
			DESCRIPTION			" "
			INDEX { historyAlarmSeqNum, historyAlarmRaisingNumber }
			::= { historyAlarmTable 1 }

		
		HistoryAlarmEntry ::=
			SEQUENCE { 
				historyAlarmSeqNum
					Unsigned32,
				historyAlarmCode
					EponAlarmCode,
				historyAlarmInstance
					EponAlarmInstance,
				historyAlarmSeverity
					EponSeverityType,
				historyAlarmRaisingNumber
					Unsigned32,
				historyAlarmFirstOccurTime
					DateAndTime,
				historyAlarmLastOccurTime
					DateAndTime,
				historyAlarmRepeats
					Counter32,
				historyAlarmCorrelationId
					Unsigned32,
				historyAlarmAdditionalText
					OCTET STRING,
				historyAlarmClearTime
					DateAndTime
			 }

		-- 1.3.6.1.4.1.17409.2.2.11.2.2.1.1
		historyAlarmSeqNum OBJECT-TYPE
			SYNTAX Unsigned32 (1..4294967295)
			MAX-ACCESS not-accessible
			STATUS current
			DESCRIPTION
				"Alarm sequence number
				
				The definition refered to the description of historyAlarmTable"
			::= { historyAlarmEntry 1 }

		
		-- 1.3.6.1.4.1.17409.2.2.11.2.2.1.2
		historyAlarmCode OBJECT-TYPE
			SYNTAX EponAlarmCode
			MAX-ACCESS read-only
			STATUS current
			DESCRIPTION
				"
				C
				"
			::= { historyAlarmEntry 2 }

		
		-- 1.3.6.1.4.1.17409.2.2.11.2.2.1.3
		historyAlarmInstance OBJECT-TYPE
			SYNTAX EponAlarmInstance
			MAX-ACCESS read-only
			STATUS current
			DESCRIPTION
				"Alarm instance, indicates the detailed managed object"
			::= { historyAlarmEntry 3 }

		
		-- 1.3.6.1.4.1.17409.2.2.11.2.2.1.4
		historyAlarmSeverity OBJECT-TYPE
			SYNTAX EponSeverityType
			MAX-ACCESS read-only
			STATUS current
			DESCRIPTION
				"
				"
			::= { historyAlarmEntry 4 }

		
		-- 1.3.6.1.4.1.17409.2.2.11.2.2.1.5
		historyAlarmRaisingNumber OBJECT-TYPE
			SYNTAX Unsigned32 (1..4294967295)
			MAX-ACCESS not-accessible
			STATUS current
			DESCRIPTION
				"Alarm raising number.        
				The definition refered to the description of historyAlarmTable"
			::= { historyAlarmEntry 5 }

		
		-- 1.3.6.1.4.1.17409.2.2.11.2.2.1.6
		historyAlarmFirstOccurTime OBJECT-TYPE
			SYNTAX DateAndTime
			MAX-ACCESS read-only
			STATUS current
			DESCRIPTION
				"
				        
				The time stamp when alarm occurs, which triggered to create the 
				history alarm entry."
			::= { historyAlarmEntry 6 }

		
		-- 1.3.6.1.4.1.17409.2.2.11.2.2.1.7
		historyAlarmLastOccurTime OBJECT-TYPE
			SYNTAX DateAndTime
			MAX-ACCESS read-only
			STATUS current
			DESCRIPTION
				"
				The time stamp when alarm occurs, where the alarm is duplicated 
				with existed history alarm entry, and it was the latest one. "
			::= { historyAlarmEntry 7 }

		
		-- 1.3.6.1.4.1.17409.2.2.11.2.2.1.8
		historyAlarmRepeats OBJECT-TYPE
			SYNTAX Counter32
			MAX-ACCESS read-only
			STATUS current
			DESCRIPTION
				"Number of repeated alarms for this history alarm entry"
			::= { historyAlarmEntry 8 }

		
		-- 1.3.6.1.4.1.17409.2.2.11.2.2.1.9
		historyAlarmCorrelationId OBJECT-TYPE
			SYNTAX Unsigned32
			MAX-ACCESS read-only
			STATUS current
			DESCRIPTION
				"It is the corresponding sequence ID of the alarm that to
				be cleared. "
			::= { historyAlarmEntry 9 }

		
		-- 1.3.6.1.4.1.17409.2.2.11.2.2.1.10
		historyAlarmAdditionalText OBJECT-TYPE
			SYNTAX OCTET STRING (SIZE (0..256))
			MAX-ACCESS read-only
			STATUS current
			DESCRIPTION
				"Additional info to the alarm, for further desciption of the
				alarm. The format of it shall be related to each kind alarm
				defined in alarm reference table"
			::= { historyAlarmEntry 10 }

		
		-- 1.3.6.1.4.1.17409.2.2.11.2.2.1.11
		historyAlarmClearTime OBJECT-TYPE
			SYNTAX DateAndTime
			MAX-ACCESS read-only
			STATUS current
			DESCRIPTION
				"Define when the alarm was cleared"
			::= { historyAlarmEntry 11 }

		
		-- 1.3.6.1.4.1.17409.2.2.11.2.3
		eventLogTable OBJECT-TYPE
			SYNTAX SEQUENCE OF EventLogEntry
			MAX-ACCESS not-accessible
			STATUS current
			DESCRIPTION
				"Event log table.        
				The device shall maintain this table, to maintain all events had
				be reported by the device, including:
				1.  The event table shall be saved in RAM memory and shall be flushed 
				  when OLT restarts.
				2.  The event log table shall support no less than 200 entries.  When 
				  the event log table is full, the oldest entry in the table shall be 
				  removed first. 
				3.  When OLT is configured with control module redundancy, active controller
				  shall automatically synchronize the events in event log table  b/w active 
				  and standby.
				"
			::= { eponAlarmObjGroup 3 }

		
		-- 1.3.6.1.4.1.17409.2.2.11.2.3.1
		eventLogEntry OBJECT-TYPE
			SYNTAX EventLogEntry
			MAX-ACCESS not-accessible
			STATUS current
			DESCRIPTION			" "
			INDEX { eventSeqNum }
			::= { eventLogTable 1 }

		
		EventLogEntry ::=
			SEQUENCE { 
				eventSeqNum
					Unsigned32,
				eventCode
					EponAlarmCode,
				eventInstance
					EponAlarmInstance,
				eventOccurTime
					DateAndTime,
				eventAdditionalText
					OCTET STRING
			 }

		-- 1.3.6.1.4.1.17409.2.2.11.2.3.1.1
		eventSeqNum OBJECT-TYPE
			SYNTAX Unsigned32 (1..4294967295)
			MAX-ACCESS not-accessible
			STATUS current
			DESCRIPTION
				"Event sequence number
				
				The definition refered to the description of eponTrapSequenceNumber"
			::= { eventLogEntry 1 }

		
		-- 1.3.6.1.4.1.17409.2.2.11.2.3.1.2
		eventCode OBJECT-TYPE
			SYNTAX EponAlarmCode
			MAX-ACCESS read-only
			STATUS current
			DESCRIPTION
				"
				C
				"
			::= { eventLogEntry 2 }

		
		-- 1.3.6.1.4.1.17409.2.2.11.2.3.1.3
		eventInstance OBJECT-TYPE
			SYNTAX EponAlarmInstance
			MAX-ACCESS read-only
			STATUS current
			DESCRIPTION
				"Event instance, indicates the detailed managed object"
			::= { eventLogEntry 3 }

		
		-- 1.3.6.1.4.1.17409.2.2.11.2.3.1.4
		eventOccurTime OBJECT-TYPE
			SYNTAX DateAndTime
			MAX-ACCESS read-only
			STATUS current
			DESCRIPTION
				"
				The time stamp when event occurs"
			::= { eventLogEntry 4 }

		
		-- 1.3.6.1.4.1.17409.2.2.11.2.3.1.5
		eventAdditionalText OBJECT-TYPE
			SYNTAX OCTET STRING (SIZE (0..256))
			MAX-ACCESS read-only
			STATUS current
			DESCRIPTION
				"Additional info to the event, for further desciption of the
				event. The format of it shall be related to each kind event
				defined in event reference table"
			::= { eventLogEntry 5 }

		
		-- 1.3.6.1.4.1.17409.2.2.11.3
		eponManagementObjGroup OBJECT IDENTIFIER ::= { eponAlarmTree 3 }

		
		-- 1.3.6.1.4.1.17409.2.2.11.3.1
		eponManagementAddrTable OBJECT-TYPE
			SYNTAX SEQUENCE OF EponManagementAddrEntry
			MAX-ACCESS not-accessible
			STATUS current
			DESCRIPTION
				"A table of transport addresses to be used in the generation
				of SNMP messages."
			::= { eponManagementObjGroup 1 }

		
		-- 1.3.6.1.4.1.17409.2.2.11.3.1.1
		eponManagementAddrEntry OBJECT-TYPE
			SYNTAX EponManagementAddrEntry
			MAX-ACCESS not-accessible
			STATUS current
			DESCRIPTION
				"A transport address to be used in the generation
				of SNMP operations.        
				Entries in the snmpTargetAddrTable are created and
				deleted using the snmpTargetAddrRowStatus object."
			INDEX { eponManagementAddrName }
			::= { eponManagementAddrTable 1 }

		
		EponManagementAddrEntry ::=
			SEQUENCE { 
				eponManagementAddrName
					OCTET STRING,
				eponManagementAddrTAddress
					TAddress,
				eponManagementAddrCommunity
					OCTET STRING,
				eponManagementAddrRowStatus
					RowStatus
			 }

		-- 1.3.6.1.4.1.17409.2.2.11.3.1.1.1
		eponManagementAddrName OBJECT-TYPE
			SYNTAX OCTET STRING (SIZE (1..32))
			MAX-ACCESS not-accessible
			STATUS current
			DESCRIPTION
				"
				EMS"
			::= { eponManagementAddrEntry 1 }

		
		-- 1.3.6.1.4.1.17409.2.2.11.3.1.1.2
		eponManagementAddrTAddress OBJECT-TYPE
			SYNTAX TAddress
			MAX-ACCESS read-create
			STATUS current
			DESCRIPTION
				"
				TRAP UDP"
			::= { eponManagementAddrEntry 2 }

		
		-- 1.3.6.1.4.1.17409.2.2.11.3.1.1.3
		eponManagementAddrCommunity OBJECT-TYPE
			SYNTAX OCTET STRING (SIZE (0..64))
			MAX-ACCESS read-create
			STATUS current
			DESCRIPTION
				"
				TRAPCommunity"
			::= { eponManagementAddrEntry 3 }

		
		-- 1.3.6.1.4.1.17409.2.2.11.3.1.1.4
		eponManagementAddrRowStatus OBJECT-TYPE
			SYNTAX RowStatus
			MAX-ACCESS read-create
			STATUS current
			DESCRIPTION
				"
				EPON"
			::= { eponManagementAddrEntry 4 }

		
--      DESCRIPTION
-- "(Alarms)MIB"
		-- 1.3.6.1.4.1.17409.2.3
		eponTree OBJECT IDENTIFIER ::= { nscrtvEponEocTree 3 }

		
		-- 1.3.6.1.4.1.17409.2.3.1
		systemObjects OBJECT IDENTIFIER ::= { eponTree 1 }

		
-- ------------------------------------------------------------------------------
-- systemObjects [](1.3.6.1.4.1.17409.2.3.1)
-- ------------------------------------------------------------------------------       
		-- 1.3.6.1.4.1.17409.2.3.1.1
		systemGlobalObjects OBJECT-IDENTITY
			STATUS current
			DESCRIPTION 
				""
			::= { systemObjects 1 }

		
		-- 1.3.6.1.4.1.17409.2.3.1.1.1
		systemTime OBJECT-TYPE
			SYNTAX DateAndTime
			MAX-ACCESS read-write
			STATUS current
			DESCRIPTION
				"
				        
				8"
			::= { systemGlobalObjects 1 }

		
		-- 1.3.6.1.4.1.17409.2.3.1.1.2
		inbandIpAddress OBJECT-TYPE
			SYNTAX IpAddress
			MAX-ACCESS read-write
			STATUS current
			DESCRIPTION
				"
				IP"
			::= { systemGlobalObjects 2 }

		
		-- 1.3.6.1.4.1.17409.2.3.1.1.3
		inbandIpSubnetMask OBJECT-TYPE
			SYNTAX IpAddress
			MAX-ACCESS read-write
			STATUS current
			DESCRIPTION
				"
				IP"
			::= { systemGlobalObjects 3 }

		
		-- 1.3.6.1.4.1.17409.2.3.1.1.4
		inbandIpGateway OBJECT-TYPE
			SYNTAX IpAddress
			MAX-ACCESS read-write
			STATUS current
			DESCRIPTION
				"
				IP"
			::= { systemGlobalObjects 4 }

		
		-- 1.3.6.1.4.1.17409.2.3.1.1.5
		inbandVlanId OBJECT-TYPE
			SYNTAX INTEGER
			MAX-ACCESS read-write
			STATUS current
			DESCRIPTION
				"
				VLAN ID.
				
				VLANVLAN"
			::= { systemGlobalObjects 5 }

		
		-- 1.3.6.1.4.1.17409.2.3.1.1.6
		inbandMacAddress OBJECT-TYPE
			SYNTAX MacAddress
			MAX-ACCESS read-only
			STATUS current
			DESCRIPTION
				"
				MAC."
			::= { systemGlobalObjects 6 }

		
		-- 1.3.6.1.4.1.17409.2.3.1.1.7
		outbandIpAddress OBJECT-TYPE
			SYNTAX IpAddress
			MAX-ACCESS read-write
			STATUS current
			DESCRIPTION
				"
				IP"
			::= { systemGlobalObjects 7 }

		
		-- 1.3.6.1.4.1.17409.2.3.1.1.8
		outbandIpSubnetMask OBJECT-TYPE
			SYNTAX IpAddress
			MAX-ACCESS read-write
			STATUS current
			DESCRIPTION
				"
				IP"
			::= { systemGlobalObjects 8 }

		
		-- 1.3.6.1.4.1.17409.2.3.1.1.9
		outbandIpGateway OBJECT-TYPE
			SYNTAX IpAddress
			MAX-ACCESS read-write
			STATUS current
			DESCRIPTION
				"
				IP"
			::= { systemGlobalObjects 9 }

		
		-- 1.3.6.1.4.1.17409.2.3.1.1.10
		outbandMacAddress OBJECT-TYPE
			SYNTAX MacAddress
			MAX-ACCESS read-only
			STATUS current
			DESCRIPTION
				"
				MAC"
			::= { systemGlobalObjects 10 }

		
		-- 1.3.6.1.4.1.17409.2.3.1.1.11
		systemOUI OBJECT-TYPE
			SYNTAX OCTET STRING (SIZE (3))
			MAX-ACCESS read-only
			STATUS current
			DESCRIPTION
				"
				OUI"
			::= { systemGlobalObjects 11 }

		
		-- 1.3.6.1.4.1.17409.2.3.1.1.12
		vendorName OBJECT-TYPE
			SYNTAX DisplayString
			MAX-ACCESS read-only
			STATUS current
			DESCRIPTION
				"
				Vender name of the OLT equipment"
			::= { systemGlobalObjects 12 }

		
		-- 1.3.6.1.4.1.17409.2.3.1.1.13
		devSn OBJECT-TYPE
			SYNTAX DisplayString
			MAX-ACCESS read-only
			STATUS current
			DESCRIPTION
				"
				Serial number of the OLT equipment"
			::= { systemGlobalObjects 13 }

		
		-- 1.3.6.1.4.1.17409.2.3.1.1.14
		saveConfig OBJECT-TYPE
			SYNTAX INTEGER
			MAX-ACCESS read-write
			STATUS current
			DESCRIPTION
				"
				Save device configuration when set value to 1."
			::= { systemGlobalObjects 14 }
		-- 1.3.6.1.4.1.17409.2.3.1.1.15	
        saveConfigStatus OBJECT-TYPE
        SYNTAX INTEGER{
             fail (0),
             success(1),
             inProcess(2)
          }
        MAX-ACCESS read-only
        STATUS current
        DESCRIPTION
       "
         Save device configuration status "
       ::= { systemGlobalObjects 15 }
		
		-- 1.3.6.1.4.1.17409.2.3.1.2
		oltObjects OBJECT-IDENTITY
			STATUS current
			DESCRIPTION 
				"
				OLT"
			::= { systemObjects 2 }

		
		-- 1.3.6.1.4.1.17409.2.3.1.2.1
		oltPropertyTable OBJECT-TYPE
			SYNTAX SEQUENCE OF OltPropertyEntry
			MAX-ACCESS not-accessible
			STATUS current
			DESCRIPTION
				"
				OLT"
			::= { oltObjects 1 }

		
		-- 1.3.6.1.4.1.17409.2.3.1.2.1.1
		oltPropertyEntry OBJECT-TYPE
			SYNTAX OltPropertyEntry
			MAX-ACCESS not-accessible
			STATUS current
			DESCRIPTION
				" "
			INDEX { oltDeviceIndex }
			::= { oltPropertyTable 1 }

		
		OltPropertyEntry ::=
			SEQUENCE { 
				oltDeviceIndex
					INTEGER,
				oltName
					DisplayString,
				oltType
					DisplayString,
				oltAdminStatus
					INTEGER,
				oltDeviceUpTime
					TimeStamp,
				oltDeviceNumOfTotalServiceSlot
					INTEGER,
				oltDeviceNumOfTotalPowerSlot
					INTEGER,
				oltDeviceNumOfTotalFanSlot
					INTEGER,
				oltDeviceStyle
					INTEGER
			 }

		-- 1.3.6.1.4.1.17409.2.3.1.2.1.1.1
		oltDeviceIndex OBJECT-TYPE
			SYNTAX INTEGER (1..2147483647)
			MAX-ACCESS read-only
			STATUS current
			DESCRIPTION
				"
				OLT
				
				OLTOLTOLTOLT"
			::= { oltPropertyEntry 1 }

		
		-- 1.3.6.1.4.1.17409.2.3.1.2.1.1.2



		oltName OBJECT-TYPE
			SYNTAX DisplayString
			MAX-ACCESS read-write
			STATUS current
			DESCRIPTION
				"
				OLT"
			::= { oltPropertyEntry 2 }

		
		-- 1.3.6.1.4.1.17409.2.3.1.2.1.1.3
		oltType OBJECT-TYPE
			SYNTAX DisplayString
			MAX-ACCESS read-only
			STATUS current
			DESCRIPTION
				"
				OLT"
			::= { oltPropertyEntry 3 }

		
		-- 1.3.6.1.4.1.17409.2.3.1.2.1.1.4
		oltAdminStatus OBJECT-TYPE
			SYNTAX INTEGER
				{
				up(1),
				down(2),
				testing(3)
				}
			MAX-ACCESS read-write
			STATUS current
			DESCRIPTION
				"
				OLT        
				up(1)      - 
				down(2)    - 
				testing(3) - "
			::= { oltPropertyEntry 4 }

		
		-- 1.3.6.1.4.1.17409.2.3.1.2.1.1.5
		oltDeviceUpTime OBJECT-TYPE
			SYNTAX TimeStamp
			MAX-ACCESS read-only
			STATUS current
			DESCRIPTION
				"
				OLT"
			::= { oltPropertyEntry 5 }

		
		-- 1.3.6.1.4.1.17409.2.3.1.2.1.1.6
		oltDeviceNumOfTotalServiceSlot OBJECT-TYPE
			SYNTAX INTEGER
			MAX-ACCESS read-only
			STATUS current
			DESCRIPTION
				"
				Total number of service slots in the OLT device, including
				service card, switch card, control card, uplink card, etc. 
				but except power, FAN, regardless whether the slot is installed
				module"
			::= { oltPropertyEntry 6 }

		
		-- 1.3.6.1.4.1.17409.2.3.1.2.1.1.7
		oltDeviceNumOfTotalPowerSlot OBJECT-TYPE
			SYNTAX INTEGER
			MAX-ACCESS read-only
			STATUS current
			DESCRIPTION
				"
				Total number of power slots in the OLT device, regardless whether 
				the slot is installed module"
			::= { oltPropertyEntry 7 }

		
		-- 1.3.6.1.4.1.17409.2.3.1.2.1.1.8
		oltDeviceNumOfTotalFanSlot OBJECT-TYPE
			SYNTAX INTEGER
			MAX-ACCESS read-only
			STATUS current
			DESCRIPTION
				"
				Total number of FAN slots in the OLT device, regardless whether 
				the slot is installed module"
			::= { oltPropertyEntry 8 }

		
		-- 1.3.6.1.4.1.17409.2.3.1.2.1.1.9
		oltDeviceStyle OBJECT-TYPE
			SYNTAX INTEGER
				{
				fixed(1),
				chassisBased(2),
				other(3)
				}
			MAX-ACCESS read-only
			STATUS current
			DESCRIPTION
				"
				The device stype of either fixed or chassis based        
				fixed(1) - such as pizza box
				chassisBased(2) - Have number of slots for installing service card, power card, etc.        
				"
			::= { oltPropertyEntry 9 }

		
		-- 1.3.6.1.4.1.17409.2.3.1.3
		boardObjects OBJECT-IDENTITY
			STATUS current
			DESCRIPTION 
				"
				"
			::= { systemObjects 3 }

		
		-- 1.3.6.1.4.1.17409.2.3.1.3.1
		boardTable OBJECT-TYPE
			SYNTAX SEQUENCE OF BoardEntry
			MAX-ACCESS not-accessible
			STATUS current
			DESCRIPTION
				"
				OLT        
				This table shall include rows for all slots, including the slots has
				a presence state of 'NotInstalled'.
				"
			::= { boardObjects 1 }

		
		-- 1.3.6.1.4.1.17409.2.3.1.3.1.1
		boardEntry OBJECT-TYPE
			SYNTAX BoardEntry
			MAX-ACCESS not-accessible
			STATUS current
			DESCRIPTION
				" "
			INDEX { bDeviceIndex, bCardIndex }
			::= { boardTable 1 }

		
		BoardEntry ::=
			SEQUENCE { 
				bDeviceIndex
					INTEGER,
				bCardIndex
					EponCardIndex,
				bType
					INTEGER,
				bAttribute
					INTEGER,
				bOperationStatus
					INTEGER,
				bAdminStatus
					INTEGER,
				bHardwareVersion
					DisplayString,
				bFirmwareVersion
					DisplayString,
				bSoftwareVersion
					DisplayString,
				bUpTime
					TimeStamp,
				bAlarmStatus
					BITS,
				bSerialNumber
					DisplayString,
				bAction
					INTEGER,
				bName
					OCTET STRING,
				bPresenceStatus
					INTEGER
			 }

		-- 1.3.6.1.4.1.17409.2.3.1.3.1.1.1
		bDeviceIndex OBJECT-TYPE
			SYNTAX INTEGER (1..2147483647)
			MAX-ACCESS not-accessible
			STATUS current
			DESCRIPTION
				"
				OLT        
				OLTOLTOLTOLT"
			::= { boardEntry 1 }

		
		-- 1.3.6.1.4.1.17409.2.3.1.3.1.1.2
		bCardIndex OBJECT-TYPE
			SYNTAX EponCardIndex (1..2147483647)
			MAX-ACCESS not-accessible
			STATUS current
			DESCRIPTION
				"
				"
			::= { boardEntry 2 }

		
		-- 1.3.6.1.4.1.17409.2.3.1.3.1.1.3
		bType OBJECT-TYPE
			SYNTAX INTEGER
				{
				controlBoard(1),
				geponBoard(2),
				uplinkBoard(3),
				switchBoard(4),
				other(5),
				vacant(6)
				}
			MAX-ACCESS read-only
			STATUS current
			DESCRIPTION
				"
				        
				controlBoard(1) - 
				geponBoard(2)    - GE EPON
				uplinkBoard(3)  - 
				switchBoard(4)  - 
				other(5)        -  
				vacant(6)   - 
				"
			::= { boardEntry 3 }

		
		-- 1.3.6.1.4.1.17409.2.3.1.3.1.1.4
		bAttribute OBJECT-TYPE
			SYNTAX INTEGER
				{
				active(1),
				standby(2),
				standalone(3),
				notApplicable(4)
				}
			MAX-ACCESS read-only
			STATUS current
			DESCRIPTION
				"
				 - 
				
				active(1)        -  
				standby(2)       - 
				standalone(3)    - OLT
				                   
				notApplicable(4) - "
			::= { boardEntry 4 }

		
		-- 1.3.6.1.4.1.17409.2.3.1.3.1.1.5
		bOperationStatus OBJECT-TYPE
			SYNTAX INTEGER
				{
				up(1),
				down(2),
				testing(3)
				}
			MAX-ACCESS read-only
			STATUS current
			DESCRIPTION
				"
				
				
				up(1)      - 
				down(2)    - 
				testing(3) - "
			::= { boardEntry 5 }

		
		-- 1.3.6.1.4.1.17409.2.3.1.3.1.1.6
		bAdminStatus OBJECT-TYPE
			SYNTAX INTEGER
				{
				up(1),
				down(2),
				testing(3)
				}
			MAX-ACCESS read-write
			STATUS current
			DESCRIPTION
				"
				        
				up(1)      - 
				down(2)    - 
				testing(3) - "
			::= { boardEntry 6 }

		
		-- 1.3.6.1.4.1.17409.2.3.1.3.1.1.7
		bHardwareVersion OBJECT-TYPE
			SYNTAX DisplayString
			MAX-ACCESS read-only
			STATUS current
			DESCRIPTION
				"
				"
			::= { boardEntry 7 }

		
		-- 1.3.6.1.4.1.17409.2.3.1.3.1.1.8
		bFirmwareVersion OBJECT-TYPE
			SYNTAX DisplayString
			MAX-ACCESS read-only
			STATUS current
			DESCRIPTION
				"
				"
			::= { boardEntry 8 }

		
		-- 1.3.6.1.4.1.17409.2.3.1.3.1.1.9
		bSoftwareVersion OBJECT-TYPE
			SYNTAX DisplayString
			MAX-ACCESS read-only
			STATUS current
			DESCRIPTION
				"
				"
			::= { boardEntry 9 }

		
		-- 1.3.6.1.4.1.17409.2.3.1.3.1.1.10
		bUpTime OBJECT-TYPE
			SYNTAX TimeStamp
			MAX-ACCESS read-only
			STATUS current
			DESCRIPTION
				"
				"
			::= { boardEntry 10 }

		
		-- 1.3.6.1.4.1.17409.2.3.1.3.1.1.11
		bAlarmStatus OBJECT-TYPE
			SYNTAX BITS
				{
				critical(0),
				major(1),
				minor(2),
				warning(3)
				}
			MAX-ACCESS read-only
			STATUS current
			DESCRIPTION
				"
				"
			::= { boardEntry 11 }

		
		-- 1.3.6.1.4.1.17409.2.3.1.3.1.1.12
		bSerialNumber OBJECT-TYPE
			SYNTAX DisplayString
			MAX-ACCESS read-only
			STATUS current
			DESCRIPTION
				"
				SN"
			::= { boardEntry 12 }

		
		-- 1.3.6.1.4.1.17409.2.3.1.3.1.1.13
		bAction OBJECT-TYPE
			SYNTAX INTEGER
				{
				noAction(1),
				switchover(2),
				upgrade(3)
				}
			MAX-ACCESS read-write
			STATUS current
			DESCRIPTION
				"
				        
				noAction(1)    - 
				switchover(2)  - 
				upgrade(3)     - "
			::= { boardEntry 13 }

		
		-- 1.3.6.1.4.1.17409.2.3.1.3.1.1.14
		bName OBJECT-TYPE
			SYNTAX OCTET STRING (SIZE (1..32))
			MAX-ACCESS read-only
			STATUS current
			DESCRIPTION
				"
				The board name defined by vendor individual"
			::= { boardEntry 14 }

		
		-- 1.3.6.1.4.1.17409.2.3.1.3.1.1.15
		bPresenceStatus OBJECT-TYPE
			SYNTAX INTEGER
				{
				installed(1),
				notInstalled(2),
				others(3)
				}
			MAX-ACCESS read-only
			STATUS current
			DESCRIPTION
				"The physical presence status of the slot"
			::= { boardEntry 15 }

		
		-- 1.3.6.1.4.1.17409.2.3.1.4
		powerObjects OBJECT-IDENTITY
			STATUS current
			DESCRIPTION 
				"
				"
			::= { systemObjects 4 }

		
		-- 1.3.6.1.4.1.17409.2.3.1.4.1
		powerPropertyTable OBJECT-TYPE
			SYNTAX SEQUENCE OF PowerPropertyEntry
			MAX-ACCESS not-accessible
			STATUS current
			DESCRIPTION
				"
				"
			::= { powerObjects 1 }

		
		-- 1.3.6.1.4.1.17409.2.3.1.4.1.1
		powerPropertyEntry OBJECT-TYPE
			SYNTAX PowerPropertyEntry
			MAX-ACCESS not-accessible
			STATUS current
			DESCRIPTION
				" "
			INDEX { powerDeviceIndex, powerCardIndex }
			::= { powerPropertyTable 1 }

		
		PowerPropertyEntry ::=
			SEQUENCE { 
				powerDeviceIndex
					INTEGER,
				powerCardIndex
					EponCardIndex,
				powerCardOperationStatus
					INTEGER,
				powerCardAlarmStatus
					BITS,
				powerCardAction
					INTEGER,
				powerCardName
					OCTET STRING,
				powerCardPresenceStatus
					INTEGER,
				powerCardRedundancyStatus
					INTEGER
			 }

		-- 1.3.6.1.4.1.17409.2.3.1.4.1.1.1
		powerDeviceIndex OBJECT-TYPE
			SYNTAX INTEGER (1..2147483647)
			MAX-ACCESS not-accessible
			STATUS current
			DESCRIPTION
				"
				OLT        
				OLTOLTOLTOLT"
			::= { powerPropertyEntry 1 }

		
		-- 1.3.6.1.4.1.17409.2.3.1.4.1.1.2
		powerCardIndex OBJECT-TYPE
			SYNTAX EponCardIndex
			MAX-ACCESS not-accessible
			STATUS current
			DESCRIPTION
				"
				"
			::= { powerPropertyEntry 2 }

		
		-- 1.3.6.1.4.1.17409.2.3.1.4.1.1.3
		powerCardOperationStatus OBJECT-TYPE
			SYNTAX INTEGER
				{
				up(1),
				down(2),
				testing(3)
				}
			MAX-ACCESS read-only
			STATUS current
			DESCRIPTION
				"
				        
				up(1)      - 
				down(2)    - 
				testing(3) - "
			::= { powerPropertyEntry 3 }

		
		-- 1.3.6.1.4.1.17409.2.3.1.4.1.1.4
		powerCardAlarmStatus OBJECT-TYPE
			SYNTAX BITS
				{
				critical(0),
				major(1),
				minor(2),
				warning(3)
				}
			MAX-ACCESS read-only
			STATUS current
			DESCRIPTION
				"
				"
			::= { powerPropertyEntry 4 }

		
		-- 1.3.6.1.4.1.17409.2.3.1.4.1.1.5
		powerCardAction OBJECT-TYPE
			SYNTAX INTEGER
				{
				noAction(1),
				switchover(2)
				}
			MAX-ACCESS read-write
			STATUS current
			DESCRIPTION
				"
				        
				noAction(1)    - 
				switchover(2)  - 
				
				Note:
				
				Switchover(2) shall be only set to the power board with powerCardRedundancyStatus
				of active(1)"
			::= { powerPropertyEntry 5 }

		
		-- 1.3.6.1.4.1.17409.2.3.1.4.1.1.6
		powerCardName OBJECT-TYPE
			SYNTAX OCTET STRING (SIZE (1..32))
			MAX-ACCESS read-only
			STATUS current
			DESCRIPTION
				"
				The power card name defined by vendor individual"
			::= { powerPropertyEntry 6 }

		
		-- 1.3.6.1.4.1.17409.2.3.1.4.1.1.7
		powerCardPresenceStatus OBJECT-TYPE
			SYNTAX INTEGER
				{
				installed(1),
				notInstalled(2),
				others(3)
				}
			MAX-ACCESS read-only
			STATUS current
			DESCRIPTION
				"The physical presence status of the power slot"
			::= { powerPropertyEntry 7 }

		
		-- 1.3.6.1.4.1.17409.2.3.1.4.1.1.8
		powerCardRedundancyStatus OBJECT-TYPE
			SYNTAX INTEGER
				{
				active(1),
				stanby(2),
				standalone(3),
				loadShareing(4)
				}
			MAX-ACCESS read-only
			STATUS current
			DESCRIPTION
				"The redundancy status of the power card        
				active(1)   -   The power card is working on redundanct active/
				            Standby mode and the current role is active.
				stanby(2)   - The power card is working on redundanct active/
				            Standby mode and the current role is standby.
				standalone(3) -   The power card is not working on redundanct mode 
				          and the current role is standalone.
				loadShareing(4) -   The power card is working on redundanct loadsharing
				          mode.
				"
			::= { powerPropertyEntry 8 }

		
		-- 1.3.6.1.4.1.17409.2.3.1.5
		fanObjects OBJECT-IDENTITY
			STATUS current
			DESCRIPTION 
				"
				"
			::= { systemObjects 5 }

		
		-- 1.3.6.1.4.1.17409.2.3.1.5.1
		fanPropertyTable OBJECT-TYPE
			SYNTAX SEQUENCE OF FanPropertyEntry
			MAX-ACCESS not-accessible
			STATUS current
			DESCRIPTION
				"
				"
			::= { fanObjects 1 }

		
		-- 1.3.6.1.4.1.17409.2.3.1.5.1.1
		fanPropertyEntry OBJECT-TYPE
			SYNTAX FanPropertyEntry
			MAX-ACCESS not-accessible
			STATUS current
			DESCRIPTION
				" "
			INDEX { fanDeviceIndex, fanCardIndex }
			::= { fanPropertyTable 1 }

		
		FanPropertyEntry ::=
			SEQUENCE { 
				fanDeviceIndex
					INTEGER,
				fanCardIndex
					EponCardIndex,
				fanCardOperationStatus
					INTEGER,
				fanCardAlarmStatus
					BITS,
				fanCardName
					OCTET STRING,
				fanCardPresenceStatus
					INTEGER
			 }

		-- 1.3.6.1.4.1.17409.2.3.1.5.1.1.1
		fanDeviceIndex OBJECT-TYPE
			SYNTAX INTEGER (1..2147483647)
			MAX-ACCESS not-accessible
			STATUS current
			DESCRIPTION
				"
				OLT        
				OLTOLTOLTOLT"
			::= { fanPropertyEntry 1 }

		
		-- 1.3.6.1.4.1.17409.2.3.1.5.1.1.2
		fanCardIndex OBJECT-TYPE
			SYNTAX EponCardIndex (1..2147483647)
			MAX-ACCESS not-accessible
			STATUS current
			DESCRIPTION
				"
				"
			::= { fanPropertyEntry 2 }

		
		-- 1.3.6.1.4.1.17409.2.3.1.5.1.1.3
		fanCardOperationStatus OBJECT-TYPE
			SYNTAX INTEGER
				{
				up(1),
				down(2),
				testing(3)
				}
			MAX-ACCESS read-only
			STATUS current
			DESCRIPTION
				"
				        
				up(1)      - 
				down(2)    - 
				testing(3) - "
			::= { fanPropertyEntry 3 }

		
		-- 1.3.6.1.4.1.17409.2.3.1.5.1.1.4
		fanCardAlarmStatus OBJECT-TYPE
			SYNTAX BITS
				{
				critical(0),
				major(1),
				minor(2),
				warning(3)
				}
			MAX-ACCESS read-only
			STATUS current
			DESCRIPTION
				"
				"
			::= { fanPropertyEntry 4 }

		
		-- 1.3.6.1.4.1.17409.2.3.1.5.1.1.5
		fanCardName OBJECT-TYPE
			SYNTAX OCTET STRING (SIZE (1..32))
			MAX-ACCESS read-only
			STATUS current
			DESCRIPTION
				"
				The FAN card name defined by vendor individual"
			::= { fanPropertyEntry 5 }

		
		-- 1.3.6.1.4.1.17409.2.3.1.5.1.1.6
		fanCardPresenceStatus OBJECT-TYPE
			SYNTAX INTEGER
				{
				installed(1),
				notInstalled(2),
				others(3)
				}
			MAX-ACCESS read-only
			STATUS current
			DESCRIPTION
				"The physical presence status of the FAN card slot"
			::= { fanPropertyEntry 6 }

		
		-- 1.3.6.1.4.1.17409.2.3.1.6
		fileTransferManagement OBJECT-IDENTITY
			STATUS current
			DESCRIPTION 
				"
				"
			::= { systemObjects 6 }

		
		-- 1.3.6.1.4.1.17409.2.3.1.6.1
		fileTransferTable OBJECT-TYPE
			SYNTAX SEQUENCE OF FileTransferEntry
			MAX-ACCESS not-accessible
			STATUS current
			DESCRIPTION
				"
				"
			::= { fileTransferManagement 1 }

		
		-- 1.3.6.1.4.1.17409.2.3.1.6.1.1
		fileTransferEntry OBJECT-TYPE
			SYNTAX FileTransferEntry
			MAX-ACCESS not-accessible
			STATUS current
			DESCRIPTION
				" "
			INDEX { fileTransferIndex }
			::= { fileTransferTable 1 }

		
		FileTransferEntry ::=
			SEQUENCE { 
				fileTransferIndex
					INTEGER,
				fileTransferProtocolType
					INTEGER,
				serverIpAddress
					IpAddress,
				ftpUserName
					DisplayString,
				ftpUserPassword
					DisplayString,
				transferFileSrcNamePath
					DisplayString,
				transferFileDstNamePath
					DisplayString,
				transferAction
					INTEGER,
				transferStatus
					INTEGER
			 }

		-- 1.3.6.1.4.1.17409.2.3.1.6.1.1.1
		fileTransferIndex OBJECT-TYPE
			SYNTAX INTEGER (1..10)
			MAX-ACCESS not-accessible
			STATUS current
			DESCRIPTION
				"
				"
			::= { fileTransferEntry 1 }

		
		-- 1.3.6.1.4.1.17409.2.3.1.6.1.1.2
		fileTransferProtocolType OBJECT-TYPE
			SYNTAX INTEGER
				{
				ftp(1),
				tftp(2)
				}
			MAX-ACCESS read-write
			STATUS current
			DESCRIPTION
				"
				"
			::= { fileTransferEntry 2 }

		
		-- 1.3.6.1.4.1.17409.2.3.1.6.1.1.3
		serverIpAddress OBJECT-TYPE
			SYNTAX IpAddress
			MAX-ACCESS read-write
			STATUS current
			DESCRIPTION
				"
				IP"
			::= { fileTransferEntry 3 }

		
		-- 1.3.6.1.4.1.17409.2.3.1.6.1.1.4
		ftpUserName OBJECT-TYPE
			SYNTAX DisplayString
			MAX-ACCESS read-write
			STATUS current
			DESCRIPTION
				"
				FTP"
			::= { fileTransferEntry 4 }

		
		-- 1.3.6.1.4.1.17409.2.3.1.6.1.1.5
		ftpUserPassword OBJECT-TYPE
			SYNTAX DisplayString
			MAX-ACCESS read-write
			STATUS current
			DESCRIPTION
				"
				FTP"
			::= { fileTransferEntry 5 }

		
		-- 1.3.6.1.4.1.17409.2.3.1.6.1.1.6
		transferFileSrcNamePath OBJECT-TYPE
			SYNTAX DisplayString
			MAX-ACCESS read-write
			STATUS current
			DESCRIPTION
				"
				'/tftproot/file/image.bin"
			::= { fileTransferEntry 6 }

		
		-- 1.3.6.1.4.1.17409.2.3.1.6.1.1.7
		transferFileDstNamePath OBJECT-TYPE
			SYNTAX DisplayString
			MAX-ACCESS read-write
			STATUS current
			DESCRIPTION
				"
				'/tftproot/file/image.bin"
			::= { fileTransferEntry 7 }

		
		-- 1.3.6.1.4.1.17409.2.3.1.6.1.1.8
		transferAction OBJECT-TYPE
			SYNTAX INTEGER
				{
				noOperation(1),
				put(2),
				get(3),
				halt(4)
				}
			MAX-ACCESS read-write
			STATUS current
			DESCRIPTION
				"
				        
				noOperation(1) - 
				put(2)       - 
				get(3)         - 
				halt(4)        - "
			::= { fileTransferEntry 8 }

		
		-- 1.3.6.1.4.1.17409.2.3.1.6.1.1.9
		transferStatus OBJECT-TYPE
			SYNTAX INTEGER
				{
				idle(1),
				inProgress(2),
				success(3),
				failure(4)
				}
			MAX-ACCESS read-only
			STATUS current
			DESCRIPTION
				"
				        
				idle(1)       - 
				inProgress(2) - 
				success(3)    - 
				failure(4)    - "
			::= { fileTransferEntry 9 }

		
		-- 1.3.6.1.4.1.17409.2.3.1.6.2
		fileInfoManagementTable OBJECT-TYPE
			SYNTAX SEQUENCE OF FileInfoManagementEntry
			MAX-ACCESS not-accessible
			STATUS current
			DESCRIPTION
				"
				OLT        
				It is done by file list per directionary.        
				Please walk filePath for the file lists in the specified
				path. If leave it NULL or walk fileInfoManagementEntry,
				the file list of the root directionary shall be returned        
				"
			::= { fileTransferManagement 2 }

		
		-- 1.3.6.1.4.1.17409.2.3.1.6.2.1
		fileInfoManagementEntry OBJECT-TYPE
			SYNTAX FileInfoManagementEntry
			MAX-ACCESS not-accessible
			STATUS current
			DESCRIPTION
				" "
			INDEX { filePath, fileName }
			::= { fileInfoManagementTable 1 }

		
		FileInfoManagementEntry ::=
			SEQUENCE { 
				filePath
					DisplayString,
				fileName
					DisplayString,
				fileSize
					Counter32,
				fileModifyTime
					DateAndTime,
				fileManagementAction
					INTEGER,
				fileAttribute
					INTEGER
			 }

		-- 1.3.6.1.4.1.17409.2.3.1.6.2.1.1
		filePath OBJECT-TYPE
			SYNTAX DisplayString
			MAX-ACCESS not-accessible
			STATUS current
			DESCRIPTION
				"
				File path        
				It shall be started with a length octet, followed with path string. The length octet
				shall indicate the number of character octets, excluding length itself.        
				For example, 0x05 41 42 43 44 45, respresents ABCDE        
				It shall be ended with '/', which is used to distinguish the two DisplayString
				indexes. For example, if the path is flash/root, filePath shall be set to flash/root/. 
				"
			::= { fileInfoManagementEntry 1 }

		
		-- 1.3.6.1.4.1.17409.2.3.1.6.2.1.2
		fileName OBJECT-TYPE
			SYNTAX DisplayString
			MAX-ACCESS not-accessible
			STATUS current
			DESCRIPTION
				"
				File name. MUST not include '/' character and MUST not be NULL.        
				It shall be started with a length octet, followed with name string. The length octet
				shall indicate the number of character octets, excluding length itself.        
				For example, 0x05 41 42 43 44 45, respresents ABCDE
				"
			::= { fileInfoManagementEntry 2 }

		
		-- 1.3.6.1.4.1.17409.2.3.1.6.2.1.3
		fileSize OBJECT-TYPE
			SYNTAX Counter32
			UNITS "bytes"
			MAX-ACCESS read-only
			STATUS current
			DESCRIPTION
				"
				"
			::= { fileInfoManagementEntry 3 }

		
		-- 1.3.6.1.4.1.17409.2.3.1.6.2.1.4
		fileModifyTime OBJECT-TYPE
			SYNTAX DateAndTime
			MAX-ACCESS read-only
			STATUS current
			DESCRIPTION
				"
				"
			::= { fileInfoManagementEntry 4 }

		
		-- 1.3.6.1.4.1.17409.2.3.1.6.2.1.5
		fileManagementAction OBJECT-TYPE
			SYNTAX INTEGER
				{
				noOperation(1),
				erase(2)
				}
			MAX-ACCESS read-write
			STATUS current
			DESCRIPTION
				"
				        
				noOperation(1) - 
				erase(2)       - "
			::= { fileInfoManagementEntry 5 }

		
--  It is a file
-- It is a directionary
		-- 1.3.6.1.4.1.17409.2.3.1.6.2.1.6
		fileAttribute OBJECT-TYPE
			SYNTAX INTEGER
				{
				file(1),
				dir(2)
				}
			MAX-ACCESS read-only
			STATUS current
			DESCRIPTION
				"
				The attribute of the file"
			::= { fileInfoManagementEntry 6 }

		
--ONU\u6279\u5904\u7406\u5347\u7ea7\u8868

 onuBatchUpgradeTable OBJECT-TYPE
 SYNTAX SEQUENCE OF OnuBatchUpgradeEntry
 MAX-ACCESS not-accessible
 STATUS current
 DESCRIPTION
 "ONU\u6279\u5904\u7406\u5347\u7ea7\u8868,\u5177\u4f53\u5b9e\u73b0\u6d41\u7a0b\u89c1\u9644\u5f55A.1 "
 ::= { systemObjects 7 }

	
	onuBatchUpgradeEntry OBJECT-TYPE
	  SYNTAX OnuBatchUpgradeEntry
	  MAX-ACCESS not-accessible
	  STATUS current
	  DESCRIPTION
	    " "
	    INDEX { onuBatchUpgradeIndex }
	  ::= { onuBatchUpgradeTable 1 }	

	OnuBatchUpgradeEntry ::=
	  SEQUENCE {
	    onuBatchUpgradeIndex
	      INTEGER,
	    onuBatchUpgradeOnuList
	      OCTET STRING,
	    onuBatchUpgradeAction
	      INTEGER,
	    onuBatchUpgradeStatus
	      OCTET STRING,
	    onuBatchUpgradeImageName
	      DisplayString
	  }
	
    onuBatchUpgradeIndex OBJECT-TYPE
      SYNTAX INTEGER (1..16)
      MAX-ACCESS not-accessible
      STATUS current
      DESCRIPTION
        "
        onu\u5347\u7ea7\u64cd\u4f5c\u7d22\u5f15,OLT\u5382\u5546\u6839\u636eOLT\u5bf9ONU\u5347\u7ea7\u7684\u5e76\u884c\u80fd\u529b,\u5efa\u7acb\u4e00\u5b9a\u6570\u91cf\u7684\u5347\u7ea7\u64cd\u4f5c\u9879,\u81f3\u5c11\u4e3a1,\u4e0d\u5f3a\u5236\u8981\u6c42\u5e76\u884c\u5347\u7ea7\u591a\u7c7b\u578bONU,\u5141\u8bb8\u4e32\u884c\u65b9\u5f0f\u6267\u884c"
      ::= { onuBatchUpgradeEntry 1 }

	onuBatchUpgradeOnuList OBJECT-TYPE
	  SYNTAX OCTET STRING
	  MAX-ACCESS read-write
	  STATUS current
	  DESCRIPTION
	    "Onu\u5217\u8868,\u6bcf4byte\u8868\u793a\u4e00\u4e2aonu(\u53c2\u7167EponDeviceIndex),\u957f\u5ea6\u4e3a4 * (onu\u4e2a\u6570),\u6700\u5927\u957f\u5ea6\u662f4*256"
	  ::= { onuBatchUpgradeEntry 2 }
	
	
	onuBatchUpgradeAction OBJECT-TYPE
	  SYNTAX INTEGER
	  MAX-ACCESS read-write
	  STATUS current
	  DESCRIPTION
	    "\u5199\u5165\u4efb\u610f\u503c\u89e6\u53d1\u5347\u7ea7"
	  ::= { onuBatchUpgradeEntry 3 }
	
	
	onuBatchUpgradeStatus OBJECT-TYPE
	  SYNTAX OCTET STRING
	  MAX-ACCESS read-only
	  STATUS current
	  DESCRIPTION
	    "
	    Onu\u5217\u8868,\u6bcf2byte\u8868\u793a\u4e00\u4e2aonu\u7684\u5347\u7ea7\u72b6\u6001,\u957f\u5ea6\u4e3a2 * (onu\u4e2a\u6570),\u540c\u5f53\u524d\u5347\u7ea7\u4efb\u52a1\u7684onulist\u4e00\u4e00\u5bf9\u5e94
	    \u72b6\u6001\u7801\u8bf4\u660e\uff1a
	    1\uff1aIdle
	    2\uff1aWaiting
	    3\uff1aInProgress
	    4\uff1aSuccess
	    5\uff1aFailure(\u4e0d\u786e\u5b9a\u539f\u56e0\u7684\u9519\u8bef)
	    6\uff1aOnuTypeNotConsistent(Onu\u7c7b\u578b\u4e0d\u4e00\u81f4)
	    7\uff1aFileDownloadFail(\u4e0b\u8f7d\u955c\u50cf\u5931\u8d25,\u5305\u62ecOLT\u5185\u90e8\u677f\u5361\u95f4\u4f20\u8f93\u5931\u8d25\u6216\u8005\u6587\u4ef6\u524d\u7f6e\u6821\u9a8c\u5931\u8d25)
	    8\uff1aOnuNotExist(Onu\u6389\u7ebf\u6216\u8005\u522b\u7684\u5bfc\u81f4Onuid\u5931\u6548\u7684\u60c5\u51b5)
	    9\uff1aNotConsistent(Onu\u540c\u5347\u7ea7\u6587\u4ef6\u4e0d\u5339\u914d)
	    10\uff1aOnuCommunicationFail(Onu\u901a\u4fe1\u5931\u8d25)
	    "
	  ::= { onuBatchUpgradeEntry 4 }
	
	onuBatchUpgradeImageName OBJECT-TYPE
	  SYNTAX DisplayString
	  MAX-ACCESS read-write
	  STATUS current
	  DESCRIPTION
	    "\u5199\u5165\u7528\u4e8e\u5347\u7ea7\u7684ONU\u955c\u50cf\u6587\u4ef6\u540d"
	  ::= { onuBatchUpgradeEntry 5 }	
	

		
		-- 1.3.6.1.4.1.17409.2.3.2
		sniObjects OBJECT IDENTIFIER ::= { eponTree 2 }

		
-- ------------------------------------------------------------------------------
-- sniObjects [OLT](1.3.6.1.4.1.17409.2.3.2)
-- ------------------------------------------------------------------------------  
		-- 1.3.6.1.4.1.17409.2.3.2.1
		sniAttributeTable OBJECT-TYPE
			SYNTAX SEQUENCE OF SniAttributeEntry
			MAX-ACCESS not-accessible
			STATUS current
			DESCRIPTION
				"A list of sniAttributeTable entries. "
			::= { sniObjects 1 }

		
		-- 1.3.6.1.4.1.17409.2.3.2.1.1
		sniAttributeEntry OBJECT-TYPE
			SYNTAX SniAttributeEntry
			MAX-ACCESS not-accessible
			STATUS current
			DESCRIPTION
				"The sniAttributeEntry Information"
			INDEX { sniAttributeDeviceIndex, sniAttributeCardIndex, sniAttributePortIndex }
			::= { sniAttributeTable 1 }

		
		SniAttributeEntry ::=
			SEQUENCE { 
				sniAttributeDeviceIndex
					INTEGER,
				sniAttributeCardIndex
					EponCardIndex,
				sniAttributePortIndex
					EponPortIndex,
				sniPortName
					DisplayString,
				sniAdminStatus
					INTEGER,
				sniOperationStatus
					INTEGER,
				sniMediaType
					INTEGER,
				sniAutoNegotiationStatus
					INTEGER,
				sniAutoNegotiationMode
					INTEGER,
				sniPerfStats15minuteEnable
					TruthValue,
				sniPerfStats24hourEnable
					TruthValue,
				sniLastStatusChangeTime
					TimeTicks,
				sniMacAddrLearnMaxNum
					INTEGER,
				sniIsolationEnable
					TruthValue,
				sniPortType
					INTEGER
			 }

		-- 1.3.6.1.4.1.17409.2.3.2.1.1.1
		sniAttributeDeviceIndex OBJECT-TYPE
			SYNTAX INTEGER (1..2147483647)
			MAX-ACCESS not-accessible
			STATUS current
			DESCRIPTION
				"Device Index"
			::= { sniAttributeEntry 1 }

		
		-- 1.3.6.1.4.1.17409.2.3.2.1.1.2
		sniAttributeCardIndex OBJECT-TYPE
			SYNTAX EponCardIndex (1..2147483647)
			MAX-ACCESS not-accessible
			STATUS current
			DESCRIPTION
				"Card Index"
			::= { sniAttributeEntry 2 }

		
		-- 1.3.6.1.4.1.17409.2.3.2.1.1.3
		sniAttributePortIndex OBJECT-TYPE
			SYNTAX EponPortIndex (1..2147483647)
			MAX-ACCESS not-accessible
			STATUS current
			DESCRIPTION
				"Port Index"
			::= { sniAttributeEntry 3 }

		
		-- 1.3.6.1.4.1.17409.2.3.2.1.1.4
		sniPortName OBJECT-TYPE
			SYNTAX DisplayString
			MAX-ACCESS read-write
			STATUS current
			DESCRIPTION
				"Port Name"
			::= { sniAttributeEntry 4 }

		
		-- 1.3.6.1.4.1.17409.2.3.2.1.1.5
		sniAdminStatus OBJECT-TYPE
			SYNTAX INTEGER
				{
				up(1),
				down(2),
				testing(3)
				}
			MAX-ACCESS read-write
			STATUS current
			DESCRIPTION
				"Admin Status"
			::= { sniAttributeEntry 5 }

		
		-- 1.3.6.1.4.1.17409.2.3.2.1.1.6
		sniOperationStatus OBJECT-TYPE
			SYNTAX INTEGER
				{
				up(1),
				down(2),
				testing(3)
				}
			MAX-ACCESS read-only
			STATUS current
			DESCRIPTION
				"Operation Status"
			::= { sniAttributeEntry 6 }

		
		-- 1.3.6.1.4.1.17409.2.3.2.1.1.7
		sniMediaType OBJECT-TYPE
			SYNTAX INTEGER
				{
				twistedPair(1),
				fiber(2),
				other(3)
				}
			MAX-ACCESS read-only
			STATUS current
			DESCRIPTION
				"Media Type"
			::= { sniAttributeEntry 7 }

		
		-- 1.3.6.1.4.1.17409.2.3.2.1.1.8
		sniAutoNegotiationStatus OBJECT-TYPE
			SYNTAX INTEGER
				{
				auto-negotiate(1),
				half-10(2),
				full-10(3),
				half-100(4),
				full-100(5),
				full-1000(6),
				full-10000(7),
				unknown(8)
				}
			MAX-ACCESS read-only
			STATUS current
			DESCRIPTION
				"Auto Negotiation Status"
			::= { sniAttributeEntry 8 }

		
		-- 1.3.6.1.4.1.17409.2.3.2.1.1.9
		sniAutoNegotiationMode OBJECT-TYPE
			SYNTAX INTEGER
				{
				auto-negotiate(1),
				half-10(2),
				full-10(3),
				half-100(4),
				full-100(5),
				full-1000(6),
				full-10000(7)
				}
			MAX-ACCESS read-write
			STATUS current
			DESCRIPTION
				"Auto Negotiation Mode"
			::= { sniAttributeEntry 9 }

		
		-- 1.3.6.1.4.1.17409.2.3.2.1.1.10
		sniPerfStats15minuteEnable OBJECT-TYPE
			SYNTAX TruthValue
			MAX-ACCESS read-write
			STATUS current
			DESCRIPTION
				"true(1) false(2)"
			::= { sniAttributeEntry 10 }

		
		-- 1.3.6.1.4.1.17409.2.3.2.1.1.11
		sniPerfStats24hourEnable OBJECT-TYPE
			SYNTAX TruthValue
			MAX-ACCESS read-write
			STATUS current
			DESCRIPTION
				"true(1) false(2)"
			::= { sniAttributeEntry 11 }

		
		-- 1.3.6.1.4.1.17409.2.3.2.1.1.12
		sniLastStatusChangeTime OBJECT-TYPE
			SYNTAX TimeTicks
			MAX-ACCESS read-only
			STATUS current
			DESCRIPTION
				"Last Change Time"
			::= { sniAttributeEntry 12 }

		
		-- 1.3.6.1.4.1.17409.2.3.2.1.1.13
		sniMacAddrLearnMaxNum OBJECT-TYPE
			SYNTAX INTEGER
			MAX-ACCESS read-write
			STATUS current
			DESCRIPTION
				"Number of MAC address limited on the SNI port.            
				value 0 means no limit"
			::= { sniAttributeEntry 13 }

		
		-- 1.3.6.1.4.1.17409.2.3.2.1.1.14
		sniIsolationEnable OBJECT-TYPE
			SYNTAX TruthValue
			MAX-ACCESS read-write
			STATUS current
			DESCRIPTION
				"Whether or not isolate the SNI port to other ports"
			::= { sniAttributeEntry 14 }

		
		-- 1.3.6.1.4.1.17409.2.3.2.1.1.15
		sniPortType OBJECT-TYPE
			SYNTAX INTEGER
				{
				ge-Port(1),
				te-Port(2)
				}
			MAX-ACCESS read-only
			STATUS current
			DESCRIPTION
				" SNI port type, Ge-Port, Te-Port"
			::= { sniAttributeEntry 15 }

		
		-- 1.3.6.1.4.1.17409.2.3.2.2
		sniTrunkManagement OBJECT-IDENTITY
			STATUS current
			DESCRIPTION 
				" "
			::= { sniObjects 2 }

		
		-- 1.3.6.1.4.1.17409.2.3.2.2.1
		sniTrunkGroupConfigTable OBJECT-TYPE
			SYNTAX SEQUENCE OF SniTrunkGroupConfigEntry
			MAX-ACCESS not-accessible
			STATUS current
			DESCRIPTION
				"A list of sniTrunkGroupConfigTable entries."
			::= { sniTrunkManagement 1 }

		
		-- 1.3.6.1.4.1.17409.2.3.2.2.1.1
		sniTrunkGroupConfigEntry OBJECT-TYPE
			SYNTAX SniTrunkGroupConfigEntry
			MAX-ACCESS not-accessible
			STATUS current
			DESCRIPTION
				"The sniTrunk Group Config Entry Information"
			INDEX { sniTrunkGroupConfigIndex }
			::= { sniTrunkGroupConfigTable 1 }

		
		SniTrunkGroupConfigEntry ::=
			SEQUENCE { 
				sniTrunkGroupConfigIndex
					INTEGER,
				sniTrunkGroupConfigName
					DisplayString,
				sniTrunkGroupConfigMember
					OCTET STRING,
				sniTrunkGroupConfigPolicy
					INTEGER,
				sniTrunkGroupConfigRowstatus
					RowStatus
			 }

		-- 1.3.6.1.4.1.17409.2.3.2.2.1.1.1
		sniTrunkGroupConfigIndex OBJECT-TYPE
			SYNTAX INTEGER (1..2147483647)
			MAX-ACCESS not-accessible
			STATUS current
			DESCRIPTION
				"Trunk Group Config Index"
			::= { sniTrunkGroupConfigEntry 1 }

		
		-- 1.3.6.1.4.1.17409.2.3.2.2.1.1.2
		sniTrunkGroupConfigName OBJECT-TYPE
			SYNTAX DisplayString
			MAX-ACCESS read-create
			STATUS current
			DESCRIPTION
				"Trunk Group Config Name"
			::= { sniTrunkGroupConfigEntry 2 }

		
		-- 1.3.6.1.4.1.17409.2.3.2.2.1.1.3
		sniTrunkGroupConfigMember OBJECT-TYPE
			SYNTAX OCTET STRING
			MAX-ACCESS read-create
			STATUS current
			DESCRIPTION
				"Trunk Group Config Member.            
				It is presented by member port list. Each member port is identified
				by 4-byte format, same as TC of EponDeviceIndex. The actual length of
				this string depends of the number of member ports in the trunk group.
				The relationship is:            
				Length of the string = 4 * (NUM of member ports)              
				For example, if device 1, port 1/2 and 2/3 is the member ports of the
				trunk, then sniTrunkGroupConfigMember is presented as:
				01 01 02 00 01 02 03 00
				"
			::= { sniTrunkGroupConfigEntry 3 }

		
		-- 1.3.6.1.4.1.17409.2.3.2.2.1.1.4
		sniTrunkGroupConfigPolicy OBJECT-TYPE
			SYNTAX INTEGER
				{
				srcMac(1),
				destMac(2),
				srcMacNDestMac(3),
				srcIp(4),
				destIp(5),
				srcIpNDestIp(6)
				}
			MAX-ACCESS read-create
			STATUS current
			DESCRIPTION
				"Trunk Group Config Policy"
			::= { sniTrunkGroupConfigEntry 4 }

		
		-- 1.3.6.1.4.1.17409.2.3.2.2.1.1.5
		sniTrunkGroupConfigRowstatus OBJECT-TYPE
			SYNTAX RowStatus
			MAX-ACCESS read-create
			STATUS current
			DESCRIPTION
				"Trunk Group Config Rowstatus"
			::= { sniTrunkGroupConfigEntry 5 }

		
		-- 1.3.6.1.4.1.17409.2.3.2.2.2
		sniTrunkGroupTable OBJECT-TYPE
			SYNTAX SEQUENCE OF SniTrunkGroupEntry
			MAX-ACCESS not-accessible
			STATUS current
			DESCRIPTION
				"a list of sniTrunkGroupConfigTable entries. "
			::= { sniTrunkManagement 2 }

		
		-- 1.3.6.1.4.1.17409.2.3.2.2.2.1
		sniTrunkGroupEntry OBJECT-TYPE
			SYNTAX SniTrunkGroupEntry
			MAX-ACCESS not-accessible
			STATUS current
			DESCRIPTION
				"Trunk Group Entry"
			INDEX { sniTrunkGroupIndex }
			::= { sniTrunkGroupTable 1 }

		
		SniTrunkGroupEntry ::=
			SEQUENCE { 
				sniTrunkGroupIndex
					INTEGER,
				sniTrunkGroupOperationStatus
					INTEGER,
				sniTrunkGroupActualSpeed
					INTEGER,
				sniTrunkGroupAdminStatus
					INTEGER
			 }

		-- 1.3.6.1.4.1.17409.2.3.2.2.2.1.1
		sniTrunkGroupIndex OBJECT-TYPE
			SYNTAX INTEGER (1..2147483647)
			MAX-ACCESS not-accessible
			STATUS current
			DESCRIPTION
				"Trunk Group Index "
			::= { sniTrunkGroupEntry 1 }

		
		-- 1.3.6.1.4.1.17409.2.3.2.2.2.1.2
		sniTrunkGroupOperationStatus OBJECT-TYPE
			SYNTAX INTEGER
				{
				up(1),
				down(2),
				testing(3)
				}
			MAX-ACCESS read-only
			STATUS current
			DESCRIPTION
				"Trunk Group Operation Status"
			::= { sniTrunkGroupEntry 2 }

		
		-- 1.3.6.1.4.1.17409.2.3.2.2.2.1.3
		sniTrunkGroupActualSpeed OBJECT-TYPE
			SYNTAX INTEGER
			UNITS "Mbps"
			MAX-ACCESS read-only
			STATUS current
			DESCRIPTION
				"Trunk Group Actual Speed.            
				The speed is the aggregated rates of all operational UP member
				ports of the trunk.            
				For example, 4 member ports of the trunk, two are UP, each is 1000M
				then the SUN is 2000M. As a result, the return of the MIB shall be
				2000Mbps"
			::= { sniTrunkGroupEntry 3 }

		
		-- 1.3.6.1.4.1.17409.2.3.2.2.2.1.4
		sniTrunkGroupAdminStatus OBJECT-TYPE
			SYNTAX INTEGER
				{
				up(1),
				down(2),
				testing(3)
				}
			MAX-ACCESS read-write
			STATUS current
			DESCRIPTION
				"Trunk Group AdminStatus"
			::= { sniTrunkGroupEntry 4 }

		
		-- 1.3.6.1.4.1.17409.2.3.2.3
		sniMirrorTable OBJECT-TYPE
			SYNTAX SEQUENCE OF SniMirrorEntry
			MAX-ACCESS not-accessible
			STATUS current
			DESCRIPTION
				"a list of sniMirrorTable entries."
			::= { sniObjects 3 }

		
		-- 1.3.6.1.4.1.17409.2.3.2.3.1
		sniMirrorEntry OBJECT-TYPE
			SYNTAX SniMirrorEntry
			MAX-ACCESS not-accessible
			STATUS current
			DESCRIPTION
				"The Mirror Information."
			INDEX { sniMirrorGroupIndex }
			::= { sniMirrorTable 1 }

		
		SniMirrorEntry ::=
			SEQUENCE { 
				sniMirrorGroupIndex
					INTEGER,
				sniMirrorGroupName
					DisplayString,
				sniMirrorGroupDstPortList
					OCTET STRING,
				sniMirrorGroupSrcInPortList
					OCTET STRING,
				sniMirrorGroupSrcOutPortList
					OCTET STRING,
				sniMirrorGroupRowstatus
					RowStatus
			 }

		-- 1.3.6.1.4.1.17409.2.3.2.3.1.1
		sniMirrorGroupIndex OBJECT-TYPE
			SYNTAX INTEGER (1..2147483647)
			MAX-ACCESS not-accessible
			STATUS current
			DESCRIPTION
				"Mirror Group Index"
			::= { sniMirrorEntry 1 }

		
		-- 1.3.6.1.4.1.17409.2.3.2.3.1.2
		sniMirrorGroupName OBJECT-TYPE
			SYNTAX DisplayString
			MAX-ACCESS read-create
			STATUS current
			DESCRIPTION
				"Mirror Group Name"
			::= { sniMirrorEntry 2 }

		
		-- 1.3.6.1.4.1.17409.2.3.2.3.1.3
		sniMirrorGroupDstPortList OBJECT-TYPE
			SYNTAX OCTET STRING
			MAX-ACCESS read-create
			STATUS current
			DESCRIPTION
				"Mirror Group Dst Port List.            
				It is presented by destination port list. Each  port is identified
				by 4-byte format, same as TC of EponDeviceIndex. The actual length of
				this string depends of the number of destination ports in this mirror 
				instance.            
				The relationship is:            
				Length of the string = 4 * (NUM of ports)              
				For example, if device 1, port 2/3 is the destination port of the
				mirror instance, then object will be presented as:
				01 02 03 00
				"
			::= { sniMirrorEntry 3 }

		
		-- 1.3.6.1.4.1.17409.2.3.2.3.1.4
		sniMirrorGroupSrcInPortList OBJECT-TYPE
			SYNTAX OCTET STRING
			MAX-ACCESS read-create
			STATUS current
			DESCRIPTION
				"Mirror Group Src In Port List.            
				It will includes the PON ports.            
				It is presented by source ingress port list. Each  port is identified
				by 4-byte format, same as TC of EponDeviceIndex. The actual length of
				this string depends of the number of source ingress ports in this mirror 
				instance.            
				The relationship is:            
				Length of the string = 4 * (NUM of ports)              
				For example, if device 1, port 2/3, device 6, port 7/8 is the source
				ingress port of the mirror instance, then object will be presented as:
				01 02 03 00 06 07 08 00            
				"
			::= { sniMirrorEntry 4 }

		
		-- 1.3.6.1.4.1.17409.2.3.2.3.1.5
		sniMirrorGroupSrcOutPortList OBJECT-TYPE
			SYNTAX OCTET STRING
			MAX-ACCESS read-create
			STATUS current
			DESCRIPTION
				"Mirror Group Src Out Port List.            
				It will includes the PON ports.            
				It is presented by source egress port list. Each  port is identified
				by 4-byte format, same as TC of EponDeviceIndex. The actual length of
				this string depends of the number of source egress ports in this mirror 
				instance.            
				The relationship is:            
				Length of the string = 4 * (NUM of ports)              
				For example, if device 1, port 2/3, device 6, port 7/8 is the source
				egress port of the mirror instance, then object will be presented as:
				01 02 03 00 06 07 08 00
				"
			::= { sniMirrorEntry 5 }

		
		-- 1.3.6.1.4.1.17409.2.3.2.3.1.6
		sniMirrorGroupRowstatus OBJECT-TYPE
			SYNTAX RowStatus
			MAX-ACCESS read-create
			STATUS current
			DESCRIPTION
				"Mirror Group Rowstatus"
			::= { sniMirrorEntry 6 }

		
		-- 1.3.6.1.4.1.17409.2.3.2.4
		sniMacAddressManagement OBJECT-IDENTITY
			STATUS current
			DESCRIPTION 
				" "
			::= { sniObjects 4 }

		
		-- 1.3.6.1.4.1.17409.2.3.2.4.1
		sniMacAddressManagementTable OBJECT-TYPE
			SYNTAX SEQUENCE OF SniMacAddressManagementEntry
			MAX-ACCESS not-accessible
			STATUS current
			DESCRIPTION
				" A list of MacAddressManagement entries. "
			::= { sniMacAddressManagement 1 }

		
		-- 1.3.6.1.4.1.17409.2.3.2.4.1.1
		sniMacAddressManagementEntry OBJECT-TYPE
			SYNTAX SniMacAddressManagementEntry
			MAX-ACCESS not-accessible
			STATUS current
			DESCRIPTION
				"The Mac Address Management Information"
			INDEX { sniMacAddressManagementDeviceIndex }
			::= { sniMacAddressManagementTable 1 }

		
		SniMacAddressManagementEntry ::=
			SEQUENCE { 
				sniMacAddressManagementDeviceIndex
					INTEGER,
				sniMacAddrTableAgingTime
					INTEGER,
				sniMacAddrTableClear
					INTEGER
			 }

		-- 1.3.6.1.4.1.17409.2.3.2.4.1.1.1
		sniMacAddressManagementDeviceIndex OBJECT-TYPE
			SYNTAX INTEGER (1..2147483647)
			MAX-ACCESS not-accessible
			STATUS current
			DESCRIPTION
				"device Index"
			::= { sniMacAddressManagementEntry 1 }

		
		-- 1.3.6.1.4.1.17409.2.3.2.4.1.1.2
		sniMacAddrTableAgingTime OBJECT-TYPE
			SYNTAX INTEGER (10..10000)
			UNITS "Seconds"
			MAX-ACCESS read-write
			STATUS current
			DESCRIPTION
				"Mac Address Table Aging Time"
			::= { sniMacAddressManagementEntry 2 }

		
		-- 1.3.6.1.4.1.17409.2.3.2.4.1.1.3
		sniMacAddrTableClear OBJECT-TYPE
			SYNTAX INTEGER { allDynamic(1),allStatic(2),allBlackhole(3),all(4),none(5)}
			MAX-ACCESS read-write
			STATUS current
			DESCRIPTION
				"Mac Address Table Clear"
			::= { sniMacAddressManagementEntry 3 }

		
		-- 1.3.6.1.4.1.17409.2.3.2.4.2
		sniMacAddressTable OBJECT-TYPE
			SYNTAX SEQUENCE OF SniMacAddressEntry
			MAX-ACCESS not-accessible
			STATUS current
			DESCRIPTION
				"A list of MacAddress entries."
			::= { sniMacAddressManagement 2 }

		
		-- 1.3.6.1.4.1.17409.2.3.2.4.2.1
		sniMacAddressEntry OBJECT-TYPE
			SYNTAX SniMacAddressEntry
			MAX-ACCESS not-accessible
			STATUS current
			DESCRIPTION
				"The Mac Address Information"
			INDEX { sniMacAddrIndex, sniMacAddrVlanIdIndex }
			::= { sniMacAddressTable 1 }

		
		SniMacAddressEntry ::=
			SEQUENCE { 
				sniMacAddrIndex
					MacAddress,
				sniMacAddrVlanIdIndex
					INTEGER,
				sniMacAddrType
					INTEGER,
				sniMacAddrPortId
					EponDeviceIndex,
				sniMacAddrRowStatus
					RowStatus
			 }

		-- 1.3.6.1.4.1.17409.2.3.2.4.2.1.1
		sniMacAddrIndex OBJECT-TYPE
			SYNTAX MacAddress
			MAX-ACCESS not-accessible
			STATUS current
			DESCRIPTION
				"Mac Address Index"
			::= { sniMacAddressEntry 1 }

		
		-- 1.3.6.1.4.1.17409.2.3.2.4.2.1.2
		sniMacAddrVlanIdIndex OBJECT-TYPE
			SYNTAX INTEGER (0..2147483647)
			MAX-ACCESS not-accessible
			STATUS current
			DESCRIPTION
				"Mac Address Vlan Id Index"
			::= { sniMacAddressEntry 2 }

		
		-- 1.3.6.1.4.1.17409.2.3.2.4.2.1.3
		sniMacAddrType OBJECT-TYPE
			SYNTAX INTEGER
				{
				static(1),
				dynamic(2),
				blackhole(3)
				}
			MAX-ACCESS read-create
			STATUS current
			DESCRIPTION
				"Mac Address Type"
			::= { sniMacAddressEntry 3 }

		
		-- 1.3.6.1.4.1.17409.2.3.2.4.2.1.4
		sniMacAddrPortId OBJECT-TYPE
			SYNTAX EponDeviceIndex
			MAX-ACCESS read-create
			STATUS current
			DESCRIPTION
				"Mac Address Port Id"
			::= { sniMacAddressEntry 4 }

		
		-- 1.3.6.1.4.1.17409.2.3.2.4.2.1.5
		sniMacAddrRowStatus OBJECT-TYPE
			SYNTAX RowStatus
			MAX-ACCESS read-create
			STATUS current
			DESCRIPTION
				"delete,create,Update"
			::= { sniMacAddressEntry 5 }

		
		-- 1.3.6.1.4.1.17409.2.3.2.5
		sniBroadcastStormSuppressionTable OBJECT-TYPE
			SYNTAX SEQUENCE OF SniBroadcastStormSuppressionEntry
			MAX-ACCESS not-accessible
			STATUS current
			DESCRIPTION
				"A list of BroadcastStormSuppression entries."
			::= { sniObjects 5 }

		
		-- 1.3.6.1.4.1.17409.2.3.2.5.1
		sniBroadcastStormSuppressionEntry OBJECT-TYPE
			SYNTAX SniBroadcastStormSuppressionEntry
			MAX-ACCESS not-accessible
			STATUS current
			DESCRIPTION
				"The Broadcast Storm Suppression Information"
			INDEX { sniBroadcastStormSuppressionDeviceIndex, sniBroadcastStormSuppressionCardIndex, sniBroadcastStormSuppressionPortIndex }
			::= { sniBroadcastStormSuppressionTable 1 }

		
		SniBroadcastStormSuppressionEntry ::=
			SEQUENCE { 
				sniBroadcastStormSuppressionDeviceIndex
					INTEGER,
				sniBroadcastStormSuppressionCardIndex
					EponCardIndex,
				sniBroadcastStormSuppressionPortIndex
					EponPortIndex,
				sniUnicastStormEnable
					TruthValue,
				sniUnicastStormInPacketRate
					INTEGER,
				sniUnicastStormOutPacketRate
					INTEGER,
				sniMulticastStormEnable
					TruthValue,
				sniMulticastStormInPacketRate
					INTEGER,
				sniMulticastStormOutPacketRate
					INTEGER,
				sniBroadcastStormEnable
					TruthValue,
				sniBroadcastStormInPacketRate
					INTEGER,
				sniBroadcastStormOutPacketRate
					INTEGER
			 }

		-- 1.3.6.1.4.1.17409.2.3.2.5.1.1
		sniBroadcastStormSuppressionDeviceIndex OBJECT-TYPE
			SYNTAX INTEGER (1..2147483647)
			MAX-ACCESS not-accessible
			STATUS current
			DESCRIPTION
				"device Index"
			::= { sniBroadcastStormSuppressionEntry 1 }

		
		-- 1.3.6.1.4.1.17409.2.3.2.5.1.2
		sniBroadcastStormSuppressionCardIndex OBJECT-TYPE
			SYNTAX EponCardIndex (1..2147483647)
			MAX-ACCESS not-accessible
			STATUS current
			DESCRIPTION
				"card Index"
			::= { sniBroadcastStormSuppressionEntry 2 }

		
		-- 1.3.6.1.4.1.17409.2.3.2.5.1.3
		sniBroadcastStormSuppressionPortIndex OBJECT-TYPE
			SYNTAX EponPortIndex (1..2147483647)
			MAX-ACCESS not-accessible
			STATUS current
			DESCRIPTION
				"port Index"
			::= { sniBroadcastStormSuppressionEntry 3 }

		
		-- 1.3.6.1.4.1.17409.2.3.2.5.1.4
		sniUnicastStormEnable OBJECT-TYPE
			SYNTAX TruthValue
			MAX-ACCESS read-write
			STATUS current
			DESCRIPTION
				"Cast Storm Enable"
			::= { sniBroadcastStormSuppressionEntry 4 }

		
		-- 1.3.6.1.4.1.17409.2.3.2.5.1.5
		sniUnicastStormInPacketRate OBJECT-TYPE
			SYNTAX INTEGER
			UNITS "pps"
			MAX-ACCESS read-write
			STATUS current
			DESCRIPTION
				"Cast Storm In Packet Rate"
			::= { sniBroadcastStormSuppressionEntry 5 }

		
		-- 1.3.6.1.4.1.17409.2.3.2.5.1.6
		sniUnicastStormOutPacketRate OBJECT-TYPE
			SYNTAX INTEGER
			UNITS "pps"
			MAX-ACCESS read-write
			STATUS current
			DESCRIPTION
				"Cast Storm Out Packet Rate"
			::= { sniBroadcastStormSuppressionEntry 6 }

		
		-- 1.3.6.1.4.1.17409.2.3.2.5.1.7
		sniMulticastStormEnable OBJECT-TYPE
			SYNTAX TruthValue
			MAX-ACCESS read-write
			STATUS current
			DESCRIPTION
				"true(1) false(2)"
			::= { sniBroadcastStormSuppressionEntry 7 }

		
		-- 1.3.6.1.4.1.17409.2.3.2.5.1.8
		sniMulticastStormInPacketRate OBJECT-TYPE
			SYNTAX INTEGER
			UNITS "pps"
			MAX-ACCESS read-write
			STATUS current
			DESCRIPTION
				"Multicast Storm In Packet Rate"
			::= { sniBroadcastStormSuppressionEntry 8 }

		
		-- 1.3.6.1.4.1.17409.2.3.2.5.1.9
		sniMulticastStormOutPacketRate OBJECT-TYPE
			SYNTAX INTEGER
			UNITS "pps"
			MAX-ACCESS read-write
			STATUS current
			DESCRIPTION
				"Multicast Storm Out Packet Rate"
			::= { sniBroadcastStormSuppressionEntry 9 }

		
		-- 1.3.6.1.4.1.17409.2.3.2.5.1.10
		sniBroadcastStormEnable OBJECT-TYPE
			SYNTAX TruthValue
			MAX-ACCESS read-write
			STATUS current
			DESCRIPTION
				"true(1) false(2)"
			::= { sniBroadcastStormSuppressionEntry 10 }

		
		-- 1.3.6.1.4.1.17409.2.3.2.5.1.11
		sniBroadcastStormInPacketRate OBJECT-TYPE
			SYNTAX INTEGER
			UNITS "pps"
			MAX-ACCESS read-write
			STATUS current
			DESCRIPTION
				"Broadcast Storm In Packet Rate"
			::= { sniBroadcastStormSuppressionEntry 11 }

		
		-- 1.3.6.1.4.1.17409.2.3.2.5.1.12
		sniBroadcastStormOutPacketRate OBJECT-TYPE
			SYNTAX INTEGER
			UNITS "pps"
			MAX-ACCESS read-write
			STATUS current
			DESCRIPTION
				"Broadcast Storm Out Packet Rate"
			::= { sniBroadcastStormSuppressionEntry 12 }

		
		-- 1.3.6.1.4.1.17409.2.3.3
		ponPortObjects OBJECT IDENTIFIER ::= { eponTree 3 }

		
-- ------------------------------------------------------------------------------
-- ponPortObjects[PON](1.3.6.1.4.1.17409.2.3.3)
-- ------------------------------------------------------------------------------ 
		-- 1.3.6.1.4.1.17409.2.3.3.1
		ponPortInfoTable OBJECT-TYPE
			SYNTAX SEQUENCE OF PonPortInfoEntry
			MAX-ACCESS not-accessible
			STATUS current
			DESCRIPTION
				"PON"
			::= { ponPortObjects 1 }

		
		-- 1.3.6.1.4.1.17409.2.3.3.1.1
		ponPortInfoEntry OBJECT-TYPE
			SYNTAX PonPortInfoEntry
			MAX-ACCESS not-accessible
			STATUS current
			DESCRIPTION
				" "
			INDEX { ponDeviceIndex, ponCardIndex, ponPortIndex }
			::= { ponPortInfoTable 1 }

		
		PonPortInfoEntry ::=
			SEQUENCE { 
				ponDeviceIndex
					INTEGER,
				ponCardIndex
					EponCardIndex,
				ponPortIndex
					EponPortIndex,
				ponPortType
					INTEGER,
				ponOperationStatus
					INTEGER,
				ponPortAdminStatus
					INTEGER,
				ponPortMaxOnuNumSupport
					INTEGER,
				ponPortUpOnuNum
					INTEGER,
				ponPortEncryptMode
					INTEGER,
				ponPortEncryptKeyExchangeTime
					INTEGER,
				ponPortIsolationEnable
					TruthValue,
				maxDsBandwidth
					INTEGER,
				actualDsBandwidthInUse
					INTEGER,
				remainDsBandwidth
					INTEGER,
				perfStats15minuteEnable
					TruthValue,
				perfStats24hourEnable
					TruthValue,
				ponPortMacAddrLearnMaxNum
					INTEGER,
				maxUsBandwidth
					INTEGER,
				actualUsBandwidthInUse
					INTEGER,
				remainUsBandwidth
					INTEGER,
				ponPortName
					DisplayString,
				onuLongEmitDetectEnable
					INTEGER
			 }

		-- 1.3.6.1.4.1.17409.2.3.3.1.1.1
		ponDeviceIndex OBJECT-TYPE
			SYNTAX INTEGER (1..2147483647)
			MAX-ACCESS not-accessible
			STATUS current
			DESCRIPTION
				"
				OLT        
				OLTOLTOLTOLT"
			::= { ponPortInfoEntry 1 }

		
		-- 1.3.6.1.4.1.17409.2.3.3.1.1.2
		ponCardIndex OBJECT-TYPE
			SYNTAX EponCardIndex (1..2147483647)
			MAX-ACCESS not-accessible
			STATUS current
			DESCRIPTION
				"
				"
			::= { ponPortInfoEntry 2 }

		
		-- 1.3.6.1.4.1.17409.2.3.3.1.1.3
		ponPortIndex OBJECT-TYPE
			SYNTAX EponPortIndex (1..2147483647)
			MAX-ACCESS not-accessible
			STATUS current
			DESCRIPTION
				"
				pon"
			::= { ponPortInfoEntry 3 }

		
		-- 1.3.6.1.4.1.17409.2.3.3.1.1.4
		ponPortType OBJECT-TYPE
			SYNTAX INTEGER
				{
				ge-epon(1),
				tenge-epon(2),
				gpon(3),
				other(4)
				}
			MAX-ACCESS read-only
			STATUS current
			DESCRIPTION
				"
				PON"
			::= { ponPortInfoEntry 4 }

		
		-- 1.3.6.1.4.1.17409.2.3.3.1.1.5
		ponOperationStatus OBJECT-TYPE
			SYNTAX INTEGER
				{
				up(1),
				down(2),
				testing(3)
				}
			MAX-ACCESS read-only
			STATUS current
			DESCRIPTION
				"
				        
				up(1)      - 
				down(2)    - 
				testing(3) - "
			::= { ponPortInfoEntry 5 }

		
		-- 1.3.6.1.4.1.17409.2.3.3.1.1.6
		ponPortAdminStatus OBJECT-TYPE
			SYNTAX INTEGER
				{
				enable(1),
				disable(2)
				}
			MAX-ACCESS read-write
			STATUS current
			DESCRIPTION
				"
				        
				enable (1)      - 
				disable (2)    - "
			::= { ponPortInfoEntry 6 }

		
		-- 1.3.6.1.4.1.17409.2.3.3.1.1.7
		ponPortMaxOnuNumSupport OBJECT-TYPE
			SYNTAX INTEGER
			MAX-ACCESS read-only
			STATUS current
			DESCRIPTION
				"
				ONU"
			::= { ponPortInfoEntry 7 }

		
		-- 1.3.6.1.4.1.17409.2.3.3.1.1.8
		ponPortUpOnuNum OBJECT-TYPE
			SYNTAX INTEGER
			MAX-ACCESS read-only
			STATUS current
			DESCRIPTION
				"
				ONU"
			::= { ponPortInfoEntry 8 }

		
		-- 1.3.6.1.4.1.17409.2.3.3.1.1.9
		ponPortEncryptMode OBJECT-TYPE
			SYNTAX INTEGER
				{
				aes128(1),
				ctcTripleChurning(2),
				other(3)
				}
			MAX-ACCESS read-write
			STATUS current
			DESCRIPTION
				"
				"
			::= { ponPortInfoEntry 9 }

		
		-- 1.3.6.1.4.1.17409.2.3.3.1.1.10
		ponPortEncryptKeyExchangeTime OBJECT-TYPE
			SYNTAX INTEGER
			UNITS "seconds"
			MAX-ACCESS read-write
			STATUS current
			DESCRIPTION
				"
				"
			::= { ponPortInfoEntry 10 }

		
		-- 1.3.6.1.4.1.17409.2.3.3.1.1.11
		ponPortIsolationEnable OBJECT-TYPE
			SYNTAX TruthValue
			MAX-ACCESS read-write
			STATUS current
			DESCRIPTION
				"
				PON"
			::= { ponPortInfoEntry 11 }

		
		-- 1.3.6.1.4.1.17409.2.3.3.1.1.12
		maxDsBandwidth OBJECT-TYPE
			SYNTAX INTEGER
			UNITS "kbps"
			MAX-ACCESS read-only
			STATUS current
			DESCRIPTION
				"
				"
			::= { ponPortInfoEntry 12 }

		
		-- 1.3.6.1.4.1.17409.2.3.3.1.1.13
		actualDsBandwidthInUse OBJECT-TYPE
			SYNTAX INTEGER
			UNITS "kbps"
			MAX-ACCESS read-only
			STATUS current
			DESCRIPTION
				"
				"
			::= { ponPortInfoEntry 13 }

		
		-- 1.3.6.1.4.1.17409.2.3.3.1.1.14
		remainDsBandwidth OBJECT-TYPE
			SYNTAX INTEGER
			UNITS "kbps"
			MAX-ACCESS read-only
			STATUS current
			DESCRIPTION
				"
				"
			::= { ponPortInfoEntry 14 }

		
		-- 1.3.6.1.4.1.17409.2.3.3.1.1.15
		perfStats15minuteEnable OBJECT-TYPE
			SYNTAX TruthValue
			MAX-ACCESS read-write
			STATUS current
			DESCRIPTION
				"
				15"
			::= { ponPortInfoEntry 15 }

		
		-- 1.3.6.1.4.1.17409.2.3.3.1.1.16
		perfStats24hourEnable OBJECT-TYPE
			SYNTAX TruthValue
			MAX-ACCESS read-write
			STATUS current
			DESCRIPTION
				"
				24"
			::= { ponPortInfoEntry 16 }

		
		-- 1.3.6.1.4.1.17409.2.3.3.1.1.17
		ponPortMacAddrLearnMaxNum OBJECT-TYPE
			SYNTAX INTEGER
			MAX-ACCESS read-write
			STATUS current
			DESCRIPTION
				"
				PONmac        
				value 0 means no limit"
			::= { ponPortInfoEntry 17 }

		
		-- 1.3.6.1.4.1.17409.2.3.3.1.1.18
		maxUsBandwidth OBJECT-TYPE
			SYNTAX INTEGER
			UNITS "kbps"
			MAX-ACCESS read-only
			STATUS current
			DESCRIPTION
				"
				"
			::= { ponPortInfoEntry 18 }

		
		-- 1.3.6.1.4.1.17409.2.3.3.1.1.19
		actualUsBandwidthInUse OBJECT-TYPE
			SYNTAX INTEGER
			UNITS "kbps"
			MAX-ACCESS read-only
			STATUS current
			DESCRIPTION
				"
				"
			::= { ponPortInfoEntry 19 }

		
		-- 1.3.6.1.4.1.17409.2.3.3.1.1.20
		remainUsBandwidth OBJECT-TYPE
			SYNTAX INTEGER
			UNITS "kbps"
			MAX-ACCESS read-only
			STATUS current
			DESCRIPTION
				"
				"
			::= { ponPortInfoEntry 20 }

		
		-- 1.3.6.1.4.1.17409.2.3.3.1.1.21
		ponPortName OBJECT-TYPE
			SYNTAX DisplayString
			MAX-ACCESS read-write
			STATUS current
			DESCRIPTION
				"
				
				PON port name."
			::= { ponPortInfoEntry 21 }

		
		-- 1.3.6.1.4.1.17409.2.3.3.1.1.22
		onuLongEmitDetectEnable OBJECT-TYPE
			SYNTAX INTEGER{
			     disable (0),
	             enable (1)
	           
             }
			MAX-ACCESS read-write
			STATUS current
			DESCRIPTION
				"PONONU
				01"
			::= { ponPortInfoEntry 22 }

		
		-- 1.3.6.1.4.1.17409.2.3.3.2
		aclManagementGroup OBJECT-IDENTITY
			STATUS current
			DESCRIPTION 
				"
				ACL"
			::= { ponPortObjects 2 }

		
		-- 1.3.6.1.4.1.17409.2.3.3.2.1
		aclListTable OBJECT-TYPE
			SYNTAX SEQUENCE OF AclListEntry
			MAX-ACCESS not-accessible
			STATUS current
			DESCRIPTION
				"
				ACL"
			::= { aclManagementGroup 1 }

		
		-- 1.3.6.1.4.1.17409.2.3.3.2.1.1
		aclListEntry OBJECT-TYPE
			SYNTAX AclListEntry
			MAX-ACCESS not-accessible
			STATUS current
			DESCRIPTION
				" "
			INDEX { aclListIndex }
			::= { aclListTable 1 }

		
		AclListEntry ::=
			SEQUENCE { 
				aclListIndex
					INTEGER,
				aclDescription
					DisplayString,
				aclRuleList
					OCTET STRING,
				ruleRowStatus
					RowStatus
			 }

		-- 1.3.6.1.4.1.17409.2.3.3.2.1.1.1
		aclListIndex OBJECT-TYPE
			SYNTAX INTEGER (1..2147483647)
			MAX-ACCESS not-accessible
			STATUS current
			DESCRIPTION
				"
				ACL"
			::= { aclListEntry 1 }

		
		-- 1.3.6.1.4.1.17409.2.3.3.2.1.1.2
		aclDescription OBJECT-TYPE
			SYNTAX DisplayString
			MAX-ACCESS read-create
			STATUS current
			DESCRIPTION
				"
				ACL"
			::= { aclListEntry 2 }

		
		-- 1.3.6.1.4.1.17409.2.3.3.2.1.1.3
--		aclRuleList OBJECT-TYPE
--			SYNTAX OCTET STRING (SIZE (0..64))
--			MAX-ACCESS read-create
--			STATUS current
--			DESCRIPTION
--				"
--				ACL        
--			INTERNETOCTETOCTET 0, OCTET 1, ...
--				OCTETbitbit0bit1...bit7
--				bitOCTETbitaclRuleTable
--				aclRuleIndexbitaclRuleIndex        
--				80ACL ruleaclRuleIndex1..8010
--				aclRuleListaclListACL rule1,15,38aclRuleList
--				0x80 02 00 00 04 00 00 00 00 00"
--			::= { aclListEntry 3 }

		
		-- 1.3.6.1.4.1.17409.2.3.3.2.1.1.4
		ruleRowStatus OBJECT-TYPE
			SYNTAX RowStatus
			MAX-ACCESS read-create
			STATUS current
			DESCRIPTION
				"
				"
			::= { aclListEntry 3 }

		
		-- 1.3.6.1.4.1.17409.2.3.3.2.2
		aclRuleTable OBJECT-TYPE
			SYNTAX SEQUENCE OF AclRuleEntry
			MAX-ACCESS not-accessible
			STATUS current
			DESCRIPTION
				"
				ACL"
			::= { aclManagementGroup 2 }

		
		-- 1.3.6.1.4.1.17409.2.3.3.2.2.1
		aclRuleEntry OBJECT-TYPE
			SYNTAX AclRuleEntry
			MAX-ACCESS not-accessible
			STATUS current
			DESCRIPTION
				" "
			INDEX {aclRuleListIndex, aclRuleIndex }
			::= { aclRuleTable 1 }

		
		    AclRuleEntry ::=
      SEQUENCE { 
aclRuleListIndex
          INTEGER,
        aclRuleIndex
          INTEGER,
        matchedSourseMac
          MacAddress,
        matchedDestinationMac
          MacAddress,
        matchedVlanId
          INTEGER,
        matchedEthernetType
          INTEGER,
        matchedSourseIP
          IpAddress,
        matchedDestinationIP
          IpAddress,
        matchedIpMessageType
          INTEGER,
        matchedDscp
          INTEGER,
        matchedSoursePort
          INTEGER,
        matchedDestinationPort
          INTEGER,
        aclRuleRowStatus
          RowStatus,
        matchedFieldSelection
          OCTET STRING,
        aclAction
          INTEGER,
        aclActionParameter
          OCTET STRING,
        matchedSourseMacMask
          MacAddress,
	matchedDestinationMacMask 
	  MacAddress,
	matchedSourseIPMask 
	 IpAddress,
	matchedDestinationIPMask
	 IpAddress
       }

	 aclRuleListIndex OBJECT-TYPE
      SYNTAX INTEGER
      MAX-ACCESS not-accessible
      STATUS current
      DESCRIPTION
        " "
      ::= { aclRuleEntry 1 }


    aclRuleIndex OBJECT-TYPE
      SYNTAX INTEGER
      MAX-ACCESS not-accessible
      STATUS current
      DESCRIPTION
        "
        ACL"
      ::= { aclRuleEntry 2 }

    matchedSourseMac OBJECT-TYPE
      SYNTAX MacAddress
      MAX-ACCESS read-create
      STATUS current
      DESCRIPTION
        ""
      ::= { aclRuleEntry 3 }

    matchedDestinationMac OBJECT-TYPE
      SYNTAX MacAddress
      MAX-ACCESS read-create
      STATUS current
      DESCRIPTION
        ""
      ::= { aclRuleEntry 4 }

    matchedVlanId OBJECT-TYPE
      SYNTAX INTEGER (0..4094)
      MAX-ACCESS read-create
      STATUS current
      DESCRIPTION
        "
        \u95c1\u544a\u7255\u7f0d\u5a47\u5d22\u9288\u590b\u510d\u95b8\u64b3\u3008an id"
      ::= { aclRuleEntry 5 }

    matchedEthernetType OBJECT-TYPE
      SYNTAX INTEGER
      MAX-ACCESS read-create
      STATUS current
      DESCRIPTION
        ""
      ::= { aclRuleEntry 6 }

    matchedSourseIP OBJECT-TYPE
      SYNTAX IpAddress
      MAX-ACCESS read-create
      STATUS current
      DESCRIPTION
        "
        \u95c1\u544a\u7255\u7f0d\u5a47\u5d22\u9288\u590b\u510d\u95b8\u66e8\u525b\u9416\u76dcP"
      ::= { aclRuleEntry 7 }

    matchedDestinationIP OBJECT-TYPE
      SYNTAX IpAddress
      MAX-ACCESS read-create
      STATUS current
      DESCRIPTION
        "
        \u95c1\u544a\u7255\u7f0d\u5a47\u5d22\u9288\u590b\u510d\u95b8\u66e8\u53bd\u7ed0\u6945\u67e3\u928a\u30e5\u6bacP"
      ::= { aclRuleEntry 8 }
    
    matchedIpMessageType OBJECT-TYPE
      SYNTAX INTEGER (0..255)
      MAX-ACCESS read-create
      STATUS current
      DESCRIPTION
        ""
      ::= { aclRuleEntry 9 }

    matchedDscp OBJECT-TYPE
      SYNTAX INTEGER (0..63)
      MAX-ACCESS read-create
      STATUS current
      DESCRIPTION
        "
        "
      ::= { aclRuleEntry 10 }    
    matchedSoursePort OBJECT-TYPE
      SYNTAX INTEGER (0..65535)
      MAX-ACCESS read-create
      STATUS current
      DESCRIPTION
        "
        "
      ::= { aclRuleEntry 11 }
    
    matchedDestinationPort OBJECT-TYPE
      SYNTAX INTEGER  (0..65535)
      MAX-ACCESS read-create
      STATUS current
      DESCRIPTION
        "
        "
      ::= { aclRuleEntry 12 }

    aclRuleRowStatus OBJECT-TYPE
      SYNTAX RowStatus
      MAX-ACCESS read-create
      STATUS current
      DESCRIPTION
        "
        "
      ::= { aclRuleEntry 13 }

    matchedFieldSelection OBJECT-TYPE
      SYNTAX OCTET STRING (SIZE (2))
      MAX-ACCESS read-create
      STATUS current
      DESCRIPTION
        "
      "  
      ::= { aclRuleEntry 14 }

    aclAction OBJECT-TYPE
      SYNTAX INTEGER
        {
        permit(1),
        deny(2),
        mark(3)
        }
      MAX-ACCESS read-create
      STATUS current
      DESCRIPTION
        "
        "
      ::= { aclRuleEntry 15 }

    aclActionParameter OBJECT-TYPE
      SYNTAX OCTET STRING
      MAX-ACCESS read-create
      STATUS current
      DESCRIPTION
        "
      "  
      ::= { aclRuleEntry 16 }
      
      matchedSourseMacMask OBJECT-TYPE
      SYNTAX MacAddress
      MAX-ACCESS read-create
      STATUS current
      DESCRIPTION
        "
        \u95c1\u544a\u7255\u7f0d\u5a47\u5d22\u9288\u590b\u510d\u95b8\u66e8\u525b\u9416\u76e1AC\u95c1\u7845\u3000\u93c5\u6fcb\u60a5\u951f\ufffd"
      ::= { aclRuleEntry 17 }

    matchedDestinationMacMask OBJECT-TYPE
      SYNTAX MacAddress
      MAX-ACCESS read-create
      STATUS current
      DESCRIPTION
        "
        \u95c1\u544a\u7255\u7f0d\u5a47\u5d22\u9288\u590b\u510d\u95b8\u66e8\u53bd\u7ed0\u6945\u67e3\u928a\u30e5\u6bb0AC\u95c1\u7845\u3000\u93c5\u6fcb\u60a5\u951f\ufffd"
      ::= { aclRuleEntry 18 }
      
      matchedSourseIPMask OBJECT-TYPE
      SYNTAX IpAddress
      MAX-ACCESS read-create
      STATUS current
      DESCRIPTION
        "
        \u95c1\u544a\u7255\u7f0d\u5a47\u5d22\u9288\u590b\u510d\u95b8\u66e8\u525b\u9416\u76dcP\u95c1\u7845\u3000\u93c5\u6fcb\u60a5\u951f\ufffd"
      ::= { aclRuleEntry 19 }

    matchedDestinationIPMask OBJECT-TYPE
      SYNTAX IpAddress
      MAX-ACCESS read-create
      STATUS current
      DESCRIPTION
        "
        \u95c1\u544a\u7255\u7f0d\u5a47\u5d22\u9288\u590b\u510d\u95b8\u66e8\u53bd\u7ed0\u6945\u67e3\u928a\u30e5\u6bacP\u95c1\u7845\u3000\u93c5\u6fcb\u60a5\u951f\ufffd"
      ::= { aclRuleEntry 20 }

		
		-- 1.3.6.1.4.1.17409.2.3.3.2.3
		portACLListTable OBJECT-TYPE
			SYNTAX SEQUENCE OF PortACLListEntry
			MAX-ACCESS not-accessible
			STATUS current
			DESCRIPTION
				"
				ACL
				This table applies on OLT pon port, OLT SNI, OLT onu ID, ONU UNI.
				1. If the table is maintained in OLT device:
				Applied Obj  - Descriptions of Index
				------------------------------------------------------------------
				OLT Pon Port - OnuNum of aclDeviceIndex shall be set to 0,
				/OLT SNI     aclCardIndex, and aclPortIndex set to 0 indicates
				         meaningless 
				OLT onu ID   - Set aclDeviceIndex to corresponding ONU ID,
				         aclCardIndex, and aclPortIndex set to 0 indicates
				         meaningless        
				ONU UNI    - Set aclDeviceIndex to corresponding ONU ID,
				         aclCardIndex, and aclPortIndex set to the corresponding 
				         value        
				2. If the table is maintained in ONU device:
				aclDeviceIndex shall be set to 0 to indicate meaningless.
				aclCardIndex shall be set to corresponding slot.
				aclPortIndex shall be set to corresponding port.        
				"
			::= { aclManagementGroup 3 }

		
		-- 1.3.6.1.4.1.17409.2.3.3.2.3.1
		portACLListEntry OBJECT-TYPE
			SYNTAX PortACLListEntry
			MAX-ACCESS not-accessible
			STATUS current
			DESCRIPTION
				" "
			INDEX { aclDeviceIndex, aclCardIndex, aclPortIndex, portAclListIndex }
			::= { portACLListTable 1 }

		
		PortACLListEntry ::=
			SEQUENCE { 
				aclDeviceIndex
					EponDeviceIndex,
				aclCardIndex
					EponCardIndex,
				aclPortIndex
					EponPortIndex,
				portAclListIndex
					INTEGER,
				aclPortDirection
					BITS,
				aclRowStatus
					RowStatus
			 }

		-- 1.3.6.1.4.1.17409.2.3.3.2.3.1.1
		aclDeviceIndex OBJECT-TYPE
			SYNTAX EponDeviceIndex (1..2147483647)
			MAX-ACCESS not-accessible
			STATUS current
			DESCRIPTION
				"
				        
				For OLT, set to corresponding PON port, SNI, or ONU
				For ONU, set to 0
				"
			::= { portACLListEntry 1 }

		
		-- 1.3.6.1.4.1.17409.2.3.3.2.3.1.2
		aclCardIndex OBJECT-TYPE
			SYNTAX EponCardIndex (1..2147483647)
			MAX-ACCESS not-accessible
			STATUS current
			DESCRIPTION
				"
				        
				For OLT, set to 0,
				For ONU, set to corresponding slot
				"
			::= { portACLListEntry 2 }

		
		-- 1.3.6.1.4.1.17409.2.3.3.2.3.1.3
		aclPortIndex OBJECT-TYPE
			SYNTAX EponPortIndex (1..2147483647)
			MAX-ACCESS not-accessible
			STATUS current
			DESCRIPTION
				"
				
				For OLT, set to 0,
				For ONU, set to corresponding slot
				"
			::= { portACLListEntry 3 }

		
		-- 1.3.6.1.4.1.17409.2.3.3.2.3.1.4
		portAclListIndex OBJECT-TYPE
			SYNTAX INTEGER (1..2147483647)
			MAX-ACCESS not-accessible
			STATUS current
			DESCRIPTION
				"
				ACL"
			::= { portACLListEntry 4 }

		
		-- 1.3.6.1.4.1.17409.2.3.3.2.3.1.5
		aclPortDirection OBJECT-TYPE
			SYNTAX BITS
				{
				ingress(0),
				egress(1)
				}
			MAX-ACCESS read-create
			STATUS current
			DESCRIPTION
				"
				ACL"
			::= { portACLListEntry 5 }

		
		-- 1.3.6.1.4.1.17409.2.3.3.2.3.1.6
		aclRowStatus OBJECT-TYPE
			SYNTAX RowStatus
			MAX-ACCESS read-create
			STATUS current
			DESCRIPTION
				"
				ACL"
			::= { portACLListEntry 6 }

		
		-- 1.3.6.1.4.1.17409.2.3.3.3
		ponBroadcastStormSuppressionTable OBJECT-TYPE
			SYNTAX SEQUENCE OF PonBroadcastStormSuppressionEntry
			MAX-ACCESS not-accessible
			STATUS current
			DESCRIPTION
				"
				        
				"
			::= { ponPortObjects 3 }

		
		-- 1.3.6.1.4.1.17409.2.3.3.3.1
		ponBroadcastStormSuppressionEntry OBJECT-TYPE
			SYNTAX PonBroadcastStormSuppressionEntry
			MAX-ACCESS not-accessible
			STATUS current
			DESCRIPTION
				" "
			INDEX { bsDeviceIndex, bsCardIndex, bsPortIndex }
			::= { ponBroadcastStormSuppressionTable 1 }

		
		PonBroadcastStormSuppressionEntry ::=
			SEQUENCE { 
				bsDeviceIndex
					INTEGER,
				bsCardIndex
					EponCardIndex,
				bsPortIndex
					EponPortIndex,
				unicastStormEnable
					TruthValue,
				unicastStormInPacketRate
					INTEGER,
				unicastStormOutPacketRate
					INTEGER,
				multicastStormEnable
					TruthValue,
				multicastStormInPacketRate
					INTEGER,
				multicastStormOutPacketRate
					INTEGER,
				broadcastStormEnable
					TruthValue,
				broadcastStormInPacketRate
					INTEGER,
				broadcastStormOutPacketRate
					INTEGER
			 }

		-- 1.3.6.1.4.1.17409.2.3.3.3.1.1
		bsDeviceIndex OBJECT-TYPE
			SYNTAX INTEGER (1..2147483647)
			MAX-ACCESS not-accessible
			STATUS current
			DESCRIPTION
				"
				OLT        
				OLTOLTOLTOLT"
			::= { ponBroadcastStormSuppressionEntry 1 }

		
		-- 1.3.6.1.4.1.17409.2.3.3.3.1.2
		bsCardIndex OBJECT-TYPE
			SYNTAX EponCardIndex (1..2147483647)
			MAX-ACCESS not-accessible
			STATUS current
			DESCRIPTION
				"
				"
			::= { ponBroadcastStormSuppressionEntry 2 }

		
		-- 1.3.6.1.4.1.17409.2.3.3.3.1.3
		bsPortIndex OBJECT-TYPE
			SYNTAX EponPortIndex
			MAX-ACCESS not-accessible
			STATUS current
			DESCRIPTION
				"
				pon"
			::= { ponBroadcastStormSuppressionEntry 3 }

		
		-- 1.3.6.1.4.1.17409.2.3.3.3.1.4
		unicastStormEnable OBJECT-TYPE
			SYNTAX TruthValue
			MAX-ACCESS read-write
			STATUS current
			DESCRIPTION
				"
				"
			::= { ponBroadcastStormSuppressionEntry 4 }

		
		-- 1.3.6.1.4.1.17409.2.3.3.3.1.5
		unicastStormInPacketRate OBJECT-TYPE
			SYNTAX INTEGER
			UNITS "pps"
			MAX-ACCESS read-write
			STATUS current
			DESCRIPTION
				"
				"
			::= { ponBroadcastStormSuppressionEntry 5 }

		
		-- 1.3.6.1.4.1.17409.2.3.3.3.1.6
		unicastStormOutPacketRate OBJECT-TYPE
			SYNTAX INTEGER
			UNITS "pps"
			MAX-ACCESS read-write
			STATUS current
			DESCRIPTION
				"
				"
			::= { ponBroadcastStormSuppressionEntry 6 }

		
		-- 1.3.6.1.4.1.17409.2.3.3.3.1.7
		multicastStormEnable OBJECT-TYPE
			SYNTAX TruthValue
			MAX-ACCESS read-write
			STATUS current
			DESCRIPTION
				"
				"
			::= { ponBroadcastStormSuppressionEntry 7 }

		
		-- 1.3.6.1.4.1.17409.2.3.3.3.1.8
		multicastStormInPacketRate OBJECT-TYPE
			SYNTAX INTEGER
			UNITS "pps"
			MAX-ACCESS read-write
			STATUS current
			DESCRIPTION
				"
				"
			::= { ponBroadcastStormSuppressionEntry 8 }

		
		-- 1.3.6.1.4.1.17409.2.3.3.3.1.9
		multicastStormOutPacketRate OBJECT-TYPE
			SYNTAX INTEGER
			UNITS "pps"
			MAX-ACCESS read-write
			STATUS current
			DESCRIPTION
				"
				"
			::= { ponBroadcastStormSuppressionEntry 9 }

		
		-- 1.3.6.1.4.1.17409.2.3.3.3.1.10
		broadcastStormEnable OBJECT-TYPE
			SYNTAX TruthValue
			MAX-ACCESS read-write
			STATUS current
			DESCRIPTION
				"
				"
			::= { ponBroadcastStormSuppressionEntry 10 }

		
		-- 1.3.6.1.4.1.17409.2.3.3.3.1.11
		broadcastStormInPacketRate OBJECT-TYPE
			SYNTAX INTEGER
			UNITS "pps"
			MAX-ACCESS read-write
			STATUS current
			DESCRIPTION
				"
				"
			::= { ponBroadcastStormSuppressionEntry 11 }

		
		-- 1.3.6.1.4.1.17409.2.3.3.3.1.12
		broadcastStormOutPacketRate OBJECT-TYPE
			SYNTAX INTEGER
			UNITS "pps"
			MAX-ACCESS read-write
			STATUS current
			DESCRIPTION
				"
				"
			::= { ponBroadcastStormSuppressionEntry 12 }

		
		-- 1.3.6.1.4.1.17409.2.3.3.4
		ponOnuAuthenticationModeTable OBJECT-TYPE
			SYNTAX SEQUENCE OF ponOnuAuthenticationModeEntry
			MAX-ACCESS not-accessible
			STATUS optional
			DESCRIPTION
				"PONONU"
			::= { ponPortObjects 4 }

		
		-- 1.3.6.1.4.1.17409.2.3.3.4.1
		ponOnuAuthenticationModeEntry OBJECT-TYPE
			SYNTAX ponOnuAuthenticationModeEntry
			MAX-ACCESS not-accessible
			STATUS current
			DESCRIPTION
				"The ponOnuAuthenticationModeEntry Information"
			INDEX { ponAuthenDeviceIndex, ponAuthenCardIndex, ponAuthenPortIndex }
			::= { ponOnuAuthenticationModeTable 1 }

		
		ponOnuAuthenticationModeEntry ::=
			SEQUENCE { 
				ponAuthenDeviceIndex
					INTEGER,
				ponAuthenCardIndex
					EponCardIndex,
				ponAuthenPortIndex
					EponPortIndex,
				ponOnuAuthenMode
					INTEGER,
				onuAuthenModeRowStatus
					INTEGER
			 }

		-- 1.3.6.1.4.1.17409.2.3.3.4.1.1
		ponAuthenDeviceIndex OBJECT-TYPE
			SYNTAX INTEGER (1..2147483647)
			MAX-ACCESS not-accessible
			STATUS current
			DESCRIPTION
				" OLTOLTOLT
				OLTOLT"
			::= { ponOnuAuthenticationModeEntry 1 }

		
		-- 1.3.6.1.4.1.17409.2.3.3.4.1.2
		ponAuthenCardIndex OBJECT-TYPE
			SYNTAX EponCardIndex (1..2147483647)
			MAX-ACCESS not-accessible
			STATUS current
			DESCRIPTION
				""
			::= { ponOnuAuthenticationModeEntry 2 }

		
		-- 1.3.6.1.4.1.17409.2.3.3.4.1.3
		ponAuthenPortIndex OBJECT-TYPE
			SYNTAX EponPortIndex (1..2147483647)
			MAX-ACCESS not-accessible
			STATUS current
			DESCRIPTION
				"pon"
			::= { ponOnuAuthenticationModeEntry 3 }

		
		-- 1.3.6.1.4.1.17409.2.3.3.4.1.4
		ponOnuAuthenMode OBJECT-TYPE
			SYNTAX  INTEGER {
              loid-password (1),
              mac_or_loid-password (2),
              loid (3),
              mac_or_loid (4),
              mac(5),
              all(6)
            }
			MAX-ACCESS read-create
			STATUS current
			DESCRIPTION
				"Authen mode: This is mode in authen ,"
			::= { ponOnuAuthenticationModeEntry 4 }

		
		-- 1.3.6.1.4.1.17409.2.3.3.4.1.5
		onuAuthenModeRowStatus OBJECT-TYPE
			SYNTAX INTEGER
			MAX-ACCESS read-create
			STATUS current
			DESCRIPTION
				"onuauthen Row Status"
			::= { ponOnuAuthenticationModeEntry 5 }

		
-- ---
		-- 1.3.6.1.4.1.17409.2.3.3.5
		ponPortOpticalTransmissionPropertyTable OBJECT-TYPE
			SYNTAX SEQUENCE OF PonPortOpticalTransmissionPropertyEntry
			MAX-ACCESS not-accessible
			STATUS current
			DESCRIPTION
				"
				
				"
			::= { ponPortObjects 5 }

		
		-- 1.3.6.1.4.1.17409.2.3.3.5.1
		ponPortOpticalTransmissionPropertyEntry OBJECT-TYPE
			SYNTAX PonPortOpticalTransmissionPropertyEntry
			MAX-ACCESS not-accessible
			STATUS current
			DESCRIPTION
				" "
			INDEX { ponOpDeviceIndex, ponOpCardIndex, ponOpPortIndex }
			::= { ponPortOpticalTransmissionPropertyTable 1 }

		
		PonPortOpticalTransmissionPropertyEntry ::=
			SEQUENCE { 
				ponOpDeviceIndex
					INTEGER,
				ponOpCardIndex
					EponCardIndex,
				ponOpPortIndex
					EponPortIndex,
				ponOpVcc
					INTEGER,
				ponOpBias
					INTEGER,
				ponOpTxPower
					INTEGER,
				ponOpRxPower
					INTEGER
			 }

		-- 1.3.6.1.4.1.17409.2.3.3.5.1.1
		ponOpDeviceIndex OBJECT-TYPE
			SYNTAX INTEGER (1..2147483647)
			MAX-ACCESS read-only
			STATUS current
			DESCRIPTION
				"
				OLT
				OLTOLTOLTOLT"
			::= { ponPortOpticalTransmissionPropertyEntry 1 }

		
		-- 1.3.6.1.4.1.17409.2.3.3.5.1.2
		ponOpCardIndex OBJECT-TYPE
			SYNTAX EponCardIndex (1..2147483647)
			MAX-ACCESS read-only
			STATUS current
			DESCRIPTION
				"
				"
			::= { ponPortOpticalTransmissionPropertyEntry 2 }

		
		-- 1.3.6.1.4.1.17409.2.3.3.5.1.3
		ponOpPortIndex OBJECT-TYPE
			SYNTAX EponPortIndex (1..2147483647)
			MAX-ACCESS read-only
			STATUS current
			DESCRIPTION
				"
				"
			::= { ponPortOpticalTransmissionPropertyEntry 3 }

		
		-- 1.3.6.1.4.1.17409.2.3.3.5.1.4
		ponOpVcc OBJECT-TYPE
			SYNTAX INTEGER
			UNITS "centi-mV"
			MAX-ACCESS read-only
			STATUS current
			DESCRIPTION
				"
				"
			::= { ponPortOpticalTransmissionPropertyEntry 4 }

		
		-- 1.3.6.1.4.1.17409.2.3.3.5.1.5
		ponOpBias OBJECT-TYPE
			SYNTAX INTEGER
			UNITS "centi-mA"
			MAX-ACCESS read-only
			STATUS current
			DESCRIPTION
				"
				"
			::= { ponPortOpticalTransmissionPropertyEntry 5 }

		
		-- 1.3.6.1.4.1.17409.2.3.3.5.1.6
		ponOpTxPower OBJECT-TYPE
			SYNTAX INTEGER
			UNITS "centi-dBm"
			MAX-ACCESS read-only
			STATUS current
			DESCRIPTION
				"
				"
			::= { ponPortOpticalTransmissionPropertyEntry 6 }

		
		-- 1.3.6.1.4.1.17409.2.3.3.5.1.7
		ponOpRxPower OBJECT-TYPE
			SYNTAX INTEGER
			UNITS "centi-dBm"
			MAX-ACCESS read-only
			STATUS current
			DESCRIPTION
				"
				"
			::= { ponPortOpticalTransmissionPropertyEntry 7 }

		
    -- 1.3.6.1.4.1.17409.2.3.3.6
    ponPortOpticalRxPowerTable OBJECT-TYPE
        SYNTAX   SEQUENCE OF PonPortOpticalRxPowerEntry
        MAX-ACCESS  not-accessible
        STATUS  optional
        DESCRIPTION
        ""
        ::= { ponPortObjects 6 }
    -- 1.3.6.1.4.1.17409.2.3.3.6.1
    ponPortOpticalRxPowerEntry OBJECT-TYPE
        SYNTAX  PonPortOpticalRxPowerEntry
        MAX-ACCESS  not-accessible
        STATUS  current
        DESCRIPTION
        "The ponPortOpticalRxPowerEntry Information"
        INDEX{ ponOpRxOfOnuDeviceIndex}  
                ::={ ponPortOpticalRxPowerTable 1 }  

        PonPortOpticalRxPowerEntry
                ::= SEQUENCE
                {  ponOpRxOfOnuDeviceIndex  EponDeviceIndex,
                   ponOpRxPowerOfOnu INTEGER
                }
    -- 1.3.6.1.4.1.17409.2.3.3.6.1.1
        ponOpRxOfOnuDeviceIndex OBJECT-TYPE
        SYNTAX      EponDeviceIndex
        MAX-ACCESS  not-accessible
        STATUS      current
        DESCRIPTION
            "onuDevice Index"
        ::= { ponPortOpticalRxPowerEntry 1 }
    -- 1.3.6.1.4.1.17409.2.3.3.6.1.2
        ponOpRxPowerOfOnu OBJECT-TYPE
        SYNTAX      INTEGER
        UNITS   "centi-dBm"
        MAX-ACCESS  read-only 
        STATUS      current
        DESCRIPTION
            "OLT pon port received onu optical power"
        ::= { ponPortOpticalRxPowerEntry  2}
		
		
		-- 1.3.6.1.4.1.17409.2.3.4
		onuObjects OBJECT IDENTIFIER ::= { eponTree 4 }
		

		
-- ------------------------------------------------------------------------------
-- onuObjects[ONU](1.3.6.1.4.1.17409.2.3.4)
-- ------------------------------------------------------------------------------  
		-- 1.3.6.1.4.1.17409.2.3.4.1
		onuInfoTable OBJECT-TYPE
			SYNTAX SEQUENCE OF OnuInfoEntry
			MAX-ACCESS not-accessible
			STATUS current
			DESCRIPTION
				"A list of onuInfoTable entries. "
			::= { onuObjects 1 }

		
		-- 1.3.6.1.4.1.17409.2.3.4.1.1
		onuInfoEntry OBJECT-TYPE
			SYNTAX OnuInfoEntry
			MAX-ACCESS not-accessible
			STATUS current
			DESCRIPTION
				"The onuInfoEntry Information"
			INDEX { onuDeviceIndex }
			::= { onuInfoTable 1 }

		
		OnuInfoEntry ::=
			SEQUENCE { 
				onuDeviceIndex
					EponDeviceIndex,
				onuName
					DisplayString,
				onuType
					INTEGER,
				onuIpAddress
					IpAddress,
				onuIpSubnetMask
					IpAddress,
				onuIpGateway
					IpAddress,
				onuMacAddress
					MacAddress,
				onuOperationStatus
					INTEGER,
				onuAdminStatus
					INTEGER,
				onuChipVendor
					DisplayString,
				onuChipType
					DisplayString,
				onuChipVersion
					DisplayString,
				onuSoftwareVersion
					DisplayString,
				onuFirmwareVersion
					DisplayString,
				onuTestDistance
					INTEGER,
				onuLlidId
					INTEGER,
				resetONU
					INTEGER,
				onuTimeSinceLastRegister
					Counter32,
				onuMgmtCvlan
					INTEGER,
				onuMgmtSvlan
					INTEGER,
				onuMgmtPriority
					INTEGER,
				onuMgmtSnmpTrapHost
					IpAddress,
				onuMgmtSnmpCommunityForRead
					DisplayString,
				onuMgmtSnmpCommunityForWrite
					DisplayString,
				onuVendorId
					DisplayString,
				onuModelId
					DisplayString,
				onuHardwareVersion
					DisplayString,
				onuSn
					DisplayString,
				onuTimeLastRegister
    				TimeTicks
			 }

		-- 1.3.6.1.4.1.17409.2.3.4.1.1.1
		onuDeviceIndex OBJECT-TYPE
			SYNTAX EponDeviceIndex (1..2147483647)
			MAX-ACCESS not-accessible
			STATUS current
			DESCRIPTION
				"onuDevice Index"
			::= { onuInfoEntry 1 }

		
		-- 1.3.6.1.4.1.17409.2.3.4.1.1.2
		onuName OBJECT-TYPE
			SYNTAX DisplayString
			MAX-ACCESS read-write
			STATUS current
			DESCRIPTION
				"onu Name"
			::= { onuInfoEntry 2 }

		
		-- 1.3.6.1.4.1.17409.2.3.4.1.1.3
		onuType OBJECT-TYPE
			SYNTAX INTEGER
				{
				fixed(1),
				chassisBased(2)
				}
			MAX-ACCESS read-only
			STATUS current
			DESCRIPTION
				"onu Type            
				fixed(1)        - not slot concept
				chassisBased(2) - port is indexed by coupling slot ID"
			::= { onuInfoEntry 3 }

		
		-- 1.3.6.1.4.1.17409.2.3.4.1.1.4
		onuIpAddress OBJECT-TYPE
			SYNTAX IpAddress
			MAX-ACCESS read-write
			STATUS current
			DESCRIPTION
				"onu Ip Address"
			::= { onuInfoEntry 4 }

		
		-- 1.3.6.1.4.1.17409.2.3.4.1.1.5
		onuIpSubnetMask OBJECT-TYPE
			SYNTAX IpAddress
			MAX-ACCESS read-write
			STATUS current
			DESCRIPTION
				"onu Ip Subnet Mask"
			::= { onuInfoEntry 5 }

		
		-- 1.3.6.1.4.1.17409.2.3.4.1.1.6
		onuIpGateway OBJECT-TYPE
			SYNTAX IpAddress
			MAX-ACCESS read-write
			STATUS current
			DESCRIPTION
				"onu Ip Gateway"
			::= { onuInfoEntry 6 }

		
		-- 1.3.6.1.4.1.17409.2.3.4.1.1.7
		onuMacAddress OBJECT-TYPE
			SYNTAX MacAddress
			MAX-ACCESS read-only
			STATUS current
			DESCRIPTION
				"onuMac Address"
			::= { onuInfoEntry 7 }

		
		-- 1.3.6.1.4.1.17409.2.3.4.1.1.8
		onuOperationStatus OBJECT-TYPE
			SYNTAX INTEGER
				{
				up(1),
				down(2),
				testing(3)
				}
			MAX-ACCESS read-only
			STATUS current
			DESCRIPTION
				"onu Operation Status"
			::= { onuInfoEntry 8 }

		
		-- 1.3.6.1.4.1.17409.2.3.4.1.1.9
		onuAdminStatus OBJECT-TYPE
			SYNTAX INTEGER
				{
				up(1),
				down(2),
				testing(3)
				}
			MAX-ACCESS read-write
			STATUS current
			DESCRIPTION
				"onu Admin Status"
			::= { onuInfoEntry 9 }

		
		-- 1.3.6.1.4.1.17409.2.3.4.1.1.10
		onuChipVendor OBJECT-TYPE
			SYNTAX DisplayString
			MAX-ACCESS read-only
			STATUS current
			DESCRIPTION
				"onu Chip Vendor"
			::= { onuInfoEntry 10 }

		
		-- 1.3.6.1.4.1.17409.2.3.4.1.1.11
		onuChipType OBJECT-TYPE
			SYNTAX DisplayString
			MAX-ACCESS read-only
			STATUS current
			DESCRIPTION
				"onu Chip Type"
			::= { onuInfoEntry 11 }

		
		-- 1.3.6.1.4.1.17409.2.3.4.1.1.12
		onuChipVersion OBJECT-TYPE
			SYNTAX DisplayString
			MAX-ACCESS read-only
			STATUS current
			DESCRIPTION
				"onu Chip Version"
			::= { onuInfoEntry 12 }

		
		-- 1.3.6.1.4.1.17409.2.3.4.1.1.13
		onuSoftwareVersion OBJECT-TYPE
			SYNTAX DisplayString
			MAX-ACCESS read-only
			STATUS current
			DESCRIPTION
				"onu Software Version"
			::= { onuInfoEntry 13 }

		
		-- 1.3.6.1.4.1.17409.2.3.4.1.1.14
		onuFirmwareVersion OBJECT-TYPE
			SYNTAX DisplayString
			MAX-ACCESS read-only
			STATUS current
			DESCRIPTION
				"onu Firmware Version"
			::= { onuInfoEntry 14 }

		
		-- 1.3.6.1.4.1.17409.2.3.4.1.1.15
		onuTestDistance OBJECT-TYPE
			SYNTAX INTEGER
			UNITS "Meter"
			MAX-ACCESS read-only
			STATUS current
			DESCRIPTION
				"onu Test Distance"
			::= { onuInfoEntry 15 }

		
		-- 1.3.6.1.4.1.17409.2.3.4.1.1.16
		onuLlidId OBJECT-TYPE
			SYNTAX INTEGER
			MAX-ACCESS read-only
			STATUS current
			DESCRIPTION
				"onu Llid Id"
			::= { onuInfoEntry 16 }

		
		-- 1.3.6.1.4.1.17409.2.3.4.1.1.17
		resetONU OBJECT-TYPE
			SYNTAX INTEGER { reset(1) }
			MAX-ACCESS read-write
			STATUS current
			DESCRIPTION
				"reset ONU"
			::= { onuInfoEntry 17 }

		
		-- 1.3.6.1.4.1.17409.2.3.4.1.1.18
		onuTimeSinceLastRegister OBJECT-TYPE
			SYNTAX Counter32
			UNITS "seconds"
			MAX-ACCESS read-only
			STATUS current
			DESCRIPTION
				"The number of seconds, since the time when the ONU is registered"
			::= { onuInfoEntry 18 }

		
		-- 1.3.6.1.4.1.17409.2.3.4.1.1.19
		onuMgmtCvlan OBJECT-TYPE
			SYNTAX INTEGER
			MAX-ACCESS read-write
			STATUS current
			DESCRIPTION
				"CVLAN ID of management data for the ONU"
			::= { onuInfoEntry 19 }

		
		-- 1.3.6.1.4.1.17409.2.3.4.1.1.20
		onuMgmtSvlan OBJECT-TYPE
			SYNTAX INTEGER
			MAX-ACCESS read-write
			STATUS optional
			DESCRIPTION
				"SVLAN ID of management data for the ONU
				Set to 0, means only single VLAN is supported, no SVLAN concept,
				for the ONU management"
			::= { onuInfoEntry 20 }

		
		-- 1.3.6.1.4.1.17409.2.3.4.1.1.21
		onuMgmtPriority OBJECT-TYPE
			SYNTAX INTEGER (0..7)
			MAX-ACCESS read-write
			STATUS optional
			DESCRIPTION
				"Tagged dot1p priority of management data for the ONU"
			::= { onuInfoEntry 21 }

		
		-- 1.3.6.1.4.1.17409.2.3.4.1.1.22
		onuMgmtSnmpTrapHost OBJECT-TYPE
			SYNTAX IpAddress
			MAX-ACCESS read-write
			STATUS current
			DESCRIPTION
				"The host IP address, to which the ONU will send trap."
			::= { onuInfoEntry 22 }

		
		-- 1.3.6.1.4.1.17409.2.3.4.1.1.23
		onuMgmtSnmpCommunityForRead OBJECT-TYPE
			SYNTAX DisplayString
			MAX-ACCESS read-write
			STATUS current
			DESCRIPTION
				"The read SNMP community to the ONU."
			::= { onuInfoEntry 23 }

		
		-- 1.3.6.1.4.1.17409.2.3.4.1.1.24
		onuMgmtSnmpCommunityForWrite OBJECT-TYPE
			SYNTAX DisplayString
			MAX-ACCESS read-write
			STATUS current
			DESCRIPTION
				"The write SNMP community to the ONU."
			::= { onuInfoEntry 24 }

		
		-- 1.3.6.1.4.1.17409.2.3.4.1.1.25
		onuVendorId OBJECT-TYPE
			SYNTAX DisplayString
			MAX-ACCESS read-only
			STATUS current
			DESCRIPTION
				"ONU vendor id."
			::= { onuInfoEntry 25 }

		
		-- 1.3.6.1.4.1.17409.2.3.4.1.1.26
		onuModelId OBJECT-TYPE
			SYNTAX DisplayString
			MAX-ACCESS read-only
			STATUS current
			DESCRIPTION
				"ONU model id."
			::= { onuInfoEntry 26 }

		
		-- 1.3.6.1.4.1.17409.2.3.4.1.1.27
		onuHardwareVersion OBJECT-TYPE
			SYNTAX DisplayString
			MAX-ACCESS read-only
			STATUS current
			DESCRIPTION
				"ONU hardware version."
			::= { onuInfoEntry 27 }

		
		-- 1.3.6.1.4.1.17409.2.3.4.1.1.28
		onuSn OBJECT-TYPE
			SYNTAX DisplayString
			MAX-ACCESS read-only
			STATUS current
			DESCRIPTION
				"ONU serial number."
			::= { onuInfoEntry 28 }
		-- 1.3.6.1.4.1.17409.2.3.4.1.1.29	
		onuTimeLastRegister OBJECT-TYPE
        SYNTAX      TimeTicks
        MAX-ACCESS  read-only
        STATUS      current
        DESCRIPTION
            " "
        ::= {onuInfoEntry 29 }

		
		-- 1.3.6.1.4.1.17409.2.3.4.2
		onuPonPortOpticalTransmissionPropertyTable OBJECT-TYPE
			SYNTAX SEQUENCE OF OnuPonPortOpticalTransmissionPropertyEntry
			MAX-ACCESS not-accessible
			STATUS current
			DESCRIPTION
				"
				This table is designed for both OLT and ONU 
				Applied Obj  - Descriptions of Index
				------------------------------------------------------------------
				OLT      - OnuNum of EponDeviceIndex TC shall be set to 0,
				     onuPonPortOpticalTransmissionPropertyCardIndex, and 
				     onuPonPortOpticalTransmissionPropertyPortIndex set to 
				     65535 indicates meaningless
				ONU      - Set EponDeviceIndex TC to corresponding ONU ID,
				       onuPonPortOpticalTransmissionPropertyCardIndex, and 
				       onuPonPortOpticalTransmissionPropertyPortIndex set to the 
				       corresponding value
				"
			::= { onuObjects 2 }

		
		-- 1.3.6.1.4.1.17409.2.3.4.2.1
		onuPonPortOpticalTransmissionPropertyEntry OBJECT-TYPE
			SYNTAX OnuPonPortOpticalTransmissionPropertyEntry
			MAX-ACCESS not-accessible
			STATUS current
			DESCRIPTION
				"The onuPonPortOpticalTransmissionPropertyEntry Information"
			INDEX { onuPonPortOpticalTransmissionPropertyDeviceIndex, onuPonPortOpticalTransmissionPropertyCardIndex, onuPonPortOpticalTransmissionPropertyPortIndex }
			::= { onuPonPortOpticalTransmissionPropertyTable 1 }

		
		OnuPonPortOpticalTransmissionPropertyEntry ::=
			SEQUENCE { 
				onuPonPortOpticalTransmissionPropertyDeviceIndex
					EponDeviceIndex,
				onuPonPortOpticalTransmissionPropertyCardIndex
					INTEGER,
				onuPonPortOpticalTransmissionPropertyPortIndex
					INTEGER,
				onuReceivedOpticalPower
					INTEGER,
				onuTramsmittedOpticalPower
					INTEGER,
				onuBiasCurrent
					INTEGER,
				onuWorkingVoltage
					INTEGER,
				onuWorkingTemperature
					INTEGER
			 }

		-- 1.3.6.1.4.1.17409.2.3.4.2.1.1
		onuPonPortOpticalTransmissionPropertyDeviceIndex OBJECT-TYPE
			SYNTAX EponDeviceIndex (1..2147483647)
			MAX-ACCESS not-accessible
			STATUS current
			DESCRIPTION
				"Device Index of the ONU."
			::= { onuPonPortOpticalTransmissionPropertyEntry 1 }

		
		-- 1.3.6.1.4.1.17409.2.3.4.2.1.2
		onuPonPortOpticalTransmissionPropertyCardIndex OBJECT-TYPE
			SYNTAX INTEGER (1..2147483647)
			MAX-ACCESS not-accessible
			STATUS current
			DESCRIPTION
				"Card Index in the ONU. Shall set to 0, if ONU is not a modulized 
				device"
			::= { onuPonPortOpticalTransmissionPropertyEntry 2 }

		
		-- 1.3.6.1.4.1.17409.2.3.4.2.1.3
		onuPonPortOpticalTransmissionPropertyPortIndex OBJECT-TYPE
			SYNTAX INTEGER (1..2147483647)
			MAX-ACCESS not-accessible
			STATUS current
			DESCRIPTION
				"Port Index in the Pon card of ONU"
			::= { onuPonPortOpticalTransmissionPropertyEntry 3 }

		
		-- 1.3.6.1.4.1.17409.2.3.4.2.1.4
		onuReceivedOpticalPower OBJECT-TYPE
			SYNTAX INTEGER
			UNITS "centi-dBm"
			MAX-ACCESS read-only
			STATUS current
			DESCRIPTION
				"received Optical Power"
			::= { onuPonPortOpticalTransmissionPropertyEntry 4 }

		
		-- 1.3.6.1.4.1.17409.2.3.4.2.1.5
		onuTramsmittedOpticalPower OBJECT-TYPE
			SYNTAX INTEGER
			UNITS "centi-dBm"
			MAX-ACCESS read-only
			STATUS current
			DESCRIPTION
				"tramsmitted Optical Power"
			::= { onuPonPortOpticalTransmissionPropertyEntry 5 }

		
		-- 1.3.6.1.4.1.17409.2.3.4.2.1.6
		onuBiasCurrent OBJECT-TYPE
			SYNTAX INTEGER
			UNITS "centi-mA"
			MAX-ACCESS read-only
			STATUS current
			DESCRIPTION
				"biasCurrent"
			::= { onuPonPortOpticalTransmissionPropertyEntry 6 }

		
		-- 1.3.6.1.4.1.17409.2.3.4.2.1.7
		onuWorkingVoltage OBJECT-TYPE
			SYNTAX INTEGER
			UNITS "centi-mV"
			MAX-ACCESS read-only
			STATUS current
			DESCRIPTION
				"onuworking Voltage"
			::= { onuPonPortOpticalTransmissionPropertyEntry 7 }

		
		-- 1.3.6.1.4.1.17409.2.3.4.2.1.8
		onuWorkingTemperature OBJECT-TYPE
			SYNTAX INTEGER
			UNITS "Centi-degree centigrade"
			MAX-ACCESS read-only
			STATUS current
			DESCRIPTION
				"working Temperature"
			::= { onuPonPortOpticalTransmissionPropertyEntry 8 }

		
		-- 1.3.6.1.4.1.17409.2.3.4.3
		onuCapabilityTable OBJECT-TYPE
			SYNTAX SEQUENCE OF OnuCapabilityEntry
			MAX-ACCESS not-accessible
			STATUS current
			DESCRIPTION
				"A list of onuInfoTable entries. "
			::= { onuObjects 3 }

		
		-- 1.3.6.1.4.1.17409.2.3.4.3.1
		onuCapabilityEntry OBJECT-TYPE
			SYNTAX OnuCapabilityEntry
			MAX-ACCESS not-accessible
			STATUS current
			DESCRIPTION
				"The onuCapabilityEntry Information"
			INDEX { onuCapabilityDeviceIndex }
			::= { onuCapabilityTable 1 }

		
		OnuCapabilityEntry ::=
			SEQUENCE { 
				onuCapabilityDeviceIndex
					EponDeviceIndex,
				onuGePortNum
					INTEGER,
				onuGePortBitmap
					OCTET STRING,
				onuFePortNum
					INTEGER,
				onuFePortBitmap
					OCTET STRING,
				onuQueueNumUplink
					INTEGER,
				onuMaxQueueNumUplink
					INTEGER,
				onuQueueNumDownlink
					INTEGER,
				onuMaxQueueNumDownlink
					INTEGER,
				onuFecEnable
					TruthValue,
				onuEncryptMode
					INTEGER,
				onuEncryptKeyExchangeTime
					TimeTicks,
				onuIsolationEnable   
				    TruthValue
			 }

		-- 1.3.6.1.4.1.17409.2.3.4.3.1.1
		onuCapabilityDeviceIndex OBJECT-TYPE
			SYNTAX EponDeviceIndex (1..2147483647)
			MAX-ACCESS not-accessible
			STATUS current
			DESCRIPTION
				"onu Device Index"
			::= { onuCapabilityEntry 1 }

		
		-- 1.3.6.1.4.1.17409.2.3.4.3.1.2
		onuGePortNum OBJECT-TYPE
			SYNTAX INTEGER
			MAX-ACCESS read-only
			STATUS current
			DESCRIPTION
				"gePort Num"
			::= { onuCapabilityEntry 2 }

		
		-- 1.3.6.1.4.1.17409.2.3.4.3.1.3
		onuGePortBitmap OBJECT-TYPE
			SYNTAX OCTET STRING
			MAX-ACCESS read-only
			STATUS current
			DESCRIPTION
				"gePort Bitmap
				
				In slot+port pair list manner. Suppose each slot support up to 64 ports.
				One octet to indentify slot and 8 octets to identify portbitmap for
				the slot. The bitmap definition is internet sequence. The most left bit 
				is for port 1 of the slot, the most right bit is for port 64 of the slot.            
				If the slot cannot support 64 ports, set the bits of not supported ports
				to 0.            
				If the port is GE port, set the corresponding bit to 1.                 
				Since the slot num depends on each individual device, the object is variable
				length. If the device is fixed box (not modulized), set the slot number to 
				255. Then the network management system could ignore the slot info.            
				It is not necessary to list the slot doesn't support GE port.                        
				For example, if have 4 GE ports, of: 1/4, 1/6, 2/3, 4/17,
				the object will be presented in:
				01 14 00 00 00 00 00 00 00
				02 20 00 00 00 00 00 00 00
				04 00 00 80 00 00 00 00 00            
				Another example, for fixed box, if have 4 ge ports of 4,6,10,17, the object
				will be presented as:
				FF 14 40 10 00 00 00 00
				"
			::= { onuCapabilityEntry 3 }

		
		-- 1.3.6.1.4.1.17409.2.3.4.3.1.4
		onuFePortNum OBJECT-TYPE
			SYNTAX INTEGER
			MAX-ACCESS read-only
			STATUS current
			DESCRIPTION
				"fePort Num"
			::= { onuCapabilityEntry 4 }

		
		-- 1.3.6.1.4.1.17409.2.3.4.3.1.5
		onuFePortBitmap OBJECT-TYPE
			SYNTAX OCTET STRING
			MAX-ACCESS read-only
			STATUS current
			DESCRIPTION
				"fePort Bitmap
				
				In slot+port pair list manner. Suppose each slot support up to 64 ports.
				One octet to indentify slot and 8 octets to identify portbitmap for
				the slot. The bitmap definition is internet sequence. The most left bit 
				is for port 1 of the slot, the most right bit is for port 64 of the slot.            
				If the slot cannot support 64 ports, set the bits of not supported ports
				to 0.            
				If the port is FE port, set the corresponding bit to 1.                 
				Since the slot num depends on each individual device, the object is variable
				length. If the device is fixed box (not modulized), set the slot number to 
				255. Then the network management system could ignore the slot info.            
				It is not necessary to list the slot doesn't support FE port.                        
				For example, if have 4 FE ports, of: 1/4, 1/6, 2/3, 4/17,
				the object will be presented in:
				01 14 00 00 00 00 00 00 00
				02 20 00 00 00 00 00 00 00
				04 00 00 80 00 00 00 00 00            
				Another example, for fixed box, if have 4 FE ports of 4,6,10,17, the object
				will be presented as:
				FF 14 40 10 00 00 00 00
				"
			::= { onuCapabilityEntry 5 }

		
		-- 1.3.6.1.4.1.17409.2.3.4.3.1.6
		onuQueueNumUplink OBJECT-TYPE
			SYNTAX INTEGER
			MAX-ACCESS read-only
			STATUS current
			DESCRIPTION
				"queue Num Uplink"
			::= { onuCapabilityEntry 6 }

		
		-- 1.3.6.1.4.1.17409.2.3.4.3.1.7
		onuMaxQueueNumUplink OBJECT-TYPE
			SYNTAX INTEGER
			MAX-ACCESS read-only
			STATUS current
			DESCRIPTION
				"max Queue Num Uplink"
			::= { onuCapabilityEntry 7 }

		
		-- 1.3.6.1.4.1.17409.2.3.4.3.1.8
		onuQueueNumDownlink OBJECT-TYPE
			SYNTAX INTEGER
			MAX-ACCESS read-only
			STATUS current
			DESCRIPTION
				"queue Num Downlink"
			::= { onuCapabilityEntry 8 }

		
		-- 1.3.6.1.4.1.17409.2.3.4.3.1.9
		onuMaxQueueNumDownlink OBJECT-TYPE
			SYNTAX INTEGER
			MAX-ACCESS read-only
			STATUS current
			DESCRIPTION
				"max Queue Num Downlink"
			::= { onuCapabilityEntry 9 }

		
		-- 1.3.6.1.4.1.17409.2.3.4.3.1.10
		onuFecEnable OBJECT-TYPE
			SYNTAX TruthValue
			MAX-ACCESS read-write
			STATUS current
			DESCRIPTION
				"fec Enable"
			::= { onuCapabilityEntry 10 }

		
		-- 1.3.6.1.4.1.17409.2.3.4.3.1.11
		onuEncryptMode OBJECT-TYPE
			SYNTAX INTEGER
				{
				aes128(1),
				ctcTripleChurning(2),
				other(3)
				}
			MAX-ACCESS read-only
			STATUS current
			DESCRIPTION
				"encrypt Mode"
			::= { onuCapabilityEntry 11 }

		
		-- 1.3.6.1.4.1.17409.2.3.4.3.1.12
		onuEncryptKeyExchangeTime OBJECT-TYPE
			SYNTAX TimeTicks
			MAX-ACCESS read-only
			STATUS current
			DESCRIPTION
				"encryptKeyExchange Time"
			::= { onuCapabilityEntry 12 }
		-- 1.3.6.1.4.1.17409.2.3.4.3.1.13
        onuIsolationEnable  OBJECT-TYPE
            SYNTAX      TruthValue    
            MAX-ACCESS  read-write
            STATUS      current
            DESCRIPTION
            "
            ONU\u7f02\u5099\u7126\u59ab\u5fdb\u5d39\u93b7\u5c7b\u4eb9\u6fde\u6219\u57ba\u9237\u66e2\u67e1\u9350\u3125\u4e9e\u95bb\u5ea2\u5f43\u9709\u95bf\u6fc6\u7246\u9354\u7538\u67db\u8e47\u30e6\u5af9
            true(1) false(2)"
            ::= { onuCapabilityEntry  13 }
		
		-- 1.3.6.1.4.1.17409.2.3.4.4
		slaTable OBJECT-TYPE
			SYNTAX SEQUENCE OF SlaEntry
			MAX-ACCESS not-accessible
			STATUS current
			DESCRIPTION
				"A list of slaTable entries. "
			::= { onuObjects 4 }

		
		-- 1.3.6.1.4.1.17409.2.3.4.4.1
		slaEntry OBJECT-TYPE
			SYNTAX SlaEntry
			MAX-ACCESS not-accessible
			STATUS current
			DESCRIPTION
				"The slaEntry Information"
			INDEX { slaIndex }
			::= { slaTable 1 }

		
		SlaEntry ::=
			SEQUENCE { 
				slaIndex
					EponDeviceIndex,
				slaDsFixedBW
					INTEGER,
				slaDsPeakBW
					INTEGER,
				slaDsCommittedBW
					INTEGER,
				slaUsFixedBW
					INTEGER,
				slaUsPeakBW
					INTEGER,
				slaUsCommittedBW
					INTEGER
			 }

		-- 1.3.6.1.4.1.17409.2.3.4.4.1.1
		slaIndex OBJECT-TYPE
			SYNTAX EponDeviceIndex (1..2147483647)
			MAX-ACCESS not-accessible
			STATUS current
			DESCRIPTION
				"sla Index"
			::= { slaEntry 1 }

		
		-- 1.3.6.1.4.1.17409.2.3.4.4.1.2
		slaDsFixedBW OBJECT-TYPE
			SYNTAX INTEGER
			UNITS "kbps"
			MAX-ACCESS read-write
			STATUS current
			DESCRIPTION
				"Downstream sla FixedBW"
			::= { slaEntry 2 }

		
		-- 1.3.6.1.4.1.17409.2.3.4.4.1.3
		slaDsPeakBW OBJECT-TYPE
			SYNTAX INTEGER
			UNITS "kbps"
			MAX-ACCESS read-write
			STATUS current
			DESCRIPTION
				"Downstream sla PeakBW"
			::= { slaEntry 3 }

		
		-- 1.3.6.1.4.1.17409.2.3.4.4.1.4
		slaDsCommittedBW OBJECT-TYPE
			SYNTAX INTEGER
			UNITS "kbps"
			MAX-ACCESS read-write
			STATUS current
			DESCRIPTION
				"Downstream sla CommittedBW"
			::= { slaEntry 4 }

		
		-- 1.3.6.1.4.1.17409.2.3.4.4.1.5
		slaUsFixedBW OBJECT-TYPE
			SYNTAX INTEGER  
			UNITS "kbps"
			MAX-ACCESS read-write
			STATUS current
			DESCRIPTION
				"Upstream sla FixedBW"
			::= { slaEntry 5 }

		
		-- 1.3.6.1.4.1.17409.2.3.4.4.1.6
		slaUsPeakBW OBJECT-TYPE
			SYNTAX INTEGER 
			UNITS "kbps"
			MAX-ACCESS read-write
			STATUS current
			DESCRIPTION
				"Upstream sla PeakBW"
			::= { slaEntry 6 }

		
		-- 1.3.6.1.4.1.17409.2.3.4.4.1.7
		slaUsCommittedBW OBJECT-TYPE
			SYNTAX INTEGER 
			UNITS "kbps"
			MAX-ACCESS read-write
			STATUS current
			DESCRIPTION
				"Upstream sla CommittedBW"
			::= { slaEntry 7 }

		
		-- 1.3.6.1.4.1.17409.2.3.4.5
		onuAuthenticationManagement OBJECT-IDENTITY
			STATUS current
			DESCRIPTION 
				" "
			::= { onuObjects 5 }

		
		-- 1.3.6.1.4.1.17409.2.3.4.5.1
		onuAuthenticationPolicy OBJECT-TYPE
			SYNTAX INTEGER
				{
				acceptAll(1),
				rejectNotConfigured(2)
				}
			MAX-ACCESS read-write
			STATUS current
			DESCRIPTION
				"
				Define the behavior on the auth policy            
				acceptAll(1) - Disable ONU authentication, all ONU could register
				               to OLT
				rejectNotConfigured(2) - Only the relationship b/w ONU ID and MAC address defined
				         in onuAuthenticationPreConfigTable could register to OLT.
				"
			::= { onuAuthenticationManagement 1 }

		
		-- 1.3.6.1.4.1.17409.2.3.4.5.2
		onuAuthenticationPreConfigTable OBJECT-TYPE
			SYNTAX SEQUENCE OF OnuAuthenticationPreConfigEntry
			MAX-ACCESS not-accessible
			STATUS current
			DESCRIPTION
				"A list of onuAuthenticationPreConfigTable entries. "
			::= { onuAuthenticationManagement 2 }

		
		-- 1.3.6.1.4.1.17409.2.3.4.5.2.1
		onuAuthenticationPreConfigEntry OBJECT-TYPE
			SYNTAX OnuAuthenticationPreConfigEntry
			MAX-ACCESS not-accessible
			STATUS current
			DESCRIPTION
				"The onuAuthenticationPreConfigEntry Information"
			INDEX { onuAuthenOnuId }
			::= { onuAuthenticationPreConfigTable 1 }

		
		OnuAuthenticationPreConfigEntry ::=
			SEQUENCE { 
				onuAuthenOnuId
					EponDeviceIndex,
				onuAuthenMacAddress
					MacAddress,
				onuAuthenAction
					INTEGER,
				onuAuthenRowStatus
					INTEGER
			 }

		-- 1.3.6.1.4.1.17409.2.3.4.5.2.1.1
		onuAuthenOnuId OBJECT-TYPE
			SYNTAX EponDeviceIndex (1..2147483647)
			MAX-ACCESS not-accessible
			STATUS current
			DESCRIPTION
				"onu logical ID"
			::= { onuAuthenticationPreConfigEntry 1 }

		
		-- 1.3.6.1.4.1.17409.2.3.4.5.2.1.2
		onuAuthenMacAddress OBJECT-TYPE
			SYNTAX MacAddress
			MAX-ACCESS read-create
			STATUS current
			DESCRIPTION
				"onu Mac Address"
			::= { onuAuthenticationPreConfigEntry 2 }

		
		-- 1.3.6.1.4.1.17409.2.3.4.5.2.1.3
		onuAuthenAction OBJECT-TYPE
			SYNTAX INTEGER
				{
				accept(1),
				reject(2)
				}
			MAX-ACCESS read-create
			STATUS current
			DESCRIPTION
				"Authen Action
				
				This is optional in function"
			::= { onuAuthenticationPreConfigEntry 3 }

		
		-- 1.3.6.1.4.1.17409.2.3.4.5.2.1.4
		onuAuthenRowStatus OBJECT-TYPE
			SYNTAX INTEGER{active(1), notInService(2), notReady(3), createAndGo(4), createAndWait(5), destroy(6) }
			MAX-ACCESS read-create
			STATUS current
			DESCRIPTION
				"authen Row Status"
			::= { onuAuthenticationPreConfigEntry 4 }

		
		 onuAuthenticationBlockTable  OBJECT-TYPE
        SYNTAX      SEQUENCE OF OnuAuthenticationBlockEntry
        MAX-ACCESS  not-accessible
        STATUS      current
        DESCRIPTION
            "A list of onuAuthenticationBlockTable entries. "
        ::= {onuAuthenticationManagement 3 }
        
    onuAuthenticationBlockEntry  OBJECT-TYPE
        SYNTAX      OnuAuthenticationBlockEntry
        MAX-ACCESS  not-accessible
        STATUS      current
        DESCRIPTION  
            "The onuAuthenticationBlockEntry Information"
        INDEX       { onuAuthenBlockOnuId }   
        ::={onuAuthenticationBlockTable 1 }   
        
    OnuAuthenticationBlockEntry ::= SEQUENCE {
        onuAuthenBlockOnuId                   EponDeviceIndex,
        onuAuthenBlockMacAddress              MacAddress,
        authenBlockTime                       TimeTicks,
        onuAuthenBlockRowStatus               RowStatus
      }    
        
       
    onuAuthenBlockOnuId  OBJECT-TYPE
        SYNTAX      EponDeviceIndex
        MAX-ACCESS  not-accessible
        STATUS      current
        DESCRIPTION
            "ONU Id"
        ::= {onuAuthenticationBlockEntry 1 }   
        
    onuAuthenBlockMacAddress  OBJECT-TYPE
        SYNTAX      MacAddress
        MAX-ACCESS  read-create
        STATUS      current
        DESCRIPTION
            "Mac Address"
        ::= {onuAuthenticationBlockEntry 2 }  
        
    authenBlockTime  OBJECT-TYPE
        SYNTAX      TimeTicks
        MAX-ACCESS  read-create
        STATUS      current
        DESCRIPTION
            "\u52a0\u5165\u9ed1\u540d\u5355\u65f6\u95f4"
        ::= {onuAuthenticationBlockEntry 3 }   

   onuAuthenBlockRowStatus  OBJECT-TYPE
        SYNTAX      RowStatus
        MAX-ACCESS  read-create 
        STATUS      current
        DESCRIPTION
            " Row Status"
        ::= { onuAuthenticationBlockEntry 4 }
        
	-- 1.3.6.1.4.1.17409.2.3.4.5.4		
    onuLoidAuthenticationConfigTable  OBJECT-TYPE
        SYNTAX      SEQUENCE OF OnuLoidAuthenticationConfigEntry
        MAX-ACCESS  not-accessible
        STATUS      current
        DESCRIPTION
            "A list of onu LOID AuthenticationConfigTable entries. "
        ::= {onuAuthenticationManagement 4 }
    -- 1.3.6.1.4.1.17409.2.3.4.5.4.1    
    onuLoidAuthenticationConfigEntry  OBJECT-TYPE
        SYNTAX      OnuLoidAuthenticationConfigEntry
        MAX-ACCESS  not-accessible
        STATUS      current
        DESCRIPTION  
            "The onuLoidAuthenticationConfigEntryInformation"
        INDEX       { onuLoidAuthenOnuId}   
        ::={ onuLoidAuthenticationConfigTable   1 }   
        
    OnuLoidAuthenticationConfigEntry  ::= SEQUENCE {
        onuLoidAuthenOnuId                        EponDeviceIndex,  
        onuLoidAuthenLOID                             OCTET STRING,
        onuLoidAuthenPassword                         OCTET STRING,
        onuLoidAuthenRowStatus                        RowStatus
      } 
         
    -- 1.3.6.1.4.1.17409.2.3.4.5.4.1.1
    onuLoidAuthenOnuId  OBJECT-TYPE
        SYNTAX      EponDeviceIndex
        MAX-ACCESS  not-accessible
        STATUS      current
        DESCRIPTION
            "onu logical ID"
        ::= { onuLoidAuthenticationConfigEntry  1 } 

    -- 1.3.6.1.4.1.17409.2.3.4.5.4.1.2
    onuLoidAuthenLOID OBJECT-TYPE
         SYNTAX  OCTET STRING(SIZE(1..24))
         MAX-ACCESS  read-create
         STATUS  current
         DESCRIPTION
                    ""
         ::= { onuLoidAuthenticationConfigEntry  2 }
    -- 1.3.6.1.4.1.17409.2.3.4.5.4.1.3
    onuLoidAuthenPassword OBJECT-TYPE
         SYNTAX  OCTET STRING(SIZE(0..12))
         MAX-ACCESS  read-create
         STATUS  current
         DESCRIPTION
         " "
         ::= { onuLoidAuthenticationConfigEntry  3 }

    -- 1.3.6.1.4.1.17409.2.3.4.5.4.1.4
    onuLoidAuthenRowStatus OBJECT-TYPE
          SYNTAX  RowStatus
          MAX-ACCESS  read-create
          STATUS  current
          DESCRIPTION
          " Row Status"
          ::= { onuLoidAuthenticationConfigEntry  4 }
	
   onuAutoFindTable  OBJECT-TYPE
        SYNTAX      SEQUENCE OF OnuAutoFindEntry
        MAX-ACCESS  not-accessible
        STATUS      current
        DESCRIPTION
            "A list of autofind list entries. "
        ::= { onuObjects 6 }
        
    onuAutoFindEntry   OBJECT-TYPE
        SYNTAX      OnuAutoFindEntry  
        MAX-ACCESS  not-accessible
        STATUS      current
        DESCRIPTION  
            "The onuAutoFindEntry  Information
          \u81ea\u52a8\u4e0a\u7535\u4e0a\u7ebf\u7684\u672a\u6388\u6743\u7684ONU,\u5168\u90e8\u53ea\u8bfb,\u4e0d\u505a\u914d\u7f6e"
        INDEX       { onuAutoFindOnuIndex  }   
        ::={ onuAutoFindTable  1 }   
        
    OnuAutoFindEntry ::= SEQUENCE {
        onuAutoFindOnuIndex	               EponDeviceIndex,
        onuAutoFindMacAddress	             MacAddress,
        onuAutoFindTime	                   TimeTicks,     
        onuAutoFindAuthenLOID             OCTET STRING,
        onuAutoFindAuthenPassword         OCTET STRING
              }    
        
       
    onuAutoFindOnuIndex  OBJECT-TYPE
        SYNTAX      EponDeviceIndex
        MAX-ACCESS  not-accessible
        STATUS      current
        DESCRIPTION
            "index "
        ::= { onuAutoFindEntry   1 }   
        
    onuAutoFindMacAddress  OBJECT-TYPE
        SYNTAX      MacAddress
        MAX-ACCESS  read-only
        STATUS      current
        DESCRIPTION
            "Mac Address"
        ::= { onuAutoFindEntry   2 }  
        
    onuAutoFindTime  OBJECT-TYPE
        SYNTAX      TimeTicks
        MAX-ACCESS  read-only
        STATUS      current
        DESCRIPTION
            "\u4e0a\u7ebf\u65f6\u95f4"
        ::= { onuAutoFindEntry   3 }   


  onuAutoFindAuthenLOID  OBJECT-TYPE
         SYNTAX  OCTET STRING(SIZE(1..24))
         MAX-ACCESS  read-only
         STATUS  current
         DESCRIPTION
             " ONU\u8ba4\u8bc1\u903b\u8f91\u6807\u8bc6;
                                   \u5f53\u4f4d\u6570\u4e3a0\u7684\u65f6\u5019,\u8868\u793a\u6ca1\u6709 "
         ::= { onuAutoFindEntry   4  }

    onuAutoFindAuthenPassword   OBJECT-TYPE
         SYNTAX  OCTET STRING(SIZE(0..12))
         MAX-ACCESS  read-only
         STATUS  current
         DESCRIPTION
         "\u5bc6\u7801\u4e3a0\uff5e12\u4f4d\u7684\u5b57\u7b26\u4e32,\u5982356abc,\u5f53\u4f4d\u6570\u4e3a0\u7684\u65f6\u5019,\u8868\u793a\u6ca1\u6709\u5bc6\u7801"
         ::= { onuAutoFindEntry  5 }
		
		
		
		
		
		-- 1.3.6.1.4.1.17409.2.3.5
		uniObjects OBJECT IDENTIFIER ::= { eponTree 5 }

		
-- ------------------------------------------------------------------------------
-- uniObjects[UNI](1.3.6.1.4.1.17409.2.3.5)
-- ------------------------------------------------------------------------------ 
		-- 1.3.6.1.4.1.17409.2.3.5.1
		uniAttributeTable OBJECT-TYPE
			SYNTAX SEQUENCE OF UniAttributeEntry
			MAX-ACCESS not-accessible
			STATUS current
			DESCRIPTION
				"A list of uniAttributeTable entries."
			::= { uniObjects 1 }

		
		-- 1.3.6.1.4.1.17409.2.3.5.1.1
		uniAttributeEntry OBJECT-TYPE
			SYNTAX UniAttributeEntry
			MAX-ACCESS not-accessible
			STATUS current
			DESCRIPTION
				"The uniAttributeEntry Information"
			INDEX { uniAttributeDeviceIndex, uniAttributeCardIndex, uniAttributePortIndex }
			::= { uniAttributeTable 1 }

		
		UniAttributeEntry ::=
			SEQUENCE { 
				uniAttributeDeviceIndex
					EponDeviceIndex,
				uniAttributeCardIndex
					EponCardIndex,
				uniAttributePortIndex
					EponPortIndex,
				uniAdminStatus
					INTEGER,
				uniOperationStatus
					INTEGER,
				uniAutoNegotiationEnable
					TruthValue,
				uniAutoNegotiationLocalTechAbility
					AutoNegotiationTechAbility,
				uniAutoNegotiationRestart
					INTEGER,
				uniMacAddrLearnMaxNum
				    INTEGER,
				uniCurrentPerfStatsEnable  
     				TruthValue
			 }

		-- 1.3.6.1.4.1.17409.2.3.5.1.1.1
		uniAttributeDeviceIndex OBJECT-TYPE
			SYNTAX EponDeviceIndex
			MAX-ACCESS not-accessible
			STATUS current
			DESCRIPTION
				"Device Index
				
				For OLT, set to corresponding ONU ID
				For ONU, set to 0
				"
			::= { uniAttributeEntry 1 }

		
		-- 1.3.6.1.4.1.17409.2.3.5.1.1.2
		uniAttributeCardIndex OBJECT-TYPE
			SYNTAX EponCardIndex (1..2147483647)
			MAX-ACCESS not-accessible
			STATUS current
			DESCRIPTION
				"Card Index            
				The value of this cardIndex depends on onuType.            
				fixed(1)        - set to 0, to indicate slot num is meaningless.
				chassisBased(2) - MUST NOT be zero            
				"
			::= { uniAttributeEntry 2 }

		
		-- 1.3.6.1.4.1.17409.2.3.5.1.1.3
		uniAttributePortIndex OBJECT-TYPE
			SYNTAX EponPortIndex (1..2147483647)
			MAX-ACCESS not-accessible
			STATUS current
			DESCRIPTION
				"Port Index"
			::= { uniAttributeEntry 3 }

		
		-- 1.3.6.1.4.1.17409.2.3.5.1.1.4
		uniAdminStatus OBJECT-TYPE
			SYNTAX INTEGER
				{
				up(1),
				down(2),
				testing(3)
				}
			MAX-ACCESS read-write
			STATUS current
			DESCRIPTION
				"Admin Status"
			::= { uniAttributeEntry 4 }

		
		-- 1.3.6.1.4.1.17409.2.3.5.1.1.5
		uniOperationStatus OBJECT-TYPE
			SYNTAX INTEGER
				{
				up(1),
				down(2),
				testing(3)
				}
			MAX-ACCESS read-only
			STATUS current
			DESCRIPTION
				"Operation Status"
			::= { uniAttributeEntry 5 }

		
		-- 1.3.6.1.4.1.17409.2.3.5.1.1.6
		uniAutoNegotiationEnable OBJECT-TYPE
			SYNTAX TruthValue
			MAX-ACCESS read-write
			STATUS current
			DESCRIPTION
				"Whether or not to enable auto negotiation on the uni port"
			::= { uniAttributeEntry 6 }

		
		-- 1.3.6.1.4.1.17409.2.3.5.1.1.7
		uniAutoNegotiationLocalTechAbility OBJECT-TYPE
			SYNTAX AutoNegotiationTechAbility
			MAX-ACCESS read-only
			STATUS current
			DESCRIPTION
				"This indicates the technology ability of the local device"
			::= { uniAttributeEntry 7 }

		
		-- 1.3.6.1.4.1.17409.2.3.5.1.1.8
		uniAutoNegotiationRestart OBJECT-TYPE
			SYNTAX INTEGER { restart(1) }
			MAX-ACCESS read-write
			STATUS current
			DESCRIPTION
				"Restart the autonegotiation"
			::= { uniAttributeEntry 8 }
			
		-- 1.3.6.1.4.1.17409.2.3.5.1.1.9	
        uniMacAddrLearnMaxNum  OBJECT-TYPE
            SYNTAX      INTEGER
            MAX-ACCESS  read-write
             STATUS      current
            DESCRIPTION
            "Mac Address Learn Max Num"
            ::= { uniAttributeEntry  9 }       

		-- 1.3.6.1.4.1.17409.2.3.5.1.1.10
        uniCurrentPerfStatsEnable   OBJECT-TYPE
           SYNTAX      TruthValue  
           MAX-ACCESS  read-write
           STATUS      current
           DESCRIPTION
           "true(1) false(2)"
           ::= { uniAttributeEntry  10 }
		
		-- 1.3.6.1.4.1.17409.2.3.5.2
		uniMacAddressManagement OBJECT-IDENTITY
			STATUS current
			DESCRIPTION 
				" "
			::= { uniObjects 2 }

		
	uniMacAddressManagementTable  OBJECT-TYPE
        SYNTAX  SEQUENCE OF UniMacAddressManagementEntry
        MAX-ACCESS  not-accessible
        STATUS      current
        DESCRIPTION
            "A list of MacAddress global parameter in a onu."
        ::= { uniMacAddressManagement 1 }

    uniMacAddressManagementEntry  OBJECT-TYPE
        SYNTAX      UniMacAddressManagementEntry
        MAX-ACCESS  not-accessible
        STATUS      current
        DESCRIPTION
            " "
        INDEX   { uniMacAddrONUIndex }
        ::= { uniMacAddressManagementTable 1 }


UniMacAddressManagementEntry::=
        SEQUENCE {
        uniMacAddrONUIndex   EponDeviceIndex,
        uniMacAddrAgingTime   INTEGER,
        uniMacAddrClear      INTEGER   
        }


    uniMacAddrONUIndex   OBJECT-TYPE
  SYNTAX      EponDeviceIndex
        MAX-ACCESS  not-accessible
        STATUS      current
        DESCRIPTION
            "onuDevice Index"
        ::= { uniMacAddressManagementEntry 1 }



    uniMacAddrAgingTime   OBJECT-TYPE
        SYNTAX      INTEGER
        UNITS   "Seconds" 
        MAX-ACCESS  read-write
        STATUS      current
        DESCRIPTION
            "Mac Address Table Aging Time"
        ::= { uniMacAddressManagementEntry 2 }

    uniMacAddrClear OBJECT-TYPE
        SYNTAX      INTEGER { allDynamic(1) }
        MAX-ACCESS  read-write
        STATUS      current
        DESCRIPTION
            "Mac Address Table Clear"
        ::= { uniMacAddressManagementEntry 3 }

		
		-- 1.3.6.1.4.1.17409.2.3.5.2.2
		uniMacAddressTable OBJECT-TYPE
			SYNTAX SEQUENCE OF UniMacAddressEntry
			MAX-ACCESS not-accessible
			STATUS current
			DESCRIPTION
				"A list of MacAddress entries."
			::= { uniMacAddressManagement 2 }

		
		-- 1.3.6.1.4.1.17409.2.3.5.2.2.1
		uniMacAddressEntry OBJECT-TYPE
			SYNTAX UniMacAddressEntry
			MAX-ACCESS not-accessible
			STATUS current
			DESCRIPTION
				"The Mac Address Information"
			INDEX { uniMacAddrIndex, uniMacAddrVlanIdIndex }
			::= { uniMacAddressTable 1 }

		
		UniMacAddressEntry ::=
			SEQUENCE { 
				uniMacAddrIndex
					MacAddress,
				uniMacAddrVlanIdIndex
					INTEGER,
				uniMacAddrType
					INTEGER,
				uniMacAddrPortId
					OCTET STRING,
				uniMacAddrRowStatus
					RowStatus
			 }

		-- 1.3.6.1.4.1.17409.2.3.5.2.2.1.1
		uniMacAddrIndex OBJECT-TYPE
			SYNTAX MacAddress
			MAX-ACCESS not-accessible
			STATUS current
			DESCRIPTION
				"Mac Address Index"
			::= { uniMacAddressEntry 1 }

		
		-- 1.3.6.1.4.1.17409.2.3.5.2.2.1.2
		uniMacAddrVlanIdIndex OBJECT-TYPE
			SYNTAX INTEGER (1..2147483647)
			MAX-ACCESS not-accessible
			STATUS current
			DESCRIPTION
				"Mac Address Vlan Id Index"
			::= { uniMacAddressEntry 2 }

		
		-- 1.3.6.1.4.1.17409.2.3.5.2.2.1.3
		uniMacAddrType OBJECT-TYPE
			SYNTAX INTEGER
				{
				static(1),
				dynamic(2),
				other(3)
				}
			MAX-ACCESS read-create
			STATUS current
			DESCRIPTION
				"Mac Address Type"
			::= { uniMacAddressEntry 3 }

		
		-- 1.3.6.1.4.1.17409.2.3.5.2.2.1.4
		uniMacAddrPortId OBJECT-TYPE
			SYNTAX OCTET STRING (SIZE (2))
			MAX-ACCESS read-create
			STATUS current
			DESCRIPTION
				"Mac Address Port Id
				The first octet is slot ID, the second octet is port ID.
				If the device is fixed (not modulized), set slot ID to 0.
				Note that, slot here shall follow the last byte definition of 
				EponCardIndex to indicate the main-slot and sub-slot index.                    
				For example, for modulized port 10/3, set to 0x0A 03
				For fix box port 3, set to 0x00 03
				"
			::= { uniMacAddressEntry 4 }

		
		-- 1.3.6.1.4.1.17409.2.3.5.2.2.1.5
		uniMacAddrRowStatus OBJECT-TYPE
			SYNTAX RowStatus
			MAX-ACCESS read-create
			STATUS current
			DESCRIPTION
				"delete,create. Update is not supported"
			::= { uniMacAddressEntry 5 }

		
		-- 1.3.6.1.4.1.17409.2.3.5.3
		uniTrunkManagement OBJECT-IDENTITY
			STATUS current
			DESCRIPTION 
				" "
			::= { uniObjects 3 }

		
		-- 1.3.6.1.4.1.17409.2.3.5.3.1
		uniTrunkGroupConfigTable OBJECT-TYPE
			SYNTAX SEQUENCE OF UniTrunkGroupConfigEntry
			MAX-ACCESS not-accessible
			STATUS current
			DESCRIPTION
				"A list of uniTrunkGroupConfigTable entries."
			::= { uniTrunkManagement 1 }

		
		-- 1.3.6.1.4.1.17409.2.3.5.3.1.1
		uniTrunkGroupConfigEntry OBJECT-TYPE
			SYNTAX UniTrunkGroupConfigEntry
			MAX-ACCESS not-accessible
			STATUS current
			DESCRIPTION
				"The uniTrunk Group Config Entry Information"
			INDEX { uniTrunkGroupConfigIndex }
			::= { uniTrunkGroupConfigTable 1 }

		
		UniTrunkGroupConfigEntry ::=
			SEQUENCE { 
				uniTrunkGroupConfigIndex
					INTEGER,
				uniTrunkGroupConfigName
					DisplayString,
				uniTrunkGroupConfigMember
					OCTET STRING,
				uniTrunkGroupConfigPolicy
					INTEGER,
				uniTrunkGroupConfigRowstatus
					RowStatus
			 }

		-- 1.3.6.1.4.1.17409.2.3.5.3.1.1.1
		uniTrunkGroupConfigIndex OBJECT-TYPE
			SYNTAX INTEGER (1..2147483647)
			MAX-ACCESS not-accessible
			STATUS current
			DESCRIPTION
				"Trunk Group Config Index"
			::= { uniTrunkGroupConfigEntry 1 }

		
		-- 1.3.6.1.4.1.17409.2.3.5.3.1.1.2
		uniTrunkGroupConfigName OBJECT-TYPE
			SYNTAX DisplayString
			MAX-ACCESS read-create
			STATUS current
			DESCRIPTION
				"Trunk Group Config Name"
			::= { uniTrunkGroupConfigEntry 2 }

		
		-- 1.3.6.1.4.1.17409.2.3.5.3.1.1.3
		uniTrunkGroupConfigMember OBJECT-TYPE
			SYNTAX OCTET STRING
			MAX-ACCESS read-create
			STATUS current
			DESCRIPTION
				"Trunk Group Config Member.            
				It is presented by member port list. Each member port is identified
				by 2-byte format, One for slot ID, the last for port ID. The actual 
				length of this string depends of the number of member ports in the 
				trunk group. If the ONU is fixed (not modulized), set slot ID to 0,
				the NMS could ignore the slot info.   
				Note that, slot here shall follow the last byte definition of 
				EponCardIndex to indicate the main-slot and sub-slot index.     
				The relationship is:  
				Length of the string = 2 * (NUM of member ports)    
				For example, if port 1/2 and 3/4 is the member ports of the
				trunk, then the object is presented as:      
				01 02 03 04                        
				      "
			::= { uniTrunkGroupConfigEntry 3 }

		
		-- 1.3.6.1.4.1.17409.2.3.5.3.1.1.4
		uniTrunkGroupConfigPolicy OBJECT-TYPE
			SYNTAX INTEGER
				{
				srcMac(1),
				destMac(2),
				srcMacNDestMac(3),
				srcIp(4),
				destIp(5),
				srcIpNDestIp(6)
				}
			MAX-ACCESS read-create
			STATUS current
			DESCRIPTION
				"Trunk Group Config Policy"
			::= { uniTrunkGroupConfigEntry 4 }

		
		-- 1.3.6.1.4.1.17409.2.3.5.3.1.1.5
		uniTrunkGroupConfigRowstatus OBJECT-TYPE
			SYNTAX RowStatus
			MAX-ACCESS read-create
			STATUS current
			DESCRIPTION
				"Trunk Group Config Rowstatus"
			::= { uniTrunkGroupConfigEntry 5 }

		
		-- 1.3.6.1.4.1.17409.2.3.5.3.2
		uniTrunkGroupTable OBJECT-TYPE
			SYNTAX SEQUENCE OF UniTrunkGroupEntry
			MAX-ACCESS not-accessible
			STATUS current
			DESCRIPTION
				"a list of uniTrunkGroupConfigTable entries."
			::= { uniTrunkManagement 2 }

		
		-- 1.3.6.1.4.1.17409.2.3.5.3.2.1
		uniTrunkGroupEntry OBJECT-TYPE
			SYNTAX UniTrunkGroupEntry
			MAX-ACCESS not-accessible
			STATUS current
			DESCRIPTION
				"Trunk Group Entry"
			INDEX { uniTrunkGroupIndex }
			::= { uniTrunkGroupTable 1 }

		
		UniTrunkGroupEntry ::=
			SEQUENCE { 
				uniTrunkGroupIndex
					INTEGER,
				uniTrunkGroupOperationStatus
					INTEGER,
				uniTrunkGroupActualSpeed
					INTEGER,
				uniTrunkGroupAdminStatus
					INTEGER
			 }

		-- 1.3.6.1.4.1.17409.2.3.5.3.2.1.1
		uniTrunkGroupIndex OBJECT-TYPE
			SYNTAX INTEGER (1..2147483647)
			MAX-ACCESS not-accessible
			STATUS current
			DESCRIPTION
				"Trunk Group Index"
			::= { uniTrunkGroupEntry 1 }

		
		-- 1.3.6.1.4.1.17409.2.3.5.3.2.1.2
		uniTrunkGroupOperationStatus OBJECT-TYPE
			SYNTAX INTEGER
				{
				up(1),
				down(2),
				testing(3)
				}
			MAX-ACCESS read-only
			STATUS current
			DESCRIPTION
				"Trunk Group Operation Status"
			::= { uniTrunkGroupEntry 2 }

		
		-- 1.3.6.1.4.1.17409.2.3.5.3.2.1.3
		uniTrunkGroupActualSpeed OBJECT-TYPE
			SYNTAX INTEGER
			UNITS "Mbps"
			MAX-ACCESS read-only
			STATUS current
			DESCRIPTION
				"Trunk Group Actual Speed.            
				The speed is the aggregated rates of all operational UP member
				ports of the trunk.            
				For example, 4 member ports of the trunk, two are UP, each is 1000M
				then the SUN is 2000M. As a result, the return of the MIB shall be
				2000Mbps"
			::= { uniTrunkGroupEntry 3 }

		
		-- 1.3.6.1.4.1.17409.2.3.5.3.2.1.4
		uniTrunkGroupAdminStatus OBJECT-TYPE
			SYNTAX INTEGER
				{
				up(1),
				down(2),
				testing(3)
				}
			MAX-ACCESS read-write
			STATUS current
			DESCRIPTION
				"Trunk Group AdminStatus"
			::= { uniTrunkGroupEntry 4 }

		
		-- 1.3.6.1.4.1.17409.2.3.5.4
		uniPortRateLimitTable OBJECT-TYPE
			SYNTAX SEQUENCE OF UniPortRateLimitEntry
			MAX-ACCESS not-accessible
			STATUS current
			DESCRIPTION
				"A list of PortRateLimit entries."
			::= { uniObjects 4 }

		
		-- 1.3.6.1.4.1.17409.2.3.5.4.1
		uniPortRateLimitEntry OBJECT-TYPE
			SYNTAX UniPortRateLimitEntry
			MAX-ACCESS not-accessible
			STATUS current
			DESCRIPTION
				"The Port Rate Limit Information"
			INDEX { uniPortRateLimitDeviceIndex, uniPortRateLimitCardIndex, uniPortRateLimitPortIndex }
			::= { uniPortRateLimitTable 1 }

		
		UniPortRateLimitEntry ::=
			SEQUENCE { 
				uniPortRateLimitDeviceIndex
					EponDeviceIndex,
				uniPortRateLimitCardIndex
					EponCardIndex,
				uniPortRateLimitPortIndex
					EponPortIndex,
				uniPortInCIR
					INTEGER,
				uniPortInCBS
					INTEGER,
				uniPortInEBS
					INTEGER,
				uniPortOutCIR
					INTEGER,
				uniPortOutPIR
					INTEGER,
				uniPortInRateLimitEnable
					TruthValue,
				uniPortOutRateLimitEnable
					TruthValue
			 }

		-- 1.3.6.1.4.1.17409.2.3.5.4.1.1
		uniPortRateLimitDeviceIndex OBJECT-TYPE
			SYNTAX EponDeviceIndex (1..2147483647)
			MAX-ACCESS not-accessible
			STATUS current
			DESCRIPTION
				"device Index
				
				For OLT, set to corresponding ONU ID
				For ONU, set to 0
				"
			::= { uniPortRateLimitEntry 1 }

		
		-- 1.3.6.1.4.1.17409.2.3.5.4.1.2
		uniPortRateLimitCardIndex OBJECT-TYPE
			SYNTAX EponCardIndex (1..2147483647)
			MAX-ACCESS not-accessible
			STATUS current
			DESCRIPTION
				"card Index            
				The value of this cardIndex depends on onuType.            
				fixed(1)        - set to 0, to indicate slot num is meaningless.
				chassisBased(2) - MUST NOT be zero 
				"
			::= { uniPortRateLimitEntry 2 }

		
		-- 1.3.6.1.4.1.17409.2.3.5.4.1.3
		uniPortRateLimitPortIndex OBJECT-TYPE
			SYNTAX EponPortIndex (1..2147483647)
			MAX-ACCESS not-accessible
			STATUS current
			DESCRIPTION
				"port Index"
			::= { uniPortRateLimitEntry 3 }

		
		-- 1.3.6.1.4.1.17409.2.3.5.4.1.4
		uniPortInCIR OBJECT-TYPE
			SYNTAX INTEGER
			UNITS "kbps"
			MAX-ACCESS read-write
			STATUS current
			DESCRIPTION
				"Committed Information Rate(CIR) in kbps."
			::= { uniPortRateLimitEntry 4 }

		
		-- 1.3.6.1.4.1.17409.2.3.5.4.1.5
		uniPortInCBS OBJECT-TYPE
			SYNTAX INTEGER
			UNITS "Kbytes"
			MAX-ACCESS read-write
			STATUS current
			DESCRIPTION
				"Committed Burst Rate(CBS) in kbyte."
			::= { uniPortRateLimitEntry 5 }

		
		-- 1.3.6.1.4.1.17409.2.3.5.4.1.6
		uniPortInEBS OBJECT-TYPE
			SYNTAX INTEGER
			UNITS "Kbytes"
			MAX-ACCESS read-write
			STATUS current
			DESCRIPTION
				"ebs in kbytes."
			::= { uniPortRateLimitEntry 6 }

		
		-- 1.3.6.1.4.1.17409.2.3.5.4.1.7
		uniPortOutCIR OBJECT-TYPE
			SYNTAX INTEGER
			UNITS "Kbps"
			MAX-ACCESS read-write
			STATUS current
			DESCRIPTION
				"Committed Information Rate(CIR) in kbps."
			::= { uniPortRateLimitEntry 7 }

		
		-- 1.3.6.1.4.1.17409.2.3.5.4.1.8
		uniPortOutPIR OBJECT-TYPE
			SYNTAX INTEGER
			UNITS "Kbps"
			MAX-ACCESS read-write
			STATUS current
			DESCRIPTION
				"PIR in kbps."
			::= { uniPortRateLimitEntry 8 }

		
		-- 1.3.6.1.4.1.17409.2.3.5.4.1.9
		uniPortInRateLimitEnable OBJECT-TYPE
			SYNTAX TruthValue
			MAX-ACCESS read-write
			STATUS current
			DESCRIPTION
				"Whether or not to enable or disable ingress rate limit for the UNI."
			::= { uniPortRateLimitEntry 9 }

		
		-- 1.3.6.1.4.1.17409.2.3.5.4.1.10
		uniPortOutRateLimitEnable OBJECT-TYPE
			SYNTAX TruthValue
			MAX-ACCESS read-write
			STATUS current
			DESCRIPTION
				"Whether or not to enable or disable egress rate limit for the UNI."
			::= { uniPortRateLimitEntry 10 }

		
		-- 1.3.6.1.4.1.17409.2.3.5.5
		uniMirrorTable OBJECT-TYPE
			SYNTAX SEQUENCE OF UniMirrorEntry
			MAX-ACCESS not-accessible
			STATUS current
			DESCRIPTION
				"a list of uniMirrorTable entries."
			::= { uniObjects 5 }

		
		-- 1.3.6.1.4.1.17409.2.3.5.5.1
		uniMirrorEntry OBJECT-TYPE
			SYNTAX UniMirrorEntry
			MAX-ACCESS not-accessible
			STATUS current
			DESCRIPTION
				"The Mirror Information."
			INDEX { uniMirrorGroupIndex }
			::= { uniMirrorTable 1 }

		
		UniMirrorEntry ::=
			SEQUENCE { 
				uniMirrorGroupIndex
					INTEGER,
				uniMirrorGroupName
					DisplayString,
				uniMirrorGroupDstPortList
					OCTET STRING,
				uniMirrorGroupSrcInPortList
					OCTET STRING,
				uniMirrorGroupSrcOutPortList
					OCTET STRING,
				uniMirrorGroupRowstatus
					RowStatus
			 }

		-- 1.3.6.1.4.1.17409.2.3.5.5.1.1
		uniMirrorGroupIndex OBJECT-TYPE
			SYNTAX INTEGER (1..2147483647)
			MAX-ACCESS not-accessible
			STATUS current
			DESCRIPTION
				"Mirror Group Index"
			::= { uniMirrorEntry 1 }

		
		-- 1.3.6.1.4.1.17409.2.3.5.5.1.2
		uniMirrorGroupName OBJECT-TYPE
			SYNTAX DisplayString
			MAX-ACCESS read-create
			STATUS current
			DESCRIPTION
				"Mirror Group Name"
			::= { uniMirrorEntry 2 }

		
		-- 1.3.6.1.4.1.17409.2.3.5.5.1.3
		uniMirrorGroupDstPortList OBJECT-TYPE
			SYNTAX OCTET STRING
			MAX-ACCESS read-create
			STATUS current
			DESCRIPTION
				"Mirror Group Dst Port List.            
				It is presented by port list. Each port is identified by 
				2-byte format, One for slot ID, the last for port ID. The 
				actual length of this string depends of the number of  
				ports in destination port list of the mirror group, 
				If the ONU is fixed (not modulized), set slot ID to 0,
				the NMS could ignore the slot info.  
				Note that, slot here shall follow the last byte definition of 
				EponCardIndex to indicate the main-slot and sub-slot index.       
				The relationship is:
				Length of the string = 2 * (NUM of ports)  
				For example, if port 1/2 and 3/4 is the destination ports of 
				the mirror group, then the object is presented as:
				01 02 03 04   
				"
			::= { uniMirrorEntry 3 }

		
		-- 1.3.6.1.4.1.17409.2.3.5.5.1.4
		uniMirrorGroupSrcInPortList OBJECT-TYPE
			SYNTAX OCTET STRING
			MAX-ACCESS read-create
			STATUS current
			DESCRIPTION
				"Mirror Group Src In Port List.            
				It is presented by port list. Each port is identified by 
				2-byte format, One for slot ID, the last for port ID. The 
				actual length of this string depends of the number of  
				ports in source ingress list of the mirror group, 
				If the ONU is fixed (not modulized), set slot ID to 0,
				the NMS could ignore the slot info.  
				Note that, slot here shall follow the last byte definition of 
				EponCardIndex to indicate the main-slot and sub-slot index.       
				The relationship is:
				Length of the string = 2 * (NUM of ports)  
				For example, if port 1/2 and 3/4 is the source ingress ports of 
				the mirror group, then the object is presented as:
				01 02 03 04  
				"
			::= { uniMirrorEntry 4 }

		
		-- 1.3.6.1.4.1.17409.2.3.5.5.1.5
		uniMirrorGroupSrcOutPortList OBJECT-TYPE
			SYNTAX OCTET STRING
			MAX-ACCESS read-create
			STATUS current
			DESCRIPTION
				"Mirror Group Src Out Port List.            
				It is presented by port list. Each port is identified by 
				2-byte format, One for slot ID, the last for port ID. The 
				actual length of this string depends of the number of  
				ports in source egress list of the mirror group, 
				If the ONU is fixed (not modulized), set slot ID to 0,
				the NMS could ignore the slot info.    
				Note that, slot here shall follow the last byte definition of 
				EponCardIndex to indicate the main-slot and sub-slot index.     
				The relationship is:
				Length of the string = 2 * (NUM of ports)  
				For example, if port 1/2 and 3/4 is the source egress ports of 
				the mirror group, then the object is presented as:
				01 02 03 04              
				"
			::= { uniMirrorEntry 5 }

		
		-- 1.3.6.1.4.1.17409.2.3.5.5.1.6
		uniMirrorGroupRowstatus OBJECT-TYPE
			SYNTAX RowStatus
			MAX-ACCESS read-create
			STATUS current
			DESCRIPTION
				"Mirror Group Rowstatus"
			::= { uniMirrorEntry 6 }

		
		-- 1.3.6.1.4.1.17409.2.3.5.6
		uniBroadcastStormSuppressionTable OBJECT-TYPE
			SYNTAX SEQUENCE OF UniBroadcastStormSuppressionEntry
			MAX-ACCESS not-accessible
			STATUS current
			DESCRIPTION
				"A list of BroadcastStormSuppression entries."
			::= { uniObjects 6 }

		
		-- 1.3.6.1.4.1.17409.2.3.5.6.1
		uniBroadcastStormSuppressionEntry OBJECT-TYPE
			SYNTAX UniBroadcastStormSuppressionEntry
			MAX-ACCESS not-accessible
			STATUS current
			DESCRIPTION
				"The Broadcast Storm Suppression Information"
			INDEX { uniBroadcastStormSuppressionCardIndex, uniBroadcastStormSuppressionPortIndex }
			::= { uniBroadcastStormSuppressionTable 1 }

		
		UniBroadcastStormSuppressionEntry ::=
			SEQUENCE { 
				uniBroadcastStormSuppressionCardIndex
					EponCardIndex,
				uniBroadcastStormSuppressionPortIndex
					EponPortIndex,
				uniUnicastStormEnable
					TruthValue,
				uniUnicastStormInPacketRate
					INTEGER,
				uniUnicastStormOutPacketRate
					INTEGER,
				uniMulticastStormEnable
					TruthValue,
				uniMulticastStormInPacketRate
					INTEGER,
				uniMulticastStormOutPacketRate
					INTEGER,
				uniBroadcastStormEnable
					TruthValue,
				uniBroadcastStormInPacketRate
					INTEGER,
				uniBroadcastStormOutPacketRate
					INTEGER
			 }

		-- 1.3.6.1.4.1.17409.2.3.5.6.1.1
		uniBroadcastStormSuppressionCardIndex OBJECT-TYPE
			SYNTAX EponCardIndex (1..2147483647)
			MAX-ACCESS not-accessible
			STATUS current
			DESCRIPTION
				"card Index
				
				The value of this cardIndex depends on onuType.
				fixed(1)        - set to 0, to indicate slot num is meaningless.
				chassisBased(2) - MUST NOT be zero 
				"
			::= { uniBroadcastStormSuppressionEntry 1 }

		
		-- 1.3.6.1.4.1.17409.2.3.5.6.1.2
		uniBroadcastStormSuppressionPortIndex OBJECT-TYPE
			SYNTAX EponPortIndex (1..2147483647)
			MAX-ACCESS not-accessible
			STATUS current
			DESCRIPTION
				"port Index"
			::= { uniBroadcastStormSuppressionEntry 2 }

		
		-- 1.3.6.1.4.1.17409.2.3.5.6.1.3
		uniUnicastStormEnable OBJECT-TYPE
			SYNTAX TruthValue
			MAX-ACCESS read-write
			STATUS current
			DESCRIPTION
				"Cast Storm Enable"
			::= { uniBroadcastStormSuppressionEntry 3 }

		
		-- 1.3.6.1.4.1.17409.2.3.5.6.1.4
		uniUnicastStormInPacketRate OBJECT-TYPE
			SYNTAX INTEGER
			UNITS "pps"
			MAX-ACCESS read-write
			STATUS current
			DESCRIPTION
				"Cast Storm In Packet Rate"
			::= { uniBroadcastStormSuppressionEntry 4 }

		
		-- 1.3.6.1.4.1.17409.2.3.5.6.1.5
		uniUnicastStormOutPacketRate OBJECT-TYPE
			SYNTAX INTEGER
			UNITS "pps"
			MAX-ACCESS read-write
			STATUS current
			DESCRIPTION
				"Cast Storm Out Packet Rate"
			::= { uniBroadcastStormSuppressionEntry 5 }

		
		-- 1.3.6.1.4.1.17409.2.3.5.6.1.6
		uniMulticastStormEnable OBJECT-TYPE
			SYNTAX TruthValue
			MAX-ACCESS read-write
			STATUS current
			DESCRIPTION
				"true(1) false(2)"
			::= { uniBroadcastStormSuppressionEntry 6 }

		
		-- 1.3.6.1.4.1.17409.2.3.5.6.1.7
		uniMulticastStormInPacketRate OBJECT-TYPE
			SYNTAX INTEGER
			UNITS "pps"
			MAX-ACCESS read-write
			STATUS current
			DESCRIPTION
				"Multicast Storm In Packet Rate"
			::= { uniBroadcastStormSuppressionEntry 7 }

		
		-- 1.3.6.1.4.1.17409.2.3.5.6.1.8
		uniMulticastStormOutPacketRate OBJECT-TYPE
			SYNTAX INTEGER
			UNITS "pps"
			MAX-ACCESS read-write
			STATUS current
			DESCRIPTION
				"Multicast Storm Out Packet Rate"
			::= { uniBroadcastStormSuppressionEntry 8 }

		
		-- 1.3.6.1.4.1.17409.2.3.5.6.1.9
		uniBroadcastStormEnable OBJECT-TYPE
			SYNTAX TruthValue
			MAX-ACCESS read-write
			STATUS current
			DESCRIPTION
				"true(1) false(2)"
			::= { uniBroadcastStormSuppressionEntry 9 }

		
		-- 1.3.6.1.4.1.17409.2.3.5.6.1.10
		uniBroadcastStormInPacketRate OBJECT-TYPE
			SYNTAX INTEGER
			UNITS "pps"
			MAX-ACCESS read-write
			STATUS current
			DESCRIPTION
				"Broadcast Storm In Packet Rate"
			::= { uniBroadcastStormSuppressionEntry 10 }

		
		-- 1.3.6.1.4.1.17409.2.3.5.6.1.11
		uniBroadcastStormOutPacketRate OBJECT-TYPE
			SYNTAX INTEGER
			UNITS "pps"
			MAX-ACCESS read-write
			STATUS current
			DESCRIPTION
				"Broadcast Storm Out Packet Rate"
			::= { uniBroadcastStormSuppressionEntry 11 }

		
		-- 1.3.6.1.4.1.17409.2.3.5.7
		uniExtAttributeTable OBJECT-TYPE
			SYNTAX SEQUENCE OF UniExtAttributeEntry
			MAX-ACCESS not-accessible
			STATUS current
			DESCRIPTION
				"The extended attribute list for each UNI. "
			::= { uniObjects 7 }

		
		-- 1.3.6.1.4.1.17409.2.3.5.7.1
		uniExtAttributeEntry OBJECT-TYPE
			SYNTAX UniExtAttributeEntry
			MAX-ACCESS not-accessible
			STATUS current
			DESCRIPTION			" "
			INDEX { uniExtAttributeCardIndex, uniExtAttributePortIndex }
			::= { uniExtAttributeTable 1 }

		
		UniExtAttributeEntry ::=
			SEQUENCE { 
				uniExtAttributeCardIndex
					EponCardIndex,
				uniExtAttributePortIndex
					EponPortIndex,
				uniPerfStats15minuteEnable
					TruthValue,
				uniPerfStats24hourEnable
					TruthValue,
				uniLastChangeTime
					TimeTicks,
				uniIsolationEnable
					TruthValue,
				uniExMacAddrLearnMaxNum
					INTEGER,
				uniAutoNegotiationAdvertisedTechAbility
					AutoNegotiationTechAbility,
				uniMacAddrClearByPort
					INTEGER
			 }

		-- 1.3.6.1.4.1.17409.2.3.5.7.1.1
		uniExtAttributeCardIndex OBJECT-TYPE
			SYNTAX EponCardIndex (1..2147483647)
			MAX-ACCESS not-accessible
			STATUS current
			DESCRIPTION
				"Card index            
				The value of this cardIndex depends on onuType.
				fixed(1)        - set to 0, to indicate slot num is meaningless.
				chassisBased(2) - MUST NOT be zero 
				"
			::= { uniExtAttributeEntry 1 }

		
		-- 1.3.6.1.4.1.17409.2.3.5.7.1.2
		uniExtAttributePortIndex OBJECT-TYPE
			SYNTAX EponPortIndex (1..2147483647)
			MAX-ACCESS not-accessible
			STATUS current
			DESCRIPTION			" "
			::= { uniExtAttributeEntry 2 }

		
		-- 1.3.6.1.4.1.17409.2.3.5.7.1.3
		uniPerfStats15minuteEnable OBJECT-TYPE
			SYNTAX TruthValue
			MAX-ACCESS read-write
			STATUS current
			DESCRIPTION
				"true(1) false(2)"
			::= { uniExtAttributeEntry 3 }

		
		-- 1.3.6.1.4.1.17409.2.3.5.7.1.4
		uniPerfStats24hourEnable OBJECT-TYPE
			SYNTAX TruthValue
			MAX-ACCESS read-write
			STATUS current
			DESCRIPTION
				"true(1) false(2)"
			::= { uniExtAttributeEntry 4 }

		
		-- 1.3.6.1.4.1.17409.2.3.5.7.1.5
		uniLastChangeTime OBJECT-TYPE
			SYNTAX TimeTicks
			MAX-ACCESS read-only
			STATUS current
			DESCRIPTION
				"Last Change Time"
			::= { uniExtAttributeEntry 5 }

		
		-- 1.3.6.1.4.1.17409.2.3.5.7.1.6
		uniIsolationEnable OBJECT-TYPE
			SYNTAX TruthValue
			MAX-ACCESS read-write
			STATUS current
			DESCRIPTION
				"true(1) false(2)"
			::= { uniExtAttributeEntry 6 }

		
		-- 1.3.6.1.4.1.17409.2.3.5.7.1.7
		uniExMacAddrLearnMaxNum OBJECT-TYPE
			SYNTAX INTEGER
			MAX-ACCESS read-write
			STATUS current
			DESCRIPTION
				"Mac Address Learn Max Num"
			::= { uniExtAttributeEntry 7 }

		
		-- 1.3.6.1.4.1.17409.2.3.5.7.1.8
		uniAutoNegotiationAdvertisedTechAbility OBJECT-TYPE
			SYNTAX INTEGER
			MAX-ACCESS read-write
			STATUS current
			DESCRIPTION
				"Refer to clause 30.6.1.1.6 of IEEE 802.3 2005 edition"
			::= { uniExtAttributeEntry 8 }

		
		-- 1.3.6.1.4.1.17409.2.3.5.7.1.9
		uniMacAddrClearByPort OBJECT-TYPE
			SYNTAX INTEGER { clearDynamic(1) }
			MAX-ACCESS read-write
			STATUS current
			DESCRIPTION
				"Clear MAC address by UNI port.
				clearDynamic(1) - Clear all dynamic MAC address learned on the UNI port"
			::= { uniExtAttributeEntry 9 }

		
		-- 1.3.6.1.4.1.17409.2.3.6
		igmpManagementObjects OBJECT IDENTIFIER ::= { eponTree 6 }

		
-- ------------------------------------------------------------------------------
-- igmpManagementObjects[IGMP](1.3.6.1.4.1.17409.2.3.6)
-- ------------------------------------------------------------------------------ 
		-- 1.3.6.1.4.1.17409.2.3.6.1
		igmpEntityTable OBJECT-TYPE
			SYNTAX SEQUENCE OF IgmpEntityEntry
			MAX-ACCESS not-accessible
			STATUS current
			DESCRIPTION
				"
				IGMP"
			::= { igmpManagementObjects 1 }

		
		-- 1.3.6.1.4.1.17409.2.3.6.1.1
		igmpEntityEntry OBJECT-TYPE
			SYNTAX IgmpEntityEntry
			MAX-ACCESS not-accessible
			STATUS current
			DESCRIPTION
				" "
			INDEX { igmpDeviceIndex }
			::= { igmpEntityTable 1 }

		
		IgmpEntityEntry ::=
			SEQUENCE { 
				igmpDeviceIndex
					INTEGER,
				igmpMode
					INTEGER,
				maxQueryResponseTime
					INTEGER,
				robustVariable
					INTEGER,
				queryInterval
					INTEGER,
				lastMemberQueryInterval
					INTEGER,
				lastMemberQueryCount
					INTEGER,
				igmpVersion
					INTEGER
			 }

		-- 1.3.6.1.4.1.17409.2.3.6.1.1.1
		igmpDeviceIndex OBJECT-TYPE
			SYNTAX INTEGER (1..2147483647)
			MAX-ACCESS not-accessible
			STATUS current
			DESCRIPTION
				"
				        
				For OLT, set to corresponding device        
				For ONU, set to 0"
			::= { igmpEntityEntry 1 }

		
		-- 1.3.6.1.4.1.17409.2.3.6.1.1.2
		igmpMode OBJECT-TYPE
			SYNTAX INTEGER
				{
				proxy(1),
				ctc(2),
				disabled(3),
				snooping(4)
				}
			MAX-ACCESS read-write
			STATUS current
			DESCRIPTION
				"
				IGMP
				centralized(1)      - All the multicast control is done by OLT
				distributedwithcm(2)    - Both OLT and ONU perform IGMP proxy and  
				              controlled multicast will be enabled. At 
				              this case, if igmp joins shall follow the 
				              definition in multicastPackageList, for the
				              port  
				disabled(3)       - Disable IGMP proxy on OLT and ONU
				distributedwocm(4)    - Both OLT and ONU perform IGMP proxy and  
				              controlled multicast will be disabled. At 
				              this case, if igmp joins shall be accept even
				              violate the definition in multicastPackageList, 
				              for the port.  
				"
			DEFVAL { disabled }
			::= { igmpEntityEntry 2 }

		
		-- 1.3.6.1.4.1.17409.2.3.6.1.1.3
		maxQueryResponseTime OBJECT-TYPE
			SYNTAX INTEGER
			UNITS "tenth second"
			MAX-ACCESS read-write
			STATUS current
			DESCRIPTION
				"
				
				1/10
				This is used for sending general query"
			::= { igmpEntityEntry 3 }

		
		-- 1.3.6.1.4.1.17409.2.3.6.1.1.4
		robustVariable OBJECT-TYPE
			SYNTAX INTEGER
			MAX-ACCESS read-write
			STATUS current
			DESCRIPTION
				"
				
				This is used for sending general query
				No less than 1"
			::= { igmpEntityEntry 4 }

		
		-- 1.3.6.1.4.1.17409.2.3.6.1.1.5
		queryInterval OBJECT-TYPE
			SYNTAX INTEGER
			UNITS "seconds"
			MAX-ACCESS read-write
			STATUS current
			DESCRIPTION
				"
				
				
				This is used for sending general query
				"
			::= { igmpEntityEntry 5 }

		
		-- 1.3.6.1.4.1.17409.2.3.6.1.1.6
		lastMemberQueryInterval OBJECT-TYPE
			SYNTAX INTEGER
			UNITS "tenth second"
			MAX-ACCESS read-write
			STATUS current
			DESCRIPTION
				"
				Max Response Time inserted into Group-Specific Queries sent in response 
				to Leave Group messages, and is also the amount of time between 
				Group-Specific Query messages
				"
			::= { igmpEntityEntry 6 }

		
		-- 1.3.6.1.4.1.17409.2.3.6.1.1.7
		lastMemberQueryCount OBJECT-TYPE
			SYNTAX INTEGER
			MAX-ACCESS read-write
			STATUS current
			DESCRIPTION
				"
				Number of Group-Specific Queries sent before the router assumes there 
				are no local members
				"
			::= { igmpEntityEntry 7 }

		
		-- 1.3.6.1.4.1.17409.2.3.6.1.1.8
		igmpVersion OBJECT-TYPE
			SYNTAX INTEGER
				{
				v1(1),
				v2(2),
				v3(3)
				}
			MAX-ACCESS read-write
			STATUS current
			DESCRIPTION
				"
				IGMP"
			DEFVAL { v2 }
			::= { igmpEntityEntry 8 }

		
		-- 1.3.6.1.4.1.17409.2.3.6.2
		igmpProxyParaTable OBJECT-TYPE
			SYNTAX SEQUENCE OF IgmpProxyParaEntry
			MAX-ACCESS not-accessible
			STATUS current
			DESCRIPTION
				"
				IGMP proxy - "
			::= { igmpManagementObjects 2 }

		
		-- 1.3.6.1.4.1.17409.2.3.6.2.1
		igmpProxyParaEntry OBJECT-TYPE
			SYNTAX IgmpProxyParaEntry
			MAX-ACCESS not-accessible
			STATUS current
			DESCRIPTION
				" "
			INDEX { proxyIndex }
			::= { igmpProxyParaTable 1 }

		
		IgmpProxyParaEntry ::=
			SEQUENCE { 
				proxyIndex
					INTEGER,
				proxyName
					OCTET STRING,
				proxySrcIPAddress
					IpAddress,
				proxyMulticastVID
					INTEGER,
				proxyMulticastIPAddress
					IpAddress,
				multicastAssuredBW
					Unsigned32,
				multicastMaxBW
					Unsigned32,
				proxyRowStatus
					RowStatus
			 }

		-- 1.3.6.1.4.1.17409.2.3.6.2.1.1
		proxyIndex OBJECT-TYPE
			SYNTAX INTEGER (1..2000)
			MAX-ACCESS not-accessible
			STATUS current
			DESCRIPTION
				"
				IGMP Proxy - "
			::= { igmpProxyParaEntry 1 }

		
		-- 1.3.6.1.4.1.17409.2.3.6.2.1.2
		proxyName OBJECT-TYPE
			SYNTAX OCTET STRING (SIZE (0..256))
			MAX-ACCESS read-create
			STATUS current
			DESCRIPTION
				"
				IGMP Proxy"
			::= { igmpProxyParaEntry 2 }

		
		-- 1.3.6.1.4.1.17409.2.3.6.2.1.3
		proxySrcIPAddress OBJECT-TYPE
			SYNTAX IpAddress
			MAX-ACCESS read-create
			STATUS current
			DESCRIPTION
				"
				proxyIP"
			::= { igmpProxyParaEntry 3 }

		
		-- 1.3.6.1.4.1.17409.2.3.6.2.1.4
		proxyMulticastVID OBJECT-TYPE
			SYNTAX INTEGER
			MAX-ACCESS read-create
			STATUS current
			DESCRIPTION
				"
				IGMP ProxyVID
				VID"
			::= { igmpProxyParaEntry 4 }

		
		-- 1.3.6.1.4.1.17409.2.3.6.2.1.5
		proxyMulticastIPAddress OBJECT-TYPE
			SYNTAX IpAddress
			MAX-ACCESS read-create
			STATUS current
			DESCRIPTION
				"
				IP"
			::= { igmpProxyParaEntry 5 }

		
		-- 1.3.6.1.4.1.17409.2.3.6.2.1.6
		multicastAssuredBW OBJECT-TYPE
			SYNTAX Unsigned32
			UNITS "kbps"
			MAX-ACCESS read-create
			STATUS current
			DESCRIPTION
				"
				        
				kbps"
			::= { igmpProxyParaEntry 6 }

		
		-- 1.3.6.1.4.1.17409.2.3.6.2.1.7
		multicastMaxBW OBJECT-TYPE
			SYNTAX Unsigned32
			UNITS "kbps"
			MAX-ACCESS read-create
			STATUS current
			DESCRIPTION
				"
				        
				kbps"
			::= { igmpProxyParaEntry 7 }

		
		-- 1.3.6.1.4.1.17409.2.3.6.2.1.8
		proxyRowStatus OBJECT-TYPE
			SYNTAX RowStatus
			MAX-ACCESS read-create
			STATUS current
			DESCRIPTION
				"
				"
			::= { igmpProxyParaEntry 8 }

		
		-- 1.3.6.1.4.1.17409.2.3.6.3
		igmpForwardingTable OBJECT-TYPE
			SYNTAX SEQUENCE OF IgmpForwardingEntry
			MAX-ACCESS not-accessible
			STATUS current
			DESCRIPTION
				"
				Multicast forwarding table        
				"
			::= { igmpManagementObjects 3 }

		
		-- 1.3.6.1.4.1.17409.2.3.6.3.1
		igmpForwardingEntry OBJECT-TYPE
			SYNTAX IgmpForwardingEntry
			MAX-ACCESS not-accessible
			STATUS current
			DESCRIPTION
				" "
			INDEX { groupDeviceIndex, groupVlanIndex, groupIPAddress }
			::= { igmpForwardingTable 1 }

		
		IgmpForwardingEntry ::=
			SEQUENCE { 
				groupDeviceIndex
					INTEGER,
				groupVlanIndex
					INTEGER,
				groupIPAddress
					IpAddress,
				groupPortList
					OCTET STRING
			 }

		-- 1.3.6.1.4.1.17409.2.3.6.3.1.1
		groupDeviceIndex OBJECT-TYPE
			SYNTAX INTEGER (1..2147483647)
			MAX-ACCESS not-accessible
			STATUS current
			DESCRIPTION
				"
				        
				For OLT, set to corresponding OLT device
				For ONU, set to 0
				"
			::= { igmpForwardingEntry 1 }

		
		-- 1.3.6.1.4.1.17409.2.3.6.3.1.2
		groupVlanIndex OBJECT-TYPE
			SYNTAX INTEGER (1..2147483647)
			MAX-ACCESS not-accessible
			STATUS current
			DESCRIPTION
				"
				Vlan"
			::= { igmpForwardingEntry 2 }

		
		-- 1.3.6.1.4.1.17409.2.3.6.3.1.3
		groupIPAddress OBJECT-TYPE
			SYNTAX IpAddress
			MAX-ACCESS not-accessible
			STATUS current
			DESCRIPTION
				"
				IP"
			::= { igmpForwardingEntry 3 }

		
		-- 1.3.6.1.4.1.17409.2.3.6.3.1.4
		groupPortList OBJECT-TYPE
			SYNTAX OCTET STRING
			MAX-ACCESS read-only
			STATUS current
			DESCRIPTION
				"
				Forwarding port list
				1. OLT
				-------------------------------------------------------------------
				It is presented by member port list. Each member port is identified
				by 4-byte format, same as TC of EponDeviceIndex. The actual length of
				this string depends of the number of member ports in the port list.
				The relationship is:
				Length of the string = 4 * (NUM of member ports)  
				For example, if device 1, port 1/2 and 2/3 is the member ports, 
				then this object will be presented as:
				01 01 02 00 01 02 03 00
				
				2. ONU
				-------------------------------------------------------------------
				It is presented by member port list. Each member port is identified
				by 2-byte format, One for slot ID, the last for port ID. The actual 
				length of this string depends of the number of member ports. If the 
				ONU is fixed (not modulized), set slot ID to 0, the NMS could ignore 
				the slot info.
				Note that, slot here shall follow the last byte definition of 
				EponCardIndex to indicate the main-slot and sub-slot index.  
				The relationship is:
				Length of the string = 2 * (NUM of member ports)  
				For example, if port 1/2 and 3/4 is the member ports of the group, 
				then the object is presented as:
				01 02 03 04       
				"
			::= { igmpForwardingEntry 4 }

		
		-- 1.3.6.1.4.1.17409.2.3.6.4
		controllededMulticastTable OBJECT-IDENTITY
			STATUS current
			DESCRIPTION 
				"
				"
			::= { igmpManagementObjects 4 }

		
		-- 1.3.6.1.4.1.17409.2.3.6.4.1
		controlledMulticastUserAuthorityTable OBJECT-TYPE
			SYNTAX SEQUENCE OF ControlledMulticastUserAuthorityEntry
			MAX-ACCESS not-accessible
			STATUS current
			DESCRIPTION
				"
				
				"
			::= { controllededMulticastTable 1 }

		
		-- 1.3.6.1.4.1.17409.2.3.6.4.1.1
		controlledMulticastUserAuthorityEntry OBJECT-TYPE
			SYNTAX ControlledMulticastUserAuthorityEntry
			MAX-ACCESS not-accessible
			STATUS current
			DESCRIPTION
				" "
			INDEX { cmDeviceIndex, cmCardIndex, cmPortIndex }
			::= { controlledMulticastUserAuthorityTable 1 }

		
		ControlledMulticastUserAuthorityEntry ::=
			SEQUENCE { 
				cmDeviceIndex
					EponDeviceIndex,
				cmCardIndex
					EponCardIndex,
				cmPortIndex
					EponPortIndex,
				multicastPackageList
					OCTET STRING,
				igmpGlobalBW
					Unsigned32,
				igmpGlobalBWUsed
					Unsigned32,
				cmUserAuthorityRowStatus
					RowStatus
			 }

		-- 1.3.6.1.4.1.17409.2.3.6.4.1.1.1
		cmDeviceIndex OBJECT-TYPE
			SYNTAX EponDeviceIndex (1..2147483647)
			MAX-ACCESS not-accessible
			STATUS current
			DESCRIPTION
				"
				        
				For OLT, set to corresponding device/slot/port/ONU
				For ONU, set to 0"
			::= { controlledMulticastUserAuthorityEntry 1 }

		
		-- 1.3.6.1.4.1.17409.2.3.6.4.1.1.2
		cmCardIndex OBJECT-TYPE
			SYNTAX EponCardIndex (1..2147483647)
			MAX-ACCESS not-accessible
			STATUS current
			DESCRIPTION
				"
				        
				Set to corresponding UNI slot
				"
			::= { controlledMulticastUserAuthorityEntry 2 }

		
		-- 1.3.6.1.4.1.17409.2.3.6.4.1.1.3
		cmPortIndex OBJECT-TYPE
			SYNTAX EponPortIndex (1..2147483647)
			MAX-ACCESS not-accessible
			STATUS current
			DESCRIPTION
				"
				Port ID        
				Set to corresponding UNI port
				"
			::= { controlledMulticastUserAuthorityEntry 3 }

		
		-- 1.3.6.1.4.1.17409.2.3.6.4.1.1.4
		multicastPackageList OBJECT-TYPE
			SYNTAX OCTET STRING (SIZE (0..250))
			MAX-ACCESS read-create
			STATUS current
			DESCRIPTION
				"
				.        
				cmProxyListbitcmIndex"
			::= { controlledMulticastUserAuthorityEntry 4 }

		
		-- 1.3.6.1.4.1.17409.2.3.6.4.1.1.5
		igmpGlobalBW OBJECT-TYPE
			SYNTAX Unsigned32
			UNITS "kbps"
			MAX-ACCESS read-create
			STATUS current
			DESCRIPTION
				"
				IGMP - 
				kbps"
			::= { controlledMulticastUserAuthorityEntry 5 }

		
		-- 1.3.6.1.4.1.17409.2.3.6.4.1.1.6
		igmpGlobalBWUsed OBJECT-TYPE
			SYNTAX Unsigned32
			UNITS "kbps"
			MAX-ACCESS read-only
			STATUS current
			DESCRIPTION
				"
				IGMP -         
				kbps"
			::= { controlledMulticastUserAuthorityEntry 6 }

		
		-- 1.3.6.1.4.1.17409.2.3.6.4.1.1.7
		cmUserAuthorityRowStatus OBJECT-TYPE
			SYNTAX RowStatus
			MAX-ACCESS read-create
			STATUS current
			DESCRIPTION			" "
			::= { controlledMulticastUserAuthorityEntry 7 }

		
		-- 1.3.6.1.4.1.17409.2.3.6.4.2
		controlledMulticastPackageTable OBJECT-TYPE
			SYNTAX SEQUENCE OF ControlledMulticastPackageEntry
			MAX-ACCESS not-accessible
			STATUS current
			DESCRIPTION
				"
				"
			::= { controllededMulticastTable 2 }

		
		-- 1.3.6.1.4.1.17409.2.3.6.4.2.1
		controlledMulticastPackageEntry OBJECT-TYPE
			SYNTAX ControlledMulticastPackageEntry
			MAX-ACCESS not-accessible
			STATUS current
			DESCRIPTION
				" "
			INDEX { cmIndex }
			::= { controlledMulticastPackageTable 1 }

		
		ControlledMulticastPackageEntry ::=
			SEQUENCE { 
				cmIndex
					INTEGER,
				cmName
					OCTET STRING,
				cmProxyList
					OCTET STRING,
				multicastUserAuthority
					INTEGER,
				maxRequestChannelNum
					INTEGER,
				singlePreviewTime
					INTEGER,
				totalPreviewTime
					INTEGER,
				previewResetTime
					INTEGER,
				previewCount
					INTEGER,
				cmRowStatus
					RowStatus
			 }

		-- 1.3.6.1.4.1.17409.2.3.6.4.2.1.1
		cmIndex OBJECT-TYPE
			SYNTAX INTEGER (1..2000)
			MAX-ACCESS not-accessible
			STATUS current
			DESCRIPTION
				"
				"
			::= { controlledMulticastPackageEntry 1 }

		
		-- 1.3.6.1.4.1.17409.2.3.6.4.2.1.2
		cmName OBJECT-TYPE
			SYNTAX OCTET STRING (SIZE (0..256))
			MAX-ACCESS read-create
			STATUS current
			DESCRIPTION
				"
				"
			::= { controlledMulticastPackageEntry 2 }

		
		-- 1.3.6.1.4.1.17409.2.3.6.4.2.1.3
		cmProxyList OBJECT-TYPE
			SYNTAX OCTET STRING (SIZE (0..250))
			MAX-ACCESS read-create
			STATUS current
			DESCRIPTION
				"
				Proxy
				INTERNETOCTETOCTET 0, OCTET 1, ...
				OCTETbitbit0bit1...bit7
				bitOCTETbitigmpProxyParaTable
				proxyIndexbitproxyIndex        
				80proxyIndex1..8010
				proxyPON1,15,38cmProxyList
				0x80 02 00 00 04 00 00 00 00 00"
			::= { controlledMulticastPackageEntry 3 }

		
		-- 1.3.6.1.4.1.17409.2.3.6.4.2.1.4
		multicastUserAuthority OBJECT-TYPE
			SYNTAX INTEGER
				{
				permit(1),
				preview(2),
				deny(3)
				}
			MAX-ACCESS read-create
			STATUS current
			DESCRIPTION
				"
				permitpreviewdeny"
			::= { controlledMulticastPackageEntry 4 }

		
		-- 1.3.6.1.4.1.17409.2.3.6.4.2.1.5
		maxRequestChannelNum OBJECT-TYPE
			SYNTAX INTEGER
			MAX-ACCESS read-create
			STATUS current
			DESCRIPTION
				"
				"
			::= { controlledMulticastPackageEntry 5 }

		
		-- 1.3.6.1.4.1.17409.2.3.6.4.2.1.6
		singlePreviewTime OBJECT-TYPE
			SYNTAX INTEGER
			UNITS "seconds"
			MAX-ACCESS read-create
			STATUS current
			DESCRIPTION
				"
				"
			::= { controlledMulticastPackageEntry 6 }

		
		-- 1.3.6.1.4.1.17409.2.3.6.4.2.1.7
		totalPreviewTime OBJECT-TYPE
			SYNTAX INTEGER
			UNITS "seconds"
			MAX-ACCESS read-create
			STATUS current
			DESCRIPTION
				"
				"
			::= { controlledMulticastPackageEntry 7 }

		
		-- 1.3.6.1.4.1.17409.2.3.6.4.2.1.8
		previewResetTime OBJECT-TYPE
			SYNTAX INTEGER
			UNITS "seconds"
			MAX-ACCESS read-create
			STATUS current
			DESCRIPTION
				"
				"
			::= { controlledMulticastPackageEntry 8 }

		
		-- 1.3.6.1.4.1.17409.2.3.6.4.2.1.9
		previewCount OBJECT-TYPE
			SYNTAX INTEGER
			MAX-ACCESS read-create
			STATUS current
			DESCRIPTION
				"
				"
			::= { controlledMulticastPackageEntry 9 }

		
		-- 1.3.6.1.4.1.17409.2.3.6.4.2.1.10
		cmRowStatus OBJECT-TYPE
			SYNTAX RowStatus
			MAX-ACCESS read-create
			STATUS current
			DESCRIPTION
				"
				"
			::= { controlledMulticastPackageEntry 10 }

		
		-- 1.3.6.1.4.1.17409.2.3.6.5
		igmpOnuUniTable OBJECT-TYPE
			SYNTAX SEQUENCE OF igmpOnuUniEntry
			MAX-ACCESS not-accessible
			STATUS current
			DESCRIPTION
				"A list of igmpOnuUniTable  entries. "
			::= { igmpManagementObjects 5 }

		
		-- 1.3.6.1.4.1.17409.2.3.6.5.1
		igmpOnuUniEntry OBJECT-TYPE
			SYNTAX igmpOnuUniEntry
			MAX-ACCESS not-accessible
			STATUS current
			DESCRIPTION
				"The igmpOnuUniEntry Information"
			INDEX { uniMvlanDeviceIndex, uniMvlanCardIndex, uniMvlanPortIndex }
			::= { igmpOnuUniTable 1 }

		
		igmpOnuUniEntry ::=
			SEQUENCE { 
				uniMvlanDeviceIndex
					EponDeviceIndex,
				uniMvlanCardIndex
					EponCardIndex,
				uniMvlanPortIndex
					EponPortIndex,
				uniMvlanVid
					OCTET STRING,
				uniMaxMultiNum
					INTEGER,
				uniMvlanTag
					INTEGER,
				uniMvlanRowstatus
					INTEGER
			 }

		-- 1.3.6.1.4.1.17409.2.3.6.5.1.1
		uniMvlanDeviceIndex OBJECT-TYPE
			SYNTAX EponDeviceIndex (1..2147483647)
			MAX-ACCESS not-accessible
			STATUS current
			DESCRIPTION
				" "
			::= { igmpOnuUniEntry 1 }

		
		-- 1.3.6.1.4.1.17409.2.3.6.5.1.2
		uniMvlanCardIndex OBJECT-TYPE
			SYNTAX EponCardIndex (0..2147483647)
			MAX-ACCESS not-accessible
			STATUS current
			DESCRIPTION
				""
			::= { igmpOnuUniEntry 2 }

		
		-- 1.3.6.1.4.1.17409.2.3.6.5.1.3
		uniMvlanPortIndex OBJECT-TYPE
			SYNTAX EponPortIndex
			MAX-ACCESS read-create
			STATUS current
			DESCRIPTION
				""
			::= { igmpOnuUniEntry 3 }

		
		-- 1.3.6.1.4.1.17409.2.3.6.5.1.4
		uniMvlanVid OBJECT-TYPE
			SYNTAX OCTET STRING (SIZE (16))
			MAX-ACCESS read-create
			STATUS current
			DESCRIPTION
				"(unimvlan(1..4084))VLAN IDUNI8VLAN"
			::= { igmpOnuUniEntry 4 }

		
		-- 1.3.6.1.4.1.17409.2.3.6.5.1.5
		uniMaxMultiNum OBJECT-TYPE
			SYNTAX INTEGER
			MAX-ACCESS read-create
			STATUS current
			DESCRIPTION
				""
			::= { igmpOnuUniEntry 5 }

		
		-- 1.3.6.1.4.1.17409.2.3.6.5.1.6
		uniMvlanTag OBJECT-TYPE
			SYNTAX INTEGER{Strip(0),NoStrip(1)}
			MAX-ACCESS read-create
			STATUS current
			DESCRIPTION
				",0 1"
			::= { igmpOnuUniEntry 6 }

		
		-- 1.3.6.1.4.1.17409.2.3.6.5.1.7
		uniMvlanRowstatus OBJECT-TYPE
			SYNTAX INTEGER {active(1), notInService(2), notReady(3), createAndGo(4), createAndWait(5), destroy(6) }
			MAX-ACCESS read-create
			STATUS current
			DESCRIPTION
				""
			::= { igmpOnuUniEntry 7 }
        -- 1.3.6.1.4.1.17409.2.3.6.6
		igmpOltMulticastVlanTable  OBJECT-TYPE
          SYNTAX SEQUENCE OF IgmpOltMulticastVlanEntry
          MAX-ACCESS not-accessible
          STATUS current
          DESCRIPTION
           "
           OLT "
          ::= { igmpManagementObjects 6 }
    
        -- 1.3.6.1.4.1.17409.2.3.6.6.1
        igmpOltMulticastVlanEntry OBJECT-TYPE
           SYNTAX IgmpOltMulticastVlanEntry
           MAX-ACCESS not-accessible
           STATUS current
           DESCRIPTION
           " "
           INDEX { igmpOltMulticastVlanDeviceIndex, multicastVlanId  }
           ::= { igmpOltMulticastVlanTable 1 }
    
        IgmpOltMulticastVlanEntry ::=
         SEQUENCE { 
        igmpOltMulticastVlanDeviceIndex
          INTEGER,
        multicastVlanId
          INTEGER,
        mVlanMaxQueryResponseTime
          INTEGER,
        mVlanRobustVariable
          INTEGER,
        mVlanQueryInterval
          INTEGER,
        mVlanLastMemberQueryInterval
          INTEGER,
        mVlanLastMemberQueryCount
          INTEGER,
        mvlanRowstatus  
          INTEGER
         }
        -- 1.3.6.1.4.1.17409.2.3.6.6.1.1
        igmpOltMulticastVlanDeviceIndex OBJECT-TYPE
             SYNTAX INTEGER
            MAX-ACCESS not-accessible
            STATUS current
         DESCRIPTION
          "        
          OLT device index"
         ::= { igmpOltMulticastVlanEntry 1 }
        -- 1.3.6.1.4.1.17409.2.3.6.6.1.2
        multicastVlanId OBJECT-TYPE
          SYNTAX INTEGER
          MAX-ACCESS read-write
          STATUS current
          DESCRIPTION
          "
          OLT \u7f02\u509a\u5037\u7ec0\u4f7a\ufffd\u9853\u3220\u7bb0\u95bb\u2543\u5d56AN ID
          "
          ::= { igmpOltMulticastVlanEntry 2 }
        -- 1.3.6.1.4.1.17409.2.3.6.6.1.3
        mVlanMaxQueryResponseTime OBJECT-TYPE
           SYNTAX INTEGER
           UNITS "tenth second"
           MAX-ACCESS read-write
           STATUS optional
          DESCRIPTION
          "
        
           This is used for sending general query"
          ::= { igmpOltMulticastVlanEntry 3 }
        -- 1.3.6.1.4.1.17409.2.3.6.6.1.4
        mVlanRobustVariable OBJECT-TYPE
           SYNTAX INTEGER
           MAX-ACCESS read-write
           STATUS optional
           DESCRIPTION
          "
           This is used for sending general query
          No less than 1"
          ::= { igmpOltMulticastVlanEntry 4 }

        -- 1.3.6.1.4.1.17409.2.3.6.6.1.5
        mVlanQueryInterval OBJECT-TYPE
          SYNTAX INTEGER
          UNITS "seconds"
          MAX-ACCESS read-write
          STATUS optional
          DESCRIPTION
         "\u599e\u308e\u5053\u93b7\ufffd          This is used for sending general query
          "
         ::= { igmpOltMulticastVlanEntry 5 }
        -- 1.3.6.1.4.1.17409.2.3.6.6.1.6
        mVlanLastMemberQueryInterval OBJECT-TYPE
          SYNTAX INTEGER
          UNITS "tenth second"
          MAX-ACCESS read-write
          STATUS optional
          DESCRIPTION
          "
          Max Response Time inserted into Group-Specific Queries sent in response 
           to Leave Group messages, and is also the amount of time between 
           Group-Specific Query messages
          "
          ::= { igmpOltMulticastVlanEntry 6 }
        -- 1.3.6.1.4.1.17409.2.3.6.6.1.7
        mVlanLastMemberQueryCount OBJECT-TYPE
          SYNTAX INTEGER
          MAX-ACCESS read-create
          STATUS optional
          DESCRIPTION
          "
          Number of Group-Specific Queries sent before the router assumes there 
          are no local members
          "               
         ::= { igmpOltMulticastVlanEntry 7 }
    
        -- 1.3.6.1.4.1.17409.2.3.6.6.1.8
        mvlanRowstatus  OBJECT-TYPE
        SYNTAX      INTEGER{active(1), notInService(2), notReady(3), createAndGo(4), createAndWait(5), destroy(6) }
        MAX-ACCESS  read-create
        STATUS      current
        DESCRIPTION
       ""
        ::= { igmpOltMulticastVlanEntry  8 }

	--1.3.6.1.4.1.17409.2.3.6.7
    igmpSniMulticastVlanTable   OBJECT-TYPE
       SYNTAX      SEQUENCE OF IgmpSniMulticastVlanEntry
       MAX-ACCESS  not-accessible
       STATUS      current
       DESCRIPTION
       "SNI"
      ::= { igmpManagementObjects 7 }
    --1.3.6.1.4.1.17409.2.3.6.7.1
    igmpSniMulticastVlanEntry OBJECT-TYPE
         SYNTAX      IgmpSniMulticastVlanEntry
          MAX-ACCESS  not-accessible
         STATUS      current
         DESCRIPTION  
         "The igmpSniMulticastVlanEntry Information"
         INDEX   { sniMultiVlanVid,sniMultiVlanDeviceIndex }   
         ::={ igmpSniMulticastVlanTable   1 }   

       IgmpSniMulticastVlanEntry ::= SEQUENCE {
       sniMultiVlanVid
         INTEGER,
       sniMultiVlanDeviceIndex
          EponDeviceIndex,
       sniMultiVlanRowstatus
          INTEGER
         }
        --1.3.6.1.4.1.17409.2.3.6.7.1.1
        sniMultiVlanVid  OBJECT-TYPE
          SYNTAX    INTEGER
          MAX-ACCESS  read-create
          STATUS      current
          DESCRIPTION
          " "
          ::= { igmpSniMulticastVlanEntry 1 }
        --1.3.6.1.4.1.17409.2.3.6.7.1.2
       sniMultiVlanDeviceIndex  OBJECT-TYPE
          SYNTAX      EponDeviceIndex
          MAX-ACCESS  not-accessible
          STATUS      current
          DESCRIPTION
          "SNI\u95c1\u8364\u59f3\u9412\ufe42\u5d15\u93b6\u527f\u56ec\ue517\u934c\u6db1\u703c\u95c1\u975b\u7e52\u6fee\u98ce\u7c9a\u9367\u6941\u7165\u6fde\u621e\ue7c7\u93c6\ue54bvice/slot/sni port "
          ::= { igmpSniMulticastVlanEntry 2 }   
        --1.3.6.1.4.1.17409.2.3.6.7.1.3
        sniMultiVlanRowstatus OBJECT-TYPE
          SYNTAX      INTEGER
          MAX-ACCESS  read-create
          STATUS      current
          DESCRIPTION
          " "
          ::= { igmpSniMulticastVlanEntry 3 }


    -- 1.3.6.1.4.1.17409.2.3.6.8
    onuIgmpModeTable   OBJECT-TYPE
           SYNTAX      SEQUENCE OF OnuIgmpModeEntry 
           MAX-ACCESS  not-accessible
           STATUS      current
           DESCRIPTION
           "ONU"
           ::= { igmpManagementObjects 8 }
        -- 1.3.6.1.4.1.17409.2.3.6.8.1
        onuIgmpModeEntry  OBJECT-TYPE
           SYNTAX      OnuIgmpModeEntry 
           MAX-ACCESS  not-accessible
           STATUS      current
           DESCRIPTION  
           "The onuIgmpModeEntry Information"
          INDEX   { onuIgmpModeDeviceIndex }   
          ::={ onuIgmpModeTable  1 }   
       
         OnuIgmpModeEntry ::= SEQUENCE {
          onuIgmpModeDeviceIndex 
           EponDeviceIndex,
          onuIgmpMode
           INTEGER
          }
        -- 1.3.6.1.4.1.17409.2.3.6.8.1.1
        onuIgmpModeDeviceIndex  OBJECT-TYPE
            SYNTAX      EponDeviceIndex
            MAX-ACCESS  not-accessible
            STATUS      current
            DESCRIPTION
            "ONU ID "
            ::= { onuIgmpModeEntry 1 }   
        -- 1.3.6.1.4.1.17409.2.3.6.8.1.2
        onuIgmpMode  OBJECT-TYPE
          SYNTAX    INTEGER{
           transparent(1),
           igmp-snooping(2),
           ctc(3)
           }
          MAX-ACCESS  read-write
          STATUS      current
          DESCRIPTION
          " "
         ::= { onuIgmpModeEntry 2 }
		
		
		
		-- 1.3.6.1.4.1.17409.2.3.7
		vlanManagementObjects OBJECT IDENTIFIER ::= { eponTree 7 }

		
-- ------------------------------------------------------------------------------
-- vlanManagementObjects [VLAN](1.3.6.1.4.1.17409.2.3.7)
-- ------------------------------------------------------------------------------    
		-- 1.3.6.1.4.1.17409.2.3.7.1
		vlanGlobalInfoTable OBJECT-TYPE
			SYNTAX SEQUENCE OF VlanGlobalInfoEntry
			MAX-ACCESS not-accessible
			STATUS current
			DESCRIPTION
				"
				VLAN"
			::= { vlanManagementObjects 1 }

		
		-- 1.3.6.1.4.1.17409.2.3.7.1.1
		vlanGlobalInfoEntry OBJECT-TYPE
			SYNTAX VlanGlobalInfoEntry
			MAX-ACCESS not-accessible
			STATUS current
			DESCRIPTION
				" "
			INDEX { vlanDeviceIndex }
			::= { vlanGlobalInfoTable 1 }

		
		VlanGlobalInfoEntry ::=
			SEQUENCE { 
				vlanDeviceIndex
					INTEGER,
				maxVlanId
					INTEGER,
				maxSupportVlans
					INTEGER,
				createdVlanNumber
					INTEGER
			 }

		-- 1.3.6.1.4.1.17409.2.3.7.1.1.1
		vlanDeviceIndex OBJECT-TYPE
			SYNTAX INTEGER (1..2147483647)
			MAX-ACCESS not-accessible
			STATUS current
			DESCRIPTION
				"
				        
				For OLT, set to corresponding device ID
				For ONU, set to 0"
			::= { vlanGlobalInfoEntry 1 }

		
		-- 1.3.6.1.4.1.17409.2.3.7.1.1.2
		maxVlanId OBJECT-TYPE
			SYNTAX INTEGER
			MAX-ACCESS read-only
			STATUS current
			DESCRIPTION
				"
				VLAN ID"
			::= { vlanGlobalInfoEntry 2 }

		
		-- 1.3.6.1.4.1.17409.2.3.7.1.1.3
		maxSupportVlans OBJECT-TYPE
			SYNTAX INTEGER
			MAX-ACCESS read-only
			STATUS current
			DESCRIPTION
				"
				VLAN"
			::= { vlanGlobalInfoEntry 3 }

		
		-- 1.3.6.1.4.1.17409.2.3.7.1.1.4
		createdVlanNumber OBJECT-TYPE
			SYNTAX INTEGER
			MAX-ACCESS read-only
			STATUS current
			DESCRIPTION
				"
				VLAN"
			::= { vlanGlobalInfoEntry 4 }

		
		-- 1.3.6.1.4.1.17409.2.3.7.2
		vlanConfigGroup OBJECT-IDENTITY
			STATUS current
			DESCRIPTION 
				"
				Vlan"
			::= { vlanManagementObjects 2 }

		
		-- 1.3.6.1.4.1.17409.2.3.7.2.1
		oltVlanConfigTable OBJECT-TYPE
			SYNTAX SEQUENCE OF OltVlanConfigEntry
			MAX-ACCESS not-accessible
			STATUS current
			DESCRIPTION
				"
				OLT VLAN"
			::= { vlanConfigGroup 1 }

		
		-- 1.3.6.1.4.1.17409.2.3.7.2.1.1
		oltVlanConfigEntry OBJECT-TYPE
			SYNTAX OltVlanConfigEntry
			MAX-ACCESS not-accessible
			STATUS current
			DESCRIPTION
				" "
			INDEX { oltVlanIndex, oltVlanDeviceIndex }
			::= { oltVlanConfigTable 1 }

		
		OltVlanConfigEntry ::=
			SEQUENCE { 
				oltVlanIndex
					INTEGER,
				oltVlanDeviceIndex
					INTEGER,
				oltVlanName
					OCTET STRING,
				taggedPort
					OCTET STRING,
				untaggedPort
					OCTET STRING,
				oltVlanRowStatus
					RowStatus
			 }

		-- 1.3.6.1.4.1.17409.2.3.7.2.1.1.1
		oltVlanIndex OBJECT-TYPE
			SYNTAX INTEGER (1..2147483647)
			MAX-ACCESS not-accessible
			STATUS current
			DESCRIPTION
				"
				Vlan"
			::= { oltVlanConfigEntry 1 }

		
		-- 1.3.6.1.4.1.17409.2.3.7.2.1.1.2
		oltVlanDeviceIndex OBJECT-TYPE
			SYNTAX INTEGER (1..2147483647)
			MAX-ACCESS not-accessible
			STATUS current
			DESCRIPTION
				"
				OLT   
				"
			::= { oltVlanConfigEntry 2 }

		
		-- 1.3.6.1.4.1.17409.2.3.7.2.1.1.3
		oltVlanName OBJECT-TYPE
			SYNTAX OCTET STRING (SIZE (0..128))
			MAX-ACCESS read-create
			STATUS current
			DESCRIPTION
				"
				OLT VLAN name"
			::= { oltVlanConfigEntry 3 }

		
		-- 1.3.6.1.4.1.17409.2.3.7.2.1.1.4
		taggedPort OBJECT-TYPE
			SYNTAX OCTET STRING
			MAX-ACCESS read-create
			STATUS current
			DESCRIPTION
				"
				VlantagPON/SNI in OLT        
				It is presented by member port list. Each member port is identified
				by 4-byte format, same as TC of EponDeviceIndex. The actual length of
				this string depends of the number of member ports in the port list.
				The relationship is:
				Length of the string = 4 * (NUM of member ports)  
				For example, if device 1, port 1/2 and 2/3 is the member ports, 
				then this object will be presented as:
				01 01 02 00 01 02 03 00       
				"
			::= { oltVlanConfigEntry 4 }

		
		-- 1.3.6.1.4.1.17409.2.3.7.2.1.1.5
		untaggedPort OBJECT-TYPE
			SYNTAX OCTET STRING
			MAX-ACCESS read-create
			STATUS current
			DESCRIPTION
				"
				VlanUntagPON/SNI in OLT        
				It is presented by member port list. Each member port is identified
				by 4-byte format, same as TC of EponDeviceIndex. The actual length of
				this string depends of the number of member ports in the port list.
				The relationship is:
				Length of the string = 4 * (NUM of member ports)  
				For example, if device 1, port 1/2 and 2/3 is the member ports, 
				then this object will be presented as:
				01 01 02 00 01 02 03 00         
				"
			::= { oltVlanConfigEntry 5 }

		
		-- 1.3.6.1.4.1.17409.2.3.7.2.1.1.6
		oltVlanRowStatus OBJECT-TYPE
			SYNTAX RowStatus
			MAX-ACCESS read-create
			STATUS current
			DESCRIPTION
				"
				"
			::= { oltVlanConfigEntry 6 }

		
		-- 1.3.6.1.4.1.17409.2.3.7.2.2
		onuVlanConfigTable OBJECT-TYPE
			SYNTAX SEQUENCE OF OnuVlanConfigEntry
			MAX-ACCESS not-accessible
			STATUS current
			DESCRIPTION
				"
				ONU VLAN
				It is maintained by ONU itself.
				"
			::= { vlanConfigGroup 2 }

		
		-- 1.3.6.1.4.1.17409.2.3.7.2.2.1
		onuVlanConfigEntry OBJECT-TYPE
			SYNTAX OnuVlanConfigEntry
			MAX-ACCESS not-accessible
			STATUS current
			DESCRIPTION
				" "
			INDEX { onuVlanIndex, onuVlanDeviceIndex }
			::= { onuVlanConfigTable 1 }

		
		OnuVlanConfigEntry ::=
			SEQUENCE { 
				onuVlanIndex
					INTEGER,
				onuVlanDeviceIndex
					EponDeviceIndex,
				onuVlanName
					OCTET STRING,
				onuVlanTaggedPort
					OCTET STRING,
				onuVlanUntaggedPort
					OCTET STRING,
				onuVlanRowStatus
					RowStatus
			 }

		-- 1.3.6.1.4.1.17409.2.3.7.2.2.1.1
		onuVlanIndex OBJECT-TYPE
			SYNTAX INTEGER (1..2147483647)
			MAX-ACCESS not-accessible
			STATUS current
			DESCRIPTION
				"
				Vlan"
			::= { onuVlanConfigEntry 1 }

		
		-- 1.3.6.1.4.1.17409.2.3.7.2.2.1.2
		onuVlanDeviceIndex OBJECT-TYPE
			SYNTAX EponDeviceIndex (1..2147483647)
			MAX-ACCESS not-accessible
			STATUS current
			DESCRIPTION
				"
				ONU"
			::= { onuVlanConfigEntry 2 }

		
		-- 1.3.6.1.4.1.17409.2.3.7.2.2.1.3
		onuVlanName OBJECT-TYPE
			SYNTAX OCTET STRING (SIZE (0..128))
			MAX-ACCESS read-create
			STATUS current
			DESCRIPTION
				"
				ONU VLAN name"
			::= { onuVlanConfigEntry 3 }

		
		-- 1.3.6.1.4.1.17409.2.3.7.2.2.1.4
		onuVlanTaggedPort OBJECT-TYPE
			SYNTAX OCTET STRING
			MAX-ACCESS read-create
			STATUS current
			DESCRIPTION
				"
				VlantagUNI        
				It is presented by member port list. Each member port is identified
				by 2-byte format, One for slot ID, the last for port ID. The actual 
				length of this string depends of the number of tagged member ports 
				in the VLAN. If the ONU is fixed (not modulized), set slot ID to 0,
				the NMS could ignore the slot info.        
				Note that, slot here shall follow the last byte definition of 
				EponCardIndex to indicate the main-slot and sub-slot index.  
				The relationship is:
				Length of the string = 2 * (NUM of member ports)  
				For example, if port 1/2 and 3/4 is the tagged member ports of the
				VLAN, then the object is presented as:
				01 02 03 04
				"
			::= { onuVlanConfigEntry 4 }

		
		-- 1.3.6.1.4.1.17409.2.3.7.2.2.1.5
		onuVlanUntaggedPort OBJECT-TYPE
			SYNTAX OCTET STRING
			MAX-ACCESS read-create
			STATUS current
			DESCRIPTION
				"
				VlanUntagUNI        
				It is presented by member port list. Each member port is identified
				by 2-byte format, One for slot ID, the last for port ID. The actual 
				length of this string depends of the number of untagged member ports 
				in the VLAN. If the ONU is fixed (not modulized), set slot ID to FF,
				the NMS could ignore the slot info.  
				Note that, slot here shall follow the last byte definition of 
				EponCardIndex to indicate the main-slot and sub-slot index. 
				The relationship is:
				Length of the string = 2 * (NUM of member ports)  
				For example, if port 1/2 and 3/4 is the untagged member ports of the
				VLAN, then the object is presented as:
				01 02 03 04       
				"
			::= { onuVlanConfigEntry 5 }

		
		-- 1.3.6.1.4.1.17409.2.3.7.2.2.1.6
		onuVlanRowStatus OBJECT-TYPE
			SYNTAX RowStatus
			MAX-ACCESS read-create
			STATUS current
			DESCRIPTION
				"
				"
			::= { onuVlanConfigEntry 6 }

		
		-- 1.3.6.1.4.1.17409.2.3.7.3
		portVlanGroup OBJECT-IDENTITY
			STATUS current
			DESCRIPTION 
				"
				Vlansniuniponport"
			::= { vlanManagementObjects 3 }

		
		-- 1.3.6.1.4.1.17409.2.3.7.3.1
		onuPortortVlanTable OBJECT-TYPE
			SYNTAX SEQUENCE OF OnuPortVlanEntry
			MAX-ACCESS not-accessible
			STATUS current
			DESCRIPTION
				"
				Vlan        
				This table applies on OLT pon port, OLT SNI, OLT onu ID, ONU UNI.        
				1. If the table is maintained in OLT device:
				Applied Obj  - Descriptions of Index
				------------------------------------------------------------------
				OLT Pon Port - OnuNum of pvlanDeviceIndex shall be set to 0,
				/OLT SNI     pvlanCardIndex, and pvlanPortIndex set to 0 indicates
				         meaningless 
				OLT onu ID   - Set pvlanDeviceIndex to corresponding ONU ID,
				         pvlanCardIndex, and pvlanPortIndex set to 0 indicates
				         meaningless        
				ONU UNI    - Set pvlanDeviceIndex to corresponding ONU ID,
				         pvlanCardIndex, and pvlanPortIndex set to the corresponding 
				         value        
				2. If the table is maintained in ONU device:
				pvlanDeviceIndex shall be set to 0 to indicate meaningless.
				pvlanCardIndex shall be set to corresponding slot.
				pvlanPortIndex shall be set to corresponding port.        
				"
			::= { portVlanGroup 1 }

		
		-- 1.3.6.1.4.1.17409.2.3.7.3.1.1
		onuPortVlanEntry OBJECT-TYPE
			SYNTAX OnuPortVlanEntry
			MAX-ACCESS not-accessible
			STATUS current
			DESCRIPTION
				" "
			INDEX { pvlanDeviceIndex, pvlanCardIndex, pvlanPortIndex }
			::= { onuPortortVlanTable 1 }

		
		OnuPortVlanEntry ::=
			SEQUENCE { 
				pvlanDeviceIndex
					EponDeviceIndex,
				pvlanCardIndex
					EponCardIndex,
				pvlanPortIndex
					EponPortIndex,
				vlanTagTpid
					OCTET STRING,
				vlanTagCfi
					TruthValue,
				vlanTagPriority
					INTEGER,
				vlanPVid
					INTEGER,
				vlanMode
					INTEGER
			 }

		-- 1.3.6.1.4.1.17409.2.3.7.3.1.1.1
		pvlanDeviceIndex OBJECT-TYPE
			SYNTAX EponDeviceIndex (1..2147483647)
			MAX-ACCESS not-accessible
			STATUS current
			DESCRIPTION
				"
				OLT/ONU"
			::= { onuPortVlanEntry 1 }

		
		-- 1.3.6.1.4.1.17409.2.3.7.3.1.1.2
		pvlanCardIndex OBJECT-TYPE
			SYNTAX EponCardIndex (1..2147483647)
			MAX-ACCESS not-accessible
			STATUS current
			DESCRIPTION
				"
				
				"
			::= { onuPortVlanEntry 2 }

		
		-- 1.3.6.1.4.1.17409.2.3.7.3.1.1.3
		pvlanPortIndex OBJECT-TYPE
			SYNTAX EponPortIndex (1..2147483647)
			MAX-ACCESS not-accessible
			STATUS current
			DESCRIPTION
				"
				pon/uni/sni
				"
			::= { onuPortVlanEntry 3 }

		
		-- 1.3.6.1.4.1.17409.2.3.7.3.1.1.4
		vlanTagTpid OBJECT-TYPE
			SYNTAX OCTET STRING (SIZE (2))
			MAX-ACCESS read-write
			STATUS current
			DESCRIPTION
				"
				        
				It shall be presented in hexadecimal format. For example, 81 00
				to indicate 0x8100"
			::= { onuPortVlanEntry 4 }

		
		-- 1.3.6.1.4.1.17409.2.3.7.3.1.1.5
		vlanTagCfi OBJECT-TYPE
			SYNTAX TruthValue
			MAX-ACCESS read-write
			STATUS current
			DESCRIPTION
				"
				"
			::= { onuPortVlanEntry 5 }

		
		-- 1.3.6.1.4.1.17409.2.3.7.3.1.1.6
		vlanTagPriority OBJECT-TYPE
			SYNTAX INTEGER (0..7)
			MAX-ACCESS read-write
			STATUS current
			DESCRIPTION
				"
				vlan"
			::= { onuPortVlanEntry 6 }

		
		-- 1.3.6.1.4.1.17409.2.3.7.3.1.1.7
		vlanPVid OBJECT-TYPE
			SYNTAX INTEGER
			MAX-ACCESS read-write
			STATUS current
			DESCRIPTION
				"
				port Vlan ID"
			::= { onuPortVlanEntry 7 }

		
		-- 1.3.6.1.4.1.17409.2.3.7.3.1.1.8
		vlanMode OBJECT-TYPE
			SYNTAX INTEGER
				{
				transparent(0),
				tag(1),
				translation(2),
				aggregation(3),
				trunk(4),
				stacking(5)
				}
			MAX-ACCESS read-write
			STATUS current
			DESCRIPTION
				"
				vlan
				"
			::= { onuPortVlanEntry 8 }

		
		-- 1.3.6.1.4.1.17409.2.3.7.3.2
		portVlanTranslationTable OBJECT-TYPE
			SYNTAX SEQUENCE OF PortVlanTranslationEntry
			MAX-ACCESS not-accessible
			STATUS current
			DESCRIPTION
				"
				Vlan
				This table applies on OLT pon port, OLT SNI, OLT onu ID, ONU UNI.
				1. If the table is maintained in OLT device:
				Applied Obj  - Descriptions of Index
				------------------------------------------------------------------
				OLT Pon Port - OnuNum of pvtDeviceIndex shall be set to 0,
				/OLT SNI     pvtCardIndex, and pvtPortIndex set to 0 indicates
				         meaningless 
				OLT onu ID   - Set pvtDeviceIndex to corresponding ONU ID,
				         pvtCardIndex, and pvtPortIndex set to 0 indicates
				         meaningless        
				ONU UNI    - Set pvtDeviceIndex to corresponding ONU ID,
				         pvtCardIndex, and pvtPortIndex set to the corresponding 
				         value
				
				2. If the table is maintained in ONU device:
				pvtDeviceIndex shall be set to 0 to indicate meaningless.
				pvtCardIndex shall be set to corresponding slot.
				pvtPortIndex shall be set to corresponding port.        
				"
			::= { portVlanGroup 2 }

		
		-- 1.3.6.1.4.1.17409.2.3.7.3.2.1
		portVlanTranslationEntry OBJECT-TYPE
			SYNTAX PortVlanTranslationEntry
			MAX-ACCESS not-accessible
			STATUS current
			DESCRIPTION
				" "
			INDEX { pvtDeviceIndex, pvtCardIndex, pvtPortIndex, portVidIndex }
			::= { portVlanTranslationTable 1 }

		
		PortVlanTranslationEntry ::=
			SEQUENCE { 
				pvtDeviceIndex
					EponDeviceIndex,
				pvtCardIndex
					EponCardIndex,
				pvtPortIndex
					EponPortIndex,
				portVidIndex
					Unsigned32,
				translationNewVid
					Unsigned32,
				translationRowStatus
					RowStatus
			 }

		-- 1.3.6.1.4.1.17409.2.3.7.3.2.1.1
		pvtDeviceIndex OBJECT-TYPE
			SYNTAX EponDeviceIndex (1..2147483647)
			MAX-ACCESS not-accessible
			STATUS current
			DESCRIPTION
				"
				OLT/ONU"
			::= { portVlanTranslationEntry 1 }

		
		-- 1.3.6.1.4.1.17409.2.3.7.3.2.1.2
		pvtCardIndex OBJECT-TYPE
			SYNTAX EponCardIndex (1..2147483647)
			MAX-ACCESS not-accessible
			STATUS current
			DESCRIPTION
				"
				"
			::= { portVlanTranslationEntry 2 }

		
		-- 1.3.6.1.4.1.17409.2.3.7.3.2.1.3
		pvtPortIndex OBJECT-TYPE
			SYNTAX EponPortIndex (1..2147483647)
			MAX-ACCESS not-accessible
			STATUS current
			DESCRIPTION
				"
				pon/ONU/uni/sni"
			::= { portVlanTranslationEntry 3 }

		
		-- 1.3.6.1.4.1.17409.2.3.7.3.2.1.4
		portVidIndex OBJECT-TYPE
			SYNTAX Unsigned32 (1..2147483647)
			MAX-ACCESS not-accessible
			STATUS current
			DESCRIPTION
				"
				VLAN ID"
			::= { portVlanTranslationEntry 4 }

		
		-- 1.3.6.1.4.1.17409.2.3.7.3.2.1.5
		translationNewVid OBJECT-TYPE
			SYNTAX Unsigned32
			MAX-ACCESS read-create
			STATUS current
			DESCRIPTION
				"
				vlan"
			::= { portVlanTranslationEntry 5 }

		
		-- 1.3.6.1.4.1.17409.2.3.7.3.2.1.6
		translationRowStatus OBJECT-TYPE
			SYNTAX RowStatus
			MAX-ACCESS read-create
			STATUS current
			DESCRIPTION
				"
				 "
			::= { portVlanTranslationEntry 6 }

		
		-- 1.3.6.1.4.1.17409.2.3.7.3.3
		portVlanAggregationManagement OBJECT-IDENTITY
			STATUS current
			DESCRIPTION 
				"
				VlanVLAN Aggregation"
			::= { portVlanGroup 3 }

		
		-- 1.3.6.1.4.1.17409.2.3.7.3.3.1
		portVlanAggregationConfigTable OBJECT-TYPE
			SYNTAX SEQUENCE OF PortVlanAggregationConfigEntry
			MAX-ACCESS not-accessible
			STATUS current
			DESCRIPTION
				"
				Vlan
				This table applies on OLT pon port, OLT onu ID, ONU UNI.
				1. If the table is maintained in OLT device:
				Applied Obj  - Descriptions of Index
				------------------------------------------------------------------
				OLT Pon Port - OnuNum of pvaDeviceIndex shall be set to 0,
				         pvaCardIndex, and pvaPortIndex set to 0 indicates
				         meaningless 
				OLT onu ID   - Set pvaDeviceIndex to corresponding ONU ID,
				         pvaCardIndex, and pvaPortIndex set to 0 indicates
				         meaningless        
				ONU UNI    - Set pvaDeviceIndex to corresponding ONU ID,
				         pvaCardIndex, and pvaPortIndex set to the corresponding 
				         value
				
				2. If the table is maintained in ONU device:
				pvaDeviceIndex shall be set to 0 to indicate meaningless.
				pvaCardIndex shall be set to corresponding slot.
				pvaPortIndex shall be set to corresponding port.        
				"
			::= { portVlanAggregationManagement 1 }

		
		-- 1.3.6.1.4.1.17409.2.3.7.3.3.1.1
		portVlanAggregationConfigEntry OBJECT-TYPE
			SYNTAX PortVlanAggregationConfigEntry
			MAX-ACCESS not-accessible
			STATUS current
			DESCRIPTION
				" "
			INDEX { pvaDeviceIndex, pvaCardIndex, pvaPortIndex, portAggregationVidIndex }
			::= { portVlanAggregationConfigTable 1 }

		
		PortVlanAggregationConfigEntry ::=
			SEQUENCE { 
				pvaDeviceIndex
					EponDeviceIndex,
				pvaCardIndex
					EponCardIndex,
				pvaPortIndex
					EponPortIndex,
				portAggregationVidIndex
					Unsigned32,
				aggregationVidList
					OCTET STRING,
				aggregationRowStatus
					RowStatus
			 }

		-- 1.3.6.1.4.1.17409.2.3.7.3.3.1.1.1
		pvaDeviceIndex OBJECT-TYPE
			SYNTAX EponDeviceIndex (1..2147483647)
			MAX-ACCESS not-accessible
			STATUS current
			DESCRIPTION
				"
				OLT/ONU"
			::= { portVlanAggregationConfigEntry 1 }

		
		-- 1.3.6.1.4.1.17409.2.3.7.3.3.1.1.2
		pvaCardIndex OBJECT-TYPE
			SYNTAX EponCardIndex (1..2147483647)
			MAX-ACCESS not-accessible
			STATUS current
			DESCRIPTION
				"
				"
			::= { portVlanAggregationConfigEntry 2 }

		
		-- 1.3.6.1.4.1.17409.2.3.7.3.3.1.1.3
		pvaPortIndex OBJECT-TYPE
			SYNTAX EponPortIndex (1..2147483647)
			MAX-ACCESS not-accessible
			STATUS current
			DESCRIPTION
				"
				pon/uni/ONU ID"
			::= { portVlanAggregationConfigEntry 3 }

		
		-- 1.3.6.1.4.1.17409.2.3.7.3.3.1.1.4
		portAggregationVidIndex OBJECT-TYPE
			SYNTAX Unsigned32 (1..2147483647)
			MAX-ACCESS not-accessible
			STATUS current
			DESCRIPTION
				"
				VLANVLAN"
			::= { portVlanAggregationConfigEntry 4 }

		
		-- 1.3.6.1.4.1.17409.2.3.7.3.3.1.1.5
		aggregationVidList OBJECT-TYPE
			SYNTAX OCTET STRING (SIZE (512))
			MAX-ACCESS read-create
			STATUS current
			DESCRIPTION
				"
				vlan ID
				INTERNETOCTETOCTET 0, OCTET 1, ...
				OCTETbitbit0bit1...bit7
				bitOCTETbitVLANVLAN ID0..4095
				bitVLAN 0,bitVLAN 4095
				bitVLAN"
			::= { portVlanAggregationConfigEntry 5 }

		
		-- 1.3.6.1.4.1.17409.2.3.7.3.3.1.1.6
		aggregationRowStatus OBJECT-TYPE
			SYNTAX RowStatus
			MAX-ACCESS read-create
			STATUS current
			DESCRIPTION
				"
				"
			::= { portVlanAggregationConfigEntry 6 }

		
		-- 1.3.6.1.4.1.17409.2.3.7.3.4
		portVlanTrunkTable OBJECT-TYPE
			SYNTAX SEQUENCE OF PortVlanTrunkEntry
			MAX-ACCESS not-accessible
			STATUS current
			DESCRIPTION
				"
				Vlan trunkVLAN Trunk?
				This table applies on OLT pon port, OLT SNI, OLT onu ID, ONU UNI.
				1. If the table is maintained in OLT device:
				Applied Obj  - Descriptions of Index
				------------------------------------------------------------------
				OLT Pon Port - OnuNum of pvtDeviceIndex shall be set to 0,
				/OLT SNI     pvtCardIndex, and pvtPortIndex set to 0 indicates
				         meaningless 
				OLT onu ID   - Set pvtDeviceIndex to corresponding ONU ID,
				         pvtCardIndex, and pvtPortIndex set to 0 indicates
				         meaningless        
				ONU UNI    - Set pvtDeviceIndex to corresponding ONU ID,
				         pvtCardIndex, and pvtPortIndex set to the corresponding 
				         value
				
				2. If the table is maintained in ONU device:
				pvtDeviceIndex shall be set to 0 to indicate meaningless.
				pvtCardIndex shall be set to corresponding slot.
				pvtPortIndex shall be set to corresponding port.        
				"
			::= { portVlanGroup 4 }

		
		-- 1.3.6.1.4.1.17409.2.3.7.3.4.1
		portVlanTrunkEntry OBJECT-TYPE
			SYNTAX PortVlanTrunkEntry
			MAX-ACCESS not-accessible
			STATUS current
			DESCRIPTION
				" "
			INDEX { trunkDeviceIndex, trunkCardIndex, trunkPortIndex }
			::= { portVlanTrunkTable 1 }

		
		PortVlanTrunkEntry ::=
			SEQUENCE { 
				trunkDeviceIndex
					EponDeviceIndex,
				trunkCardIndex
					EponCardIndex,
				trunkPortIndex
					EponPortIndex,
				trunkVidList
					OCTET STRING,
				portVlanTrunkRowStatus
					RowStatus
			 }

		-- 1.3.6.1.4.1.17409.2.3.7.3.4.1.1
		trunkDeviceIndex OBJECT-TYPE
			SYNTAX EponDeviceIndex (1..2147483647)
			MAX-ACCESS not-accessible
			STATUS current
			DESCRIPTION
				"
				
				"
			::= { portVlanTrunkEntry 1 }

		
		-- 1.3.6.1.4.1.17409.2.3.7.3.4.1.2
		trunkCardIndex OBJECT-TYPE
			SYNTAX EponCardIndex (1..2147483647)
			MAX-ACCESS not-accessible
			STATUS current
			DESCRIPTION
				"
				"
			::= { portVlanTrunkEntry 2 }

		
		-- 1.3.6.1.4.1.17409.2.3.7.3.4.1.3
		trunkPortIndex OBJECT-TYPE
			SYNTAX EponPortIndex (1..2147483647)
			MAX-ACCESS not-accessible
			STATUS current
			DESCRIPTION
				"
				"
			::= { portVlanTrunkEntry 3 }

		
		-- 1.3.6.1.4.1.17409.2.3.7.3.4.1.4
		trunkVidList OBJECT-TYPE
			SYNTAX OCTET STRING (SIZE (512))
			MAX-ACCESS read-create
			STATUS current
			DESCRIPTION
				"
				Trunked Vlan List for the port
				INTERNETOCTETOCTET 0, OCTET 1, ...
				OCTETbitbit0bit1...bit7
				bitOCTETbitVLANVLAN ID0..4095
				bitVLAN 0,bitVLAN 4095
				bitVLAN
				"
			::= { portVlanTrunkEntry 4 }

		
		-- 1.3.6.1.4.1.17409.2.3.7.3.4.1.5
		portVlanTrunkRowStatus OBJECT-TYPE
			SYNTAX RowStatus
			MAX-ACCESS read-create
			STATUS current
			DESCRIPTION
				"
				"
			::= { portVlanTrunkEntry 5 }
	-- 1.3.6.1.4.1.17409.2.3.7.3.5		
    oltPortVlanTable OBJECT-TYPE
            SYNTAX SEQUENCE OF OltPortVlanEntry
             MAX-ACCESS not-accessible
            STATUS current
            DESCRIPTION
            "
             SNI/PON\u7f02\u5099\u7126\u59ab\u5fdb\u5d39\u93b7\u5c7b\u4eb9\u6fde\u5c7d\u57d0an\u95c1\u8364\u505e\u9350\u5a5a\u5e4f\u951f\ufffd     
             This table applies on OLT pon port, OLT SNI       
             Applied Obj  - Descriptions of Index
            ------------------------------------------------------------------
            OLT Pon Port/OLT SNI - OnuNum of pvlanDeviceIndex shall be set to 0
            "
           ::= { portVlanGroup 5 }
        -- 1.3.6.1.4.1.17409.2.3.7.3.5.1
        oltPortVlanEntry OBJECT-TYPE
          SYNTAX OltPortVlanEntry
           MAX-ACCESS not-accessible
          STATUS current
          DESCRIPTION
          " "
          INDEX { oltPortVlanDeviceIndex	 }
          ::= { oltPortVlanTable 1 }
    
        OltPortVlanEntry  ::=
         SEQUENCE {
        oltPortVlanDeviceIndex	
          EponDeviceIndex,
        oltPortVlanTagPriority
          INTEGER,
        oltPortVlanPVid  
          INTEGER,
        oltPortVlanMode
          INTEGER
         }
        -- 1.3.6.1.4.1.17409.2.3.7.3.5.1.1
        oltPortVlanDeviceIndex  OBJECT-TYPE
          SYNTAX EponDeviceIndex
          MAX-ACCESS not-accessible
          STATUS current
          DESCRIPTION
         "
         SNI/PON port "
         ::= { oltPortVlanEntry 1 }
        -- 1.3.6.1.4.1.17409.2.3.7.3.5.1.2
        oltPortVlanTagPriority  OBJECT-TYPE
          SYNTAX INTEGER (0..7)
          MAX-ACCESS read-write
          STATUS current
          DESCRIPTION
          "
          vlan"
          ::= { oltPortVlanEntry 2 }
        -- 1.3.6.1.4.1.17409.2.3.7.3.5.1.3
        oltPortVlanPVid  OBJECT-TYPE
          SYNTAX INTEGER
          MAX-ACCESS read-write
          STATUS current
          DESCRIPTION
          "
          port Vlan ID"
         ::= { oltPortVlanEntry 3 }
        -- 1.3.6.1.4.1.17409.2.3.7.3.5.1.4
        oltPortVlanMode OBJECT-TYPE
          SYNTAX INTEGER
          {
           trunk(1),
           access(2),
          hybrid(3)
          }
          MAX-ACCESS read-write
         STATUS current
         DESCRIPTION
         "
          vlan\u6fe0\u7898\u69c5\u9368\ue048\u6553\u9423\u5c7e\ue78f\u95bf\u71c2\u62f7          "
         ::= { oltPortVlanEntry 4 }
		
		-- 1.3.6.1.4.1.17409.2.3.7.4
		qinQConfigGroup OBJECT-IDENTITY
			STATUS current
			DESCRIPTION 
				"
				QinQ
				OLT/ONUQINQOLTONU"
			::= { vlanManagementObjects 4 }

		
		-- 1.3.6.1.4.1.17409.2.3.7.4.1
		portQinQConfigTable OBJECT-TYPE
			SYNTAX SEQUENCE OF PortQinQConfigEntry
			MAX-ACCESS not-accessible
			STATUS current
			DESCRIPTION
				"
				QinQ
				This table applies on OLT pon port, OLT SNI, OLT onu ID, ONU UNI.
				1. If the table is maintained in OLT device:
				Applied Obj  - Descriptions of Index
				------------------------------------------------------------------
				OLT Pon Port - OnuNum of pqDeviceIndex shall be set to 0,
				/OLT SNI     pqCardIndex, and pqPortIndex set to 0 indicates
				         meaningless 
				OLT onu ID   - Set pqDeviceIndex to corresponding ONU ID,
				         pqCardIndex, and pqPortIndex set to 0 indicates
				         meaningless        
				ONU UNI    - Set pqDeviceIndex to corresponding ONU ID,
				           pqCardIndex, and pqPortIndex set to the corresponding 
				           value
				   
				2. If the table is maintained in ONU device:
				pqDeviceIndex shall be set to 0 to indicate meaningless.
				pqCardIndex shall be set to corresponding slot.
				pqPortIndex shall be set to corresponding port.       
				"
			::= { qinQConfigGroup 1 }

		
		-- 1.3.6.1.4.1.17409.2.3.7.4.1.1
		portQinQConfigEntry OBJECT-TYPE
			SYNTAX PortQinQConfigEntry
			MAX-ACCESS not-accessible
			STATUS current
			DESCRIPTION
				" "
			INDEX { pqDeviceIndex, pqCardIndex, pqPortIndex, pqStartVlanId, pqEndVlanId
				 }
			::= { portQinQConfigTable 1 }

		
		PortQinQConfigEntry ::=
			SEQUENCE { 
				pqDeviceIndex
					EponDeviceIndex,
				pqCardIndex
					EponCardIndex,
				pqPortIndex
					EponPortIndex,
				pqStartVlanId
					INTEGER,
				pqEndVlanId
					INTEGER,
				pqSVlanId
					INTEGER,
				pqSTagCosDetermine
					INTEGER,
				pqSTagCosNewValue
					INTEGER,
				pqRowStatus
					RowStatus
			 }

		-- 1.3.6.1.4.1.17409.2.3.7.4.1.1.1
		pqDeviceIndex OBJECT-TYPE
			SYNTAX EponDeviceIndex (1..2147483647)
			MAX-ACCESS not-accessible
			STATUS current
			DESCRIPTION
				"
				ONU ID, for a specific ONU"
			::= { portQinQConfigEntry 1 }

		
		-- 1.3.6.1.4.1.17409.2.3.7.4.1.1.2
		pqCardIndex OBJECT-TYPE
			SYNTAX EponCardIndex (1..2147483647)
			MAX-ACCESS not-accessible
			STATUS current
			DESCRIPTION
				"
				"
			::= { portQinQConfigEntry 2 }

		
		-- 1.3.6.1.4.1.17409.2.3.7.4.1.1.3
		pqPortIndex OBJECT-TYPE
			SYNTAX EponPortIndex (1..2147483647)
			MAX-ACCESS not-accessible
			STATUS current
			DESCRIPTION
				"
				"
			::= { portQinQConfigEntry 3 }

		
		-- 1.3.6.1.4.1.17409.2.3.7.4.1.1.4
		pqStartVlanId OBJECT-TYPE
			SYNTAX INTEGER (1..2147483647)
			MAX-ACCESS not-accessible
			STATUS current
			DESCRIPTION
				"
				The starting VLAN ID, working together with pqEndVlanId,
				consists of a VLAN group. The VLAN ID match the VLAN group
				will be QinQed with specified outer VLAN
				"
			::= { portQinQConfigEntry 4 }

		
		-- 1.3.6.1.4.1.17409.2.3.7.4.1.1.5
		pqEndVlanId OBJECT-TYPE
			SYNTAX INTEGER (1..2147483647)
			MAX-ACCESS not-accessible
			STATUS current
			DESCRIPTION
				"
				The ending VLAN ID, working together with pqStartVlanId,
				consists of a VLAN range. The VLAN ID match the VLAN range
				will be QinQed with specified outer VLAN
				"
			::= { portQinQConfigEntry 5 }

		
		-- 1.3.6.1.4.1.17409.2.3.7.4.1.1.6
		pqSVlanId OBJECT-TYPE
			SYNTAX INTEGER
			MAX-ACCESS read-create
			STATUS current
			DESCRIPTION
				"
				The outer VLAN id to be QinQed"
			::= { portQinQConfigEntry 6 }

		
		-- 1.3.6.1.4.1.17409.2.3.7.4.1.1.7
		pqSTagCosDetermine OBJECT-TYPE
			SYNTAX INTEGER
				{
				NO(1),
				YES(2)
				}
			MAX-ACCESS read-create
			STATUS current
			DESCRIPTION
				"
				What STAG COS will be set for this QinQ instance. It could
				be either a new definition or copied from CTAG
				"
			::= { portQinQConfigEntry 7 }

		
		-- 1.3.6.1.4.1.17409.2.3.7.4.1.1.8
		pqSTagCosNewValue OBJECT-TYPE
			SYNTAX INTEGER (0..7)
			MAX-ACCESS read-create
			STATUS current
			DESCRIPTION
				"
				The new STAG COS value if pqSTagCosDetermine is selected as
				redefine(1)
				"
			DEFVAL { 0 }
			::= { portQinQConfigEntry 8 }

		
		-- 1.3.6.1.4.1.17409.2.3.7.4.1.1.9
		pqRowStatus OBJECT-TYPE
			SYNTAX RowStatus
			MAX-ACCESS read-create
			STATUS current
			DESCRIPTION
				"
				"
			::= { portQinQConfigEntry 9 }

		
		-- 1.3.6.1.4.1.17409.2.3.8
		qosManagementObjects OBJECT IDENTIFIER ::= { eponTree 8 }

		
-- ------------------------------------------------------------------------------
-- qosManagementObjects[ Qos](1.3.6.1.4.1.17409.2.3.8)
-- ------------------------------------------------------------------------------ 
		-- 1.3.6.1.4.1.17409.2.3.8.1
		qosGlobalSetTable OBJECT-TYPE
			SYNTAX SEQUENCE OF QosGlobalSetEntry
			MAX-ACCESS not-accessible
			STATUS current
			DESCRIPTION
				"Global QoS parameters."
			::= { qosManagementObjects 1 }

		
		-- 1.3.6.1.4.1.17409.2.3.8.1.1
		qosGlobalSetEntry OBJECT-TYPE
			SYNTAX QosGlobalSetEntry
			MAX-ACCESS not-accessible
			STATUS current
			DESCRIPTION			" "
			INDEX { qosGlobalSetDeviceIndex }
			::= { qosGlobalSetTable 1 }

		
		QosGlobalSetEntry ::=
			SEQUENCE { 
				qosGlobalSetDeviceIndex
					EponDeviceIndex,
				qosGlobalSetMaxQueueCount
					INTEGER,
				qosGlobalSetMode
					INTEGER
			 }

		-- 1.3.6.1.4.1.17409.2.3.8.1.1.1
		qosGlobalSetDeviceIndex OBJECT-TYPE
			SYNTAX EponDeviceIndex (1..2147483647)
			MAX-ACCESS not-accessible
			STATUS current
			DESCRIPTION
				"
				Device index        
				For OLT - Set to corresponding device
				For ONU - Set to 0
				"
			::= { qosGlobalSetEntry 1 }

		
		-- 1.3.6.1.4.1.17409.2.3.8.1.1.2
		qosGlobalSetMaxQueueCount OBJECT-TYPE
			SYNTAX INTEGER (1..256)
			MAX-ACCESS read-only
			STATUS current
			DESCRIPTION
				"
				80-7"
			::= { qosGlobalSetEntry 2 }

		
		-- 1.3.6.1.4.1.17409.2.3.8.1.1.3
		qosGlobalSetMode OBJECT-TYPE
			SYNTAX INTEGER
				{
				deviceBased(1),
				portBased(2)
				}
			MAX-ACCESS read-write
			STATUS current
			DESCRIPTION
				"
				Define how to set QoS parameter
				deviceBased(1)  - When set, only the table started with deviceBase is applicable
				portBased(2)  - When set, only the table started with portBase is applicable
				"
			DEFVAL { deviceBased }
			::= { qosGlobalSetEntry 3 }

		
		-- 1.3.6.1.4.1.17409.2.3.8.2
		deviceBaseQosMapTable OBJECT-TYPE
			SYNTAX SEQUENCE OF DeviceBaseQosMapEntry
			MAX-ACCESS not-accessible
			STATUS current
			DESCRIPTION
				"Deviced based setting.        
				It is used to define how to map QoS options to queue"
			::= { qosManagementObjects 2 }

		
		-- 1.3.6.1.4.1.17409.2.3.8.2.1
		deviceBaseQosMapEntry OBJECT-TYPE
			SYNTAX DeviceBaseQosMapEntry
			MAX-ACCESS not-accessible
			STATUS current
			DESCRIPTION			" "
			INDEX { deviceBaseQosMapDeviceIndex, deviceBaseQosMapRuleIndex }
			::= { deviceBaseQosMapTable 1 }

		
		DeviceBaseQosMapEntry ::=
			SEQUENCE { 
				deviceBaseQosMapDeviceIndex
					EponDeviceIndex,
				deviceBaseQosMapRuleIndex
					INTEGER,
				deviceBaseQosMapOctet
					OCTET STRING
			 }

		-- 1.3.6.1.4.1.17409.2.3.8.2.1.1
		deviceBaseQosMapDeviceIndex OBJECT-TYPE
			SYNTAX EponDeviceIndex (1..2147483647)
			MAX-ACCESS not-accessible
			STATUS current
			DESCRIPTION
				"
				Device index        
				For OLT - Set to corresponding device
				For ONU - Set to 0
				"
			::= { deviceBaseQosMapEntry 1 }

		
		-- 1.3.6.1.4.1.17409.2.3.8.2.1.2
		deviceBaseQosMapRuleIndex OBJECT-TYPE
			SYNTAX INTEGER
				{
				cos(1),
				tos(2),
				diffserv(3)
				}
			MAX-ACCESS not-accessible
			STATUS current
			DESCRIPTION
				"
				"
			::= { deviceBaseQosMapEntry 2 }

		
		-- 1.3.6.1.4.1.17409.2.3.8.2.1.3
		deviceBaseQosMapOctet OBJECT-TYPE
			SYNTAX OCTET STRING (SIZE (8 | 64))
			MAX-ACCESS read-write
			STATUS current
			DESCRIPTION
				"
				
				864
				qosGlobalSetMaxQueueCountqosGlobalSetMaxQueueCount80-7        
				 cos 8cos0-7 
				 tos 16tos0-15 
				 diffserv64diffserv0-63        
				
				get 1.3.6.1.4.1.17409.2.3.8.3.1.3.deviceBaseQosMapDeviceIndex(410100101).cos(1) = hex(00 00 01 02 03 03 04 04)
				
				cos 0 -> queue 0
				cos 1 -> queue 0
				cos 2 -> queue 1
				cos 3 -> queue 2
				cos 4 -> queue 3
				cos 5 -> queue 3
				cos 6 -> queue 4
				cos 7 -> queue 4
				"
			::= { deviceBaseQosMapEntry 3 }

		
		-- 1.3.6.1.4.1.17409.2.3.8.3
		deviceBaseQosPolicyTable OBJECT-TYPE
			SYNTAX SEQUENCE OF DeviceBaseQosPolicyEntry
			MAX-ACCESS not-accessible
			STATUS current
			DESCRIPTION
				"Deviced based setting
				
				It is used to define QoS specification"
			::= { qosManagementObjects 3 }

		
		-- 1.3.6.1.4.1.17409.2.3.8.3.1
		deviceBaseQosPolicyEntry OBJECT-TYPE
			SYNTAX DeviceBaseQosPolicyEntry
			MAX-ACCESS not-accessible
			STATUS current
			DESCRIPTION			" "
			INDEX { deviceBaseQosPolicyDeviceIndex }
			::= { deviceBaseQosPolicyTable 1 }

		
		DeviceBaseQosPolicyEntry ::=
			SEQUENCE { 
				deviceBaseQosPolicyDeviceIndex
					EponDeviceIndex,
				deviceBaseQosPolicyMode
					INTEGER,
				deviceBaseQosPolicyWeightOctet
					OCTET STRING,
				deviceBaseQosPolicySpBandwidthRange
					OCTET STRING
			 }

		-- 1.3.6.1.4.1.17409.2.3.8.3.1.1
		deviceBaseQosPolicyDeviceIndex OBJECT-TYPE
			SYNTAX EponDeviceIndex (1..2147483647)
			MAX-ACCESS not-accessible
			STATUS current
			DESCRIPTION
				"
				Device index        
				For OLT - Set to corresponding device
				For ONU - Set to 0
				"
			::= { deviceBaseQosPolicyEntry 1 }

		
		-- 1.3.6.1.4.1.17409.2.3.8.3.1.2
		deviceBaseQosPolicyMode OBJECT-TYPE
			SYNTAX INTEGER
				{
				sp(1),
				wrr(2),
				spWrr(3),
				wfp(4)
				}
			MAX-ACCESS read-write
			STATUS current
			DESCRIPTION
				"
				"
			::= { deviceBaseQosPolicyEntry 2 }

		
		-- 1.3.6.1.4.1.17409.2.3.8.3.1.3
		deviceBaseQosPolicyWeightOctet OBJECT-TYPE
			SYNTAX OCTET STRING
			MAX-ACCESS read-write
			STATUS current
			DESCRIPTION
				"
				        
				
				 sp0
				 wrr1-100100
				 spWrr0-1000sp0100
				 wfp0        
				
				get 1.3.6.1.4.1.17409.2.3.8.4.1.2.deviceBaseQosPolicyDeviceIndex(410100101). = wrr(2)
				get 1.3.6.1.4.1.17409.2.3.8.4.1.3.deviceBaseQosPolicyDeviceIndex(410100101). = hex(5 5 5 5 10 20 20 30)
				
				8
				queue 0  5
				queue 1  5
				queue 2  5
				queue 3  5
				queue 4  10
				queue 5  20
				queue 6  20
				queue 7  30
				
				"
			::= { deviceBaseQosPolicyEntry 3 }

		
		-- 1.3.6.1.4.1.17409.2.3.8.3.1.4
		deviceBaseQosPolicySpBandwidthRange OBJECT-TYPE
			SYNTAX OCTET STRING
			MAX-ACCESS read-write
			STATUS current
			DESCRIPTION
				"
				Define SP assured bandwidth for each queue.        
				The size of this object is 4*(number of queue). For each queue, use 4 octets 
				to represend the assured bandwidth for the queue. The four-octet could be mapped
				to an unsigned integer, in units of kbps. The sequence of the map is from queue 
				0 to queue max (for example, 7).        
				For example, 00 00 00 10  00 00 01 00  00 00 00 00  00 00 00 00
				             00 00 10 00  00 00 00 01  00 01 01 00  00 00 11 11                     
				It means, 8 queues and the assured bandwidth for each queue as:        
				queue 0  16kbps
				queue 1  256kbps
				queue 2  0 
				queue 3  0
				queue 4  4096kbps
				queue 5  1kbps
				queue 6  65792kbps
				queue 7  65535kbps
				"
			::= { deviceBaseQosPolicyEntry 4 }

		
		-- 1.3.6.1.4.1.17409.2.3.8.4
		portBaseQosMapTable OBJECT-TYPE
			SYNTAX SEQUENCE OF PortBaseQosMapEntry
			MAX-ACCESS not-accessible
			STATUS current
			DESCRIPTION			" "
			::= { qosManagementObjects 4 }

		
		-- 1.3.6.1.4.1.17409.2.3.8.4.1
		portBaseQosMapEntry OBJECT-TYPE
			SYNTAX PortBaseQosMapEntry
			MAX-ACCESS not-accessible
			STATUS current
			DESCRIPTION			" "
			INDEX { portBaseQosMapDeviceIndex, portBaseQosMapCardIndex, portBaseQosMapPortIndex, portBaseQosMapRuleIndex }
			::= { portBaseQosMapTable 1 }

		
		PortBaseQosMapEntry ::=
			SEQUENCE { 
				portBaseQosMapDeviceIndex
					EponDeviceIndex,
				portBaseQosMapCardIndex
					EponPortIndex,
				portBaseQosMapPortIndex
					EponPortIndex,
				portBaseQosMapRuleIndex
					INTEGER,
				portBaseQosMapOctet
					OCTET STRING
			 }

		-- 1.3.6.1.4.1.17409.2.3.8.4.1.1
		portBaseQosMapDeviceIndex OBJECT-TYPE
			SYNTAX EponDeviceIndex (1..2147483647)
			MAX-ACCESS not-accessible
			STATUS current
			DESCRIPTION
				"
				Device index        
				For OLT, set to corresponding SNI port or PON port
				For ONU, set to 0
				"
			::= { portBaseQosMapEntry 1 }

		
		-- 1.3.6.1.4.1.17409.2.3.8.4.1.2
		portBaseQosMapCardIndex OBJECT-TYPE
			SYNTAX EponPortIndex (1..2147483647)
			MAX-ACCESS not-accessible
			STATUS current
			DESCRIPTION
				"
				        
				For OLT, set to 0
				For ONU, set to corresponding slot
				"
			::= { portBaseQosMapEntry 2 }

		
		-- 1.3.6.1.4.1.17409.2.3.8.4.1.3
		portBaseQosMapPortIndex OBJECT-TYPE
			SYNTAX EponPortIndex (1..2147483647)
			MAX-ACCESS not-accessible
			STATUS current
			DESCRIPTION
				"
				        
				For OLT, set to 0
				For ONU, set to corresponding port
				"
			::= { portBaseQosMapEntry 3 }

		
		-- 1.3.6.1.4.1.17409.2.3.8.4.1.4
		portBaseQosMapRuleIndex OBJECT-TYPE
			SYNTAX INTEGER
				{
				cos(1),
				tos(2),
				diffserv(3)
				}
			MAX-ACCESS not-accessible
			STATUS current
			DESCRIPTION
				"
				"
			::= { portBaseQosMapEntry 4 }

		
		-- 1.3.6.1.4.1.17409.2.3.8.4.1.5
		portBaseQosMapOctet OBJECT-TYPE
			SYNTAX OCTET STRING (SIZE (8..64))
			MAX-ACCESS read-write
			STATUS current
			DESCRIPTION
				"
				
				864
				qosGlobalSetMaxQueueCountqosGlobalSetMaxQueueCount80-7        
				 cos 8cos0-7 
				 tos 16tos0-16 
				 diffserv64diffserv0-64        
				
				get 1.3.6.1.4.1.17409.2.3.8.3.1.3.deviceBaseQosMapDeviceIndex(410100101).cos(1) = hex(00 00 01 02 03 03 04 04)
				
				cos 0 -> queue 0
				cos 1 -> queue 0
				cos 2 -> queue 1
				cos 3 -> queue 2
				cos 4 -> queue 3
				cos 5 -> queue 3
				cos 6 -> queue 4
				cos 7 -> queue 4
				"
			::= { portBaseQosMapEntry 5 }

		
		-- 1.3.6.1.4.1.17409.2.3.8.5
		portBaseQosPolicyTable OBJECT-TYPE
			SYNTAX SEQUENCE OF PortBaseQosPolicyEntry
			MAX-ACCESS not-accessible
			STATUS current
			DESCRIPTION
				"Description."
			::= { qosManagementObjects 5 }

		
		-- 1.3.6.1.4.1.17409.2.3.8.5.1
		portBaseQosPolicyEntry OBJECT-TYPE
			SYNTAX PortBaseQosPolicyEntry
			MAX-ACCESS not-accessible
			STATUS current
			DESCRIPTION			" "
			INDEX { portBaseQosPolicyDeviceIndex, portBaseQosPolicyCardIndex, portBaseQosPolicyPortIndex }
			::= { portBaseQosPolicyTable 1 }

		
		PortBaseQosPolicyEntry ::=
			SEQUENCE { 
				portBaseQosPolicyDeviceIndex
					EponDeviceIndex,
				portBaseQosPolicyCardIndex
					EponPortIndex,
				portBaseQosPolicyPortIndex
					EponPortIndex,
				portBaseQosPolicyMode
					INTEGER,
				portBaseQosPolicyWeightOctet
					OCTET STRING,
				portBaseQosPolicySpBandwidthRange
					OCTET STRING
			 }

		-- 1.3.6.1.4.1.17409.2.3.8.5.1.1
		portBaseQosPolicyDeviceIndex OBJECT-TYPE
			SYNTAX EponDeviceIndex
			MAX-ACCESS not-accessible
			STATUS current
			DESCRIPTION
				"
				Device index
				For OLT, set to corresponding SNI port or PON port
				For ONU, set to 0
				"
			::= { portBaseQosPolicyEntry 1 }

		
		-- 1.3.6.1.4.1.17409.2.3.8.5.1.2
		portBaseQosPolicyCardIndex OBJECT-TYPE
			SYNTAX EponPortIndex (1..2147483647)
			MAX-ACCESS not-accessible
			STATUS current
			DESCRIPTION
				"
				        
				For OLT, set to 0
				For ONU, set to corresponding slot
				"
			::= { portBaseQosPolicyEntry 2 }

		
		-- 1.3.6.1.4.1.17409.2.3.8.5.1.3
		portBaseQosPolicyPortIndex OBJECT-TYPE
			SYNTAX EponPortIndex (1..2147483647)
			MAX-ACCESS not-accessible
			STATUS current
			DESCRIPTION
				"
				        
				For OLT, set to 0
				For ONU, set to corresponding port
				"
			::= { portBaseQosPolicyEntry 3 }

		
		-- 1.3.6.1.4.1.17409.2.3.8.5.1.4
		portBaseQosPolicyMode OBJECT-TYPE
			SYNTAX INTEGER
				{
				sp(1),
				wrr(2),
				spWrr(3),
				wfp(4)
				}
			MAX-ACCESS read-write
			STATUS current
			DESCRIPTION
				"
				        
				sp 
				wrr 
				spWrr sp+wrr
				wfp "
			::= { portBaseQosPolicyEntry 4 }

		
		-- 1.3.6.1.4.1.17409.2.3.8.5.1.5
		portBaseQosPolicyWeightOctet OBJECT-TYPE
			SYNTAX OCTET STRING (SIZE (1..256))
			MAX-ACCESS read-write
			STATUS current
			DESCRIPTION
				"
				        
				        
				 sp0
				 wrr1-100100
				 spWrr0-1000sp0100
				 wfp0        
				
				get 1.3.6.1.4.1.17409.2.3.8.4.1.2.deviceBaseQosPolicyDeviceIndex(410100101). = wrr(2)
				get 1.3.6.1.4.1.17409.2.3.8.4.1.3.deviceBaseQosPolicyDeviceIndex(410100101). = hex(5 5 5 5 10 20 20 30)        
				8
				queue 0  5
				queue 1  5
				queue 2  5
				queue 3  5
				queue 4  10
				queue 5  20
				queue 6  20
				queue 7  30        
				"
			::= { portBaseQosPolicyEntry 5 }

		
		-- 1.3.6.1.4.1.17409.2.3.8.5.1.6
		portBaseQosPolicySpBandwidthRange OBJECT-TYPE
			SYNTAX OCTET STRING
			MAX-ACCESS read-write
			STATUS current
			DESCRIPTION
				"     
				Define SP assured bandwidth for each queue.        
				The size of this object is 4*(number of queue). For each queue, use 4 octets 
				to represend the assured bandwidth for the queue. The four-octet could be mapped
				to an unsigned integer, in units of kbps. The sequence of the map is from queue 
				0 to queue max (for example, 7).        
				For example, 00 00 00 10  00 00 01 00  00 00 00 00  00 00 00 00
				             00 00 10 00  00 00 00 01  00 01 01 00  00 00 11 11                     
				It means, 8 queues and the assured bandwidth for each queue as:        
				queue 0  16kbps
				queue 1  256kbps
				queue 2  0 
				queue 3  0
				queue 4  4096kbps
				queue 5  1kbps
				queue 6  65792kbps
				queue 7  65535kbps
				"
			::= { portBaseQosPolicyEntry 6 }

		
		-- 1.3.6.1.4.1.17409.2.3.9
		stpManagementObjects OBJECT IDENTIFIER ::= { eponTree 9 }

		
-- ------------------------------------------------------------------------------
-- stpManagementObjects[STP](1.3.6.1.4.1.17409.2.3.9)
-- ------------------------------------------------------------------------------ 
		-- 1.3.6.1.4.1.17409.2.3.9.1
		stpGlobalSetTable OBJECT-TYPE
			SYNTAX SEQUENCE OF StpGlobalSetEntry
			MAX-ACCESS not-accessible
			STATUS current
			DESCRIPTION
				"
				STP"
			::= { stpManagementObjects 1 }

		
		-- 1.3.6.1.4.1.17409.2.3.9.1.1
		stpGlobalSetEntry OBJECT-TYPE
			SYNTAX StpGlobalSetEntry
			MAX-ACCESS not-accessible
			STATUS current
			DESCRIPTION			" "
			INDEX { stpGlobalSetIndex }
			::= { stpGlobalSetTable 1 }

		
		StpGlobalSetEntry ::=
			SEQUENCE { 
				stpGlobalSetIndex
					Counter32,
				stpGlobalSetVersion
					INTEGER,
				stpGlobalSetPriority
					INTEGER,
				stpGlobalSetTimeSinceTopologyChange
					TimeTicks,
				stpGlobalSetTopChanges
					Counter32,
				stpGlobalSetDesignatedRoot
					BridgeId,
				stpGlobalSetRootCost
					INTEGER,
				stpGlobalSetRootPort
					OCTET STRING,
				stpGlobalSetMaxAge
					Timeout,
				stpGlobalSetHelloTime
					Timeout,
				stpGlobalSetHoldTime
					INTEGER,
				stpGlobalSetForwardDelay
					Timeout,
				stpGlobalSetBridgeMaxAge
					Timeout,
				stpGlobalSetBridgeHelloTime
					Timeout,
				stpGlobalSetBridgeForwardDelay
					Timeout,
				stpGlobalSetRstpTxHoldCount
					INTEGER,
				stpGlobalSetEnable
					TruthValue
			 }

		-- 1.3.6.1.4.1.17409.2.3.9.1.1.1
		stpGlobalSetIndex OBJECT-TYPE
			SYNTAX Counter32
			MAX-ACCESS not-accessible
			STATUS current
			DESCRIPTION
				"
				        
				For OLT - Set to corresponding device
				For ONU - Set to 0
				"
			::= { stpGlobalSetEntry 1 }

		
		-- 1.3.6.1.4.1.17409.2.3.9.1.1.2
		stpGlobalSetVersion OBJECT-TYPE
			SYNTAX INTEGER
				{
				rstp(1),
				stp(2)
				}
			MAX-ACCESS read-write
			STATUS current
			DESCRIPTION
				"
				"
			DEFVAL { rstp }
			::= { stpGlobalSetEntry 2 }

		
		-- 1.3.6.1.4.1.17409.2.3.9.1.1.3
		stpGlobalSetPriority OBJECT-TYPE
			SYNTAX INTEGER (0..65535)
			MAX-ACCESS read-write
			STATUS current
			DESCRIPTION
				"
				
				IEEE 802.1dIEEE 802.1w0-614404096"
			::= { stpGlobalSetEntry 3 }

		
		-- 1.3.6.1.4.1.17409.2.3.9.1.1.4
		stpGlobalSetTimeSinceTopologyChange OBJECT-TYPE
			SYNTAX TimeTicks
			MAX-ACCESS read-only
			STATUS current
			DESCRIPTION
				"
				"
			::= { stpGlobalSetEntry 4 }

		
		-- 1.3.6.1.4.1.17409.2.3.9.1.1.5
		stpGlobalSetTopChanges OBJECT-TYPE
			SYNTAX Counter32
			UNITS "topology changes"
			MAX-ACCESS read-only
			STATUS current
			DESCRIPTION
				"
				"
			::= { stpGlobalSetEntry 5 }

		
		-- 1.3.6.1.4.1.17409.2.3.9.1.1.6
		stpGlobalSetDesignatedRoot OBJECT-TYPE
			SYNTAX BridgeId
			MAX-ACCESS read-only
			STATUS current
			DESCRIPTION
				"
				BridgeId"
			::= { stpGlobalSetEntry 6 }

		
		-- 1.3.6.1.4.1.17409.2.3.9.1.1.7
		stpGlobalSetRootCost OBJECT-TYPE
			SYNTAX INTEGER
			MAX-ACCESS read-only
			STATUS current
			DESCRIPTION
				"
				"
			::= { stpGlobalSetEntry 7 }

		
		-- 1.3.6.1.4.1.17409.2.3.9.1.1.8
		stpGlobalSetRootPort OBJECT-TYPE
			SYNTAX OCTET STRING (SIZE (3))
			MAX-ACCESS read-only
			STATUS current
			DESCRIPTION
				"
				
				The port is presented by three octets, in sequence of device ID, slot,
				and port.
				For ONU, device ID is meaningless and shall set 0. Slot and port shall
				be set to corresponding value.
				For OLT, device ID, slot, and port shall be set to corresponding value.
				For example, 
				01 02 03 means device 1, slot 2, port 3 is root port.
				0x00 04 05 means ONU slot 4, port 5 is root port.
				"
			::= { stpGlobalSetEntry 8 }

		
		-- 1.3.6.1.4.1.17409.2.3.9.1.1.9
		stpGlobalSetMaxAge OBJECT-TYPE
			SYNTAX Timeout
			UNITS "centi-seconds"
			MAX-ACCESS read-only
			STATUS current
			DESCRIPTION
				"
				1/100 secs"
			::= { stpGlobalSetEntry 9 }

		
		-- 1.3.6.1.4.1.17409.2.3.9.1.1.10
		stpGlobalSetHelloTime OBJECT-TYPE
			SYNTAX Timeout
			UNITS "centi-seconds"
			MAX-ACCESS read-only
			STATUS current
			DESCRIPTION
				"
				PDU"
			::= { stpGlobalSetEntry 10 }

		
		-- 1.3.6.1.4.1.17409.2.3.9.1.1.11
		stpGlobalSetHoldTime OBJECT-TYPE
			SYNTAX INTEGER
			UNITS "centi-seconds"
			MAX-ACCESS read-only
			STATUS current
			DESCRIPTION
				"
				PDU"
			::= { stpGlobalSetEntry 11 }

		
		-- 1.3.6.1.4.1.17409.2.3.9.1.1.12
		stpGlobalSetForwardDelay OBJECT-TYPE
			SYNTAX Timeout
			UNITS "centi-seconds"
			MAX-ACCESS read-only
			STATUS current
			DESCRIPTION
				"
				
				
				"
			::= { stpGlobalSetEntry 12 }

		
		-- 1.3.6.1.4.1.17409.2.3.9.1.1.13
		stpGlobalSetBridgeMaxAge OBJECT-TYPE
			SYNTAX Timeout (600..4000)
			UNITS "centi-seconds"
			MAX-ACCESS read-write
			STATUS current
			DESCRIPTION
				"
				"
			::= { stpGlobalSetEntry 13 }

		
		-- 1.3.6.1.4.1.17409.2.3.9.1.1.14
		stpGlobalSetBridgeHelloTime OBJECT-TYPE
			SYNTAX Timeout (100..1000)
			UNITS "centi-seconds"
			MAX-ACCESS read-write
			STATUS current
			DESCRIPTION
				"
				"
			::= { stpGlobalSetEntry 14 }

		
		-- 1.3.6.1.4.1.17409.2.3.9.1.1.15
		stpGlobalSetBridgeForwardDelay OBJECT-TYPE
			SYNTAX Timeout (400..3000)
			UNITS "centi-seconds"
			MAX-ACCESS read-write
			STATUS current
			DESCRIPTION
				"
				"
			::= { stpGlobalSetEntry 15 }

		
		-- 1.3.6.1.4.1.17409.2.3.9.1.1.16
		stpGlobalSetRstpTxHoldCount OBJECT-TYPE
			SYNTAX INTEGER (1..10)
			MAX-ACCESS read-write
			STATUS current
			DESCRIPTION
				"
				RSTP"
			DEFVAL { 3 }
			::= { stpGlobalSetEntry 16 }

		
		-- 1.3.6.1.4.1.17409.2.3.9.1.1.17
		stpGlobalSetEnable OBJECT-TYPE
			SYNTAX TruthValue
			MAX-ACCESS read-write
			STATUS current
			DESCRIPTION
				"
				STPtrue(1)"
			::= { stpGlobalSetEntry 17 }

		
		-- 1.3.6.1.4.1.17409.2.3.9.2
		stpPortTable OBJECT-TYPE
			SYNTAX SEQUENCE OF StpPortEntry
			MAX-ACCESS not-accessible
			STATUS current
			DESCRIPTION
				"
				STP"
			::= { stpManagementObjects 2 }

		
		-- 1.3.6.1.4.1.17409.2.3.9.2.1
		stpPortEntry OBJECT-TYPE
			SYNTAX StpPortEntry
			MAX-ACCESS not-accessible
			STATUS current
			DESCRIPTION			" "
			INDEX { stpPortStpIndex, stpPortCardIndex, stpPortIndex }
			::= { stpPortTable 1 }

		
		StpPortEntry ::=
			SEQUENCE { 
				stpPortStpIndex
					EponDeviceIndex,
				stpPortCardIndex
					EponCardIndex,
				stpPortIndex
					EponPortIndex,
				stpPortStatus
					INTEGER,
				stpPortPriority
					INTEGER,
				stpPortPathCost
					INTEGER,
				stpPortDesignatedRoot
					BridgeId,
				stpPortDesignatedCost
					INTEGER,
				stpPortDesignatedBridge
					BridgeId,
				stpPortDesignatedPort
					Gauge32,
				stpPortForwardTransitions
					Unsigned32,
				stpPortRstpProtocolMigration
					TruthValue,
				stpPortRstpAdminEdgePort
					TruthValue,
				stpPortRstpOperEdgePort
					TruthValue,
				stpPortPointToPointAdminStatus
					INTEGER,
				stpPortPointToPointOperStatus
					TruthValue,
				stpPortEnabled
					TruthValue
			 }

		-- 1.3.6.1.4.1.17409.2.3.9.2.1.1
		stpPortStpIndex OBJECT-TYPE
			SYNTAX EponDeviceIndex (1..2147483647)
			MAX-ACCESS not-accessible
			STATUS current
			DESCRIPTION
				"
				        
				For OLT - Set to corresponding device/SLOT/PORT
				For ONU - Set to 0
				"
			::= { stpPortEntry 1 }

		
		-- 1.3.6.1.4.1.17409.2.3.9.2.1.2
		stpPortCardIndex OBJECT-TYPE
			SYNTAX EponCardIndex (1..255)
			MAX-ACCESS not-accessible
			STATUS current
			DESCRIPTION
				"
				Epon        
				For OLT, set to 0
				For ONU, set to correspond card index"
			::= { stpPortEntry 2 }

		
		-- 1.3.6.1.4.1.17409.2.3.9.2.1.3
		stpPortIndex OBJECT-TYPE
			SYNTAX EponPortIndex (1..2147483647)
			MAX-ACCESS not-accessible
			STATUS current
			DESCRIPTION
				"
				OLTSNI/PON portONUUNI        
				For OLT, set to 0
				For ONU, set to correspond port index"
			::= { stpPortEntry 3 }

		
		-- 1.3.6.1.4.1.17409.2.3.9.2.1.4
		stpPortStatus OBJECT-TYPE
			SYNTAX INTEGER
				{
				disabled(1),
				blocking(2),
				listening(3),
				learning(4),
				forwarding(5),
				broken(6)
				}
			MAX-ACCESS read-only
			STATUS current
			DESCRIPTION
				"
				STPdisable"
			::= { stpPortEntry 4 }

		
		-- 1.3.6.1.4.1.17409.2.3.9.2.1.5
		stpPortPriority OBJECT-TYPE
			SYNTAX INTEGER (0..240)
			MAX-ACCESS read-write
			STATUS current
			DESCRIPTION
				"
				"
			::= { stpPortEntry 5 }

		
		-- 1.3.6.1.4.1.17409.2.3.9.2.1.6
		stpPortPathCost OBJECT-TYPE
			SYNTAX INTEGER (1..200000000)
			MAX-ACCESS read-write
			STATUS current
			DESCRIPTION
				"
				802.1D-1998LAN"
			::= { stpPortEntry 6 }

		
		-- 1.3.6.1.4.1.17409.2.3.9.2.1.7
		stpPortDesignatedRoot OBJECT-TYPE
			SYNTAX BridgeId
			MAX-ACCESS read-only
			STATUS current
			DESCRIPTION
				"
				BPDUBPDU"
			::= { stpPortEntry 7 }

		
		-- 1.3.6.1.4.1.17409.2.3.9.2.1.8
		stpPortDesignatedCost OBJECT-TYPE
			SYNTAX INTEGER
			MAX-ACCESS read-only
			STATUS current
			DESCRIPTION
				"
				PDU"
			::= { stpPortEntry 8 }

		
		-- 1.3.6.1.4.1.17409.2.3.9.2.1.9
		stpPortDesignatedBridge OBJECT-TYPE
			SYNTAX BridgeId
			MAX-ACCESS read-only
			STATUS current
			DESCRIPTION
				"
				ID"
			::= { stpPortEntry 9 }

		
		-- 1.3.6.1.4.1.17409.2.3.9.2.1.10
		stpPortDesignatedPort OBJECT-TYPE
			SYNTAX Gauge32
			MAX-ACCESS read-only
			STATUS current
			DESCRIPTION
				"
				"
			::= { stpPortEntry 10 }

		
		-- 1.3.6.1.4.1.17409.2.3.9.2.1.11
		stpPortForwardTransitions OBJECT-TYPE
			SYNTAX Unsigned32
			UNITS "seconds"
			MAX-ACCESS read-only
			STATUS current
			DESCRIPTION
				"
				"
			::= { stpPortEntry 11 }

		
		-- 1.3.6.1.4.1.17409.2.3.9.2.1.12
		stpPortRstpProtocolMigration OBJECT-TYPE
			SYNTAX TruthValue
			MAX-ACCESS read-write
			STATUS current
			DESCRIPTION
				"
				RSTPTRUE(1)RSTP BPDUFALSE(2)"
			::= { stpPortEntry 12 }

		
		-- 1.3.6.1.4.1.17409.2.3.9.2.1.13
		stpPortRstpAdminEdgePort OBJECT-TYPE
			SYNTAX TruthValue
			MAX-ACCESS read-write
			STATUS current
			DESCRIPTION
				"
				stpPortRstpOperEdgePort
				        true(1)BPDUstpPortRstpOperEdgePortfalse(2)
				        "
			::= { stpPortEntry 13 }

		
		-- 1.3.6.1.4.1.17409.2.3.9.2.1.14
		stpPortRstpOperEdgePort OBJECT-TYPE
			SYNTAX TruthValue
			MAX-ACCESS read-only
			STATUS current
			DESCRIPTION
				"
				stpPortRstpAdminEdgePortBPDUfalse(2)"
			::= { stpPortEntry 14 }

		
		-- 1.3.6.1.4.1.17409.2.3.9.2.1.15
		stpPortPointToPointAdminStatus OBJECT-TYPE
			SYNTAX INTEGER
				{
				false(0),
				true(1),
				auto(2)
				}
			MAX-ACCESS read-write
			STATUS current
			DESCRIPTION
				"
				"
			::= { stpPortEntry 15 }

		
		-- 1.3.6.1.4.1.17409.2.3.9.2.1.16
		stpPortPointToPointOperStatus OBJECT-TYPE
			SYNTAX TruthValue
			MAX-ACCESS read-only
			STATUS current
			DESCRIPTION
				"
				"
			::= { stpPortEntry 16 }

		
		-- 1.3.6.1.4.1.17409.2.3.9.2.1.17
		stpPortEnabled OBJECT-TYPE
			SYNTAX TruthValue
			MAX-ACCESS read-write
			STATUS current
			DESCRIPTION
				"
				true(1)"
			::= { stpPortEntry 17 }

		
		-- 1.3.6.1.4.1.17409.2.3.10
		performanceStatisticObjects OBJECT IDENTIFIER ::= { eponTree 10 }

		
-- ------------------------------------------------------------------------------
-- performanceStatisticObjects[](1.3.6.1.4.1.17409.2.3.10)
-- ------------------------------------------------------------------------------ 
		-- 1.3.6.1.4.1.17409.2.3.10.1
		curStatsTable OBJECT-TYPE
			SYNTAX SEQUENCE OF CurStatsEntry
			MAX-ACCESS not-accessible
			STATUS current
			DESCRIPTION
				""
			::= { performanceStatisticObjects 1 }

		
		-- 1.3.6.1.4.1.17409.2.3.10.1.1
		curStatsEntry OBJECT-TYPE
			SYNTAX CurStatsEntry
			MAX-ACCESS not-accessible
			STATUS current
			DESCRIPTION
				""
			INDEX { curStatsDeviceIndex, curStatsCardIndex, curStatsPortIndex }
			::= { curStatsTable 1 }

		
		CurStatsEntry ::=
			SEQUENCE { 
				curStatsDeviceIndex
					EponDeviceIndex,
				curStatsCardIndex
					EponCardIndex,
				curStatsPortIndex
					EponPortIndex,
				curStatsInOctets
					Counter64,
				curStatsInPkts
					Counter64,
				curStatsInBroadcastPkts
					Counter64,
				curStatsInMulticastPkts
					Counter64,
				curStatsInPkts64Octets
					Counter64,
				curStatsInPkts65to127Octets
					Counter64,
				curStatsInPkts128to255Octets
					Counter64,
				curStatsInPkts256to511Octets
					Counter64,
				curStatsInPkts512to1023Octets
					Counter64,
				curStatsInPkts1024to1518Octets
					Counter64,
				curStatsInPkts1519to1522Octets
					Counter64,
				curStatsInUndersizePkts
					Counter64,
				curStatsInOversizePkts
					Counter64,
				curStatsInFragments
					Counter64,
				curStatsInMpcpFrames
					Counter64,
				curStatsInMpcpOctets
					Counter64,
				curStatsInOAMFrames
					Counter64,
				curStatsInOAMOctets
					Counter64,
				curStatsInCRCErrorPkts
					Counter64,
				curStatsInDropEvents
					Counter64,
				curStatsInJabbers
					Counter64,
				curStatsInCollision
					Counter64,
				curStatsOutOctets
					Counter64,
				curStatsOutPkts
					Counter64,
				curStatsOutBroadcastPkts
					Counter64,
				curStatsOutMulticastPkts
					Counter64,
				curStatsOutPkts64Octets
					Counter64,
				curStatsOutPkts65to127Octets
					Counter64,
				curStatsOutPkts128to255Octets
					Counter64,
				curStatsOutPkts256to511Octets
					Counter64,
				curStatsOutPkts512to1023Octets
					Counter64,
				curStatsOutPkts1024to1518Octets
					Counter64,
				curStatsOutPkts1519o1522Octets
					Counter64,
				curStatsOutUndersizePkts
					Counter64,
				curStatsOutOversizePkts
					Counter64,
				curStatsOutFragments
					Counter64,
				curStatsOutMpcpFrames
					Counter64,
				curStatsOutMpcpOctets
					Counter64,
				curStatsOutOAMFrames
					Counter64,
				curStatsOutOAMOctets
					Counter64,
				curStatsOutCRCErrorPkts
					Counter64,
				curStatsOutDropEvents
					Counter64,
				curStatsOutJabbers
					Counter64,
				curStatsOutCollision
					Counter64,
				curStatsStatusAndAction
					INTEGER
			 }

		-- 1.3.6.1.4.1.17409.2.3.10.1.1.1
		curStatsDeviceIndex OBJECT-TYPE
			SYNTAX EponDeviceIndex (1..2147483647)
			MAX-ACCESS not-accessible
			STATUS current
			DESCRIPTION
				"        
				For OLT, set to corresponding device/slot/port
				For ONU, set to 0"
			::= { curStatsEntry 1 }

		
		-- 1.3.6.1.4.1.17409.2.3.10.1.1.2
		curStatsCardIndex OBJECT-TYPE
			SYNTAX EponCardIndex (1..2147483647)
			MAX-ACCESS not-accessible
			STATUS current
			DESCRIPTION
				"        
				For OLT, set to 0
				For ONU, set to corresponding slot
				"
			::= { curStatsEntry 2 }

		
		-- 1.3.6.1.4.1.17409.2.3.10.1.1.3
		curStatsPortIndex OBJECT-TYPE
			SYNTAX EponPortIndex (1..2147483647)
			MAX-ACCESS not-accessible
			STATUS current
			DESCRIPTION
				"         
				For OLT, set to 0
				For ONU, set to corresponding port
				"
			::= { curStatsEntry 3 }

		
		-- 1.3.6.1.4.1.17409.2.3.10.1.1.4
		curStatsInOctets OBJECT-TYPE
			SYNTAX Counter64
			MAX-ACCESS read-only
			STATUS current
			DESCRIPTION
				""
			::= { curStatsEntry 4 }

		
		-- 1.3.6.1.4.1.17409.2.3.10.1.1.5
		curStatsInPkts OBJECT-TYPE
			SYNTAX Counter64
			MAX-ACCESS read-only
			STATUS current
			DESCRIPTION
				""
			::= { curStatsEntry 5 }

		
		-- 1.3.6.1.4.1.17409.2.3.10.1.1.6
		curStatsInBroadcastPkts OBJECT-TYPE
			SYNTAX Counter64
			MAX-ACCESS read-only
			STATUS current
			DESCRIPTION
				""
			::= { curStatsEntry 6 }

		
		-- 1.3.6.1.4.1.17409.2.3.10.1.1.7
		curStatsInMulticastPkts OBJECT-TYPE
			SYNTAX Counter64
			MAX-ACCESS read-only
			STATUS current
			DESCRIPTION
				""
			::= { curStatsEntry 7 }

		
		-- 1.3.6.1.4.1.17409.2.3.10.1.1.8
		curStatsInPkts64Octets OBJECT-TYPE
			SYNTAX Counter64
			MAX-ACCESS read-only
			STATUS current
			DESCRIPTION
				"64"
			::= { curStatsEntry 8 }

		
		-- 1.3.6.1.4.1.17409.2.3.10.1.1.9
		curStatsInPkts65to127Octets OBJECT-TYPE
			SYNTAX Counter64
			MAX-ACCESS read-only
			STATUS current
			DESCRIPTION
				"65127"
			::= { curStatsEntry 9 }

		
		-- 1.3.6.1.4.1.17409.2.3.10.1.1.10
		curStatsInPkts128to255Octets OBJECT-TYPE
			SYNTAX Counter64
			MAX-ACCESS read-only
			STATUS current
			DESCRIPTION
				"128255"
			::= { curStatsEntry 10 }

		
		-- 1.3.6.1.4.1.17409.2.3.10.1.1.11
		curStatsInPkts256to511Octets OBJECT-TYPE
			SYNTAX Counter64
			MAX-ACCESS read-only
			STATUS current
			DESCRIPTION
				"256511"
			::= { curStatsEntry 11 }

		
		-- 1.3.6.1.4.1.17409.2.3.10.1.1.12
		curStatsInPkts512to1023Octets OBJECT-TYPE
			SYNTAX Counter64
			MAX-ACCESS read-only
			STATUS current
			DESCRIPTION
				"5121023"
			::= { curStatsEntry 12 }

		
		-- 1.3.6.1.4.1.17409.2.3.10.1.1.13
		curStatsInPkts1024to1518Octets OBJECT-TYPE
			SYNTAX Counter64
			MAX-ACCESS read-only
			STATUS current
			DESCRIPTION
				"10241518"
			::= { curStatsEntry 13 }

		
		-- 1.3.6.1.4.1.17409.2.3.10.1.1.14
		curStatsInPkts1519to1522Octets OBJECT-TYPE
			SYNTAX Counter64
			MAX-ACCESS read-only
			STATUS current
			DESCRIPTION
				"15191522"
			::= { curStatsEntry 14 }

		
		-- 1.3.6.1.4.1.17409.2.3.10.1.1.15
		curStatsInUndersizePkts OBJECT-TYPE
			SYNTAX Counter64
			MAX-ACCESS read-only
			STATUS current
			DESCRIPTION
				""
			::= { curStatsEntry 15 }

		
		-- 1.3.6.1.4.1.17409.2.3.10.1.1.16
		curStatsInOversizePkts OBJECT-TYPE
			SYNTAX Counter64
			MAX-ACCESS read-only
			STATUS current
			DESCRIPTION
				""
			::= { curStatsEntry 16 }

		
		-- 1.3.6.1.4.1.17409.2.3.10.1.1.17
		curStatsInFragments OBJECT-TYPE
			SYNTAX Counter64
			MAX-ACCESS read-only
			STATUS current
			DESCRIPTION
				""
			::= { curStatsEntry 17 }

		
		-- 1.3.6.1.4.1.17409.2.3.10.1.1.18
		curStatsInMpcpFrames OBJECT-TYPE
			SYNTAX Counter64
			MAX-ACCESS read-only
			STATUS current
			DESCRIPTION
				"MPCP"
			::= { curStatsEntry 18 }

		
		-- 1.3.6.1.4.1.17409.2.3.10.1.1.19
		curStatsInMpcpOctets OBJECT-TYPE
			SYNTAX Counter64
			MAX-ACCESS read-only
			STATUS current
			DESCRIPTION
				"MPCP"
			::= { curStatsEntry 19 }

		
		-- 1.3.6.1.4.1.17409.2.3.10.1.1.20
		curStatsInOAMFrames OBJECT-TYPE
			SYNTAX Counter64
			MAX-ACCESS read-only
			STATUS current
			DESCRIPTION
				"OAM"
			::= { curStatsEntry 20 }

		
		-- 1.3.6.1.4.1.17409.2.3.10.1.1.21
		curStatsInOAMOctets OBJECT-TYPE
			SYNTAX Counter64
			MAX-ACCESS read-only
			STATUS current
			DESCRIPTION
				"OAM"
			::= { curStatsEntry 21 }

		
		-- 1.3.6.1.4.1.17409.2.3.10.1.1.22
		curStatsInCRCErrorPkts OBJECT-TYPE
			SYNTAX Counter64
			MAX-ACCESS read-only
			STATUS current
			DESCRIPTION
				"CRC"
			::= { curStatsEntry 22 }

		
		-- 1.3.6.1.4.1.17409.2.3.10.1.1.23
		curStatsInDropEvents OBJECT-TYPE
			SYNTAX Counter64
			MAX-ACCESS read-only
			STATUS current
			DESCRIPTION
				""
			::= { curStatsEntry 23 }

		
		-- 1.3.6.1.4.1.17409.2.3.10.1.1.24
		curStatsInJabbers OBJECT-TYPE
			SYNTAX Counter64
			MAX-ACCESS read-only
			STATUS current
			DESCRIPTION
				""
			::= { curStatsEntry 24 }

		
		-- 1.3.6.1.4.1.17409.2.3.10.1.1.25
		curStatsInCollision OBJECT-TYPE
			SYNTAX Counter64
			MAX-ACCESS read-only
			STATUS current
			DESCRIPTION
				""
			::= { curStatsEntry 25 }

		
		-- 1.3.6.1.4.1.17409.2.3.10.1.1.26
		curStatsOutOctets OBJECT-TYPE
			SYNTAX Counter64
			MAX-ACCESS read-only
			STATUS current
			DESCRIPTION
				""
			::= { curStatsEntry 26 }

		
		-- 1.3.6.1.4.1.17409.2.3.10.1.1.27
		curStatsOutPkts OBJECT-TYPE
			SYNTAX Counter64
			MAX-ACCESS read-only
			STATUS current
			DESCRIPTION
				""
			::= { curStatsEntry 27 }

		
		-- 1.3.6.1.4.1.17409.2.3.10.1.1.28
		curStatsOutBroadcastPkts OBJECT-TYPE
			SYNTAX Counter64
			MAX-ACCESS read-only
			STATUS current
			DESCRIPTION
				""
			::= { curStatsEntry 28 }

		
		-- 1.3.6.1.4.1.17409.2.3.10.1.1.29
		curStatsOutMulticastPkts OBJECT-TYPE
			SYNTAX Counter64
			MAX-ACCESS read-only
			STATUS current
			DESCRIPTION
				""
			::= { curStatsEntry 29 }

		
		-- 1.3.6.1.4.1.17409.2.3.10.1.1.30
		curStatsOutPkts64Octets OBJECT-TYPE
			SYNTAX Counter64
			MAX-ACCESS read-only
			STATUS current
			DESCRIPTION
				"64"
			::= { curStatsEntry 30 }

		
		-- 1.3.6.1.4.1.17409.2.3.10.1.1.31
		curStatsOutPkts65to127Octets OBJECT-TYPE
			SYNTAX Counter64
			MAX-ACCESS read-only
			STATUS current
			DESCRIPTION
				"65127"
			::= { curStatsEntry 31 }

		
		-- 1.3.6.1.4.1.17409.2.3.10.1.1.32
		curStatsOutPkts128to255Octets OBJECT-TYPE
			SYNTAX Counter64
			MAX-ACCESS read-only
			STATUS current
			DESCRIPTION
				"128255"
			::= { curStatsEntry 32 }

		
		-- 1.3.6.1.4.1.17409.2.3.10.1.1.33
		curStatsOutPkts256to511Octets OBJECT-TYPE
			SYNTAX Counter64
			MAX-ACCESS read-only
			STATUS current
			DESCRIPTION
				"256511"
			::= { curStatsEntry 33 }

		
		-- 1.3.6.1.4.1.17409.2.3.10.1.1.34
		curStatsOutPkts512to1023Octets OBJECT-TYPE
			SYNTAX Counter64
			MAX-ACCESS read-only
			STATUS current
			DESCRIPTION
				"5121023"
			::= { curStatsEntry 34 }

		
		-- 1.3.6.1.4.1.17409.2.3.10.1.1.35
		curStatsOutPkts1024to1518Octets OBJECT-TYPE
			SYNTAX Counter64
			MAX-ACCESS read-only
			STATUS current
			DESCRIPTION
				"10241518"
			::= { curStatsEntry 35 }

		
		-- 1.3.6.1.4.1.17409.2.3.10.1.1.36
		curStatsOutPkts1519o1522Octets OBJECT-TYPE
			SYNTAX Counter64
			MAX-ACCESS read-only
			STATUS current
			DESCRIPTION
				"15191522"
			::= { curStatsEntry 36 }

		
		-- 1.3.6.1.4.1.17409.2.3.10.1.1.37
		curStatsOutUndersizePkts OBJECT-TYPE
			SYNTAX Counter64
			MAX-ACCESS read-only
			STATUS current
			DESCRIPTION
				""
			::= { curStatsEntry 37 }

		
		-- 1.3.6.1.4.1.17409.2.3.10.1.1.38
		curStatsOutOversizePkts OBJECT-TYPE
			SYNTAX Counter64
			MAX-ACCESS read-only
			STATUS current
			DESCRIPTION
				""
			::= { curStatsEntry 38 }

		
		-- 1.3.6.1.4.1.17409.2.3.10.1.1.39
		curStatsOutFragments OBJECT-TYPE
			SYNTAX Counter64
			MAX-ACCESS read-only
			STATUS current
			DESCRIPTION
				""
			::= { curStatsEntry 39 }

		
		-- 1.3.6.1.4.1.17409.2.3.10.1.1.40
		curStatsOutMpcpFrames OBJECT-TYPE
			SYNTAX Counter64
			MAX-ACCESS read-only
			STATUS current
			DESCRIPTION
				"MPCP"
			::= { curStatsEntry 40 }

		
		-- 1.3.6.1.4.1.17409.2.3.10.1.1.41
		curStatsOutMpcpOctets OBJECT-TYPE
			SYNTAX Counter64
			MAX-ACCESS read-only
			STATUS current
			DESCRIPTION
				"MPCP"
			::= { curStatsEntry 41 }

		
		-- 1.3.6.1.4.1.17409.2.3.10.1.1.42
		curStatsOutOAMFrames OBJECT-TYPE
			SYNTAX Counter64
			MAX-ACCESS read-only
			STATUS current
			DESCRIPTION
				"OAM"
			::= { curStatsEntry 42 }

		
		-- 1.3.6.1.4.1.17409.2.3.10.1.1.43
		curStatsOutOAMOctets OBJECT-TYPE
			SYNTAX Counter64
			MAX-ACCESS read-only
			STATUS current
			DESCRIPTION
				"OAM"
			::= { curStatsEntry 43 }

		
		-- 1.3.6.1.4.1.17409.2.3.10.1.1.44
		curStatsOutCRCErrorPkts OBJECT-TYPE
			SYNTAX Counter64
			MAX-ACCESS read-only
			STATUS current
			DESCRIPTION
				"CRC"
			::= { curStatsEntry 44 }

		
		-- 1.3.6.1.4.1.17409.2.3.10.1.1.45
		curStatsOutDropEvents OBJECT-TYPE
			SYNTAX Counter64
			MAX-ACCESS read-only
			STATUS current
			DESCRIPTION
				""
			::= { curStatsEntry 45 }

		
		-- 1.3.6.1.4.1.17409.2.3.10.1.1.46
		curStatsOutJabbers OBJECT-TYPE
			SYNTAX Counter64
			MAX-ACCESS read-only
			STATUS current
			DESCRIPTION
				""
			::= { curStatsEntry 46 }

		
		-- 1.3.6.1.4.1.17409.2.3.10.1.1.47
		curStatsOutCollision OBJECT-TYPE
			SYNTAX Counter64
			MAX-ACCESS read-only
			STATUS current
			DESCRIPTION
				""
			::= { curStatsEntry 47 }

		
		-- 1.3.6.1.4.1.17409.2.3.10.1.1.48
		curStatsStatusAndAction OBJECT-TYPE
			SYNTAX INTEGER
				{
				none(1),
				clean(2)
				}
			MAX-ACCESS read-write
			STATUS current
			DESCRIPTION
				"
				clean(2) "
			::= { curStatsEntry 48 }

		
		-- 1.3.6.1.4.1.17409.2.3.10.2
		stats15Table OBJECT-TYPE
			SYNTAX SEQUENCE OF Stats15Entry
			MAX-ACCESS not-accessible
			STATUS current
			DESCRIPTION
				"15 minutes performance data"
			::= { performanceStatisticObjects 2 }

		
		-- 1.3.6.1.4.1.17409.2.3.10.2.1
		stats15Entry OBJECT-TYPE
			SYNTAX Stats15Entry
			MAX-ACCESS not-accessible
			STATUS current
			DESCRIPTION			" "
			INDEX { stats15DeviceIndex, stats15CardIndex, stats15PortIndex, stats15Index }
			::= { stats15Table 1 }

		
		Stats15Entry ::=
			SEQUENCE { 
				stats15DeviceIndex
					EponDeviceIndex,
				stats15CardIndex
					EponCardIndex,
				stats15PortIndex
					EponPortIndex,
				stats15Index
					EponStats15MinRecordType,
				stats15InOctets
					Counter64,
				stats15InPkts
					Counter64,
				stats15InBroadcastPkts
					Counter64,
				stats15InMulticastPkts
					Counter64,
				stats15InPkts64Octets
					Counter64,
				stats15InPkts65to127Octets
					Counter64,
				stats15InPkts128to255Octets
					Counter64,
				stats15InPkts256to511Octets
					Counter64,
				stats15InPkts512to1023Octets
					Counter64,
				stats15InPkts1024to1518Octets
					Counter64,
				stats15InPkts1519to1522Octets
					Counter64,
				stats15InUndersizePkts
					Counter64,
				stats15InOversizePkts
					Counter64,
				stats15InFragments
					Counter64,
				stats15InMpcpFrames
					Counter64,
				stats15InMpcpOctets
					Counter64,
				stats15InOAMFrames
					Counter64,
				stats15InOAMOctets
					Counter64,
				stats15InCRCErrorPkts
					Counter64,
				stats15InDropEvents
					Counter64,
				stats15InJabbers
					Counter64,
				stats15InCollision
					Counter64,
				stats15OutOctets
					Counter64,
				stats15OutPkts
					Counter64,
				stats15OutBroadcastPkts
					Counter64,
				stats15OutMulticastPkts
					Counter64,
				stats15OutPkts64Octets
					Counter64,
				stats15OutPkts65to127Octets
					Counter64,
				stats15OutPkts128to255Octets
					Counter64,
				stats15OutPkts256to511Octets
					Counter64,
				stats15OutPkts512to1023Octets
					Counter64,
				stats15OutPkts1024to1518Octets
					Counter64,
				stats15OutPkts1519o1522Octets
					Counter64,
				stats15OutUndersizePkts
					Counter64,
				stats15OutOversizePkts
					Counter64,
				stats15OutFragments
					Counter64,
				stats15OutMpcpFrames
					Counter64,
				stats15OutMpcpOctets
					Counter64,
				stats15OutOAMFrames
					Counter64,
				stats15OutOAMOctets
					Counter64,
				stats15OutCRCErrorPkts
					Counter64,
				stats15OutDropEvents
					Counter64,
				stats15OutJabbers
					Counter64,
				stats15OutCollision
					Counter64,
				stats15StatusAndAction
					INTEGER,
				stats15ValidityTag
					TruthValue,
				stats15ElapsedTime
					Counter32,
				stats15EndTime
					DateAndTime
			 }

		-- 1.3.6.1.4.1.17409.2.3.10.2.1.1
		stats15DeviceIndex OBJECT-TYPE
			SYNTAX EponDeviceIndex (1..2147483647)
			MAX-ACCESS not-accessible
			STATUS current
			DESCRIPTION
				"        
				For OLT, set to corresponding device/slot/port
				For ONU, set to 0       "
			::= { stats15Entry 1 }

		
		-- 1.3.6.1.4.1.17409.2.3.10.2.1.2
		stats15CardIndex OBJECT-TYPE
			SYNTAX EponCardIndex (1..2147483647)
			MAX-ACCESS not-accessible
			STATUS current
			DESCRIPTION
				"        
				For OLT, set to 0
				For ONU, set to corresponding slot
				"
			::= { stats15Entry 2 }

		
		-- 1.3.6.1.4.1.17409.2.3.10.2.1.3
		stats15PortIndex OBJECT-TYPE
			SYNTAX EponPortIndex (1..2147483647)
			MAX-ACCESS not-accessible
			STATUS current
			DESCRIPTION
				"        
				For OLT, set to 0
				For ONU, set to corresponding port
				"
			::= { stats15Entry 3 }

		
		-- 1.3.6.1.4.1.17409.2.3.10.2.1.4
		stats15Index OBJECT-TYPE
			SYNTAX EponStats15MinRecordType (1..2147483647)
			MAX-ACCESS not-accessible
			STATUS current
			DESCRIPTION
				"
				
				"
			::= { stats15Entry 4 }

		
		-- 1.3.6.1.4.1.17409.2.3.10.2.1.5
		stats15InOctets OBJECT-TYPE
			SYNTAX Counter64
			MAX-ACCESS read-only
			STATUS current
			DESCRIPTION
				""
			::= { stats15Entry 5 }

		
		-- 1.3.6.1.4.1.17409.2.3.10.2.1.6
		stats15InPkts OBJECT-TYPE
			SYNTAX Counter64
			MAX-ACCESS read-only
			STATUS current
			DESCRIPTION
				""
			::= { stats15Entry 6 }

		
		-- 1.3.6.1.4.1.17409.2.3.10.2.1.7
		stats15InBroadcastPkts OBJECT-TYPE
			SYNTAX Counter64
			MAX-ACCESS read-only
			STATUS current
			DESCRIPTION
				""
			::= { stats15Entry 7 }

		
		-- 1.3.6.1.4.1.17409.2.3.10.2.1.8
		stats15InMulticastPkts OBJECT-TYPE
			SYNTAX Counter64
			MAX-ACCESS read-only
			STATUS current
			DESCRIPTION
				""
			::= { stats15Entry 8 }

		
		-- 1.3.6.1.4.1.17409.2.3.10.2.1.9
		stats15InPkts64Octets OBJECT-TYPE
			SYNTAX Counter64
			MAX-ACCESS read-only
			STATUS current
			DESCRIPTION
				"64"
			::= { stats15Entry 9 }

		
		-- 1.3.6.1.4.1.17409.2.3.10.2.1.10
		stats15InPkts65to127Octets OBJECT-TYPE
			SYNTAX Counter64
			MAX-ACCESS read-only
			STATUS current
			DESCRIPTION
				"65127"
			::= { stats15Entry 10 }

		
		-- 1.3.6.1.4.1.17409.2.3.10.2.1.11
		stats15InPkts128to255Octets OBJECT-TYPE
			SYNTAX Counter64
			MAX-ACCESS read-only
			STATUS current
			DESCRIPTION
				"128255"
			::= { stats15Entry 11 }

		
		-- 1.3.6.1.4.1.17409.2.3.10.2.1.12
		stats15InPkts256to511Octets OBJECT-TYPE
			SYNTAX Counter64
			MAX-ACCESS read-only
			STATUS current
			DESCRIPTION
				"256511"
			::= { stats15Entry 12 }

		
		-- 1.3.6.1.4.1.17409.2.3.10.2.1.13
		stats15InPkts512to1023Octets OBJECT-TYPE
			SYNTAX Counter64
			MAX-ACCESS read-only
			STATUS current
			DESCRIPTION
				"5121023"
			::= { stats15Entry 13 }

		
		-- 1.3.6.1.4.1.17409.2.3.10.2.1.14
		stats15InPkts1024to1518Octets OBJECT-TYPE
			SYNTAX Counter64
			MAX-ACCESS read-only
			STATUS current
			DESCRIPTION
				"10241518"
			::= { stats15Entry 14 }

		
		-- 1.3.6.1.4.1.17409.2.3.10.2.1.15
		stats15InPkts1519to1522Octets OBJECT-TYPE
			SYNTAX Counter64
			MAX-ACCESS read-only
			STATUS current
			DESCRIPTION
				"15191522"
			::= { stats15Entry 15 }

		
		-- 1.3.6.1.4.1.17409.2.3.10.2.1.16
		stats15InUndersizePkts OBJECT-TYPE
			SYNTAX Counter64
			MAX-ACCESS read-only
			STATUS current
			DESCRIPTION
				""
			::= { stats15Entry 16 }

		
		-- 1.3.6.1.4.1.17409.2.3.10.2.1.17
		stats15InOversizePkts OBJECT-TYPE
			SYNTAX Counter64
			MAX-ACCESS read-only
			STATUS current
			DESCRIPTION
				""
			::= { stats15Entry 17 }

		
		-- 1.3.6.1.4.1.17409.2.3.10.2.1.18
		stats15InFragments OBJECT-TYPE
			SYNTAX Counter64
			MAX-ACCESS read-only
			STATUS current
			DESCRIPTION
				""
			::= { stats15Entry 18 }

		
		-- 1.3.6.1.4.1.17409.2.3.10.2.1.19
		stats15InMpcpFrames OBJECT-TYPE
			SYNTAX Counter64
			MAX-ACCESS read-only
			STATUS current
			DESCRIPTION
				"MPCP"
			::= { stats15Entry 19 }

		
		-- 1.3.6.1.4.1.17409.2.3.10.2.1.20
		stats15InMpcpOctets OBJECT-TYPE
			SYNTAX Counter64
			MAX-ACCESS read-only
			STATUS current
			DESCRIPTION
				"MPCP"
			::= { stats15Entry 20 }

		
		-- 1.3.6.1.4.1.17409.2.3.10.2.1.21
		stats15InOAMFrames OBJECT-TYPE
			SYNTAX Counter64
			MAX-ACCESS read-only
			STATUS current
			DESCRIPTION
				"OAM"
			::= { stats15Entry 21 }

		
		-- 1.3.6.1.4.1.17409.2.3.10.2.1.22
		stats15InOAMOctets OBJECT-TYPE
			SYNTAX Counter64
			MAX-ACCESS read-only
			STATUS current
			DESCRIPTION
				"OAM"
			::= { stats15Entry 22 }

		
		-- 1.3.6.1.4.1.17409.2.3.10.2.1.23
		stats15InCRCErrorPkts OBJECT-TYPE
			SYNTAX Counter64
			MAX-ACCESS read-only
			STATUS current
			DESCRIPTION
				"CRC"
			::= { stats15Entry 23 }

		
		-- 1.3.6.1.4.1.17409.2.3.10.2.1.24
		stats15InDropEvents OBJECT-TYPE
			SYNTAX Counter64
			MAX-ACCESS read-only
			STATUS current
			DESCRIPTION
				""
			::= { stats15Entry 24 }

		
		-- 1.3.6.1.4.1.17409.2.3.10.2.1.25
		stats15InJabbers OBJECT-TYPE
			SYNTAX Counter64
			MAX-ACCESS read-only
			STATUS current
			DESCRIPTION
				""
			::= { stats15Entry 25 }

		
		-- 1.3.6.1.4.1.17409.2.3.10.2.1.26
		stats15InCollision OBJECT-TYPE
			SYNTAX Counter64
			MAX-ACCESS read-only
			STATUS current
			DESCRIPTION
				""
			::= { stats15Entry 26 }

		
		-- 1.3.6.1.4.1.17409.2.3.10.2.1.27
		stats15OutOctets OBJECT-TYPE
			SYNTAX Counter64
			MAX-ACCESS read-only
			STATUS current
			DESCRIPTION
				""
			::= { stats15Entry 27 }

		
		-- 1.3.6.1.4.1.17409.2.3.10.2.1.28
		stats15OutPkts OBJECT-TYPE
			SYNTAX Counter64
			MAX-ACCESS read-only
			STATUS current
			DESCRIPTION
				""
			::= { stats15Entry 28 }

		
		-- 1.3.6.1.4.1.17409.2.3.10.2.1.29
		stats15OutBroadcastPkts OBJECT-TYPE
			SYNTAX Counter64
			MAX-ACCESS read-only
			STATUS current
			DESCRIPTION
				""
			::= { stats15Entry 29 }

		
		-- 1.3.6.1.4.1.17409.2.3.10.2.1.30
		stats15OutMulticastPkts OBJECT-TYPE
			SYNTAX Counter64
			MAX-ACCESS read-only
			STATUS current
			DESCRIPTION
				""
			::= { stats15Entry 30 }

		
		-- 1.3.6.1.4.1.17409.2.3.10.2.1.31
		stats15OutPkts64Octets OBJECT-TYPE
			SYNTAX Counter64
			MAX-ACCESS read-only
			STATUS current
			DESCRIPTION
				"64"
			::= { stats15Entry 31 }

		
		-- 1.3.6.1.4.1.17409.2.3.10.2.1.32
		stats15OutPkts65to127Octets OBJECT-TYPE
			SYNTAX Counter64
			MAX-ACCESS read-only
			STATUS current
			DESCRIPTION
				"65127"
			::= { stats15Entry 32 }

		
		-- 1.3.6.1.4.1.17409.2.3.10.2.1.33
		stats15OutPkts128to255Octets OBJECT-TYPE
			SYNTAX Counter64
			MAX-ACCESS read-only
			STATUS current
			DESCRIPTION
				"128255"
			::= { stats15Entry 33 }

		
		-- 1.3.6.1.4.1.17409.2.3.10.2.1.34
		stats15OutPkts256to511Octets OBJECT-TYPE
			SYNTAX Counter64
			MAX-ACCESS read-only
			STATUS current
			DESCRIPTION
				"256511"
			::= { stats15Entry 34 }

		
		-- 1.3.6.1.4.1.17409.2.3.10.2.1.35
		stats15OutPkts512to1023Octets OBJECT-TYPE
			SYNTAX Counter64
			MAX-ACCESS read-only
			STATUS current
			DESCRIPTION
				"5121023"
			::= { stats15Entry 35 }

		
		-- 1.3.6.1.4.1.17409.2.3.10.2.1.36
		stats15OutPkts1024to1518Octets OBJECT-TYPE
			SYNTAX Counter64
			MAX-ACCESS read-only
			STATUS current
			DESCRIPTION
				"10241518"
			::= { stats15Entry 36 }

		
		-- 1.3.6.1.4.1.17409.2.3.10.2.1.37
		stats15OutPkts1519o1522Octets OBJECT-TYPE
			SYNTAX Counter64
			MAX-ACCESS read-only
			STATUS current
			DESCRIPTION
				"15191522"
			::= { stats15Entry 37 }

		
		-- 1.3.6.1.4.1.17409.2.3.10.2.1.38
		stats15OutUndersizePkts OBJECT-TYPE
			SYNTAX Counter64
			MAX-ACCESS read-only
			STATUS current
			DESCRIPTION
				""
			::= { stats15Entry 38 }

		
		-- 1.3.6.1.4.1.17409.2.3.10.2.1.39
		stats15OutOversizePkts OBJECT-TYPE
			SYNTAX Counter64
			MAX-ACCESS read-only
			STATUS current
			DESCRIPTION
				""
			::= { stats15Entry 39 }

		
		-- 1.3.6.1.4.1.17409.2.3.10.2.1.40
		stats15OutFragments OBJECT-TYPE
			SYNTAX Counter64
			MAX-ACCESS read-only
			STATUS current
			DESCRIPTION
				""
			::= { stats15Entry 40 }

		
		-- 1.3.6.1.4.1.17409.2.3.10.2.1.41
		stats15OutMpcpFrames OBJECT-TYPE
			SYNTAX Counter64
			MAX-ACCESS read-only
			STATUS current
			DESCRIPTION
				"MPCP"
			::= { stats15Entry 41 }

		
		-- 1.3.6.1.4.1.17409.2.3.10.2.1.42
		stats15OutMpcpOctets OBJECT-TYPE
			SYNTAX Counter64
			MAX-ACCESS read-only
			STATUS current
			DESCRIPTION
				"MPCP"
			::= { stats15Entry 42 }

		
		-- 1.3.6.1.4.1.17409.2.3.10.2.1.43
		stats15OutOAMFrames OBJECT-TYPE
			SYNTAX Counter64
			MAX-ACCESS read-only
			STATUS current
			DESCRIPTION
				"OAM"
			::= { stats15Entry 43 }

		
		-- 1.3.6.1.4.1.17409.2.3.10.2.1.44
		stats15OutOAMOctets OBJECT-TYPE
			SYNTAX Counter64
			MAX-ACCESS read-only
			STATUS current
			DESCRIPTION
				"OAM"
			::= { stats15Entry 44 }

		
		-- 1.3.6.1.4.1.17409.2.3.10.2.1.45
		stats15OutCRCErrorPkts OBJECT-TYPE
			SYNTAX Counter64
			MAX-ACCESS read-only
			STATUS current
			DESCRIPTION
				"CRC"
			::= { stats15Entry 45 }

		
		-- 1.3.6.1.4.1.17409.2.3.10.2.1.46
		stats15OutDropEvents OBJECT-TYPE
			SYNTAX Counter64
			MAX-ACCESS read-only
			STATUS current
			DESCRIPTION
				""
			::= { stats15Entry 46 }

		
		-- 1.3.6.1.4.1.17409.2.3.10.2.1.47
		stats15OutJabbers OBJECT-TYPE
			SYNTAX Counter64
			MAX-ACCESS read-only
			STATUS current
			DESCRIPTION
				""
			::= { stats15Entry 47 }

		
		-- 1.3.6.1.4.1.17409.2.3.10.2.1.48
		stats15OutCollision OBJECT-TYPE
			SYNTAX Counter64
			MAX-ACCESS read-only
			STATUS current
			DESCRIPTION
				""
			::= { stats15Entry 48 }

		
		-- 1.3.6.1.4.1.17409.2.3.10.2.1.49
		stats15StatusAndAction OBJECT-TYPE
			SYNTAX INTEGER
				{
				none(1),
				clean(2)
				}
			MAX-ACCESS read-write
			STATUS current
			DESCRIPTION
				"
				clean(2) "
			::= { stats15Entry 49 }

		
		-- 1.3.6.1.4.1.17409.2.3.10.2.1.50
		stats15ValidityTag OBJECT-TYPE
			SYNTAX TruthValue
			MAX-ACCESS read-only
			STATUS current
			DESCRIPTION
				"Whether or not the current 15-min PM data is valid"
			::= { stats15Entry 50 }

		
		-- 1.3.6.1.4.1.17409.2.3.10.2.1.51
		stats15ElapsedTime OBJECT-TYPE
			SYNTAX Counter32
			UNITS "seconds"
			MAX-ACCESS read-only
			STATUS current
			DESCRIPTION
				"
				It is elapsed time, since start of this 15-min interval.
				It is only valid for current PM data. For history PM data, set to 0.
				"
			::= { stats15Entry 51 }

		
		-- 1.3.6.1.4.1.17409.2.3.10.2.1.52
		stats15EndTime OBJECT-TYPE
			SYNTAX DateAndTime
			MAX-ACCESS read-only
			STATUS current
			DESCRIPTION
				"
				It is time, when the PM history data is created.
				It is only valid for history PM data.
				"
			::= { stats15Entry 52 }

		
		-- 1.3.6.1.4.1.17409.2.3.10.3
		stats24Table OBJECT-TYPE
			SYNTAX SEQUENCE OF Stats24Entry
			MAX-ACCESS not-accessible
			STATUS current
			DESCRIPTION
				"1-day performance data"
			::= { performanceStatisticObjects 3 }

		
		-- 1.3.6.1.4.1.17409.2.3.10.3.1
		stats24Entry OBJECT-TYPE
			SYNTAX Stats24Entry
			MAX-ACCESS not-accessible
			STATUS current
			DESCRIPTION			" "
			INDEX { stats24DeviceIndex, stats24CardIndex, stats24PortIndex, stats24Index }
			::= { stats24Table 1 }

		
		Stats24Entry ::=
			SEQUENCE { 
				stats24DeviceIndex
					EponDeviceIndex,
				stats24CardIndex
					EponCardIndex,
				stats24PortIndex
					EponPortIndex,
				stats24Index
					EponStats24HourRecordType,
				stats24InOctets
					Counter64,
				stats24InPkts
					Counter64,
				stats24InBroadcastPkts
					Counter64,
				stats24InMulticastPkts
					Counter64,
				stats24InPkts64Octets
					Counter64,
				stats24InPkts65to127Octets
					Counter64,
				stats24InPkts128to255Octets
					Counter64,
				stats24InPkts256to511Octets
					Counter64,
				stats24InPkts512to1023Octets
					Counter64,
				stats24InPkts1024to1518Octets
					Counter64,
				stats24InPkts1519to1522Octets
					Counter64,
				stats24InUndersizePkts
					Counter64,
				stats24InOversizePkts
					Counter64,
				stats24InFragments
					Counter64,
				stats24InMpcpFrames
					Counter64,
				stats24InMpcpOctets
					Counter64,
				stats24InOAMFrames
					Counter64,
				stats24InOAMOctets
					Counter64,
				stats24InCRCErrorPkts
					Counter64,
				stats24InDropEvents
					Counter64,
				stats24InJabbers
					Counter64,
				stats24InCollision
					Counter64,
				stats24OutOctets
					Counter64,
				stats24OutPkts
					Counter64,
				stats24OutBroadcastPkts
					Counter64,
				stats24OutMulticastPkts
					Counter64,
				stats24OutPkts64Octets
					Counter64,
				stats24OutPkts65to127Octets
					Counter64,
				stats24OutPkts128to255Octets
					Counter64,
				stats24OutPkts256to511Octets
					Counter64,
				stats24OutPkts512to1023Octets
					Counter64,
				stats24OutPkts1024to1518Octets
					Counter64,
				stats24OutPkts1519o1522Octets
					Counter64,
				stats24OutUndersizePkts
					Counter64,
				stats24OutOversizePkts
					Counter64,
				stats24OutFragments
					Counter64,
				stats24OutMpcpFrames
					Counter64,
				stats24OutMpcpOctets
					Counter64,
				stats24OutOAMFrames
					Counter64,
				stats24OutOAMOctets
					Counter64,
				stats24OutCRCErrorPkts
					Counter64,
				stats24OutDropEvents
					Counter64,
				stats24OutJabbers
					Counter64,
				stats24OutCollision
					Counter64,
				stats24StatusAndAction
					INTEGER,
				stats24ValidityTag
					TruthValue,
				stats24ElapsedTime
					Counter32,
				stats24EndTime
					DateAndTime
			 }

		-- 1.3.6.1.4.1.17409.2.3.10.3.1.1
		stats24DeviceIndex OBJECT-TYPE
			SYNTAX EponDeviceIndex (1..2147483647)
			MAX-ACCESS not-accessible
			STATUS current
			DESCRIPTION
				"        
				For OLT, set to corresponding device/slot/port
				For ONU, set to 0
				"
			::= { stats24Entry 1 }

		
		-- 1.3.6.1.4.1.17409.2.3.10.3.1.2
		stats24CardIndex OBJECT-TYPE
			SYNTAX EponCardIndex (1..2147483647)
			MAX-ACCESS not-accessible
			STATUS current
			DESCRIPTION
				"        
				For OLT, set to 0
				For ONU, set to corresponding slot
				"
			::= { stats24Entry 2 }

		
		-- 1.3.6.1.4.1.17409.2.3.10.3.1.3
		stats24PortIndex OBJECT-TYPE
			SYNTAX EponPortIndex (1..2147483647)
			MAX-ACCESS not-accessible
			STATUS current
			DESCRIPTION
				"        
				For OLT, set to 0
				For ONU, set to corresponding port
				"
			::= { stats24Entry 3 }

		
		-- 1.3.6.1.4.1.17409.2.3.10.3.1.4
		stats24Index OBJECT-TYPE
			SYNTAX EponStats24HourRecordType (1..2147483647)
			MAX-ACCESS not-accessible
			STATUS current
			DESCRIPTION
				""
			::= { stats24Entry 4 }

		
		-- 1.3.6.1.4.1.17409.2.3.10.3.1.5
		stats24InOctets OBJECT-TYPE
			SYNTAX Counter64
			MAX-ACCESS read-only
			STATUS current
			DESCRIPTION
				""
			::= { stats24Entry 5 }

		
		-- 1.3.6.1.4.1.17409.2.3.10.3.1.6
		stats24InPkts OBJECT-TYPE
			SYNTAX Counter64
			MAX-ACCESS read-only
			STATUS current
			DESCRIPTION
				""
			::= { stats24Entry 6 }

		
		-- 1.3.6.1.4.1.17409.2.3.10.3.1.7
		stats24InBroadcastPkts OBJECT-TYPE
			SYNTAX Counter64
			MAX-ACCESS read-only
			STATUS current
			DESCRIPTION
				""
			::= { stats24Entry 7 }

		
		-- 1.3.6.1.4.1.17409.2.3.10.3.1.8
		stats24InMulticastPkts OBJECT-TYPE
			SYNTAX Counter64
			MAX-ACCESS read-only
			STATUS current
			DESCRIPTION
				""
			::= { stats24Entry 8 }

		
		-- 1.3.6.1.4.1.17409.2.3.10.3.1.9
		stats24InPkts64Octets OBJECT-TYPE
			SYNTAX Counter64
			MAX-ACCESS read-only
			STATUS current
			DESCRIPTION
				"64"
			::= { stats24Entry 9 }

		
		-- 1.3.6.1.4.1.17409.2.3.10.3.1.10
		stats24InPkts65to127Octets OBJECT-TYPE
			SYNTAX Counter64
			MAX-ACCESS read-only
			STATUS current
			DESCRIPTION
				"65127"
			::= { stats24Entry 10 }

		
		-- 1.3.6.1.4.1.17409.2.3.10.3.1.11
		stats24InPkts128to255Octets OBJECT-TYPE
			SYNTAX Counter64
			MAX-ACCESS read-only
			STATUS current
			DESCRIPTION
				"128255"
			::= { stats24Entry 11 }

		
		-- 1.3.6.1.4.1.17409.2.3.10.3.1.12
		stats24InPkts256to511Octets OBJECT-TYPE
			SYNTAX Counter64
			MAX-ACCESS read-only
			STATUS current
			DESCRIPTION
				"256511"
			::= { stats24Entry 12 }

		
		-- 1.3.6.1.4.1.17409.2.3.10.3.1.13
		stats24InPkts512to1023Octets OBJECT-TYPE
			SYNTAX Counter64
			MAX-ACCESS read-only
			STATUS current
			DESCRIPTION
				"5121023"
			::= { stats24Entry 13 }

		
		-- 1.3.6.1.4.1.17409.2.3.10.3.1.14
		stats24InPkts1024to1518Octets OBJECT-TYPE
			SYNTAX Counter64
			MAX-ACCESS read-only
			STATUS current
			DESCRIPTION
				"10241518"
			::= { stats24Entry 14 }

		
		-- 1.3.6.1.4.1.17409.2.3.10.3.1.15
		stats24InPkts1519to1522Octets OBJECT-TYPE
			SYNTAX Counter64
			MAX-ACCESS read-only
			STATUS current
			DESCRIPTION
				"15191522"
			::= { stats24Entry 15 }

		
		-- 1.3.6.1.4.1.17409.2.3.10.3.1.16
		stats24InUndersizePkts OBJECT-TYPE
			SYNTAX Counter64
			MAX-ACCESS read-only
			STATUS current
			DESCRIPTION
				""
			::= { stats24Entry 16 }

		
		-- 1.3.6.1.4.1.17409.2.3.10.3.1.17
		stats24InOversizePkts OBJECT-TYPE
			SYNTAX Counter64
			MAX-ACCESS read-only
			STATUS current
			DESCRIPTION
				""
			::= { stats24Entry 17 }

		
		-- 1.3.6.1.4.1.17409.2.3.10.3.1.18
		stats24InFragments OBJECT-TYPE
			SYNTAX Counter64
			MAX-ACCESS read-only
			STATUS current
			DESCRIPTION
				""
			::= { stats24Entry 18 }

		
		-- 1.3.6.1.4.1.17409.2.3.10.3.1.19
		stats24InMpcpFrames OBJECT-TYPE
			SYNTAX Counter64
			MAX-ACCESS read-only
			STATUS current
			DESCRIPTION
				"MPCP"
			::= { stats24Entry 19 }

		
		-- 1.3.6.1.4.1.17409.2.3.10.3.1.20
		stats24InMpcpOctets OBJECT-TYPE
			SYNTAX Counter64
			MAX-ACCESS read-only
			STATUS current
			DESCRIPTION
				"MPCP"
			::= { stats24Entry 20 }

		
		-- 1.3.6.1.4.1.17409.2.3.10.3.1.21
		stats24InOAMFrames OBJECT-TYPE
			SYNTAX Counter64
			MAX-ACCESS read-only
			STATUS current
			DESCRIPTION
				"OAM"
			::= { stats24Entry 21 }

		
		-- 1.3.6.1.4.1.17409.2.3.10.3.1.22
		stats24InOAMOctets OBJECT-TYPE
			SYNTAX Counter64
			MAX-ACCESS read-only
			STATUS current
			DESCRIPTION
				"OAM"
			::= { stats24Entry 22 }

		
		-- 1.3.6.1.4.1.17409.2.3.10.3.1.23
		stats24InCRCErrorPkts OBJECT-TYPE
			SYNTAX Counter64
			MAX-ACCESS read-only
			STATUS current
			DESCRIPTION
				"CRC"
			::= { stats24Entry 23 }

		
		-- 1.3.6.1.4.1.17409.2.3.10.3.1.24
		stats24InDropEvents OBJECT-TYPE
			SYNTAX Counter64
			MAX-ACCESS read-only
			STATUS current
			DESCRIPTION
				""
			::= { stats24Entry 24 }

		
		-- 1.3.6.1.4.1.17409.2.3.10.3.1.25
		stats24InJabbers OBJECT-TYPE
			SYNTAX Counter64
			MAX-ACCESS read-only
			STATUS current
			DESCRIPTION
				""
			::= { stats24Entry 25 }

		
		-- 1.3.6.1.4.1.17409.2.3.10.3.1.26
		stats24InCollision OBJECT-TYPE
			SYNTAX Counter64
			MAX-ACCESS read-only
			STATUS current
			DESCRIPTION
				""
			::= { stats24Entry 26 }

		
		-- 1.3.6.1.4.1.17409.2.3.10.3.1.27
		stats24OutOctets OBJECT-TYPE
			SYNTAX Counter64
			MAX-ACCESS read-only
			STATUS current
			DESCRIPTION
				""
			::= { stats24Entry 27 }

		
		-- 1.3.6.1.4.1.17409.2.3.10.3.1.28
		stats24OutPkts OBJECT-TYPE
			SYNTAX Counter64
			MAX-ACCESS read-only
			STATUS current
			DESCRIPTION
				""
			::= { stats24Entry 28 }

		
		-- 1.3.6.1.4.1.17409.2.3.10.3.1.29
		stats24OutBroadcastPkts OBJECT-TYPE
			SYNTAX Counter64
			MAX-ACCESS read-only
			STATUS current
			DESCRIPTION
				""
			::= { stats24Entry 29 }

		
		-- 1.3.6.1.4.1.17409.2.3.10.3.1.30
		stats24OutMulticastPkts OBJECT-TYPE
			SYNTAX Counter64
			MAX-ACCESS read-only
			STATUS current
			DESCRIPTION
				""
			::= { stats24Entry 30 }

		
		-- 1.3.6.1.4.1.17409.2.3.10.3.1.31
		stats24OutPkts64Octets OBJECT-TYPE
			SYNTAX Counter64
			MAX-ACCESS read-only
			STATUS current
			DESCRIPTION
				"64"
			::= { stats24Entry 31 }

		
		-- 1.3.6.1.4.1.17409.2.3.10.3.1.32
		stats24OutPkts65to127Octets OBJECT-TYPE
			SYNTAX Counter64
			MAX-ACCESS read-only
			STATUS current
			DESCRIPTION
				"65127"
			::= { stats24Entry 32 }

		
		-- 1.3.6.1.4.1.17409.2.3.10.3.1.33
		stats24OutPkts128to255Octets OBJECT-TYPE
			SYNTAX Counter64
			MAX-ACCESS read-only
			STATUS current
			DESCRIPTION
				"128255"
			::= { stats24Entry 33 }

		
		-- 1.3.6.1.4.1.17409.2.3.10.3.1.34
		stats24OutPkts256to511Octets OBJECT-TYPE
			SYNTAX Counter64
			MAX-ACCESS read-only
			STATUS current
			DESCRIPTION
				"256511"
			::= { stats24Entry 34 }

		
		-- 1.3.6.1.4.1.17409.2.3.10.3.1.35
		stats24OutPkts512to1023Octets OBJECT-TYPE
			SYNTAX Counter64
			MAX-ACCESS read-only
			STATUS current
			DESCRIPTION
				"5121023"
			::= { stats24Entry 35 }

		
		-- 1.3.6.1.4.1.17409.2.3.10.3.1.36
		stats24OutPkts1024to1518Octets OBJECT-TYPE
			SYNTAX Counter64
			MAX-ACCESS read-only
			STATUS current
			DESCRIPTION
				"10241518"
			::= { stats24Entry 36 }

		
		-- 1.3.6.1.4.1.17409.2.3.10.3.1.37
		stats24OutPkts1519o1522Octets OBJECT-TYPE
			SYNTAX Counter64
			MAX-ACCESS read-only
			STATUS current
			DESCRIPTION
				"15191522"
			::= { stats24Entry 37 }

		
		-- 1.3.6.1.4.1.17409.2.3.10.3.1.38
		stats24OutUndersizePkts OBJECT-TYPE
			SYNTAX Counter64
			MAX-ACCESS read-only
			STATUS current
			DESCRIPTION
				""
			::= { stats24Entry 38 }

		
		-- 1.3.6.1.4.1.17409.2.3.10.3.1.39
		stats24OutOversizePkts OBJECT-TYPE
			SYNTAX Counter64
			MAX-ACCESS read-only
			STATUS current
			DESCRIPTION
				""
			::= { stats24Entry 39 }

		
		-- 1.3.6.1.4.1.17409.2.3.10.3.1.40
		stats24OutFragments OBJECT-TYPE
			SYNTAX Counter64
			MAX-ACCESS read-only
			STATUS current
			DESCRIPTION
				""
			::= { stats24Entry 40 }

		
		-- 1.3.6.1.4.1.17409.2.3.10.3.1.41
		stats24OutMpcpFrames OBJECT-TYPE
			SYNTAX Counter64
			MAX-ACCESS read-only
			STATUS current
			DESCRIPTION
				"MPCP"
			::= { stats24Entry 41 }

		
		-- 1.3.6.1.4.1.17409.2.3.10.3.1.42
		stats24OutMpcpOctets OBJECT-TYPE
			SYNTAX Counter64
			MAX-ACCESS read-only
			STATUS current
			DESCRIPTION
				"MPCP"
			::= { stats24Entry 42 }

		
		-- 1.3.6.1.4.1.17409.2.3.10.3.1.43
		stats24OutOAMFrames OBJECT-TYPE
			SYNTAX Counter64
			MAX-ACCESS read-only
			STATUS current
			DESCRIPTION
				"OAM"
			::= { stats24Entry 43 }

		
		-- 1.3.6.1.4.1.17409.2.3.10.3.1.44
		stats24OutOAMOctets OBJECT-TYPE
			SYNTAX Counter64
			MAX-ACCESS read-only
			STATUS current
			DESCRIPTION
				"OAM"
			::= { stats24Entry 44 }

		
		-- 1.3.6.1.4.1.17409.2.3.10.3.1.45
		stats24OutCRCErrorPkts OBJECT-TYPE
			SYNTAX Counter64
			MAX-ACCESS read-only
			STATUS current
			DESCRIPTION
				"CRC"
			::= { stats24Entry 45 }

		
		-- 1.3.6.1.4.1.17409.2.3.10.3.1.46
		stats24OutDropEvents OBJECT-TYPE
			SYNTAX Counter64
			MAX-ACCESS read-only
			STATUS current
			DESCRIPTION
				""
			::= { stats24Entry 46 }

		
		-- 1.3.6.1.4.1.17409.2.3.10.3.1.47
		stats24OutJabbers OBJECT-TYPE
			SYNTAX Counter64
			MAX-ACCESS read-only
			STATUS current
			DESCRIPTION
				""
			::= { stats24Entry 47 }

		
		-- 1.3.6.1.4.1.17409.2.3.10.3.1.48
		stats24OutCollision OBJECT-TYPE
			SYNTAX Counter64
			MAX-ACCESS read-only
			STATUS current
			DESCRIPTION
				""
			::= { stats24Entry 48 }

		
		-- 1.3.6.1.4.1.17409.2.3.10.3.1.49
		stats24StatusAndAction OBJECT-TYPE
			SYNTAX INTEGER
				{
				none(1),
				clear(2)
				}
			MAX-ACCESS read-write
			STATUS current
			DESCRIPTION
				"
				clear(2) "
			::= { stats24Entry 49 }

		
		-- 1.3.6.1.4.1.17409.2.3.10.3.1.50
		stats24ValidityTag OBJECT-TYPE
			SYNTAX TruthValue
			MAX-ACCESS read-only
			STATUS current
			DESCRIPTION
				"Whether or not the current 1-day PM data is valid"
			::= { stats24Entry 50 }

		
		-- 1.3.6.1.4.1.17409.2.3.10.3.1.51
		stats24ElapsedTime OBJECT-TYPE
			SYNTAX Counter32
			UNITS "seconds"
			MAX-ACCESS read-only
			STATUS current
			DESCRIPTION
				"
				It is elapsed time, since start of this 1-day interval.
				It is only valid for current PM data. For history PM data, set to 0.
				"
			::= { stats24Entry 51 }

		
		-- 1.3.6.1.4.1.17409.2.3.10.3.1.52
		stats24EndTime OBJECT-TYPE
			SYNTAX DateAndTime
			MAX-ACCESS read-only
			STATUS current
			DESCRIPTION
				"
				It is time, when the PM history data is created.
				It is only valid for history PM data.
				"
			::= { stats24Entry 52 }

		
		-- 1.3.6.1.4.1.17409.2.3.10.4
		perfStatsGlobalSet OBJECT-IDENTITY
			STATUS current
			DESCRIPTION 
				" "
			::= { performanceStatisticObjects 4 }

		
		-- 1.3.6.1.4.1.17409.2.3.10.4.1
		perfStats15MinMaxRecord OBJECT-TYPE
			SYNTAX EponStats15MinRecordType
			MAX-ACCESS read-write
			STATUS current
			DESCRIPTION
				"15, 0"
			DEFVAL { 96 }
			::= { perfStatsGlobalSet 1 }

		
		-- 1.3.6.1.4.1.17409.2.3.10.4.2
		perfStats24HourMaxRecord OBJECT-TYPE
			SYNTAX EponStats24HourRecordType
			MAX-ACCESS read-write
			STATUS current
			DESCRIPTION
				"24 0"
			DEFVAL { 7 }
			::= { perfStatsGlobalSet 2 }

		
		-- 1.3.6.1.4.1.17409.2.3.10.5
		perfStatsThresholdTable OBJECT-TYPE
			SYNTAX SEQUENCE OF PerfStatsThresholdEntry
			MAX-ACCESS not-accessible
			STATUS current
			DESCRIPTION
				""
			::= { performanceStatisticObjects 5 }

		
		-- 1.3.6.1.4.1.17409.2.3.10.5.1
		perfStatsThresholdEntry OBJECT-TYPE
			SYNTAX PerfStatsThresholdEntry
			MAX-ACCESS not-accessible
			STATUS current
			DESCRIPTION
				""
			INDEX { perfStatsThresholdDeviceIndex, perfStatsThresholdCardIndex, perfStatsThresholdPortIndex, perfStatsThresholdTypeIndex }
			::= { perfStatsThresholdTable 1 }

		
		PerfStatsThresholdEntry ::=
			SEQUENCE { 
				perfStatsThresholdDeviceIndex
					EponDeviceIndex,
				perfStatsThresholdCardIndex
					EponCardIndex,
				perfStatsThresholdPortIndex
					EponPortIndex,
				perfStatsThresholdTypeIndex
					EponStatsThresholdType,
				perfStatsThresholdUpper
					Counter64,
				perfStatsThresholdLower
					Counter64,
				perfStatsThresholdRowStatus
					RowStatus
			 }

		-- 1.3.6.1.4.1.17409.2.3.10.5.1.1
		perfStatsThresholdDeviceIndex OBJECT-TYPE
			SYNTAX EponDeviceIndex (1..2147483647)
			MAX-ACCESS not-accessible
			STATUS current
			DESCRIPTION
				"        
				curStatsDeviceIndex"
			::= { perfStatsThresholdEntry 1 }

		
		-- 1.3.6.1.4.1.17409.2.3.10.5.1.2
		perfStatsThresholdCardIndex OBJECT-TYPE
			SYNTAX EponCardIndex (1..2147483647)
			MAX-ACCESS not-accessible
			STATUS current
			DESCRIPTION
				"        
				curStatsCardIndex"
			::= { perfStatsThresholdEntry 2 }

		
		-- 1.3.6.1.4.1.17409.2.3.10.5.1.3
		perfStatsThresholdPortIndex OBJECT-TYPE
			SYNTAX EponPortIndex (1..2147483647)
			MAX-ACCESS not-accessible
			STATUS current
			DESCRIPTION
				"        
				curStatsPortIndex"
			::= { perfStatsThresholdEntry 3 }

		
		-- 1.3.6.1.4.1.17409.2.3.10.5.1.4
		perfStatsThresholdTypeIndex OBJECT-TYPE
			SYNTAX EponStatsThresholdType
			MAX-ACCESS not-accessible
			STATUS current
			DESCRIPTION
				""
			::= { perfStatsThresholdEntry 4 }

		
		-- 1.3.6.1.4.1.17409.2.3.10.5.1.5
		perfStatsThresholdUpper OBJECT-TYPE
			SYNTAX Counter64
			MAX-ACCESS read-create
			STATUS current
			DESCRIPTION
				""
			::= { perfStatsThresholdEntry 5 }

		
		-- 1.3.6.1.4.1.17409.2.3.10.5.1.6
		perfStatsThresholdLower OBJECT-TYPE
			SYNTAX Counter64
			MAX-ACCESS read-create
			STATUS current
			DESCRIPTION
				""
			::= { perfStatsThresholdEntry 6 }

		
		-- 1.3.6.1.4.1.17409.2.3.10.5.1.7
		perfStatsThresholdRowStatus OBJECT-TYPE
			SYNTAX RowStatus
			MAX-ACCESS read-create
			STATUS current
			DESCRIPTION
				""
			::= { perfStatsThresholdEntry 7 }

		
--      DESCRIPTION
-- "EPON MIB"
		-- 1.3.6.1.4.1.17409.2.4
		eoCTree OBJECT IDENTIFIER ::= { nscrtvEponEocTree 4 }

		
--      DESCRIPTION
-- "EoC MIB"   
		-- 1.3.6.1.4.1.17409.2.5
		orTree OBJECT IDENTIFIER ::= { nscrtvEponEocTree 5 }

		
		-- 1.3.6.1.4.1.17409.2.5.1
		catvOrObjects OBJECT IDENTIFIER ::= { orTree 1 }

		
-- ------------------------------------------------------------------------------
-- catvOrObjects [catv](1.3.6.1.4.1.17409.2.5.1)
-- ------------------------------------------------------------------------------      
		-- 1.3.6.1.4.1.17409.2.5.1.1
		onuCatvOrConfigTable OBJECT-TYPE
			SYNTAX SEQUENCE OF onuCatvOrConfigEntry
			MAX-ACCESS not-accessible
			STATUS current
			DESCRIPTION
				"A list of onuCatvOrConfigTable entries. "
			::= { catvOrObjects 1 }

		
		-- 1.3.6.1.4.1.17409.2.5.1.1.1
		onuCatvOrConfigEntry OBJECT-TYPE
			SYNTAX onuCatvOrConfigEntry
			MAX-ACCESS not-accessible
			STATUS current
			DESCRIPTION
				"The onuCatvOrConfigEntry Information"
			INDEX { onuCatvOrConfigDeviceIndex }
			::= { onuCatvOrConfigTable 1 }

		
		onuCatvOrConfigEntry ::=
			SEQUENCE { 
				onuCatvOrConfigDeviceIndex
					EponDeviceIndex,
				onuCatvOrConfigSwitch
					INTEGER,
				onuCatvOrConfigGainControlType
					INTEGER,
				onuCatvOrConfigAGCUpValue
					INTEGER,
				onuCatvOrConfigAGCRange
					INTEGER,
				onuCatvOrConfigMGCTxAttenuation
					INTEGER,
				onuCatvOrConfigInputLO
					INTEGER,
				onuCatvOrConfigInputHI
					INTEGER,
				onuCatvOrConfigOutputLO
					INTEGER,
				onuCatvOrConfigOutputHI
					INTEGER,
				onuCatvOrConfigVoltageHI
					INTEGER,
				onuCatvOrConfigVoltageLO
					INTEGER,
				onuCatvOrConfigTemperatureHI
					INTEGER,
				onuCatvOrConfigTemperatureLO
					INTEGER
			 }

		-- 1.3.6.1.4.1.17409.2.5.1.1.1.1
		onuCatvOrConfigDeviceIndex OBJECT-TYPE
			SYNTAX EponDeviceIndex (1..2147483647)
			MAX-ACCESS not-accessible
			STATUS current
			DESCRIPTION
				"onu Catv Opitcal receiver config Index"
			::= { onuCatvOrConfigEntry 1 }

		
		-- 1.3.6.1.4.1.17409.2.5.1.1.1.2
		onuCatvOrConfigSwitch OBJECT-TYPE
			SYNTAX INTEGER
				{
				on(1),
				off(2)
				}
			MAX-ACCESS read-write
			STATUS current
			DESCRIPTION
				"onu Catv Opitcal receiver switch."
			::= { onuCatvOrConfigEntry 2 }

		
		-- 1.3.6.1.4.1.17409.2.5.1.1.1.3
		onuCatvOrConfigGainControlType OBJECT-TYPE
			SYNTAX INTEGER
			MAX-ACCESS read-write
			STATUS current
			DESCRIPTION
				"onu Catv Opitcal receiver switch."
			::= { onuCatvOrConfigEntry 3 }

		
		-- 1.3.6.1.4.1.17409.2.5.1.1.1.4
		onuCatvOrConfigAGCUpValue OBJECT-TYPE
			SYNTAX INTEGER
			MAX-ACCESS read-write
			STATUS current
			DESCRIPTION
				"onu Catv Opitcal receiver switch."
			::= { onuCatvOrConfigEntry 4 }

		
		-- 1.3.6.1.4.1.17409.2.5.1.1.1.5
		onuCatvOrConfigAGCRange OBJECT-TYPE
			SYNTAX INTEGER
			MAX-ACCESS read-write
			STATUS current
			DESCRIPTION
				"onu Catv Opitcal receiver switch."
			::= { onuCatvOrConfigEntry 5 }

		
		-- 1.3.6.1.4.1.17409.2.5.1.1.1.6
		onuCatvOrConfigMGCTxAttenuation OBJECT-TYPE
			SYNTAX INTEGER
			MAX-ACCESS read-write
			STATUS current
			DESCRIPTION
				"onu Catv Opitcal receiver switch."
			::= { onuCatvOrConfigEntry 6 }

		
		-- 1.3.6.1.4.1.17409.2.5.1.1.1.7
		onuCatvOrConfigInputLO OBJECT-TYPE
			SYNTAX INTEGER
			MAX-ACCESS read-write
			STATUS current
			DESCRIPTION
				"onu Catv Opitcal receiver switch."
			::= { onuCatvOrConfigEntry 7 }

		
		-- 1.3.6.1.4.1.17409.2.5.1.1.1.8
		onuCatvOrConfigInputHI OBJECT-TYPE
			SYNTAX INTEGER
			MAX-ACCESS read-write
			STATUS current
			DESCRIPTION
				"onu Catv Opitcal receiver switch."
			::= { onuCatvOrConfigEntry 8 }

		
		-- 1.3.6.1.4.1.17409.2.5.1.1.1.9
		onuCatvOrConfigOutputLO OBJECT-TYPE
			SYNTAX INTEGER
			MAX-ACCESS read-write
			STATUS current
			DESCRIPTION
				"onu Catv Opitcal receiver switch."
			::= { onuCatvOrConfigEntry 9 }

		
		-- 1.3.6.1.4.1.17409.2.5.1.1.1.10
		onuCatvOrConfigOutputHI OBJECT-TYPE
			SYNTAX INTEGER
			MAX-ACCESS read-write
			STATUS current
			DESCRIPTION
				"onu Catv Opitcal receiver switch."
			::= { onuCatvOrConfigEntry 10 }

		
		-- 1.3.6.1.4.1.17409.2.5.1.1.1.11
		onuCatvOrConfigVoltageHI OBJECT-TYPE
			SYNTAX INTEGER
			MAX-ACCESS read-write
			STATUS current
			DESCRIPTION
				"onu Catv Opitcal receiver switch."
			::= { onuCatvOrConfigEntry 11 }

		
		-- 1.3.6.1.4.1.17409.2.5.1.1.1.12
		onuCatvOrConfigVoltageLO OBJECT-TYPE
			SYNTAX INTEGER
			MAX-ACCESS read-write
			STATUS current
			DESCRIPTION
				"onu Catv Opitcal receiver switch."
			::= { onuCatvOrConfigEntry 12 }

		
		-- 1.3.6.1.4.1.17409.2.5.1.1.1.13
		onuCatvOrConfigTemperatureHI OBJECT-TYPE
			SYNTAX INTEGER
			MAX-ACCESS read-write
			STATUS current
			DESCRIPTION
				"onu Catv Opitcal receiver switch."
			::= { onuCatvOrConfigEntry 13 }

		
		-- 1.3.6.1.4.1.17409.2.5.1.1.1.14
		onuCatvOrConfigTemperatureLO OBJECT-TYPE
			SYNTAX INTEGER
			MAX-ACCESS read-write
			STATUS current
			DESCRIPTION
				"onu Catv Opitcal receiver switch."
			::= { onuCatvOrConfigEntry 14 }

		
		-- 1.3.6.1.4.1.17409.2.5.1.2
		onuCatvOrInfoTable OBJECT-TYPE
			SYNTAX SEQUENCE OF onuCatvOrInfoEntry
			MAX-ACCESS not-accessible
			STATUS current
			DESCRIPTION
				"A list of onuCatvOrInfoTable entries. "
			::= { catvOrObjects 2 }

		
		-- 1.3.6.1.4.1.17409.2.5.1.2.1
		onuCatvOrInfoEntry OBJECT-TYPE
			SYNTAX onuCatvOrInfoEntry
			MAX-ACCESS not-accessible
			STATUS current
			DESCRIPTION
				"The onuCatvOrConfigEntry Information"
			INDEX { onuCatvOrInfoDeviceIndex }
			::= { onuCatvOrInfoTable 1 }

		
		onuCatvOrInfoEntry ::=
			SEQUENCE { 
				onuCatvOrInfoDeviceIndex
					EponDeviceIndex,
				onuCatvOrInfoRxPower
					INTEGER,
				onuCatvOrInfoRfOutVoltage
					INTEGER,
				onuCatvOrInfoVoltage
					INTEGER,
				onuCatvOrInfoTemperature
					INTEGER
			 }

		-- 1.3.6.1.4.1.17409.2.5.1.2.1.1
		onuCatvOrInfoDeviceIndex OBJECT-TYPE
			SYNTAX EponDeviceIndex (1..2147483647)
			MAX-ACCESS not-accessible
			STATUS current
			DESCRIPTION
				"onu Catv Opitcal receiver information Index"
			::= { onuCatvOrInfoEntry 1 }

		
		-- 1.3.6.1.4.1.17409.2.5.1.2.1.2
		onuCatvOrInfoRxPower OBJECT-TYPE
			SYNTAX INTEGER
			MAX-ACCESS read-only
			STATUS current
			DESCRIPTION
				"onu Catv Opitcal receiver information rx-power."
			::= { onuCatvOrInfoEntry 2 }

		
		-- 1.3.6.1.4.1.17409.2.5.1.2.1.3
		onuCatvOrInfoRfOutVoltage OBJECT-TYPE
			SYNTAX INTEGER
			MAX-ACCESS read-only
			STATUS current
			DESCRIPTION
				"onu Catv Opitcal receiver information rf out voltage."
			::= { onuCatvOrInfoEntry 3 }

		
		-- 1.3.6.1.4.1.17409.2.5.1.2.1.4
		onuCatvOrInfoVoltage OBJECT-TYPE
			SYNTAX INTEGER
			MAX-ACCESS read-only
			STATUS current
			DESCRIPTION
				"onu Catv Opitcal receiver information voltage."
			::= { onuCatvOrInfoEntry 4 }

		
		-- 1.3.6.1.4.1.17409.2.5.1.2.1.5
		onuCatvOrInfoTemperature OBJECT-TYPE
			SYNTAX INTEGER
			MAX-ACCESS read-only
			STATUS current
			DESCRIPTION
				"onu Catv Opitcal receiver information temperat."
			::= { onuCatvOrInfoEntry 5 }

		
--      DESCRIPTION
-- "OpticalReceiver MIB"
		-- 1.3.6.1.4.1.17409.2.6
		oTTree OBJECT IDENTIFIER ::= { nscrtvEponEocTree 6 }

		
		-- 1.3.6.1.4.1.17409.2.6.1
		cityNetworkOpticalTransmissionCommonQuery OBJECT IDENTIFIER ::= { oTTree 1 }

		
-- ------------------------------------------------------------------------------
-- cityNetworkOpticalTransmissionCommonQuery [](1.3.6.1.4.1.17409.2.6.1)
-- -------------------------------------------------------------------------
		-- 1.3.6.1.4.1.17409.2.6.1.1
		CityNetworkOpticalTransmissionCommonTable OBJECT-TYPE
			SYNTAX SEQUENCE OF commonEponDeviceEntry
			MAX-ACCESS not-accessible
			STATUS current
			DESCRIPTION
				""
			::= { cityNetworkOpticalTransmissionCommonQuery 1 }

		
		-- 1.3.6.1.4.1.17409.2.6.1.1.1
		commonEponDeviceEntry OBJECT-TYPE
			SYNTAX commonEponDeviceEntry
			MAX-ACCESS not-accessible
			STATUS current
			DESCRIPTION
				"The commonEponDeviceEntry Information"
			INDEX { commonEponDeviceIndex }
			::= { CityNetworkOpticalTransmissionCommonTable 1 }

		
		commonEponDeviceEntry ::=
			SEQUENCE { 
				commonEponDeviceIndex
					INTEGER,
				commonEponDeviceType
					DisplayString,
				commonEponDeviceName
					DisplayString,
				commonEponVendorName
					DisplayString,
				commonEponModelNumber
					DisplayString,
				commonEponSerialNumber
					DisplayString,
				commonEponIpAddress
					IpAddress,
				commonEponMacAddress
					INTEGER,
				commonEponDeviceMFD
					DisplayString,
				commonEponDeviceInternalTemperature
					INTEGER,
				commonEponInputRFLevel
					INTEGER,
				commonEponOpicalInputPower
					INTEGER,
				commonEponOutputOpticalPower
					INTEGER,
				commonEponPowerVoltage
					INTEGER,
				commonEponPowerCurrent
					INTEGER
			 }

		-- 1.3.6.1.4.1.17409.2.6.1.1.1.1
		commonEponDeviceIndex OBJECT-TYPE
			SYNTAX INTEGER (1..2147483647)
			MAX-ACCESS not-accessible
			STATUS current
			DESCRIPTION
				"CityNetworkOpticalTransmissionCommonQueryTable Index"
			::= { commonEponDeviceEntry 1 }

		
		-- 1.3.6.1.4.1.17409.2.6.1.1.1.2
		commonEponDeviceType OBJECT-TYPE
			SYNTAX DisplayString (SIZE (0..255))
			MAX-ACCESS read-only
			STATUS current
			DESCRIPTION
				""
			::= { commonEponDeviceEntry 2 }

		
		-- 1.3.6.1.4.1.17409.2.6.1.1.1.3
		commonEponDeviceName OBJECT-TYPE
			SYNTAX DisplayString (SIZE (0..255))
			MAX-ACCESS read-only
			STATUS current
			DESCRIPTION
				""
			::= { commonEponDeviceEntry 3 }

		
		-- 1.3.6.1.4.1.17409.2.6.1.1.1.4
		commonEponVendorName OBJECT-TYPE
			SYNTAX DisplayString (SIZE (0..255))
			MAX-ACCESS read-only
			STATUS current
			DESCRIPTION
				""
			::= { commonEponDeviceEntry 4 }

		
		-- 1.3.6.1.4.1.17409.2.6.1.1.1.5
		commonEponModelNumber OBJECT-TYPE
			SYNTAX DisplayString (SIZE (0..255))
			MAX-ACCESS read-only
			STATUS current
			DESCRIPTION
				""
			::= { commonEponDeviceEntry 5 }

		
		-- 1.3.6.1.4.1.17409.2.6.1.1.1.6
		commonEponSerialNumber OBJECT-TYPE
			SYNTAX DisplayString (SIZE (0..255))
			MAX-ACCESS read-only
			STATUS current
			DESCRIPTION
				""
			::= { commonEponDeviceEntry 6 }

		
		-- 1.3.6.1.4.1.17409.2.6.1.1.1.7
		commonEponIpAddress OBJECT-TYPE
			SYNTAX IpAddress
			MAX-ACCESS read-write
			STATUS current
			DESCRIPTION
				"IP"
			::= { commonEponDeviceEntry 7 }

		
		-- 1.3.6.1.4.1.17409.2.6.1.1.1.8
		commonEponMacAddress OBJECT-TYPE
			SYNTAX INTEGER
			MAX-ACCESS read-only
			STATUS current
			DESCRIPTION
				"MAC"
			::= { commonEponDeviceEntry 8 }

		
		-- 1.3.6.1.4.1.17409.2.6.1.1.1.10
		commonEponDeviceMFD OBJECT-TYPE
			SYNTAX DisplayString (SIZE (10))
			MAX-ACCESS read-only
			STATUS current
			DESCRIPTION
				""
			::= { commonEponDeviceEntry 10 }

		
		-- 1.3.6.1.4.1.17409.2.6.1.1.1.12
		commonEponDeviceInternalTemperature OBJECT-TYPE
			SYNTAX INTEGER (-128..127)
			MAX-ACCESS read-only
			STATUS optional
			DESCRIPTION
				""
			::= { commonEponDeviceEntry 12 }

		
		-- 1.3.6.1.4.1.17409.2.6.1.1.1.13
		commonEponInputRFLevel OBJECT-TYPE
			SYNTAX INTEGER (0..127)
			MAX-ACCESS read-only
			STATUS optional
			DESCRIPTION
				",dBuV/ch"
			::= { commonEponDeviceEntry 13 }

		
		-- 1.3.6.1.4.1.17409.2.6.1.1.1.14
		commonEponOpicalInputPower OBJECT-TYPE
			SYNTAX INTEGER (-32768..32767)
			MAX-ACCESS read-only
			STATUS current
			DESCRIPTION
				",0.1dBm"
			::= { commonEponDeviceEntry 14 }

		
		-- 1.3.6.1.4.1.17409.2.6.1.1.1.15
		commonEponOutputOpticalPower OBJECT-TYPE
			SYNTAX INTEGER (0..65535)
			MAX-ACCESS read-only
			STATUS current
			DESCRIPTION
				",0.1dBm"
			::= { commonEponDeviceEntry 15 }

		
		-- 1.3.6.1.4.1.17409.2.6.1.1.1.16
		commonEponPowerVoltage OBJECT-TYPE
			SYNTAX INTEGER (-32768..32767)
			MAX-ACCESS read-only
			STATUS current
			DESCRIPTION
				"0.1V"
			::= { commonEponDeviceEntry 16 }

		
		-- 1.3.6.1.4.1.17409.2.6.1.1.1.17
		commonEponPowerCurrent OBJECT-TYPE
			SYNTAX INTEGER (0..65535)
			MAX-ACCESS read-only
			STATUS current
			DESCRIPTION
				"0.01A"
			::= { commonEponDeviceEntry 17 }

		
	
	END

--
-- NSCRTV-FTTX-EPON-MIB.my
--
