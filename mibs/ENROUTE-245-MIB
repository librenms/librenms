TRANZEO-ENROUTE-MUNIWIFI-MIB DEFINITIONS ::= BEGIN

IMPORTS
	MODULE-IDENTITY, OBJECT-TYPE, enterprises, Integer32
		FROM SNMPv2-SMI
	TRAP-TYPE
		FROM RFC-1215;

enRoute MODULE-IDENTITY
	LAST-UPDATED "200807011200Z"
	ORGANIZATION "www.tranzeo.com"
	CONTACT-INFO
		"postal: Ron Dippold
		         Tranzeo Wireless USA
		         15950 Bernardo Center Drive, Suite J
		         San Diego, CA 92127-1829

		 email:  rdippold@tranzeo.com
		"
	DESCRIPTION	"The Tranzeo EnRoute platform MIB."
	REVISION	"200807011200Z"
	DESCRIPTION	"v4.060 - Jun 10 2008"
	::= { enterprises 24350 }

--
-- Tranzeo Wireless EnRoute enterprise-specific management objects
--


----------------------------------------------------
-- .1. BRANCH version.
--
version OBJECT IDENTIFIER ::= { enRoute 1 }
-- .1.1 LEAF version.driver80211
versionDriver80211 OBJECT-TYPE
  SYNTAX OCTET STRING
  MAX-ACCESS read-only
  STATUS current
  DESCRIPTION "80211 driver release version"
  ::= { version 1 }
-- .1.2 LEAF version.firmware
versionFirmware OBJECT-TYPE
  SYNTAX OCTET STRING
  MAX-ACCESS read-only
  STATUS current
  DESCRIPTION "firmware release version"
  ::= { version 2 }
-- .1.3 LEAF version.loaded-profile
versionLoaded-profile OBJECT-TYPE
  SYNTAX OCTET STRING
  MAX-ACCESS read-only
  STATUS current
  DESCRIPTION "last mcm cfg-load or cfg-save profile"
  ::= { version 3 }
-- .1.4 LEAF version.mcm
versionMcm OBJECT-TYPE
  SYNTAX OCTET STRING
  MAX-ACCESS read-only
  STATUS current
  DESCRIPTION "mcm version"
  ::= { version 4 }
-- .1.5 LEAF version.patches
versionPatches OBJECT-TYPE
  SYNTAX OCTET STRING
  MAX-ACCESS read-only
  STATUS current
  DESCRIPTION "applied patches"
  ::= { version 5 }
-- .1.6 LEAF version.qos
versionQos OBJECT-TYPE
  SYNTAX OCTET STRING
  MAX-ACCESS read-only
  STATUS current
  DESCRIPTION "QoS version"
  ::= { version 6 }
-- .1.7 LEAF version.release
versionRelease OBJECT-TYPE
  SYNTAX OCTET STRING
  MAX-ACCESS read-only
  STATUS current
  DESCRIPTION "software release version"
  ::= { version 7 }
----------------------------------------------------
-- .2. BRANCH sys.
--
sys OBJECT IDENTIFIER ::= { enRoute 2 }
----------------------------------------------------
-- .2.1. BRANCH sys.apply.
--
sysApply OBJECT IDENTIFIER ::= { sys 1 }
-- .2.1.1 LEAF sys.apply.effect
sysApplyEffect OBJECT-TYPE
  SYNTAX OCTET STRING
  MAX-ACCESS read-only
  STATUS current
  DESCRIPTION "approximate severity of applying outstanding changes"
  ::= { sysApply 1 }
-- .2.1.2 LEAF sys.apply.time
sysApplyTime OBJECT-TYPE
  SYNTAX INTEGER
  MAX-ACCESS read-only
  STATUS current
  DESCRIPTION "time in seconds to apply outstanding changes"
  ::= { sysApply 2 }
----------------------------------------------------
-- .2.2. BRANCH sys.dev.
--
sysDev OBJECT IDENTIFIER ::= { sys 2 }
----------------------------------------------------
-- .2.2.1. BRANCH sys.dev.battery.
--
sysDevBattery OBJECT IDENTIFIER ::= { sysDev 1 }
-- .2.2.1.1 LEAF sys.dev.battery.enable
sysDevBatteryEnable OBJECT-TYPE
  SYNTAX OCTET STRING
  MAX-ACCESS read-write
  STATUS current
  DESCRIPTION "enable battery"
  ::= { sysDevBattery 1 }
-- .2.2.1.2 LEAF sys.dev.battery.installed
sysDevBatteryInstalled OBJECT-TYPE
  SYNTAX OCTET STRING
  MAX-ACCESS read-only
  STATUS current
  DESCRIPTION "battery hardware could be installed"
  ::= { sysDevBattery 2 }
----------------------------------------------------
-- .2.2.2. BRANCH sys.dev.led.
--
sysDevLed OBJECT IDENTIFIER ::= { sysDev 2 }
-- .2.2.2.1 LEAF sys.dev.led.enable
sysDevLedEnable OBJECT-TYPE
  SYNTAX OCTET STRING
  MAX-ACCESS read-write
  STATUS current
  DESCRIPTION "enable led display"
  ::= { sysDevLed 1 }
----------------------------------------------------
-- .2.2.3. BRANCH sys.dev.poe.
--
sysDevPoe OBJECT IDENTIFIER ::= { sysDev 3 }
-- .2.2.3.1 LEAF sys.dev.poe.enable
sysDevPoeEnable OBJECT-TYPE
  SYNTAX OCTET STRING
  MAX-ACCESS read-write
  STATUS current
  DESCRIPTION "supply power over ethernet"
  ::= { sysDevPoe 1 }
-- .2.2.3.2 LEAF sys.dev.poe.installed
sysDevPoeInstalled OBJECT-TYPE
  SYNTAX OCTET STRING
  MAX-ACCESS read-only
  STATUS current
  DESCRIPTION "poe hardware is installed"
  ::= { sysDevPoe 2 }
-- .2.2.3.3 LEAF sys.dev.poe.voltage
sysDevPoeVoltage OBJECT-TYPE
  SYNTAX OCTET STRING
  MAX-ACCESS read-write
  STATUS current
  DESCRIPTION "power over ethernet voltage - 24 or 48"
  ::= { sysDevPoe 3 }
----------------------------------------------------
-- .2.2.4. BRANCH sys.dev.wlan.
--
sysDevWlan OBJECT IDENTIFIER ::= { sysDev 4 }
-- .2.2.4.1 LEAF sys.dev.wlan.country
sysDevWlanCountry OBJECT-TYPE
  SYNTAX INTEGER
  MAX-ACCESS read-write
  STATUS current
  DESCRIPTION "ansi country code - 124=canada, 840=us, 826=uk"
  ::= { sysDevWlan 1 }
----------------------------------------------------
-- .2.3. BRANCH sys.dhcp.
--
sysDhcp OBJECT IDENTIFIER ::= { sys 3 }
-- .2.3.1 LEAF sys.dhcp.args
sysDhcpArgs OBJECT-TYPE
  SYNTAX OCTET STRING
  MAX-ACCESS read-only
  STATUS current
  DESCRIPTION "dhcp server arguments"
  ::= { sysDhcp 1 }
-- .2.3.2 LEAF sys.dhcp.enable_server
sysDhcpEnableserver OBJECT-TYPE
  SYNTAX OCTET STRING
  MAX-ACCESS read-write
  STATUS current
  DESCRIPTION "enable dhcp server if any of the interfaces require it"
  ::= { sysDhcp 2 }
----------------------------------------------------
-- .2.3.3. BRANCH sys.dhcp.relay.
--
sysDhcpRelay OBJECT IDENTIFIER ::= { sysDhcp 3 }
----------------------------------------------------
-- .2.3.3.1. BRANCH sys.dhcp.relay.agent.
--
sysDhcpRelayAgent OBJECT IDENTIFIER ::= { sysDhcpRelay 1 }
-- .2.3.3.1.1 LEAF sys.dhcp.relay.agent.base
sysDhcpRelayAgentBase OBJECT-TYPE
  SYNTAX OCTET STRING
  MAX-ACCESS read-write
  STATUS current
  DESCRIPTION "base octet to use for alias VAP IP addresses"
  ::= { sysDhcpRelayAgent 1 }
-- .2.3.3.2 LEAF sys.dhcp.relay.args
sysDhcpRelayArgs OBJECT-TYPE
  SYNTAX OCTET STRING
  MAX-ACCESS read-write
  STATUS current
  DESCRIPTION "roamd arguments except for -D and -a"
  ::= { sysDhcpRelay 2 }
-- .2.3.3.3 LEAF sys.dhcp.relay.arp_num_bc
sysDhcpRelayArpnumbc OBJECT-TYPE
  SYNTAX INTEGER
  MAX-ACCESS read-write
  STATUS current
  DESCRIPTION "number of unsolicited arp broadcasts to establish ips"
  ::= { sysDhcpRelay 3 }
-- .2.3.3.4 LEAF sys.dhcp.relay.bind_retries
sysDhcpRelayBindretries OBJECT-TYPE
  SYNTAX INTEGER
  MAX-ACCESS read-write
  STATUS current
  DESCRIPTION "number of interface bind attempts"
  ::= { sysDhcpRelay 4 }
-- .2.3.3.5 LEAF sys.dhcp.relay.enable
sysDhcpRelayEnable OBJECT-TYPE
  SYNTAX OCTET STRING
  MAX-ACCESS read-write
  STATUS current
  DESCRIPTION "use remote dhcp server instead of local"
  ::= { sysDhcpRelay 5 }
-- .2.3.3.6 LEAF sys.dhcp.relay.extra_hosts
sysDhcpRelayExtrahosts OBJECT-TYPE
  SYNTAX OCTET STRING
  MAX-ACCESS read-write
  STATUS current
  DESCRIPTION "space separated list of extra host ip addresses to consider external"
  ::= { sysDhcpRelay 6 }
-- .2.3.3.7 LEAF sys.dhcp.relay.gateway
sysDhcpRelayGateway OBJECT-TYPE
  SYNTAX OCTET STRING
  MAX-ACCESS read-write
  STATUS current
  DESCRIPTION "base address to use VAP IP addresses globally"
  ::= { sysDhcpRelay 7 }
----------------------------------------------------
-- .2.3.3.8. BRANCH sys.dhcp.relay.imr.
--
sysDhcpRelayImr OBJECT IDENTIFIER ::= { sysDhcpRelay 8 }
-- .2.3.3.8.1 LEAF sys.dhcp.relay.imr.num_bc
sysDhcpRelayImrNumbc OBJECT-TYPE
  SYNTAX INTEGER
  MAX-ACCESS read-write
  STATUS current
  DESCRIPTION "notification broadcast count"
  ::= { sysDhcpRelayImr 1 }
-- .2.3.3.9 LEAF sys.dhcp.relay.proxy
sysDhcpRelayProxy OBJECT-TYPE
  SYNTAX OCTET STRING
  MAX-ACCESS read-write
  STATUS current
  DESCRIPTION "redirect all dhcp traffic to relay on gateway"
  ::= { sysDhcpRelay 9 }
-- .2.3.3.10 LEAF sys.dhcp.relay.server
sysDhcpRelayServer OBJECT-TYPE
  SYNTAX OCTET STRING
  MAX-ACCESS read-write
  STATUS current
  DESCRIPTION "numeric ip address of the external DHCP server"
  ::= { sysDhcpRelay 10 }
-- .2.3.3.11 LEAF sys.dhcp.relay.stale_check_interval
sysDhcpRelayStalecheckinterval OBJECT-TYPE
  SYNTAX INTEGER
  MAX-ACCESS read-write
  STATUS current
  DESCRIPTION "check for stale route (seconds)"
  ::= { sysDhcpRelay 11 }
----------------------------------------------------
-- .2.3.3.12. BRANCH sys.dhcp.relay.static.
--
sysDhcpRelayStatic OBJECT IDENTIFIER ::= { sysDhcpRelay 12 }
-- .2.3.3.12.1 LEAF sys.dhcp.relay.static.begin
sysDhcpRelayStaticBegin OBJECT-TYPE
  SYNTAX OCTET STRING
  MAX-ACCESS read-write
  STATUS current
  DESCRIPTION "beginning of statif ip range"
  ::= { sysDhcpRelayStatic 1 }
-- .2.3.3.12.2 LEAF sys.dhcp.relay.static.enable
sysDhcpRelayStaticEnable OBJECT-TYPE
  SYNTAX OCTET STRING
  MAX-ACCESS read-write
  STATUS current
  DESCRIPTION "allow static allocation range"
  ::= { sysDhcpRelayStatic 2 }
-- .2.3.3.12.3 LEAF sys.dhcp.relay.static.end
sysDhcpRelayStaticEnd OBJECT-TYPE
  SYNTAX OCTET STRING
  MAX-ACCESS read-write
  STATUS current
  DESCRIPTION "end of static ip range"
  ::= { sysDhcpRelayStatic 3 }
-- .2.3.3.13 LEAF sys.dhcp.relay.subnet
sysDhcpRelaySubnet OBJECT-TYPE
  SYNTAX OCTET STRING
  MAX-ACCESS read-write
  STATUS current
  DESCRIPTION "subnet for roamd"
  ::= { sysDhcpRelay 13 }
----------------------------------------------------
-- .2.3.3.14. BRANCH sys.dhcp.relay.tunnel.
--
sysDhcpRelayTunnel OBJECT IDENTIFIER ::= { sysDhcpRelay 14 }
-- .2.3.3.14.1 LEAF sys.dhcp.relay.tunnel.endpoint
sysDhcpRelayTunnelEndpoint OBJECT-TYPE
  SYNTAX OCTET STRING
  MAX-ACCESS read-write
  STATUS current
  DESCRIPTION "tunnel subnet for roamd"
  ::= { sysDhcpRelayTunnel 1 }
-- .2.3.3.14.2 LEAF sys.dhcp.relay.tunnel.keepalive
sysDhcpRelayTunnelKeepalive OBJECT-TYPE
  SYNTAX INTEGER
  MAX-ACCESS read-write
  STATUS current
  DESCRIPTION "tunnel keepalive interval in seconds"
  ::= { sysDhcpRelayTunnel 2 }
-- .2.3.3.14.3 LEAF sys.dhcp.relay.tunnel.timeout_factor
sysDhcpRelayTunnelTimeoutfactor OBJECT-TYPE
  SYNTAX INTEGER
  MAX-ACCESS read-write
  STATUS current
  DESCRIPTION "tunnel timeout factor"
  ::= { sysDhcpRelayTunnel 3 }
----------------------------------------------------
-- .2.4. BRANCH sys.dns.
--
sysDns OBJECT IDENTIFIER ::= { sys 4 }
-- .2.4.1 LEAF sys.dns.servers
sysDnsServers OBJECT-TYPE
  SYNTAX OCTET STRING
  MAX-ACCESS read-write
  STATUS current
  DESCRIPTION "space separated DNS server list"
  ::= { sysDns 1 }
-- .2.4.2 LEAF sys.dns.update_style
sysDnsUpdatestyle OBJECT-TYPE
  SYNTAX OCTET STRING
  MAX-ACCESS read-write
  STATUS current
  DESCRIPTION "dns update style ('ad-hoc', 'interim', 'none' )"
  ::= { sysDns 2 }
----------------------------------------------------
-- .2.5. BRANCH sys.dnsproxy.
--
sysDnsproxy OBJECT IDENTIFIER ::= { sys 5 }
-- .2.5.1 LEAF sys.dnsproxy.enable
sysDnsproxyEnable OBJECT-TYPE
  SYNTAX OCTET STRING
  MAX-ACCESS read-write
  STATUS current
  DESCRIPTION "enable dns proxy"
  ::= { sysDnsproxy 1 }
-- .2.5.2 LEAF sys.dnsproxy.hosts
sysDnsproxyHosts OBJECT-TYPE
  SYNTAX OCTET STRING
  MAX-ACCESS read-write
  STATUS current
  DESCRIPTION "<hostname>=<ip>;<hostname>=<ip>; (etc)"
  ::= { sysDnsproxy 2 }
-- .2.6 LEAF sys.domain
sysDomain OBJECT-TYPE
  SYNTAX OCTET STRING
  MAX-ACCESS read-write
  STATUS current
  DESCRIPTION "domain for this node"
  ::= { sys 6 }
----------------------------------------------------
-- .2.7. BRANCH sys.gui.
--
sysGui OBJECT IDENTIFIER ::= { sys 7 }
----------------------------------------------------
-- .2.7.1. BRANCH sys.gui.upgrade.
--
sysGuiUpgrade OBJECT IDENTIFIER ::= { sysGui 1 }
-- .2.7.1.1 LEAF sys.gui.upgrade.force
sysGuiUpgradeForce OBJECT-TYPE
  SYNTAX OCTET STRING
  MAX-ACCESS read-write
  STATUS current
  DESCRIPTION "gui defaults to forcing upgrade"
  ::= { sysGuiUpgrade 1 }
-- .2.8 LEAF sys.hostname
sysHostname OBJECT-TYPE
  SYNTAX OCTET STRING
  MAX-ACCESS read-write
  STATUS current
  DESCRIPTION "hostname (also set if you change id.node)"
  ::= { sys 8 }
----------------------------------------------------
-- .2.9. BRANCH sys.hosts.
--
sysHosts OBJECT IDENTIFIER ::= { sys 9 }
-- .2.9.1 LEAF sys.hosts.nms
sysHostsNms OBJECT-TYPE
  SYNTAX OCTET STRING
  MAX-ACCESS read-write
  STATUS current
  DESCRIPTION "hostname or ip address of the network management station (snmp)"
  ::= { sysHosts 1 }
----------------------------------------------------
-- .2.10. BRANCH sys.id.
--
sysId OBJECT IDENTIFIER ::= { sys 10 }
-- .2.10.1 LEAF sys.id.lanprefix
sysIdLanprefix OBJECT-TYPE
  SYNTAX OCTET STRING
  MAX-ACCESS read-write
  STATUS current
  DESCRIPTION "first octet for non-mesh interfaces"
  ::= { sysId 1 }
-- .2.10.2 LEAF sys.id.mesh
sysIdMesh OBJECT-TYPE
  SYNTAX OCTET STRING
  MAX-ACCESS read-write
  STATUS current
  DESCRIPTION "3rd mesh octet (2nd octet for other interfaces in implicit mode)"
  ::= { sysId 2 }
-- .2.10.3 LEAF sys.id.meshprefix
sysIdMeshprefix OBJECT-TYPE
  SYNTAX OCTET STRING
  MAX-ACCESS read-write
  STATUS current
  DESCRIPTION "first two octets for mesh"
  ::= { sysId 3 }
-- .2.10.4 LEAF sys.id.node
sysIdNode OBJECT-TYPE
  SYNTAX OCTET STRING
  MAX-ACCESS read-write
  STATUS current
  DESCRIPTION "4th mesh octet (3rd octet for other interfaces in implicit mode)"
  ::= { sysId 4 }
----------------------------------------------------
-- .2.11. BRANCH sys.implicit.
--
sysImplicit OBJECT IDENTIFIER ::= { sys 11 }
-- .2.11.1 LEAF sys.implicit.enable
sysImplicitEnable OBJECT-TYPE
  SYNTAX OCTET STRING
  MAX-ACCESS read-write
  STATUS current
  DESCRIPTION "use implicit addressing scheme - limits ap ranges"
  ::= { sysImplicit 1 }
----------------------------------------------------
-- .2.12. BRANCH sys.info.
--
sysInfo OBJECT IDENTIFIER ::= { sys 12 }
-- .2.12.1 LEAF sys.info.cluster
sysInfoCluster OBJECT-TYPE
  SYNTAX OCTET STRING
  MAX-ACCESS read-write
  STATUS current
  DESCRIPTION "freeform string which will be displayed on web pages"
  ::= { sysInfo 1 }
----------------------------------------------------
-- .2.13. BRANCH sys.l2.
--
sysL2 OBJECT IDENTIFIER ::= { sys 13 }
----------------------------------------------------
-- .2.13.1. BRANCH sys.l2.bridge.
--
sysL2Bridge OBJECT IDENTIFIER ::= { sysL2 1 }
-- .2.13.1.1 LEAF sys.l2.bridge.enable
sysL2BridgeEnable OBJECT-TYPE
  SYNTAX OCTET STRING
  MAX-ACCESS read-write
  STATUS current
  DESCRIPTION "enable level 2 bridge mode"
  ::= { sysL2Bridge 1 }
-- .2.13.2 LEAF sys.l2.client_mac_fwd
sysL2Clientmacfwd OBJECT-TYPE
  SYNTAX OCTET STRING
  MAX-ACCESS read-write
  STATUS current
  DESCRIPTION "preserve client source mac to gateway and enable gateway proxy_arp"
  ::= { sysL2 2 }
----------------------------------------------------
-- .2.13.3. BRANCH sys.l2.hide_internal.
--
sysL2Hideinternal OBJECT IDENTIFIER ::= { sysL2 3 }
-- .2.13.3.1 LEAF sys.l2.hide_internal.enable
sysL2HideinternalEnable OBJECT-TYPE
  SYNTAX OCTET STRING
  MAX-ACCESS read-write
  STATUS current
  DESCRIPTION "hide internal subnets from proxy arps"
  ::= { sysL2Hideinternal 1 }
----------------------------------------------------
-- .2.13.3.2. BRANCH sys.l2.hide_internal.gateway.
--
sysL2HideinternalGateway OBJECT IDENTIFIER ::= { sysL2Hideinternal 2 }
----------------------------------------------------
-- .2.13.3.2.1. BRANCH sys.l2.hide_internal.gateway.allow.
--
sysL2HideinternalGatewayAllow OBJECT IDENTIFIER ::= { sysL2HideinternalGateway 1 }
-- .2.13.3.2.1.1 LEAF sys.l2.hide_internal.gateway.allow.relay_dhcp
sysL2HideinternalGatewayAllowRelaydhcp OBJECT-TYPE
  SYNTAX OCTET STRING
  MAX-ACCESS read-write
  STATUS current
  DESCRIPTION "arp for dhcp relay subnet"
  ::= { sysL2HideinternalGatewayAllow 1 }
----------------------------------------------------
-- .2.13.3.2.2. BRANCH sys.l2.hide_internal.gateway.deny.
--
sysL2HideinternalGatewayDeny OBJECT IDENTIFIER ::= { sysL2HideinternalGateway 2 }
-- .2.13.3.2.2.1 LEAF sys.l2.hide_internal.gateway.deny.all
sysL2HideinternalGatewayDenyAll OBJECT-TYPE
  SYNTAX OCTET STRING
  MAX-ACCESS read-write
  STATUS current
  DESCRIPTION "deny all proxy arps from gateway, unless .allowed"
  ::= { sysL2HideinternalGatewayDeny 1 }
-- .2.13.3.2.2.2 LEAF sys.l2.hide_internal.gateway.deny.mesh
sysL2HideinternalGatewayDenyMesh OBJECT-TYPE
  SYNTAX OCTET STRING
  MAX-ACCESS read-write
  STATUS current
  DESCRIPTION "hide mesh from proxy arp"
  ::= { sysL2HideinternalGatewayDeny 2 }
----------------------------------------------------
-- .2.14. BRANCH sys.location.
--
sysLocation OBJECT IDENTIFIER ::= { sys 14 }
----------------------------------------------------
-- .2.14.1. BRANCH sys.location.gps.
--
sysLocationGps OBJECT IDENTIFIER ::= { sysLocation 1 }
-- .2.14.1.1 LEAF sys.location.gps.altitude
sysLocationGpsAltitude OBJECT-TYPE
  SYNTAX OCTET STRING
  MAX-ACCESS read-write
  STATUS current
  DESCRIPTION "gps altitude in meters"
  ::= { sysLocationGps 1 }
-- .2.14.1.2 LEAF sys.location.gps.latitude
sysLocationGpsLatitude OBJECT-TYPE
  SYNTAX OCTET STRING
  MAX-ACCESS read-write
  STATUS current
  DESCRIPTION "gps latitude in decimal degrees"
  ::= { sysLocationGps 2 }
-- .2.14.1.3 LEAF sys.location.gps.longitude
sysLocationGpsLongitude OBJECT-TYPE
  SYNTAX OCTET STRING
  MAX-ACCESS read-write
  STATUS current
  DESCRIPTION "gps longitude in decimal degrees"
  ::= { sysLocationGps 3 }
-- .2.14.2 LEAF sys.location.postal
sysLocationPostal OBJECT-TYPE
  SYNTAX OCTET STRING
  MAX-ACCESS read-write
  STATUS current
  DESCRIPTION "useful description of node's physical location"
  ::= { sysLocation 2 }
----------------------------------------------------
-- .2.15. BRANCH sys.mainstub.
--
sysMainstub OBJECT IDENTIFIER ::= { sys 15 }
-- .2.15.1 LEAF sys.mainstub.if
sysMainstubIf OBJECT-TYPE
  SYNTAX OCTET STRING
  MAX-ACCESS read-write
  STATUS current
  DESCRIPTION "interface to multicast network"
  ::= { sysMainstub 1 }
-- .2.15.2 LEAF sys.mainstub.proxy_arp
sysMainstubProxyarp OBJECT-TYPE
  SYNTAX OCTET STRING
  MAX-ACCESS read-write
  STATUS current
  DESCRIPTION "proxy arp on multicast interface?"
  ::= { sysMainstub 2 }
----------------------------------------------------
-- .2.16. BRANCH sys.monitor.
--
sysMonitor OBJECT IDENTIFIER ::= { sys 16 }
----------------------------------------------------
-- .2.16.1. BRANCH sys.monitor.health.
--
sysMonitorHealth OBJECT IDENTIFIER ::= { sysMonitor 1 }
-- .2.16.1.1 LEAF sys.monitor.health.enable
sysMonitorHealthEnable OBJECT-TYPE
  SYNTAX OCTET STRING
  MAX-ACCESS read-write
  STATUS current
  DESCRIPTION "enable health monitoring for gateway failover"
  ::= { sysMonitorHealth 1 }
-- .2.16.1.2 LEAF sys.monitor.health.host
sysMonitorHealthHost OBJECT-TYPE
  SYNTAX OCTET STRING
  MAX-ACCESS read-write
  STATUS current
  DESCRIPTION "host to ping"
  ::= { sysMonitorHealth 2 }
----------------------------------------------------
-- .2.17. BRANCH sys.nat.
--
sysNat OBJECT IDENTIFIER ::= { sys 17 }
-- .2.17.1 LEAF sys.nat.enable
sysNatEnable OBJECT-TYPE
  SYNTAX OCTET STRING
  MAX-ACCESS read-write
  STATUS current
  DESCRIPTION "masquerading (on eth0, if gateway)"
  ::= { sysNat 1 }
----------------------------------------------------
-- .2.18. BRANCH sys.netbios.
--
sysNetbios OBJECT IDENTIFIER ::= { sys 18 }
-- .2.18.1 LEAF sys.netbios.servers
sysNetbiosServers OBJECT-TYPE
  SYNTAX OCTET STRING
  MAX-ACCESS read-write
  STATUS current
  DESCRIPTION "space separated netbios server list"
  ::= { sysNetbios 1 }
----------------------------------------------------
-- .2.19. BRANCH sys.nets.
--
sysNets OBJECT IDENTIFIER ::= { sys 19 }
----------------------------------------------------
-- .2.19.1. BRANCH sys.nets.external.
--
sysNetsExternal OBJECT IDENTIFIER ::= { sysNets 1 }
-- .2.19.1.1 LEAF sys.nets.external.combined
sysNetsExternalCombined OBJECT-TYPE
  SYNTAX OCTET STRING
  MAX-ACCESS read-only
  STATUS current
  DESCRIPTION "coalesced .external.default, external.roamd, and .external.extra subnets"
  ::= { sysNetsExternal 1 }
-- .2.19.1.2 LEAF sys.nets.external.default
sysNetsExternalDefault OBJECT-TYPE
  SYNTAX OCTET STRING
  MAX-ACCESS read-only
  STATUS current
  DESCRIPTION "subnets considered external to the mesh by default"
  ::= { sysNetsExternal 2 }
-- .2.19.1.3 LEAF sys.nets.external.extra
sysNetsExternalExtra OBJECT-TYPE
  SYNTAX OCTET STRING
  MAX-ACCESS read-write
  STATUS current
  DESCRIPTION "extra subnets to be considered external to the mesh"
  ::= { sysNetsExternal 3 }
----------------------------------------------------
-- .2.19.2. BRANCH sys.nets.internal.
--
sysNetsInternal OBJECT IDENTIFIER ::= { sysNets 2 }
-- .2.19.2.1 LEAF sys.nets.internal.combined
sysNetsInternalCombined OBJECT-TYPE
  SYNTAX OCTET STRING
  MAX-ACCESS read-only
  STATUS current
  DESCRIPTION "coalesced .internal.default and internal.extra internal subnets"
  ::= { sysNetsInternal 1 }
-- .2.19.2.2 LEAF sys.nets.internal.default
sysNetsInternalDefault OBJECT-TYPE
  SYNTAX OCTET STRING
  MAX-ACCESS read-only
  STATUS current
  DESCRIPTION "default mesh-internal subnets"
  ::= { sysNetsInternal 2 }
-- .2.19.2.3 LEAF sys.nets.internal.extra
sysNetsInternalExtra OBJECT-TYPE
  SYNTAX OCTET STRING
  MAX-ACCESS read-write
  STATUS current
  DESCRIPTION "added to .default internal subnets"
  ::= { sysNetsInternal 3 }
-- .2.19.2.4 LEAF sys.nets.internal.flexip_default
sysNetsInternalFlexipdefault OBJECT-TYPE
  SYNTAX OCTET STRING
  MAX-ACCESS read-write
  STATUS current
  DESCRIPTION "override the .nets.internal.default for flexip"
  ::= { sysNetsInternal 4 }
----------------------------------------------------
-- .2.20. BRANCH sys.organization.
--
sysOrganization OBJECT IDENTIFIER ::= { sys 20 }
-- .2.20.1 LEAF sys.organization.city
sysOrganizationCity OBJECT-TYPE
  SYNTAX OCTET STRING
  MAX-ACCESS read-write
  STATUS current
  DESCRIPTION "city or locality"
  ::= { sysOrganization 1 }
-- .2.20.2 LEAF sys.organization.country
sysOrganizationCountry OBJECT-TYPE
  SYNTAX OCTET STRING
  MAX-ACCESS read-write
  STATUS current
  DESCRIPTION "2 letter country code"
  ::= { sysOrganization 2 }
-- .2.20.3 LEAF sys.organization.name
sysOrganizationName OBJECT-TYPE
  SYNTAX OCTET STRING
  MAX-ACCESS read-write
  STATUS current
  DESCRIPTION "organization name"
  ::= { sysOrganization 3 }
-- .2.20.4 LEAF sys.organization.state
sysOrganizationState OBJECT-TYPE
  SYNTAX OCTET STRING
  MAX-ACCESS read-write
  STATUS current
  DESCRIPTION "state or province"
  ::= { sysOrganization 4 }
----------------------------------------------------
-- .2.21. BRANCH sys.password.
--
sysPassword OBJECT IDENTIFIER ::= { sys 21 }
-- .2.21.1 LEAF sys.password.admin
sysPasswordAdmin OBJECT-TYPE
  SYNTAX OCTET STRING
  MAX-ACCESS read-write
  STATUS current
  DESCRIPTION "admin account password"
  ::= { sysPassword 1 }
-- .2.21.2 LEAF sys.password.monitor
sysPasswordMonitor OBJECT-TYPE
  SYNTAX OCTET STRING
  MAX-ACCESS read-write
  STATUS current
  DESCRIPTION "monitor account password"
  ::= { sysPassword 2 }
-- .2.22 LEAF sys.platform
sysPlatform OBJECT-TYPE
  SYNTAX OCTET STRING
  MAX-ACCESS read-only
  STATUS current
  DESCRIPTION "hardware platform"
  ::= { sys 22 }
----------------------------------------------------
-- .2.23. BRANCH sys.provisioning.
--
sysProvisioning OBJECT IDENTIFIER ::= { sys 23 }
-- .2.23.1 LEAF sys.provisioning.enable
sysProvisioningEnable OBJECT-TYPE
  SYNTAX OCTET STRING
  MAX-ACCESS read-write
  STATUS current
  DESCRIPTION "enable OnRamp provisioning"
  ::= { sysProvisioning 1 }
----------------------------------------------------
-- .2.24. BRANCH sys.routing.
--
sysRouting OBJECT IDENTIFIER ::= { sys 24 }
-- .2.24.1 LEAF sys.routing.ospf
sysRoutingOspf OBJECT-TYPE
  SYNTAX OCTET STRING
  MAX-ACCESS read-write
  STATUS current
  DESCRIPTION "enable OSPF dynamic routing"
  ::= { sysRouting 1 }
-- .2.24.2 LEAF sys.routing.rip
sysRoutingRip OBJECT-TYPE
  SYNTAX OCTET STRING
  MAX-ACCESS read-write
  STATUS current
  DESCRIPTION "enable RIP dynamic routing"
  ::= { sysRouting 2 }
-- .2.25 LEAF sys.scheme
sysScheme OBJECT-TYPE
  SYNTAX OCTET STRING
  MAX-ACCESS read-write
  STATUS current
  DESCRIPTION "wireless node type"
  ::= { sys 25 }
----------------------------------------------------
-- .2.26. BRANCH sys.shell.
--
sysShell OBJECT IDENTIFIER ::= { sys 26 }
-- .2.26.1 LEAF sys.shell.timeout
sysShellTimeout OBJECT-TYPE
  SYNTAX INTEGER
  MAX-ACCESS read-write
  STATUS current
  DESCRIPTION "shell inactivity timeout"
  ::= { sysShell 1 }
----------------------------------------------------
-- .2.27. BRANCH sys.snmp.
--
sysSnmp OBJECT IDENTIFIER ::= { sys 27 }
----------------------------------------------------
-- .2.27.1. BRANCH sys.snmp.community.
--
sysSnmpCommunity OBJECT IDENTIFIER ::= { sysSnmp 1 }
-- .2.27.1.1 LEAF sys.snmp.community.ro
sysSnmpCommunityRo OBJECT-TYPE
  SYNTAX OCTET STRING
  MAX-ACCESS read-write
  STATUS current
  DESCRIPTION "ro community password"
  ::= { sysSnmpCommunity 1 }
-- .2.27.1.2 LEAF sys.snmp.community.rw
sysSnmpCommunityRw OBJECT-TYPE
  SYNTAX OCTET STRING
  MAX-ACCESS read-write
  STATUS current
  DESCRIPTION "rw community password"
  ::= { sysSnmpCommunity 2 }
-- .2.27.1.3 LEAF sys.snmp.community.trap
sysSnmpCommunityTrap OBJECT-TYPE
  SYNTAX OCTET STRING
  MAX-ACCESS read-write
  STATUS current
  DESCRIPTION "trap community password"
  ::= { sysSnmpCommunity 3 }
-- .2.27.2 LEAF sys.snmp.contact
sysSnmpContact OBJECT-TYPE
  SYNTAX OCTET STRING
  MAX-ACCESS read-write
  STATUS current
  DESCRIPTION "snmp contact"
  ::= { sysSnmp 2 }
-- .2.27.3 LEAF sys.snmp.location
sysSnmpLocation OBJECT-TYPE
  SYNTAX OCTET STRING
  MAX-ACCESS read-write
  STATUS current
  DESCRIPTION "location (taken from sys.location.postal)"
  ::= { sysSnmp 3 }
-- .2.27.4 LEAF sys.snmp.port
sysSnmpPort OBJECT-TYPE
  SYNTAX INTEGER
  MAX-ACCESS read-write
  STATUS current
  DESCRIPTION "snmp port"
  ::= { sysSnmp 4 }
----------------------------------------------------
-- .2.27.5. BRANCH sys.snmp.trap.
--
sysSnmpTrap OBJECT IDENTIFIER ::= { sysSnmp 5 }
-- .2.27.5.1 LEAF sys.snmp.trap.host
sysSnmpTrapHost OBJECT-TYPE
  SYNTAX OCTET STRING
  MAX-ACCESS read-write
  STATUS current
  DESCRIPTION "trap host (trapsink)"
  ::= { sysSnmpTrap 1 }
----------------------------------------------------
-- .2.28. BRANCH sys.splash.
--
sysSplash OBJECT IDENTIFIER ::= { sys 28 }
----------------------------------------------------
-- .2.28.1. BRANCH sys.splash.auth.
--
sysSplashAuth OBJECT IDENTIFIER ::= { sysSplash 1 }
----------------------------------------------------
-- .2.28.1.1. BRANCH sys.splash.auth.server.
--
sysSplashAuthServer OBJECT IDENTIFIER ::= { sysSplashAuth 1 }
----------------------------------------------------
-- .2.28.1.1.1. BRANCH sys.splash.auth.server.wlan1.
--
sysSplashAuthServerWlan1 OBJECT IDENTIFIER ::= { sysSplashAuthServer 1 }
-- .2.28.1.1.1.1 LEAF sys.splash.auth.server.wlan1.enable
sysSplashAuthServerWlan1Enable OBJECT-TYPE
  SYNTAX OCTET STRING
  MAX-ACCESS read-write
  STATUS current
  DESCRIPTION "require authentication"
  ::= { sysSplashAuthServerWlan1 1 }
-- .2.28.1.1.1.2 LEAF sys.splash.auth.server.wlan1.host
sysSplashAuthServerWlan1Host OBJECT-TYPE
  SYNTAX OCTET STRING
  MAX-ACCESS read-write
  STATUS current
  DESCRIPTION "host for remote radius authentication"
  ::= { sysSplashAuthServerWlan1 2 }
-- .2.28.1.1.1.3 LEAF sys.splash.auth.server.wlan1.port
sysSplashAuthServerWlan1Port OBJECT-TYPE
  SYNTAX INTEGER
  MAX-ACCESS read-write
  STATUS current
  DESCRIPTION "port for remote radius authentication"
  ::= { sysSplashAuthServerWlan1 3 }
-- .2.28.1.1.1.4 LEAF sys.splash.auth.server.wlan1.secret
sysSplashAuthServerWlan1Secret OBJECT-TYPE
  SYNTAX OCTET STRING
  MAX-ACCESS read-write
  STATUS current
  DESCRIPTION "shared secret for remote radius authentication"
  ::= { sysSplashAuthServerWlan1 4 }
----------------------------------------------------
-- .2.28.1.1.2. BRANCH sys.splash.auth.server.wlan2.
--
sysSplashAuthServerWlan2 OBJECT IDENTIFIER ::= { sysSplashAuthServer 2 }
-- .2.28.1.1.2.1 LEAF sys.splash.auth.server.wlan2.enable
sysSplashAuthServerWlan2Enable OBJECT-TYPE
  SYNTAX OCTET STRING
  MAX-ACCESS read-write
  STATUS current
  DESCRIPTION "require authentication"
  ::= { sysSplashAuthServerWlan2 1 }
-- .2.28.1.1.2.2 LEAF sys.splash.auth.server.wlan2.host
sysSplashAuthServerWlan2Host OBJECT-TYPE
  SYNTAX OCTET STRING
  MAX-ACCESS read-write
  STATUS current
  DESCRIPTION "host for remote radius authentication"
  ::= { sysSplashAuthServerWlan2 2 }
-- .2.28.1.1.2.3 LEAF sys.splash.auth.server.wlan2.port
sysSplashAuthServerWlan2Port OBJECT-TYPE
  SYNTAX INTEGER
  MAX-ACCESS read-write
  STATUS current
  DESCRIPTION "port for remote radius authentication"
  ::= { sysSplashAuthServerWlan2 3 }
-- .2.28.1.1.2.4 LEAF sys.splash.auth.server.wlan2.secret
sysSplashAuthServerWlan2Secret OBJECT-TYPE
  SYNTAX OCTET STRING
  MAX-ACCESS read-write
  STATUS current
  DESCRIPTION "shared secret for remote radius authentication"
  ::= { sysSplashAuthServerWlan2 4 }
----------------------------------------------------
-- .2.28.1.1.3. BRANCH sys.splash.auth.server.wlan3.
--
sysSplashAuthServerWlan3 OBJECT IDENTIFIER ::= { sysSplashAuthServer 3 }
-- .2.28.1.1.3.1 LEAF sys.splash.auth.server.wlan3.enable
sysSplashAuthServerWlan3Enable OBJECT-TYPE
  SYNTAX OCTET STRING
  MAX-ACCESS read-write
  STATUS current
  DESCRIPTION "require authentication"
  ::= { sysSplashAuthServerWlan3 1 }
-- .2.28.1.1.3.2 LEAF sys.splash.auth.server.wlan3.host
sysSplashAuthServerWlan3Host OBJECT-TYPE
  SYNTAX OCTET STRING
  MAX-ACCESS read-write
  STATUS current
  DESCRIPTION "host for remote radius authentication"
  ::= { sysSplashAuthServerWlan3 2 }
-- .2.28.1.1.3.3 LEAF sys.splash.auth.server.wlan3.port
sysSplashAuthServerWlan3Port OBJECT-TYPE
  SYNTAX INTEGER
  MAX-ACCESS read-write
  STATUS current
  DESCRIPTION "port for remote radius authentication"
  ::= { sysSplashAuthServerWlan3 3 }
-- .2.28.1.1.3.4 LEAF sys.splash.auth.server.wlan3.secret
sysSplashAuthServerWlan3Secret OBJECT-TYPE
  SYNTAX OCTET STRING
  MAX-ACCESS read-write
  STATUS current
  DESCRIPTION "shared secret for remote radius authentication"
  ::= { sysSplashAuthServerWlan3 4 }
----------------------------------------------------
-- .2.28.1.1.4. BRANCH sys.splash.auth.server.wlan4.
--
sysSplashAuthServerWlan4 OBJECT IDENTIFIER ::= { sysSplashAuthServer 4 }
-- .2.28.1.1.4.1 LEAF sys.splash.auth.server.wlan4.enable
sysSplashAuthServerWlan4Enable OBJECT-TYPE
  SYNTAX OCTET STRING
  MAX-ACCESS read-write
  STATUS current
  DESCRIPTION "require authentication"
  ::= { sysSplashAuthServerWlan4 1 }
-- .2.28.1.1.4.2 LEAF sys.splash.auth.server.wlan4.host
sysSplashAuthServerWlan4Host OBJECT-TYPE
  SYNTAX OCTET STRING
  MAX-ACCESS read-write
  STATUS current
  DESCRIPTION "host for remote radius authentication"
  ::= { sysSplashAuthServerWlan4 2 }
-- .2.28.1.1.4.3 LEAF sys.splash.auth.server.wlan4.port
sysSplashAuthServerWlan4Port OBJECT-TYPE
  SYNTAX INTEGER
  MAX-ACCESS read-write
  STATUS current
  DESCRIPTION "port for remote radius authentication"
  ::= { sysSplashAuthServerWlan4 3 }
-- .2.28.1.1.4.4 LEAF sys.splash.auth.server.wlan4.secret
sysSplashAuthServerWlan4Secret OBJECT-TYPE
  SYNTAX OCTET STRING
  MAX-ACCESS read-write
  STATUS current
  DESCRIPTION "shared secret for remote radius authentication"
  ::= { sysSplashAuthServerWlan4 4 }
-- .2.28.2 LEAF sys.splash.bypass_hosts
sysSplashBypasshosts OBJECT-TYPE
  SYNTAX OCTET STRING
  MAX-ACCESS read-write
  STATUS current
  DESCRIPTION "comma separated list of hosts to bypass sign in"
  ::= { sysSplash 2 }
----------------------------------------------------
-- .2.28.3. BRANCH sys.splash.enable.
--
sysSplashEnable OBJECT IDENTIFIER ::= { sysSplash 3 }
-- .2.28.3.1 LEAF sys.splash.enable.wlan1
sysSplashEnableWlan1 OBJECT-TYPE
  SYNTAX OCTET STRING
  MAX-ACCESS read-write
  STATUS current
  DESCRIPTION "enable splash screen for wlan1"
  ::= { sysSplashEnable 1 }
-- .2.28.3.2 LEAF sys.splash.enable.wlan2
sysSplashEnableWlan2 OBJECT-TYPE
  SYNTAX OCTET STRING
  MAX-ACCESS read-write
  STATUS current
  DESCRIPTION "enable splash screen for wlan2"
  ::= { sysSplashEnable 2 }
-- .2.28.3.3 LEAF sys.splash.enable.wlan3
sysSplashEnableWlan3 OBJECT-TYPE
  SYNTAX OCTET STRING
  MAX-ACCESS read-write
  STATUS current
  DESCRIPTION "enable splash screen for wlan3"
  ::= { sysSplashEnable 3 }
-- .2.28.3.4 LEAF sys.splash.enable.wlan4
sysSplashEnableWlan4 OBJECT-TYPE
  SYNTAX OCTET STRING
  MAX-ACCESS read-write
  STATUS current
  DESCRIPTION "enable splash screen for wlan4"
  ::= { sysSplashEnable 4 }
-- .2.28.4 LEAF sys.splash.external
sysSplashExternal OBJECT-TYPE
  SYNTAX OCTET STRING
  MAX-ACCESS read-write
  STATUS current
  DESCRIPTION "external network device, set by sys.scheme"
  ::= { sysSplash 4 }
-- .2.28.5 LEAF sys.splash.internal
sysSplashInternal OBJECT-TYPE
  SYNTAX OCTET STRING
  MAX-ACCESS read-only
  STATUS current
  DESCRIPTION "internal network devices, set by sys.scheme"
  ::= { sysSplash 5 }
-- .2.28.6 LEAF sys.splash.trusted_macs
sysSplashTrustedmacs OBJECT-TYPE
  SYNTAX OCTET STRING
  MAX-ACCESS read-write
  STATUS current
  DESCRIPTION "comma separated list of mac addresses than can pass"
  ::= { sysSplash 6 }
----------------------------------------------------
-- .2.28.7. BRANCH sys.splash.url.
--
sysSplashUrl OBJECT IDENTIFIER ::= { sysSplash 7 }
----------------------------------------------------
-- .2.28.7.1. BRANCH sys.splash.url.wlan1.
--
sysSplashUrlWlan1 OBJECT IDENTIFIER ::= { sysSplashUrl 1 }
-- .2.28.7.1.1 LEAF sys.splash.url.wlan1.error
sysSplashUrlWlan1Error OBJECT-TYPE
  SYNTAX OCTET STRING
  MAX-ACCESS read-write
  STATUS current
  DESCRIPTION "full url to page shown on login (internal) error"
  ::= { sysSplashUrlWlan1 1 }
-- .2.28.7.1.2 LEAF sys.splash.url.wlan1.fail
sysSplashUrlWlan1Fail OBJECT-TYPE
  SYNTAX OCTET STRING
  MAX-ACCESS read-write
  STATUS current
  DESCRIPTION "full url to page shown on failed login"
  ::= { sysSplashUrlWlan1 2 }
-- .2.28.7.1.3 LEAF sys.splash.url.wlan1.login
sysSplashUrlWlan1Login OBJECT-TYPE
  SYNTAX OCTET STRING
  MAX-ACCESS read-write
  STATUS current
  DESCRIPTION "full url to desired login page"
  ::= { sysSplashUrlWlan1 3 }
-- .2.28.7.1.4 LEAF sys.splash.url.wlan1.success
sysSplashUrlWlan1Success OBJECT-TYPE
  SYNTAX OCTET STRING
  MAX-ACCESS read-write
  STATUS current
  DESCRIPTION "full url to page shown on successful login"
  ::= { sysSplashUrlWlan1 4 }
----------------------------------------------------
-- .2.28.7.2. BRANCH sys.splash.url.wlan2.
--
sysSplashUrlWlan2 OBJECT IDENTIFIER ::= { sysSplashUrl 2 }
-- .2.28.7.2.1 LEAF sys.splash.url.wlan2.error
sysSplashUrlWlan2Error OBJECT-TYPE
  SYNTAX OCTET STRING
  MAX-ACCESS read-write
  STATUS current
  DESCRIPTION "full url to page shown on login (internal) error"
  ::= { sysSplashUrlWlan2 1 }
-- .2.28.7.2.2 LEAF sys.splash.url.wlan2.fail
sysSplashUrlWlan2Fail OBJECT-TYPE
  SYNTAX OCTET STRING
  MAX-ACCESS read-write
  STATUS current
  DESCRIPTION "full url to page shown on failed login"
  ::= { sysSplashUrlWlan2 2 }
-- .2.28.7.2.3 LEAF sys.splash.url.wlan2.login
sysSplashUrlWlan2Login OBJECT-TYPE
  SYNTAX OCTET STRING
  MAX-ACCESS read-write
  STATUS current
  DESCRIPTION "full url to desired login page"
  ::= { sysSplashUrlWlan2 3 }
-- .2.28.7.2.4 LEAF sys.splash.url.wlan2.success
sysSplashUrlWlan2Success OBJECT-TYPE
  SYNTAX OCTET STRING
  MAX-ACCESS read-write
  STATUS current
  DESCRIPTION "full url to page shown on successful login"
  ::= { sysSplashUrlWlan2 4 }
----------------------------------------------------
-- .2.28.7.3. BRANCH sys.splash.url.wlan3.
--
sysSplashUrlWlan3 OBJECT IDENTIFIER ::= { sysSplashUrl 3 }
-- .2.28.7.3.1 LEAF sys.splash.url.wlan3.error
sysSplashUrlWlan3Error OBJECT-TYPE
  SYNTAX OCTET STRING
  MAX-ACCESS read-write
  STATUS current
  DESCRIPTION "full url to page shown on login (internal) error"
  ::= { sysSplashUrlWlan3 1 }
-- .2.28.7.3.2 LEAF sys.splash.url.wlan3.fail
sysSplashUrlWlan3Fail OBJECT-TYPE
  SYNTAX OCTET STRING
  MAX-ACCESS read-write
  STATUS current
  DESCRIPTION "full url to page shown on failed login"
  ::= { sysSplashUrlWlan3 2 }
-- .2.28.7.3.3 LEAF sys.splash.url.wlan3.login
sysSplashUrlWlan3Login OBJECT-TYPE
  SYNTAX OCTET STRING
  MAX-ACCESS read-write
  STATUS current
  DESCRIPTION "full url to desired login page"
  ::= { sysSplashUrlWlan3 3 }
-- .2.28.7.3.4 LEAF sys.splash.url.wlan3.success
sysSplashUrlWlan3Success OBJECT-TYPE
  SYNTAX OCTET STRING
  MAX-ACCESS read-write
  STATUS current
  DESCRIPTION "full url to page shown on successful login"
  ::= { sysSplashUrlWlan3 4 }
----------------------------------------------------
-- .2.28.7.4. BRANCH sys.splash.url.wlan4.
--
sysSplashUrlWlan4 OBJECT IDENTIFIER ::= { sysSplashUrl 4 }
-- .2.28.7.4.1 LEAF sys.splash.url.wlan4.error
sysSplashUrlWlan4Error OBJECT-TYPE
  SYNTAX OCTET STRING
  MAX-ACCESS read-write
  STATUS current
  DESCRIPTION "full url to page shown on login (internal) error"
  ::= { sysSplashUrlWlan4 1 }
-- .2.28.7.4.2 LEAF sys.splash.url.wlan4.fail
sysSplashUrlWlan4Fail OBJECT-TYPE
  SYNTAX OCTET STRING
  MAX-ACCESS read-write
  STATUS current
  DESCRIPTION "full url to page shown on failed login"
  ::= { sysSplashUrlWlan4 2 }
-- .2.28.7.4.3 LEAF sys.splash.url.wlan4.login
sysSplashUrlWlan4Login OBJECT-TYPE
  SYNTAX OCTET STRING
  MAX-ACCESS read-write
  STATUS current
  DESCRIPTION "full url to desired login page"
  ::= { sysSplashUrlWlan4 3 }
-- .2.28.7.4.4 LEAF sys.splash.url.wlan4.success
sysSplashUrlWlan4Success OBJECT-TYPE
  SYNTAX OCTET STRING
  MAX-ACCESS read-write
  STATUS current
  DESCRIPTION "full url to page shown on successful login"
  ::= { sysSplashUrlWlan4 4 }
----------------------------------------------------
-- .2.29. BRANCH sys.time.
--
sysTime OBJECT IDENTIFIER ::= { sys 29 }
----------------------------------------------------
-- .2.29.1. BRANCH sys.time.rfc868.
--
sysTimeRfc868 OBJECT IDENTIFIER ::= { sysTime 1 }
-- .2.29.1.1 LEAF sys.time.rfc868.server
sysTimeRfc868Server OBJECT-TYPE
  SYNTAX OCTET STRING
  MAX-ACCESS read-write
  STATUS current
  DESCRIPTION "RFC868 time server name or address for gateway nodes"
  ::= { sysTimeRfc868 1 }
-- .2.29.2 LEAF sys.time.sync_delay
sysTimeSyncdelay OBJECT-TYPE
  SYNTAX INTEGER
  MAX-ACCESS read-write
  STATUS current
  DESCRIPTION "how many seconds repeaters should delay syncing to gateway"
  ::= { sysTime 2 }
-- .2.30 LEAF sys.units
sysUnits OBJECT-TYPE
  SYNTAX OCTET STRING
  MAX-ACCESS read-write
  STATUS current
  DESCRIPTION "imperial (feet) or metric (meters)"
  ::= { sys 30 }
----------------------------------------------------
-- .3. BRANCH firewall.
--
firewall OBJECT IDENTIFIER ::= { enRoute 3 }
----------------------------------------------------
-- .3.1. BRANCH firewall.conntrack.
--
firewallConntrack OBJECT IDENTIFIER ::= { firewall 1 }
----------------------------------------------------
-- .3.1.1. BRANCH firewall.conntrack.connlimit.
--
firewallConntrackConnlimit OBJECT IDENTIFIER ::= { firewallConntrack 1 }
-- .3.1.1.1 LEAF firewall.conntrack.connlimit.connections
firewallConntrackConnlimitConnections OBJECT-TYPE
  SYNTAX INTEGER
  MAX-ACCESS read-write
  STATUS current
  DESCRIPTION "number of connections allowed per client"
  ::= { firewallConntrackConnlimit 1 }
-- .3.1.1.2 LEAF firewall.conntrack.connlimit.enable
firewallConntrackConnlimitEnable OBJECT-TYPE
  SYNTAX OCTET STRING
  MAX-ACCESS read-write
  STATUS current
  DESCRIPTION "limit the number of tcp connections per client"
  ::= { firewallConntrackConnlimit 2 }
-- .3.1.2 LEAF firewall.conntrack.table_size
firewallConntrackTablesize OBJECT-TYPE
  SYNTAX INTEGER
  MAX-ACCESS read-write
  STATUS current
  DESCRIPTION "size of connection tracking table"
  ::= { firewallConntrack 2 }
-- .3.1.3 LEAF firewall.conntrack.tcp_timeout_established
firewallConntrackTcptimeoutestablished OBJECT-TYPE
  SYNTAX INTEGER
  MAX-ACCESS read-write
  STATUS current
  DESCRIPTION "tcp connections completely idle this many seconds can be dropped"
  ::= { firewallConntrack 3 }
----------------------------------------------------
-- .3.2. BRANCH firewall.gateway.
--
firewallGateway OBJECT IDENTIFIER ::= { firewall 2 }
-- .3.2.1 LEAF firewall.gateway.enable
firewallGatewayEnable OBJECT-TYPE
  SYNTAX OCTET STRING
  MAX-ACCESS read-write
  STATUS current
  DESCRIPTION "prevent incoming connections past gateway node"
  ::= { firewallGateway 1 }
----------------------------------------------------
-- .3.3. BRANCH firewall.node.
--
firewallNode OBJECT IDENTIFIER ::= { firewall 3 }
----------------------------------------------------
-- .3.3.1. BRANCH firewall.node.allowc2c.
--
firewallNodeAllowc2c OBJECT IDENTIFIER ::= { firewallNode 1 }
-- .3.3.1.1 LEAF firewall.node.allowc2c.eth0
firewallNodeAllowc2cEth0 OBJECT-TYPE
  SYNTAX OCTET STRING
  MAX-ACCESS read-write
  STATUS current
  DESCRIPTION "allow clients to see each other if eth0.role=access"
  ::= { firewallNodeAllowc2c 1 }
-- .3.3.1.2 LEAF firewall.node.allowc2c.wlan1
firewallNodeAllowc2cWlan1 OBJECT-TYPE
  SYNTAX OCTET STRING
  MAX-ACCESS read-write
  STATUS current
  DESCRIPTION "allow clients to see each other if wlan1.role=access"
  ::= { firewallNodeAllowc2c 2 }
-- .3.3.1.3 LEAF firewall.node.allowc2c.wlan2
firewallNodeAllowc2cWlan2 OBJECT-TYPE
  SYNTAX OCTET STRING
  MAX-ACCESS read-write
  STATUS current
  DESCRIPTION "allow clients to see each other if wlan2.role=access"
  ::= { firewallNodeAllowc2c 3 }
-- .3.3.1.4 LEAF firewall.node.allowc2c.wlan3
firewallNodeAllowc2cWlan3 OBJECT-TYPE
  SYNTAX OCTET STRING
  MAX-ACCESS read-write
  STATUS current
  DESCRIPTION "allow clients to see each other if wlan3.role=access"
  ::= { firewallNodeAllowc2c 4 }
-- .3.3.1.5 LEAF firewall.node.allowc2c.wlan4
firewallNodeAllowc2cWlan4 OBJECT-TYPE
  SYNTAX OCTET STRING
  MAX-ACCESS read-write
  STATUS current
  DESCRIPTION "allow clients to see each other if wlan4.role=access"
  ::= { firewallNodeAllowc2c 5 }
-- .3.3.2 LEAF firewall.node.enable
firewallNodeEnable OBJECT-TYPE
  SYNTAX OCTET STRING
  MAX-ACCESS read-write
  STATUS current
  DESCRIPTION "enable firewall on the node"
  ::= { firewallNode 2 }
----------------------------------------------------
-- .3.3.3. BRANCH firewall.node.tcp.
--
firewallNodeTcp OBJECT IDENTIFIER ::= { firewallNode 3 }
----------------------------------------------------
-- .3.3.3.1. BRANCH firewall.node.tcp.allow.
--
firewallNodeTcpAllow OBJECT IDENTIFIER ::= { firewallNodeTcp 1 }
-- .3.3.3.1.1 LEAF firewall.node.tcp.allow.dest
firewallNodeTcpAllowDest OBJECT-TYPE
  SYNTAX OCTET STRING
  MAX-ACCESS read-write
  STATUS current
  DESCRIPTION "tcp dest ports (space separated) to allow to this node"
  ::= { firewallNodeTcpAllow 1 }
-- .3.3.3.1.2 LEAF firewall.node.tcp.allow.source
firewallNodeTcpAllowSource OBJECT-TYPE
  SYNTAX OCTET STRING
  MAX-ACCESS read-write
  STATUS current
  DESCRIPTION "tcp source ports (space separated) to allow to this node"
  ::= { firewallNodeTcpAllow 2 }
----------------------------------------------------
-- .3.3.4. BRANCH firewall.node.udp.
--
firewallNodeUdp OBJECT IDENTIFIER ::= { firewallNode 4 }
----------------------------------------------------
-- .3.3.4.1. BRANCH firewall.node.udp.allow.
--
firewallNodeUdpAllow OBJECT IDENTIFIER ::= { firewallNodeUdp 1 }
-- .3.3.4.1.1 LEAF firewall.node.udp.allow.dest
firewallNodeUdpAllowDest OBJECT-TYPE
  SYNTAX OCTET STRING
  MAX-ACCESS read-write
  STATUS current
  DESCRIPTION "udp dest ports (space separated) to allow to this node"
  ::= { firewallNodeUdpAllow 1 }
-- .3.3.4.1.2 LEAF firewall.node.udp.allow.source
firewallNodeUdpAllowSource OBJECT-TYPE
  SYNTAX OCTET STRING
  MAX-ACCESS read-write
  STATUS current
  DESCRIPTION "udp source ports (space separated) to allow to this node"
  ::= { firewallNodeUdpAllow 2 }
----------------------------------------------------
-- .4. BRANCH qos.
--
qos OBJECT IDENTIFIER ::= { enRoute 4 }
-- .4.1 LEAF qos.enable
qosEnable OBJECT-TYPE
  SYNTAX OCTET STRING
  MAX-ACCESS read-write
  STATUS current
  DESCRIPTION "qos enabled? if not, nothing else here matters."
  ::= { qos 1 }
-- .4.2 LEAF qos.extra
qosExtra OBJECT-TYPE
  SYNTAX OCTET STRING
  MAX-ACCESS read-write
  STATUS current
  DESCRIPTION "space separated list of extra <key>=<limit> qos values"
  ::= { qos 2 }
----------------------------------------------------
-- .4.3. BRANCH qos.in.
--
qosIn OBJECT IDENTIFIER ::= { qos 3 }
----------------------------------------------------
-- .4.3.1. BRANCH qos.in.default.
--
qosInDefault OBJECT IDENTIFIER ::= { qosIn 1 }
-- .4.3.1.1 LEAF qos.in.default.flow_priority
qosInDefaultFlowpriority OBJECT-TYPE
  SYNTAX OCTET STRING
  MAX-ACCESS read-write
  STATUS current
  DESCRIPTION "input flow priority 0-99 or 'inherit' (higher is higher priority)"
  ::= { qosInDefault 1 }
----------------------------------------------------
-- .4.3.1.2. BRANCH qos.in.default.hwpri.
--
qosInDefaultHwpri OBJECT IDENTIFIER ::= { qosInDefault 2 }
-- .4.3.1.2.1 LEAF qos.in.default.hwpri.max
qosInDefaultHwpriMax OBJECT-TYPE
  SYNTAX OCTET STRING
  MAX-ACCESS read-write
  STATUS current
  DESCRIPTION "max hardware priority on output (1-4, 0 for default, or 'inherit')"
  ::= { qosInDefaultHwpri 1 }
-- .4.3.1.2.2 LEAF qos.in.default.hwpri.min
qosInDefaultHwpriMin OBJECT-TYPE
  SYNTAX OCTET STRING
  MAX-ACCESS read-write
  STATUS current
  DESCRIPTION "min hardware priority on output (1-4, 0 for default, or 'inherit')"
  ::= { qosInDefaultHwpri 2 }
----------------------------------------------------
-- .4.3.2. BRANCH qos.in.eth0.
--
qosInEth0 OBJECT IDENTIFIER ::= { qosIn 2 }
-- .4.3.2.1 LEAF qos.in.eth0.flow_priority
qosInEth0Flowpriority OBJECT-TYPE
  SYNTAX OCTET STRING
  MAX-ACCESS read-write
  STATUS current
  DESCRIPTION "input flow priority 0-99 or 'inherit' (higher is higher priority)"
  ::= { qosInEth0 1 }
----------------------------------------------------
-- .4.3.2.2. BRANCH qos.in.eth0.hwpri.
--
qosInEth0Hwpri OBJECT IDENTIFIER ::= { qosInEth0 2 }
-- .4.3.2.2.1 LEAF qos.in.eth0.hwpri.max
qosInEth0HwpriMax OBJECT-TYPE
  SYNTAX OCTET STRING
  MAX-ACCESS read-write
  STATUS current
  DESCRIPTION "max hardware priority on output (1-4, 0 for default, or 'inherit')"
  ::= { qosInEth0Hwpri 1 }
-- .4.3.2.2.2 LEAF qos.in.eth0.hwpri.min
qosInEth0HwpriMin OBJECT-TYPE
  SYNTAX OCTET STRING
  MAX-ACCESS read-write
  STATUS current
  DESCRIPTION "min hardware priority on output (1-4, 0 for default, or 'inherit')"
  ::= { qosInEth0Hwpri 2 }
----------------------------------------------------
-- .4.3.3. BRANCH qos.in.local.
--
qosInLocal OBJECT IDENTIFIER ::= { qosIn 3 }
-- .4.3.3.1 LEAF qos.in.local.flow_priority
qosInLocalFlowpriority OBJECT-TYPE
  SYNTAX OCTET STRING
  MAX-ACCESS read-write
  STATUS current
  DESCRIPTION "input flow priority 0-99 or 'inherit' (higher is higher priority)"
  ::= { qosInLocal 1 }
----------------------------------------------------
-- .4.3.3.2. BRANCH qos.in.local.hwpri.
--
qosInLocalHwpri OBJECT IDENTIFIER ::= { qosInLocal 2 }
-- .4.3.3.2.1 LEAF qos.in.local.hwpri.max
qosInLocalHwpriMax OBJECT-TYPE
  SYNTAX OCTET STRING
  MAX-ACCESS read-write
  STATUS current
  DESCRIPTION "max hardware priority on output (1-4, 0 for default, or 'inherit')"
  ::= { qosInLocalHwpri 1 }
-- .4.3.3.2.2 LEAF qos.in.local.hwpri.min
qosInLocalHwpriMin OBJECT-TYPE
  SYNTAX OCTET STRING
  MAX-ACCESS read-write
  STATUS current
  DESCRIPTION "min hardware priority on output (1-4, 0 for default, or 'inherit')"
  ::= { qosInLocalHwpri 2 }
----------------------------------------------------
-- .4.3.4. BRANCH qos.in.wlan0.
--
qosInWlan0 OBJECT IDENTIFIER ::= { qosIn 4 }
-- .4.3.4.1 LEAF qos.in.wlan0.flow_priority
qosInWlan0Flowpriority OBJECT-TYPE
  SYNTAX OCTET STRING
  MAX-ACCESS read-write
  STATUS current
  DESCRIPTION "input flow priority 0-99 or 'inherit' (higher is higher priority)"
  ::= { qosInWlan0 1 }
----------------------------------------------------
-- .4.3.4.2. BRANCH qos.in.wlan0.hwpri.
--
qosInWlan0Hwpri OBJECT IDENTIFIER ::= { qosInWlan0 2 }
-- .4.3.4.2.1 LEAF qos.in.wlan0.hwpri.max
qosInWlan0HwpriMax OBJECT-TYPE
  SYNTAX OCTET STRING
  MAX-ACCESS read-write
  STATUS current
  DESCRIPTION "max hardware priority on output (1-4, 0 for default, or 'inherit')"
  ::= { qosInWlan0Hwpri 1 }
-- .4.3.4.2.2 LEAF qos.in.wlan0.hwpri.min
qosInWlan0HwpriMin OBJECT-TYPE
  SYNTAX OCTET STRING
  MAX-ACCESS read-write
  STATUS current
  DESCRIPTION "min hardware priority on output (1-4, 0 for default, or 'inherit')"
  ::= { qosInWlan0Hwpri 2 }
----------------------------------------------------
-- .4.3.5. BRANCH qos.in.wlan1.
--
qosInWlan1 OBJECT IDENTIFIER ::= { qosIn 5 }
-- .4.3.5.1 LEAF qos.in.wlan1.flow_priority
qosInWlan1Flowpriority OBJECT-TYPE
  SYNTAX OCTET STRING
  MAX-ACCESS read-write
  STATUS current
  DESCRIPTION "input flow priority 0-99 or 'inherit' (higher is higher priority)"
  ::= { qosInWlan1 1 }
----------------------------------------------------
-- .4.3.5.2. BRANCH qos.in.wlan1.hwpri.
--
qosInWlan1Hwpri OBJECT IDENTIFIER ::= { qosInWlan1 2 }
-- .4.3.5.2.1 LEAF qos.in.wlan1.hwpri.max
qosInWlan1HwpriMax OBJECT-TYPE
  SYNTAX OCTET STRING
  MAX-ACCESS read-write
  STATUS current
  DESCRIPTION "max hardware priority on output (1-4, 0 for default, or 'inherit')"
  ::= { qosInWlan1Hwpri 1 }
-- .4.3.5.2.2 LEAF qos.in.wlan1.hwpri.min
qosInWlan1HwpriMin OBJECT-TYPE
  SYNTAX OCTET STRING
  MAX-ACCESS read-write
  STATUS current
  DESCRIPTION "min hardware priority on output (1-4, 0 for default, or 'inherit')"
  ::= { qosInWlan1Hwpri 2 }
----------------------------------------------------
-- .4.3.6. BRANCH qos.in.wlan2.
--
qosInWlan2 OBJECT IDENTIFIER ::= { qosIn 6 }
-- .4.3.6.1 LEAF qos.in.wlan2.flow_priority
qosInWlan2Flowpriority OBJECT-TYPE
  SYNTAX OCTET STRING
  MAX-ACCESS read-write
  STATUS current
  DESCRIPTION "input flow priority 0-99 or 'inherit' (higher is higher priority)"
  ::= { qosInWlan2 1 }
----------------------------------------------------
-- .4.3.6.2. BRANCH qos.in.wlan2.hwpri.
--
qosInWlan2Hwpri OBJECT IDENTIFIER ::= { qosInWlan2 2 }
-- .4.3.6.2.1 LEAF qos.in.wlan2.hwpri.max
qosInWlan2HwpriMax OBJECT-TYPE
  SYNTAX OCTET STRING
  MAX-ACCESS read-write
  STATUS current
  DESCRIPTION "max hardware priority on output (1-4, 0 for default, or 'inherit')"
  ::= { qosInWlan2Hwpri 1 }
-- .4.3.6.2.2 LEAF qos.in.wlan2.hwpri.min
qosInWlan2HwpriMin OBJECT-TYPE
  SYNTAX OCTET STRING
  MAX-ACCESS read-write
  STATUS current
  DESCRIPTION "min hardware priority on output (1-4, 0 for default, or 'inherit')"
  ::= { qosInWlan2Hwpri 2 }
----------------------------------------------------
-- .4.3.7. BRANCH qos.in.wlan3.
--
qosInWlan3 OBJECT IDENTIFIER ::= { qosIn 7 }
-- .4.3.7.1 LEAF qos.in.wlan3.flow_priority
qosInWlan3Flowpriority OBJECT-TYPE
  SYNTAX OCTET STRING
  MAX-ACCESS read-write
  STATUS current
  DESCRIPTION "input flow priority 0-99 or 'inherit' (higher is higher priority)"
  ::= { qosInWlan3 1 }
----------------------------------------------------
-- .4.3.7.2. BRANCH qos.in.wlan3.hwpri.
--
qosInWlan3Hwpri OBJECT IDENTIFIER ::= { qosInWlan3 2 }
-- .4.3.7.2.1 LEAF qos.in.wlan3.hwpri.max
qosInWlan3HwpriMax OBJECT-TYPE
  SYNTAX OCTET STRING
  MAX-ACCESS read-write
  STATUS current
  DESCRIPTION "max hardware priority on output (1-4, 0 for default, or 'inherit')"
  ::= { qosInWlan3Hwpri 1 }
-- .4.3.7.2.2 LEAF qos.in.wlan3.hwpri.min
qosInWlan3HwpriMin OBJECT-TYPE
  SYNTAX OCTET STRING
  MAX-ACCESS read-write
  STATUS current
  DESCRIPTION "min hardware priority on output (1-4, 0 for default, or 'inherit')"
  ::= { qosInWlan3Hwpri 2 }
----------------------------------------------------
-- .4.3.8. BRANCH qos.in.wlan4.
--
qosInWlan4 OBJECT IDENTIFIER ::= { qosIn 8 }
-- .4.3.8.1 LEAF qos.in.wlan4.flow_priority
qosInWlan4Flowpriority OBJECT-TYPE
  SYNTAX OCTET STRING
  MAX-ACCESS read-write
  STATUS current
  DESCRIPTION "input flow priority 0-99 or 'inherit' (higher is higher priority)"
  ::= { qosInWlan4 1 }
----------------------------------------------------
-- .4.3.8.2. BRANCH qos.in.wlan4.hwpri.
--
qosInWlan4Hwpri OBJECT IDENTIFIER ::= { qosInWlan4 2 }
-- .4.3.8.2.1 LEAF qos.in.wlan4.hwpri.max
qosInWlan4HwpriMax OBJECT-TYPE
  SYNTAX OCTET STRING
  MAX-ACCESS read-write
  STATUS current
  DESCRIPTION "max hardware priority on output (1-4, 0 for default, or 'inherit')"
  ::= { qosInWlan4Hwpri 1 }
-- .4.3.8.2.2 LEAF qos.in.wlan4.hwpri.min
qosInWlan4HwpriMin OBJECT-TYPE
  SYNTAX OCTET STRING
  MAX-ACCESS read-write
  STATUS current
  DESCRIPTION "min hardware priority on output (1-4, 0 for default, or 'inherit')"
  ::= { qosInWlan4Hwpri 2 }
----------------------------------------------------
-- .4.4. BRANCH qos.out.
--
qosOut OBJECT IDENTIFIER ::= { qos 4 }
----------------------------------------------------
-- .4.4.1. BRANCH qos.out.default.
--
qosOutDefault OBJECT IDENTIFIER ::= { qosOut 1 }
----------------------------------------------------
-- .4.4.1.1. BRANCH qos.out.default.default.
--
qosOutDefaultDefault OBJECT IDENTIFIER ::= { qosOutDefault 1 }
-- .4.4.1.1.1 LEAF qos.out.default.default.limit
qosOutDefaultDefaultLimit OBJECT-TYPE
  SYNTAX OCTET STRING
  MAX-ACCESS read-write
  STATUS current
  DESCRIPTION "max bw for all data coming from default"
  ::= { qosOutDefaultDefault 1 }
-- .4.4.1.1.2 LEAF qos.out.default.default.reserve
qosOutDefaultDefaultReserve OBJECT-TYPE
  SYNTAX OCTET STRING
  MAX-ACCESS read-write
  STATUS current
  DESCRIPTION "reserved bw for all data coming from default"
  ::= { qosOutDefaultDefault 2 }
----------------------------------------------------
-- .4.4.1.2. BRANCH qos.out.default.eth0.
--
qosOutDefaultEth0 OBJECT IDENTIFIER ::= { qosOutDefault 2 }
-- .4.4.1.2.1 LEAF qos.out.default.eth0.limit
qosOutDefaultEth0Limit OBJECT-TYPE
  SYNTAX OCTET STRING
  MAX-ACCESS read-write
  STATUS current
  DESCRIPTION "max bw for all data coming from eth0"
  ::= { qosOutDefaultEth0 1 }
-- .4.4.1.2.2 LEAF qos.out.default.eth0.reserve
qosOutDefaultEth0Reserve OBJECT-TYPE
  SYNTAX OCTET STRING
  MAX-ACCESS read-write
  STATUS current
  DESCRIPTION "reserved bw for all data coming from eth0"
  ::= { qosOutDefaultEth0 2 }
-- .4.4.1.3 LEAF qos.out.default.limit
qosOutDefaultLimit OBJECT-TYPE
  SYNTAX OCTET STRING
  MAX-ACCESS read-write
  STATUS current
  DESCRIPTION "limit total output rate. *if blank, no other rates are used*"
  ::= { qosOutDefault 3 }
----------------------------------------------------
-- .4.4.1.4. BRANCH qos.out.default.local.
--
qosOutDefaultLocal OBJECT IDENTIFIER ::= { qosOutDefault 4 }
-- .4.4.1.4.1 LEAF qos.out.default.local.limit
qosOutDefaultLocalLimit OBJECT-TYPE
  SYNTAX OCTET STRING
  MAX-ACCESS read-write
  STATUS current
  DESCRIPTION "max bw for all data coming from local"
  ::= { qosOutDefaultLocal 1 }
-- .4.4.1.4.2 LEAF qos.out.default.local.reserve
qosOutDefaultLocalReserve OBJECT-TYPE
  SYNTAX OCTET STRING
  MAX-ACCESS read-write
  STATUS current
  DESCRIPTION "reserved bw for all data coming from local"
  ::= { qosOutDefaultLocal 2 }
----------------------------------------------------
-- .4.4.1.5. BRANCH qos.out.default.wlan0.
--
qosOutDefaultWlan0 OBJECT IDENTIFIER ::= { qosOutDefault 5 }
-- .4.4.1.5.1 LEAF qos.out.default.wlan0.limit
qosOutDefaultWlan0Limit OBJECT-TYPE
  SYNTAX OCTET STRING
  MAX-ACCESS read-write
  STATUS current
  DESCRIPTION "max bw for all data coming from wlan0"
  ::= { qosOutDefaultWlan0 1 }
-- .4.4.1.5.2 LEAF qos.out.default.wlan0.reserve
qosOutDefaultWlan0Reserve OBJECT-TYPE
  SYNTAX OCTET STRING
  MAX-ACCESS read-write
  STATUS current
  DESCRIPTION "reserved bw for all data coming from wlan0"
  ::= { qosOutDefaultWlan0 2 }
----------------------------------------------------
-- .4.4.1.6. BRANCH qos.out.default.wlan1.
--
qosOutDefaultWlan1 OBJECT IDENTIFIER ::= { qosOutDefault 6 }
-- .4.4.1.6.1 LEAF qos.out.default.wlan1.limit
qosOutDefaultWlan1Limit OBJECT-TYPE
  SYNTAX OCTET STRING
  MAX-ACCESS read-write
  STATUS current
  DESCRIPTION "max bw for all data coming from wlan1"
  ::= { qosOutDefaultWlan1 1 }
-- .4.4.1.6.2 LEAF qos.out.default.wlan1.reserve
qosOutDefaultWlan1Reserve OBJECT-TYPE
  SYNTAX OCTET STRING
  MAX-ACCESS read-write
  STATUS current
  DESCRIPTION "reserved bw for all data coming from wlan1"
  ::= { qosOutDefaultWlan1 2 }
----------------------------------------------------
-- .4.4.1.7. BRANCH qos.out.default.wlan2.
--
qosOutDefaultWlan2 OBJECT IDENTIFIER ::= { qosOutDefault 7 }
-- .4.4.1.7.1 LEAF qos.out.default.wlan2.limit
qosOutDefaultWlan2Limit OBJECT-TYPE
  SYNTAX OCTET STRING
  MAX-ACCESS read-write
  STATUS current
  DESCRIPTION "max bw for all data coming from wlan2"
  ::= { qosOutDefaultWlan2 1 }
-- .4.4.1.7.2 LEAF qos.out.default.wlan2.reserve
qosOutDefaultWlan2Reserve OBJECT-TYPE
  SYNTAX OCTET STRING
  MAX-ACCESS read-write
  STATUS current
  DESCRIPTION "reserved bw for all data coming from wlan2"
  ::= { qosOutDefaultWlan2 2 }
----------------------------------------------------
-- .4.4.1.8. BRANCH qos.out.default.wlan3.
--
qosOutDefaultWlan3 OBJECT IDENTIFIER ::= { qosOutDefault 8 }
-- .4.4.1.8.1 LEAF qos.out.default.wlan3.limit
qosOutDefaultWlan3Limit OBJECT-TYPE
  SYNTAX OCTET STRING
  MAX-ACCESS read-write
  STATUS current
  DESCRIPTION "max bw for all data coming from wlan3"
  ::= { qosOutDefaultWlan3 1 }
-- .4.4.1.8.2 LEAF qos.out.default.wlan3.reserve
qosOutDefaultWlan3Reserve OBJECT-TYPE
  SYNTAX OCTET STRING
  MAX-ACCESS read-write
  STATUS current
  DESCRIPTION "reserved bw for all data coming from wlan3"
  ::= { qosOutDefaultWlan3 2 }
----------------------------------------------------
-- .4.4.1.9. BRANCH qos.out.default.wlan4.
--
qosOutDefaultWlan4 OBJECT IDENTIFIER ::= { qosOutDefault 9 }
-- .4.4.1.9.1 LEAF qos.out.default.wlan4.limit
qosOutDefaultWlan4Limit OBJECT-TYPE
  SYNTAX OCTET STRING
  MAX-ACCESS read-write
  STATUS current
  DESCRIPTION "max bw for all data coming from wlan4"
  ::= { qosOutDefaultWlan4 1 }
-- .4.4.1.9.2 LEAF qos.out.default.wlan4.reserve
qosOutDefaultWlan4Reserve OBJECT-TYPE
  SYNTAX OCTET STRING
  MAX-ACCESS read-write
  STATUS current
  DESCRIPTION "reserved bw for all data coming from wlan4"
  ::= { qosOutDefaultWlan4 2 }
----------------------------------------------------
-- .4.4.2. BRANCH qos.out.wlan0.
--
qosOutWlan0 OBJECT IDENTIFIER ::= { qosOut 2 }
----------------------------------------------------
-- .4.4.2.1. BRANCH qos.out.wlan0.default.
--
qosOutWlan0Default OBJECT IDENTIFIER ::= { qosOutWlan0 1 }
----------------------------------------------------
-- .4.4.2.1.1. BRANCH qos.out.wlan0.default.be.
--
qosOutWlan0DefaultBe OBJECT IDENTIFIER ::= { qosOutWlan0Default 1 }
-- .4.4.2.1.1.1 LEAF qos.out.wlan0.default.be.limit
qosOutWlan0DefaultBeLimit OBJECT-TYPE
  SYNTAX OCTET STRING
  MAX-ACCESS read-write
  STATUS current
  DESCRIPTION "max bw for BE data coming from default"
  ::= { qosOutWlan0DefaultBe 1 }
-- .4.4.2.1.1.2 LEAF qos.out.wlan0.default.be.reserve
qosOutWlan0DefaultBeReserve OBJECT-TYPE
  SYNTAX OCTET STRING
  MAX-ACCESS read-write
  STATUS current
  DESCRIPTION "reserved bw for BE data coming from default"
  ::= { qosOutWlan0DefaultBe 2 }
----------------------------------------------------
-- .4.4.2.1.2. BRANCH qos.out.wlan0.default.bk.
--
qosOutWlan0DefaultBk OBJECT IDENTIFIER ::= { qosOutWlan0Default 2 }
-- .4.4.2.1.2.1 LEAF qos.out.wlan0.default.bk.limit
qosOutWlan0DefaultBkLimit OBJECT-TYPE
  SYNTAX OCTET STRING
  MAX-ACCESS read-write
  STATUS current
  DESCRIPTION "max bw for BK data coming from default"
  ::= { qosOutWlan0DefaultBk 1 }
-- .4.4.2.1.2.2 LEAF qos.out.wlan0.default.bk.reserve
qosOutWlan0DefaultBkReserve OBJECT-TYPE
  SYNTAX OCTET STRING
  MAX-ACCESS read-write
  STATUS current
  DESCRIPTION "reserved bw for BK data coming from default"
  ::= { qosOutWlan0DefaultBk 2 }
-- .4.4.2.1.3 LEAF qos.out.wlan0.default.limit
qosOutWlan0DefaultLimit OBJECT-TYPE
  SYNTAX OCTET STRING
  MAX-ACCESS read-write
  STATUS current
  DESCRIPTION "max bw for all data coming from default"
  ::= { qosOutWlan0Default 3 }
-- .4.4.2.1.4 LEAF qos.out.wlan0.default.reserve
qosOutWlan0DefaultReserve OBJECT-TYPE
  SYNTAX OCTET STRING
  MAX-ACCESS read-write
  STATUS current
  DESCRIPTION "reserved bw for all data coming from default"
  ::= { qosOutWlan0Default 4 }
----------------------------------------------------
-- .4.4.2.1.5. BRANCH qos.out.wlan0.default.vi.
--
qosOutWlan0DefaultVi OBJECT IDENTIFIER ::= { qosOutWlan0Default 5 }
-- .4.4.2.1.5.1 LEAF qos.out.wlan0.default.vi.limit
qosOutWlan0DefaultViLimit OBJECT-TYPE
  SYNTAX OCTET STRING
  MAX-ACCESS read-write
  STATUS current
  DESCRIPTION "max bw for VI data coming from default"
  ::= { qosOutWlan0DefaultVi 1 }
-- .4.4.2.1.5.2 LEAF qos.out.wlan0.default.vi.reserve
qosOutWlan0DefaultViReserve OBJECT-TYPE
  SYNTAX OCTET STRING
  MAX-ACCESS read-write
  STATUS current
  DESCRIPTION "reserved bw for VI data coming from default"
  ::= { qosOutWlan0DefaultVi 2 }
----------------------------------------------------
-- .4.4.2.1.6. BRANCH qos.out.wlan0.default.vo.
--
qosOutWlan0DefaultVo OBJECT IDENTIFIER ::= { qosOutWlan0Default 6 }
-- .4.4.2.1.6.1 LEAF qos.out.wlan0.default.vo.limit
qosOutWlan0DefaultVoLimit OBJECT-TYPE
  SYNTAX OCTET STRING
  MAX-ACCESS read-write
  STATUS current
  DESCRIPTION "max bw for VO data coming from default"
  ::= { qosOutWlan0DefaultVo 1 }
-- .4.4.2.1.6.2 LEAF qos.out.wlan0.default.vo.reserve
qosOutWlan0DefaultVoReserve OBJECT-TYPE
  SYNTAX OCTET STRING
  MAX-ACCESS read-write
  STATUS current
  DESCRIPTION "reserved bw for VO data coming from default"
  ::= { qosOutWlan0DefaultVo 2 }
----------------------------------------------------
-- .4.4.2.2. BRANCH qos.out.wlan0.eth0.
--
qosOutWlan0Eth0 OBJECT IDENTIFIER ::= { qosOutWlan0 2 }
----------------------------------------------------
-- .4.4.2.2.1. BRANCH qos.out.wlan0.eth0.be.
--
qosOutWlan0Eth0Be OBJECT IDENTIFIER ::= { qosOutWlan0Eth0 1 }
-- .4.4.2.2.1.1 LEAF qos.out.wlan0.eth0.be.limit
qosOutWlan0Eth0BeLimit OBJECT-TYPE
  SYNTAX OCTET STRING
  MAX-ACCESS read-write
  STATUS current
  DESCRIPTION "max bw for BE data coming from eth0"
  ::= { qosOutWlan0Eth0Be 1 }
-- .4.4.2.2.1.2 LEAF qos.out.wlan0.eth0.be.reserve
qosOutWlan0Eth0BeReserve OBJECT-TYPE
  SYNTAX OCTET STRING
  MAX-ACCESS read-write
  STATUS current
  DESCRIPTION "reserved bw for BE data coming from eth0"
  ::= { qosOutWlan0Eth0Be 2 }
----------------------------------------------------
-- .4.4.2.2.2. BRANCH qos.out.wlan0.eth0.bk.
--
qosOutWlan0Eth0Bk OBJECT IDENTIFIER ::= { qosOutWlan0Eth0 2 }
-- .4.4.2.2.2.1 LEAF qos.out.wlan0.eth0.bk.limit
qosOutWlan0Eth0BkLimit OBJECT-TYPE
  SYNTAX OCTET STRING
  MAX-ACCESS read-write
  STATUS current
  DESCRIPTION "max bw for BK data coming from eth0"
  ::= { qosOutWlan0Eth0Bk 1 }
-- .4.4.2.2.2.2 LEAF qos.out.wlan0.eth0.bk.reserve
qosOutWlan0Eth0BkReserve OBJECT-TYPE
  SYNTAX OCTET STRING
  MAX-ACCESS read-write
  STATUS current
  DESCRIPTION "reserved bw for BK data coming from eth0"
  ::= { qosOutWlan0Eth0Bk 2 }
-- .4.4.2.2.3 LEAF qos.out.wlan0.eth0.limit
qosOutWlan0Eth0Limit OBJECT-TYPE
  SYNTAX OCTET STRING
  MAX-ACCESS read-write
  STATUS current
  DESCRIPTION "max bw for all data coming from eth0"
  ::= { qosOutWlan0Eth0 3 }
-- .4.4.2.2.4 LEAF qos.out.wlan0.eth0.reserve
qosOutWlan0Eth0Reserve OBJECT-TYPE
  SYNTAX OCTET STRING
  MAX-ACCESS read-write
  STATUS current
  DESCRIPTION "reserved bw for all data coming from eth0"
  ::= { qosOutWlan0Eth0 4 }
----------------------------------------------------
-- .4.4.2.2.5. BRANCH qos.out.wlan0.eth0.vi.
--
qosOutWlan0Eth0Vi OBJECT IDENTIFIER ::= { qosOutWlan0Eth0 5 }
-- .4.4.2.2.5.1 LEAF qos.out.wlan0.eth0.vi.limit
qosOutWlan0Eth0ViLimit OBJECT-TYPE
  SYNTAX OCTET STRING
  MAX-ACCESS read-write
  STATUS current
  DESCRIPTION "max bw for VI data coming from eth0"
  ::= { qosOutWlan0Eth0Vi 1 }
-- .4.4.2.2.5.2 LEAF qos.out.wlan0.eth0.vi.reserve
qosOutWlan0Eth0ViReserve OBJECT-TYPE
  SYNTAX OCTET STRING
  MAX-ACCESS read-write
  STATUS current
  DESCRIPTION "reserved bw for VI data coming from eth0"
  ::= { qosOutWlan0Eth0Vi 2 }
----------------------------------------------------
-- .4.4.2.2.6. BRANCH qos.out.wlan0.eth0.vo.
--
qosOutWlan0Eth0Vo OBJECT IDENTIFIER ::= { qosOutWlan0Eth0 6 }
-- .4.4.2.2.6.1 LEAF qos.out.wlan0.eth0.vo.limit
qosOutWlan0Eth0VoLimit OBJECT-TYPE
  SYNTAX OCTET STRING
  MAX-ACCESS read-write
  STATUS current
  DESCRIPTION "max bw for VO data coming from eth0"
  ::= { qosOutWlan0Eth0Vo 1 }
-- .4.4.2.2.6.2 LEAF qos.out.wlan0.eth0.vo.reserve
qosOutWlan0Eth0VoReserve OBJECT-TYPE
  SYNTAX OCTET STRING
  MAX-ACCESS read-write
  STATUS current
  DESCRIPTION "reserved bw for VO data coming from eth0"
  ::= { qosOutWlan0Eth0Vo 2 }
-- .4.4.2.3 LEAF qos.out.wlan0.limit
qosOutWlan0Limit OBJECT-TYPE
  SYNTAX OCTET STRING
  MAX-ACCESS read-write
  STATUS current
  DESCRIPTION "limit total output rate. *if blank, no other rates are used*"
  ::= { qosOutWlan0 3 }
----------------------------------------------------
-- .4.4.2.4. BRANCH qos.out.wlan0.local.
--
qosOutWlan0Local OBJECT IDENTIFIER ::= { qosOutWlan0 4 }
----------------------------------------------------
-- .4.4.2.4.1. BRANCH qos.out.wlan0.local.be.
--
qosOutWlan0LocalBe OBJECT IDENTIFIER ::= { qosOutWlan0Local 1 }
-- .4.4.2.4.1.1 LEAF qos.out.wlan0.local.be.limit
qosOutWlan0LocalBeLimit OBJECT-TYPE
  SYNTAX OCTET STRING
  MAX-ACCESS read-write
  STATUS current
  DESCRIPTION "max bw for BE data coming from local"
  ::= { qosOutWlan0LocalBe 1 }
-- .4.4.2.4.1.2 LEAF qos.out.wlan0.local.be.reserve
qosOutWlan0LocalBeReserve OBJECT-TYPE
  SYNTAX OCTET STRING
  MAX-ACCESS read-write
  STATUS current
  DESCRIPTION "reserved bw for BE data coming from local"
  ::= { qosOutWlan0LocalBe 2 }
----------------------------------------------------
-- .4.4.2.4.2. BRANCH qos.out.wlan0.local.bk.
--
qosOutWlan0LocalBk OBJECT IDENTIFIER ::= { qosOutWlan0Local 2 }
-- .4.4.2.4.2.1 LEAF qos.out.wlan0.local.bk.limit
qosOutWlan0LocalBkLimit OBJECT-TYPE
  SYNTAX OCTET STRING
  MAX-ACCESS read-write
  STATUS current
  DESCRIPTION "max bw for BK data coming from local"
  ::= { qosOutWlan0LocalBk 1 }
-- .4.4.2.4.2.2 LEAF qos.out.wlan0.local.bk.reserve
qosOutWlan0LocalBkReserve OBJECT-TYPE
  SYNTAX OCTET STRING
  MAX-ACCESS read-write
  STATUS current
  DESCRIPTION "reserved bw for BK data coming from local"
  ::= { qosOutWlan0LocalBk 2 }
-- .4.4.2.4.3 LEAF qos.out.wlan0.local.limit
qosOutWlan0LocalLimit OBJECT-TYPE
  SYNTAX OCTET STRING
  MAX-ACCESS read-write
  STATUS current
  DESCRIPTION "max bw for all data coming from local"
  ::= { qosOutWlan0Local 3 }
-- .4.4.2.4.4 LEAF qos.out.wlan0.local.reserve
qosOutWlan0LocalReserve OBJECT-TYPE
  SYNTAX OCTET STRING
  MAX-ACCESS read-write
  STATUS current
  DESCRIPTION "reserved bw for all data coming from local"
  ::= { qosOutWlan0Local 4 }
----------------------------------------------------
-- .4.4.2.4.5. BRANCH qos.out.wlan0.local.vi.
--
qosOutWlan0LocalVi OBJECT IDENTIFIER ::= { qosOutWlan0Local 5 }
-- .4.4.2.4.5.1 LEAF qos.out.wlan0.local.vi.limit
qosOutWlan0LocalViLimit OBJECT-TYPE
  SYNTAX OCTET STRING
  MAX-ACCESS read-write
  STATUS current
  DESCRIPTION "max bw for VI data coming from local"
  ::= { qosOutWlan0LocalVi 1 }
-- .4.4.2.4.5.2 LEAF qos.out.wlan0.local.vi.reserve
qosOutWlan0LocalViReserve OBJECT-TYPE
  SYNTAX OCTET STRING
  MAX-ACCESS read-write
  STATUS current
  DESCRIPTION "reserved bw for VI data coming from local"
  ::= { qosOutWlan0LocalVi 2 }
----------------------------------------------------
-- .4.4.2.4.6. BRANCH qos.out.wlan0.local.vo.
--
qosOutWlan0LocalVo OBJECT IDENTIFIER ::= { qosOutWlan0Local 6 }
-- .4.4.2.4.6.1 LEAF qos.out.wlan0.local.vo.limit
qosOutWlan0LocalVoLimit OBJECT-TYPE
  SYNTAX OCTET STRING
  MAX-ACCESS read-write
  STATUS current
  DESCRIPTION "max bw for VO data coming from local"
  ::= { qosOutWlan0LocalVo 1 }
-- .4.4.2.4.6.2 LEAF qos.out.wlan0.local.vo.reserve
qosOutWlan0LocalVoReserve OBJECT-TYPE
  SYNTAX OCTET STRING
  MAX-ACCESS read-write
  STATUS current
  DESCRIPTION "reserved bw for VO data coming from local"
  ::= { qosOutWlan0LocalVo 2 }
----------------------------------------------------
-- .4.4.2.5. BRANCH qos.out.wlan0.wlan0.
--
qosOutWlan0Wlan0 OBJECT IDENTIFIER ::= { qosOutWlan0 5 }
----------------------------------------------------
-- .4.4.2.5.1. BRANCH qos.out.wlan0.wlan0.be.
--
qosOutWlan0Wlan0Be OBJECT IDENTIFIER ::= { qosOutWlan0Wlan0 1 }
-- .4.4.2.5.1.1 LEAF qos.out.wlan0.wlan0.be.limit
qosOutWlan0Wlan0BeLimit OBJECT-TYPE
  SYNTAX OCTET STRING
  MAX-ACCESS read-write
  STATUS current
  DESCRIPTION "max bw for BE data coming from wlan0"
  ::= { qosOutWlan0Wlan0Be 1 }
-- .4.4.2.5.1.2 LEAF qos.out.wlan0.wlan0.be.reserve
qosOutWlan0Wlan0BeReserve OBJECT-TYPE
  SYNTAX OCTET STRING
  MAX-ACCESS read-write
  STATUS current
  DESCRIPTION "reserved bw for BE data coming from wlan0"
  ::= { qosOutWlan0Wlan0Be 2 }
----------------------------------------------------
-- .4.4.2.5.2. BRANCH qos.out.wlan0.wlan0.bk.
--
qosOutWlan0Wlan0Bk OBJECT IDENTIFIER ::= { qosOutWlan0Wlan0 2 }
-- .4.4.2.5.2.1 LEAF qos.out.wlan0.wlan0.bk.limit
qosOutWlan0Wlan0BkLimit OBJECT-TYPE
  SYNTAX OCTET STRING
  MAX-ACCESS read-write
  STATUS current
  DESCRIPTION "max bw for BK data coming from wlan0"
  ::= { qosOutWlan0Wlan0Bk 1 }
-- .4.4.2.5.2.2 LEAF qos.out.wlan0.wlan0.bk.reserve
qosOutWlan0Wlan0BkReserve OBJECT-TYPE
  SYNTAX OCTET STRING
  MAX-ACCESS read-write
  STATUS current
  DESCRIPTION "reserved bw for BK data coming from wlan0"
  ::= { qosOutWlan0Wlan0Bk 2 }
-- .4.4.2.5.3 LEAF qos.out.wlan0.wlan0.limit
qosOutWlan0Wlan0Limit OBJECT-TYPE
  SYNTAX OCTET STRING
  MAX-ACCESS read-write
  STATUS current
  DESCRIPTION "max bw for all data coming from wlan0"
  ::= { qosOutWlan0Wlan0 3 }
-- .4.4.2.5.4 LEAF qos.out.wlan0.wlan0.reserve
qosOutWlan0Wlan0Reserve OBJECT-TYPE
  SYNTAX OCTET STRING
  MAX-ACCESS read-write
  STATUS current
  DESCRIPTION "reserved bw for all data coming from wlan0"
  ::= { qosOutWlan0Wlan0 4 }
----------------------------------------------------
-- .4.4.2.5.5. BRANCH qos.out.wlan0.wlan0.vi.
--
qosOutWlan0Wlan0Vi OBJECT IDENTIFIER ::= { qosOutWlan0Wlan0 5 }
-- .4.4.2.5.5.1 LEAF qos.out.wlan0.wlan0.vi.limit
qosOutWlan0Wlan0ViLimit OBJECT-TYPE
  SYNTAX OCTET STRING
  MAX-ACCESS read-write
  STATUS current
  DESCRIPTION "max bw for VI data coming from wlan0"
  ::= { qosOutWlan0Wlan0Vi 1 }
-- .4.4.2.5.5.2 LEAF qos.out.wlan0.wlan0.vi.reserve
qosOutWlan0Wlan0ViReserve OBJECT-TYPE
  SYNTAX OCTET STRING
  MAX-ACCESS read-write
  STATUS current
  DESCRIPTION "reserved bw for VI data coming from wlan0"
  ::= { qosOutWlan0Wlan0Vi 2 }
----------------------------------------------------
-- .4.4.2.5.6. BRANCH qos.out.wlan0.wlan0.vo.
--
qosOutWlan0Wlan0Vo OBJECT IDENTIFIER ::= { qosOutWlan0Wlan0 6 }
-- .4.4.2.5.6.1 LEAF qos.out.wlan0.wlan0.vo.limit
qosOutWlan0Wlan0VoLimit OBJECT-TYPE
  SYNTAX OCTET STRING
  MAX-ACCESS read-write
  STATUS current
  DESCRIPTION "max bw for VO data coming from wlan0"
  ::= { qosOutWlan0Wlan0Vo 1 }
-- .4.4.2.5.6.2 LEAF qos.out.wlan0.wlan0.vo.reserve
qosOutWlan0Wlan0VoReserve OBJECT-TYPE
  SYNTAX OCTET STRING
  MAX-ACCESS read-write
  STATUS current
  DESCRIPTION "reserved bw for VO data coming from wlan0"
  ::= { qosOutWlan0Wlan0Vo 2 }
----------------------------------------------------
-- .4.4.2.6. BRANCH qos.out.wlan0.wlan1.
--
qosOutWlan0Wlan1 OBJECT IDENTIFIER ::= { qosOutWlan0 6 }
----------------------------------------------------
-- .4.4.2.6.1. BRANCH qos.out.wlan0.wlan1.be.
--
qosOutWlan0Wlan1Be OBJECT IDENTIFIER ::= { qosOutWlan0Wlan1 1 }
-- .4.4.2.6.1.1 LEAF qos.out.wlan0.wlan1.be.limit
qosOutWlan0Wlan1BeLimit OBJECT-TYPE
  SYNTAX OCTET STRING
  MAX-ACCESS read-write
  STATUS current
  DESCRIPTION "max bw for BE data coming from wlan1"
  ::= { qosOutWlan0Wlan1Be 1 }
-- .4.4.2.6.1.2 LEAF qos.out.wlan0.wlan1.be.reserve
qosOutWlan0Wlan1BeReserve OBJECT-TYPE
  SYNTAX OCTET STRING
  MAX-ACCESS read-write
  STATUS current
  DESCRIPTION "reserved bw for BE data coming from wlan1"
  ::= { qosOutWlan0Wlan1Be 2 }
----------------------------------------------------
-- .4.4.2.6.2. BRANCH qos.out.wlan0.wlan1.bk.
--
qosOutWlan0Wlan1Bk OBJECT IDENTIFIER ::= { qosOutWlan0Wlan1 2 }
-- .4.4.2.6.2.1 LEAF qos.out.wlan0.wlan1.bk.limit
qosOutWlan0Wlan1BkLimit OBJECT-TYPE
  SYNTAX OCTET STRING
  MAX-ACCESS read-write
  STATUS current
  DESCRIPTION "max bw for BK data coming from wlan1"
  ::= { qosOutWlan0Wlan1Bk 1 }
-- .4.4.2.6.2.2 LEAF qos.out.wlan0.wlan1.bk.reserve
qosOutWlan0Wlan1BkReserve OBJECT-TYPE
  SYNTAX OCTET STRING
  MAX-ACCESS read-write
  STATUS current
  DESCRIPTION "reserved bw for BK data coming from wlan1"
  ::= { qosOutWlan0Wlan1Bk 2 }
-- .4.4.2.6.3 LEAF qos.out.wlan0.wlan1.limit
qosOutWlan0Wlan1Limit OBJECT-TYPE
  SYNTAX OCTET STRING
  MAX-ACCESS read-write
  STATUS current
  DESCRIPTION "max bw for all data coming from wlan1"
  ::= { qosOutWlan0Wlan1 3 }
-- .4.4.2.6.4 LEAF qos.out.wlan0.wlan1.reserve
qosOutWlan0Wlan1Reserve OBJECT-TYPE
  SYNTAX OCTET STRING
  MAX-ACCESS read-write
  STATUS current
  DESCRIPTION "reserved bw for all data coming from wlan1"
  ::= { qosOutWlan0Wlan1 4 }
----------------------------------------------------
-- .4.4.2.6.5. BRANCH qos.out.wlan0.wlan1.vi.
--
qosOutWlan0Wlan1Vi OBJECT IDENTIFIER ::= { qosOutWlan0Wlan1 5 }
-- .4.4.2.6.5.1 LEAF qos.out.wlan0.wlan1.vi.limit
qosOutWlan0Wlan1ViLimit OBJECT-TYPE
  SYNTAX OCTET STRING
  MAX-ACCESS read-write
  STATUS current
  DESCRIPTION "max bw for VI data coming from wlan1"
  ::= { qosOutWlan0Wlan1Vi 1 }
-- .4.4.2.6.5.2 LEAF qos.out.wlan0.wlan1.vi.reserve
qosOutWlan0Wlan1ViReserve OBJECT-TYPE
  SYNTAX OCTET STRING
  MAX-ACCESS read-write
  STATUS current
  DESCRIPTION "reserved bw for VI data coming from wlan1"
  ::= { qosOutWlan0Wlan1Vi 2 }
----------------------------------------------------
-- .4.4.2.6.6. BRANCH qos.out.wlan0.wlan1.vo.
--
qosOutWlan0Wlan1Vo OBJECT IDENTIFIER ::= { qosOutWlan0Wlan1 6 }
-- .4.4.2.6.6.1 LEAF qos.out.wlan0.wlan1.vo.limit
qosOutWlan0Wlan1VoLimit OBJECT-TYPE
  SYNTAX OCTET STRING
  MAX-ACCESS read-write
  STATUS current
  DESCRIPTION "max bw for VO data coming from wlan1"
  ::= { qosOutWlan0Wlan1Vo 1 }
-- .4.4.2.6.6.2 LEAF qos.out.wlan0.wlan1.vo.reserve
qosOutWlan0Wlan1VoReserve OBJECT-TYPE
  SYNTAX OCTET STRING
  MAX-ACCESS read-write
  STATUS current
  DESCRIPTION "reserved bw for VO data coming from wlan1"
  ::= { qosOutWlan0Wlan1Vo 2 }
----------------------------------------------------
-- .4.4.2.7. BRANCH qos.out.wlan0.wlan2.
--
qosOutWlan0Wlan2 OBJECT IDENTIFIER ::= { qosOutWlan0 7 }
----------------------------------------------------
-- .4.4.2.7.1. BRANCH qos.out.wlan0.wlan2.be.
--
qosOutWlan0Wlan2Be OBJECT IDENTIFIER ::= { qosOutWlan0Wlan2 1 }
-- .4.4.2.7.1.1 LEAF qos.out.wlan0.wlan2.be.limit
qosOutWlan0Wlan2BeLimit OBJECT-TYPE
  SYNTAX OCTET STRING
  MAX-ACCESS read-write
  STATUS current
  DESCRIPTION "max bw for BE data coming from wlan2"
  ::= { qosOutWlan0Wlan2Be 1 }
-- .4.4.2.7.1.2 LEAF qos.out.wlan0.wlan2.be.reserve
qosOutWlan0Wlan2BeReserve OBJECT-TYPE
  SYNTAX OCTET STRING
  MAX-ACCESS read-write
  STATUS current
  DESCRIPTION "reserved bw for BE data coming from wlan2"
  ::= { qosOutWlan0Wlan2Be 2 }
----------------------------------------------------
-- .4.4.2.7.2. BRANCH qos.out.wlan0.wlan2.bk.
--
qosOutWlan0Wlan2Bk OBJECT IDENTIFIER ::= { qosOutWlan0Wlan2 2 }
-- .4.4.2.7.2.1 LEAF qos.out.wlan0.wlan2.bk.limit
qosOutWlan0Wlan2BkLimit OBJECT-TYPE
  SYNTAX OCTET STRING
  MAX-ACCESS read-write
  STATUS current
  DESCRIPTION "max bw for BK data coming from wlan2"
  ::= { qosOutWlan0Wlan2Bk 1 }
-- .4.4.2.7.2.2 LEAF qos.out.wlan0.wlan2.bk.reserve
qosOutWlan0Wlan2BkReserve OBJECT-TYPE
  SYNTAX OCTET STRING
  MAX-ACCESS read-write
  STATUS current
  DESCRIPTION "reserved bw for BK data coming from wlan2"
  ::= { qosOutWlan0Wlan2Bk 2 }
-- .4.4.2.7.3 LEAF qos.out.wlan0.wlan2.limit
qosOutWlan0Wlan2Limit OBJECT-TYPE
  SYNTAX OCTET STRING
  MAX-ACCESS read-write
  STATUS current
  DESCRIPTION "max bw for all data coming from wlan2"
  ::= { qosOutWlan0Wlan2 3 }
-- .4.4.2.7.4 LEAF qos.out.wlan0.wlan2.reserve
qosOutWlan0Wlan2Reserve OBJECT-TYPE
  SYNTAX OCTET STRING
  MAX-ACCESS read-write
  STATUS current
  DESCRIPTION "reserved bw for all data coming from wlan2"
  ::= { qosOutWlan0Wlan2 4 }
----------------------------------------------------
-- .4.4.2.7.5. BRANCH qos.out.wlan0.wlan2.vi.
--
qosOutWlan0Wlan2Vi OBJECT IDENTIFIER ::= { qosOutWlan0Wlan2 5 }
-- .4.4.2.7.5.1 LEAF qos.out.wlan0.wlan2.vi.limit
qosOutWlan0Wlan2ViLimit OBJECT-TYPE
  SYNTAX OCTET STRING
  MAX-ACCESS read-write
  STATUS current
  DESCRIPTION "max bw for VI data coming from wlan2"
  ::= { qosOutWlan0Wlan2Vi 1 }
-- .4.4.2.7.5.2 LEAF qos.out.wlan0.wlan2.vi.reserve
qosOutWlan0Wlan2ViReserve OBJECT-TYPE
  SYNTAX OCTET STRING
  MAX-ACCESS read-write
  STATUS current
  DESCRIPTION "reserved bw for VI data coming from wlan2"
  ::= { qosOutWlan0Wlan2Vi 2 }
----------------------------------------------------
-- .4.4.2.7.6. BRANCH qos.out.wlan0.wlan2.vo.
--
qosOutWlan0Wlan2Vo OBJECT IDENTIFIER ::= { qosOutWlan0Wlan2 6 }
-- .4.4.2.7.6.1 LEAF qos.out.wlan0.wlan2.vo.limit
qosOutWlan0Wlan2VoLimit OBJECT-TYPE
  SYNTAX OCTET STRING
  MAX-ACCESS read-write
  STATUS current
  DESCRIPTION "max bw for VO data coming from wlan2"
  ::= { qosOutWlan0Wlan2Vo 1 }
-- .4.4.2.7.6.2 LEAF qos.out.wlan0.wlan2.vo.reserve
qosOutWlan0Wlan2VoReserve OBJECT-TYPE
  SYNTAX OCTET STRING
  MAX-ACCESS read-write
  STATUS current
  DESCRIPTION "reserved bw for VO data coming from wlan2"
  ::= { qosOutWlan0Wlan2Vo 2 }
----------------------------------------------------
-- .4.4.2.8. BRANCH qos.out.wlan0.wlan3.
--
qosOutWlan0Wlan3 OBJECT IDENTIFIER ::= { qosOutWlan0 8 }
----------------------------------------------------
-- .4.4.2.8.1. BRANCH qos.out.wlan0.wlan3.be.
--
qosOutWlan0Wlan3Be OBJECT IDENTIFIER ::= { qosOutWlan0Wlan3 1 }
-- .4.4.2.8.1.1 LEAF qos.out.wlan0.wlan3.be.limit
qosOutWlan0Wlan3BeLimit OBJECT-TYPE
  SYNTAX OCTET STRING
  MAX-ACCESS read-write
  STATUS current
  DESCRIPTION "max bw for BE data coming from wlan3"
  ::= { qosOutWlan0Wlan3Be 1 }
-- .4.4.2.8.1.2 LEAF qos.out.wlan0.wlan3.be.reserve
qosOutWlan0Wlan3BeReserve OBJECT-TYPE
  SYNTAX OCTET STRING
  MAX-ACCESS read-write
  STATUS current
  DESCRIPTION "reserved bw for BE data coming from wlan3"
  ::= { qosOutWlan0Wlan3Be 2 }
----------------------------------------------------
-- .4.4.2.8.2. BRANCH qos.out.wlan0.wlan3.bk.
--
qosOutWlan0Wlan3Bk OBJECT IDENTIFIER ::= { qosOutWlan0Wlan3 2 }
-- .4.4.2.8.2.1 LEAF qos.out.wlan0.wlan3.bk.limit
qosOutWlan0Wlan3BkLimit OBJECT-TYPE
  SYNTAX OCTET STRING
  MAX-ACCESS read-write
  STATUS current
  DESCRIPTION "max bw for BK data coming from wlan3"
  ::= { qosOutWlan0Wlan3Bk 1 }
-- .4.4.2.8.2.2 LEAF qos.out.wlan0.wlan3.bk.reserve
qosOutWlan0Wlan3BkReserve OBJECT-TYPE
  SYNTAX OCTET STRING
  MAX-ACCESS read-write
  STATUS current
  DESCRIPTION "reserved bw for BK data coming from wlan3"
  ::= { qosOutWlan0Wlan3Bk 2 }
-- .4.4.2.8.3 LEAF qos.out.wlan0.wlan3.limit
qosOutWlan0Wlan3Limit OBJECT-TYPE
  SYNTAX OCTET STRING
  MAX-ACCESS read-write
  STATUS current
  DESCRIPTION "max bw for all data coming from wlan3"
  ::= { qosOutWlan0Wlan3 3 }
-- .4.4.2.8.4 LEAF qos.out.wlan0.wlan3.reserve
qosOutWlan0Wlan3Reserve OBJECT-TYPE
  SYNTAX OCTET STRING
  MAX-ACCESS read-write
  STATUS current
  DESCRIPTION "reserved bw for all data coming from wlan3"
  ::= { qosOutWlan0Wlan3 4 }
----------------------------------------------------
-- .4.4.2.8.5. BRANCH qos.out.wlan0.wlan3.vi.
--
qosOutWlan0Wlan3Vi OBJECT IDENTIFIER ::= { qosOutWlan0Wlan3 5 }
-- .4.4.2.8.5.1 LEAF qos.out.wlan0.wlan3.vi.limit
qosOutWlan0Wlan3ViLimit OBJECT-TYPE
  SYNTAX OCTET STRING
  MAX-ACCESS read-write
  STATUS current
  DESCRIPTION "max bw for VI data coming from wlan3"
  ::= { qosOutWlan0Wlan3Vi 1 }
-- .4.4.2.8.5.2 LEAF qos.out.wlan0.wlan3.vi.reserve
qosOutWlan0Wlan3ViReserve OBJECT-TYPE
  SYNTAX OCTET STRING
  MAX-ACCESS read-write
  STATUS current
  DESCRIPTION "reserved bw for VI data coming from wlan3"
  ::= { qosOutWlan0Wlan3Vi 2 }
----------------------------------------------------
-- .4.4.2.8.6. BRANCH qos.out.wlan0.wlan3.vo.
--
qosOutWlan0Wlan3Vo OBJECT IDENTIFIER ::= { qosOutWlan0Wlan3 6 }
-- .4.4.2.8.6.1 LEAF qos.out.wlan0.wlan3.vo.limit
qosOutWlan0Wlan3VoLimit OBJECT-TYPE
  SYNTAX OCTET STRING
  MAX-ACCESS read-write
  STATUS current
  DESCRIPTION "max bw for VO data coming from wlan3"
  ::= { qosOutWlan0Wlan3Vo 1 }
-- .4.4.2.8.6.2 LEAF qos.out.wlan0.wlan3.vo.reserve
qosOutWlan0Wlan3VoReserve OBJECT-TYPE
  SYNTAX OCTET STRING
  MAX-ACCESS read-write
  STATUS current
  DESCRIPTION "reserved bw for VO data coming from wlan3"
  ::= { qosOutWlan0Wlan3Vo 2 }
----------------------------------------------------
-- .4.4.2.9. BRANCH qos.out.wlan0.wlan4.
--
qosOutWlan0Wlan4 OBJECT IDENTIFIER ::= { qosOutWlan0 9 }
----------------------------------------------------
-- .4.4.2.9.1. BRANCH qos.out.wlan0.wlan4.be.
--
qosOutWlan0Wlan4Be OBJECT IDENTIFIER ::= { qosOutWlan0Wlan4 1 }
-- .4.4.2.9.1.1 LEAF qos.out.wlan0.wlan4.be.limit
qosOutWlan0Wlan4BeLimit OBJECT-TYPE
  SYNTAX OCTET STRING
  MAX-ACCESS read-write
  STATUS current
  DESCRIPTION "max bw for BE data coming from wlan4"
  ::= { qosOutWlan0Wlan4Be 1 }
-- .4.4.2.9.1.2 LEAF qos.out.wlan0.wlan4.be.reserve
qosOutWlan0Wlan4BeReserve OBJECT-TYPE
  SYNTAX OCTET STRING
  MAX-ACCESS read-write
  STATUS current
  DESCRIPTION "reserved bw for BE data coming from wlan4"
  ::= { qosOutWlan0Wlan4Be 2 }
----------------------------------------------------
-- .4.4.2.9.2. BRANCH qos.out.wlan0.wlan4.bk.
--
qosOutWlan0Wlan4Bk OBJECT IDENTIFIER ::= { qosOutWlan0Wlan4 2 }
-- .4.4.2.9.2.1 LEAF qos.out.wlan0.wlan4.bk.limit
qosOutWlan0Wlan4BkLimit OBJECT-TYPE
  SYNTAX OCTET STRING
  MAX-ACCESS read-write
  STATUS current
  DESCRIPTION "max bw for BK data coming from wlan4"
  ::= { qosOutWlan0Wlan4Bk 1 }
-- .4.4.2.9.2.2 LEAF qos.out.wlan0.wlan4.bk.reserve
qosOutWlan0Wlan4BkReserve OBJECT-TYPE
  SYNTAX OCTET STRING
  MAX-ACCESS read-write
  STATUS current
  DESCRIPTION "reserved bw for BK data coming from wlan4"
  ::= { qosOutWlan0Wlan4Bk 2 }
-- .4.4.2.9.3 LEAF qos.out.wlan0.wlan4.limit
qosOutWlan0Wlan4Limit OBJECT-TYPE
  SYNTAX OCTET STRING
  MAX-ACCESS read-write
  STATUS current
  DESCRIPTION "max bw for all data coming from wlan4"
  ::= { qosOutWlan0Wlan4 3 }
-- .4.4.2.9.4 LEAF qos.out.wlan0.wlan4.reserve
qosOutWlan0Wlan4Reserve OBJECT-TYPE
  SYNTAX OCTET STRING
  MAX-ACCESS read-write
  STATUS current
  DESCRIPTION "reserved bw for all data coming from wlan4"
  ::= { qosOutWlan0Wlan4 4 }
----------------------------------------------------
-- .4.4.2.9.5. BRANCH qos.out.wlan0.wlan4.vi.
--
qosOutWlan0Wlan4Vi OBJECT IDENTIFIER ::= { qosOutWlan0Wlan4 5 }
-- .4.4.2.9.5.1 LEAF qos.out.wlan0.wlan4.vi.limit
qosOutWlan0Wlan4ViLimit OBJECT-TYPE
  SYNTAX OCTET STRING
  MAX-ACCESS read-write
  STATUS current
  DESCRIPTION "max bw for VI data coming from wlan4"
  ::= { qosOutWlan0Wlan4Vi 1 }
-- .4.4.2.9.5.2 LEAF qos.out.wlan0.wlan4.vi.reserve
qosOutWlan0Wlan4ViReserve OBJECT-TYPE
  SYNTAX OCTET STRING
  MAX-ACCESS read-write
  STATUS current
  DESCRIPTION "reserved bw for VI data coming from wlan4"
  ::= { qosOutWlan0Wlan4Vi 2 }
----------------------------------------------------
-- .4.4.2.9.6. BRANCH qos.out.wlan0.wlan4.vo.
--
qosOutWlan0Wlan4Vo OBJECT IDENTIFIER ::= { qosOutWlan0Wlan4 6 }
-- .4.4.2.9.6.1 LEAF qos.out.wlan0.wlan4.vo.limit
qosOutWlan0Wlan4VoLimit OBJECT-TYPE
  SYNTAX OCTET STRING
  MAX-ACCESS read-write
  STATUS current
  DESCRIPTION "max bw for VO data coming from wlan4"
  ::= { qosOutWlan0Wlan4Vo 1 }
-- .4.4.2.9.6.2 LEAF qos.out.wlan0.wlan4.vo.reserve
qosOutWlan0Wlan4VoReserve OBJECT-TYPE
  SYNTAX OCTET STRING
  MAX-ACCESS read-write
  STATUS current
  DESCRIPTION "reserved bw for VO data coming from wlan4"
  ::= { qosOutWlan0Wlan4Vo 2 }
----------------------------------------------------
-- .5. BRANCH logs.
--
logs OBJECT IDENTIFIER ::= { enRoute 5 }
----------------------------------------------------
-- .5.1. BRANCH logs.mconfd.
--
logsMconfd OBJECT IDENTIFIER ::= { logs 1 }
-- .5.1.1 LEAF logs.mconfd.files
logsMconfdFiles OBJECT-TYPE
  SYNTAX INTEGER
  MAX-ACCESS read-write
  STATUS current
  DESCRIPTION "number of old files kept"
  ::= { logsMconfd 1 }
-- .5.1.2 LEAF logs.mconfd.size
logsMconfdSize OBJECT-TYPE
  SYNTAX OCTET STRING
  MAX-ACCESS read-write
  STATUS current
  DESCRIPTION "maximum file size in bytes"
  ::= { logsMconfd 2 }
----------------------------------------------------
-- .5.2. BRANCH logs.secure.
--
logsSecure OBJECT IDENTIFIER ::= { logs 2 }
-- .5.2.1 LEAF logs.secure.files
logsSecureFiles OBJECT-TYPE
  SYNTAX INTEGER
  MAX-ACCESS read-write
  STATUS current
  DESCRIPTION "number of old files kept"
  ::= { logsSecure 1 }
-- .5.2.2 LEAF logs.secure.size
logsSecureSize OBJECT-TYPE
  SYNTAX OCTET STRING
  MAX-ACCESS read-write
  STATUS current
  DESCRIPTION "maximum file size in bytes"
  ::= { logsSecure 2 }
----------------------------------------------------
-- .5.3. BRANCH logs.snmp.
--
logsSnmp OBJECT IDENTIFIER ::= { logs 3 }
-- .5.3.1 LEAF logs.snmp.files
logsSnmpFiles OBJECT-TYPE
  SYNTAX INTEGER
  MAX-ACCESS read-write
  STATUS current
  DESCRIPTION "number of old files kept"
  ::= { logsSnmp 1 }
-- .5.3.2 LEAF logs.snmp.size
logsSnmpSize OBJECT-TYPE
  SYNTAX OCTET STRING
  MAX-ACCESS read-write
  STATUS current
  DESCRIPTION "maximum file size in bytes"
  ::= { logsSnmp 2 }
----------------------------------------------------
-- .5.4. BRANCH logs.syslog.
--
logsSyslog OBJECT IDENTIFIER ::= { logs 4 }
-- .5.4.1 LEAF logs.syslog.files
logsSyslogFiles OBJECT-TYPE
  SYNTAX INTEGER
  MAX-ACCESS read-write
  STATUS current
  DESCRIPTION "number of old files kept"
  ::= { logsSyslog 1 }
-- .5.4.2 LEAF logs.syslog.size
logsSyslogSize OBJECT-TYPE
  SYNTAX OCTET STRING
  MAX-ACCESS read-write
  STATUS current
  DESCRIPTION "maximum file size in bytes"
  ::= { logsSyslog 2 }
----------------------------------------------------
-- .6. BRANCH eth0.
--
eth0 OBJECT IDENTIFIER ::= { enRoute 6 }
----------------------------------------------------
-- .6.1. BRANCH eth0.acl.
--
eth0Acl OBJECT IDENTIFIER ::= { eth0 1 }
-- .6.1.1 LEAF eth0.acl.mode
eth0AclMode OBJECT-TYPE
  SYNTAX OCTET STRING
  MAX-ACCESS read-write
  STATUS current
  DESCRIPTION "access control list mode ( 'none', 'whitelist', 'blacklist' )"
  ::= { eth0Acl 1 }
----------------------------------------------------
-- .6.2. BRANCH eth0.dhcp.
--
eth0Dhcp OBJECT IDENTIFIER ::= { eth0 2 }
-- .6.2.1 LEAF eth0.dhcp.alwaysbroadcast
eth0DhcpAlwaysbroadcast OBJECT-TYPE
  SYNTAX OCTET STRING
  MAX-ACCESS read-write
  STATUS current
  DESCRIPTION "always broadcast dhcp responses"
  ::= { eth0Dhcp 1 }
-- .6.2.2 LEAF eth0.dhcp.default_lease_time
eth0DhcpDefaultleasetime OBJECT-TYPE
  SYNTAX INTEGER
  MAX-ACCESS read-write
  STATUS current
  DESCRIPTION "default dhcp lease expiration in seconds"
  ::= { eth0Dhcp 2 }
-- .6.2.3 LEAF eth0.dhcp.max_lease_time
eth0DhcpMaxleasetime OBJECT-TYPE
  SYNTAX INTEGER
  MAX-ACCESS read-write
  STATUS current
  DESCRIPTION "maximum requestable dhcp lease expiration in seconds"
  ::= { eth0Dhcp 3 }
----------------------------------------------------
-- .6.2.4. BRANCH eth0.dhcp.relay.
--
eth0DhcpRelay OBJECT IDENTIFIER ::= { eth0Dhcp 4 }
-- .6.2.4.1 LEAF eth0.dhcp.relay.enable
eth0DhcpRelayEnable OBJECT-TYPE
  SYNTAX OCTET STRING
  MAX-ACCESS read-write
  STATUS current
  DESCRIPTION "use dhcp relay (if sys.dhcp.relay.enable=yes)"
  ::= { eth0DhcpRelay 1 }
-- .6.2.5 LEAF eth0.dhcp.reserve
eth0DhcpReserve OBJECT-TYPE
  SYNTAX INTEGER
  MAX-ACCESS read-write
  STATUS current
  DESCRIPTION "ip addresses to reserve at bottom of range for static assignments"
  ::= { eth0Dhcp 5 }
-- .6.2.6 LEAF eth0.dhcp.role
eth0DhcpRole OBJECT-TYPE
  SYNTAX OCTET STRING
  MAX-ACCESS read-write
  STATUS current
  DESCRIPTION "interface dhcp role (none, client, server)"
  ::= { eth0Dhcp 6 }
-- .6.3 LEAF eth0.enable
eth0Enable OBJECT-TYPE
  SYNTAX OCTET STRING
  MAX-ACCESS read-write
  STATUS current
  DESCRIPTION "interface is enabled"
  ::= { eth0 3 }
-- .6.4 LEAF eth0.if
eth0If OBJECT-TYPE
  SYNTAX OCTET STRING
  MAX-ACCESS read-only
  STATUS current
  DESCRIPTION "interface associated with this module"
  ::= { eth0 4 }
----------------------------------------------------
-- .6.5. BRANCH eth0.ip.
--
eth0Ip OBJECT IDENTIFIER ::= { eth0 5 }
-- .6.5.1 LEAF eth0.ip.address
eth0IpAddress OBJECT-TYPE
  SYNTAX OCTET STRING
  MAX-ACCESS read-only
  STATUS current
  DESCRIPTION "ip address"
  ::= { eth0Ip 1 }
-- .6.5.2 LEAF eth0.ip.address_force
eth0IpAddressforce OBJECT-TYPE
  SYNTAX OCTET STRING
  MAX-ACCESS read-write
  STATUS current
  DESCRIPTION "override .ip.address (or blank)"
  ::= { eth0Ip 2 }
-- .6.5.3 LEAF eth0.ip.broadcast
eth0IpBroadcast OBJECT-TYPE
  SYNTAX OCTET STRING
  MAX-ACCESS read-only
  STATUS current
  DESCRIPTION "broadcast address"
  ::= { eth0Ip 3 }
-- .6.5.4 LEAF eth0.ip.broadcast_force
eth0IpBroadcastforce OBJECT-TYPE
  SYNTAX OCTET STRING
  MAX-ACCESS read-write
  STATUS current
  DESCRIPTION "override .ip.broadcast (or blank)"
  ::= { eth0Ip 4 }
-- .6.5.5 LEAF eth0.ip.gateway
eth0IpGateway OBJECT-TYPE
  SYNTAX OCTET STRING
  MAX-ACCESS read-only
  STATUS current
  DESCRIPTION "gateway address"
  ::= { eth0Ip 5 }
-- .6.5.6 LEAF eth0.ip.gateway_force
eth0IpGatewayforce OBJECT-TYPE
  SYNTAX OCTET STRING
  MAX-ACCESS read-write
  STATUS current
  DESCRIPTION "override .ip.gateway (or blank)"
  ::= { eth0Ip 6 }
----------------------------------------------------
-- .6.5.7. BRANCH eth0.ip.implicit.
--
eth0IpImplicit OBJECT IDENTIFIER ::= { eth0Ip 7 }
----------------------------------------------------
-- .6.5.7.1. BRANCH eth0.ip.implicit.size.
--
eth0IpImplicitSize OBJECT IDENTIFIER ::= { eth0IpImplicit 1 }
-- .6.5.7.1.1 LEAF eth0.ip.implicit.size.actual
eth0IpImplicitSizeActual OBJECT-TYPE
  SYNTAX INTEGER
  MAX-ACCESS read-only
  STATUS current
  DESCRIPTION "actual size of assigned address range"
  ::= { eth0IpImplicitSize 1 }
-- .6.5.7.1.2 LEAF eth0.ip.implicit.size.requested
eth0IpImplicitSizeRequested OBJECT-TYPE
  SYNTAX OCTET STRING
  MAX-ACCESS read-write
  STATUS current
  DESCRIPTION "requested size of address range (multiple of 32 minus 1)"
  ::= { eth0IpImplicitSize 2 }
----------------------------------------------------
-- .6.5.7.2. BRANCH eth0.ip.implicit.start.
--
eth0IpImplicitStart OBJECT IDENTIFIER ::= { eth0IpImplicit 2 }
-- .6.5.7.2.1 LEAF eth0.ip.implicit.start.actual
eth0IpImplicitStartActual OBJECT-TYPE
  SYNTAX INTEGER
  MAX-ACCESS read-only
  STATUS current
  DESCRIPTION "actual assigned fourth octet"
  ::= { eth0IpImplicitStart 1 }
-- .6.5.7.2.2 LEAF eth0.ip.implicit.start.requested
eth0IpImplicitStartRequested OBJECT-TYPE
  SYNTAX OCTET STRING
  MAX-ACCESS read-write
  STATUS current
  DESCRIPTION "requested interface fourth octet (multiple of 32 plus 1)"
  ::= { eth0IpImplicitStart 2 }
-- .6.5.8 LEAF eth0.ip.netmask
eth0IpNetmask OBJECT-TYPE
  SYNTAX OCTET STRING
  MAX-ACCESS read-only
  STATUS current
  DESCRIPTION "network mask"
  ::= { eth0Ip 8 }
-- .6.5.9 LEAF eth0.ip.netmask_force
eth0IpNetmaskforce OBJECT-TYPE
  SYNTAX OCTET STRING
  MAX-ACCESS read-write
  STATUS current
  DESCRIPTION "override .ip.netmask (or blank)"
  ::= { eth0Ip 9 }
-- .6.6 LEAF eth0.role
eth0Role OBJECT-TYPE
  SYNTAX OCTET STRING
  MAX-ACCESS read-write
  STATUS current
  DESCRIPTION "intended interface role (gateway, access, bridge)"
  ::= { eth0 6 }
----------------------------------------------------
-- .6.7. BRANCH eth0.routes.
--
eth0Routes OBJECT IDENTIFIER ::= { eth0 7 }
-- .6.7.1 LEAF eth0.routes.static
eth0RoutesStatic OBJECT-TYPE
  SYNTAX OCTET STRING
  MAX-ACCESS read-write
  STATUS current
  DESCRIPTION "static routes for this interface"
  ::= { eth0Routes 1 }
----------------------------------------------------
-- .6.8. BRANCH eth0.vlan.
--
eth0Vlan OBJECT IDENTIFIER ::= { eth0 8 }
-- .6.8.1 LEAF eth0.vlan.enable
eth0VlanEnable OBJECT-TYPE
  SYNTAX OCTET STRING
  MAX-ACCESS read-write
  STATUS current
  DESCRIPTION "use a vlan for this interface"
  ::= { eth0Vlan 1 }
-- .6.8.2 LEAF eth0.vlan.id
eth0VlanId OBJECT-TYPE
  SYNTAX INTEGER
  MAX-ACCESS read-write
  STATUS current
  DESCRIPTION "vlan id (0 and 1 are usually reserved)"
  ::= { eth0Vlan 2 }
----------------------------------------------------
-- .6.9. BRANCH eth0.vpn.
--
eth0Vpn OBJECT IDENTIFIER ::= { eth0 9 }
-- .6.9.1 LEAF eth0.vpn.device
eth0VpnDevice OBJECT-TYPE
  SYNTAX OCTET STRING
  MAX-ACCESS read-write
  STATUS current
  DESCRIPTION "device type (tap or tun)"
  ::= { eth0Vpn 1 }
-- .6.9.2 LEAF eth0.vpn.enable
eth0VpnEnable OBJECT-TYPE
  SYNTAX OCTET STRING
  MAX-ACCESS read-write
  STATUS current
  DESCRIPTION "enable vpn on gateway node"
  ::= { eth0Vpn 2 }
-- .6.9.3 LEAF eth0.vpn.keyfile
eth0VpnKeyfile OBJECT-TYPE
  SYNTAX OCTET STRING
  MAX-ACCESS read-write
  STATUS current
  DESCRIPTION "base name of crt/key files"
  ::= { eth0Vpn 3 }
-- .6.9.4 LEAF eth0.vpn.port
eth0VpnPort OBJECT-TYPE
  SYNTAX INTEGER
  MAX-ACCESS read-write
  STATUS current
  DESCRIPTION "port number at vpn server"
  ::= { eth0Vpn 4 }
-- .6.9.5 LEAF eth0.vpn.protocol
eth0VpnProtocol OBJECT-TYPE
  SYNTAX OCTET STRING
  MAX-ACCESS read-write
  STATUS current
  DESCRIPTION "protocol used for vpn"
  ::= { eth0Vpn 5 }
-- .6.9.6 LEAF eth0.vpn.server
eth0VpnServer OBJECT-TYPE
  SYNTAX OCTET STRING
  MAX-ACCESS read-write
  STATUS current
  DESCRIPTION "hostname or ip address of the vpn server"
  ::= { eth0Vpn 6 }
----------------------------------------------------
-- .7. BRANCH br0.
--
br0 OBJECT IDENTIFIER ::= { enRoute 7 }
----------------------------------------------------
-- .7.1. BRANCH br0.acl.
--
br0Acl OBJECT IDENTIFIER ::= { br0 1 }
-- .7.1.1 LEAF br0.acl.mode
br0AclMode OBJECT-TYPE
  SYNTAX OCTET STRING
  MAX-ACCESS read-write
  STATUS current
  DESCRIPTION "access control list mode ( 'none', 'whitelist', 'blacklist' )"
  ::= { br0Acl 1 }
----------------------------------------------------
-- .7.2. BRANCH br0.dhcp.
--
br0Dhcp OBJECT IDENTIFIER ::= { br0 2 }
-- .7.2.1 LEAF br0.dhcp.alwaysbroadcast
br0DhcpAlwaysbroadcast OBJECT-TYPE
  SYNTAX OCTET STRING
  MAX-ACCESS read-write
  STATUS current
  DESCRIPTION "always broadcast dhcp responses"
  ::= { br0Dhcp 1 }
-- .7.2.2 LEAF br0.dhcp.default_lease_time
br0DhcpDefaultleasetime OBJECT-TYPE
  SYNTAX INTEGER
  MAX-ACCESS read-write
  STATUS current
  DESCRIPTION "default dhcp lease expiration in seconds"
  ::= { br0Dhcp 2 }
-- .7.2.3 LEAF br0.dhcp.max_lease_time
br0DhcpMaxleasetime OBJECT-TYPE
  SYNTAX INTEGER
  MAX-ACCESS read-write
  STATUS current
  DESCRIPTION "maximum requestable dhcp lease expiration in seconds"
  ::= { br0Dhcp 3 }
----------------------------------------------------
-- .7.2.4. BRANCH br0.dhcp.relay.
--
br0DhcpRelay OBJECT IDENTIFIER ::= { br0Dhcp 4 }
-- .7.2.4.1 LEAF br0.dhcp.relay.enable
br0DhcpRelayEnable OBJECT-TYPE
  SYNTAX OCTET STRING
  MAX-ACCESS read-write
  STATUS current
  DESCRIPTION "use dhcp relay (if sys.dhcp.relay.enable=yes)"
  ::= { br0DhcpRelay 1 }
-- .7.2.5 LEAF br0.dhcp.reserve
br0DhcpReserve OBJECT-TYPE
  SYNTAX INTEGER
  MAX-ACCESS read-write
  STATUS current
  DESCRIPTION "ip addresses to reserve at bottom of range for static assignments"
  ::= { br0Dhcp 5 }
-- .7.2.6 LEAF br0.dhcp.role
br0DhcpRole OBJECT-TYPE
  SYNTAX OCTET STRING
  MAX-ACCESS read-write
  STATUS current
  DESCRIPTION "interface dhcp role (none, client, server)"
  ::= { br0Dhcp 6 }
-- .7.3 LEAF br0.enable
br0Enable OBJECT-TYPE
  SYNTAX OCTET STRING
  MAX-ACCESS read-write
  STATUS current
  DESCRIPTION "interface is enabled"
  ::= { br0 3 }
-- .7.4 LEAF br0.forwarding_delay
br0Forwardingdelay OBJECT-TYPE
  SYNTAX INTEGER
  MAX-ACCESS read-write
  STATUS current
  DESCRIPTION "how long bridge watches traffic before participating"
  ::= { br0 4 }
-- .7.5 LEAF br0.if
br0If OBJECT-TYPE
  SYNTAX OCTET STRING
  MAX-ACCESS read-only
  STATUS current
  DESCRIPTION "interface associated with this module"
  ::= { br0 5 }
----------------------------------------------------
-- .7.6. BRANCH br0.ip.
--
br0Ip OBJECT IDENTIFIER ::= { br0 6 }
-- .7.6.1 LEAF br0.ip.address
br0IpAddress OBJECT-TYPE
  SYNTAX OCTET STRING
  MAX-ACCESS read-only
  STATUS current
  DESCRIPTION "ip address"
  ::= { br0Ip 1 }
-- .7.6.2 LEAF br0.ip.address_force
br0IpAddressforce OBJECT-TYPE
  SYNTAX OCTET STRING
  MAX-ACCESS read-write
  STATUS current
  DESCRIPTION "override .ip.address (or blank)"
  ::= { br0Ip 2 }
-- .7.6.3 LEAF br0.ip.broadcast
br0IpBroadcast OBJECT-TYPE
  SYNTAX OCTET STRING
  MAX-ACCESS read-only
  STATUS current
  DESCRIPTION "broadcast address"
  ::= { br0Ip 3 }
-- .7.6.4 LEAF br0.ip.broadcast_force
br0IpBroadcastforce OBJECT-TYPE
  SYNTAX OCTET STRING
  MAX-ACCESS read-write
  STATUS current
  DESCRIPTION "override .ip.broadcast (or blank)"
  ::= { br0Ip 4 }
-- .7.6.5 LEAF br0.ip.gateway
br0IpGateway OBJECT-TYPE
  SYNTAX OCTET STRING
  MAX-ACCESS read-only
  STATUS current
  DESCRIPTION "gateway address"
  ::= { br0Ip 5 }
-- .7.6.6 LEAF br0.ip.gateway_force
br0IpGatewayforce OBJECT-TYPE
  SYNTAX OCTET STRING
  MAX-ACCESS read-write
  STATUS current
  DESCRIPTION "override .ip.gateway (or blank)"
  ::= { br0Ip 6 }
-- .7.6.7 LEAF br0.ip.netmask
br0IpNetmask OBJECT-TYPE
  SYNTAX OCTET STRING
  MAX-ACCESS read-only
  STATUS current
  DESCRIPTION "network mask"
  ::= { br0Ip 7 }
-- .7.6.8 LEAF br0.ip.netmask_force
br0IpNetmaskforce OBJECT-TYPE
  SYNTAX OCTET STRING
  MAX-ACCESS read-write
  STATUS current
  DESCRIPTION "override .ip.netmask (or blank)"
  ::= { br0Ip 8 }
-- .7.7 LEAF br0.role
br0Role OBJECT-TYPE
  SYNTAX OCTET STRING
  MAX-ACCESS read-only
  STATUS current
  DESCRIPTION "intended interface role (bridge)"
  ::= { br0 7 }
----------------------------------------------------
-- .7.8. BRANCH br0.routes.
--
br0Routes OBJECT IDENTIFIER ::= { br0 8 }
-- .7.8.1 LEAF br0.routes.static
br0RoutesStatic OBJECT-TYPE
  SYNTAX OCTET STRING
  MAX-ACCESS read-write
  STATUS current
  DESCRIPTION "static routes for this interface"
  ::= { br0Routes 1 }
----------------------------------------------------
-- .7.9. BRANCH br0.stp.
--
br0Stp OBJECT IDENTIFIER ::= { br0 9 }
-- .7.9.1 LEAF br0.stp.enable
br0StpEnable OBJECT-TYPE
  SYNTAX OCTET STRING
  MAX-ACCESS read-write
  STATUS current
  DESCRIPTION "enable spanning tree protocol"
  ::= { br0Stp 1 }
----------------------------------------------------
-- .8. BRANCH alias99.
--
alias99 OBJECT IDENTIFIER ::= { enRoute 8 }
-- .8.1 LEAF alias99.if
alias99If OBJECT-TYPE
  SYNTAX OCTET STRING
  MAX-ACCESS read-only
  STATUS current
  DESCRIPTION "interface associated with this module"
  ::= { alias99 1 }
----------------------------------------------------
-- .8.2. BRANCH alias99.ip.
--
alias99Ip OBJECT IDENTIFIER ::= { alias99 2 }
-- .8.2.1 LEAF alias99.ip.address
alias99IpAddress OBJECT-TYPE
  SYNTAX OCTET STRING
  MAX-ACCESS read-write
  STATUS current
  DESCRIPTION "ip address"
  ::= { alias99Ip 1 }
-- .8.2.2 LEAF alias99.ip.broadcast
alias99IpBroadcast OBJECT-TYPE
  SYNTAX OCTET STRING
  MAX-ACCESS read-write
  STATUS current
  DESCRIPTION "broadcast address"
  ::= { alias99Ip 2 }
-- .8.2.3 LEAF alias99.ip.gateway
alias99IpGateway OBJECT-TYPE
  SYNTAX OCTET STRING
  MAX-ACCESS read-write
  STATUS current
  DESCRIPTION "gateway address"
  ::= { alias99Ip 3 }
-- .8.2.4 LEAF alias99.ip.netmask
alias99IpNetmask OBJECT-TYPE
  SYNTAX OCTET STRING
  MAX-ACCESS read-write
  STATUS current
  DESCRIPTION "network mask"
  ::= { alias99Ip 4 }
----------------------------------------------------
-- .9. BRANCH radio0.
--
radio0 OBJECT IDENTIFIER ::= { enRoute 9 }
-- .9.1 LEAF radio0.channel
radio0Channel OBJECT-TYPE
  SYNTAX INTEGER
  MAX-ACCESS read-write
  STATUS current
  DESCRIPTION "wireless channel"
  ::= { radio0 1 }
-- .9.2 LEAF radio0.chansize
radio0Chansize OBJECT-TYPE
  SYNTAX OCTET STRING
  MAX-ACCESS read-write
  STATUS current
  DESCRIPTION "wireless channel size - 1=full, 2=half, 4=quarter"
  ::= { radio0 2 }
-- .9.3 LEAF radio0.distance
radio0Distance OBJECT-TYPE
  SYNTAX OCTET STRING
  MAX-ACCESS read-write
  STATUS current
  DESCRIPTION "distance (in miles or km, see sys.units) of maximum link distance, or blank"
  ::= { radio0 3 }
-- .9.4 LEAF radio0.distance_meters
radio0Distancemeters OBJECT-TYPE
  SYNTAX OCTET STRING
  MAX-ACCESS read-write
  STATUS current
  DESCRIPTION "distance in meters"
  ::= { radio0 4 }
-- .9.5 LEAF radio0.frequency
radio0Frequency OBJECT-TYPE
  SYNTAX OCTET STRING
  MAX-ACCESS read-write
  STATUS current
  DESCRIPTION "wireless frequency (overrides radio0.channel)"
  ::= { radio0 5 }
-- .9.6 LEAF radio0.mode
radio0Mode OBJECT-TYPE
  SYNTAX INTEGER
  MAX-ACCESS read-write
  STATUS current
  DESCRIPTION "802.11 mode (0=auto, 1=802.11a, 2=802.11b, 3=802.11g)"
  ::= { radio0 6 }
-- .9.7 LEAF radio0.modes
radio0Modes OBJECT-TYPE
  SYNTAX OCTET STRING
  MAX-ACCESS read-only
  STATUS current
  DESCRIPTION "802.11 modes supported by this card"
  ::= { radio0 7 }
-- .9.8 LEAF radio0.pureg
radio0Pureg OBJECT-TYPE
  SYNTAX OCTET STRING
  MAX-ACCESS read-write
  STATUS current
  DESCRIPTION "802.11g only mode (no 802.11b)"
  ::= { radio0 8 }
-- .9.9 LEAF radio0.ratectl
radio0Ratectl OBJECT-TYPE
  SYNTAX OCTET STRING
  MAX-ACCESS read-write
  STATUS current
  DESCRIPTION "rate control algorithm (sample, minstrel)"
  ::= { radio0 9 }
-- .9.10 LEAF radio0.rts
radio0Rts OBJECT-TYPE
  SYNTAX OCTET STRING
  MAX-ACCESS read-write
  STATUS current
  DESCRIPTION "rts threshold"
  ::= { radio0 10 }
-- .9.11 LEAF radio0.short_preamble
radio0Shortpreamble OBJECT-TYPE
  SYNTAX OCTET STRING
  MAX-ACCESS read-write
  STATUS current
  DESCRIPTION "allow short preamble - buggy old clients may need this off"
  ::= { radio0 11 }
-- .9.12 LEAF radio0.turbo
radio0Turbo OBJECT-TYPE
  SYNTAX OCTET STRING
  MAX-ACCESS read-write
  STATUS current
  DESCRIPTION "802.11g turbo mode"
  ::= { radio0 12 }
-- .9.13 LEAF radio0.txpower
radio0Txpower OBJECT-TYPE
  SYNTAX OCTET STRING
  MAX-ACCESS read-write
  STATUS current
  DESCRIPTION "max transmit power in dBm (0-30)"
  ::= { radio0 13 }
-- .9.14 LEAF radio0.wlans
radio0Wlans OBJECT-TYPE
  SYNTAX OCTET STRING
  MAX-ACCESS read-only
  STATUS current
  DESCRIPTION "wlans mapped to this radio"
  ::= { radio0 14 }
-- .9.15 LEAF radio0.wlans_extra
radio0Wlansextra OBJECT-TYPE
  SYNTAX OCTET STRING
  MAX-ACCESS read-only
  STATUS current
  DESCRIPTION ""
  ::= { radio0 15 }
----------------------------------------------------
-- .10. BRANCH radio1.
--
radio1 OBJECT IDENTIFIER ::= { enRoute 10 }
-- .10.1 LEAF radio1.channel
radio1Channel OBJECT-TYPE
  SYNTAX INTEGER
  MAX-ACCESS read-write
  STATUS current
  DESCRIPTION "wireless channel"
  ::= { radio1 1 }
-- .10.2 LEAF radio1.chansize
radio1Chansize OBJECT-TYPE
  SYNTAX OCTET STRING
  MAX-ACCESS read-write
  STATUS current
  DESCRIPTION "wireless channel size - 1=full, 2=half, 4=quarter"
  ::= { radio1 2 }
-- .10.3 LEAF radio1.distance
radio1Distance OBJECT-TYPE
  SYNTAX OCTET STRING
  MAX-ACCESS read-write
  STATUS current
  DESCRIPTION "distance (in miles or km, see sys.units) of maximum link distance, or blank"
  ::= { radio1 3 }
-- .10.4 LEAF radio1.distance_meters
radio1Distancemeters OBJECT-TYPE
  SYNTAX OCTET STRING
  MAX-ACCESS read-write
  STATUS current
  DESCRIPTION "distance in meters"
  ::= { radio1 4 }
-- .10.5 LEAF radio1.frequency
radio1Frequency OBJECT-TYPE
  SYNTAX OCTET STRING
  MAX-ACCESS read-write
  STATUS current
  DESCRIPTION "wireless frequency (overrides radio1.channel)"
  ::= { radio1 5 }
-- .10.6 LEAF radio1.mode
radio1Mode OBJECT-TYPE
  SYNTAX INTEGER
  MAX-ACCESS read-write
  STATUS current
  DESCRIPTION "802.11 mode (0=auto, 1=802.11a, 2=802.11b, 3=802.11g)"
  ::= { radio1 6 }
-- .10.7 LEAF radio1.modes
radio1Modes OBJECT-TYPE
  SYNTAX OCTET STRING
  MAX-ACCESS read-only
  STATUS current
  DESCRIPTION "802.11 modes supported by this card"
  ::= { radio1 7 }
-- .10.8 LEAF radio1.pureg
radio1Pureg OBJECT-TYPE
  SYNTAX OCTET STRING
  MAX-ACCESS read-write
  STATUS current
  DESCRIPTION "802.11g only mode (no 802.11b)"
  ::= { radio1 8 }
-- .10.9 LEAF radio1.ratectl
radio1Ratectl OBJECT-TYPE
  SYNTAX OCTET STRING
  MAX-ACCESS read-write
  STATUS current
  DESCRIPTION "rate control algorithm (sample, minstrel)"
  ::= { radio1 9 }
-- .10.10 LEAF radio1.rts
radio1Rts OBJECT-TYPE
  SYNTAX OCTET STRING
  MAX-ACCESS read-write
  STATUS current
  DESCRIPTION "rts threshold"
  ::= { radio1 10 }
-- .10.11 LEAF radio1.short_preamble
radio1Shortpreamble OBJECT-TYPE
  SYNTAX OCTET STRING
  MAX-ACCESS read-write
  STATUS current
  DESCRIPTION "allow short preamble - buggy old clients may need this off"
  ::= { radio1 11 }
-- .10.12 LEAF radio1.turbo
radio1Turbo OBJECT-TYPE
  SYNTAX OCTET STRING
  MAX-ACCESS read-write
  STATUS current
  DESCRIPTION "802.11g turbo mode"
  ::= { radio1 12 }
-- .10.13 LEAF radio1.txpower
radio1Txpower OBJECT-TYPE
  SYNTAX OCTET STRING
  MAX-ACCESS read-write
  STATUS current
  DESCRIPTION "max transmit power in dBm (0-30)"
  ::= { radio1 13 }
-- .10.14 LEAF radio1.wlans
radio1Wlans OBJECT-TYPE
  SYNTAX OCTET STRING
  MAX-ACCESS read-only
  STATUS current
  DESCRIPTION "wlans mapped to this radio"
  ::= { radio1 14 }
-- .10.15 LEAF radio1.wlans_extra
radio1Wlansextra OBJECT-TYPE
  SYNTAX OCTET STRING
  MAX-ACCESS read-only
  STATUS current
  DESCRIPTION ""
  ::= { radio1 15 }
----------------------------------------------------
-- .11. BRANCH wlan0.
--
wlan0 OBJECT IDENTIFIER ::= { enRoute 11 }
----------------------------------------------------
-- .11.1. BRANCH wlan0.acl.
--
wlan0Acl OBJECT IDENTIFIER ::= { wlan0 1 }
-- .11.1.1 LEAF wlan0.acl.mode
wlan0AclMode OBJECT-TYPE
  SYNTAX OCTET STRING
  MAX-ACCESS read-write
  STATUS current
  DESCRIPTION "access control list mode ( 'none', 'whitelist', 'blacklist' )"
  ::= { wlan0Acl 1 }
-- .11.2 LEAF wlan0.beacon_interval
wlan0Beaconinterval OBJECT-TYPE
  SYNTAX INTEGER
  MAX-ACCESS read-write
  STATUS current
  DESCRIPTION "beacon interval in milliseconds"
  ::= { wlan0 2 }
-- .11.3 LEAF wlan0.cellid
wlan0Cellid OBJECT-TYPE
  SYNTAX OCTET STRING
  MAX-ACCESS read-only
  STATUS current
  DESCRIPTION "adhoc cell id"
  ::= { wlan0 3 }
----------------------------------------------------
-- .11.4. BRANCH wlan0.dhcp.
--
wlan0Dhcp OBJECT IDENTIFIER ::= { wlan0 4 }
-- .11.4.1 LEAF wlan0.dhcp.alwaysbroadcast
wlan0DhcpAlwaysbroadcast OBJECT-TYPE
  SYNTAX OCTET STRING
  MAX-ACCESS read-write
  STATUS current
  DESCRIPTION "always broadcast dhcp responses"
  ::= { wlan0Dhcp 1 }
-- .11.4.2 LEAF wlan0.dhcp.default_lease_time
wlan0DhcpDefaultleasetime OBJECT-TYPE
  SYNTAX INTEGER
  MAX-ACCESS read-write
  STATUS current
  DESCRIPTION "default dhcp lease expiration in seconds"
  ::= { wlan0Dhcp 2 }
-- .11.4.3 LEAF wlan0.dhcp.max_lease_time
wlan0DhcpMaxleasetime OBJECT-TYPE
  SYNTAX INTEGER
  MAX-ACCESS read-write
  STATUS current
  DESCRIPTION "maximum requestable dhcp lease expiration in seconds"
  ::= { wlan0Dhcp 3 }
----------------------------------------------------
-- .11.4.4. BRANCH wlan0.dhcp.relay.
--
wlan0DhcpRelay OBJECT IDENTIFIER ::= { wlan0Dhcp 4 }
-- .11.4.4.1 LEAF wlan0.dhcp.relay.enable
wlan0DhcpRelayEnable OBJECT-TYPE
  SYNTAX OCTET STRING
  MAX-ACCESS read-write
  STATUS current
  DESCRIPTION "use dhcp relay (if sys.dhcp.relay.enable=yes)"
  ::= { wlan0DhcpRelay 1 }
-- .11.4.5 LEAF wlan0.dhcp.reserve
wlan0DhcpReserve OBJECT-TYPE
  SYNTAX INTEGER
  MAX-ACCESS read-write
  STATUS current
  DESCRIPTION "ip addresses to reserve at bottom of range for static assignments"
  ::= { wlan0Dhcp 5 }
-- .11.4.6 LEAF wlan0.dhcp.role
wlan0DhcpRole OBJECT-TYPE
  SYNTAX OCTET STRING
  MAX-ACCESS read-write
  STATUS current
  DESCRIPTION "interface dhcp role (none, client, server)"
  ::= { wlan0Dhcp 6 }
-- .11.5 LEAF wlan0.enable
wlan0Enable OBJECT-TYPE
  SYNTAX OCTET STRING
  MAX-ACCESS read-write
  STATUS current
  DESCRIPTION "interface is enabled"
  ::= { wlan0 5 }
-- .11.6 LEAF wlan0.enh_sec
wlan0Enhsec OBJECT-TYPE
  SYNTAX OCTET STRING
  MAX-ACCESS read-write
  STATUS current
  DESCRIPTION "ignore clients that specify 'ANY' ssid"
  ::= { wlan0 6 }
-- .11.7 LEAF wlan0.essid
wlan0Essid OBJECT-TYPE
  SYNTAX OCTET STRING
  MAX-ACCESS read-write
  STATUS current
  DESCRIPTION "essid for this ap"
  ::= { wlan0 7 }
----------------------------------------------------
-- .11.8. BRANCH wlan0.fabric.
--
wlan0Fabric OBJECT IDENTIFIER ::= { wlan0 8 }
-- .11.8.1 LEAF wlan0.fabric.args
wlan0FabricArgs OBJECT-TYPE
  SYNTAX OCTET STRING
  MAX-ACCESS read-write
  STATUS current
  DESCRIPTION "mesh fabric arguments - touch at your peril!"
  ::= { wlan0Fabric 1 }
-- .11.8.2 LEAF wlan0.fabric.bridge
wlan0FabricBridge OBJECT-TYPE
  SYNTAX OCTET STRING
  MAX-ACCESS read-write
  STATUS current
  DESCRIPTION "bridge argument"
  ::= { wlan0Fabric 2 }
-- .11.8.3 LEAF wlan0.fabric.cmd1
wlan0FabricCmd1 OBJECT-TYPE
  SYNTAX OCTET STRING
  MAX-ACCESS read-write
  STATUS current
  DESCRIPTION "command to activate mesh fabric part 1"
  ::= { wlan0Fabric 3 }
-- .11.8.4 LEAF wlan0.fabric.cmd2
wlan0FabricCmd2 OBJECT-TYPE
  SYNTAX OCTET STRING
  MAX-ACCESS read-write
  STATUS current
  DESCRIPTION "command to activate mesh part 2"
  ::= { wlan0Fabric 4 }
-- .11.8.5 LEAF wlan0.fabric.enable
wlan0FabricEnable OBJECT-TYPE
  SYNTAX OCTET STRING
  MAX-ACCESS read-write
  STATUS current
  DESCRIPTION "run mesh fabric?"
  ::= { wlan0Fabric 5 }
----------------------------------------------------
-- .11.8.6. BRANCH wlan0.fabric.gateway.
--
wlan0FabricGateway OBJECT IDENTIFIER ::= { wlan0Fabric 6 }
-- .11.8.6.1 LEAF wlan0.fabric.gateway.enable
wlan0FabricGatewayEnable OBJECT-TYPE
  SYNTAX OCTET STRING
  MAX-ACCESS read-only
  STATUS current
  DESCRIPTION "is this node a gateway"
  ::= { wlan0FabricGateway 1 }
-- .11.8.6.2 LEAF wlan0.fabric.gateway.if
wlan0FabricGatewayIf OBJECT-TYPE
  SYNTAX OCTET STRING
  MAX-ACCESS read-only
  STATUS current
  DESCRIPTION "interface acting as mesh gateway, if any"
  ::= { wlan0FabricGateway 2 }
-- .11.8.7 LEAF wlan0.fabric.margin
wlan0FabricMargin OBJECT-TYPE
  SYNTAX INTEGER
  MAX-ACCESS read-write
  STATUS current
  DESCRIPTION "if rssi drops this far below .join, drop the neighbor"
  ::= { wlan0Fabric 7 }
-- .11.8.8 LEAF wlan0.fabric.route_advert
wlan0FabricRouteadvert OBJECT-TYPE
  SYNTAX OCTET STRING
  MAX-ACCESS read-write
  STATUS current
  DESCRIPTION "route advertisement arguments"
  ::= { wlan0Fabric 8 }
----------------------------------------------------
-- .11.8.9. BRANCH wlan0.fabric.rssi.
--
wlan0FabricRssi OBJECT IDENTIFIER ::= { wlan0Fabric 9 }
-- .11.8.9.1 LEAF wlan0.fabric.rssi.join
wlan0FabricRssiJoin OBJECT-TYPE
  SYNTAX INTEGER
  MAX-ACCESS read-write
  STATUS current
  DESCRIPTION "rssi level to join neighbor"
  ::= { wlan0FabricRssi 1 }
-- .11.8.9.2 LEAF wlan0.fabric.rssi.margin
wlan0FabricRssiMargin OBJECT-TYPE
  SYNTAX INTEGER
  MAX-ACCESS read-write
  STATUS current
  DESCRIPTION "if rssi drops this far below .join, drop neighbor"
  ::= { wlan0FabricRssi 2 }
-- .11.9 LEAF wlan0.frag
wlan0Frag OBJECT-TYPE
  SYNTAX OCTET STRING
  MAX-ACCESS read-write
  STATUS current
  DESCRIPTION "fragmentation threshold"
  ::= { wlan0 9 }
-- .11.10 LEAF wlan0.hide_essid
wlan0Hideessid OBJECT-TYPE
  SYNTAX OCTET STRING
  MAX-ACCESS read-write
  STATUS current
  DESCRIPTION "don't broadcast the essid"
  ::= { wlan0 10 }
-- .11.11 LEAF wlan0.if
wlan0If OBJECT-TYPE
  SYNTAX OCTET STRING
  MAX-ACCESS read-only
  STATUS current
  DESCRIPTION "interface associated with this module"
  ::= { wlan0 11 }
----------------------------------------------------
-- .11.12. BRANCH wlan0.ip.
--
wlan0Ip OBJECT IDENTIFIER ::= { wlan0 12 }
-- .11.12.1 LEAF wlan0.ip.address
wlan0IpAddress OBJECT-TYPE
  SYNTAX OCTET STRING
  MAX-ACCESS read-only
  STATUS current
  DESCRIPTION "ip address"
  ::= { wlan0Ip 1 }
-- .11.12.2 LEAF wlan0.ip.address_force
wlan0IpAddressforce OBJECT-TYPE
  SYNTAX OCTET STRING
  MAX-ACCESS read-only
  STATUS current
  DESCRIPTION "override .ip.address (or blank)"
  ::= { wlan0Ip 2 }
-- .11.12.3 LEAF wlan0.ip.broadcast
wlan0IpBroadcast OBJECT-TYPE
  SYNTAX OCTET STRING
  MAX-ACCESS read-only
  STATUS current
  DESCRIPTION "broadcast address"
  ::= { wlan0Ip 3 }
-- .11.12.4 LEAF wlan0.ip.broadcast_force
wlan0IpBroadcastforce OBJECT-TYPE
  SYNTAX OCTET STRING
  MAX-ACCESS read-only
  STATUS current
  DESCRIPTION "override .ip.broadcast (or blank)"
  ::= { wlan0Ip 4 }
-- .11.12.5 LEAF wlan0.ip.gateway
wlan0IpGateway OBJECT-TYPE
  SYNTAX OCTET STRING
  MAX-ACCESS read-only
  STATUS current
  DESCRIPTION "gateway address"
  ::= { wlan0Ip 5 }
-- .11.12.6 LEAF wlan0.ip.gateway_force
wlan0IpGatewayforce OBJECT-TYPE
  SYNTAX OCTET STRING
  MAX-ACCESS read-only
  STATUS current
  DESCRIPTION "override .ip.gateway (or blank)"
  ::= { wlan0Ip 6 }
-- .11.12.7 LEAF wlan0.ip.netmask
wlan0IpNetmask OBJECT-TYPE
  SYNTAX OCTET STRING
  MAX-ACCESS read-write
  STATUS current
  DESCRIPTION "network mask"
  ::= { wlan0Ip 7 }
-- .11.12.8 LEAF wlan0.ip.netmask_force
wlan0IpNetmaskforce OBJECT-TYPE
  SYNTAX OCTET STRING
  MAX-ACCESS read-only
  STATUS current
  DESCRIPTION "override .ip.netmask (or blank)"
  ::= { wlan0Ip 8 }
----------------------------------------------------
-- .11.13. BRANCH wlan0.iwconfig.
--
wlan0Iwconfig OBJECT IDENTIFIER ::= { wlan0 13 }
-- .11.13.1 LEAF wlan0.iwconfig.cmd
wlan0IwconfigCmd OBJECT-TYPE
  SYNTAX OCTET STRING
  MAX-ACCESS read-write
  STATUS current
  DESCRIPTION "parameters to pass to iwconfig after all other settings"
  ::= { wlan0Iwconfig 1 }
----------------------------------------------------
-- .11.14. BRANCH wlan0.iwpriv.
--
wlan0Iwpriv OBJECT IDENTIFIER ::= { wlan0 14 }
-- .11.14.1 LEAF wlan0.iwpriv.cmd
wlan0IwprivCmd OBJECT-TYPE
  SYNTAX OCTET STRING
  MAX-ACCESS read-write
  STATUS current
  DESCRIPTION "parameters to pass to iwpriv after all other settings"
  ::= { wlan0Iwpriv 1 }
-- .11.15 LEAF wlan0.key
wlan0Key OBJECT-TYPE
  SYNTAX OCTET STRING
  MAX-ACCESS read-write
  STATUS current
  DESCRIPTION "wep key - if present, overrides .keys"
  ::= { wlan0 15 }
----------------------------------------------------
-- .11.16. BRANCH wlan0.keys.
--
wlan0Keys OBJECT IDENTIFIER ::= { wlan0 16 }
-- .11.16.1 LEAF wlan0.keys.1
wlan0Keys1 OBJECT-TYPE
  SYNTAX OCTET STRING
  MAX-ACCESS read-write
  STATUS current
  DESCRIPTION "one of four keys selected with .keys.default"
  ::= { wlan0Keys 1 }
-- .11.16.2 LEAF wlan0.keys.2
wlan0Keys2 OBJECT-TYPE
  SYNTAX OCTET STRING
  MAX-ACCESS read-write
  STATUS current
  DESCRIPTION "one of four keys selected with .keys.default"
  ::= { wlan0Keys 2 }
-- .11.16.3 LEAF wlan0.keys.3
wlan0Keys3 OBJECT-TYPE
  SYNTAX OCTET STRING
  MAX-ACCESS read-write
  STATUS current
  DESCRIPTION "one of four keys selected with .keys.default"
  ::= { wlan0Keys 3 }
-- .11.16.4 LEAF wlan0.keys.4
wlan0Keys4 OBJECT-TYPE
  SYNTAX OCTET STRING
  MAX-ACCESS read-write
  STATUS current
  DESCRIPTION "one of four keys selected with .keys.default"
  ::= { wlan0Keys 4 }
-- .11.16.5 LEAF wlan0.keys.default
wlan0KeysDefault OBJECT-TYPE
  SYNTAX OCTET STRING
  MAX-ACCESS read-write
  STATUS current
  DESCRIPTION "1 to 4 to choose which of wlan0.keys.1-4 to use"
  ::= { wlan0Keys 5 }
----------------------------------------------------
-- .11.17. BRANCH wlan0.mconfd.
--
wlan0Mconfd OBJECT IDENTIFIER ::= { wlan0 17 }
-- .11.17.1 LEAF wlan0.mconfd.enable
wlan0MconfdEnable OBJECT-TYPE
  SYNTAX OCTET STRING
  MAX-ACCESS read-write
  STATUS current
  DESCRIPTION "run mconfd daemon? distributed mesh configuration"
  ::= { wlan0Mconfd 1 }
-- .11.17.2 LEAF wlan0.mconfd.external_hosts
wlan0MconfdExternalhosts OBJECT-TYPE
  SYNTAX OCTET STRING
  MAX-ACCESS read-only
  STATUS current
  DESCRIPTION "list of external hosts we try to make external"
  ::= { wlan0Mconfd 2 }
-- .11.18 LEAF wlan0.mode
wlan0Mode OBJECT-TYPE
  SYNTAX OCTET STRING
  MAX-ACCESS read-write
  STATUS current
  DESCRIPTION "operating mode ( ap/master, adhoc, adhoc-demo, sta/client )"
  ::= { wlan0 18 }
----------------------------------------------------
-- .11.19. BRANCH wlan0.mroute.
--
wlan0Mroute OBJECT IDENTIFIER ::= { wlan0 19 }
-- .11.19.1 LEAF wlan0.mroute.args
wlan0MrouteArgs OBJECT-TYPE
  SYNTAX OCTET STRING
  MAX-ACCESS read-write
  STATUS current
  DESCRIPTION "mroute arguments"
  ::= { wlan0Mroute 1 }
-- .11.19.2 LEAF wlan0.mroute.cmd
wlan0MrouteCmd OBJECT-TYPE
  SYNTAX OCTET STRING
  MAX-ACCESS read-write
  STATUS current
  DESCRIPTION "mroute command"
  ::= { wlan0Mroute 2 }
-- .11.19.3 LEAF wlan0.mroute.enable
wlan0MrouteEnable OBJECT-TYPE
  SYNTAX OCTET STRING
  MAX-ACCESS read-write
  STATUS current
  DESCRIPTION "run mroute daemon - IGMP query utility"
  ::= { wlan0Mroute 3 }
-- .11.20 LEAF wlan0.mtu
wlan0Mtu OBJECT-TYPE
  SYNTAX INTEGER
  MAX-ACCESS read-write
  STATUS current
  DESCRIPTION "maximum transmission unit - may cause serious problems if set too low"
  ::= { wlan0 20 }
-- .11.21 LEAF wlan0.radio
wlan0Radio OBJECT-TYPE
  SYNTAX OCTET STRING
  MAX-ACCESS read-write
  STATUS current
  DESCRIPTION "which physical radio this vap is on (0 or 1)"
  ::= { wlan0 21 }
-- .11.22 LEAF wlan0.rate
wlan0Rate OBJECT-TYPE
  SYNTAX OCTET STRING
  MAX-ACCESS read-write
  STATUS current
  DESCRIPTION "communications rate"
  ::= { wlan0 22 }
-- .11.23 LEAF wlan0.role
wlan0Role OBJECT-TYPE
  SYNTAX OCTET STRING
  MAX-ACCESS read-write
  STATUS current
  DESCRIPTION "intended interface role (mesh, pxp (point to point), bridge)"
  ::= { wlan0 23 }
----------------------------------------------------
-- .11.24. BRANCH wlan0.routes.
--
wlan0Routes OBJECT IDENTIFIER ::= { wlan0 24 }
-- .11.24.1 LEAF wlan0.routes.add_privnets
wlan0RoutesAddprivnets OBJECT-TYPE
  SYNTAX OCTET STRING
  MAX-ACCESS read-write
  STATUS current
  DESCRIPTION "add sys.nets.internal.combined to mesh static routes?"
  ::= { wlan0Routes 1 }
-- .11.24.2 LEAF wlan0.routes.static
wlan0RoutesStatic OBJECT-TYPE
  SYNTAX OCTET STRING
  MAX-ACCESS read-write
  STATUS current
  DESCRIPTION "static routes for this interface"
  ::= { wlan0Routes 2 }
----------------------------------------------------
-- .11.25. BRANCH wlan0.topomc.
--
wlan0Topomc OBJECT IDENTIFIER ::= { wlan0 25 }
-- .11.25.1 LEAF wlan0.topomc.args
wlan0TopomcArgs OBJECT-TYPE
  SYNTAX OCTET STRING
  MAX-ACCESS read-write
  STATUS current
  DESCRIPTION "topomc arguments"
  ::= { wlan0Topomc 1 }
-- .11.25.2 LEAF wlan0.topomc.cmd
wlan0TopomcCmd OBJECT-TYPE
  SYNTAX OCTET STRING
  MAX-ACCESS read-write
  STATUS current
  DESCRIPTION "topomc command"
  ::= { wlan0Topomc 2 }
-- .11.25.3 LEAF wlan0.topomc.enable
wlan0TopomcEnable OBJECT-TYPE
  SYNTAX OCTET STRING
  MAX-ACCESS read-write
  STATUS current
  DESCRIPTION "run topomc daemon? - network topology reporting"
  ::= { wlan0Topomc 3 }
----------------------------------------------------
-- .12. BRANCH wlan1.
--
wlan1 OBJECT IDENTIFIER ::= { enRoute 12 }
----------------------------------------------------
-- .12.1. BRANCH wlan1.acl.
--
wlan1Acl OBJECT IDENTIFIER ::= { wlan1 1 }
-- .12.1.1 LEAF wlan1.acl.mode
wlan1AclMode OBJECT-TYPE
  SYNTAX OCTET STRING
  MAX-ACCESS read-write
  STATUS current
  DESCRIPTION "access control list mode ( 'none', 'whitelist', 'blacklist' )"
  ::= { wlan1Acl 1 }
-- .12.2 LEAF wlan1.beacon_interval
wlan1Beaconinterval OBJECT-TYPE
  SYNTAX INTEGER
  MAX-ACCESS read-write
  STATUS current
  DESCRIPTION "beacon interval in milliseconds"
  ::= { wlan1 2 }
-- .12.3 LEAF wlan1.cellid
wlan1Cellid OBJECT-TYPE
  SYNTAX OCTET STRING
  MAX-ACCESS read-write
  STATUS current
  DESCRIPTION "cell id for adhoc mode"
  ::= { wlan1 3 }
----------------------------------------------------
-- .12.4. BRANCH wlan1.dhcp.
--
wlan1Dhcp OBJECT IDENTIFIER ::= { wlan1 4 }
-- .12.4.1 LEAF wlan1.dhcp.alwaysbroadcast
wlan1DhcpAlwaysbroadcast OBJECT-TYPE
  SYNTAX OCTET STRING
  MAX-ACCESS read-write
  STATUS current
  DESCRIPTION "always broadcast dhcp responses"
  ::= { wlan1Dhcp 1 }
-- .12.4.2 LEAF wlan1.dhcp.default_lease_time
wlan1DhcpDefaultleasetime OBJECT-TYPE
  SYNTAX INTEGER
  MAX-ACCESS read-write
  STATUS current
  DESCRIPTION "default dhcp lease expiration in seconds"
  ::= { wlan1Dhcp 2 }
-- .12.4.3 LEAF wlan1.dhcp.max_lease_time
wlan1DhcpMaxleasetime OBJECT-TYPE
  SYNTAX INTEGER
  MAX-ACCESS read-write
  STATUS current
  DESCRIPTION "maximum requestable dhcp lease expiration in seconds"
  ::= { wlan1Dhcp 3 }
----------------------------------------------------
-- .12.4.4. BRANCH wlan1.dhcp.relay.
--
wlan1DhcpRelay OBJECT IDENTIFIER ::= { wlan1Dhcp 4 }
-- .12.4.4.1 LEAF wlan1.dhcp.relay.enable
wlan1DhcpRelayEnable OBJECT-TYPE
  SYNTAX OCTET STRING
  MAX-ACCESS read-write
  STATUS current
  DESCRIPTION "use dhcp relay (if sys.dhcp.relay.enable=yes)"
  ::= { wlan1DhcpRelay 1 }
-- .12.4.5 LEAF wlan1.dhcp.reserve
wlan1DhcpReserve OBJECT-TYPE
  SYNTAX INTEGER
  MAX-ACCESS read-write
  STATUS current
  DESCRIPTION "ip addresses to reserve at bottom of range for static assignments"
  ::= { wlan1Dhcp 5 }
-- .12.4.6 LEAF wlan1.dhcp.role
wlan1DhcpRole OBJECT-TYPE
  SYNTAX OCTET STRING
  MAX-ACCESS read-write
  STATUS current
  DESCRIPTION "interface dhcp role (none, client, server)"
  ::= { wlan1Dhcp 6 }
-- .12.5 LEAF wlan1.enable
wlan1Enable OBJECT-TYPE
  SYNTAX OCTET STRING
  MAX-ACCESS read-write
  STATUS current
  DESCRIPTION "interface is enabled"
  ::= { wlan1 5 }
-- .12.6 LEAF wlan1.enh_sec
wlan1Enhsec OBJECT-TYPE
  SYNTAX OCTET STRING
  MAX-ACCESS read-write
  STATUS current
  DESCRIPTION "ignore clients that specify 'ANY' ssid"
  ::= { wlan1 6 }
-- .12.7 LEAF wlan1.essid
wlan1Essid OBJECT-TYPE
  SYNTAX OCTET STRING
  MAX-ACCESS read-write
  STATUS current
  DESCRIPTION "essid for this ap"
  ::= { wlan1 7 }
-- .12.8 LEAF wlan1.frag
wlan1Frag OBJECT-TYPE
  SYNTAX OCTET STRING
  MAX-ACCESS read-write
  STATUS current
  DESCRIPTION "fragmentation threshold"
  ::= { wlan1 8 }
-- .12.9 LEAF wlan1.hide_essid
wlan1Hideessid OBJECT-TYPE
  SYNTAX OCTET STRING
  MAX-ACCESS read-write
  STATUS current
  DESCRIPTION "don't broadcast the essid"
  ::= { wlan1 9 }
-- .12.10 LEAF wlan1.if
wlan1If OBJECT-TYPE
  SYNTAX OCTET STRING
  MAX-ACCESS read-only
  STATUS current
  DESCRIPTION "interface associated with this module"
  ::= { wlan1 10 }
----------------------------------------------------
-- .12.11. BRANCH wlan1.ip.
--
wlan1Ip OBJECT IDENTIFIER ::= { wlan1 11 }
-- .12.11.1 LEAF wlan1.ip.address
wlan1IpAddress OBJECT-TYPE
  SYNTAX OCTET STRING
  MAX-ACCESS read-only
  STATUS current
  DESCRIPTION "ip address"
  ::= { wlan1Ip 1 }
-- .12.11.2 LEAF wlan1.ip.address_force
wlan1IpAddressforce OBJECT-TYPE
  SYNTAX OCTET STRING
  MAX-ACCESS read-write
  STATUS current
  DESCRIPTION "override .ip.address (or blank)"
  ::= { wlan1Ip 2 }
-- .12.11.3 LEAF wlan1.ip.broadcast
wlan1IpBroadcast OBJECT-TYPE
  SYNTAX OCTET STRING
  MAX-ACCESS read-only
  STATUS current
  DESCRIPTION "broadcast address"
  ::= { wlan1Ip 3 }
-- .12.11.4 LEAF wlan1.ip.broadcast_force
wlan1IpBroadcastforce OBJECT-TYPE
  SYNTAX OCTET STRING
  MAX-ACCESS read-write
  STATUS current
  DESCRIPTION "override .ip.broadcast (or blank)"
  ::= { wlan1Ip 4 }
-- .12.11.5 LEAF wlan1.ip.gateway
wlan1IpGateway OBJECT-TYPE
  SYNTAX OCTET STRING
  MAX-ACCESS read-only
  STATUS current
  DESCRIPTION "gateway address"
  ::= { wlan1Ip 5 }
-- .12.11.6 LEAF wlan1.ip.gateway_force
wlan1IpGatewayforce OBJECT-TYPE
  SYNTAX OCTET STRING
  MAX-ACCESS read-write
  STATUS current
  DESCRIPTION "override .ip.gateway (or blank)"
  ::= { wlan1Ip 6 }
----------------------------------------------------
-- .12.11.7. BRANCH wlan1.ip.implicit.
--
wlan1IpImplicit OBJECT IDENTIFIER ::= { wlan1Ip 7 }
----------------------------------------------------
-- .12.11.7.1. BRANCH wlan1.ip.implicit.size.
--
wlan1IpImplicitSize OBJECT IDENTIFIER ::= { wlan1IpImplicit 1 }
-- .12.11.7.1.1 LEAF wlan1.ip.implicit.size.actual
wlan1IpImplicitSizeActual OBJECT-TYPE
  SYNTAX INTEGER
  MAX-ACCESS read-only
  STATUS current
  DESCRIPTION "actual size of assigned address range"
  ::= { wlan1IpImplicitSize 1 }
-- .12.11.7.1.2 LEAF wlan1.ip.implicit.size.requested
wlan1IpImplicitSizeRequested OBJECT-TYPE
  SYNTAX OCTET STRING
  MAX-ACCESS read-write
  STATUS current
  DESCRIPTION "requested size of address range (multiple of 32 minus 1)"
  ::= { wlan1IpImplicitSize 2 }
----------------------------------------------------
-- .12.11.7.2. BRANCH wlan1.ip.implicit.start.
--
wlan1IpImplicitStart OBJECT IDENTIFIER ::= { wlan1IpImplicit 2 }
-- .12.11.7.2.1 LEAF wlan1.ip.implicit.start.actual
wlan1IpImplicitStartActual OBJECT-TYPE
  SYNTAX INTEGER
  MAX-ACCESS read-only
  STATUS current
  DESCRIPTION "actual assigned fourth octet"
  ::= { wlan1IpImplicitStart 1 }
-- .12.11.7.2.2 LEAF wlan1.ip.implicit.start.requested
wlan1IpImplicitStartRequested OBJECT-TYPE
  SYNTAX OCTET STRING
  MAX-ACCESS read-write
  STATUS current
  DESCRIPTION "requested interface fourth octet (multiple of 32 plus 1)"
  ::= { wlan1IpImplicitStart 2 }
-- .12.11.8 LEAF wlan1.ip.netmask
wlan1IpNetmask OBJECT-TYPE
  SYNTAX OCTET STRING
  MAX-ACCESS read-only
  STATUS current
  DESCRIPTION "network mask"
  ::= { wlan1Ip 8 }
-- .12.11.9 LEAF wlan1.ip.netmask_force
wlan1IpNetmaskforce OBJECT-TYPE
  SYNTAX OCTET STRING
  MAX-ACCESS read-write
  STATUS current
  DESCRIPTION "override .ip.netmask (or blank)"
  ::= { wlan1Ip 9 }
----------------------------------------------------
-- .12.12. BRANCH wlan1.iwconfig.
--
wlan1Iwconfig OBJECT IDENTIFIER ::= { wlan1 12 }
-- .12.12.1 LEAF wlan1.iwconfig.cmd
wlan1IwconfigCmd OBJECT-TYPE
  SYNTAX OCTET STRING
  MAX-ACCESS read-write
  STATUS current
  DESCRIPTION "parameters to pass to iwconfig after all other settings"
  ::= { wlan1Iwconfig 1 }
----------------------------------------------------
-- .12.13. BRANCH wlan1.iwpriv.
--
wlan1Iwpriv OBJECT IDENTIFIER ::= { wlan1 13 }
-- .12.13.1 LEAF wlan1.iwpriv.cmd
wlan1IwprivCmd OBJECT-TYPE
  SYNTAX OCTET STRING
  MAX-ACCESS read-write
  STATUS current
  DESCRIPTION "parameters to pass to iwpriv after all other settings"
  ::= { wlan1Iwpriv 1 }
-- .12.14 LEAF wlan1.key
wlan1Key OBJECT-TYPE
  SYNTAX OCTET STRING
  MAX-ACCESS read-write
  STATUS current
  DESCRIPTION "wep key - if present, overrides .keys"
  ::= { wlan1 14 }
----------------------------------------------------
-- .12.15. BRANCH wlan1.keys.
--
wlan1Keys OBJECT IDENTIFIER ::= { wlan1 15 }
-- .12.15.1 LEAF wlan1.keys.1
wlan1Keys1 OBJECT-TYPE
  SYNTAX OCTET STRING
  MAX-ACCESS read-write
  STATUS current
  DESCRIPTION "one of four keys selected with .keys.default"
  ::= { wlan1Keys 1 }
-- .12.15.2 LEAF wlan1.keys.2
wlan1Keys2 OBJECT-TYPE
  SYNTAX OCTET STRING
  MAX-ACCESS read-write
  STATUS current
  DESCRIPTION "one of four keys selected with .keys.default"
  ::= { wlan1Keys 2 }
-- .12.15.3 LEAF wlan1.keys.3
wlan1Keys3 OBJECT-TYPE
  SYNTAX OCTET STRING
  MAX-ACCESS read-write
  STATUS current
  DESCRIPTION "one of four keys selected with .keys.default"
  ::= { wlan1Keys 3 }
-- .12.15.4 LEAF wlan1.keys.4
wlan1Keys4 OBJECT-TYPE
  SYNTAX OCTET STRING
  MAX-ACCESS read-write
  STATUS current
  DESCRIPTION "one of four keys selected with .keys.default"
  ::= { wlan1Keys 4 }
-- .12.15.5 LEAF wlan1.keys.default
wlan1KeysDefault OBJECT-TYPE
  SYNTAX OCTET STRING
  MAX-ACCESS read-write
  STATUS current
  DESCRIPTION "1 to 4 to choose which of wlan1.keys.1-4 to use"
  ::= { wlan1Keys 5 }
-- .12.16 LEAF wlan1.mode
wlan1Mode OBJECT-TYPE
  SYNTAX OCTET STRING
  MAX-ACCESS read-write
  STATUS current
  DESCRIPTION "operating mode ( ap/master, adhoc, adhoc-demo, sta/client )"
  ::= { wlan1 16 }
-- .12.17 LEAF wlan1.mtu
wlan1Mtu OBJECT-TYPE
  SYNTAX INTEGER
  MAX-ACCESS read-write
  STATUS current
  DESCRIPTION "maximum transmission unit - may cause serious problems if set too low"
  ::= { wlan1 17 }
-- .12.18 LEAF wlan1.radio
wlan1Radio OBJECT-TYPE
  SYNTAX OCTET STRING
  MAX-ACCESS read-write
  STATUS current
  DESCRIPTION "which physical radio this vap is on (0 or 1)"
  ::= { wlan1 18 }
-- .12.19 LEAF wlan1.rate
wlan1Rate OBJECT-TYPE
  SYNTAX OCTET STRING
  MAX-ACCESS read-write
  STATUS current
  DESCRIPTION "communications rate"
  ::= { wlan1 19 }
-- .12.20 LEAF wlan1.role
wlan1Role OBJECT-TYPE
  SYNTAX OCTET STRING
  MAX-ACCESS read-write
  STATUS current
  DESCRIPTION "intended interface role (access, bridge)"
  ::= { wlan1 20 }
----------------------------------------------------
-- .12.21. BRANCH wlan1.routes.
--
wlan1Routes OBJECT IDENTIFIER ::= { wlan1 21 }
-- .12.21.1 LEAF wlan1.routes.static
wlan1RoutesStatic OBJECT-TYPE
  SYNTAX OCTET STRING
  MAX-ACCESS read-write
  STATUS current
  DESCRIPTION "static routes for this interface"
  ::= { wlan1Routes 1 }
----------------------------------------------------
-- .12.22. BRANCH wlan1.vlan.
--
wlan1Vlan OBJECT IDENTIFIER ::= { wlan1 22 }
-- .12.22.1 LEAF wlan1.vlan.enable
wlan1VlanEnable OBJECT-TYPE
  SYNTAX OCTET STRING
  MAX-ACCESS read-write
  STATUS current
  DESCRIPTION "use a vlan for this interface"
  ::= { wlan1Vlan 1 }
-- .12.22.2 LEAF wlan1.vlan.id
wlan1VlanId OBJECT-TYPE
  SYNTAX INTEGER
  MAX-ACCESS read-write
  STATUS current
  DESCRIPTION "vlan id (0 and 1 are usually reserved)"
  ::= { wlan1Vlan 2 }
----------------------------------------------------
-- .12.23. BRANCH wlan1.wpa.
--
wlan1Wpa OBJECT IDENTIFIER ::= { wlan1 23 }
----------------------------------------------------
-- .12.23.1. BRANCH wlan1.wpa.auth.
--
wlan1WpaAuth OBJECT IDENTIFIER ::= { wlan1Wpa 1 }
-- .12.23.1.1 LEAF wlan1.wpa.auth.args
wlan1WpaAuthArgs OBJECT-TYPE
  SYNTAX OCTET STRING
  MAX-ACCESS read-write
  STATUS current
  DESCRIPTION "arguments passed to authenticator"
  ::= { wlan1WpaAuth 1 }
-- .12.23.1.2 LEAF wlan1.wpa.auth.custom
wlan1WpaAuthCustom OBJECT-TYPE
  SYNTAX OCTET STRING
  MAX-ACCESS read-write
  STATUS current
  DESCRIPTION "command used to start authenticator if .wpa.auth.type is 'custom'"
  ::= { wlan1WpaAuth 2 }
-- .12.23.1.3 LEAF wlan1.wpa.auth.internal
wlan1WpaAuthInternal OBJECT-TYPE
  SYNTAX OCTET STRING
  MAX-ACCESS read-write
  STATUS current
  DESCRIPTION "0 for external, 1 for internal"
  ::= { wlan1WpaAuth 3 }
----------------------------------------------------
-- .12.23.1.4. BRANCH wlan1.wpa.auth.server.
--
wlan1WpaAuthServer OBJECT IDENTIFIER ::= { wlan1WpaAuth 4 }
-- .12.23.1.4.1 LEAF wlan1.wpa.auth.server.addr
wlan1WpaAuthServerAddr OBJECT-TYPE
  SYNTAX OCTET STRING
  MAX-ACCESS read-write
  STATUS current
  DESCRIPTION "authentication server address"
  ::= { wlan1WpaAuthServer 1 }
-- .12.23.1.4.2 LEAF wlan1.wpa.auth.server.port
wlan1WpaAuthServerPort OBJECT-TYPE
  SYNTAX INTEGER
  MAX-ACCESS read-write
  STATUS current
  DESCRIPTION "authentication server port"
  ::= { wlan1WpaAuthServer 2 }
-- .12.23.1.4.3 LEAF wlan1.wpa.auth.server.shared_secret
wlan1WpaAuthServerSharedsecret OBJECT-TYPE
  SYNTAX OCTET STRING
  MAX-ACCESS read-write
  STATUS current
  DESCRIPTION "shared secret"
  ::= { wlan1WpaAuthServer 3 }
-- .12.23.1.5 LEAF wlan1.wpa.auth.type
wlan1WpaAuthType OBJECT-TYPE
  SYNTAX OCTET STRING
  MAX-ACCESS read-write
  STATUS current
  DESCRIPTION "'hostapd' or 'custom'"
  ::= { wlan1WpaAuth 5 }
-- .12.23.2 LEAF wlan1.wpa.bridge
wlan1WpaBridge OBJECT-TYPE
  SYNTAX OCTET STRING
  MAX-ACCESS read-only
  STATUS current
  DESCRIPTION "bridge if any, set by sys.l2.bridge.enable"
  ::= { wlan1Wpa 2 }
----------------------------------------------------
-- .12.23.3. BRANCH wlan1.wpa.ca.
--
wlan1WpaCa OBJECT IDENTIFIER ::= { wlan1Wpa 3 }
----------------------------------------------------
-- .12.23.3.1. BRANCH wlan1.wpa.ca.cert.
--
wlan1WpaCaCert OBJECT IDENTIFIER ::= { wlan1WpaCa 1 }
-- .12.23.3.1.1 LEAF wlan1.wpa.ca.cert.file
wlan1WpaCaCertFile OBJECT-TYPE
  SYNTAX OCTET STRING
  MAX-ACCESS read-write
  STATUS current
  DESCRIPTION "ca_cert file"
  ::= { wlan1WpaCaCert 1 }
----------------------------------------------------
-- .12.23.4. BRANCH wlan1.wpa.eapol.
--
wlan1WpaEapol OBJECT IDENTIFIER ::= { wlan1Wpa 4 }
-- .12.23.4.1 LEAF wlan1.wpa.eapol.version
wlan1WpaEapolVersion OBJECT-TYPE
  SYNTAX OCTET STRING
  MAX-ACCESS read-write
  STATUS current
  DESCRIPTION "2 is default, but some older clients need 1"
  ::= { wlan1WpaEapol 1 }
-- .12.23.5 LEAF wlan1.wpa.enable
wlan1WpaEnable OBJECT-TYPE
  SYNTAX OCTET STRING
  MAX-ACCESS read-write
  STATUS current
  DESCRIPTION "wpa support enabled?"
  ::= { wlan1Wpa 5 }
-- .12.23.6 LEAF wlan1.wpa.essid
wlan1WpaEssid OBJECT-TYPE
  SYNTAX OCTET STRING
  MAX-ACCESS read-write
  STATUS current
  DESCRIPTION "essid for wpa authentication"
  ::= { wlan1Wpa 6 }
-- .12.23.7 LEAF wlan1.wpa.if
wlan1WpaIf OBJECT-TYPE
  SYNTAX OCTET STRING
  MAX-ACCESS read-only
  STATUS current
  DESCRIPTION "management frame interface, same as wlan1.if"
  ::= { wlan1Wpa 7 }
-- .12.23.8 LEAF wlan1.wpa.key_mgmt
wlan1WpaKeymgmt OBJECT-TYPE
  SYNTAX OCTET STRING
  MAX-ACCESS read-write
  STATUS current
  DESCRIPTION "WPA-PSK and/or WPA-EAP"
  ::= { wlan1Wpa 8 }
-- .12.23.9 LEAF wlan1.wpa.mode
wlan1WpaMode OBJECT-TYPE
  SYNTAX INTEGER
  MAX-ACCESS read-write
  STATUS current
  DESCRIPTION "wpa modes: 1=wpa1, 2=wpa2, 3=both"
  ::= { wlan1Wpa 9 }
----------------------------------------------------
-- .12.23.10. BRANCH wlan1.wpa.node.
--
wlan1WpaNode OBJECT IDENTIFIER ::= { wlan1Wpa 10 }
----------------------------------------------------
-- .12.23.10.1. BRANCH wlan1.wpa.node.cert.
--
wlan1WpaNodeCert OBJECT IDENTIFIER ::= { wlan1WpaNode 1 }
-- .12.23.10.1.1 LEAF wlan1.wpa.node.cert.file
wlan1WpaNodeCertFile OBJECT-TYPE
  SYNTAX OCTET STRING
  MAX-ACCESS read-write
  STATUS current
  DESCRIPTION "server_cert file"
  ::= { wlan1WpaNodeCert 1 }
----------------------------------------------------
-- .12.23.10.2. BRANCH wlan1.wpa.node.key.
--
wlan1WpaNodeKey OBJECT IDENTIFIER ::= { wlan1WpaNode 2 }
-- .12.23.10.2.1 LEAF wlan1.wpa.node.key.file
wlan1WpaNodeKeyFile OBJECT-TYPE
  SYNTAX OCTET STRING
  MAX-ACCESS read-write
  STATUS current
  DESCRIPTION "private_key file"
  ::= { wlan1WpaNodeKey 1 }
-- .12.23.10.2.2 LEAF wlan1.wpa.node.key.passphrase
wlan1WpaNodeKeyPassphrase OBJECT-TYPE
  SYNTAX OCTET STRING
  MAX-ACCESS read-write
  STATUS current
  DESCRIPTION "passphrase for the node's private key"
  ::= { wlan1WpaNodeKey 2 }
-- .12.23.11 LEAF wlan1.wpa.pairwise
wlan1WpaPairwise OBJECT-TYPE
  SYNTAX OCTET STRING
  MAX-ACCESS read-write
  STATUS current
  DESCRIPTION "accepted cipher suites - CCMP and/or TKIP"
  ::= { wlan1Wpa 11 }
-- .12.23.12 LEAF wlan1.wpa.passphrase
wlan1WpaPassphrase OBJECT-TYPE
  SYNTAX OCTET STRING
  MAX-ACCESS read-write
  STATUS current
  DESCRIPTION "wpa passphrase"
  ::= { wlan1Wpa 12 }
----------------------------------------------------
-- .13. BRANCH wlan2.
--
wlan2 OBJECT IDENTIFIER ::= { enRoute 13 }
----------------------------------------------------
-- .13.1. BRANCH wlan2.acl.
--
wlan2Acl OBJECT IDENTIFIER ::= { wlan2 1 }
-- .13.1.1 LEAF wlan2.acl.mode
wlan2AclMode OBJECT-TYPE
  SYNTAX OCTET STRING
  MAX-ACCESS read-write
  STATUS current
  DESCRIPTION "access control list mode ( 'none', 'whitelist', 'blacklist' )"
  ::= { wlan2Acl 1 }
-- .13.2 LEAF wlan2.beacon_interval
wlan2Beaconinterval OBJECT-TYPE
  SYNTAX INTEGER
  MAX-ACCESS read-write
  STATUS current
  DESCRIPTION "beacon interval in milliseconds"
  ::= { wlan2 2 }
-- .13.3 LEAF wlan2.cellid
wlan2Cellid OBJECT-TYPE
  SYNTAX OCTET STRING
  MAX-ACCESS read-write
  STATUS current
  DESCRIPTION "cell id for adhoc mode"
  ::= { wlan2 3 }
----------------------------------------------------
-- .13.4. BRANCH wlan2.dhcp.
--
wlan2Dhcp OBJECT IDENTIFIER ::= { wlan2 4 }
-- .13.4.1 LEAF wlan2.dhcp.alwaysbroadcast
wlan2DhcpAlwaysbroadcast OBJECT-TYPE
  SYNTAX OCTET STRING
  MAX-ACCESS read-write
  STATUS current
  DESCRIPTION "always broadcast dhcp responses"
  ::= { wlan2Dhcp 1 }
-- .13.4.2 LEAF wlan2.dhcp.default_lease_time
wlan2DhcpDefaultleasetime OBJECT-TYPE
  SYNTAX INTEGER
  MAX-ACCESS read-write
  STATUS current
  DESCRIPTION "default dhcp lease expiration in seconds"
  ::= { wlan2Dhcp 2 }
-- .13.4.3 LEAF wlan2.dhcp.max_lease_time
wlan2DhcpMaxleasetime OBJECT-TYPE
  SYNTAX INTEGER
  MAX-ACCESS read-write
  STATUS current
  DESCRIPTION "maximum requestable dhcp lease expiration in seconds"
  ::= { wlan2Dhcp 3 }
----------------------------------------------------
-- .13.4.4. BRANCH wlan2.dhcp.relay.
--
wlan2DhcpRelay OBJECT IDENTIFIER ::= { wlan2Dhcp 4 }
-- .13.4.4.1 LEAF wlan2.dhcp.relay.enable
wlan2DhcpRelayEnable OBJECT-TYPE
  SYNTAX OCTET STRING
  MAX-ACCESS read-write
  STATUS current
  DESCRIPTION "use dhcp relay (if sys.dhcp.relay.enable=yes)"
  ::= { wlan2DhcpRelay 1 }
-- .13.4.5 LEAF wlan2.dhcp.reserve
wlan2DhcpReserve OBJECT-TYPE
  SYNTAX INTEGER
  MAX-ACCESS read-write
  STATUS current
  DESCRIPTION "ip addresses to reserve at bottom of range for static assignments"
  ::= { wlan2Dhcp 5 }
-- .13.4.6 LEAF wlan2.dhcp.role
wlan2DhcpRole OBJECT-TYPE
  SYNTAX OCTET STRING
  MAX-ACCESS read-write
  STATUS current
  DESCRIPTION "interface dhcp role (none, client, server)"
  ::= { wlan2Dhcp 6 }
-- .13.5 LEAF wlan2.enable
wlan2Enable OBJECT-TYPE
  SYNTAX OCTET STRING
  MAX-ACCESS read-write
  STATUS current
  DESCRIPTION "interface is enabled"
  ::= { wlan2 5 }
-- .13.6 LEAF wlan2.enh_sec
wlan2Enhsec OBJECT-TYPE
  SYNTAX OCTET STRING
  MAX-ACCESS read-write
  STATUS current
  DESCRIPTION "ignore clients that specify 'ANY' ssid"
  ::= { wlan2 6 }
-- .13.7 LEAF wlan2.essid
wlan2Essid OBJECT-TYPE
  SYNTAX OCTET STRING
  MAX-ACCESS read-write
  STATUS current
  DESCRIPTION "essid for this ap"
  ::= { wlan2 7 }
-- .13.8 LEAF wlan2.frag
wlan2Frag OBJECT-TYPE
  SYNTAX OCTET STRING
  MAX-ACCESS read-write
  STATUS current
  DESCRIPTION "fragmentation threshold"
  ::= { wlan2 8 }
-- .13.9 LEAF wlan2.hide_essid
wlan2Hideessid OBJECT-TYPE
  SYNTAX OCTET STRING
  MAX-ACCESS read-write
  STATUS current
  DESCRIPTION "don't broadcast the essid"
  ::= { wlan2 9 }
-- .13.10 LEAF wlan2.if
wlan2If OBJECT-TYPE
  SYNTAX OCTET STRING
  MAX-ACCESS read-only
  STATUS current
  DESCRIPTION "interface associated with this module"
  ::= { wlan2 10 }
----------------------------------------------------
-- .13.11. BRANCH wlan2.ip.
--
wlan2Ip OBJECT IDENTIFIER ::= { wlan2 11 }
-- .13.11.1 LEAF wlan2.ip.address
wlan2IpAddress OBJECT-TYPE
  SYNTAX OCTET STRING
  MAX-ACCESS read-only
  STATUS current
  DESCRIPTION "ip address"
  ::= { wlan2Ip 1 }
-- .13.11.2 LEAF wlan2.ip.address_force
wlan2IpAddressforce OBJECT-TYPE
  SYNTAX OCTET STRING
  MAX-ACCESS read-write
  STATUS current
  DESCRIPTION "override .ip.address (or blank)"
  ::= { wlan2Ip 2 }
-- .13.11.3 LEAF wlan2.ip.broadcast
wlan2IpBroadcast OBJECT-TYPE
  SYNTAX OCTET STRING
  MAX-ACCESS read-only
  STATUS current
  DESCRIPTION "broadcast address"
  ::= { wlan2Ip 3 }
-- .13.11.4 LEAF wlan2.ip.broadcast_force
wlan2IpBroadcastforce OBJECT-TYPE
  SYNTAX OCTET STRING
  MAX-ACCESS read-write
  STATUS current
  DESCRIPTION "override .ip.broadcast (or blank)"
  ::= { wlan2Ip 4 }
-- .13.11.5 LEAF wlan2.ip.gateway
wlan2IpGateway OBJECT-TYPE
  SYNTAX OCTET STRING
  MAX-ACCESS read-only
  STATUS current
  DESCRIPTION "gateway address"
  ::= { wlan2Ip 5 }
-- .13.11.6 LEAF wlan2.ip.gateway_force
wlan2IpGatewayforce OBJECT-TYPE
  SYNTAX OCTET STRING
  MAX-ACCESS read-write
  STATUS current
  DESCRIPTION "override .ip.gateway (or blank)"
  ::= { wlan2Ip 6 }
----------------------------------------------------
-- .13.11.7. BRANCH wlan2.ip.implicit.
--
wlan2IpImplicit OBJECT IDENTIFIER ::= { wlan2Ip 7 }
----------------------------------------------------
-- .13.11.7.1. BRANCH wlan2.ip.implicit.size.
--
wlan2IpImplicitSize OBJECT IDENTIFIER ::= { wlan2IpImplicit 1 }
-- .13.11.7.1.1 LEAF wlan2.ip.implicit.size.actual
wlan2IpImplicitSizeActual OBJECT-TYPE
  SYNTAX INTEGER
  MAX-ACCESS read-only
  STATUS current
  DESCRIPTION "actual size of assigned address range"
  ::= { wlan2IpImplicitSize 1 }
-- .13.11.7.1.2 LEAF wlan2.ip.implicit.size.requested
wlan2IpImplicitSizeRequested OBJECT-TYPE
  SYNTAX OCTET STRING
  MAX-ACCESS read-write
  STATUS current
  DESCRIPTION "requested size of address range (multiple of 32 minus 1)"
  ::= { wlan2IpImplicitSize 2 }
----------------------------------------------------
-- .13.11.7.2. BRANCH wlan2.ip.implicit.start.
--
wlan2IpImplicitStart OBJECT IDENTIFIER ::= { wlan2IpImplicit 2 }
-- .13.11.7.2.1 LEAF wlan2.ip.implicit.start.actual
wlan2IpImplicitStartActual OBJECT-TYPE
  SYNTAX INTEGER
  MAX-ACCESS read-only
  STATUS current
  DESCRIPTION "actual assigned fourth octet"
  ::= { wlan2IpImplicitStart 1 }
-- .13.11.7.2.2 LEAF wlan2.ip.implicit.start.requested
wlan2IpImplicitStartRequested OBJECT-TYPE
  SYNTAX OCTET STRING
  MAX-ACCESS read-write
  STATUS current
  DESCRIPTION "requested interface fourth octet (multiple of 32 plus 1)"
  ::= { wlan2IpImplicitStart 2 }
-- .13.11.8 LEAF wlan2.ip.netmask
wlan2IpNetmask OBJECT-TYPE
  SYNTAX OCTET STRING
  MAX-ACCESS read-only
  STATUS current
  DESCRIPTION "network mask"
  ::= { wlan2Ip 8 }
-- .13.11.9 LEAF wlan2.ip.netmask_force
wlan2IpNetmaskforce OBJECT-TYPE
  SYNTAX OCTET STRING
  MAX-ACCESS read-write
  STATUS current
  DESCRIPTION "override .ip.netmask (or blank)"
  ::= { wlan2Ip 9 }
----------------------------------------------------
-- .13.12. BRANCH wlan2.iwconfig.
--
wlan2Iwconfig OBJECT IDENTIFIER ::= { wlan2 12 }
-- .13.12.1 LEAF wlan2.iwconfig.cmd
wlan2IwconfigCmd OBJECT-TYPE
  SYNTAX OCTET STRING
  MAX-ACCESS read-write
  STATUS current
  DESCRIPTION "parameters to pass to iwconfig after all other settings"
  ::= { wlan2Iwconfig 1 }
----------------------------------------------------
-- .13.13. BRANCH wlan2.iwpriv.
--
wlan2Iwpriv OBJECT IDENTIFIER ::= { wlan2 13 }
-- .13.13.1 LEAF wlan2.iwpriv.cmd
wlan2IwprivCmd OBJECT-TYPE
  SYNTAX OCTET STRING
  MAX-ACCESS read-write
  STATUS current
  DESCRIPTION "parameters to pass to iwpriv after all other settings"
  ::= { wlan2Iwpriv 1 }
-- .13.14 LEAF wlan2.key
wlan2Key OBJECT-TYPE
  SYNTAX OCTET STRING
  MAX-ACCESS read-write
  STATUS current
  DESCRIPTION "wep key - if present, overrides .keys"
  ::= { wlan2 14 }
----------------------------------------------------
-- .13.15. BRANCH wlan2.keys.
--
wlan2Keys OBJECT IDENTIFIER ::= { wlan2 15 }
-- .13.15.1 LEAF wlan2.keys.1
wlan2Keys1 OBJECT-TYPE
  SYNTAX OCTET STRING
  MAX-ACCESS read-write
  STATUS current
  DESCRIPTION "one of four keys selected with .keys.default"
  ::= { wlan2Keys 1 }
-- .13.15.2 LEAF wlan2.keys.2
wlan2Keys2 OBJECT-TYPE
  SYNTAX OCTET STRING
  MAX-ACCESS read-write
  STATUS current
  DESCRIPTION "one of four keys selected with .keys.default"
  ::= { wlan2Keys 2 }
-- .13.15.3 LEAF wlan2.keys.3
wlan2Keys3 OBJECT-TYPE
  SYNTAX OCTET STRING
  MAX-ACCESS read-write
  STATUS current
  DESCRIPTION "one of four keys selected with .keys.default"
  ::= { wlan2Keys 3 }
-- .13.15.4 LEAF wlan2.keys.4
wlan2Keys4 OBJECT-TYPE
  SYNTAX OCTET STRING
  MAX-ACCESS read-write
  STATUS current
  DESCRIPTION "one of four keys selected with .keys.default"
  ::= { wlan2Keys 4 }
-- .13.15.5 LEAF wlan2.keys.default
wlan2KeysDefault OBJECT-TYPE
  SYNTAX OCTET STRING
  MAX-ACCESS read-write
  STATUS current
  DESCRIPTION "1 to 4 to choose which of wlan2.keys.1-4 to use"
  ::= { wlan2Keys 5 }
-- .13.16 LEAF wlan2.mode
wlan2Mode OBJECT-TYPE
  SYNTAX OCTET STRING
  MAX-ACCESS read-write
  STATUS current
  DESCRIPTION "operating mode ( ap/master, adhoc, adhoc-demo, sta/client )"
  ::= { wlan2 16 }
-- .13.17 LEAF wlan2.mtu
wlan2Mtu OBJECT-TYPE
  SYNTAX INTEGER
  MAX-ACCESS read-write
  STATUS current
  DESCRIPTION "maximum transmission unit - may cause serious problems if set too low"
  ::= { wlan2 17 }
-- .13.18 LEAF wlan2.radio
wlan2Radio OBJECT-TYPE
  SYNTAX OCTET STRING
  MAX-ACCESS read-write
  STATUS current
  DESCRIPTION "which physical radio this vap is on (0 or 1)"
  ::= { wlan2 18 }
-- .13.19 LEAF wlan2.rate
wlan2Rate OBJECT-TYPE
  SYNTAX OCTET STRING
  MAX-ACCESS read-write
  STATUS current
  DESCRIPTION "communications rate"
  ::= { wlan2 19 }
-- .13.20 LEAF wlan2.role
wlan2Role OBJECT-TYPE
  SYNTAX OCTET STRING
  MAX-ACCESS read-write
  STATUS current
  DESCRIPTION "intended interface role (access, bridge)"
  ::= { wlan2 20 }
----------------------------------------------------
-- .13.21. BRANCH wlan2.routes.
--
wlan2Routes OBJECT IDENTIFIER ::= { wlan2 21 }
-- .13.21.1 LEAF wlan2.routes.static
wlan2RoutesStatic OBJECT-TYPE
  SYNTAX OCTET STRING
  MAX-ACCESS read-write
  STATUS current
  DESCRIPTION "static routes for this interface"
  ::= { wlan2Routes 1 }
----------------------------------------------------
-- .13.22. BRANCH wlan2.vlan.
--
wlan2Vlan OBJECT IDENTIFIER ::= { wlan2 22 }
-- .13.22.1 LEAF wlan2.vlan.enable
wlan2VlanEnable OBJECT-TYPE
  SYNTAX OCTET STRING
  MAX-ACCESS read-write
  STATUS current
  DESCRIPTION "use a vlan for this interface"
  ::= { wlan2Vlan 1 }
-- .13.22.2 LEAF wlan2.vlan.id
wlan2VlanId OBJECT-TYPE
  SYNTAX INTEGER
  MAX-ACCESS read-write
  STATUS current
  DESCRIPTION "vlan id (0 and 1 are usually reserved)"
  ::= { wlan2Vlan 2 }
----------------------------------------------------
-- .13.23. BRANCH wlan2.wpa.
--
wlan2Wpa OBJECT IDENTIFIER ::= { wlan2 23 }
----------------------------------------------------
-- .13.23.1. BRANCH wlan2.wpa.auth.
--
wlan2WpaAuth OBJECT IDENTIFIER ::= { wlan2Wpa 1 }
-- .13.23.1.1 LEAF wlan2.wpa.auth.args
wlan2WpaAuthArgs OBJECT-TYPE
  SYNTAX OCTET STRING
  MAX-ACCESS read-write
  STATUS current
  DESCRIPTION "arguments passed to authenticator"
  ::= { wlan2WpaAuth 1 }
-- .13.23.1.2 LEAF wlan2.wpa.auth.custom
wlan2WpaAuthCustom OBJECT-TYPE
  SYNTAX OCTET STRING
  MAX-ACCESS read-write
  STATUS current
  DESCRIPTION "command used to start authenticator if .wpa.auth.type is 'custom'"
  ::= { wlan2WpaAuth 2 }
-- .13.23.1.3 LEAF wlan2.wpa.auth.internal
wlan2WpaAuthInternal OBJECT-TYPE
  SYNTAX OCTET STRING
  MAX-ACCESS read-write
  STATUS current
  DESCRIPTION "0 for external, 1 for internal"
  ::= { wlan2WpaAuth 3 }
----------------------------------------------------
-- .13.23.1.4. BRANCH wlan2.wpa.auth.server.
--
wlan2WpaAuthServer OBJECT IDENTIFIER ::= { wlan2WpaAuth 4 }
-- .13.23.1.4.1 LEAF wlan2.wpa.auth.server.addr
wlan2WpaAuthServerAddr OBJECT-TYPE
  SYNTAX OCTET STRING
  MAX-ACCESS read-write
  STATUS current
  DESCRIPTION "authentication server address"
  ::= { wlan2WpaAuthServer 1 }
-- .13.23.1.4.2 LEAF wlan2.wpa.auth.server.port
wlan2WpaAuthServerPort OBJECT-TYPE
  SYNTAX INTEGER
  MAX-ACCESS read-write
  STATUS current
  DESCRIPTION "authentication server port"
  ::= { wlan2WpaAuthServer 2 }
-- .13.23.1.4.3 LEAF wlan2.wpa.auth.server.shared_secret
wlan2WpaAuthServerSharedsecret OBJECT-TYPE
  SYNTAX OCTET STRING
  MAX-ACCESS read-write
  STATUS current
  DESCRIPTION "shared secret"
  ::= { wlan2WpaAuthServer 3 }
-- .13.23.1.5 LEAF wlan2.wpa.auth.type
wlan2WpaAuthType OBJECT-TYPE
  SYNTAX OCTET STRING
  MAX-ACCESS read-write
  STATUS current
  DESCRIPTION "'hostapd' or 'custom'"
  ::= { wlan2WpaAuth 5 }
-- .13.23.2 LEAF wlan2.wpa.bridge
wlan2WpaBridge OBJECT-TYPE
  SYNTAX OCTET STRING
  MAX-ACCESS read-only
  STATUS current
  DESCRIPTION "bridge if any, set by sys.l2.bridge.enable"
  ::= { wlan2Wpa 2 }
----------------------------------------------------
-- .13.23.3. BRANCH wlan2.wpa.ca.
--
wlan2WpaCa OBJECT IDENTIFIER ::= { wlan2Wpa 3 }
----------------------------------------------------
-- .13.23.3.1. BRANCH wlan2.wpa.ca.cert.
--
wlan2WpaCaCert OBJECT IDENTIFIER ::= { wlan2WpaCa 1 }
-- .13.23.3.1.1 LEAF wlan2.wpa.ca.cert.file
wlan2WpaCaCertFile OBJECT-TYPE
  SYNTAX OCTET STRING
  MAX-ACCESS read-write
  STATUS current
  DESCRIPTION "ca_cert file"
  ::= { wlan2WpaCaCert 1 }
----------------------------------------------------
-- .13.23.4. BRANCH wlan2.wpa.eapol.
--
wlan2WpaEapol OBJECT IDENTIFIER ::= { wlan2Wpa 4 }
-- .13.23.4.1 LEAF wlan2.wpa.eapol.version
wlan2WpaEapolVersion OBJECT-TYPE
  SYNTAX OCTET STRING
  MAX-ACCESS read-write
  STATUS current
  DESCRIPTION "2 is default, but some older clients need 1"
  ::= { wlan2WpaEapol 1 }
-- .13.23.5 LEAF wlan2.wpa.enable
wlan2WpaEnable OBJECT-TYPE
  SYNTAX OCTET STRING
  MAX-ACCESS read-write
  STATUS current
  DESCRIPTION "wpa support enabled?"
  ::= { wlan2Wpa 5 }
-- .13.23.6 LEAF wlan2.wpa.essid
wlan2WpaEssid OBJECT-TYPE
  SYNTAX OCTET STRING
  MAX-ACCESS read-write
  STATUS current
  DESCRIPTION "essid for wpa authentication"
  ::= { wlan2Wpa 6 }
-- .13.23.7 LEAF wlan2.wpa.if
wlan2WpaIf OBJECT-TYPE
  SYNTAX OCTET STRING
  MAX-ACCESS read-only
  STATUS current
  DESCRIPTION "management frame interface, same as wlan2.if"
  ::= { wlan2Wpa 7 }
-- .13.23.8 LEAF wlan2.wpa.key_mgmt
wlan2WpaKeymgmt OBJECT-TYPE
  SYNTAX OCTET STRING
  MAX-ACCESS read-write
  STATUS current
  DESCRIPTION "WPA-PSK and/or WPA-EAP"
  ::= { wlan2Wpa 8 }
-- .13.23.9 LEAF wlan2.wpa.mode
wlan2WpaMode OBJECT-TYPE
  SYNTAX INTEGER
  MAX-ACCESS read-write
  STATUS current
  DESCRIPTION "wpa modes: 1=wpa1, 2=wpa2, 3=both"
  ::= { wlan2Wpa 9 }
----------------------------------------------------
-- .13.23.10. BRANCH wlan2.wpa.node.
--
wlan2WpaNode OBJECT IDENTIFIER ::= { wlan2Wpa 10 }
----------------------------------------------------
-- .13.23.10.1. BRANCH wlan2.wpa.node.cert.
--
wlan2WpaNodeCert OBJECT IDENTIFIER ::= { wlan2WpaNode 1 }
-- .13.23.10.1.1 LEAF wlan2.wpa.node.cert.file
wlan2WpaNodeCertFile OBJECT-TYPE
  SYNTAX OCTET STRING
  MAX-ACCESS read-write
  STATUS current
  DESCRIPTION "server_cert file"
  ::= { wlan2WpaNodeCert 1 }
----------------------------------------------------
-- .13.23.10.2. BRANCH wlan2.wpa.node.key.
--
wlan2WpaNodeKey OBJECT IDENTIFIER ::= { wlan2WpaNode 2 }
-- .13.23.10.2.1 LEAF wlan2.wpa.node.key.file
wlan2WpaNodeKeyFile OBJECT-TYPE
  SYNTAX OCTET STRING
  MAX-ACCESS read-write
  STATUS current
  DESCRIPTION "private_key file"
  ::= { wlan2WpaNodeKey 1 }
-- .13.23.10.2.2 LEAF wlan2.wpa.node.key.passphrase
wlan2WpaNodeKeyPassphrase OBJECT-TYPE
  SYNTAX OCTET STRING
  MAX-ACCESS read-write
  STATUS current
  DESCRIPTION "passphrase for the node's private key"
  ::= { wlan2WpaNodeKey 2 }
-- .13.23.11 LEAF wlan2.wpa.pairwise
wlan2WpaPairwise OBJECT-TYPE
  SYNTAX OCTET STRING
  MAX-ACCESS read-write
  STATUS current
  DESCRIPTION "accepted cipher suites - CCMP and/or TKIP"
  ::= { wlan2Wpa 11 }
-- .13.23.12 LEAF wlan2.wpa.passphrase
wlan2WpaPassphrase OBJECT-TYPE
  SYNTAX OCTET STRING
  MAX-ACCESS read-write
  STATUS current
  DESCRIPTION "wpa passphrase"
  ::= { wlan2Wpa 12 }
----------------------------------------------------
-- .14. BRANCH wlan3.
--
wlan3 OBJECT IDENTIFIER ::= { enRoute 14 }
----------------------------------------------------
-- .14.1. BRANCH wlan3.acl.
--
wlan3Acl OBJECT IDENTIFIER ::= { wlan3 1 }
-- .14.1.1 LEAF wlan3.acl.mode
wlan3AclMode OBJECT-TYPE
  SYNTAX OCTET STRING
  MAX-ACCESS read-write
  STATUS current
  DESCRIPTION "access control list mode ( 'none', 'whitelist', 'blacklist' )"
  ::= { wlan3Acl 1 }
-- .14.2 LEAF wlan3.beacon_interval
wlan3Beaconinterval OBJECT-TYPE
  SYNTAX INTEGER
  MAX-ACCESS read-write
  STATUS current
  DESCRIPTION "beacon interval in milliseconds"
  ::= { wlan3 2 }
-- .14.3 LEAF wlan3.cellid
wlan3Cellid OBJECT-TYPE
  SYNTAX OCTET STRING
  MAX-ACCESS read-write
  STATUS current
  DESCRIPTION "cell id for adhoc mode"
  ::= { wlan3 3 }
----------------------------------------------------
-- .14.4. BRANCH wlan3.dhcp.
--
wlan3Dhcp OBJECT IDENTIFIER ::= { wlan3 4 }
-- .14.4.1 LEAF wlan3.dhcp.alwaysbroadcast
wlan3DhcpAlwaysbroadcast OBJECT-TYPE
  SYNTAX OCTET STRING
  MAX-ACCESS read-write
  STATUS current
  DESCRIPTION "always broadcast dhcp responses"
  ::= { wlan3Dhcp 1 }
-- .14.4.2 LEAF wlan3.dhcp.default_lease_time
wlan3DhcpDefaultleasetime OBJECT-TYPE
  SYNTAX INTEGER
  MAX-ACCESS read-write
  STATUS current
  DESCRIPTION "default dhcp lease expiration in seconds"
  ::= { wlan3Dhcp 2 }
-- .14.4.3 LEAF wlan3.dhcp.max_lease_time
wlan3DhcpMaxleasetime OBJECT-TYPE
  SYNTAX INTEGER
  MAX-ACCESS read-write
  STATUS current
  DESCRIPTION "maximum requestable dhcp lease expiration in seconds"
  ::= { wlan3Dhcp 3 }
----------------------------------------------------
-- .14.4.4. BRANCH wlan3.dhcp.relay.
--
wlan3DhcpRelay OBJECT IDENTIFIER ::= { wlan3Dhcp 4 }
-- .14.4.4.1 LEAF wlan3.dhcp.relay.enable
wlan3DhcpRelayEnable OBJECT-TYPE
  SYNTAX OCTET STRING
  MAX-ACCESS read-write
  STATUS current
  DESCRIPTION "use dhcp relay (if sys.dhcp.relay.enable=yes)"
  ::= { wlan3DhcpRelay 1 }
-- .14.4.5 LEAF wlan3.dhcp.reserve
wlan3DhcpReserve OBJECT-TYPE
  SYNTAX INTEGER
  MAX-ACCESS read-write
  STATUS current
  DESCRIPTION "ip addresses to reserve at bottom of range for static assignments"
  ::= { wlan3Dhcp 5 }
-- .14.4.6 LEAF wlan3.dhcp.role
wlan3DhcpRole OBJECT-TYPE
  SYNTAX OCTET STRING
  MAX-ACCESS read-write
  STATUS current
  DESCRIPTION "interface dhcp role (none, client, server)"
  ::= { wlan3Dhcp 6 }
-- .14.5 LEAF wlan3.enable
wlan3Enable OBJECT-TYPE
  SYNTAX OCTET STRING
  MAX-ACCESS read-write
  STATUS current
  DESCRIPTION "interface is enabled"
  ::= { wlan3 5 }
-- .14.6 LEAF wlan3.enh_sec
wlan3Enhsec OBJECT-TYPE
  SYNTAX OCTET STRING
  MAX-ACCESS read-write
  STATUS current
  DESCRIPTION "ignore clients that specify 'ANY' ssid"
  ::= { wlan3 6 }
-- .14.7 LEAF wlan3.essid
wlan3Essid OBJECT-TYPE
  SYNTAX OCTET STRING
  MAX-ACCESS read-write
  STATUS current
  DESCRIPTION "essid for this ap"
  ::= { wlan3 7 }
-- .14.8 LEAF wlan3.frag
wlan3Frag OBJECT-TYPE
  SYNTAX OCTET STRING
  MAX-ACCESS read-write
  STATUS current
  DESCRIPTION "fragmentation threshold"
  ::= { wlan3 8 }
-- .14.9 LEAF wlan3.hide_essid
wlan3Hideessid OBJECT-TYPE
  SYNTAX OCTET STRING
  MAX-ACCESS read-write
  STATUS current
  DESCRIPTION "don't broadcast the essid"
  ::= { wlan3 9 }
-- .14.10 LEAF wlan3.if
wlan3If OBJECT-TYPE
  SYNTAX OCTET STRING
  MAX-ACCESS read-only
  STATUS current
  DESCRIPTION "interface associated with this module"
  ::= { wlan3 10 }
----------------------------------------------------
-- .14.11. BRANCH wlan3.ip.
--
wlan3Ip OBJECT IDENTIFIER ::= { wlan3 11 }
-- .14.11.1 LEAF wlan3.ip.address
wlan3IpAddress OBJECT-TYPE
  SYNTAX OCTET STRING
  MAX-ACCESS read-only
  STATUS current
  DESCRIPTION "ip address"
  ::= { wlan3Ip 1 }
-- .14.11.2 LEAF wlan3.ip.address_force
wlan3IpAddressforce OBJECT-TYPE
  SYNTAX OCTET STRING
  MAX-ACCESS read-write
  STATUS current
  DESCRIPTION "override .ip.address (or blank)"
  ::= { wlan3Ip 2 }
-- .14.11.3 LEAF wlan3.ip.broadcast
wlan3IpBroadcast OBJECT-TYPE
  SYNTAX OCTET STRING
  MAX-ACCESS read-only
  STATUS current
  DESCRIPTION "broadcast address"
  ::= { wlan3Ip 3 }
-- .14.11.4 LEAF wlan3.ip.broadcast_force
wlan3IpBroadcastforce OBJECT-TYPE
  SYNTAX OCTET STRING
  MAX-ACCESS read-write
  STATUS current
  DESCRIPTION "override .ip.broadcast (or blank)"
  ::= { wlan3Ip 4 }
-- .14.11.5 LEAF wlan3.ip.gateway
wlan3IpGateway OBJECT-TYPE
  SYNTAX OCTET STRING
  MAX-ACCESS read-only
  STATUS current
  DESCRIPTION "gateway address"
  ::= { wlan3Ip 5 }
-- .14.11.6 LEAF wlan3.ip.gateway_force
wlan3IpGatewayforce OBJECT-TYPE
  SYNTAX OCTET STRING
  MAX-ACCESS read-write
  STATUS current
  DESCRIPTION "override .ip.gateway (or blank)"
  ::= { wlan3Ip 6 }
----------------------------------------------------
-- .14.11.7. BRANCH wlan3.ip.implicit.
--
wlan3IpImplicit OBJECT IDENTIFIER ::= { wlan3Ip 7 }
----------------------------------------------------
-- .14.11.7.1. BRANCH wlan3.ip.implicit.size.
--
wlan3IpImplicitSize OBJECT IDENTIFIER ::= { wlan3IpImplicit 1 }
-- .14.11.7.1.1 LEAF wlan3.ip.implicit.size.actual
wlan3IpImplicitSizeActual OBJECT-TYPE
  SYNTAX INTEGER
  MAX-ACCESS read-only
  STATUS current
  DESCRIPTION "actual size of assigned address range"
  ::= { wlan3IpImplicitSize 1 }
-- .14.11.7.1.2 LEAF wlan3.ip.implicit.size.requested
wlan3IpImplicitSizeRequested OBJECT-TYPE
  SYNTAX OCTET STRING
  MAX-ACCESS read-write
  STATUS current
  DESCRIPTION "requested size of address range (multiple of 32 minus 1)"
  ::= { wlan3IpImplicitSize 2 }
----------------------------------------------------
-- .14.11.7.2. BRANCH wlan3.ip.implicit.start.
--
wlan3IpImplicitStart OBJECT IDENTIFIER ::= { wlan3IpImplicit 2 }
-- .14.11.7.2.1 LEAF wlan3.ip.implicit.start.actual
wlan3IpImplicitStartActual OBJECT-TYPE
  SYNTAX INTEGER
  MAX-ACCESS read-only
  STATUS current
  DESCRIPTION "actual assigned fourth octet"
  ::= { wlan3IpImplicitStart 1 }
-- .14.11.7.2.2 LEAF wlan3.ip.implicit.start.requested
wlan3IpImplicitStartRequested OBJECT-TYPE
  SYNTAX OCTET STRING
  MAX-ACCESS read-write
  STATUS current
  DESCRIPTION "requested interface fourth octet (multiple of 32 plus 1)"
  ::= { wlan3IpImplicitStart 2 }
-- .14.11.8 LEAF wlan3.ip.netmask
wlan3IpNetmask OBJECT-TYPE
  SYNTAX OCTET STRING
  MAX-ACCESS read-only
  STATUS current
  DESCRIPTION "network mask"
  ::= { wlan3Ip 8 }
-- .14.11.9 LEAF wlan3.ip.netmask_force
wlan3IpNetmaskforce OBJECT-TYPE
  SYNTAX OCTET STRING
  MAX-ACCESS read-write
  STATUS current
  DESCRIPTION "override .ip.netmask (or blank)"
  ::= { wlan3Ip 9 }
----------------------------------------------------
-- .14.12. BRANCH wlan3.iwconfig.
--
wlan3Iwconfig OBJECT IDENTIFIER ::= { wlan3 12 }
-- .14.12.1 LEAF wlan3.iwconfig.cmd
wlan3IwconfigCmd OBJECT-TYPE
  SYNTAX OCTET STRING
  MAX-ACCESS read-write
  STATUS current
  DESCRIPTION "parameters to pass to iwconfig after all other settings"
  ::= { wlan3Iwconfig 1 }
----------------------------------------------------
-- .14.13. BRANCH wlan3.iwpriv.
--
wlan3Iwpriv OBJECT IDENTIFIER ::= { wlan3 13 }
-- .14.13.1 LEAF wlan3.iwpriv.cmd
wlan3IwprivCmd OBJECT-TYPE
  SYNTAX OCTET STRING
  MAX-ACCESS read-write
  STATUS current
  DESCRIPTION "parameters to pass to iwpriv after all other settings"
  ::= { wlan3Iwpriv 1 }
-- .14.14 LEAF wlan3.key
wlan3Key OBJECT-TYPE
  SYNTAX OCTET STRING
  MAX-ACCESS read-write
  STATUS current
  DESCRIPTION "wep key - if present, overrides .keys"
  ::= { wlan3 14 }
----------------------------------------------------
-- .14.15. BRANCH wlan3.keys.
--
wlan3Keys OBJECT IDENTIFIER ::= { wlan3 15 }
-- .14.15.1 LEAF wlan3.keys.1
wlan3Keys1 OBJECT-TYPE
  SYNTAX OCTET STRING
  MAX-ACCESS read-write
  STATUS current
  DESCRIPTION "one of four keys selected with .keys.default"
  ::= { wlan3Keys 1 }
-- .14.15.2 LEAF wlan3.keys.2
wlan3Keys2 OBJECT-TYPE
  SYNTAX OCTET STRING
  MAX-ACCESS read-write
  STATUS current
  DESCRIPTION "one of four keys selected with .keys.default"
  ::= { wlan3Keys 2 }
-- .14.15.3 LEAF wlan3.keys.3
wlan3Keys3 OBJECT-TYPE
  SYNTAX OCTET STRING
  MAX-ACCESS read-write
  STATUS current
  DESCRIPTION "one of four keys selected with .keys.default"
  ::= { wlan3Keys 3 }
-- .14.15.4 LEAF wlan3.keys.4
wlan3Keys4 OBJECT-TYPE
  SYNTAX OCTET STRING
  MAX-ACCESS read-write
  STATUS current
  DESCRIPTION "one of four keys selected with .keys.default"
  ::= { wlan3Keys 4 }
-- .14.15.5 LEAF wlan3.keys.default
wlan3KeysDefault OBJECT-TYPE
  SYNTAX OCTET STRING
  MAX-ACCESS read-write
  STATUS current
  DESCRIPTION "1 to 4 to choose which of wlan3.keys.1-4 to use"
  ::= { wlan3Keys 5 }
-- .14.16 LEAF wlan3.mode
wlan3Mode OBJECT-TYPE
  SYNTAX OCTET STRING
  MAX-ACCESS read-write
  STATUS current
  DESCRIPTION "operating mode ( ap/master, adhoc, adhoc-demo, sta/client )"
  ::= { wlan3 16 }
-- .14.17 LEAF wlan3.mtu
wlan3Mtu OBJECT-TYPE
  SYNTAX INTEGER
  MAX-ACCESS read-write
  STATUS current
  DESCRIPTION "maximum transmission unit - may cause serious problems if set too low"
  ::= { wlan3 17 }
-- .14.18 LEAF wlan3.radio
wlan3Radio OBJECT-TYPE
  SYNTAX OCTET STRING
  MAX-ACCESS read-write
  STATUS current
  DESCRIPTION "which physical radio this vap is on (0 or 1)"
  ::= { wlan3 18 }
-- .14.19 LEAF wlan3.rate
wlan3Rate OBJECT-TYPE
  SYNTAX OCTET STRING
  MAX-ACCESS read-write
  STATUS current
  DESCRIPTION "communications rate"
  ::= { wlan3 19 }
-- .14.20 LEAF wlan3.role
wlan3Role OBJECT-TYPE
  SYNTAX OCTET STRING
  MAX-ACCESS read-write
  STATUS current
  DESCRIPTION "intended interface role (access, bridge)"
  ::= { wlan3 20 }
----------------------------------------------------
-- .14.21. BRANCH wlan3.routes.
--
wlan3Routes OBJECT IDENTIFIER ::= { wlan3 21 }
-- .14.21.1 LEAF wlan3.routes.static
wlan3RoutesStatic OBJECT-TYPE
  SYNTAX OCTET STRING
  MAX-ACCESS read-write
  STATUS current
  DESCRIPTION "static routes for this interface"
  ::= { wlan3Routes 1 }
----------------------------------------------------
-- .14.22. BRANCH wlan3.vlan.
--
wlan3Vlan OBJECT IDENTIFIER ::= { wlan3 22 }
-- .14.22.1 LEAF wlan3.vlan.enable
wlan3VlanEnable OBJECT-TYPE
  SYNTAX OCTET STRING
  MAX-ACCESS read-write
  STATUS current
  DESCRIPTION "use a vlan for this interface"
  ::= { wlan3Vlan 1 }
-- .14.22.2 LEAF wlan3.vlan.id
wlan3VlanId OBJECT-TYPE
  SYNTAX INTEGER
  MAX-ACCESS read-write
  STATUS current
  DESCRIPTION "vlan id (0 and 1 are usually reserved)"
  ::= { wlan3Vlan 2 }
----------------------------------------------------
-- .14.23. BRANCH wlan3.wpa.
--
wlan3Wpa OBJECT IDENTIFIER ::= { wlan3 23 }
----------------------------------------------------
-- .14.23.1. BRANCH wlan3.wpa.auth.
--
wlan3WpaAuth OBJECT IDENTIFIER ::= { wlan3Wpa 1 }
-- .14.23.1.1 LEAF wlan3.wpa.auth.args
wlan3WpaAuthArgs OBJECT-TYPE
  SYNTAX OCTET STRING
  MAX-ACCESS read-write
  STATUS current
  DESCRIPTION "arguments passed to authenticator"
  ::= { wlan3WpaAuth 1 }
-- .14.23.1.2 LEAF wlan3.wpa.auth.custom
wlan3WpaAuthCustom OBJECT-TYPE
  SYNTAX OCTET STRING
  MAX-ACCESS read-write
  STATUS current
  DESCRIPTION "command used to start authenticator if .wpa.auth.type is 'custom'"
  ::= { wlan3WpaAuth 2 }
-- .14.23.1.3 LEAF wlan3.wpa.auth.internal
wlan3WpaAuthInternal OBJECT-TYPE
  SYNTAX OCTET STRING
  MAX-ACCESS read-write
  STATUS current
  DESCRIPTION "0 for external, 1 for internal"
  ::= { wlan3WpaAuth 3 }
----------------------------------------------------
-- .14.23.1.4. BRANCH wlan3.wpa.auth.server.
--
wlan3WpaAuthServer OBJECT IDENTIFIER ::= { wlan3WpaAuth 4 }
-- .14.23.1.4.1 LEAF wlan3.wpa.auth.server.addr
wlan3WpaAuthServerAddr OBJECT-TYPE
  SYNTAX OCTET STRING
  MAX-ACCESS read-write
  STATUS current
  DESCRIPTION "authentication server address"
  ::= { wlan3WpaAuthServer 1 }
-- .14.23.1.4.2 LEAF wlan3.wpa.auth.server.port
wlan3WpaAuthServerPort OBJECT-TYPE
  SYNTAX INTEGER
  MAX-ACCESS read-write
  STATUS current
  DESCRIPTION "authentication server port"
  ::= { wlan3WpaAuthServer 2 }
-- .14.23.1.4.3 LEAF wlan3.wpa.auth.server.shared_secret
wlan3WpaAuthServerSharedsecret OBJECT-TYPE
  SYNTAX OCTET STRING
  MAX-ACCESS read-write
  STATUS current
  DESCRIPTION "shared secret"
  ::= { wlan3WpaAuthServer 3 }
-- .14.23.1.5 LEAF wlan3.wpa.auth.type
wlan3WpaAuthType OBJECT-TYPE
  SYNTAX OCTET STRING
  MAX-ACCESS read-write
  STATUS current
  DESCRIPTION "'hostapd' or 'custom'"
  ::= { wlan3WpaAuth 5 }
-- .14.23.2 LEAF wlan3.wpa.bridge
wlan3WpaBridge OBJECT-TYPE
  SYNTAX OCTET STRING
  MAX-ACCESS read-only
  STATUS current
  DESCRIPTION "bridge if any, set by sys.l2.bridge.enable"
  ::= { wlan3Wpa 2 }
----------------------------------------------------
-- .14.23.3. BRANCH wlan3.wpa.ca.
--
wlan3WpaCa OBJECT IDENTIFIER ::= { wlan3Wpa 3 }
----------------------------------------------------
-- .14.23.3.1. BRANCH wlan3.wpa.ca.cert.
--
wlan3WpaCaCert OBJECT IDENTIFIER ::= { wlan3WpaCa 1 }
-- .14.23.3.1.1 LEAF wlan3.wpa.ca.cert.file
wlan3WpaCaCertFile OBJECT-TYPE
  SYNTAX OCTET STRING
  MAX-ACCESS read-write
  STATUS current
  DESCRIPTION "ca_cert file"
  ::= { wlan3WpaCaCert 1 }
----------------------------------------------------
-- .14.23.4. BRANCH wlan3.wpa.eapol.
--
wlan3WpaEapol OBJECT IDENTIFIER ::= { wlan3Wpa 4 }
-- .14.23.4.1 LEAF wlan3.wpa.eapol.version
wlan3WpaEapolVersion OBJECT-TYPE
  SYNTAX OCTET STRING
  MAX-ACCESS read-write
  STATUS current
  DESCRIPTION "2 is default, but some older clients need 1"
  ::= { wlan3WpaEapol 1 }
-- .14.23.5 LEAF wlan3.wpa.enable
wlan3WpaEnable OBJECT-TYPE
  SYNTAX OCTET STRING
  MAX-ACCESS read-write
  STATUS current
  DESCRIPTION "wpa support enabled?"
  ::= { wlan3Wpa 5 }
-- .14.23.6 LEAF wlan3.wpa.essid
wlan3WpaEssid OBJECT-TYPE
  SYNTAX OCTET STRING
  MAX-ACCESS read-write
  STATUS current
  DESCRIPTION "essid for wpa authentication"
  ::= { wlan3Wpa 6 }
-- .14.23.7 LEAF wlan3.wpa.if
wlan3WpaIf OBJECT-TYPE
  SYNTAX OCTET STRING
  MAX-ACCESS read-only
  STATUS current
  DESCRIPTION "management frame interface, same as wlan3.if"
  ::= { wlan3Wpa 7 }
-- .14.23.8 LEAF wlan3.wpa.key_mgmt
wlan3WpaKeymgmt OBJECT-TYPE
  SYNTAX OCTET STRING
  MAX-ACCESS read-write
  STATUS current
  DESCRIPTION "WPA-PSK and/or WPA-EAP"
  ::= { wlan3Wpa 8 }
-- .14.23.9 LEAF wlan3.wpa.mode
wlan3WpaMode OBJECT-TYPE
  SYNTAX INTEGER
  MAX-ACCESS read-write
  STATUS current
  DESCRIPTION "wpa modes: 1=wpa1, 2=wpa2, 3=both"
  ::= { wlan3Wpa 9 }
----------------------------------------------------
-- .14.23.10. BRANCH wlan3.wpa.node.
--
wlan3WpaNode OBJECT IDENTIFIER ::= { wlan3Wpa 10 }
----------------------------------------------------
-- .14.23.10.1. BRANCH wlan3.wpa.node.cert.
--
wlan3WpaNodeCert OBJECT IDENTIFIER ::= { wlan3WpaNode 1 }
-- .14.23.10.1.1 LEAF wlan3.wpa.node.cert.file
wlan3WpaNodeCertFile OBJECT-TYPE
  SYNTAX OCTET STRING
  MAX-ACCESS read-write
  STATUS current
  DESCRIPTION "server_cert file"
  ::= { wlan3WpaNodeCert 1 }
----------------------------------------------------
-- .14.23.10.2. BRANCH wlan3.wpa.node.key.
--
wlan3WpaNodeKey OBJECT IDENTIFIER ::= { wlan3WpaNode 2 }
-- .14.23.10.2.1 LEAF wlan3.wpa.node.key.file
wlan3WpaNodeKeyFile OBJECT-TYPE
  SYNTAX OCTET STRING
  MAX-ACCESS read-write
  STATUS current
  DESCRIPTION "private_key file"
  ::= { wlan3WpaNodeKey 1 }
-- .14.23.10.2.2 LEAF wlan3.wpa.node.key.passphrase
wlan3WpaNodeKeyPassphrase OBJECT-TYPE
  SYNTAX OCTET STRING
  MAX-ACCESS read-write
  STATUS current
  DESCRIPTION "passphrase for the node's private key"
  ::= { wlan3WpaNodeKey 2 }
-- .14.23.11 LEAF wlan3.wpa.pairwise
wlan3WpaPairwise OBJECT-TYPE
  SYNTAX OCTET STRING
  MAX-ACCESS read-write
  STATUS current
  DESCRIPTION "accepted cipher suites - CCMP and/or TKIP"
  ::= { wlan3Wpa 11 }
-- .14.23.12 LEAF wlan3.wpa.passphrase
wlan3WpaPassphrase OBJECT-TYPE
  SYNTAX OCTET STRING
  MAX-ACCESS read-write
  STATUS current
  DESCRIPTION "wpa passphrase"
  ::= { wlan3Wpa 12 }
----------------------------------------------------
-- .15. BRANCH wlan4.
--
wlan4 OBJECT IDENTIFIER ::= { enRoute 15 }
----------------------------------------------------
-- .15.1. BRANCH wlan4.acl.
--
wlan4Acl OBJECT IDENTIFIER ::= { wlan4 1 }
-- .15.1.1 LEAF wlan4.acl.mode
wlan4AclMode OBJECT-TYPE
  SYNTAX OCTET STRING
  MAX-ACCESS read-write
  STATUS current
  DESCRIPTION "access control list mode ( 'none', 'whitelist', 'blacklist' )"
  ::= { wlan4Acl 1 }
-- .15.2 LEAF wlan4.beacon_interval
wlan4Beaconinterval OBJECT-TYPE
  SYNTAX INTEGER
  MAX-ACCESS read-write
  STATUS current
  DESCRIPTION "beacon interval in milliseconds"
  ::= { wlan4 2 }
-- .15.3 LEAF wlan4.cellid
wlan4Cellid OBJECT-TYPE
  SYNTAX OCTET STRING
  MAX-ACCESS read-write
  STATUS current
  DESCRIPTION "cell id for adhoc mode"
  ::= { wlan4 3 }
----------------------------------------------------
-- .15.4. BRANCH wlan4.dhcp.
--
wlan4Dhcp OBJECT IDENTIFIER ::= { wlan4 4 }
-- .15.4.1 LEAF wlan4.dhcp.alwaysbroadcast
wlan4DhcpAlwaysbroadcast OBJECT-TYPE
  SYNTAX OCTET STRING
  MAX-ACCESS read-write
  STATUS current
  DESCRIPTION "always broadcast dhcp responses"
  ::= { wlan4Dhcp 1 }
-- .15.4.2 LEAF wlan4.dhcp.default_lease_time
wlan4DhcpDefaultleasetime OBJECT-TYPE
  SYNTAX INTEGER
  MAX-ACCESS read-write
  STATUS current
  DESCRIPTION "default dhcp lease expiration in seconds"
  ::= { wlan4Dhcp 2 }
-- .15.4.3 LEAF wlan4.dhcp.max_lease_time
wlan4DhcpMaxleasetime OBJECT-TYPE
  SYNTAX INTEGER
  MAX-ACCESS read-write
  STATUS current
  DESCRIPTION "maximum requestable dhcp lease expiration in seconds"
  ::= { wlan4Dhcp 3 }
----------------------------------------------------
-- .15.4.4. BRANCH wlan4.dhcp.relay.
--
wlan4DhcpRelay OBJECT IDENTIFIER ::= { wlan4Dhcp 4 }
-- .15.4.4.1 LEAF wlan4.dhcp.relay.enable
wlan4DhcpRelayEnable OBJECT-TYPE
  SYNTAX OCTET STRING
  MAX-ACCESS read-write
  STATUS current
  DESCRIPTION "use dhcp relay (if sys.dhcp.relay.enable=yes)"
  ::= { wlan4DhcpRelay 1 }
-- .15.4.5 LEAF wlan4.dhcp.reserve
wlan4DhcpReserve OBJECT-TYPE
  SYNTAX INTEGER
  MAX-ACCESS read-write
  STATUS current
  DESCRIPTION "ip addresses to reserve at bottom of range for static assignments"
  ::= { wlan4Dhcp 5 }
-- .15.4.6 LEAF wlan4.dhcp.role
wlan4DhcpRole OBJECT-TYPE
  SYNTAX OCTET STRING
  MAX-ACCESS read-write
  STATUS current
  DESCRIPTION "interface dhcp role (none, client, server)"
  ::= { wlan4Dhcp 6 }
-- .15.5 LEAF wlan4.enable
wlan4Enable OBJECT-TYPE
  SYNTAX OCTET STRING
  MAX-ACCESS read-write
  STATUS current
  DESCRIPTION "interface is enabled"
  ::= { wlan4 5 }
-- .15.6 LEAF wlan4.enh_sec
wlan4Enhsec OBJECT-TYPE
  SYNTAX OCTET STRING
  MAX-ACCESS read-write
  STATUS current
  DESCRIPTION "ignore clients that specify 'ANY' ssid"
  ::= { wlan4 6 }
-- .15.7 LEAF wlan4.essid
wlan4Essid OBJECT-TYPE
  SYNTAX OCTET STRING
  MAX-ACCESS read-write
  STATUS current
  DESCRIPTION "essid for this ap"
  ::= { wlan4 7 }
-- .15.8 LEAF wlan4.frag
wlan4Frag OBJECT-TYPE
  SYNTAX OCTET STRING
  MAX-ACCESS read-write
  STATUS current
  DESCRIPTION "fragmentation threshold"
  ::= { wlan4 8 }
-- .15.9 LEAF wlan4.hide_essid
wlan4Hideessid OBJECT-TYPE
  SYNTAX OCTET STRING
  MAX-ACCESS read-write
  STATUS current
  DESCRIPTION "don't broadcast the essid"
  ::= { wlan4 9 }
-- .15.10 LEAF wlan4.if
wlan4If OBJECT-TYPE
  SYNTAX OCTET STRING
  MAX-ACCESS read-only
  STATUS current
  DESCRIPTION "interface associated with this module"
  ::= { wlan4 10 }
----------------------------------------------------
-- .15.11. BRANCH wlan4.ip.
--
wlan4Ip OBJECT IDENTIFIER ::= { wlan4 11 }
-- .15.11.1 LEAF wlan4.ip.address
wlan4IpAddress OBJECT-TYPE
  SYNTAX OCTET STRING
  MAX-ACCESS read-only
  STATUS current
  DESCRIPTION "ip address"
  ::= { wlan4Ip 1 }
-- .15.11.2 LEAF wlan4.ip.address_force
wlan4IpAddressforce OBJECT-TYPE
  SYNTAX OCTET STRING
  MAX-ACCESS read-write
  STATUS current
  DESCRIPTION "override .ip.address (or blank)"
  ::= { wlan4Ip 2 }
-- .15.11.3 LEAF wlan4.ip.broadcast
wlan4IpBroadcast OBJECT-TYPE
  SYNTAX OCTET STRING
  MAX-ACCESS read-only
  STATUS current
  DESCRIPTION "broadcast address"
  ::= { wlan4Ip 3 }
-- .15.11.4 LEAF wlan4.ip.broadcast_force
wlan4IpBroadcastforce OBJECT-TYPE
  SYNTAX OCTET STRING
  MAX-ACCESS read-write
  STATUS current
  DESCRIPTION "override .ip.broadcast (or blank)"
  ::= { wlan4Ip 4 }
-- .15.11.5 LEAF wlan4.ip.gateway
wlan4IpGateway OBJECT-TYPE
  SYNTAX OCTET STRING
  MAX-ACCESS read-only
  STATUS current
  DESCRIPTION "gateway address"
  ::= { wlan4Ip 5 }
-- .15.11.6 LEAF wlan4.ip.gateway_force
wlan4IpGatewayforce OBJECT-TYPE
  SYNTAX OCTET STRING
  MAX-ACCESS read-write
  STATUS current
  DESCRIPTION "override .ip.gateway (or blank)"
  ::= { wlan4Ip 6 }
----------------------------------------------------
-- .15.11.7. BRANCH wlan4.ip.implicit.
--
wlan4IpImplicit OBJECT IDENTIFIER ::= { wlan4Ip 7 }
----------------------------------------------------
-- .15.11.7.1. BRANCH wlan4.ip.implicit.size.
--
wlan4IpImplicitSize OBJECT IDENTIFIER ::= { wlan4IpImplicit 1 }
-- .15.11.7.1.1 LEAF wlan4.ip.implicit.size.actual
wlan4IpImplicitSizeActual OBJECT-TYPE
  SYNTAX INTEGER
  MAX-ACCESS read-only
  STATUS current
  DESCRIPTION "actual size of assigned address range"
  ::= { wlan4IpImplicitSize 1 }
-- .15.11.7.1.2 LEAF wlan4.ip.implicit.size.requested
wlan4IpImplicitSizeRequested OBJECT-TYPE
  SYNTAX OCTET STRING
  MAX-ACCESS read-write
  STATUS current
  DESCRIPTION "requested size of address range (multiple of 32 minus 1)"
  ::= { wlan4IpImplicitSize 2 }
----------------------------------------------------
-- .15.11.7.2. BRANCH wlan4.ip.implicit.start.
--
wlan4IpImplicitStart OBJECT IDENTIFIER ::= { wlan4IpImplicit 2 }
-- .15.11.7.2.1 LEAF wlan4.ip.implicit.start.actual
wlan4IpImplicitStartActual OBJECT-TYPE
  SYNTAX INTEGER
  MAX-ACCESS read-only
  STATUS current
  DESCRIPTION "actual assigned fourth octet"
  ::= { wlan4IpImplicitStart 1 }
-- .15.11.7.2.2 LEAF wlan4.ip.implicit.start.requested
wlan4IpImplicitStartRequested OBJECT-TYPE
  SYNTAX OCTET STRING
  MAX-ACCESS read-write
  STATUS current
  DESCRIPTION "requested interface fourth octet (multiple of 32 plus 1)"
  ::= { wlan4IpImplicitStart 2 }
-- .15.11.8 LEAF wlan4.ip.netmask
wlan4IpNetmask OBJECT-TYPE
  SYNTAX OCTET STRING
  MAX-ACCESS read-only
  STATUS current
  DESCRIPTION "network mask"
  ::= { wlan4Ip 8 }
-- .15.11.9 LEAF wlan4.ip.netmask_force
wlan4IpNetmaskforce OBJECT-TYPE
  SYNTAX OCTET STRING
  MAX-ACCESS read-write
  STATUS current
  DESCRIPTION "override .ip.netmask (or blank)"
  ::= { wlan4Ip 9 }
----------------------------------------------------
-- .15.12. BRANCH wlan4.iwconfig.
--
wlan4Iwconfig OBJECT IDENTIFIER ::= { wlan4 12 }
-- .15.12.1 LEAF wlan4.iwconfig.cmd
wlan4IwconfigCmd OBJECT-TYPE
  SYNTAX OCTET STRING
  MAX-ACCESS read-write
  STATUS current
  DESCRIPTION "parameters to pass to iwconfig after all other settings"
  ::= { wlan4Iwconfig 1 }
----------------------------------------------------
-- .15.13. BRANCH wlan4.iwpriv.
--
wlan4Iwpriv OBJECT IDENTIFIER ::= { wlan4 13 }
-- .15.13.1 LEAF wlan4.iwpriv.cmd
wlan4IwprivCmd OBJECT-TYPE
  SYNTAX OCTET STRING
  MAX-ACCESS read-write
  STATUS current
  DESCRIPTION "parameters to pass to iwpriv after all other settings"
  ::= { wlan4Iwpriv 1 }
-- .15.14 LEAF wlan4.key
wlan4Key OBJECT-TYPE
  SYNTAX OCTET STRING
  MAX-ACCESS read-write
  STATUS current
  DESCRIPTION "wep key - if present, overrides .keys"
  ::= { wlan4 14 }
----------------------------------------------------
-- .15.15. BRANCH wlan4.keys.
--
wlan4Keys OBJECT IDENTIFIER ::= { wlan4 15 }
-- .15.15.1 LEAF wlan4.keys.1
wlan4Keys1 OBJECT-TYPE
  SYNTAX OCTET STRING
  MAX-ACCESS read-write
  STATUS current
  DESCRIPTION "one of four keys selected with .keys.default"
  ::= { wlan4Keys 1 }
-- .15.15.2 LEAF wlan4.keys.2
wlan4Keys2 OBJECT-TYPE
  SYNTAX OCTET STRING
  MAX-ACCESS read-write
  STATUS current
  DESCRIPTION "one of four keys selected with .keys.default"
  ::= { wlan4Keys 2 }
-- .15.15.3 LEAF wlan4.keys.3
wlan4Keys3 OBJECT-TYPE
  SYNTAX OCTET STRING
  MAX-ACCESS read-write
  STATUS current
  DESCRIPTION "one of four keys selected with .keys.default"
  ::= { wlan4Keys 3 }
-- .15.15.4 LEAF wlan4.keys.4
wlan4Keys4 OBJECT-TYPE
  SYNTAX OCTET STRING
  MAX-ACCESS read-write
  STATUS current
  DESCRIPTION "one of four keys selected with .keys.default"
  ::= { wlan4Keys 4 }
-- .15.15.5 LEAF wlan4.keys.default
wlan4KeysDefault OBJECT-TYPE
  SYNTAX OCTET STRING
  MAX-ACCESS read-write
  STATUS current
  DESCRIPTION "1 to 4 to choose which of wlan4.keys.1-4 to use"
  ::= { wlan4Keys 5 }
-- .15.16 LEAF wlan4.mode
wlan4Mode OBJECT-TYPE
  SYNTAX OCTET STRING
  MAX-ACCESS read-write
  STATUS current
  DESCRIPTION "operating mode ( ap/master, adhoc, adhoc-demo, sta/client )"
  ::= { wlan4 16 }
-- .15.17 LEAF wlan4.mtu
wlan4Mtu OBJECT-TYPE
  SYNTAX INTEGER
  MAX-ACCESS read-write
  STATUS current
  DESCRIPTION "maximum transmission unit - may cause serious problems if set too low"
  ::= { wlan4 17 }
-- .15.18 LEAF wlan4.radio
wlan4Radio OBJECT-TYPE
  SYNTAX OCTET STRING
  MAX-ACCESS read-write
  STATUS current
  DESCRIPTION "which physical radio this vap is on (0 or 1)"
  ::= { wlan4 18 }
-- .15.19 LEAF wlan4.rate
wlan4Rate OBJECT-TYPE
  SYNTAX OCTET STRING
  MAX-ACCESS read-write
  STATUS current
  DESCRIPTION "communications rate"
  ::= { wlan4 19 }
-- .15.20 LEAF wlan4.role
wlan4Role OBJECT-TYPE
  SYNTAX OCTET STRING
  MAX-ACCESS read-write
  STATUS current
  DESCRIPTION "intended interface role (access, bridge)"
  ::= { wlan4 20 }
----------------------------------------------------
-- .15.21. BRANCH wlan4.routes.
--
wlan4Routes OBJECT IDENTIFIER ::= { wlan4 21 }
-- .15.21.1 LEAF wlan4.routes.static
wlan4RoutesStatic OBJECT-TYPE
  SYNTAX OCTET STRING
  MAX-ACCESS read-write
  STATUS current
  DESCRIPTION "static routes for this interface"
  ::= { wlan4Routes 1 }
----------------------------------------------------
-- .15.22. BRANCH wlan4.vlan.
--
wlan4Vlan OBJECT IDENTIFIER ::= { wlan4 22 }
-- .15.22.1 LEAF wlan4.vlan.enable
wlan4VlanEnable OBJECT-TYPE
  SYNTAX OCTET STRING
  MAX-ACCESS read-write
  STATUS current
  DESCRIPTION "use a vlan for this interface"
  ::= { wlan4Vlan 1 }
-- .15.22.2 LEAF wlan4.vlan.id
wlan4VlanId OBJECT-TYPE
  SYNTAX INTEGER
  MAX-ACCESS read-write
  STATUS current
  DESCRIPTION "vlan id (0 and 1 are usually reserved)"
  ::= { wlan4Vlan 2 }
----------------------------------------------------
-- .15.23. BRANCH wlan4.wpa.
--
wlan4Wpa OBJECT IDENTIFIER ::= { wlan4 23 }
----------------------------------------------------
-- .15.23.1. BRANCH wlan4.wpa.auth.
--
wlan4WpaAuth OBJECT IDENTIFIER ::= { wlan4Wpa 1 }
-- .15.23.1.1 LEAF wlan4.wpa.auth.args
wlan4WpaAuthArgs OBJECT-TYPE
  SYNTAX OCTET STRING
  MAX-ACCESS read-write
  STATUS current
  DESCRIPTION "arguments passed to authenticator"
  ::= { wlan4WpaAuth 1 }
-- .15.23.1.2 LEAF wlan4.wpa.auth.custom
wlan4WpaAuthCustom OBJECT-TYPE
  SYNTAX OCTET STRING
  MAX-ACCESS read-write
  STATUS current
  DESCRIPTION "command used to start authenticator if .wpa.auth.type is 'custom'"
  ::= { wlan4WpaAuth 2 }
-- .15.23.1.3 LEAF wlan4.wpa.auth.internal
wlan4WpaAuthInternal OBJECT-TYPE
  SYNTAX OCTET STRING
  MAX-ACCESS read-write
  STATUS current
  DESCRIPTION "0 for external, 1 for internal"
  ::= { wlan4WpaAuth 3 }
----------------------------------------------------
-- .15.23.1.4. BRANCH wlan4.wpa.auth.server.
--
wlan4WpaAuthServer OBJECT IDENTIFIER ::= { wlan4WpaAuth 4 }
-- .15.23.1.4.1 LEAF wlan4.wpa.auth.server.addr
wlan4WpaAuthServerAddr OBJECT-TYPE
  SYNTAX OCTET STRING
  MAX-ACCESS read-write
  STATUS current
  DESCRIPTION "authentication server address"
  ::= { wlan4WpaAuthServer 1 }
-- .15.23.1.4.2 LEAF wlan4.wpa.auth.server.port
wlan4WpaAuthServerPort OBJECT-TYPE
  SYNTAX INTEGER
  MAX-ACCESS read-write
  STATUS current
  DESCRIPTION "authentication server port"
  ::= { wlan4WpaAuthServer 2 }
-- .15.23.1.4.3 LEAF wlan4.wpa.auth.server.shared_secret
wlan4WpaAuthServerSharedsecret OBJECT-TYPE
  SYNTAX OCTET STRING
  MAX-ACCESS read-write
  STATUS current
  DESCRIPTION "shared secret"
  ::= { wlan4WpaAuthServer 3 }
-- .15.23.1.5 LEAF wlan4.wpa.auth.type
wlan4WpaAuthType OBJECT-TYPE
  SYNTAX OCTET STRING
  MAX-ACCESS read-write
  STATUS current
  DESCRIPTION "'hostapd' or 'custom'"
  ::= { wlan4WpaAuth 5 }
-- .15.23.2 LEAF wlan4.wpa.bridge
wlan4WpaBridge OBJECT-TYPE
  SYNTAX OCTET STRING
  MAX-ACCESS read-only
  STATUS current
  DESCRIPTION "bridge if any, set by sys.l2.bridge.enable"
  ::= { wlan4Wpa 2 }
----------------------------------------------------
-- .15.23.3. BRANCH wlan4.wpa.ca.
--
wlan4WpaCa OBJECT IDENTIFIER ::= { wlan4Wpa 3 }
----------------------------------------------------
-- .15.23.3.1. BRANCH wlan4.wpa.ca.cert.
--
wlan4WpaCaCert OBJECT IDENTIFIER ::= { wlan4WpaCa 1 }
-- .15.23.3.1.1 LEAF wlan4.wpa.ca.cert.file
wlan4WpaCaCertFile OBJECT-TYPE
  SYNTAX OCTET STRING
  MAX-ACCESS read-write
  STATUS current
  DESCRIPTION "ca_cert file"
  ::= { wlan4WpaCaCert 1 }
----------------------------------------------------
-- .15.23.4. BRANCH wlan4.wpa.eapol.
--
wlan4WpaEapol OBJECT IDENTIFIER ::= { wlan4Wpa 4 }
-- .15.23.4.1 LEAF wlan4.wpa.eapol.version
wlan4WpaEapolVersion OBJECT-TYPE
  SYNTAX OCTET STRING
  MAX-ACCESS read-write
  STATUS current
  DESCRIPTION "2 is default, but some older clients need 1"
  ::= { wlan4WpaEapol 1 }
-- .15.23.5 LEAF wlan4.wpa.enable
wlan4WpaEnable OBJECT-TYPE
  SYNTAX OCTET STRING
  MAX-ACCESS read-write
  STATUS current
  DESCRIPTION "wpa support enabled?"
  ::= { wlan4Wpa 5 }
-- .15.23.6 LEAF wlan4.wpa.essid
wlan4WpaEssid OBJECT-TYPE
  SYNTAX OCTET STRING
  MAX-ACCESS read-write
  STATUS current
  DESCRIPTION "essid for wpa authentication"
  ::= { wlan4Wpa 6 }
-- .15.23.7 LEAF wlan4.wpa.if
wlan4WpaIf OBJECT-TYPE
  SYNTAX OCTET STRING
  MAX-ACCESS read-only
  STATUS current
  DESCRIPTION "management frame interface, same as wlan4.if"
  ::= { wlan4Wpa 7 }
-- .15.23.8 LEAF wlan4.wpa.key_mgmt
wlan4WpaKeymgmt OBJECT-TYPE
  SYNTAX OCTET STRING
  MAX-ACCESS read-write
  STATUS current
  DESCRIPTION "WPA-PSK and/or WPA-EAP"
  ::= { wlan4Wpa 8 }
-- .15.23.9 LEAF wlan4.wpa.mode
wlan4WpaMode OBJECT-TYPE
  SYNTAX INTEGER
  MAX-ACCESS read-write
  STATUS current
  DESCRIPTION "wpa modes: 1=wpa1, 2=wpa2, 3=both"
  ::= { wlan4Wpa 9 }
----------------------------------------------------
-- .15.23.10. BRANCH wlan4.wpa.node.
--
wlan4WpaNode OBJECT IDENTIFIER ::= { wlan4Wpa 10 }
----------------------------------------------------
-- .15.23.10.1. BRANCH wlan4.wpa.node.cert.
--
wlan4WpaNodeCert OBJECT IDENTIFIER ::= { wlan4WpaNode 1 }
-- .15.23.10.1.1 LEAF wlan4.wpa.node.cert.file
wlan4WpaNodeCertFile OBJECT-TYPE
  SYNTAX OCTET STRING
  MAX-ACCESS read-write
  STATUS current
  DESCRIPTION "server_cert file"
  ::= { wlan4WpaNodeCert 1 }
----------------------------------------------------
-- .15.23.10.2. BRANCH wlan4.wpa.node.key.
--
wlan4WpaNodeKey OBJECT IDENTIFIER ::= { wlan4WpaNode 2 }
-- .15.23.10.2.1 LEAF wlan4.wpa.node.key.file
wlan4WpaNodeKeyFile OBJECT-TYPE
  SYNTAX OCTET STRING
  MAX-ACCESS read-write
  STATUS current
  DESCRIPTION "private_key file"
  ::= { wlan4WpaNodeKey 1 }
-- .15.23.10.2.2 LEAF wlan4.wpa.node.key.passphrase
wlan4WpaNodeKeyPassphrase OBJECT-TYPE
  SYNTAX OCTET STRING
  MAX-ACCESS read-write
  STATUS current
  DESCRIPTION "passphrase for the node's private key"
  ::= { wlan4WpaNodeKey 2 }
-- .15.23.11 LEAF wlan4.wpa.pairwise
wlan4WpaPairwise OBJECT-TYPE
  SYNTAX OCTET STRING
  MAX-ACCESS read-write
  STATUS current
  DESCRIPTION "accepted cipher suites - CCMP and/or TKIP"
  ::= { wlan4Wpa 11 }
-- .15.23.12 LEAF wlan4.wpa.passphrase
wlan4WpaPassphrase OBJECT-TYPE
  SYNTAX OCTET STRING
  MAX-ACCESS read-write
  STATUS current
  DESCRIPTION "wpa passphrase"
  ::= { wlan4Wpa 12 }
			
--
-- Sensoria enterprise-specific traps
-- (number 6 traps):
--
enRouteTraps	OBJECT IDENTIFIER ::= { enRoute 100 }

-- traps are rooted at
-- .1.3.6.1.4.1.24350.100

--
-- Configuration Change Trap:
-- .1.3.6.1.4.1.24350.100.1
--
enRouteConfigChange TRAP-TYPE
	ENTERPRISE enRouteTraps
	VARIABLES { lastModification }
	DESCRIPTION
		"This trap is triggered when any modification
		 is done in the node configuration. Important note:
		 modifying interface status on a node does not send a
		 linkDown or linkUp trap to the NMS because the change
		 occurs at a node reboot. Only a config change trap
		 (this one) is sent."
	::= 1

--
-- Configuration Reset Trap
-- .1.3.6.1.4.1.24350.100.2
--
enRouteConfigReset TRAP-TYPE
	ENTERPRISE enRouteTraps
	VARIABLES { lastModification }
	DESCRIPTION
		"This trap is triggered when the node configuration is reloaded"
	::= 2

END
