-- 
-- Dell Remote Access Controller (RAC) and Chassis Management Controller (CMC)
-- Management Information Base
--
-- This MIB is the legacy iDRAC MIB.  Changes are no longer made to this MIB
-- for iDRACs.  iDRACs don't support all of the objects and traps defined
-- in this MIB.  There is a new and more extensive iDRAC MIB available for
-- newer iDRACs (iDRAC7 and newer).
--
-- This MIB is also the CMC MIB.  Changes are made to this MIB only for CMCs now.
--
-- Copyright (c) 2015 Dell Inc.
--
-- Last Changed Revision: 18
-- Last Changed Date: 2015-01-16 12:25:06 -0500 (Fri, 16 Jan 2015)
-- Text Last Updated: 2015-01-16 12:25:06 -0500 (Fri, 16 Jan 2015)
--

DELL-RAC-MIB DEFINITIONS ::= BEGIN
     
IMPORTS
	enterprises, TimeTicks
		FROM RFC1155-SMI
	OBJECT-TYPE
		FROM RFC-1212
	TRAP-TYPE
		FROM RFC-1215
	DisplayString
		FROM RFC1213-MIB;

-- text convention ------------------------------------------------------------------------     

	-------------------------------------------------------------------------------
	-- This data type is used to model textual information taken
	-- from the NVT ASCII character set.  By convention, objects
	-- with this syntax are declared as having
	--      SIZE (0..1023)
	-------------------------------------------------------------------------------
	DellString ::= DisplayString (SIZE (0..1023))

	DellRacType ::= INTEGER
	{
		other(1),               -- the DRAC type is not one of the following
		unknown(2),             -- the DRAC type is unknown
		dracIII(3),             -- Drac III
		era(4),                 -- ERA
		drac4(5),               -- Drac 4
		drac5(6),               -- Drac 5
		drac5MC(7),             -- Drac 5/MC
		cmc(8),                 -- CMC
		idrac(9),               -- iDRAC
		idrac7monolithic(16),   -- iDRAC7 Monolithic
		idrac7modular(17),      -- iDRAC7 Modular
		vrtxCMC(18),            -- VRTX CMC
		fx2CMC(19),             -- FX2 Family CMC
		idrac8monolithic(32),   -- iDRAC8 Monolithic
		idrac8modular(33)       -- iDRAC8 Modular
	}

	DellStatus ::= INTEGER
	{
		other(1),               -- the status of the object is not one of the following:
		unknown(2),             -- the status of the object is unknown
										--  (not known or monitored)
		ok(3),                  -- the status of the object is ok
		nonCritical(4),         -- the status of the object is warning, non-critical
		critical(5),            -- the status of the object is critical (failure)
		nonRecoverable(6)       -- the status of the object is non-recoverable (dead)
	}

	-------------------------------------------------------------------------------
	-- DellPowerReading is a string representation of a floating point value, 
	--   having exactly 3 digits of precision, and a maximum of 31 characters.
	--
	-- DellChassisPowerIndexRange defines the possible chassis power instances
	--   in this MIB.
	--
	-- DellCMCPSUIndexRange defines the possible CMC Power Supply Unit (PSU) 
	--   instances, per chassis power instance, in this MIB.
	--
	-- DellCMCPSUCapable is an enumeration of PSU presence and/or monitoring 
	--   capabilities.
	--
	-- DellTemperatureReading is an integer value, expressed in degrees Celsius.
	-------------------------------------------------------------------------------
	DellPowerReading ::= DisplayString (SIZE (0..32))

	DellCMCPowerIndexRange ::= INTEGER (1..1)

	DellCMCPSUIndexRange ::= INTEGER (1..6)

	DellCMCPSUCapable ::= INTEGER
	{
		absent(1),      -- power supply is not present
		none(2),        -- no power monitoring abilities
		basic(3)        -- basic power monitoring abilities
	}

	DellTemperatureReading ::= INTEGER

	-------------------------------------------------------------------------------
	-- DellTimestamp is defined in the displayable format:
	--
	--			yyyymmddHHMMSS.uuuuuuDooo
	--
	-- where yyyy is the year, mm is the month number, dd is the day of the month,
	-- HHMMSS are the hours, minutes and seconds, respectively, uuuuuu is the
	-- number of microseconds, D is the UTC offset direction, and ooo is the 
	-- offset from UTC, in minutes. 
	--
	-- Note: D is a plus (+) sign if east of UTC, and a minus (-) if west of UTC.
	--
	-- For example, Wednesday, May 25, 1994, at 1:30:15 PM EDT
	--   would be represented as: 19940525133015.000000-300
	-------------------------------------------------------------------------------
	DellTimestamp ::= DisplayString (SIZE (26))

	-------------------------------------------------------------------------------
	-- DellCMCServerIndexRange defines the possible chassis server instances
	--   in this MIB.
	--
	-- DellCMCServerCapable is an enumeration of server presence and/or monitoring 
	--   capabilities.
	-------------------------------------------------------------------------------
	DellCMCServerIndexRange ::= INTEGER (1..32)

	DellCMCServerCapable ::= INTEGER
	{
		absent(1),      -- server is not present
		none(2),        -- no server monitoring abilities
		basic(3),       -- basic server monitoring abilities
		off(4)          -- server is powered off
	}

	DellCMCServerStorageMode ::= INTEGER
	{
		notApplicable(1),    -- not applicable to server
		joined(2),           -- storage mode is Joined
		splitDualHost(3),    -- storage mode is Split Dual Host
		splitSingleHost(4),  -- storage mode is Split Single Host
		unknown(99)          -- storage mode is unknown
	}

	DellCMCServerIntrusionState ::= INTEGER
	{
		notApplicable(1),    -- not applicable to server
		closed(2),           -- intrusion state is Closed
		open(3),             -- intrusion state is Open
		unknown(99)          -- intrusion state is unknown
	}


-- MIB Objects and Tables --------------------------------------------------------

	dell                          OBJECT IDENTIFIER ::= { enterprises    674   }
	server3                       OBJECT IDENTIFIER ::= { dell           10892 }
	drsOutofBandGroup             OBJECT IDENTIFIER ::= { server3        2     }
	drsInformationGroup           OBJECT IDENTIFIER ::= { drsOutofBandGroup     1 }
	drsProductInfoGroup           OBJECT IDENTIFIER ::= { drsInformationGroup   1 }
	drsFirmwareGroup              OBJECT IDENTIFIER ::= { drsInformationGroup   2 }

	drsStatusGroup                OBJECT IDENTIFIER ::= { drsOutofBandGroup     2 }

	drsChassisStatusGroup         OBJECT IDENTIFIER ::= { drsOutofBandGroup     3 }
	drsStatusNowGroup             OBJECT IDENTIFIER ::= { drsChassisStatusGroup 1 }
	drsStatusPrevGroup            OBJECT IDENTIFIER ::= { drsChassisStatusGroup 2 }
	drsStatusChangeGroup          OBJECT IDENTIFIER ::= { drsChassisStatusGroup 3 }

	drsChassisPowerGroup          OBJECT IDENTIFIER ::= { drsOutofBandGroup     4 }

		DrsCMCPowerTableEntry ::= SEQUENCE
		{
			drsChassisIndex				DellCMCPowerIndexRange,
			drsPotentialPower				DellPowerReading,
			drsIdlePower					DellPowerReading,
			drsMaxPowerSpecification	DellPowerReading,
			drsPowerSurplus				DellPowerReading,
			drsKWhCumulative				DellPowerReading,
			drsKWhCumulativeTime			DellTimestamp,
			drsWattsPeakUsage				DellPowerReading,
			drsWattsPeakTime				DellTimestamp,
			drsWattsMinUsage				DellPowerReading,
			drsWattsMinTime				DellTimestamp,
			drsWattsResetTime				DellTimestamp,
			drsWattsReading				DellPowerReading,
			drsAmpsReading					DellPowerReading
		}

		DrsCMCPSUTableEntry ::= SEQUENCE
		{
			drsPSUChassisIndex			DellCMCPowerIndexRange,
			drsPSUIndex						DellCMCPSUIndexRange,
			drsPSULocation					DellString,
			drsPSUMonitoringCapable		DellCMCPSUCapable,
			drsPSUVoltsReading			DellPowerReading,
			drsPSUAmpsReading				DellPowerReading,
			drsPSUWattsReading			DellPowerReading
		}

	drsChassisServerGroup         OBJECT IDENTIFIER ::= { drsOutofBandGroup     5 }

		DrsCMCServerTableEntry ::= SEQUENCE
		{
			drsServerIndex				DellCMCServerIndexRange,
			drsServerMonitoringCapable  DellCMCServerCapable,
			drsServerServiceTag			DellString,
			drsServerSlotName			DellString,
			drsServerSlotNumber			DellString,
			drsServerNodeID				DellString,
			drsServerModel				DellString,
			drsServerAssetTag			DellString,
			drsServerNumStorageControllers	INTEGER,
			drsServerStorageMode        DellCMCServerStorageMode,
			drsServerIntrusionState     DellCMCServerIntrusionState,
			drsServerAssignedServerSlots  DellString
		}

	drsCMCAlertGroup              OBJECT IDENTIFIER ::= { drsOutofBandGroup    20 }
	drsChassisAlertVariables      OBJECT IDENTIFIER ::= { drsCMCAlertGroup     10 }
	drsCMCAlert2Group             OBJECT IDENTIFIER ::= { drsOutofBandGroup    21 }
	drsChassisAlert2Variables     OBJECT IDENTIFIER ::= { drsCMCAlert2Group    10 }

	drsAlertGroup                 OBJECT IDENTIFIER ::= { drsOutofBandGroup  5000 }
	drsAlertVariables             OBJECT IDENTIFIER ::= { drsAlertGroup        10 }
        

-- Variables and Traps ------------------------------------------------------------------------

	-------------------------------------------------------------------------------
	-- group: product information
	-------------------------------------------------------------------------------

	drsProductName      OBJECT-TYPE
		SYNTAX          DellString
		ACCESS          read-only
		STATUS          mandatory
		DESCRIPTION     "0001.0001.0001 This attribute defines the product name of a chassis management controller." 
			::= { drsProductInfoGroup 1 }

	drsProductShortName OBJECT-TYPE
		SYNTAX          DellString
		ACCESS          read-only
		STATUS          mandatory
		DESCRIPTION     "0001.0001.0002 This attribute defines the short product name of a chassis management controller. " 
			::= { drsProductInfoGroup 2 }

	drsProductDescription OBJECT-TYPE
		SYNTAX          DellString
		ACCESS          read-only
		STATUS          mandatory
		DESCRIPTION     "0001.0001.0003 This attribute defines the product description of a chassis management controller. " 
			::= { drsProductInfoGroup 3 }

	drsProductManufacturer OBJECT-TYPE
		SYNTAX          DellString
		ACCESS          read-only
		STATUS          mandatory
		DESCRIPTION     "0001.0001.0004 This attribute defines the product manufacturer of a chassis management controller. " 
			::= { drsProductInfoGroup 4 }

	drsProductVersion OBJECT-TYPE
		SYNTAX          DellString
		ACCESS          read-only
		STATUS          mandatory
		DESCRIPTION     "0001.0001.0005 This attribute defines the product version of a chassis management controller. " 
			::= { drsProductInfoGroup 5 }

	drsChassisServiceTag OBJECT-TYPE
		SYNTAX          DellString
		ACCESS          read-only
		STATUS          mandatory
		DESCRIPTION     "0001.0001.0007 This attribute defines the Service Tag of the chassis. " 
			::= { drsProductInfoGroup 6 }

	drsProductURL       OBJECT-TYPE
		SYNTAX          DellString 
		ACCESS          read-only
		STATUS          mandatory
		DESCRIPTION     "0001.0001.0006 This attribute defines the out-of-band UI URL of a chassis management controller. "
			::= { drsProductInfoGroup 7 }
                        
	drsProductChassisAssetTag  OBJECT-TYPE
		SYNTAX          DellString 
		ACCESS          read-only
		STATUS          mandatory
		DESCRIPTION     "0001.0001.0008 This attribute defines the Asset Tag of the chassis. "
			::= { drsProductInfoGroup 8 }

	drsProductChassisLocation  OBJECT-TYPE
		SYNTAX          DellString 
		ACCESS          read-only
		STATUS          mandatory
		DESCRIPTION     "0001.0001.0009 This attribute defines the location of the chassis. "
			::= { drsProductInfoGroup 9 }

	drsProductChassisName  OBJECT-TYPE
		SYNTAX          DellString 
		ACCESS          read-only
		STATUS          mandatory
		DESCRIPTION     "0001.0001.0010 This attribute defines the name of the chassis. "
			::= { drsProductInfoGroup 10 }

	drsSystemServiceTag  OBJECT-TYPE
		SYNTAX          DellString 
		ACCESS          read-only
		STATUS          mandatory
		DESCRIPTION     "0001.0001.0011 This attribute defines the service tag of a system. "
			::= { drsProductInfoGroup 11 }

	drsProductSystemAssetTag  OBJECT-TYPE
		SYNTAX          DellString 
		ACCESS          read-only
		STATUS          mandatory
		DESCRIPTION     "0001.0001.0012 This attribute defines the asset tag of a system. "
			::= { drsProductInfoGroup 12 }

	drsProductSystemSlot OBJECT-TYPE
		SYNTAX          DellString 
		ACCESS          read-only
		STATUS          mandatory
		DESCRIPTION     "0001.0001.0013 This attribute defines the slot number of a CMC. "
			::= { drsProductInfoGroup 13 }

	drsProductType  OBJECT-TYPE
		SYNTAX          DellRacType
		ACCESS          read-only
		STATUS          mandatory
		DESCRIPTION     "0001.0001.0014 This attribute defines type of a remote access card "
			::= { drsProductInfoGroup 14 }
               
	drsProductChassisDataCenter  OBJECT-TYPE
		SYNTAX          DellString 
		ACCESS          read-only
		STATUS          mandatory
		DESCRIPTION     "0001.0001.0015 This attribute defines the Data Center locator of the chassis. "
			::= { drsProductInfoGroup 15 }

	drsProductChassisAisle  OBJECT-TYPE
		SYNTAX          DellString 
		ACCESS          read-only
		STATUS          mandatory
		DESCRIPTION     "0001.0001.0016 This attribute defines the Aisle locator of the chassis. "
			::= { drsProductInfoGroup 16 }

	drsProductChassisRack  OBJECT-TYPE
		SYNTAX          DellString 
		ACCESS          read-only
		STATUS          mandatory
		DESCRIPTION     "0001.0001.0017 This attribute defines the Rack locator of the chassis. "
			::= { drsProductInfoGroup 17 }

	drsProductChassisRackSlot  OBJECT-TYPE
		SYNTAX          DellString 
		ACCESS          read-only
		STATUS          mandatory
		DESCRIPTION     "0001.0001.0018 This attribute defines the Rack Slot locator of the chassis. "
			::= { drsProductInfoGroup 18 }
               
	drsProductChassisModel  OBJECT-TYPE
		SYNTAX          DellString
		ACCESS          read-only
		STATUS          mandatory
		DESCRIPTION     "0001.0001.0019 This attribute defines the Model of the chassis."
			::= { drsProductInfoGroup 19 }
               
	drsProductChassisExpressServiceCode  OBJECT-TYPE
		SYNTAX          DellString
		ACCESS          read-only
		STATUS          mandatory
		DESCRIPTION     "0001.0001.0020 This attribute defines the Express Service Code of the chassis."
			::= { drsProductInfoGroup 20 }
               
	drsProductChassisSystemID  OBJECT-TYPE
		SYNTAX          INTEGER
		ACCESS          read-only
		STATUS          mandatory
		DESCRIPTION     "0001.0001.0021 This attribute defines the System ID of the chassis."
			::= { drsProductInfoGroup 21 }
               
	drsProductChassisSize  OBJECT-TYPE
		SYNTAX          INTEGER
		ACCESS          read-only
		STATUS          mandatory
		DESCRIPTION     "0001.0001.0022 This attribute defines the size of the
						chassis in rack units (U).  A U is a standard unit of
						measure for the height of a rack or rack-mountable component."
			::= { drsProductInfoGroup 22 }

	-------------------------------------------------------------------------------
	-- group: firmware
	-------------------------------------------------------------------------------

	drsFirmwareVersion  OBJECT-TYPE
		SYNTAX          DellString
		ACCESS          read-only
		STATUS          mandatory
		DESCRIPTION     "0001.0002.0001 This attribute defines the firmware version of chassis management controller 1."
			::= { drsFirmwareGroup 1 }

	drsiKVMFirmwareVersion  OBJECT-TYPE
		SYNTAX          DellString
		ACCESS          read-only
		STATUS          mandatory
		DESCRIPTION     "0001.0002.0002 This attribute defines the firmware version of the iKVM. " 
			::= { drsFirmwareGroup 2 }

	drsFirmwareVersion2 OBJECT-TYPE
		SYNTAX          DellString
		ACCESS          read-only
		STATUS          mandatory
		DESCRIPTION     "0001.0002.0003 This attribute defines the firmware version of chassis management controller 2."
			::= { drsFirmwareGroup 3 }

	-------------------------------------------------------------------------------
	-- group: chassis status
	-------------------------------------------------------------------------------

	drsGlobalSystemStatus OBJECT-TYPE
		SYNTAX          DellStatus
		ACCESS          read-only
		STATUS          mandatory
		DESCRIPTION     "0002.0001.0001 This attribute defines the overall chassis status
                      being monitored by the chassis management card." 
			::= { drsStatusGroup 1 }

	drsGlobalCurrStatus OBJECT-TYPE
		SYNTAX          DellStatus
		ACCESS          read-only
		STATUS          mandatory
		DESCRIPTION     "0003.0001.0001 This attribute defines the overall chassis status
                      being monitored by the chassis management card." 
			::= { drsStatusNowGroup 1 }

	drsIOMCurrStatus  OBJECT-TYPE
		SYNTAX          DellStatus
		ACCESS          read-only
		STATUS          mandatory
		DESCRIPTION     "0003.0001.0002 This attribute defines the IOM subsystem status
                      being monitored by the chassis management card." 
			::= { drsStatusNowGroup 2 }

	drsKVMCurrStatus  OBJECT-TYPE
		SYNTAX          DellStatus
		ACCESS          read-only
		STATUS          mandatory
		DESCRIPTION     "0003.0001.0003 This attribute defines the iKVM subsystem health status
                      being monitored by the chassis management card." 
			::= { drsStatusNowGroup 3 }

	drsRedCurrStatus  OBJECT-TYPE
		SYNTAX          DellStatus
		ACCESS          read-only
		STATUS          mandatory
		DESCRIPTION     "0003.0001.0004 This attribute defines the Redundancy status
                      being monitored by the chassis management card." 
			::= { drsStatusNowGroup 4 }

	drsPowerCurrStatus OBJECT-TYPE
		SYNTAX          DellStatus
		ACCESS          read-only
		STATUS          mandatory
		DESCRIPTION     "0003.0001.0005 This attribute defines the power subsystem health status
                      being monitored by the chassis management card." 
			::= { drsStatusNowGroup 5 }

	drsFanCurrStatus OBJECT-TYPE
		SYNTAX          DellStatus
		ACCESS          read-only
		STATUS          mandatory
		DESCRIPTION     "0003.0001.0006 This attribute defines the Fan subsystem health status
                      being monitored by the chassis management card." 
			::= { drsStatusNowGroup 6 }

	drsBladeCurrStatus OBJECT-TYPE
		SYNTAX          DellStatus
		ACCESS          read-only
		STATUS          mandatory
		DESCRIPTION     "0003.0001.0007 This attribute defines the Blade subsystem health status
                      being monitored by the chassis management card." 
			::= { drsStatusNowGroup 7 }

	drsTempCurrStatus OBJECT-TYPE
		SYNTAX          DellStatus
		ACCESS          read-only
		STATUS          mandatory
		DESCRIPTION     "0003.0001.0008 This attribute defines the Temp Sensor subsystem health status
                      being monitored by the chassis management card." 
			::= { drsStatusNowGroup 8 }

	drsCMCCurrStatus OBJECT-TYPE
		SYNTAX          DellStatus
		ACCESS          read-only
		STATUS          mandatory
		DESCRIPTION     "0003.0001.0009 This attribute defines the CMC health status
                      being monitored by the chassis management card." 
			::= { drsStatusNowGroup 9 }

	drsChassisFrontPanelAmbientTemperature OBJECT-TYPE
		SYNTAX          DellTemperatureReading
		ACCESS          read-only
		STATUS          mandatory
		DESCRIPTION     "0003.0001.0010 This attribute defines the ambient temperature
                      reading (in degrees Celsius) for the chassis front panel controller." 
			::= { drsStatusNowGroup 10 }

	drsCMCAmbientTemperature OBJECT-TYPE
		SYNTAX          DellTemperatureReading
		ACCESS          read-only
		STATUS          mandatory
		DESCRIPTION     "0003.0001.0011 This attribute defines the ambient temperature
                      reading (in degrees Celsius) for the chassis management card." 
			::= { drsStatusNowGroup 11 }

	drsCMCProcessorTemperature OBJECT-TYPE
		SYNTAX          DellTemperatureReading
		ACCESS          read-only
		STATUS          mandatory
		DESCRIPTION     "0003.0001.0012 This attribute defines the temperature reading
                      (in degrees Celsius) for the chassis management card processor." 
			::= { drsStatusNowGroup 12 }

	drsGlobalPrevStatus OBJECT-TYPE
		SYNTAX          DellStatus
		ACCESS          read-only
		STATUS          mandatory
		DESCRIPTION     "0003.0002.0001 This attribute defines the previous chassis status
                      recorded by the chassis management card." 
			::= { drsStatusPrevGroup 1 }
                
	drsIOMPrevStatus    OBJECT-TYPE
		SYNTAX          DellStatus
		ACCESS          read-only
		STATUS          mandatory
		DESCRIPTION     "0003.0002.0002 This attribute defines the previous IOM subsystem status
                      recorded by the chassis management card." 
			::= { drsStatusPrevGroup 2 }

	drsKVMPrevStatus    OBJECT-TYPE
		SYNTAX          DellStatus
		ACCESS          read-only
		STATUS          mandatory
		DESCRIPTION     "0003.0002.0003 This attribute defines the previous iKVM subsystem health status
                      recorded by the chassis management card." 
			::= { drsStatusPrevGroup 3 }

	drsRedPrevStatus    OBJECT-TYPE
		SYNTAX          DellStatus
		ACCESS          read-only
		STATUS          mandatory
		DESCRIPTION     "0003.0002.0004 This attribute defines the previous Redundancy status
                      recorded by the chassis management card." 
			::= { drsStatusPrevGroup 4 }

	drsPowerPrevStatus  OBJECT-TYPE
		SYNTAX          DellStatus
		ACCESS          read-only
		STATUS          mandatory
		DESCRIPTION     "0003.0002.0005 This attribute defines the previous power subsystem health status
                      recorded by the chassis management card." 
			::= { drsStatusPrevGroup 5 }

	drsFanPrevStatus OBJECT-TYPE
		SYNTAX          DellStatus
		ACCESS          read-only
		STATUS          mandatory
		DESCRIPTION     "0003.0002.0006 This attribute defines the previous Fan health status
                      being monitored by the chassis management card." 
			::= { drsStatusPrevGroup 6 }

	drsBladePrevStatus  OBJECT-TYPE
		SYNTAX          DellStatus
		ACCESS          read-only
		STATUS          mandatory
		DESCRIPTION     "0003.0002.0007 This attribute defines the previous Blade subsystem health status
                      recorded by the chassis management card." 
			::= { drsStatusPrevGroup 7 }

	drsTempPrevStatus OBJECT-TYPE
		SYNTAX          DellStatus
		ACCESS          read-only
		STATUS          mandatory
		DESCRIPTION     "0003.0001.0008 This attribute defines the Temp Sensor health status
                      being monitored by the chassis management card." 
			::= { drsStatusPrevGroup 8 }

	drsCMCPrevStatus OBJECT-TYPE
		SYNTAX          DellStatus
		ACCESS          read-only
		STATUS          mandatory
		DESCRIPTION     "0003.0001.0009 This attribute defines the CMC health status
                      being monitored by the chassis management card." 
			::= { drsStatusPrevGroup 9 }

	drsGlobalChangeTime OBJECT-TYPE
		SYNTAX          TimeTicks
		ACCESS          read-only
		STATUS          mandatory
		DESCRIPTION     "0003.0003.0001 This attribute defines the timestamp of the most recent 
                      global status change." 
			::= { drsStatusChangeGroup 1 }

	drsIOMChangeTime    OBJECT-TYPE
		SYNTAX          TimeTicks
		ACCESS          read-only
		STATUS          mandatory
		DESCRIPTION     "0003.0003.0002 This attribute defines the timestamp of the most recent 
                      IOM status change." 
			::= { drsStatusChangeGroup 2 }

	drsKVMChangeTime    OBJECT-TYPE
		SYNTAX          TimeTicks
		ACCESS          read-only
		STATUS          mandatory
		DESCRIPTION     "0003.0003.0003 This attribute defines the timestamp of the most recent 
                      iKVM status change." 
			::= { drsStatusChangeGroup 3 }

	drsRedChangeTime    OBJECT-TYPE
		SYNTAX          TimeTicks
		ACCESS          read-only
		STATUS          mandatory
		DESCRIPTION     "0003.0003.0004 This attribute defines the timestamp of the most recent 
                      Redundancy status change." 
			::= { drsStatusChangeGroup 4 }

	drsPowerChangeTime  OBJECT-TYPE
		SYNTAX          TimeTicks
		ACCESS          read-only
		STATUS          mandatory
		DESCRIPTION     "0003.0003.0005 This attribute defines the timestamp of the most recent 
                      power health status change." 
			::= { drsStatusChangeGroup 5 }

	drsFanChangeTime OBJECT-TYPE
		SYNTAX          TimeTicks
		ACCESS          read-only
		STATUS          mandatory
		DESCRIPTION     "0003.0003.0006 This attribute defines the timestamp of the most recent 
                      Fan health status change." 
			::= { drsStatusChangeGroup 6 }

	drsBladeChangeTime  OBJECT-TYPE
		SYNTAX          TimeTicks
		ACCESS          read-only
		STATUS          mandatory
		DESCRIPTION     "0003.0003.0007 This attribute defines the timestamp of the most recent 
                      Blade health status change." 
			::= { drsStatusChangeGroup 7 }

	drsTempChangeTime OBJECT-TYPE
		SYNTAX          TimeTicks
		ACCESS          read-only
		STATUS          mandatory
		DESCRIPTION     "0003.0003.0008 This attribute defines the timestamp of the most recent 
                      Temp Sensor health status change." 
			::= { drsStatusChangeGroup 8 }

	drsCMCChangeTime OBJECT-TYPE
		SYNTAX          TimeTicks
		ACCESS          read-only
		STATUS          mandatory
		DESCRIPTION     "0003.0003.0009 This attribute defines the timestamp of the most recent 
                      CMC health status change." 
			::= { drsStatusChangeGroup 9 }

	-------------------------------------------------------------------------------
	-- group: chassis power
	-------------------------------------------------------------------------------

	drsCMCPowerTable OBJECT-TYPE
		SYNTAX			SEQUENCE OF DrsCMCPowerTableEntry
		ACCESS			not-accessible
		STATUS			mandatory
		DESCRIPTION		"0004.0001 This object defines the CMC power table."
			::= { drsChassisPowerGroup 1 }

	drsCMCPowerTableEntry OBJECT-TYPE
		SYNTAX			DrsCMCPowerTableEntry
		ACCESS      	not-accessible
		STATUS      	mandatory
		DESCRIPTION 	"0004.0001.0001 This object defines the CMC power table entry."
		INDEX       	{ drsChassisIndex }
			::= { drsCMCPowerTable 1 }

	drsCMCPSUTable OBJECT-TYPE
		SYNTAX			SEQUENCE OF DrsCMCPSUTableEntry
		ACCESS			not-accessible
		STATUS			mandatory
		DESCRIPTION		"0004.0002 This object defines the CMC PSU table."
			::= { drsChassisPowerGroup 2 }

	drsCMCPSUTableEntry OBJECT-TYPE
		SYNTAX			DrsCMCPSUTableEntry
		ACCESS      	not-accessible
		STATUS      	mandatory
		DESCRIPTION 	"0004.0002.0001 This object defines the CMC PSU table entry."
		INDEX       	{ drsPSUChassisIndex, drsPSUIndex }
			::= { drsCMCPSUTable 1 }

	-------------------------------------------------------------------------------
	-- table: CMC power information
	-------------------------------------------------------------------------------

	drsChassisIndex OBJECT-TYPE
		SYNTAX			DellCMCPowerIndexRange
		ACCESS			read-only
		STATUS			mandatory
		DESCRIPTION		"0004.0001.0001.0001 This attribute defines the index
							(one-based) of the associated chassis."
			::= { drsCMCPowerTableEntry 1 }

	drsPotentialPower OBJECT-TYPE
		SYNTAX			DellPowerReading
		ACCESS			read-only
		STATUS			mandatory
		DESCRIPTION		"0004.0001.0001.0002 This attribute defines the power (in Watts) required by
							the chassis infrastructure, plus the sum of the maximum power requirements
							for all currently powered-on servers."
			::= { drsCMCPowerTableEntry 2 }

	drsIdlePower OBJECT-TYPE
		SYNTAX			DellPowerReading
		ACCESS			read-only
		STATUS			mandatory
		DESCRIPTION		"0004.0001.0001.0003 This attribute defines the power (in Watts) required by 
							the chassis	infrastructure, plus the sum of the minimum power requirements
							for all currently powered-on servers."
			::= { drsCMCPowerTableEntry 3 }

	drsMaxPowerSpecification OBJECT-TYPE
		SYNTAX			DellPowerReading
		ACCESS			read-only
		STATUS			mandatory
		DESCRIPTION		"0004.0001.0001.0004 This attribute defines the power limit (in Watts) 
							at which server throttling will take place."
			::= { drsCMCPowerTableEntry 4 }


	drsPowerSurplus OBJECT-TYPE
		SYNTAX			DellPowerReading
		ACCESS			read-only
		STATUS			mandatory
		DESCRIPTION		"0004.0001.0001.0005 This attribute defines the power surplus (in Watts)
							remaining above the drsPotentialPower reading." 
			::= { drsCMCPowerTableEntry 5 }

	drsKWhCumulative OBJECT-TYPE
		SYNTAX			DellPowerReading
		ACCESS			read-only
		STATUS			mandatory
		DESCRIPTION		"0004.0001.0001.0006 This attribute defines the cumulative chassis power
							usage (in KWh) since last reset." 
			::= { drsCMCPowerTableEntry 6 }

	drsKWhCumulativeTime OBJECT-TYPE
		SYNTAX			DellTimestamp
		ACCESS			read-only
		STATUS			mandatory
		DESCRIPTION		"0004.0001.0001.0007 This attribute defines the timestamp of the most recent
							chassis power accumulator reset." 
			::= { drsCMCPowerTableEntry 7 }

	drsWattsPeakUsage OBJECT-TYPE
		SYNTAX			DellPowerReading
		ACCESS			read-only
		STATUS			mandatory
		DESCRIPTION		"0004.0001.0001.0008 This attribute defines the chassis peak power
							usage (in Watts) since last reset." 
			::= { drsCMCPowerTableEntry 8 }

	drsWattsPeakTime OBJECT-TYPE
		SYNTAX			DellTimestamp
		ACCESS			read-only
		STATUS			mandatory
		DESCRIPTION		"0004.0001.0001.0009 This attribute defines the timestamp of the most recent
							chassis peak power usage." 
			::= { drsCMCPowerTableEntry 9 }

	drsWattsMinUsage OBJECT-TYPE
		SYNTAX			DellPowerReading
		ACCESS			read-only
		STATUS			mandatory
		DESCRIPTION		"0004.0001.0001.0010 This attribute defines the chassis mimimum power
							usage (in Watts) since last reset." 
			::= { drsCMCPowerTableEntry 10 }

	drsWattsMinTime OBJECT-TYPE
		SYNTAX			DellTimestamp
		ACCESS			read-only
		STATUS			mandatory
		DESCRIPTION		"0004.0001.0001.0011 This attribute defines the timestamp of the most recent
							chassis minimum power usage." 
			::= { drsCMCPowerTableEntry 11 }

	drsWattsResetTime OBJECT-TYPE
		SYNTAX			DellTimestamp
		ACCESS			read-only
		STATUS			mandatory
		DESCRIPTION		"0004.0001.0001.0012 This attribute defines the timestamp of the most recent
							reset of the chassis min/peak Watts readings." 
			::= { drsCMCPowerTableEntry 12 }

	drsWattsReading OBJECT-TYPE
		SYNTAX			DellPowerReading
		ACCESS			read-only
		STATUS			mandatory
		DESCRIPTION		"0004.0001.0001.0013 This attribute defines the instantaneous chassis power
							usage (in Watts)." 
			::= { drsCMCPowerTableEntry 13 }

	drsAmpsReading OBJECT-TYPE
		SYNTAX			DellPowerReading
		ACCESS			read-only
		STATUS			mandatory
		DESCRIPTION		"0004.0001.0001.0014 This attribute defines the instantaneous chassis current
							usage (in Watts)." 
			::= { drsCMCPowerTableEntry 14 }

	-------------------------------------------------------------------------------
	-- table: CMC PSU info
	-------------------------------------------------------------------------------

	drsPSUChassisIndex OBJECT-TYPE
		SYNTAX			DellCMCPowerIndexRange
		ACCESS			read-only
		STATUS			mandatory
		DESCRIPTION		"0004.0002.0001.0001 This attribute defines the index
							(one-based) of the associated chassis."
			::= { drsCMCPSUTableEntry 1 }

	drsPSUIndex OBJECT-TYPE
		SYNTAX			DellCMCPSUIndexRange
		ACCESS			read-only
		STATUS			mandatory
		DESCRIPTION		"0004.0002.0001.0002 This attribute defines the index
							(one-based) of the associated CMC PSU."
			::= { drsCMCPSUTableEntry 2 }

	drsPSULocation OBJECT-TYPE
		SYNTAX			DellString
		ACCESS			read-only
		STATUS			mandatory
		DESCRIPTION		"0004.0002.0001.0003 This attribute defines the location
							of the CMC PSU."
			::= { drsCMCPSUTableEntry 3 }

	drsPSUMonitoringCapable OBJECT-TYPE
		SYNTAX			DellCMCPSUCapable
		ACCESS			read-only
		STATUS			mandatory
		DESCRIPTION		"0004.0002.0001.0004 This attribute defines the PSU Monitoring
							capabilities, or the absence of a PSU in this location."
			::= { drsCMCPSUTableEntry 4 }

	drsPSUVoltsReading OBJECT-TYPE
		SYNTAX			DellPowerReading
		ACCESS			read-only
		STATUS			mandatory
		DESCRIPTION		"0004.0002.0001.0005 This attribute defines the instantaneous
							PSU Voltage reading."
			::= { drsCMCPSUTableEntry 5 }

	drsPSUAmpsReading OBJECT-TYPE
		SYNTAX			DellPowerReading
		ACCESS			read-only
		STATUS			mandatory
		DESCRIPTION		"0004.0002.0001.0006 This attribute defines the instantaneous
							PSU Current reading."
			::= { drsCMCPSUTableEntry 6 }

	drsPSUWattsReading OBJECT-TYPE
		SYNTAX			DellPowerReading
		ACCESS			read-only
		STATUS			mandatory
		DESCRIPTION		"0004.0002.0001.0007 This attribute defines the instantaneous
							PSU Wattage reading."
			::= { drsCMCPSUTableEntry 7 }

	-------------------------------------------------------------------------------
	-- group: chassis servers
	-------------------------------------------------------------------------------

	drsCMCServerTable OBJECT-TYPE
		SYNTAX			SEQUENCE OF DrsCMCServerTableEntry
		ACCESS			not-accessible
		STATUS			mandatory
		DESCRIPTION		"0005.0001 This object defines the CMC server table."
			::= { drsChassisServerGroup 1 }

	drsCMCServerTableEntry OBJECT-TYPE
		SYNTAX			DrsCMCServerTableEntry
		ACCESS      	not-accessible
		STATUS      	mandatory
		DESCRIPTION 	"0005.0001.0001 This object defines the CMC server table entry."
		INDEX       	{ drsServerIndex }
			::= { drsCMCServerTable 1 }

	-------------------------------------------------------------------------------
	-- table: CMC Server info
	-------------------------------------------------------------------------------

	drsServerIndex OBJECT-TYPE
		SYNTAX			DellCMCServerIndexRange
		ACCESS			read-only
		STATUS			mandatory
		DESCRIPTION		"0005.0001.0001.0001 This attribute defines the index
							(one-based) of the associated CMC server."
			::= { drsCMCServerTableEntry 1 }

	drsServerMonitoringCapable OBJECT-TYPE
		SYNTAX			DellCMCServerCapable
		ACCESS			read-only
		STATUS			mandatory
		DESCRIPTION		"0005.0001.0001.0002 This attribute defines the server monitoring
							capabilities, or the absence of a server in this location."
			::= { drsCMCServerTableEntry 2 }

	drsServerServiceTag OBJECT-TYPE
		SYNTAX			DellString
		ACCESS			read-only
		STATUS			mandatory
		DESCRIPTION		"0005.0001.0001.0003 This attribute defines the Service Tag
							of the CMC server."
			::= { drsCMCServerTableEntry 3 }

	drsServerSlotName OBJECT-TYPE
		SYNTAX			DellString
		ACCESS			read-only
		STATUS			mandatory
		DESCRIPTION		"0005.0001.0001.0004 This attribute defines the Slot Name
							of the CMC server."
			::= { drsCMCServerTableEntry 4 }

	drsServerSlotNumber OBJECT-TYPE
		SYNTAX			DellString
		ACCESS			read-only
		STATUS			mandatory
		DESCRIPTION		"0005.0001.0001.0005 This attribute defines the Chassis
							Slot Number of the CMC server."
			::= { drsCMCServerTableEntry 5 }

	drsServerNodeID OBJECT-TYPE
		SYNTAX			DellString
		ACCESS			read-only
		STATUS			mandatory
		DESCRIPTION		"0005.0001.0001.0006 This attribute defines the Node ID
							of the CMC server.  The Node ID provides a unique identifier
							for the server."
			::= { drsCMCServerTableEntry 6 }

	drsServerModel OBJECT-TYPE
		SYNTAX			DellString
		ACCESS			read-only
		STATUS			mandatory
		DESCRIPTION		"0005.0001.0001.0007 This attribute defines the Model
							of the CMC server."
			::= { drsCMCServerTableEntry 7 }

	drsServerAssetTag OBJECT-TYPE
		SYNTAX			DellString
		ACCESS			read-only
		STATUS			mandatory
		DESCRIPTION		"0005.0001.0001.0008 This attribute defines the Asset Tag
							of the CMC server."
			::= { drsCMCServerTableEntry 8 }

	drsServerNumStorageControllers OBJECT-TYPE
		SYNTAX			INTEGER
		ACCESS			read-only
		STATUS			mandatory
		DESCRIPTION		"0005.0001.0001.0009 This attribute defines the number of
							storage controllers on the storage sled.  The value
							will be zero if this is not a storage sled."
			::= { drsCMCServerTableEntry 9 }

	drsServerStorageMode OBJECT-TYPE
		SYNTAX			DellCMCServerStorageMode
		ACCESS			read-only
		STATUS			mandatory
		DESCRIPTION		"0005.0001.0001.0010 This attribute defines the Storage
							Mode of the storage sled."
			::= { drsCMCServerTableEntry 10 }

	drsServerIntrusionState OBJECT-TYPE
		SYNTAX			DellCMCServerIntrusionState
		ACCESS			read-only
		STATUS			mandatory
		DESCRIPTION		"0005.0001.0001.0011 This attribute defines the Intrusion
							State of the CMC server if supported by the server."
			::= { drsCMCServerTableEntry 11 }

	drsServerAssignedServerSlots OBJECT-TYPE
		SYNTAX			DellString
		ACCESS			read-only
		STATUS			mandatory
		DESCRIPTION		"0005.0001.0001.0012 This attribute defines the the server
							slots to which a storage sled is assigned.  If this is
							a storage sled that is assigned to one more or more
							server slots, the value will be a comma-separated list
							of one or more server slot names.  If the storage sled
							is not assigned to a server slot, the value will be an
							empty string.  If this is not a storage sled, the value
							will be N/A."
			::= { drsCMCServerTableEntry 12 }

	-------------------------------------------------------------------------------
	-- group: Chassis Alerts 1
	-------------------------------------------------------------------------------

            drsCASubSystem      OBJECT-TYPE
                SYNTAX		  DellString
                ACCESS		  read-only
                STATUS		  mandatory
                DESCRIPTION     "0020.0010.0001 This attribute defines the Sub-System Name of the CMC Alert"
               ::= { drsChassisAlertVariables 1 }

            drsCASSCurrStatus   OBJECT-TYPE
                SYNTAX		  DellStatus
                ACCESS		  read-only
                STATUS		  mandatory
                DESCRIPTION     "0020.0010.0002 This attribute defines the Current Status of the Alerting 
                                 Sub-System"
               ::= { drsChassisAlertVariables 2 }

            drsCASSPrevStatus   OBJECT-TYPE
                SYNTAX		  DellStatus
                ACCESS		  read-only
                STATUS		  mandatory
                DESCRIPTION     "0020.0010.0003 This attribute defines the Previous Status of the Alerting 
                                 Sub-System"
               ::= { drsChassisAlertVariables 3 }

            drsCASSChangeTime   OBJECT-TYPE
                SYNTAX		  TimeTicks
                ACCESS		  read-only
                STATUS		  mandatory
                DESCRIPTION     "0020.0010.0004 This attribute defines the Timestamp of Most Recent Change of 
                                 the Alerting Sub-System"
               ::= { drsChassisAlertVariables 4 }

            drsCAMessage        OBJECT-TYPE
                SYNTAX		  DellString
                ACCESS		  read-only
                STATUS		  mandatory
                DESCRIPTION     "0020.0010.0005 This attribute defines the CSSD message of the CMC Alert"
               ::= { drsChassisAlertVariables 5 }

            alertCMCTestTrap  TRAP-TYPE
                ENTERPRISE 	  drsOutofBandGroup
                DESCRIPTION   "The CMC has generated a test trap"
                --#TYPE "CMC Test Trap"
                --#SUMMARY "CMC Test Trap"
                --#SEVERITY INFORMATIONAL
                --#CATEGORY Error Events
               ::= 2000
              
            alertCMCNormalTrap  TRAP-TYPE
                ENTERPRISE  	  drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a return-to-normal or informational event."
                --#TYPE "CMC Return-to-Normal / Informational Trap"
                --#SUMMARY "Return-to-Normal / Informational Trap from CMC in system %s in location %s, message: %s"
                --#ARGUMENTS {0,1,7}
                --#SEVERITY NORMAL
                --#CATEGORY Error Events
               ::= 2002

            alertCMCWarningTrap TRAP-TYPE
                ENTERPRISE 	    drsOutofBandGroup
                VARIABLES {     drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a warning event."
                --#TYPE "CMC Warning Trap"
                --#SUMMARY "Warning Trap from CMC in system %s in location %s, message: %s"
                --#ARGUMENTS {0,1,7}
                --#SEVERITY WARNING
                --#CATEGORY Error Events
               ::= 2003

            alertCMCCriticalTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a critical event."
                --#TYPE "CMC Critical Trap"
                --#SUMMARY "Critical Trap from CMC in system %s in location %s, message: %s"
                --#ARGUMENTS {0,1,7}
                --#SEVERITY CRITICAL
                --#CATEGORY Error Events
               ::= 2004

            alertCMCNonRecoverableTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a catastrophic event."
                --#TYPE "CMC Non-Recoverable Trap"
                --#SUMMARY "Non-Recoverable Trap from CMC in system %s in location %s, message: %s"
                --#ARGUMENTS {0,1,7}
                --#SEVERITY NON-RECOVERABLE
                --#CATEGORY Error Events
               ::= 2005

	-------------------------------------------------------------------------------
	-- group: Chassis Alerts 2
	-------------------------------------------------------------------------------

    drsCA2MessageID     OBJECT-TYPE
        SYNTAX          DisplayString (SIZE (0..8))
        ACCESS          read-only
        STATUS          mandatory
        DESCRIPTION     "Message ID of the alert."
        ::= { drsChassisAlert2Variables 1 }

    drsCA2Message       OBJECT-TYPE
        SYNTAX          DellString
        ACCESS          read-only
        STATUS          mandatory
        DESCRIPTION     "Message describing the alert."
        ::= { drsChassisAlert2Variables 2 }

    drsCA2MessageArgs   OBJECT-TYPE
        SYNTAX          DellString
        ACCESS          read-only
        STATUS          mandatory
        DESCRIPTION     "Concatenated set of strings representing any message arguments
                         that were used to construct the alert message.  Each message
                         argument string is enclosed in double quotes, and there is a
                         comma after the ending double quote of each message argument
                         string, except the last one.  Any double quotes found within a
                         message argument string were preprocessed and changed to single
                         quotes."
        ::= { drsChassisAlert2Variables 3 }

    drsCA2AlertStatus   OBJECT-TYPE
        SYNTAX          DellStatus
        ACCESS          read-only
        STATUS          mandatory
        DESCRIPTION     "Status of the alert."
        ::= { drsChassisAlert2Variables 4 }

    drsCA2FQDD          OBJECT-TYPE
        SYNTAX          DisplayString (SIZE (0..512))
        ACCESS          read-only
        STATUS          mandatory
        DESCRIPTION     "Fully qualified device descriptor of device causing the alert."
        ::= { drsChassisAlert2Variables 5 }

    ------------------------------------------------------------------------------
    -- Chassis Alerts 2: System: Amperage Probe Traps
    --
    -- Category: System/1
    -- Subcategory: AMP/16
    ------------------------------------------------------------------------------

    alert2AmperageProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor reading is within range."
        --#TYPE       "System: Amperage Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2179

    alert2AmperageProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor has detected a warning value."
        --#TYPE       "System: Amperage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2178

    alert2AmperageProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor has detected a failure value."
        --#TYPE       "System: Amperage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2177
        
    ------------------------------------------------------------------------------
    -- Chassis Alerts 2: System: Battery Traps
    --
    -- Category: System/1
    -- Subcategory: BAT/22
    ------------------------------------------------------------------------------

    alert2BatteryNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery state has returned to normal;
             or battery presence had been detected."
        --#TYPE       "System: Battery Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2227

    alert2BatteryWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery is low."
        --#TYPE       "System: Battery Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2226

    alert2BatteryFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery has failed or battery is absent."
        --#TYPE       "System: Battery Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2225

    ------------------------------------------------------------------------------
    -- Chassis Alerts 2: System: Cable Traps
    --
    -- Category: System/1
    -- Subcategory: CBL/43
    ------------------------------------------------------------------------------

    alert2CableFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Cable failure."
        --#TYPE       "System: Cable Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2393

    ------------------------------------------------------------------------------
    -- Chassis Alerts 2: System: CMC Traps
    --
    -- Category: System/1
    -- Subcategory: CMC/62
    ------------------------------------------------------------------------------

    alert2CMCWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller detected a warning."
        --#TYPE       "System: CMC Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2546

    alert2CMCFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller detected an error."
        --#TYPE       "System: CMC Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2545

    ------------------------------------------------------------------------------
    -- Chassis Alerts 2: System: Fan Traps
    --
    -- Category: System/1
    -- Subcategory: FAN/13
    ------------------------------------------------------------------------------

    alert2FanInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan information."
        --#TYPE       "System: Fan Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2155

    alert2FanWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan warning."
        --#TYPE       "System: Fan Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2154

    alert2FanFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan failure."
        --#TYPE       "System: Fan Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2153

    ------------------------------------------------------------------------------
    -- Chassis Alerts 2: System: Hardware Configuration Traps
    --
    -- Category: System/1
    -- Subcategory: HWC/35
    ------------------------------------------------------------------------------

    alert2HardwareConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration information."
        --#TYPE       "System: Hardware Configuration Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2331

    alert2HardwareConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration warning."
        --#TYPE       "System: Hardware Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2330

    alert2HardwareConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration failure or critical event."
        --#TYPE       "System: Hardware Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2329

    ------------------------------------------------------------------------------
    -- Chassis Alerts 2: System: IO Virtualization Traps
    --
    -- Category: System/1
    -- Subcategory: IOV/63
    ------------------------------------------------------------------------------

    alert2IOVirtualizationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization information."
        --#TYPE       "System: IO Virtualization Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2555

    alert2IOVirtualizationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization warning."
        --#TYPE       "System: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2554

    alert2IOVirtualizationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization failure or critical event."
        --#TYPE       "System: IO Virtualization Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2553

    ------------------------------------------------------------------------------
    -- Chassis Alerts 2: System: Link Status Traps
    --
    -- Category: System/1
    -- Subcategory: LNK/25
    ------------------------------------------------------------------------------

    alert2LinkStatusInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status information."
        --#TYPE       "System: Link Status Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2251

    alert2LinkStatusWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status warning."
        --#TYPE       "System: Link Status Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2250

    alert2LinkStatusFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status failure or critical event."
        --#TYPE       "System: Link Status Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2249

    ------------------------------------------------------------------------------
    -- Chassis Alerts 2: System: PCI Device Traps
    --
    -- Category: System/1
    -- Subcategory: PCI/46
    ------------------------------------------------------------------------------

    alert2PCIDeviceInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device information."
        --#TYPE       "System: PCI Device Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2419

    alert2PCIDeviceWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device warning."
        --#TYPE       "System: PCI Device Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2418

    alert2PCIDeviceFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device failure or critical event."
        --#TYPE       "System: PCI Device Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2417

    ------------------------------------------------------------------------------
    -- Chassis Alerts 2: System: Power Supply Traps
    --
    -- Category: System/1
    -- Subcategory: PSU/17
    ------------------------------------------------------------------------------

    alert2PowerSupplyNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has returned to normal."
        --#TYPE       "System: Power Supply Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2187

    alert2PowerSupplyWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has detected a warning."
        --#TYPE       "System: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2186

    alert2PowerSupplyFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has detected a failure."
        --#TYPE       "System: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2185

    ------------------------------------------------------------------------------
    -- Chassis Alerts 2: System: Power Supply Absent Traps
    --
    -- Category: System/1
    -- Subcategory: PSUA/52
    ------------------------------------------------------------------------------

    alert2PowerSupplyAbsent TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply is absent."
        --#TYPE       "System: Power Supply Absent"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2465

    ------------------------------------------------------------------------------
    -- Chassis Alerts 2: System: Power Usage Traps
    --
    -- Category: System/1
    -- Subcategory: PWR/28
    ------------------------------------------------------------------------------

    alert2PowerUsageInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage information."
        --#TYPE       "System: Power Usage Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2275

    alert2PowerUsageWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage warning."
        --#TYPE       "System: Power Usage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2274

    alert2PowerUsageFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage failure."
        --#TYPE       "System: Power Usage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2273

    ------------------------------------------------------------------------------
    -- Chassis Alerts 2: System: Redundancy Traps
    --
    -- Category: System/1
    -- Subcategory: RDU/53
    ------------------------------------------------------------------------------

    alert2RedundancyInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy information."
        --#TYPE       "System: Redundancy Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2475

    alert2RedundancyDegraded TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy is degraded."
        --#TYPE       "System: Redundancy Degraded"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2474

    alert2RedundancyLost TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy is lost."
        --#TYPE       "System: Redundancy Lost"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2473

    ------------------------------------------------------------------------------
    -- Chassis Alerts 2: System: Security Event Traps
    --
    -- Category: System/1
    -- Subcategory: SEC/42
    ------------------------------------------------------------------------------

    alert2SecurityInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security information."
        --#TYPE       "System: Security Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2387

    alert2SecurityWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security warning."
        --#TYPE       "System: Security Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2386

    alert2SecurityFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security failure or critical event."
        --#TYPE       "System: Security Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 2385

    ------------------------------------------------------------------------------
    -- Chassis Alerts 2: System: System Event Log Traps
    --
    -- Category: System/1
    -- Subcategory: SEL/41
    ------------------------------------------------------------------------------

    alert2SystemEventLogInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log information."
        --#TYPE       "System: System Event Log Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2379

    alert2SystemEventLogWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log warning."
        --#TYPE       "System: System Event Log Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2378

    alert2SystemEventLogFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log failure or critical event."
        --#TYPE       "System: System Event Log Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 2377

    ------------------------------------------------------------------------------
    -- Chassis Alerts 2: System: Software Configuration Traps
    --
    -- Category: System/1
    -- Subcategory: SWC/36
    ------------------------------------------------------------------------------

    alert2SoftwareConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration information."
        --#TYPE       "System: Software Configuration Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2339

    alert2SoftwareConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration warning."
        --#TYPE       "System: Software Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2338

    alert2SoftwareConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration failure."
        --#TYPE       "System: Software Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2337

    ------------------------------------------------------------------------------
    -- Chassis Alerts 2: System: Temperature Probe Traps
    --
    -- Category: System/1
    -- Subcategory: TMP/14
    ------------------------------------------------------------------------------

    alert2TemperatureProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor value is within range."
        --#TYPE       "System: Temperature Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2163

    alert2TemperatureProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor has detected a warning value."
        --#TYPE       "System: Temperature Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2162

    alert2TemperatureProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor has detected a failure value."
        --#TYPE       "System: Temperature Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2161

    ------------------------------------------------------------------------------
    -- Chassis Alerts 2: System: Voltage Probe Traps
    --
    -- Category: System/1
    -- Subcategory: VLT/15
    ------------------------------------------------------------------------------

    alert2VoltageProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor reading is within range."
        --#TYPE       "System: Voltage Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2171

    alert2VoltageProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor has detected a warning value."
        --#TYPE       "System: Voltage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2170

    alert2VoltageProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor has detected a failure value."
        --#TYPE       "System: Voltage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2169

    -------------------------------------------------------------------------------
    -- Chassis Alerts 2: Storage: Battery Traps
    --
    -- Category: Storage/2
    -- Subcategory: BAT/22
    -------------------------------------------------------------------------------

    alert2StorageBatteryInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Battery information."
        --#TYPE       "Storage: Battery Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4275

    alert2StorageBatteryWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Battery warning."
        --#TYPE       "Storage: Battery Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4274

    alert2StorageBatteryFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Battery failure."
        --#TYPE       "Storage: Battery Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4273

    ------------------------------------------------------------------------------
    -- Chassis Alerts 2: Storage: Controller Traps
    --
    -- Category: Storage/2
    -- Subcategory: CTL/29
    ------------------------------------------------------------------------------

    alert2StorageControllerInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller information."
        --#TYPE       "Storage: Controller Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4331

    alert2StorageControllerWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller warning."
        --#TYPE       "Storage: Controller Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4330

    alert2StorageControllerFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller failure."
        --#TYPE       "Storage: Controller Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4329

    ------------------------------------------------------------------------------
    -- Chassis Alerts 2: Storage: Enclosure Traps
    --
    -- Category: Storage/2
    -- Subcategory: ENC/30
    ------------------------------------------------------------------------------

    alert2StorageEnclosureInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure information."
        --#TYPE       "Storage: Enclosure Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4339

    alert2StorageEnclosureWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure warning."
        --#TYPE       "Storage: Enclosure Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4338

    alert2StorageEnclosureFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure failure."
        --#TYPE       "Storage: Enclosure Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4337

    ------------------------------------------------------------------------------
    -- Chassis Alerts 2: Storage: Fan Traps
    --
    -- Category: Storage/2
    -- Subcategory: FAN/13
    ------------------------------------------------------------------------------

    alert2StorageFanInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan information."
        --#TYPE       "Storage: Fan Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4203

    alert2StorageFanWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan warning."
        --#TYPE       "Storage: Fan Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 4202

    alert2StorageFanFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan failure."
        --#TYPE       "Storage: Fan Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4201

    ------------------------------------------------------------------------------
    -- Chassis Alerts 2: Storage: Physical Disk Traps
    --
    -- Category: Storage/2
    -- Subcategory: PDR/31
    ------------------------------------------------------------------------------

    alert2StoragePhysicalDiskInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk information."
        --#TYPE       "Storage: Physical Disk Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4347

    alert2StoragePhysicalDiskWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk warning."
        --#TYPE       "Storage: Physical Disk Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4346

    alert2StoragePhysicalDiskFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk failure."
        --#TYPE       "Storage: Physical Disk Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4345

    ------------------------------------------------------------------------------
    -- Chassis Alerts 2: Storage: Power Supply Traps
    --
    -- Category: Storage/2
    -- Subcategory: PSU/17
    ------------------------------------------------------------------------------

    alert2StoragePowerSupplyInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply information."
        --#TYPE       "Storage: Power Supply Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4235

    alert2StoragePowerSupplyWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply warning."
        --#TYPE       "Storage: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4234

    alert2StoragePowerSupplyFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply failure."
        --#TYPE       "Storage: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4233

    ------------------------------------------------------------------------------
    -- Chassis Alerts 2: Storage: Security Event Traps
    --
    -- Category: Storage/2
    -- Subcategory: SEC/42
    ------------------------------------------------------------------------------

    alert2StorageSecurityInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security information."
        --#TYPE       "Storage: Security Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 4435

    alert2StorageSecurityWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security warning."
        --#TYPE       "Storage: Security Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 4434

    alert2StorageSecurityFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security failure or critical event."
        --#TYPE       "Storage: Security Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4433

    ------------------------------------------------------------------------------
    -- Chassis Alerts 2: Storage: Storage Management Status Traps
    --
    -- Category: Storage/2
    -- Subcategory: STOR/10
    ------------------------------------------------------------------------------

    alert2StorageManagementInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management information.
            There is no global status change associated with this trap."
        --#TYPE       "Storage: Storage Management Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4179

    alert2StorageManagementWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management has detected a device independent warning
            condition. There is no global status change associated with this
            trap."
        --#TYPE       "Storage: Storage Management Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4178

    alert2StorageManagementFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management has detected a device independent error condition.
            There is no global status change associated with this trap."
        --#TYPE       "Storage: Storage Management Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4177

    ------------------------------------------------------------------------------
    -- Chassis Alerts 2: Storage: Temperature Probe Traps
    --
    -- Category: Storage/2
    -- Subcategory: TMP/14
    ------------------------------------------------------------------------------

    alert2StorageTemperatureProbeInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe information."
        --#TYPE       "Storage: Temperature Probe Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4211

    alert2StorageTemperatureProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe warning."
        --#TYPE       "Storage: Temperature Probe Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4210

    alert2StorageTemperatureProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe failure."
        --#TYPE       "Storage: Temperature Probe Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4209

    ------------------------------------------------------------------------------
    -- Chassis Alerts 2: Storage: Virtual Disk Traps
    --
    -- Category: Storage/2
    -- Subcategory: VDR/32
    ------------------------------------------------------------------------------

    alert2StorageVirtualDiskInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk information."
        --#TYPE       "Storage: Virtual Disk Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4355

    alert2StorageVirtualDiskWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk warning."
        --#TYPE       "Storage: Virtual Disk Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4354

    alert2StorageVirtualDiskFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk failure."
        --#TYPE       "Storage: Virtual Disk Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4353

    ------------------------------------------------------------------------------
    -- Chassis Alerts 2: Updates: Software Change Traps
    --
    -- Category: Updates/3
    -- Subcategory: SWU/21
    ------------------------------------------------------------------------------

    alert2SoftwareChangeUpdateWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software change update warning."
        --#TYPE       "Updates: Software Change Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 6314

    ------------------------------------------------------------------------------
    -- Chassis Alerts 2: Audit: CMC Traps
    --
    -- Category: Audit/4
    -- Subcategory: CMC/62
    ------------------------------------------------------------------------------

    alert2CMCAuditInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit information."
        --#TYPE       "Audit: CMC Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8691

    alert2CMCAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit warning."
        --#TYPE       "Audit: CMC Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8690

    alert2CMCAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit failure or critical event."
        --#TYPE       "Audit: CMC Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8689

    ------------------------------------------------------------------------------
    -- Chassis Alerts 2: Audit: IO Virtualization Traps
    --
    -- Category: Audit/4
    -- Subcategory: IOV/63
    ------------------------------------------------------------------------------

    alert2IOVirtualizationAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization audit warning."
        --#TYPE       "Audit: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8698

    ------------------------------------------------------------------------------
    -- Chassis Alerts 2: Audit: License Traps
    --
    -- Category: Audit/4
    -- Subcategory: LIC/40
    ------------------------------------------------------------------------------

    alert2LicenseInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License information."
        --#TYPE       "Audit: License Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8515

    alert2LicenseWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License warning."
        --#TYPE       "Audit: License Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8514

    alert2LicenseFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License failure."
        --#TYPE       "Audit: License Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8513

    ------------------------------------------------------------------------------
    -- Chassis Alerts 2: Audit: PCI Device Traps
    --
    -- Category: Audit/4
    -- Subcategory: PCI/46
    ------------------------------------------------------------------------------

    alert2PCIDeviceAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device audit warning."
        --#TYPE       "Audit: PCI Device Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8562

    ------------------------------------------------------------------------------
    -- Chassis Alerts 2: Audit: Power Supply Traps
    --
    -- Category: Audit/4
    -- Subcategory: PSU/17
    ------------------------------------------------------------------------------

    alert2PowerSupplyAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power Supply audit warning."
        --#TYPE       "Audit: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8330

    alert2PowerSupplyAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power Supply audit failure or critical event."
        --#TYPE       "Audit: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8329

    ------------------------------------------------------------------------------
    -- Chassis Alerts 2: Audit: Power Usage Traps
    --
    -- Category: Audit/4
    -- Subcategory: PWR/28
    ------------------------------------------------------------------------------

    alert2PowerUsageAuditInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit information."
        --#TYPE       "Audit: Power Usage Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8419

    alert2PowerUsageAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit warning."
        --#TYPE       "Audit: Power Usage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8418

    alert2PowerUsageAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit failure or critical event."
        --#TYPE       "Audit: Power Usage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8417

    ------------------------------------------------------------------------------
    -- Chassis Alerts 2: Audit: Software Change Traps
    --
    -- Category: Audit/4
    -- Subcategory: SWU/21
    ------------------------------------------------------------------------------

    alert2SoftwareChangeAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software change audit failure or critical event."
        --#TYPE       "Audit: Software Change Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8361

    ------------------------------------------------------------------------------
    -- Chassis Alerts 2: Configuration: IO Virtualization Traps
    --
    -- Category: Configuration/5
    -- Subcategory: IOV/63
    ------------------------------------------------------------------------------

    alert2IOVConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization configuration information."
        --#TYPE       "Configuration: IO Virtualization Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 10747

    alert2IOVConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization configuration warning."
        --#TYPE       "Configuration: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 10746

    ------------------------------------------------------------------------------
    -- Chassis Alerts 2: Configuration: PCI Device Traps
    --
    -- Category: Configuration/5
    -- Subcategory: PCI/46
    ------------------------------------------------------------------------------

    alert2PCIDeviceConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device configuration information."
        --#TYPE       "Configuration: PCI Device Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 10611

    ------------------------------------------------------------------------------
    -- Chassis Alerts 2: Configuration: Software Configuration Traps
    --
    -- Category: Configuration/5
    -- Subcategory: SWC/36
    ------------------------------------------------------------------------------

    alert2SWCConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration warning."
        --#TYPE       "Configuration: Software Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 10530

    alert2SWCConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration failure."
        --#TYPE       "Configuration: Software Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 10529

    ------------------------------------------------------------------------------
    -- Chassis Alerts 2: Configuration: Test Traps
    --
    -- Category: Configuration/5
    -- Subcategory: TST/19
    ------------------------------------------------------------------------------

    alert2CMCTestTrap TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Test trap generated by CMC in response to a user request."
        --#TYPE       "Configuration: CMC Test Trap"
        --#SEVERITY   INFORMATIONAL
        --#SUMMARY    "%s"
        --#ARGUMENTS  {1}
        --#CATEGORY   "Status Events"
        --#STATE      OPERATIONAL
        --#STATUS     MANDATORY
        ::= 10395

	-------------------------------------------------------------------------------
    -- group: Legacy Alerts
	-------------------------------------------------------------------------------

        drsAlertSystem         OBJECT-TYPE
            SYNTAX             OCTET STRING (SIZE (0..255))
            ACCESS             read-only
            STATUS             mandatory
            DESCRIPTION
            "5000.0010.0001 Name of the system generating the alert."
            --DEFAULT get-function-async    get_%n_async
            --DEFAULT next-function-async   std_next_async
            ::= { drsAlertVariables 1 }

        drsAlertTableIndexOID  OBJECT-TYPE
            SYNTAX             OBJECT IDENTIFIER
            ACCESS             read-only
            STATUS             mandatory
            DESCRIPTION
            "5000.0010.0002 0.0"
            --DEFAULT get-function-async    get_OID_null_async
            --DEFAULT next-function-async   std_next_async
            ::= { drsAlertVariables 2 }

        drsAlertMessage        OBJECT-TYPE
            SYNTAX             OCTET STRING (SIZE (0..1024))
            ACCESS             read-only
            STATUS             mandatory
            DESCRIPTION
            "5000.0010.0003 Message describing the alert."
            --DEFAULT get-function-async    get_string_null_async
            --DEFAULT next-function-async   std_next_async
            ::= { drsAlertVariables 3 }

        drsAlertCurrentStatus  OBJECT-TYPE
            SYNTAX             DellStatus
            ACCESS             read-only
            STATUS             mandatory
            DESCRIPTION
            "5000.0010.0004 Current status of object causing the alert."
            --DEFAULT get-function-async    get_dellstatus_unknow_async
            --DEFAULT next-function-async   std_next_async
            ::= { drsAlertVariables 4 }

        drsAlertPreviousStatus OBJECT-TYPE
            SYNTAX             DellStatus
            ACCESS             read-only
            STATUS             mandatory
            DESCRIPTION
            "5000.0010.0005 Previous status of object causing the alert."
            --DEFAULT get-function-async    get_dellstatus_unknow_async
            --DEFAULT next-function-async   std_next_async
            ::= { drsAlertVariables 5 }

        drsAlertData           OBJECT-TYPE
            SYNTAX             OCTET STRING (SIZE (0..1024))
            ACCESS             read-only
            STATUS             mandatory
            DESCRIPTION
            "5000.0010.0006 Alert data."
            --DEFAULT get-function-async    get_string_null_async
            --DEFAULT next-function-async   std_next_async
            ::= { drsAlertVariables 6 }

        alertDrscTestTrapEvent      TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC generated a test trap event in response to a user request."
        --#TYPE "Dell RAC Test TRAP Event"
        --#SUMMARY "%s"
        --#ARGUMENTS {2}
        --#SEVERITY INFORMATIONAL
        --#CATEGORY Status Events
        ::= 1001
    
        alertDrscAuthError          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Authentication Failures during a time period have Exceeded a Threshold."
        --#TYPE "Dell RAC Authentication Error"
        --#SUMMARY "%s"
        --#ARGUMENTS {2}
        --#SEVERITY MINOR
        --#CATEGORY Error Events
        ::= 1002

        alertDrscLostESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC cannot communicate with the baseboard management controller (ESM)."
        --#TYPE "Dell RAC Lost Communication with ESM"
        --#SUMMARY "%s"
        --#ARGUMENTS {2}
        --#SEVERITY MINOR
        --#CATEGORY Error Events
        ::= 1003

        alertDrscFoundESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC is communicating normally with the baseboard management controller (ESM)."
        --#TYPE "Dell RAC Communication with ESM is OK"
        --#SUMMARY "%s"
        --#ARGUMENTS {2}
        --#SEVERITY INFORMATIONAL
        --#CATEGORY Error Events
        ::= 1004

        alertDrscPowerOff          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a System power state change to powered-off."
        --#TYPE "Dell RAC Detected System Powered-Off"
        --#SUMMARY "%s"
        --#ARGUMENTS {2}
        --#SEVERITY CRITICAL
        --#CATEGORY Error Events
        ::= 1005

        alertDrscPowerOn          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a system power state change to powered-on."
        --#TYPE "Dell RAC Detected System Powered-On"
        --#SUMMARY "%s"
        --#ARGUMENTS {2}
        --#SEVERITY INFORMATIONAL
        --#CATEGORY Error Events
        ::= 1006

        alertDrscWatchdogExpired          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the system watchdog has expired indicating a system hang."
        --#TYPE "Dell RAC Detected Watchdog Expired"
        --#SUMMARY "%s"
        --#ARGUMENTS {2}
        --#SEVERITY CRITICAL
        --#CATEGORY Error Events
        ::= 1007

        alertDrscBattLow          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Battery charge is below 25% indicating that the battery may only be able to power the DRSC for 8-10 minutes."
        --#TYPE "Dell RAC Battery Charge Low"
        --#SUMMARY "%s"
        --#ARGUMENTS {2}
        --#SEVERITY MINOR
        --#CATEGORY Error Events
        ::= 1008

        alertDrscTempNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has retured to a normal value."
        --#TYPE "Dell RAC Temperature Normal"
        --#SUMMARY "%s"
        --#ARGUMENTS {2}
        --#SEVERITY INFORMATIONAL
        --#CATEGORY Error Events
        ::= 1009

        alertDrscTempWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a Warning value."
        --#TYPE "Dell RAC Temperature Warning"
        --#SUMMARY "%s"
        --#ARGUMENTS {2}
        --#SEVERITY MINOR
        --#CATEGORY Error Events
        ::= 1010

        alertDrscTempCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a failure (or critical) value."
        --#TYPE "Dell RAC Temperature Failure"
        --#SUMMARY "%s"
        --#ARGUMENTS {2}
        --#SEVERITY CRITICAL
        --#CATEGORY Error Events
        ::= 1011

        alertDrscVoltNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage has returned to a normal value."
        --#TYPE "Dell RAC Voltage Normal"
        --#SUMMARY "%s"
        --#ARGUMENTS {2}
        --#SEVERITY INFORMATIONAL
        --#CATEGORY Error Events
        ::= 1012

        alertDrscVoltWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a warning value."
        --#TYPE "Dell RAC Battery Warning"
        --#SUMMARY "%s"
        --#ARGUMENTS {2}
        --#SEVERITY MINOR
        --#CATEGORY Error Events
        ::= 1013

        alertDrscVoltCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a failure (or critical) value."
        --#TYPE "Dell RAC Voltage Failure"
        --#SUMMARY "%s"
        --#ARGUMENTS {2}
        --#SEVERITY CRITICAL
        --#CATEGORY Error Events
        ::= 1014

        alertDrscSELWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Warning."
        --#TYPE "Dell RAC System Event Log Warning"
        --#SUMMARY "%s"
        --#ARGUMENTS {2}
        --#SEVERITY MAJOR
        --#CATEGORY Error Events
        ::= 1015

        alertDrscSELCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Critical."
        --#TYPE "Dell RAC System Event Log Critical"
        --#SUMMARY "%s"
        --#ARGUMENTS {2}
        --#SEVERITY CRITICAL
        --#CATEGORY Error Events
        ::= 1016

        alertDrscSEL80percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 80% full."
        --#TYPE "Dell System Event Log 80% Full Warning"
        --#SUMMARY "%s"
        --#ARGUMENTS {2}
        --#SEVERITY MAJOR
        --#CATEGORY Status Events
        ::= 1017

        alertDrscSEL90percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 90% full."
        --#TYPE " Dell System Event Log 90% Full Warning "
        --#SUMMARY "%s"
        --#ARGUMENTS {2}
        --#SEVERITY MAJOR
        --#CATEGORY Status Events
        ::= 1018

        alertDrscSEL100percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 100% full."
        --#TYPE " Dell System Event Log 100% Full Warning "
        --#SUMMARY "%s"
        --#ARGUMENTS {2}
        --#SEVERITY MAJOR
        --#CATEGORY Status Events
        ::= 1019

        alertDrscSELNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Normal."
        --#TYPE "Dell RAC System Event Log Normal"
        --#SUMMARY "%s"
        --#ARGUMENTS {2}
        --#SEVERITY INFORMATIONAL
        --#CATEGORY Error Events
        ::= 1020
END
