-- COPYRIGHT NOTICE
-- Copyright (c) Radware Ltd. 2009
-- All rights reserved

ALTEON-CHEETAH-NETWORK-MIB DEFINITIONS ::= BEGIN

IMPORTS
    MODULE-IDENTITY, OBJECT-TYPE, Integer32, Counter32, Gauge32, Counter64,
    IpAddress, Unsigned32
        FROM SNMPv2-SMI
    DisplayString, PhysAddress
        FROM SNMPv2-TC
    aws-switch 
        FROM ALTEON-ROOT-MIB;

layer3 MODULE-IDENTITY
    LAST-UPDATED "200908050000Z"     -- 5 August, 2009
    ORGANIZATION "Radware Ltd."
    CONTACT-INFO "Lobby 1 (Visitors) and Lobby 2 (Deliveries)
                  575 Corporate Drive
                  Mahwah, NJ 07430
  	     	  support@radware.com"
    DESCRIPTION
        "The MIB module for the Alteon OS Layer 3 configuration, statistics
         and information ."
    REVISION "200908050000Z"     -- 5 August, 2009
    DESCRIPTION
        "Added revision clause for SMIv2 compliance."
    ::= { aws-switch 3 }
layer3Configs     OBJECT IDENTIFIER ::= { layer3 1 }
layer3Stats       OBJECT IDENTIFIER ::= { layer3 2 }
layer3Info        OBJECT IDENTIFIER ::= { layer3 3 }
layer3Oper        OBJECT IDENTIFIER ::= { layer3 4 }

ipInterfaceCfg	    OBJECT IDENTIFIER ::= { layer3Configs 1 }
ipGatewayCfg	    OBJECT IDENTIFIER ::= { layer3Configs 2 }
ipStaticRouteCfg    OBJECT IDENTIFIER ::= { layer3Configs 3 }
ipForwardCfg	    OBJECT IDENTIFIER ::= { layer3Configs 4 }
ripCfg              OBJECT IDENTIFIER ::= { layer3Configs 5 }
vrrpCfg		    OBJECT IDENTIFIER ::= { layer3Configs 6 }
arpCfg		    OBJECT IDENTIFIER ::= { layer3Configs 7 }
ipBootpCfg	    OBJECT IDENTIFIER ::= { layer3Configs 8 }
dnsCfg  	    OBJECT IDENTIFIER ::= { layer3Configs 9 }
ipNwfCfg	    OBJECT IDENTIFIER ::= { layer3Configs 10 }
ipRmapCfg	    OBJECT IDENTIFIER ::= { layer3Configs 11 }
bgpCfg		    OBJECT IDENTIFIER ::= { layer3Configs 12 }
ospfCfg		    OBJECT IDENTIFIER ::= { layer3Configs 13 }
ipGeneralCfg	    OBJECT IDENTIFIER ::= { layer3Configs 14 }
ipStaticArpCfg      OBJECT IDENTIFIER ::= { layer3Configs 15 }
rip2Cfg		    OBJECT IDENTIFIER ::= { layer3Configs 18 }
ospfv3Cfg           OBJECT IDENTIFIER ::= { layer3Configs 20 }
haCfg               OBJECT IDENTIFIER ::= { layer3Configs 21 }
ipv6StaticNbrCfg    OBJECT IDENTIFIER ::= { layer3Configs 22 }
bfdCfg               OBJECT IDENTIFIER ::= { layer3Configs 23 }
ipTunnelCfg               OBJECT IDENTIFIER ::= { layer3Configs 24 }

ripStats            OBJECT IDENTIFIER ::= { layer3Stats 1 }
arpStats  	  OBJECT IDENTIFIER ::= { layer3Stats 2 }
routeStats  	  OBJECT IDENTIFIER ::= { layer3Stats 3 }
dnsStats  	  OBJECT IDENTIFIER ::= { layer3Stats 4 }
vrrpStats         OBJECT IDENTIFIER ::= { layer3Stats 5 }
ospfStats	  OBJECT IDENTIFIER ::= { layer3Stats 6 }
clearStats	  OBJECT IDENTIFIER ::= { layer3Stats 7 }
ip6Stats          OBJECT IDENTIFIER ::= { layer3Stats 10}
icmp6Stats        OBJECT IDENTIFIER ::= { layer3Stats 11}
ip6gwStats        OBJECT IDENTIFIER ::= { layer3Stats 12}
rip2Stats  	  OBJECT IDENTIFIER ::= { layer3Stats 13 }
tcpStats  	  OBJECT IDENTIFIER ::= { layer3Stats 14 }
ospfv3Stats       OBJECT IDENTIFIER ::= { layer3Stats 15 }
vrrp6Stats        OBJECT IDENTIFIER ::= { layer3Stats 16 }
ipTunnelStats     OBJECT IDENTIFIER ::= { layer3Stats 17 }

ipRoutingInfo	  OBJECT IDENTIFIER ::= { layer3Info 1 }
arpInfo		  OBJECT IDENTIFIER ::= { layer3Info 2 }
vrrpInfo	  OBJECT IDENTIFIER ::= { layer3Info 3 }
ospfinfo	  OBJECT IDENTIFIER ::= { layer3Info 4 }

ospfv3info    OBJECT IDENTIFIER ::= { layer3Info 13 }

haInfo     OBJECT IDENTIFIER ::= { layer3Info 14 }

gatewayInfo	  OBJECT IDENTIFIER ::= { layer3Info 5 }
nbrcacheInfo      OBJECT IDENTIFIER ::= { layer3Info 7 }
ipRoute6Info      OBJECT IDENTIFIER ::= { layer3Info 8 }
ipIntfInfo        OBJECT IDENTIFIER ::= { layer3Info 9 }
rip2Info          OBJECT IDENTIFIER ::= { layer3Info 10 }

rip2RoutesInfo    OBJECT IDENTIFIER ::= { layer3Info 11 }
allowedNwInfo     OBJECT IDENTIFIER ::= { layer3Info 12 }
vrrpOper          OBJECT IDENTIFIER ::= { layer3Oper 1 }

ipOper            OBJECT IDENTIFIER ::= { layer3Oper 2 }

haOper            OBJECT IDENTIFIER ::= { layer3Oper 3 }

-- IP Configuration

ipInterfaceTableMax OBJECT-TYPE
    SYNTAX  Integer32
    MAX-ACCESS  read-only
    STATUS  current
    DESCRIPTION
        "The maximum number of rows in the IP interface table.
         Note:This mib is not supported for VX instance of Virtualization."
    ::= { ipInterfaceCfg 1 }

ipCurCfgIntfTable OBJECT-TYPE
    SYNTAX  SEQUENCE OF IpCurCfgIntfEntry
    MAX-ACCESS  not-accessible
    STATUS  current
    DESCRIPTION
        "The table of IP interface configuration.
         Note:This mib is not supported for VX instance of Virtualization."
    ::= { ipInterfaceCfg 2 }

ipCurCfgIntfEntry OBJECT-TYPE
    SYNTAX  IpCurCfgIntfEntry
    MAX-ACCESS  not-accessible
    STATUS  current
    DESCRIPTION
        "A row in the Ip interface table,
         Note:This mib is not supported for VX instance of Virtualization."
    INDEX   { ipCurCfgIntfIndex }
    ::= { ipCurCfgIntfTable 1 }

IpCurCfgIntfEntry ::= SEQUENCE {
    ipCurCfgIntfIndex         Integer32,
    ipCurCfgIntfAddr          IpAddress,
    ipCurCfgIntfMask          IpAddress,
    ipCurCfgIntfBroadcast     IpAddress,
    ipCurCfgIntfState         INTEGER,
    ipCurCfgIntfBootpRelay    INTEGER,
    ipCurCfgIntfIpVer         INTEGER,
    ipCurCfgIntfIpv6Addr      DisplayString,
    ipCurCfgIntfPrefixLen     INTEGER,
    ipCurCfgIntfRouteAdv      INTEGER,
    ipCurCfgIntfVlan          Integer32,
    ipCurCfgIntfPeer	      DisplayString,
    ipCurCfgIntfDescription   DisplayString,
    ipCurCfgIntfBfd           INTEGER
    }

ipCurCfgIntfIndex OBJECT-TYPE
    SYNTAX  Integer32
    MAX-ACCESS  read-only
    STATUS  current
    DESCRIPTION
        "The interface number for which the IP information is related."
    ::= { ipCurCfgIntfEntry 1}

ipCurCfgIntfAddr OBJECT-TYPE
    SYNTAX  IpAddress
    MAX-ACCESS  read-only
    STATUS  current
    DESCRIPTION
        "The IP address of the interface."
    ::= { ipCurCfgIntfEntry 2 }

ipCurCfgIntfMask OBJECT-TYPE
    SYNTAX  IpAddress
    MAX-ACCESS  read-only
    STATUS  current  
    DESCRIPTION
        "The subnet mask of the interface."
    ::= { ipCurCfgIntfEntry 3 }

ipCurCfgIntfBroadcast OBJECT-TYPE
    SYNTAX  IpAddress
    MAX-ACCESS  read-only
    STATUS  obsolete  
    DESCRIPTION
        "The broadcast address of the interface."
    ::= { ipCurCfgIntfEntry 4 }

ipCurCfgIntfVlan OBJECT-TYPE
    SYNTAX  Integer32
    MAX-ACCESS  read-only
    STATUS  current  
    DESCRIPTION
        "The VLAN associated with the interface."
    ::= { ipCurCfgIntfEntry 5 }

ipCurCfgIntfState OBJECT-TYPE
    SYNTAX  INTEGER { 
	enabled(2),
	disabled(3),
        unsupported(2147483647)
	}
    MAX-ACCESS  read-only
    STATUS  current  
    DESCRIPTION
        "The state of the interface."
    ::= { ipCurCfgIntfEntry 6 }

ipCurCfgIntfBootpRelay OBJECT-TYPE
    SYNTAX  INTEGER { 
	enabled(1),
	disabled(2),
        unsupported(2147483647)
	}
    MAX-ACCESS  read-only
    STATUS  current  
    DESCRIPTION
        "Enable/disable BOOTP relay."
    ::= { ipCurCfgIntfEntry 7 }


ipCurCfgIntfIpVer OBJECT-TYPE
    SYNTAX  INTEGER{
        ipv4(1),
        ipv6(2),
        unsupported(2147483647)
        }
    MAX-ACCESS  read-only
    STATUS  current
    DESCRIPTION
        "The type of IP address."
    ::= { ipCurCfgIntfEntry 9 }

ipCurCfgIntfIpv6Addr OBJECT-TYPE
    SYNTAX   DisplayString (SIZE(0..40))
    MAX-ACCESS  read-only
    STATUS  current
    DESCRIPTION
        "The IPv6 address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { ipCurCfgIntfEntry 10 }

ipCurCfgIntfPrefixLen OBJECT-TYPE
    SYNTAX  INTEGER(1..128) 
    MAX-ACCESS  read-only
    STATUS  current
    DESCRIPTION
        "The prefix length associated with this IP address ."
    ::= { ipCurCfgIntfEntry 11 }

ipCurCfgIntfRouteAdv  OBJECT-TYPE
    SYNTAX  INTEGER {
        enabled(1),
        disabled(2),
        unsupported(2147483647)
        }
    MAX-ACCESS  read-only
    STATUS  current
    DESCRIPTION
        "Enable/disable route advertisement of the interface."
    ::= { ipCurCfgIntfEntry 12 }


ipCurCfgIntfPeer  OBJECT-TYPE
    SYNTAX   DisplayString (SIZE(0..40))
    MAX-ACCESS  read-only
    STATUS  current
    DESCRIPTION
        "The Peer IP of the interface."
    ::= { ipCurCfgIntfEntry 13 }

ipCurCfgIntfDescription OBJECT-TYPE
    SYNTAX   DisplayString (SIZE(0..50))
    MAX-ACCESS  read-only
    STATUS  current
    DESCRIPTION
        "The Description of the interface."
    ::= { ipCurCfgIntfEntry 14 }

ipCurCfgIntfBfd OBJECT-TYPE
    SYNTAX INTEGER {
        on(1),
        off(2),
        unsupported(2147483647)
        }
    MAX-ACCESS  read-only
    STATUS  current
    DESCRIPTION
        "Current BFD on/off configuration on the interface."
    ::= { ipCurCfgIntfEntry 15 }

ipNewCfgIntfTable OBJECT-TYPE
    SYNTAX  SEQUENCE OF IpNewCfgIntfEntry
    MAX-ACCESS  not-accessible
    STATUS  current
    DESCRIPTION
        "The table of interface configuration in the New Configuration Block.
         Note:This mib is not supported for VX instance of Virtualization."
    ::= { ipInterfaceCfg 3 }

ipNewCfgIntfEntry OBJECT-TYPE
    SYNTAX  IpNewCfgIntfEntry
    MAX-ACCESS  not-accessible
    STATUS  current
    DESCRIPTION
        "A row in the Ip interface table,
         Note:This mib is not supported for VX instance of Virtualization."
    INDEX   { ipNewCfgIntfIndex }
    ::= { ipNewCfgIntfTable 1 }
 
IpNewCfgIntfEntry ::= SEQUENCE {
    ipNewCfgIntfIndex         Integer32,
    ipNewCfgIntfAddr          IpAddress,
    ipNewCfgIntfMask          IpAddress,
    ipNewCfgIntfBroadcast     IpAddress,
    ipNewCfgIntfVlan          Integer32,
    ipNewCfgIntfState         INTEGER,
    ipNewCfgIntfBootpRelay    INTEGER,
    ipNewCfgIntfIpVer         INTEGER,
    ipNewCfgIntfIpv6Addr      DisplayString,
    ipNewCfgIntfPrefixLen     INTEGER,
    ipNewCfgIntfRouteAdv      INTEGER,
    ipNewCfgIntfDelete	      INTEGER,
    ipNewCfgIntfPeer          DisplayString,
    ipNewCfgIntfDescription   DisplayString
    }
 
ipNewCfgIntfIndex OBJECT-TYPE
    SYNTAX  Integer32
    MAX-ACCESS  read-only
    STATUS  current
    DESCRIPTION
	"The interface number for which the IP information is related."
    ::= { ipNewCfgIntfEntry 1 }

ipNewCfgIntfAddr OBJECT-TYPE
    SYNTAX  IpAddress
    MAX-ACCESS  read-create
    STATUS  current
    DESCRIPTION
        "The IP address of the interface."
    ::= { ipNewCfgIntfEntry 2 }

ipNewCfgIntfMask OBJECT-TYPE
    SYNTAX  IpAddress
    MAX-ACCESS  read-create
    STATUS  current  
    DESCRIPTION
        "The subnet mask of the interface."
    ::= { ipNewCfgIntfEntry 3 }

ipNewCfgIntfBroadcast OBJECT-TYPE
    SYNTAX  IpAddress
    MAX-ACCESS  read-create
    STATUS  obsolete  
    DESCRIPTION
        "The broadcast address of the interface."
    ::= { ipNewCfgIntfEntry 4 }

ipNewCfgIntfVlan OBJECT-TYPE
    SYNTAX  Integer32
    MAX-ACCESS  read-create
    STATUS  current  
    DESCRIPTION
        "The VLAN associated with the interface."
    ::= { ipNewCfgIntfEntry 5 }

ipNewCfgIntfState OBJECT-TYPE
    SYNTAX  INTEGER { 
	enabled(2),
	disabled(3),
        unsupported(2147483647)
	}
    MAX-ACCESS  read-create
    STATUS  current  
    DESCRIPTION
        "The state of the interface."
    ::= { ipNewCfgIntfEntry 6 }

ipNewCfgIntfDelete OBJECT-TYPE
    SYNTAX  INTEGER { 
	other(1),
        delete(2),
        unsupported(2147483647)
	}
    MAX-ACCESS  read-create
    STATUS  current
    DESCRIPTION
        "When set to the value of 2 (delete), the entire row is deleted. 
         When read, other(1) is returned. Setting the value to anything 
         other than 2(delete) has no effect on the state of the row."
    ::= { ipNewCfgIntfEntry 7 }

ipNewCfgIntfBootpRelay OBJECT-TYPE
    SYNTAX  INTEGER { 
	enabled(1),
	disabled(2),
        unsupported(2147483647)
	}
    MAX-ACCESS  read-create
    STATUS  current  
    DESCRIPTION
        "Enable/disable BOOTP relay."
    ::= { ipNewCfgIntfEntry 8 }

ipNewCfgIntfIpVer OBJECT-TYPE
    SYNTAX  INTEGER{
        ipv4(1),
        ipv6(2),
        unsupported(2147483647)
        }
    MAX-ACCESS read-create
    STATUS  current
    DESCRIPTION
        "The type of IP address."
    ::= { ipNewCfgIntfEntry 10 }

ipNewCfgIntfIpv6Addr OBJECT-TYPE
    SYNTAX  DisplayString  (SIZE(0..40))
    MAX-ACCESS read-create
    STATUS  current
    DESCRIPTION
        "The IPv6 address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { ipNewCfgIntfEntry 11 }

ipNewCfgIntfPrefixLen OBJECT-TYPE
    SYNTAX  INTEGER (1..128) 
    MAX-ACCESS read-create
    STATUS  current
    DESCRIPTION
        "The prefix length associated with this IP address ."
    ::= { ipNewCfgIntfEntry 12 }

ipNewCfgIntfRouteAdv  OBJECT-TYPE
    SYNTAX  INTEGER {
        enabled(1),
        disabled(2),
        unsupported(2147483647)
        }
    MAX-ACCESS  read-create
    STATUS  current
    DESCRIPTION
        "Enable/disable route advertisement of the interface."
    ::= { ipNewCfgIntfEntry 13 }


ipNewCfgIntfPeer  OBJECT-TYPE
    SYNTAX  DisplayString (SIZE(0..40))
    MAX-ACCESS  read-create
    STATUS  current
    DESCRIPTION
        "The Peer IP of the interface."
    ::= { ipNewCfgIntfEntry 14 }

ipNewCfgIntfDescription  OBJECT-TYPE
	SYNTAX  DisplayString (SIZE(0..50))
    MAX-ACCESS  read-create
    STATUS  current
    DESCRIPTION
        "The Description of the interface."
    ::= { ipNewCfgIntfEntry 15 }

ipCurLanIfId OBJECT-TYPE
    SYNTAX Integer32
    MAX-ACCESS read-only
    STATUS current
    DESCRIPTION
        "Holds the LAN interface ID,
         Note:This mib is not supported for VX instance of Virtualization."
    ::= { ipInterfaceCfg 4 }
    
ipNewLanIfId OBJECT-TYPE
    SYNTAX Integer32
    MAX-ACCESS read-create
    STATUS current
    DESCRIPTION
         "Holds the LAN interface ID,
          Note:This mib is not supported for VX instance of Virtualization."
    ::= { ipInterfaceCfg 5 }
    
-- IP Gateway Table Configuration

ipCurCfgGwMetric OBJECT-TYPE
    SYNTAX  INTEGER {
        strict(1),
        roundrobin(2),
        unsupported(2147483647)
        }  
    MAX-ACCESS  read-only
    STATUS  current
    DESCRIPTION
        "The default gateway metric.
         Note:This mib is not supported for VX instance of Virtualization."
    ::= { ipGatewayCfg 1 }

ipNewCfgGwMetric OBJECT-TYPE
    SYNTAX  INTEGER {
        strict(1),
        roundrobin(2),
        unsupported(2147483647)
        }  
    MAX-ACCESS  read-write
    STATUS  current
    DESCRIPTION
        "The default gateway metric.
         Note:This mib is not supported for VX instance of Virtualization."
    ::= { ipGatewayCfg 2 }

ipGatewayTableMax OBJECT-TYPE
    SYNTAX  Integer32
    MAX-ACCESS  read-only
    STATUS  current
    DESCRIPTION
        "The maximum number of rows in the IP gateway table.
         Note:This mib is not supported for VX instance of Virtualization."
    ::= { ipGatewayCfg 3 }

ipCurCfgGwTable OBJECT-TYPE
    SYNTAX  SEQUENCE OF IpCurCfgGwEntry
    MAX-ACCESS  not-accessible
    STATUS  current
    DESCRIPTION
        "The table of gateways  in the Current configuration Block.
         Note:This mib is not supported for VX instance of Virtualization."
    ::= { ipGatewayCfg 4 }

ipCurCfgGwEntry OBJECT-TYPE
    SYNTAX  IpCurCfgGwEntry
    MAX-ACCESS  not-accessible
    STATUS  current
    DESCRIPTION
        "A row in the Ip gateway table"
    INDEX   { ipCurCfgGwIndex }
    ::= { ipCurCfgGwTable 1 }

IpCurCfgGwEntry ::= SEQUENCE {
    ipCurCfgGwIndex         Integer32,
    ipCurCfgGwAddr          IpAddress,
    ipCurCfgGwInterval      INTEGER,
    ipCurCfgGwRetry         INTEGER,
    ipCurCfgGwArp           INTEGER,
    ipCurCfgGwVlan          Integer32,
    ipCurCfgGwIpVer         INTEGER,
    ipCurCfgGwIpv6Addr      DisplayString,
    ipCurCfgGwPriority      INTEGER,
    ipCurCfgGwState         INTEGER
    }

ipCurCfgGwIndex OBJECT-TYPE
    SYNTAX  Integer32
    MAX-ACCESS  read-only
    STATUS  current
    DESCRIPTION
        "The gateway number for which the information is related."
    ::= { ipCurCfgGwEntry 1}

ipCurCfgGwAddr OBJECT-TYPE
    SYNTAX  IpAddress
    MAX-ACCESS  read-only
    STATUS  current
    DESCRIPTION
        "The IP address of the default gateway."
    ::= { ipCurCfgGwEntry 2 }

ipCurCfgGwInterval OBJECT-TYPE 
    SYNTAX  INTEGER (0..60)
    MAX-ACCESS  read-only 
    STATUS  current 
    DESCRIPTION 
        "The interval between ping attempts." 
    ::= { ipCurCfgGwEntry 3 }

ipCurCfgGwRetry OBJECT-TYPE
    SYNTAX  INTEGER (1..120)   
    MAX-ACCESS  read-only
    STATUS  current
    DESCRIPTION
        "The number of failed attempts to declare the default gateway DOWN."
    ::= { ipCurCfgGwEntry 4 }

ipCurCfgGwState OBJECT-TYPE
    SYNTAX  INTEGER {
        enabled(2),
        disabled(3),
        unsupported(2147483647)
	}  
    MAX-ACCESS  read-only
    STATUS  current
    DESCRIPTION
        "The state of the default gateway."
    ::= { ipCurCfgGwEntry 5 }

ipCurCfgGwArp OBJECT-TYPE
    SYNTAX  INTEGER {
        enabled(2),
        disabled(3),
        unsupported(2147483647)
        } 
    MAX-ACCESS  read-only
    STATUS  current
    DESCRIPTION
        "The state of ARP/Neighbor Discovery health check."
    ::= { ipCurCfgGwEntry 6 }

ipCurCfgGwVlan OBJECT-TYPE
    SYNTAX  Integer32
    MAX-ACCESS  read-only
    STATUS  current
    DESCRIPTION
        "The VLAN number for this gateway. The first 4 entries in the table 
         are only used for default gateway load balancing hence the VLAN 
         cannot be specified for the first 4 entries."
    ::= { ipCurCfgGwEntry 7 }

ipCurCfgGwPriority OBJECT-TYPE
    SYNTAX  INTEGER {
	low(1),
	high(2),
        unsupported(2147483647)
	}
    MAX-ACCESS  read-only
    STATUS  current
    DESCRIPTION
        "The priority of the default route for this gateway. High priority
	 means that the default gateway route will have higher priority
	 over learned default routes.  Low priority means that the default
	 gateway route will have lower priority than learned default
	 routes."
    ::= { ipCurCfgGwEntry 8 }

ipCurCfgGwIpVer OBJECT-TYPE
    SYNTAX  INTEGER{
        ipv4(1),
        ipv6(2),
        unsupported(2147483647)
        }
    MAX-ACCESS  read-only
    STATUS  current
    DESCRIPTION
        "The type of IP address."
   ::= { ipCurCfgGwEntry 9 }

ipCurCfgGwIpv6Addr OBJECT-TYPE
    SYNTAX   DisplayString (SIZE(0..40))
    MAX-ACCESS  read-only
    STATUS  current
    DESCRIPTION
        "The IPv6 address of the gateway. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipCurCfgGwEntry 10 }


ipNewCfgGwTable OBJECT-TYPE
    SYNTAX  SEQUENCE OF IpNewCfgGwEntry
    MAX-ACCESS  not-accessible
    STATUS  current
    DESCRIPTION
        "The table of gateway configuration in the new configuration block.
         Note:This mib is not supported for VX instance of Virtualization."
    ::= { ipGatewayCfg 5 }

ipNewCfgGwEntry OBJECT-TYPE
    SYNTAX  IpNewCfgGwEntry
    MAX-ACCESS  not-accessible
    STATUS  current
    DESCRIPTION
        "A row in the Ip default gateway table,
         Note:This mib is not supported for VX instance of Virtualization."
    INDEX   { ipNewCfgGwIndex }
    ::= { ipNewCfgGwTable 1 }

IpNewCfgGwEntry ::= SEQUENCE {
    ipNewCfgGwIndex         Integer32,
    ipNewCfgGwAddr          IpAddress,
    ipNewCfgGwInterval      INTEGER,
    ipNewCfgGwRetry         INTEGER,
    ipNewCfgGwState         INTEGER,
    ipNewCfgGwArp           INTEGER,
    ipNewCfgGwVlan          Integer32,
    ipNewCfgGwIpVer         INTEGER,
    ipNewCfgGwIpv6Addr      DisplayString,
    ipNewCfgGwPriority      INTEGER,
    ipNewCfgGwDelete        INTEGER
    }

ipNewCfgGwIndex OBJECT-TYPE
    SYNTAX  Integer32
    MAX-ACCESS  read-only
    STATUS  current
    DESCRIPTION
        "The gateway number for which the information is related."
    ::= { ipNewCfgGwEntry 1}

ipNewCfgGwAddr OBJECT-TYPE
    SYNTAX  IpAddress
    MAX-ACCESS  read-create
    STATUS  current
    DESCRIPTION
        "The IP address of the default gateway."
    ::= { ipNewCfgGwEntry 2 }

ipNewCfgGwInterval OBJECT-TYPE 
    SYNTAX  INTEGER (0..60)
    MAX-ACCESS  read-create 
    STATUS  current 
    DESCRIPTION 
        "The interval in seconds between ping attempts." 
    ::= { ipNewCfgGwEntry 3 }

ipNewCfgGwRetry OBJECT-TYPE
    SYNTAX  INTEGER (1..120)   
    MAX-ACCESS  read-create
    STATUS  current
    DESCRIPTION
        "The number of failed attempts to declare the default gateway DOWN."
    ::= { ipNewCfgGwEntry 4 }

ipNewCfgGwState OBJECT-TYPE
    SYNTAX  INTEGER {
        enabled(2),
        disabled(3),
        unsupported(2147483647)
	}
    MAX-ACCESS  read-create
    STATUS  current
    DESCRIPTION
        "The state of the default gateway."
    ::= { ipNewCfgGwEntry 5 }

ipNewCfgGwDelete OBJECT-TYPE
    SYNTAX  INTEGER {
	other(1),
        delete(2),
        unsupported(2147483647)
        }
    MAX-ACCESS  read-create
    STATUS  current
    DESCRIPTION
        "When set to the value of 2 (delete), the entire row is deleted. 
         When read, other is returned. Setting the value to anything other 
         than 2(delete) has no effect on the state of the row."
    ::= { ipNewCfgGwEntry 6 }

ipNewCfgGwArp OBJECT-TYPE
    SYNTAX  INTEGER {
        enabled(2),
        disabled(3),
        unsupported(2147483647)
        }
    MAX-ACCESS  read-create
    STATUS  current
    DESCRIPTION
        "The state of the ARP/Neighbor Discovery health checks."
    ::= { ipNewCfgGwEntry 7 }

ipNewCfgGwVlan OBJECT-TYPE
    SYNTAX  Integer32
    MAX-ACCESS  read-create
    STATUS  current
    DESCRIPTION
        "The VLAN number for this gateway. The first 4 entries in the table 
         are only used for default gateway load balancing hence the VLAN 
         cannot be specified for the first 4 entries."
    ::= { ipNewCfgGwEntry 8 }

ipNewCfgGwPriority OBJECT-TYPE
    SYNTAX  INTEGER {
	low(1),
	high(2),
        unsupported(2147483647)
	}
    MAX-ACCESS  read-create
    STATUS  current
    DESCRIPTION
        "The priority of the default route for this gateway. High priority
	 means that the default gateway route will have higher priority
	 over learned default routes.  Low priority means that the default
	 gateway route will have lower priority than learned default
	 routes."
    ::= { ipNewCfgGwEntry 9 }


ipNewCfgGwIpVer OBJECT-TYPE
    SYNTAX  INTEGER{
        ipv4(1),
        ipv6(2),
        unsupported(2147483647)
        }
    MAX-ACCESS read-create
    STATUS  current
    DESCRIPTION
        "The type of IP address."
    ::= { ipNewCfgGwEntry 10 }

ipNewCfgGwIpv6Addr OBJECT-TYPE
    SYNTAX  DisplayString  (SIZE(0..40))
    MAX-ACCESS read-create
    STATUS  current
    DESCRIPTION
        "The IPv6 address of the gateway. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipNewCfgGwEntry 11 }


--
-- IP Static Route Configuration
--
ipStaticRouteTableMaxSize OBJECT-TYPE
    SYNTAX  Integer32
    MAX-ACCESS  read-only
    STATUS  current
    DESCRIPTION
        "The maximum number of rows in the Static Route table.
         Note:This mib is not supported for VX instance of Virtualization."
    ::= { ipStaticRouteCfg 1 }

ipCurCfgStaticRouteTable OBJECT-TYPE
    SYNTAX  SEQUENCE OF IpCurCfgStaticRouteEntry
    MAX-ACCESS  not-accessible
    STATUS  current
    DESCRIPTION
        "The table of static routes in the current configuration block.
         Note:This mib is not supported for VX instance of Virtualization."
    ::= { ipStaticRouteCfg 2 }

ipCurCfgStaticRouteEntry OBJECT-TYPE
    SYNTAX  IpCurCfgStaticRouteEntry
    MAX-ACCESS  not-accessible
    STATUS  current
    DESCRIPTION
        "A row in the static IP route table"

    INDEX   { ipCurCfgStaticRouteIndx }
    ::= { ipCurCfgStaticRouteTable 1 }

IpCurCfgStaticRouteEntry ::= SEQUENCE {
    ipCurCfgStaticRouteIndx         Integer32,
    ipCurCfgStaticRouteDestIp       IpAddress,
    ipCurCfgStaticRouteMask         IpAddress,
    ipCurCfgStaticRouteGateway      IpAddress,
    ipCurCfgStaticRouteInterface    Integer32
    }

ipCurCfgStaticRouteIndx OBJECT-TYPE
    SYNTAX  Integer32
    MAX-ACCESS  read-only
    STATUS  current
    DESCRIPTION
        "The index of the static routing table."
    ::= { ipCurCfgStaticRouteEntry 1}

ipCurCfgStaticRouteDestIp OBJECT-TYPE
    SYNTAX  IpAddress
    MAX-ACCESS  read-only
    STATUS  current
    DESCRIPTION
        "The destination IP address of this route."
    ::= { ipCurCfgStaticRouteEntry 2}

ipCurCfgStaticRouteMask OBJECT-TYPE 
    SYNTAX  IpAddress
    MAX-ACCESS  read-only 
    STATUS  current 
    DESCRIPTION 
        "The destination IP address of this route."
    ::= { ipCurCfgStaticRouteEntry 3}

ipCurCfgStaticRouteGateway OBJECT-TYPE 
    SYNTAX  IpAddress
    MAX-ACCESS  read-only 
    STATUS  current 
    DESCRIPTION 
        "The destination IP address of this route."
    ::= { ipCurCfgStaticRouteEntry 4}

ipCurCfgStaticRouteInterface OBJECT-TYPE 
    SYNTAX  Integer32
    MAX-ACCESS  read-only 
    STATUS  current 
    DESCRIPTION 
        "The IP interface of this route.  The IP address of the specified 
         interface shall be use as source IP when performs routing."
    ::= { ipCurCfgStaticRouteEntry 5}

ipNewCfgStaticRouteTable OBJECT-TYPE
    SYNTAX  SEQUENCE OF IpNewCfgStaticRouteEntry
    MAX-ACCESS  not-accessible
    STATUS  current
    DESCRIPTION
        "The table of static routes in the new configuration block.
         Note:This mib is not supported for VX instance of Virtualization."
    ::= { ipStaticRouteCfg 3 }

ipNewCfgStaticRouteEntry OBJECT-TYPE
    SYNTAX  IpNewCfgStaticRouteEntry
    MAX-ACCESS  not-accessible
    STATUS  current
    DESCRIPTION
        "A row in the static IP route table,
         Note:This mib is not supported for VX instance of Virtualization."
    INDEX   { ipNewCfgStaticRouteIndx }
    ::= { ipNewCfgStaticRouteTable 1 }

IpNewCfgStaticRouteEntry ::= SEQUENCE {
    ipNewCfgStaticRouteIndx         Integer32,
    ipNewCfgStaticRouteDestIp       IpAddress,
    ipNewCfgStaticRouteMask         IpAddress,
    ipNewCfgStaticRouteGateway      IpAddress,
    ipNewCfgStaticRouteAction       INTEGER,
    ipNewCfgStaticRouteInterface    Integer32
    }

ipNewCfgStaticRouteIndx OBJECT-TYPE
    SYNTAX  Integer32
    MAX-ACCESS  read-only
    STATUS  current
    DESCRIPTION
        "The index of the static routing table."
    ::= { ipNewCfgStaticRouteEntry 1}

ipNewCfgStaticRouteDestIp OBJECT-TYPE
    SYNTAX  IpAddress
    MAX-ACCESS  read-create
    STATUS  current
    DESCRIPTION
        "The destination IP address of this route."
    ::= { ipNewCfgStaticRouteEntry 2}

ipNewCfgStaticRouteMask OBJECT-TYPE 
    SYNTAX  IpAddress
    MAX-ACCESS  read-create 
    STATUS  current 
    DESCRIPTION 
        "The subnet mask of this route."
    ::= { ipNewCfgStaticRouteEntry 3}

ipNewCfgStaticRouteGateway OBJECT-TYPE 
    SYNTAX  IpAddress
    MAX-ACCESS  read-create 
    STATUS  current 
    DESCRIPTION 
        "The IP address of the gateway for this route."
    ::= { ipNewCfgStaticRouteEntry 4}

ipNewCfgStaticRouteAction OBJECT-TYPE
    SYNTAX  INTEGER {
        other(1),
        delete(2),
        unsupported(2147483647)
       }  
    MAX-ACCESS  read-create
    STATUS  current
    DESCRIPTION
        "When set to the value of 2 (delete), the entire row is deleted. 
         When read, other is returned. Setting the value to anything other 
         than 2(delete) has no effect on the state of the row."
    ::= { ipNewCfgStaticRouteEntry 5 }

ipNewCfgStaticRouteInterface OBJECT-TYPE 
    SYNTAX  Integer32
    MAX-ACCESS  read-create 
    STATUS  current 
    DESCRIPTION 
        "The IP interface of this route.  The IP address of the specified 
         interface shall be use as source IP when performs routing."
    ::= { ipNewCfgStaticRouteEntry 6 }

-- IPV6 static routes
ipv6CurCfgStaticRouteTable OBJECT-TYPE
    SYNTAX  SEQUENCE OF Ipv6CurCfgStaticRouteEntry
    MAX-ACCESS  not-accessible
    STATUS  current
    DESCRIPTION
        "The table of ipv6 static routes in the current configuration block.
         Note:This mib is not supported for VX instance of Virtualization."
    ::= { ipStaticRouteCfg 4 }

ipv6CurCfgStaticRouteEntry OBJECT-TYPE
    SYNTAX  Ipv6CurCfgStaticRouteEntry
    MAX-ACCESS  not-accessible
    STATUS  current
    DESCRIPTION
        "A row in the static IP route table"
    INDEX   { ipv6CurCfgStaticRouteIndx }
    ::= { ipv6CurCfgStaticRouteTable 1 }

Ipv6CurCfgStaticRouteEntry ::= SEQUENCE {
    ipv6CurCfgStaticRouteIndx         Integer32,
    ipv6CurCfgStaticRouteDestIp       DisplayString,
    ipv6CurCfgStaticRouteMask         Integer32,
    ipv6CurCfgStaticRouteGateway      DisplayString,
    ipv6CurCfgStaticRouteVlan         Integer32
    }


ipv6CurCfgStaticRouteIndx OBJECT-TYPE
    SYNTAX  Integer32
    MAX-ACCESS  read-only
    STATUS  current
    DESCRIPTION
        "The index of the ipv6 static routing table."
    ::= { ipv6CurCfgStaticRouteEntry 1}

ipv6CurCfgStaticRouteDestIp OBJECT-TYPE
    SYNTAX  DisplayString (SIZE(0..40))
    MAX-ACCESS  read-only
    STATUS  current
    DESCRIPTION
        " The destination IPv6 address of this route.
          Address should be 4-byte haxadecimal colon notation. Valid IPv6 address should be in
          any of the following forms xxxx:xxxx:xxxx:xxxx:xxxx:xxxx:xxxx:xxxx or xxxx::xxxx:xxxx:xxxx:xxxx or ::xxxx"
    ::= { ipv6CurCfgStaticRouteEntry 2}

ipv6CurCfgStaticRouteMask OBJECT-TYPE
    SYNTAX  Integer32 (1..128)
    MAX-ACCESS  read-only
    STATUS  current
    DESCRIPTION
        "The prefix length associated with this IP address."
    ::= { ipv6CurCfgStaticRouteEntry 3}

ipv6CurCfgStaticRouteGateway OBJECT-TYPE
    SYNTAX  DisplayString (SIZE(0..40))
    MAX-ACCESS  read-only
    STATUS  current
    DESCRIPTION
        "The destination IPv6 gateway address of this route.
          Address should be 4-byte haxadecimal colon notation. Valid IPv6 address should be in
          any of the following forms xxxx:xxxx:xxxx:xxxx:xxxx:xxxx:xxxx:xxxx or xxxx::xxxx:xxxx:xxxx:xxxx or ::xxxx"
    ::= { ipv6CurCfgStaticRouteEntry 4}

ipv6CurCfgStaticRouteVlan OBJECT-TYPE
    SYNTAX  Integer32 (1..4090)
    MAX-ACCESS  read-only
    STATUS  current
    DESCRIPTION
        "The IPv6 Vlan of this route.  The IPv6 address of the specified
         Vlan shall be use as source IP when performs routing."
    ::= { ipv6CurCfgStaticRouteEntry 5}

ipv6NewCfgStaticRouteTable OBJECT-TYPE
    SYNTAX  SEQUENCE OF Ipv6NewCfgStaticRouteEntry
    MAX-ACCESS  not-accessible
    STATUS  current
    DESCRIPTION
        "The table of ipv6 static routes in the current configuration block.
         Note:This mib is not supported for VX instance of Virtualization."
    ::= { ipStaticRouteCfg 5 }

ipv6NewCfgStaticRouteEntry OBJECT-TYPE
    SYNTAX  Ipv6NewCfgStaticRouteEntry
    MAX-ACCESS  not-accessible
    STATUS  current
    DESCRIPTION
        "A row in the static IP route table,
         Note:This mib is not supported for VX instance of Virtualization."
    INDEX   { ipv6NewCfgStaticRouteIndx }
    ::= { ipv6NewCfgStaticRouteTable 1 }

Ipv6NewCfgStaticRouteEntry ::= SEQUENCE {
    ipv6NewCfgStaticRouteIndx         Integer32,
    ipv6NewCfgStaticRouteDestIp       DisplayString,
    ipv6NewCfgStaticRouteMask         Integer32,
    ipv6NewCfgStaticRouteGateway      DisplayString,
    ipv6NewCfgStaticRouteAction       INTEGER,
    ipv6NewCfgStaticRouteVlan         Integer32
    }

ipv6NewCfgStaticRouteIndx OBJECT-TYPE
    SYNTAX  Integer32
    MAX-ACCESS  read-create
    STATUS  current
    DESCRIPTION
        "The index of the ipv6 static routing table."
    ::= { ipv6NewCfgStaticRouteEntry 1}

ipv6NewCfgStaticRouteDestIp OBJECT-TYPE
    SYNTAX  DisplayString (SIZE(0..40))
    MAX-ACCESS  read-create
    STATUS  current
    DESCRIPTION
        "The destination IPv6 address of this route.
         Address should be 4-byte haxadecimal colon notation. Valid IPv6 address should be in
         any of the following forms xxxx:xxxx:xxxx:xxxx:xxxx:xxxx:xxxx:xxxx or xxxx::xxxx:xxxx:xxxx:xxxx or ::xxxx"
    ::= { ipv6NewCfgStaticRouteEntry 2}

ipv6NewCfgStaticRouteMask OBJECT-TYPE
    SYNTAX  Integer32 (1..128)
    MAX-ACCESS  read-create
    STATUS  current
    DESCRIPTION
        "The prefix length associated with this IP address."
    ::= { ipv6NewCfgStaticRouteEntry 3}

ipv6NewCfgStaticRouteGateway OBJECT-TYPE
    SYNTAX  DisplayString (SIZE(0..40))
    MAX-ACCESS  read-create
    STATUS  current
    DESCRIPTION
        "The destination IPv6 gateway address of this route.
         Address should be 4-byte haxadecimal colon notation. Valid IPv6 address should be in
         any of the following forms xxxx:xxxx:xxxx:xxxx:xxxx:xxxx:xxxx:xxxx or xxxx::xxxx:xxxx:xxxx:xxxx or ::xxxx"
    ::= { ipv6NewCfgStaticRouteEntry 4}

ipv6NewCfgStaticRouteAction OBJECT-TYPE
    SYNTAX  INTEGER {
        other(1),
        delete(2),
        unsupported(2147483647)
       }
    MAX-ACCESS  read-create
    STATUS  current
    DESCRIPTION
        "When set to the value of 2 (delete), the entire row is deleted.
         When read, other is returned. Setting the value to anything other
         than 2(delete) has no effect on the state of the row."
    ::= { ipv6NewCfgStaticRouteEntry 5 }

ipv6NewCfgStaticRouteVlan OBJECT-TYPE
    SYNTAX  Integer32 (1..4090)
    MAX-ACCESS  read-create
    STATUS  current
    DESCRIPTION
        "The IPv6 Vlan of this route.  The IPv6 address of the specified
         vlan shall be use as source IP when performs routing."
    ::= { ipv6NewCfgStaticRouteEntry 6}

-- Static Tunnel Route Table IPv4

ipStaticTnlRouteTableMaxSize OBJECT-TYPE
    SYNTAX  Integer32
    MAX-ACCESS  read-only
    STATUS  current
    DESCRIPTION
        "The maximum number of rows in the Static Tunnel Route table.
        Note:This mib is not supported for VX instance of virtualization."
    ::= { ipStaticRouteCfg 6 }

ipCurCfgStaticTnlRouteTable OBJECT-TYPE
    SYNTAX  SEQUENCE OF IpCurCfgStaticTnlRouteEntry
    MAX-ACCESS  not-accessible
    STATUS  current
    DESCRIPTION
        "The table of static routes in the current configuration block.
        Note:This mib is not supported for VX instance of virtualization."
    ::= { ipStaticRouteCfg 7 }

ipCurCfgStaticTnlRouteEntry OBJECT-TYPE
    SYNTAX  IpCurCfgStaticTnlRouteEntry
    MAX-ACCESS  not-accessible
    STATUS  current
    DESCRIPTION
        "A row in the static IP route table.
        Note:This mib is not supported for VX instance of virtualization."
    INDEX   { ipCurCfgStaticTnlRouteIndx }
    ::= { ipCurCfgStaticTnlRouteTable 1 }

IpCurCfgStaticTnlRouteEntry ::= SEQUENCE {
    ipCurCfgStaticTnlRouteIndx         Integer32,
    ipCurCfgStaticTnlRouteDestIp       IpAddress,
    ipCurCfgStaticTnlRouteMask         IpAddress,
    ipCurCfgStaticTnlRouteTunnelId     DisplayString
    }

ipCurCfgStaticTnlRouteIndx OBJECT-TYPE
    SYNTAX  Integer32
    MAX-ACCESS  read-only
    STATUS  current
    DESCRIPTION
        "The index of the static routing table.
        Note:This mib is not supported for VX instance of virtualization."
    ::= { ipCurCfgStaticTnlRouteEntry 1}

ipCurCfgStaticTnlRouteDestIp OBJECT-TYPE
    SYNTAX  IpAddress
    MAX-ACCESS  read-only
    STATUS  current
    DESCRIPTION
        "The destination IP address of this route.
        Note:This mib is not supported for VX instance of virtualization."
    ::= { ipCurCfgStaticTnlRouteEntry 2}

ipCurCfgStaticTnlRouteMask OBJECT-TYPE
    SYNTAX  IpAddress
    MAX-ACCESS  read-only
    STATUS  current
    DESCRIPTION
        "The destination IP address of this route.
        Note:This mib is not supported for VX instance of virtualization."
    ::= { ipCurCfgStaticTnlRouteEntry 3}

ipCurCfgStaticTnlRouteTunnelId OBJECT-TYPE
    SYNTAX DisplayString  (SIZE(0..32))
    MAX-ACCESS  read-only
    STATUS  current
    DESCRIPTION
        "Tunnel ID for this route.
        Note:This mib is not supported for VX instance of virtualization."
    ::= { ipCurCfgStaticTnlRouteEntry 4}

ipNewCfgStaticTnlRouteTable OBJECT-TYPE
    SYNTAX  SEQUENCE OF IpNewCfgStaticTnlRouteEntry
    MAX-ACCESS  not-accessible
    STATUS  current
    DESCRIPTION
        "The table of static routes in the new configuration block.
        Note:This mib is not supported for VX instance of virtualization."
    ::= { ipStaticRouteCfg 8 }

ipNewCfgStaticTnlRouteEntry OBJECT-TYPE
    SYNTAX  IpNewCfgStaticTnlRouteEntry
    MAX-ACCESS  not-accessible
    STATUS  current
    DESCRIPTION
        "A row in the static IP route table.
        Note:This mib is not supported for VX instance of virtualization."
    INDEX   { ipNewCfgStaticTnlRouteIndx }
    ::= { ipNewCfgStaticTnlRouteTable 1 }

IpNewCfgStaticTnlRouteEntry ::= SEQUENCE {
    ipNewCfgStaticTnlRouteIndx         Integer32,
    ipNewCfgStaticTnlRouteDestIp       IpAddress,
    ipNewCfgStaticTnlRouteMask         IpAddress,
    ipNewCfgStaticTnlRouteTunnelId     DisplayString,
    ipNewCfgStaticTnlRouteAction       INTEGER
    }

ipNewCfgStaticTnlRouteIndx OBJECT-TYPE
    SYNTAX  Integer32
    MAX-ACCESS  read-only
    STATUS  current
    DESCRIPTION
        "The index of the static routing table.
        Note:This mib is not supported for VX instance of virtualization."
    ::= { ipNewCfgStaticTnlRouteEntry 1}

ipNewCfgStaticTnlRouteDestIp OBJECT-TYPE
    SYNTAX  IpAddress
    MAX-ACCESS  read-create
    STATUS  current
    DESCRIPTION
        "The destination IP address of this route.
        Note:This mib is not supported for VX instance of virtualization."
    ::= { ipNewCfgStaticTnlRouteEntry 2}

ipNewCfgStaticTnlRouteMask OBJECT-TYPE
    SYNTAX  IpAddress
    MAX-ACCESS  read-create
    STATUS  current
    DESCRIPTION
        "The subnet mask of this route.
        Note:This mib is not supported for VX instance of virtualization."
    ::= { ipNewCfgStaticTnlRouteEntry 3}

ipNewCfgStaticTnlRouteTunnelId OBJECT-TYPE
    SYNTAX  DisplayString (SIZE(0..32))
    MAX-ACCESS  read-create
    STATUS  current
    DESCRIPTION
        "Tunnel ID for this route.
        Note:This mib is not supported for VX instance of virtualization."
    ::= { ipNewCfgStaticTnlRouteEntry 4}
 
ipNewCfgStaticTnlRouteAction OBJECT-TYPE
    SYNTAX  INTEGER {
        other(1),
        delete(2),
        unsupported(2147483647)
       }
    MAX-ACCESS  read-create
    STATUS  current
    DESCRIPTION
        "When set to the value of 2 (delete), the entire row is deleted.
         When read, other is returned. Setting the value to anything other
         than 2(delete) has no effect on the state of the row.
        Note:This mib is not supported for VX instance of virtualization."
    ::= { ipNewCfgStaticTnlRouteEntry 5 }

-- Static Tunnel Route configuration table IPV6

ipv6CurCfgStaticTnlRouteTable OBJECT-TYPE
    SYNTAX  SEQUENCE OF Ipv6CurCfgStaticTnlRouteEntry
    MAX-ACCESS  not-accessible
    STATUS  current
    DESCRIPTION
        "The table of static routes in the current configuration block.
        Note:This mib is not supported for VX instance of virtualization."
    ::= { ipStaticRouteCfg 9 }

ipv6CurCfgStaticTnlRouteEntry OBJECT-TYPE
    SYNTAX  Ipv6CurCfgStaticTnlRouteEntry
    MAX-ACCESS  not-accessible
    STATUS  current
    DESCRIPTION
        "A row in the static IP route table.
        Note:This mib is not supported for VX instance of virtualization."
    INDEX   { ipv6CurCfgStaticTnlRouteIndx }
    ::= { ipv6CurCfgStaticTnlRouteTable 1 }

Ipv6CurCfgStaticTnlRouteEntry ::= SEQUENCE {
    ipv6CurCfgStaticTnlRouteIndx         Integer32,
    ipv6CurCfgStaticTnlRouteDestIp       DisplayString,
    ipv6CurCfgStaticTnlRoutePrefixLen    Integer32,
    ipv6CurCfgStaticTnlRouteTunnelId     DisplayString
    }

ipv6CurCfgStaticTnlRouteIndx OBJECT-TYPE
    SYNTAX  Integer32
    MAX-ACCESS  read-only
    STATUS  current
    DESCRIPTION
        "The index of the static routing table.
        Note:This mib is not supported for VX instance of virtualization."
    ::= { ipv6CurCfgStaticTnlRouteEntry 1}

ipv6CurCfgStaticTnlRouteDestIp OBJECT-TYPE
    SYNTAX DisplayString (SIZE(0..40)) 
    MAX-ACCESS  read-only
    STATUS  current
    DESCRIPTION
        "The destination IP address of this route.
        Note:This mib is not supported for VX instance of virtualization."
    ::= { ipv6CurCfgStaticTnlRouteEntry 2}

ipv6CurCfgStaticTnlRoutePrefixLen OBJECT-TYPE
    SYNTAX  Integer32 (1..128) 
    MAX-ACCESS  read-only
    STATUS  current
    DESCRIPTION
        "The destination IP address of this route.
        Note:This mib is not supported for VX instance of virtualization."
    ::= { ipv6CurCfgStaticTnlRouteEntry 3}

ipv6CurCfgStaticTnlRouteTunnelId OBJECT-TYPE
    SYNTAX DisplayString  (SIZE(0..32))
    MAX-ACCESS  read-only
    STATUS  current
    DESCRIPTION
        "Tunnel ID for this route.
        Note:This mib is not supported for VX instance of virtualization."
    ::= { ipv6CurCfgStaticTnlRouteEntry 4}

ipv6NewCfgStaticTnlRouteTable OBJECT-TYPE
    SYNTAX  SEQUENCE OF Ipv6NewCfgStaticTnlRouteEntry
    MAX-ACCESS  not-accessible
    STATUS  current
    DESCRIPTION
        "The table of static routes in the new configuration block.
        Note:This mib is not supported for VX instance of virtualization."
    ::= { ipStaticRouteCfg 10 }

ipv6NewCfgStaticTnlRouteEntry OBJECT-TYPE
    SYNTAX  Ipv6NewCfgStaticTnlRouteEntry
    MAX-ACCESS  not-accessible
    STATUS  current
    DESCRIPTION
        "A row in the static IP route table.
        Note:This mib is not supported for VX instance of virtualization."
    INDEX   { ipv6NewCfgStaticTnlRouteIndx }
    ::= { ipv6NewCfgStaticTnlRouteTable 1 }

Ipv6NewCfgStaticTnlRouteEntry ::= SEQUENCE {
    ipv6NewCfgStaticTnlRouteIndx         Integer32,
    ipv6NewCfgStaticTnlRouteDestIp       DisplayString,
    ipv6NewCfgStaticTnlRoutePrefixLen    Integer32,
    ipv6NewCfgStaticTnlRouteTunnelId     DisplayString,
    ipv6NewCfgStaticTnlRouteAction       INTEGER
    }

ipv6NewCfgStaticTnlRouteIndx OBJECT-TYPE
    SYNTAX  Integer32
    MAX-ACCESS  read-only
    STATUS  current
    DESCRIPTION
        "The index of the static routing table.
        Note:This mib is not supported for VX instance of virtualization."
    ::= { ipv6NewCfgStaticTnlRouteEntry 1}

ipv6NewCfgStaticTnlRouteDestIp OBJECT-TYPE
    SYNTAX DisplayString (SIZE(0..40)) 
    MAX-ACCESS  read-create
    STATUS  current
    DESCRIPTION
        "The destination IP address of this route.
        Note:This mib is not supported for VX instance of virtualization."
    ::= { ipv6NewCfgStaticTnlRouteEntry 2}

ipv6NewCfgStaticTnlRoutePrefixLen OBJECT-TYPE
    SYNTAX  Integer32 (1..128)
    MAX-ACCESS  read-create
    STATUS  current
    DESCRIPTION
        "The subnet mask of this route.
        Note:This mib is not supported for VX instance of virtualization."
    ::= { ipv6NewCfgStaticTnlRouteEntry 3}

ipv6NewCfgStaticTnlRouteTunnelId OBJECT-TYPE
    SYNTAX  DisplayString (SIZE(0..32))
    MAX-ACCESS  read-create
    STATUS  current
    DESCRIPTION
        "Tunnel ID for this route.
        Note:This mib is not supported for VX instance of virtualization."
    ::= { ipv6NewCfgStaticTnlRouteEntry 4}

ipv6NewCfgStaticTnlRouteAction OBJECT-TYPE
    SYNTAX  INTEGER {
        other(1),
        delete(2),
        unsupported(2147483647)
       }
    MAX-ACCESS  read-create
    STATUS  current
    DESCRIPTION
        "When set to the value of 2 (delete), the entire row is deleted.
         When read, other is returned. Setting the value to anything other
         than 2(delete) has no effect on the state of the row.
        Note:This mib is not supported for VX instance of virtualization."
    ::= { ipv6NewCfgStaticTnlRouteEntry 5 }

-- RIP version 1 Configuration 

ripCurCfgSupply OBJECT-TYPE
    SYNTAX  INTEGER {
    enabled(2),
    disabled(3),
    unsupported(2147483647)
    }
    MAX-ACCESS  read-only
    STATUS  current
    DESCRIPTION
        "Enable or disable supplying route updates for RIPv1.
         RIPv1 mibs are not supported anymore.
         Note:This mib is not supported for VX instance of Virtualization."
    ::= { ripCfg 1 }

ripNewCfgSupply OBJECT-TYPE
    SYNTAX  INTEGER {
        enabled(2),
        disabled(3),
        unsupported(2147483647)
        }
    MAX-ACCESS  read-write
    STATUS  current
    DESCRIPTION
        "Enable or disable supplying route updates for RIPv1.
         RIPv1 mibs are not supported anymore.
         Note:This mib is not supported for VX instance of Virtualization."
    ::= { ripCfg 2 }

ripCurCfgListen OBJECT-TYPE 
    SYNTAX  INTEGER {
        enabled(2),      
        disabled(3),
        unsupported(2147483647)
	}
    MAX-ACCESS  read-only 
    STATUS  current  
    DESCRIPTION 
        "Enable or disable listening to route updates for RIPv1.
         RIPv1 mibs are not supported anymore.
         Note:This mib is not supported for VX instance of Virtualization."
    ::= { ripCfg 3 }

ripNewCfgListen OBJECT-TYPE
    SYNTAX  INTEGER {
        enabled(2),
        disabled(3),
        unsupported(2147483647)
	}
    MAX-ACCESS  read-write
    STATUS  current
    DESCRIPTION
        "Enable or disable listening to route updates for RIPv1.
         RIPv1 mibs are not supported anymore.
         Note:This mib is not supported for VX instance of Virtualization."
    ::= { ripCfg 4 }

ripCurCfgDefListen OBJECT-TYPE 
    SYNTAX  INTEGER {
        enabled(2),      
        disabled(3),
        unsupported(2147483647)
	}
    MAX-ACCESS  read-only 
    STATUS  current  
    DESCRIPTION 
        "Enable or disable listening to default routes for RIPv1.
         RIPv1 mibs are not supported anymore.
         Note:This mib is not supported for VX instance of Virtualization."
    ::= { ripCfg 5 }

ripNewCfgDefListen OBJECT-TYPE
    SYNTAX  INTEGER {
        enabled(2),
        disabled(3),
        unsupported(2147483647)
	}
    MAX-ACCESS  read-write
    STATUS  current
    DESCRIPTION
        "Enable or disable listening to default routes for RIPv1.
         RIPv1 mibs are not supported anymore.
         Note:This mib is not supported for VX instance of Virtualization."
    ::= { ripCfg 6 }

ripCurCfgStaticSupply OBJECT-TYPE 
    SYNTAX  INTEGER {
        enabled(2),      
        disabled(3),
        unsupported(2147483647)
	}
    MAX-ACCESS  read-only 
    STATUS  current  
    DESCRIPTION 
        "Enable or disable supplying static route updates for RIPv1.
         RIPv1 mibs are not supported anymore.
         Note:This mib is not supported for VX instance of Virtualization."
    ::= { ripCfg 7 }

ripNewCfgStaticSupply OBJECT-TYPE
    SYNTAX  INTEGER {
        enabled(2),
        disabled(3),
        unsupported(2147483647)
	}
    MAX-ACCESS  read-write
    STATUS  current
    DESCRIPTION
        "Enable or disable supplying static route updates for RIPv1.
         RIPv1 mibs are not supported anymore.
         Note:This mib is not supported for VX instance of Virtualization."
    ::= { ripCfg 8 }

ripCurCfgUpdatePeriod OBJECT-TYPE
    SYNTAX  INTEGER (1..120)
    MAX-ACCESS  read-only
    STATUS  current
    DESCRIPTION
        "Update Period in seconds for RIPv1.
         RIPv1 mibs are not supported anymore.
         Note:This mib is not supported for VX instance of Virtualization."
    ::= { ripCfg 9 }

ripNewCfgUpdatePeriod OBJECT-TYPE
    SYNTAX  INTEGER (1..120)
    MAX-ACCESS  read-write
    STATUS  current
    DESCRIPTION
        "Update period in seconds for RIPv1.
         RIPv1 mibs are not supported anymore.
         Note:This mib is not supported for VX instance of Virtualization."
    ::= { ripCfg 10 }

ripCurCfgState OBJECT-TYPE
    SYNTAX  INTEGER {
        on(2),
        off(3),
        unsupported(2147483647)
        }
    MAX-ACCESS  read-only
    STATUS  current
    DESCRIPTION
        "RIP global state for RIPv1.
         RIPv1 mibs are not supported anymore.
         Note:This mib is not supported for VX instance of Virtualization."
    ::= { ripCfg 11 }

ripNewCfgState OBJECT-TYPE
    SYNTAX  INTEGER {
        on(2),
        off(3),
        unsupported(2147483647)
        }
    MAX-ACCESS  read-write
    STATUS  current
    DESCRIPTION
        "Globally turn RIP on or off for RIPv1.
         RIPv1 mibs are not supported anymore.
         Note:This mib is not supported for VX instance of Virtualization."
    ::= { ripCfg 12 }

ripCurCfgPoisonReverse OBJECT-TYPE
    SYNTAX  INTEGER {
        enabled(2),
        disabled(3),
        unsupported(2147483647)
	}
    MAX-ACCESS  read-only
    STATUS  current
    DESCRIPTION
        "RIPv1 poison reverse.
         RIPv1 mibs are not supported anymore.
         Note:This mib is not supported for VX instance of Virtualization."
    ::= { ripCfg 13 }
 
ripNewCfgPoisonReverse OBJECT-TYPE
    SYNTAX  INTEGER {
        enabled(2),
        disabled(3),
        unsupported(2147483647)
	}
    MAX-ACCESS  read-write
    STATUS  current
    DESCRIPTION
        "RIPv1 poison reverse.
         RIPv1 mibs are not supported anymore.
         Note:This mib is not supported for VX instance of Virtualization."
    ::= { ripCfg 14 }

ripCurCfgVip OBJECT-TYPE
      SYNTAX  INTEGER {
                enabled(2),
                disabled(3),
                unsupported(2147483647)
                }
      MAX-ACCESS  read-only
      STATUS  current
      DESCRIPTION
        "Advertise VIP Host Routes for RIPv1.
         RIPv1 mibs are not supported anymore.
         Note:This mib is not supported for VX instance of Virtualization."
      ::= { ripCfg 15 }

ripNewCfgVip OBJECT-TYPE
      SYNTAX  INTEGER {
                enabled(2),
                disabled(3),
                unsupported(2147483647)
                }
      MAX-ACCESS  read-write
      STATUS  current
      DESCRIPTION
        "Advertise VIP Host Routes for RIPv1.
         RIPv1 mibs are not supported anymore.
         Note:This mib is not supported for VX instance of Virtualization."
      ::= { ripCfg 16 }

-- RIP version 2 Configuration 

ripCurCfgIntfTable OBJECT-TYPE
    SYNTAX SEQUENCE OF RipCurCfgIntfEntry
    MAX-ACCESS not-accessible
    STATUS current
    DESCRIPTION
        "The table of RIPv2 on IP interface configuration in the current_config.
         Note:This mib is not supported for VX instance of Virtualization."
    ::= { rip2Cfg 1 }

ripCurCfgIntfEntry OBJECT-TYPE
    SYNTAX RipCurCfgIntfEntry
    MAX-ACCESS not-accessible
    STATUS current
    DESCRIPTION
        "Information about  RIPv2 on IP interface.
         Note:This mib is not supported for VX instance of Virtualization."
    INDEX { ripCurCfgIntfIndex }
    ::= { ripCurCfgIntfTable 1 }
 
RipCurCfgIntfEntry ::= SEQUENCE {
    ripCurCfgIntfIndex  	Integer32,
    ripCurCfgIntfVersion	INTEGER,
    ripCurCfgIntfSupply		INTEGER,
    ripCurCfgIntfListen		INTEGER,
    ripCurCfgIntfDefListen	INTEGER,
    ripCurCfgIntfTrigUpdate	INTEGER,
    ripCurCfgIntfMcastUpdate	INTEGER,
    ripCurCfgIntfPoisonReverse	INTEGER,
    ripCurCfgIntfState		INTEGER,
    ripCurCfgIntfMetric         INTEGER, 
    ripCurCfgIntfAuth           INTEGER, 
    ripCurCfgIntfKey            DisplayString,
    ripCurCfgIntfDefault	INTEGER
    }
 
ripCurCfgIntfIndex OBJECT-TYPE
    SYNTAX Integer32
    MAX-ACCESS read-only
    STATUS current
    DESCRIPTION
        "The interface number for which the RIPv2 information is related."
    ::= { ripCurCfgIntfEntry 1}

ripCurCfgIntfVersion OBJECT-TYPE
    SYNTAX INTEGER {
        ripVersion1(1),
        ripVersion2(2),
        both(3),
        unsupported(2147483647)
        }
    MAX-ACCESS read-only
    STATUS current
    DESCRIPTION
        "RIP version. Only RIPv2 is supported"
    ::= { ripCurCfgIntfEntry 2 }

ripCurCfgIntfState OBJECT-TYPE
    SYNTAX INTEGER {
        enabled(1),
        disabled(2),
        unsupported(2147483647)
        }
    MAX-ACCESS read-only
    STATUS current
    DESCRIPTION
        "Enable or disable RIPv2 protocol."
    ::= { ripCurCfgIntfEntry 3 }


ripCurCfgIntfListen OBJECT-TYPE
    SYNTAX INTEGER {
        enabled(1),
        disabled(2),
        unsupported(2147483647)
        }
    MAX-ACCESS read-only
    STATUS current
    DESCRIPTION
        "Enable or disable listening to route updates for RIPv2."
    ::= { ripCurCfgIntfEntry 4 }
 
ripCurCfgIntfDefListen OBJECT-TYPE
    SYNTAX  INTEGER {
        enabled(1),
        disabled(2),
        unsupported(2147483647)
        }
    MAX-ACCESS read-only
    STATUS obsolete
    DESCRIPTION
        "Enable or disable listening to default routes for RIPv2."
    ::= { ripCurCfgIntfEntry 5 }

ripCurCfgIntfTrigUpdate OBJECT-TYPE
    SYNTAX INTEGER {
        enabled(1),
        disabled(2),
        unsupported(2147483647)
        }
    MAX-ACCESS read-only
    STATUS current
    DESCRIPTION
        "Enable or disable triggered updates for RIPv2."
    ::= { ripCurCfgIntfEntry 6 }

ripCurCfgIntfMcastUpdate OBJECT-TYPE
    SYNTAX INTEGER {
        enabled(1),
        disabled(2),
        unsupported(2147483647)
        }
    MAX-ACCESS read-only
    STATUS current
    DESCRIPTION
        "Enable or disable multicast updates for RIPv2."
    ::= { ripCurCfgIntfEntry 7 }

ripCurCfgIntfPoisonReverse OBJECT-TYPE
    SYNTAX  INTEGER {
        enabled(1),
        disabled(2),
        unsupported(2147483647)
        }
    MAX-ACCESS read-only
    STATUS current
    DESCRIPTION
        "RIPv2 poison reverse."
    ::= { ripCurCfgIntfEntry 8 }

ripCurCfgIntfSupply OBJECT-TYPE
    SYNTAX INTEGER {
        enabled(1),
        disabled(2),
        unsupported(2147483647)
        }
    MAX-ACCESS read-only
    STATUS current
    DESCRIPTION
        "Enable or disable supplying route updates for RIPv2."
    ::= { ripCurCfgIntfEntry 9 }

ripCurCfgIntfMetric OBJECT-TYPE
    SYNTAX  INTEGER (1..15)
    MAX-ACCESS read-only
    STATUS current
    DESCRIPTION
        "RIPv2 route metric for this interface."
    ::= { ripCurCfgIntfEntry 10 }

ripCurCfgIntfAuth OBJECT-TYPE
    SYNTAX INTEGER {
        none(1),
        password(2),
        unsupported(2147483647)
        }
    MAX-ACCESS read-only
    STATUS current
    DESCRIPTION
        "The type of Authentication used on this interface for RIPv2."
    ::= { ripCurCfgIntfEntry 11 }

ripCurCfgIntfKey OBJECT-TYPE
    SYNTAX  DisplayString (SIZE(0..16))
    MAX-ACCESS  read-only
    STATUS  current
    DESCRIPTION
        "RIPv2 update authentication password."
    ::= { ripCurCfgIntfEntry 12 }

ripCurCfgIntfDefault OBJECT-TYPE
    SYNTAX  INTEGER {
        both(1),
        listen(2),
        supply(3),
        none(4),
        unsupported(2147483647)
        }
    MAX-ACCESS read-only
    STATUS current
    DESCRIPTION
        "Specifies what RIPv2 does with default routes."
    ::= { ripCurCfgIntfEntry 13 }

ripNewCfgIntfTable OBJECT-TYPE
    SYNTAX SEQUENCE OF RipNewCfgIntfEntry
    MAX-ACCESS not-accessible
    STATUS current
    DESCRIPTION
        "The table of RIPv2 on IP interface configuration in the new_config.
         Note:This mib is not supported for VX instance of Virtualization."
    ::= { rip2Cfg 2 }

ripNewCfgIntfEntry OBJECT-TYPE
    SYNTAX RipNewCfgIntfEntry
    MAX-ACCESS not-accessible
    STATUS current
    DESCRIPTION
        "Information about  RIPv2 on IP interface.
         Note:This mib is not supported for VX instance of Virtualization."
    INDEX { ripNewCfgIntfIndex }
    ::= { ripNewCfgIntfTable 1 }
 
RipNewCfgIntfEntry ::= SEQUENCE {
    ripNewCfgIntfIndex  	Integer32,
    ripNewCfgIntfVersion	INTEGER,
    ripNewCfgIntfSupply		INTEGER,
    ripNewCfgIntfListen		INTEGER,
    ripNewCfgIntfDefListen	INTEGER,
    ripNewCfgIntfTrigUpdate	INTEGER,
    ripNewCfgIntfMcastUpdate	INTEGER,
    ripNewCfgIntfPoisonReverse	INTEGER,
    ripNewCfgIntfState		INTEGER,
    ripNewCfgIntfMetric         INTEGER, 
    ripNewCfgIntfAuth           INTEGER, 
    ripNewCfgIntfKey            DisplayString,
    ripNewCfgIntfDefault	INTEGER
    }
 
ripNewCfgIntfIndex OBJECT-TYPE
    SYNTAX Integer32
    MAX-ACCESS read-only
    STATUS current
    DESCRIPTION
        "The interface number for which the RIPv2 information is related."
    ::= { ripNewCfgIntfEntry 1}

ripNewCfgIntfVersion OBJECT-TYPE
    SYNTAX INTEGER {
        ripVersion1(1),
        ripVersion2(2),
        both(3),
        unsupported(2147483647)
        }
    MAX-ACCESS read-create
    STATUS current
    DESCRIPTION
        "RIP version. Only RIPv2 is supported."
    ::= { ripNewCfgIntfEntry 2 }

ripNewCfgIntfSupply OBJECT-TYPE
    SYNTAX INTEGER {
        enabled(1),
        disabled(2),
        unsupported(2147483647)
        }
    MAX-ACCESS read-create
    STATUS current
    DESCRIPTION
        "Enable or disable supplying route updates for RIPv2."
    ::= { ripNewCfgIntfEntry 3 }

ripNewCfgIntfListen OBJECT-TYPE
    SYNTAX INTEGER {
        enabled(1),
        disabled(2),
        unsupported(2147483647)
        }
    MAX-ACCESS read-create
    STATUS current
    DESCRIPTION
        "Enable or disable listening to route updates for RIPv2."
    ::= { ripNewCfgIntfEntry 4 }
 
ripNewCfgIntfDefListen OBJECT-TYPE
    SYNTAX INTEGER {
        enabled(1),
        disabled(2),
        unsupported(2147483647)
        }
    MAX-ACCESS read-create
    STATUS obsolete
    DESCRIPTION
        "Enable or disable listening to default routes for RIPv2."
    ::= { ripNewCfgIntfEntry 5 }

ripNewCfgIntfTrigUpdate OBJECT-TYPE
    SYNTAX INTEGER {
        enabled(1),
        disabled(2),
        unsupported(2147483647)
        }
    MAX-ACCESS read-create
    STATUS current
    DESCRIPTION
        "Enable or disable triggered updates for RIPv2."
    ::= { ripNewCfgIntfEntry 6 }

ripNewCfgIntfMcastUpdate OBJECT-TYPE
    SYNTAX INTEGER {
        enabled(1),
        disabled(2),
        unsupported(2147483647)
        }
    MAX-ACCESS read-create
    STATUS current
    DESCRIPTION
        "Enable or disable multicast updates for RIPv2."
    ::= { ripNewCfgIntfEntry 7 }

ripNewCfgIntfPoisonReverse OBJECT-TYPE
    SYNTAX INTEGER {
        enabled(1),
        disabled(2),
        unsupported(2147483647)
        }
    MAX-ACCESS read-create
    STATUS current
    DESCRIPTION
        "RIPv2 poison reverse."
    ::= { ripNewCfgIntfEntry 8 }

ripNewCfgIntfState OBJECT-TYPE
    SYNTAX INTEGER {
        enabled(1),
        disabled(2),
        unsupported(2147483647)
        }
    MAX-ACCESS read-create
    STATUS current
    DESCRIPTION
        "Enable or disable RIPv2 protocol."
    ::= { ripNewCfgIntfEntry 9 }

ripNewCfgIntfMetric OBJECT-TYPE
    SYNTAX  INTEGER (1..15)
    MAX-ACCESS read-write
    STATUS current
    DESCRIPTION
        "RIPv2 route metric for this interface."
    ::= { ripNewCfgIntfEntry 10 }

ripNewCfgIntfAuth OBJECT-TYPE
    SYNTAX INTEGER {
        none(1),
        password(2),
        unsupported(2147483647)
        }
    MAX-ACCESS read-write
    STATUS current
    DESCRIPTION
        "The type of Authentication used on this interface for RIPv2."
    ::= { ripNewCfgIntfEntry 11 }

ripNewCfgIntfKey OBJECT-TYPE
    SYNTAX  DisplayString (SIZE(0..16))
    MAX-ACCESS  read-create
    STATUS  current
    DESCRIPTION
        "RIPv2 update authentication password."
    ::= { ripNewCfgIntfEntry 12 }

ripNewCfgIntfDefault OBJECT-TYPE
    SYNTAX INTEGER {
        both(1),
        listen(2),
        supply(3),
        none(4),
        unsupported(2147483647)
        }
    MAX-ACCESS read-create
    STATUS current
    DESCRIPTION
        "Specifies what RIPv2 does with default routes. The default routes
         action could be set to listen/supply/both/none."
    ::= { ripNewCfgIntfEntry 13 }

ripGeneral	OBJECT IDENTIFIER ::= { rip2Cfg 3 }

rip2CurCfgState OBJECT-TYPE
    SYNTAX INTEGER {
        on(1),
        off(2),
        unsupported(2147483647)
        }
    MAX-ACCESS read-only
    STATUS current
    DESCRIPTION
        "RIPv2 global state.
         Note:This mib is not supported for VX instance of Virtualization."
    ::= { ripGeneral 1 }

rip2NewCfgState OBJECT-TYPE
    SYNTAX INTEGER {
        on(1),
        off(2),
        unsupported(2147483647)
        }
    MAX-ACCESS read-write
    STATUS current
    DESCRIPTION
        "Globally turn RIPv2 on or off.
         Note:This mib is not supported for VX instance of Virtualization."
    ::= { ripGeneral 2 }

rip2CurCfgUpdatePeriod OBJECT-TYPE
      SYNTAX  INTEGER  (1..120)
      MAX-ACCESS  read-only
      STATUS  current
      DESCRIPTION
        "Update Period in seconds for RIPv2.
         Note:This mib is not supported for VX instance of Virtualization."
      ::= { ripGeneral 3 }

rip2NewCfgUpdatePeriod OBJECT-TYPE
      SYNTAX  INTEGER  (1..120)
      MAX-ACCESS  read-write
      STATUS  current
      DESCRIPTION
        "Update Period in seconds for RIPv2.
         Note:This mib is not supported for VX instance of Virtualization."
      ::= { ripGeneral 4 }

rip2CurCfgVip OBJECT-TYPE
      SYNTAX  INTEGER {
                enabled(2),
                disabled(3),
                unsupported(2147483647)
                }
      MAX-ACCESS  read-only
      STATUS  current
      DESCRIPTION
        "Advertise VIP Host Routes for RIPv2.
         Note:This mib is not supported for VX instance of Virtualization."
      ::= { ripGeneral 5 }

rip2NewCfgVip OBJECT-TYPE
      SYNTAX  INTEGER {
                enabled(2),
                disabled(3),
                unsupported(2147483647)
                }
      MAX-ACCESS  read-write
      STATUS  current
      DESCRIPTION
        "Advertise VIP Host Routes for RIPv2.
         Note:This mib is not supported for VX instance of Virtualization."
      ::= { ripGeneral 6 }

rip2CurCfgStaticSupply OBJECT-TYPE
      SYNTAX  INTEGER {
                enabled(2),
                disabled(3),
                unsupported(2147483647)
                }
      MAX-ACCESS  read-only
      STATUS  current
      DESCRIPTION
        "Advertise Static Routes for RIPv2.
         Note:This mib is not supported for VX instance of Virtualization."
      ::= { ripGeneral 7 }

rip2NewCfgStaticSupply OBJECT-TYPE
      SYNTAX  INTEGER {
                enabled(2),
                disabled(3),
                unsupported(2147483647)
                }
      MAX-ACCESS  read-write
      STATUS  current
      DESCRIPTION
        "Advertise Static Routes for RIPv2.
         Note:This mib is not supported for VX instance of Virtualization."
      ::= { ripGeneral 8 }

-- IP Forwarding Configuration 

ipFwdGeneralCfg   OBJECT IDENTIFIER ::=  {ipForwardCfg 1 }

ipFwdCurCfgState OBJECT-TYPE
    SYNTAX  INTEGER {
        on(2),
        off(3),
        unsupported(2147483647)
	}
    MAX-ACCESS  read-only
    STATUS  current
    DESCRIPTION
        "IP forwarding global state.
         Note:This mib is not supported for VX instance of Virtualization."
    ::= { ipFwdGeneralCfg 1 }

ipFwdNewCfgState OBJECT-TYPE
    SYNTAX  INTEGER { 
        on(2),
        off(3),
        unsupported(2147483647)
	}
    MAX-ACCESS  read-write
    STATUS  current  
    DESCRIPTION 
        "IP forwarding global state.
         Note:This mib is not supported for VX instance of Virtualization."
    ::= { ipFwdGeneralCfg 2 }

ipFwdCurCfgDirectedBcast OBJECT-TYPE
    SYNTAX INTEGER {
        enabled(2),
        disabled(3),
        unsupported(2147483647)
	}
    MAX-ACCESS read-only
    STATUS current
    DESCRIPTION
        "Enable or disable forwarding directed broadcasts.
         Note:This mib is not supported for VX instance of Virtualization."
    ::= { ipFwdGeneralCfg 3 }

ipFwdNewCfgDirectedBcast OBJECT-TYPE
    SYNTAX INTEGER {
        enabled(2),
        disabled(3),
        unsupported(2147483647)
	}
    MAX-ACCESS read-write
    STATUS current
    DESCRIPTION
        "Enable or disable forwarding directed broadcasts.
         Note:This mib is not supported for VX instance of Virtualization."
    ::= { ipFwdGeneralCfg 4 }

ipFwdCurCfgNoICMPRedirect OBJECT-TYPE
    SYNTAX INTEGER {
        enabled(2),
        disabled(3),
        unsupported(2147483647)
        }
    MAX-ACCESS read-only
    STATUS current
    DESCRIPTION
        "Enable or disable no icmp redirects.
         Note:This mib is not supported for VX instance of Virtualization."
    ::= { ipFwdGeneralCfg 5 }

ipFwdNewCfgNoICMPRedirect OBJECT-TYPE
    SYNTAX INTEGER {
        enabled(2),
        disabled(3),
        unsupported(2147483647)
        }
    MAX-ACCESS read-write
    STATUS current
    DESCRIPTION
        "Enable or disable no icmp redirects.
         Note:This mib is not supported for VX instance of Virtualization."
    ::= { ipFwdGeneralCfg 6 }

ipFwdCurCfgRtCache OBJECT-TYPE
    SYNTAX INTEGER {
        enabled(2),
        disabled(3),
        unsupported(2147483647)
        }
    MAX-ACCESS read-only
    STATUS current
    DESCRIPTION
        "Enable or disable SP Route Caching.
         Note:This mib is not supported for VX instance of Virtualization."
    ::= { ipFwdGeneralCfg 7 }

ipFwdNewCfgRtCache OBJECT-TYPE
    SYNTAX INTEGER {
        enabled(2),
        disabled(3),
        unsupported(2147483647)
        }
    MAX-ACCESS read-write
    STATUS current
    DESCRIPTION
        "Enable or disable SP Route Caching.
         Note:This mib is not supported for VX instance of Virtualization."
    ::= { ipFwdGeneralCfg 8 }

ipFwdPortTableMaxSize OBJECT-TYPE
    SYNTAX Integer32
    MAX-ACCESS read-only
    STATUS current
    DESCRIPTION
        "The maximum number of rows in the IP Port table.
         Note:This mib is not supported for VX instance of Virtualization."
    ::= { ipForwardCfg 2 }

ipFwdCurCfgPortTable OBJECT-TYPE
    SYNTAX  SEQUENCE OF IpFwdCurCfgPortEntry
    MAX-ACCESS  not-accessible
    STATUS  current
    DESCRIPTION
        "The table of ports and their forwarding states,
         Note:This mib is not supported for VX instance of Virtualization."
    ::= { ipForwardCfg 3 }

ipFwdCurCfgPortEntry OBJECT-TYPE
    SYNTAX  IpFwdCurCfgPortEntry
    MAX-ACCESS  not-accessible
    STATUS  current
    DESCRIPTION
        "A row in the ipFwdCurCfgPortTable,
         Note:This mib is not supported for VX instance of Virtualization."
    INDEX   { ipFwdCurCfgPortIndex }
    ::= { ipFwdCurCfgPortTable 1 }

IpFwdCurCfgPortEntry ::= SEQUENCE {
    ipFwdCurCfgPortIndex	Integer32,
    ipFwdCurCfgPortState	INTEGER
    }

ipFwdCurCfgPortIndex OBJECT-TYPE
    SYNTAX  Integer32
    MAX-ACCESS  read-only
    STATUS  current
    DESCRIPTION
        "The port number for which the forwarding state information pertains."
    ::= { ipFwdCurCfgPortEntry 1 }
 
ipFwdCurCfgPortState OBJECT-TYPE
    SYNTAX  INTEGER {
	enabled(2),
	disabled(3),
        unsupported(2147483647)
        }
    MAX-ACCESS  read-only
    STATUS  current
    DESCRIPTION
        "The forwarding state of the port."
    ::= { ipFwdCurCfgPortEntry 2 }

ipFwdNewCfgPortTable OBJECT-TYPE
    SYNTAX  SEQUENCE OF IpFwdNewCfgPortEntry
    MAX-ACCESS  not-accessible
    STATUS  current
    DESCRIPTION
        "The table of ports and their forwarding states,
         Note:This mib is not supported for VX instance of Virtualization."
    ::= { ipForwardCfg 4 }
 
ipFwdNewCfgPortEntry OBJECT-TYPE
    SYNTAX  IpFwdNewCfgPortEntry
    MAX-ACCESS  not-accessible
    STATUS  current
    DESCRIPTION
        "A row in the ipFwdNewCfgPortTable,
         Note:This mib is not supported for VX instance of Virtualization."
    INDEX   { ipFwdNewCfgPortIndex }
    ::= { ipFwdNewCfgPortTable 1 }
 
IpFwdNewCfgPortEntry ::= SEQUENCE {
    ipFwdNewCfgPortIndex           Integer32,
    ipFwdNewCfgPortState           INTEGER
    }
 
ipFwdNewCfgPortIndex OBJECT-TYPE
    SYNTAX  Integer32
    MAX-ACCESS  read-only
    STATUS  current
    DESCRIPTION
        "The port number for which the forwarding state information pertains."
    ::= { ipFwdNewCfgPortEntry 1 }
 
ipFwdNewCfgPortState OBJECT-TYPE
    SYNTAX  INTEGER {
        enabled(2),
        disabled(3),
        unsupported(2147483647)
        }
    MAX-ACCESS  read-write  
    STATUS  current
    DESCRIPTION
        "The forwarding state of the port."
    ::= { ipFwdNewCfgPortEntry 2 }

ipFwdLocalTableMaxSize OBJECT-TYPE
    SYNTAX Integer32
    MAX-ACCESS read-only
    STATUS current
    DESCRIPTION
        "The maximum number of rows in the Local table.
         Note:This mib is not supported for VX instance of Virtualization."
    ::= { ipForwardCfg 5 }

ipFwdCurCfgLocalTable OBJECT-TYPE
    SYNTAX  SEQUENCE OF IpFwdCurCfgLocalEntry
    MAX-ACCESS  not-accessible
    STATUS  current
    DESCRIPTION
        "The table of local network definition.
         Note:This mib is not supported for VX instance of Virtualization."
    ::= { ipForwardCfg 6 }

ipFwdCurCfgLocalEntry OBJECT-TYPE
    SYNTAX  IpFwdCurCfgLocalEntry
    MAX-ACCESS  not-accessible
    STATUS  current
    DESCRIPTION
        "A row in the ipFwdCurCfgLocalTable,
         Note:This mib is not supported for VX instance of Virtualization."
    INDEX   { ipFwdCurCfgLocalIndex }
    ::= { ipFwdCurCfgLocalTable 1 }

IpFwdCurCfgLocalEntry ::= SEQUENCE {
    ipFwdCurCfgLocalIndex	Integer32,
    ipFwdCurCfgLocalSubnet	IpAddress,
    ipFwdCurCfgLocalMask	IpAddress
    }

ipFwdCurCfgLocalIndex OBJECT-TYPE
    SYNTAX  Integer32 
    MAX-ACCESS  read-only
    STATUS  current
    DESCRIPTION
        "The index of ipFwdCurCfgLocalTable."
    ::= { ipFwdCurCfgLocalEntry 1 }

ipFwdCurCfgLocalSubnet OBJECT-TYPE
    SYNTAX  IpAddress
    MAX-ACCESS  read-only
    STATUS  current
    DESCRIPTION
        "The current local IP subnet."
    ::= { ipFwdCurCfgLocalEntry 2 }

ipFwdCurCfgLocalMask OBJECT-TYPE 
    SYNTAX  IpAddress 
    MAX-ACCESS  read-only 
    STATUS  current
    DESCRIPTION 
        "The current local IP subnet mask." 
    ::= { ipFwdCurCfgLocalEntry 3 } 
 
ipFwdNewCfgLocalTable OBJECT-TYPE
    SYNTAX  SEQUENCE OF IpFwdNewCfgLocalEntry
    MAX-ACCESS  not-accessible
    STATUS  current
    DESCRIPTION
        "The table of local network definition.
         Note:This mib is not supported for VX instance of Virtualization."
    ::= { ipForwardCfg 7 }

ipFwdNewCfgLocalEntry OBJECT-TYPE
    SYNTAX  IpFwdNewCfgLocalEntry
    MAX-ACCESS  not-accessible
    STATUS  current
    DESCRIPTION
        "A row in the ipFwdNewCfgLocalTable,
         Note:This mib is not supported for VX instance of Virtualization."
    INDEX   { ipFwdNewCfgLocalIndex }
    ::= { ipFwdNewCfgLocalTable 1 }

IpFwdNewCfgLocalEntry ::= SEQUENCE {
    ipFwdNewCfgLocalIndex	Integer32,
    ipFwdNewCfgLocalSubnet	IpAddress,
    ipFwdNewCfgLocalMask	IpAddress,
    ipFwdNewCfgLocalDelete      INTEGER
    }

ipFwdNewCfgLocalIndex OBJECT-TYPE
    SYNTAX  Integer32
    MAX-ACCESS  read-only
    STATUS  current
    DESCRIPTION
        "The index of ipFwdNewCfgLocalTable."
    ::= { ipFwdNewCfgLocalEntry 1 }

ipFwdNewCfgLocalSubnet OBJECT-TYPE 
    SYNTAX  IpAddress 
    MAX-ACCESS  read-create 
    STATUS  current
    DESCRIPTION 
        "The new local IP subnet." 
    ::= { ipFwdNewCfgLocalEntry 2 }

ipFwdNewCfgLocalMask OBJECT-TYPE  
    SYNTAX  IpAddress  
    MAX-ACCESS  read-create  
    STATUS  current
    DESCRIPTION  
        "The new local IP subnet mask."  
    ::= { ipFwdNewCfgLocalEntry 3 }

ipFwdNewCfgLocalDelete OBJECT-TYPE
    SYNTAX INTEGER { 
        other(1),
        delete(2),
        unsupported(2147483647)
	}
    MAX-ACCESS read-create
    STATUS current
    DESCRIPTION
        "When set to the value of 2 (delete), the entire row is deleted. 
         When read, other(1) is returned. Setting the value to anything 
         other than 2(delete) has no effect on the state of the row."
    ::= { ipFwdNewCfgLocalEntry 4 }

ipv6FwdCurCfgLocalTable OBJECT-TYPE
    SYNTAX  SEQUENCE OF Ipv6FwdCurCfgLocalEntry
    MAX-ACCESS  not-accessible
    STATUS  current
    DESCRIPTION
        "The table of local network definition.
         Note:This mib is not supported for VX instance of Virtualization."
    ::= { ipForwardCfg 8 }

ipv6FwdCurCfgLocalEntry OBJECT-TYPE
    SYNTAX  Ipv6FwdCurCfgLocalEntry
    MAX-ACCESS  not-accessible
    STATUS  current
    DESCRIPTION
        "A row in the ipv6FwdCurCfgLocalTable,
         Note:This mib is not supported for VX instance of Virtualization."
    INDEX   { ipv6FwdCurCfgLocalIndex }
    ::= { ipv6FwdCurCfgLocalTable 1 }

Ipv6FwdCurCfgLocalEntry ::= SEQUENCE {
    ipv6FwdCurCfgLocalIndex     Integer32,
    ipv6FwdCurCfgLocalSubnet    DisplayString,
    ipv6FwdCurCfgLocalMask     Integer32 
    }

ipv6FwdCurCfgLocalIndex OBJECT-TYPE
    SYNTAX  Integer32
    MAX-ACCESS  read-only
    STATUS  current
    DESCRIPTION
        "The index of ipv6FwdCurCfgLocalTable."
    ::= { ipv6FwdCurCfgLocalEntry 1 }

ipv6FwdCurCfgLocalSubnet OBJECT-TYPE
    SYNTAX  DisplayString (SIZE(0..40))
    MAX-ACCESS  read-only
    STATUS  current
    DESCRIPTION
        "The current local IPv6 subnet."
    ::= { ipv6FwdCurCfgLocalEntry 2 }

ipv6FwdCurCfgLocalMask OBJECT-TYPE
    SYNTAX  Integer32 (1..128) 
    MAX-ACCESS  read-only
    STATUS  current
    DESCRIPTION
        "The current local IPv6 subnet mask."
    ::= { ipv6FwdCurCfgLocalEntry 3 }

ipv6FwdNewCfgLocalTable OBJECT-TYPE
    SYNTAX  SEQUENCE OF Ipv6FwdNewCfgLocalEntry
    MAX-ACCESS  not-accessible
    STATUS  current
    DESCRIPTION
        "The table of local IPv6 network definition.
         Note:This mib is not supported for VX instance of Virtualization."
    ::= { ipForwardCfg 9 }

ipv6FwdNewCfgLocalEntry OBJECT-TYPE
    SYNTAX  Ipv6FwdNewCfgLocalEntry
    MAX-ACCESS  not-accessible
    STATUS  current
    DESCRIPTION
        "A row in the ipv6FwdNewCfgLocalTable "
    INDEX   { ipv6FwdNewCfgLocalIndex }
    ::= { ipv6FwdNewCfgLocalTable 1 }

Ipv6FwdNewCfgLocalEntry ::= SEQUENCE {
    ipv6FwdNewCfgLocalIndex     Integer32,
    ipv6FwdNewCfgLocalSubnet    DisplayString,
    ipv6FwdNewCfgLocalMask      Integer32,
    ipv6FwdNewCfgLocalDelete      INTEGER
    }

ipv6FwdNewCfgLocalIndex OBJECT-TYPE
    SYNTAX  Integer32
    MAX-ACCESS  read-only
    STATUS  current
    DESCRIPTION
        "The index of ipv6FwdNewCfgLocalTable."
    ::= { ipv6FwdNewCfgLocalEntry 1 }

ipv6FwdNewCfgLocalSubnet OBJECT-TYPE
    SYNTAX  DisplayString (SIZE(0..40))
    MAX-ACCESS  read-create
    STATUS  current
    DESCRIPTION
        "The new local IPv6 subnet."
    ::= { ipv6FwdNewCfgLocalEntry 2 }

ipv6FwdNewCfgLocalMask OBJECT-TYPE
    SYNTAX  Integer32 (1..128) 
    MAX-ACCESS  read-create
    STATUS  current
    DESCRIPTION
        "The new local IPv6 subnet mask."
    ::= { ipv6FwdNewCfgLocalEntry 3 }

ipv6FwdNewCfgLocalDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row."
    ::= { ipv6FwdNewCfgLocalEntry 4 }

--
-- ARP configuration
--
arpCurCfgReARPPeriod OBJECT-TYPE
    SYNTAX INTEGER (2..120)
    MAX-ACCESS read-only
    STATUS current
    DESCRIPTION
        "Re-ARP Period in seconds.
         Note:This mib is not supported for VX instance of Virtualization."
    ::= { arpCfg 1 }

arpNewCfgReARPPeriod OBJECT-TYPE 
    SYNTAX  INTEGER (2..120)
    MAX-ACCESS  read-write
    STATUS  current 
    DESCRIPTION 
        "Re-ARP Period in seconds.
         Note:This mib is not supported for VX instance of Virtualization."
    ::= { arpCfg 2 }

arpCurCfgVIPRspnd OBJECT-TYPE
    SYNTAX INTEGER {
        enable(1),
        disable(2),
        unsupported(2147483647)
        }
    MAX-ACCESS read-only
    STATUS current
    DESCRIPTION
        "Responding to ARP for VIPs, either enable or disable.
         Note:This mib is not supported for VX instance of Virtualization."
    ::= { arpCfg 3 }

arpNewCfgVIPRspnd OBJECT-TYPE
    SYNTAX INTEGER {
        enable(1),
        disable(2),
        unsupported(2147483647)
        }
    MAX-ACCESS  read-write
    STATUS  current
    DESCRIPTION
        "Set responding to ARP for VIPs, either enable or disable.
         Note:This mib is not supported for VX instance of Virtualization."
    ::= { arpCfg 4 }

--
-- IP Bootp Configration
--
ipCurCfgBootpAddr OBJECT-TYPE
    SYNTAX  IpAddress
    MAX-ACCESS  read-only
    STATUS  current
    DESCRIPTION
        "The IP address of BOOTP server.
         Note:This mib is not supported for VX instance of Virtualization."
    ::= { ipBootpCfg 1 }

ipNewCfgBootpAddr OBJECT-TYPE
    SYNTAX  IpAddress
    MAX-ACCESS  read-write
    STATUS  current
    DESCRIPTION
        "The IP address of BOOTP server.
         Note:This mib is not supported for VX instance of Virtualization."
    ::= { ipBootpCfg 2 }

ipCurCfgBootpAddr2 OBJECT-TYPE
    SYNTAX  IpAddress
    MAX-ACCESS  read-only
    STATUS  current
    DESCRIPTION
        "The IP address of second BOOTP server.
         Note:This mib is not supported for VX instance of Virtualization."
    ::= { ipBootpCfg 3 }

ipNewCfgBootpAddr2 OBJECT-TYPE
    SYNTAX  IpAddress
    MAX-ACCESS  read-write
    STATUS  current
    DESCRIPTION
        "The IP address of second BOOTP server.
         Note:This mib is not supported for VX instance of Virtualization."
    ::= { ipBootpCfg 4 }

ipCurCfgBootpState OBJECT-TYPE
    SYNTAX  INTEGER {
        enabled(2),
        disabled(3),
        unsupported(2147483647)
        }
    MAX-ACCESS  read-only
    STATUS  current
    DESCRIPTION
        "The state of BOOTP relay.
         Note:This mib is not supported for VX instance of Virtualization."
    ::= { ipBootpCfg 5 }

ipNewCfgBootpState OBJECT-TYPE
    SYNTAX  INTEGER {
        enabled(2),
        disabled(3),
        unsupported(2147483647)
        }
    MAX-ACCESS  read-write  
    STATUS  current
    DESCRIPTION
        "The state of BOOTP relay.
         Note:This mib is not supported for VX instance of Virtualization."
    ::= { ipBootpCfg 6 }

ipCurCfgBootpPrsvPort OBJECT-TYPE
    SYNTAX  INTEGER {
        enabled(2),
        disabled(3),
        unsupported(2147483647)
        }
    MAX-ACCESS  read-only
    STATUS  current
    DESCRIPTION
        "Enable/Disable preserve source port by relay agent.
         Note:This mib is not supported for VX instance of Virtualization."
    ::= { ipBootpCfg 7 }


ipNewCfgBootpPrsvPort OBJECT-TYPE
    SYNTAX  INTEGER {
        enabled(2),
        disabled(3),
        unsupported(2147483647)
        }
    MAX-ACCESS  read-write
    STATUS  current
    DESCRIPTION
        "Enable/Disable preserve source port by relay agent,
         Note:This mib is not supported for VX instance of Virtualization."
    ::= { ipBootpCfg 8 }


-- VRRP (Virtual Router Redundantcy Protocol) Group

vrrpGeneral       OBJECT IDENTIFIER ::= { vrrpCfg 1 }

vrrpCurCfgGenState OBJECT-TYPE
    SYNTAX  INTEGER {
        enabled(1),
        disabled(2),
        unsupported(2147483647)
        }
    MAX-ACCESS  read-only
    STATUS  current
    DESCRIPTION
        "Enable or disable VRRP operation globally.
         Note:This mib is not supported for VX instance of Virtualization."
    ::= { vrrpGeneral 1 }

vrrpNewCfgGenState OBJECT-TYPE
    SYNTAX  INTEGER {
        enabled(1),
        disabled(2),
        unsupported(2147483647)
        }
    MAX-ACCESS  read-write
    STATUS  current
    DESCRIPTION
        "Enable or disable VRRP operation globally.
         Note:This mib is not supported for VX instance of Virtualization."
    ::= { vrrpGeneral 2 }

vrrpCurCfgGenTckVirtRtrInc OBJECT-TYPE
    SYNTAX  INTEGER (0..254)
    MAX-ACCESS  read-only
    STATUS  current
    DESCRIPTION
        "The increment of VRRP virtual router priority. The priority is 
         adjusted by tracking the state of other virtual routers.
         Note:This mib is not supported for VX instance of Virtualization."
    ::= { vrrpGeneral 3 }

vrrpNewCfgGenTckVirtRtrInc OBJECT-TYPE
    SYNTAX  INTEGER (0..254)
    MAX-ACCESS  read-write
    STATUS  current
    DESCRIPTION
        "The increment of VRRP virtual router priority. The priority is 
         adjusted by tracking the state of other virtual routers.
         Note:This mib is not supported for VX instance of Virtualization."
    ::= { vrrpGeneral 4 }

vrrpCurCfgGenTckIpIntfInc OBJECT-TYPE
    SYNTAX  INTEGER (0..254)
    MAX-ACCESS  read-only
    STATUS  current
    DESCRIPTION
        "The increment of VRRP virtual router priority. The priority is 
         adjusted by tracking the state of other router interfaces.
         Note:This mib is not supported for VX instance of Virtualization."
    ::= { vrrpGeneral 5 }

vrrpNewCfgGenTckIpIntfInc OBJECT-TYPE
    SYNTAX  INTEGER (0..254)
    MAX-ACCESS  read-write
    STATUS  current
    DESCRIPTION
        "The increment of VRRP virtual router priority. The priority is 
         adjusted by tracking the state of other router interfaces.
         Note:This mib is not supported for VX instance of Virtualization."
    ::= { vrrpGeneral 6 }

vrrpCurCfgGenTckVlanPortInc OBJECT-TYPE
    SYNTAX  INTEGER (0..254)
    MAX-ACCESS  read-only
    STATUS  current
    DESCRIPTION
        "The increment of VRRP virtual router priority. The priority is 
         adjusted by tracking the port state of ports that belongs to the 
         same virtual LAN as the virtual router.
         Note:This mib is not supported for VX instance of Virtualization."
    ::= { vrrpGeneral 7 }

vrrpNewCfgGenTckVlanPortInc OBJECT-TYPE
    SYNTAX  INTEGER (0..254)
    MAX-ACCESS  read-write
    STATUS  current
    DESCRIPTION
        "The increment of VRRP virtual router priority. The priority is 
         adjusted by tracking the port state of ports that belongs to the 
         same virtual LAN as the virtual router.
         Note:This mib is not supported for VX instance of Virtualization."
    ::= { vrrpGeneral 8 }

vrrpCurCfgGenTckL4PortInc OBJECT-TYPE
    SYNTAX  INTEGER (0..254)
    MAX-ACCESS  read-only
    STATUS  current
    DESCRIPTION
        "The increment of VRRP virtual router priority. The priority is 
         adjusted by tracking the Layer 4 port states. This is valid when 
         virtual server is configured as a VRRP virtual router.
         Note:This mib is not supported for VX instance of Virtualization."
    ::= { vrrpGeneral 9 }

vrrpNewCfgGenTckL4PortInc OBJECT-TYPE
    SYNTAX  INTEGER (0..254)
    MAX-ACCESS  read-write
    STATUS  current
    DESCRIPTION
        "The increment of VRRP virtual router priority. The priority is 
         adjusted by tracking the Layer 4 port states. This is valid when 
         virtual server is configured as a VRRP virtual router.
         Note:This mib is not supported for VX instance of Virtualization."
    ::= { vrrpGeneral 10 }

vrrpCurCfgGenTckRServerInc OBJECT-TYPE
    SYNTAX  INTEGER (0..254)
    MAX-ACCESS  read-only
    STATUS  current
    DESCRIPTION
        "The increment of VRRP virtual router priority. The priority is 
         adjusted by tracking the state of real servers under the virtual 
         server which is configured as a VRRP virtual router.
         Note:This mib is not supported for VX instance of Virtualization."
    ::= { vrrpGeneral 11 }

vrrpNewCfgGenTckRServerInc OBJECT-TYPE
    SYNTAX  INTEGER (0..254)
    MAX-ACCESS  read-write
    STATUS  current
    DESCRIPTION
        "The increment of VRRP virtual router priority. The priority is 
         adjusted by tracking the state of real servers under the virtual 
         server which is configured as a VRRP virtual router.
         Note:This mib is not supported for VX instance of Virtualization."
    ::= { vrrpGeneral 12 }

vrrpCurCfgGenTckHsrpInc OBJECT-TYPE
    SYNTAX  INTEGER (0..254)
    MAX-ACCESS  read-only
    STATUS  current
    DESCRIPTION
        "The increment of VRRP virtual router priority.  The
	 priority is adjusted by tracking the HSRP advertisements.
         Note:This mib is not supported for VX instance of Virtualization."
    ::= { vrrpGeneral 13 }

vrrpNewCfgGenTckHsrpInc OBJECT-TYPE
    SYNTAX  INTEGER (0..254)
    MAX-ACCESS  read-write
    STATUS  current
    DESCRIPTION
        "The increment of VRRP virtual router priority.  The
         priority is adjusted by tracking the HSRP advertisements.
         Note:This mib is not supported for VX instance of Virtualization."
    ::= { vrrpGeneral 14 }

vrrpCurCfgGenHotstandby OBJECT-TYPE
    SYNTAX  INTEGER {
        enabled(1),
        disabled(2),
        unsupported(2147483647)
        }
    MAX-ACCESS  read-only
    STATUS  current
    DESCRIPTION
        "Enable or disable hotstandby processing.
         Note:This mib is not supported for VX instance of Virtualization."
    ::= { vrrpGeneral 15 }

vrrpNewCfgGenHotstandby OBJECT-TYPE
    SYNTAX  INTEGER {
        enabled(1),
        disabled(2),
        unsupported(2147483647)
        }
    MAX-ACCESS  read-write
    STATUS  current
    DESCRIPTION
        "Enable or disable hotstandby processing.
         Note:This mib is not supported for VX instance of Virtualization."
    ::= { vrrpGeneral 16 }

vrrpCurCfgGenTckHsrvInc OBJECT-TYPE
        SYNTAX  INTEGER (0..254)
        MAX-ACCESS  read-only
        STATUS  current
        DESCRIPTION
                "The increment of VRRP virtual router priority.  The
                 priority is adjusted by tracking the HSRP advertisements
                 by VLAN.
                 Note:This mib is not supported for VX instance of Virtualization."
        ::= { vrrpGeneral 17 }
 
vrrpNewCfgGenTckHsrvInc OBJECT-TYPE
        SYNTAX  INTEGER (0..254)
        MAX-ACCESS  read-write
        STATUS  current
        DESCRIPTION
                "The increment of VRRP virtual router priority.  The
                 priority is adjusted by tracking the HSRP advertisements
                 by VLAN.
                 Note:This mib is not supported for VX instance of Virtualization."
        ::= { vrrpGeneral 18 }

vrrpCurCfgGenHoldoff OBJECT-TYPE
        SYNTAX  INTEGER (0..255)
        MAX-ACCESS  read-only
        STATUS  current
        DESCRIPTION
                "The time for VRRP virtual router to hold before it 
                 begins to change state to backup or master state.
                 Note:This mib is not supported for VX instance of Virtualization."
        ::= { vrrpGeneral 19 }

vrrpNewCfgGenHoldoff OBJECT-TYPE
        SYNTAX  INTEGER (0..255)
        MAX-ACCESS  read-write
        STATUS  current
        DESCRIPTION
                "The time for VRRP virtual router to hold before it 
                 begins to change state to backup or master state.
                 Note:This mib is not supported for VX instance of Virtualization."
        ::= { vrrpGeneral 20 }

vrrpCurCfgGenOspfCost OBJECT-TYPE
    SYNTAX  INTEGER (1..65535)
    MAX-ACCESS  read-only
    STATUS  current
    DESCRIPTION
    "OSPF Cost Adjustment,
     Note:This mib is not supported for VX instance of Virtualization."
    ::= { vrrpGeneral 23 }

vrrpNewCfgGenOspfCost OBJECT-TYPE
    SYNTAX  INTEGER (0..65535) 
    MAX-ACCESS  read-write
    STATUS  current
    DESCRIPTION
    "OSPF Cost Adjustment,
     Note:This mib is not supported for VX instance of Virtualization."
    ::= { vrrpGeneral 24 }
vrrpCurCfgGenTckSwExtInc OBJECT-TYPE
    SYNTAX  INTEGER (0..254)
    MAX-ACCESS  read-only
    STATUS  current
    DESCRIPTION
        "The increment of VRRP virtual router priority. The priority is
         adjusted by tracking the availability of Switch Extension in the chassis.
         Note:This mib is not supported for VX instance of Virtualization."
    ::= { vrrpGeneral 25 }

vrrpNewCfgGenTckSwExtInc OBJECT-TYPE
    SYNTAX  INTEGER (0..254)
    MAX-ACCESS  read-write
    STATUS  current
    DESCRIPTION
        "The increment of VRRP virtual router priority. The priority is
         adjusted by tracking the availability of Switch Extension in the chassis.
         Note:This mib is not supported for VX instance of Virtualization."
    ::= { vrrpGeneral 26 }
vrrpCurCfgGenUnicast OBJECT-TYPE
    SYNTAX  INTEGER {
        enabled(1),
        disabled(2),
        unsupported(2147483647)
        }
    MAX-ACCESS  read-only
    STATUS  current
    DESCRIPTION
        "Enable or disable unicast advertisement.
         Note:This mib is not supported for VX instance of Virtualization."
    ::= { vrrpGeneral 27 }

vrrpNewCfgGenUnicast OBJECT-TYPE
    SYNTAX  INTEGER {
        enabled(1),
        disabled(2),
        unsupported(2147483647)
        }
    MAX-ACCESS  read-write
    STATUS  current
    DESCRIPTION
        "Enable or disable unicast advertisement.
         Note:This mib is not supported for VX instance of Virtualization."
    ::= { vrrpGeneral 28 }
vrrpCurCfgGenFovdelay OBJECT-TYPE
    SYNTAX  INTEGER {
        enabled(1),
        disabled(2),
        unsupported(2147483647)
        }
    MAX-ACCESS  read-only
    STATUS  current
    DESCRIPTION
        "Enable/disable the delay to process the traffic on ports during  failover (hot-standby only).
         Note:This mib is not supported for VX instance of Virtualization."
    ::= { vrrpGeneral 29 }
vrrpNewCfgGenFovdelay OBJECT-TYPE
    SYNTAX  INTEGER {
        enabled(1),
        disabled(2),
        unsupported(2147483647)
        }
    MAX-ACCESS  read-write
    STATUS  current
    DESCRIPTION
        "Enable/disable the delay to process the traffic on ports during  failover (hot-standby only).
         Note:This mib is not supported for VX instance of Virtualization."
    ::= { vrrpGeneral 30 }
vrrpCurCfgGenVrMac OBJECT-TYPE
    SYNTAX  INTEGER {
        enabled(1),
        disabled(2)
        }
    MAX-ACCESS  read-only
    STATUS  current
    DESCRIPTION
        "Enable/disable usage of VRRP MAC instead of Interface MAC for VR owner. "
    ::= { vrrpGeneral 31 }

vrrpNewCfgGenVrMac OBJECT-TYPE
    SYNTAX  INTEGER {
        enabled(1),
        disabled(2)
        }
    MAX-ACCESS  read-write
    STATUS  current
    DESCRIPTION
        "Enable/disable usage of VRRP MAC instead of Interface MAC for VR owner. "
    ::= { vrrpGeneral 32 }

vrrpVirtRtrTableMaxSize OBJECT-TYPE
    SYNTAX Integer32
    MAX-ACCESS read-only
    STATUS current
    DESCRIPTION
        "The maximum number of entries in VRRP virtual router table.
         Note:This mib is not supported for VX instance of Virtualization."
    ::= { vrrpCfg 2 }

vrrpCurCfgVirtRtrTable OBJECT-TYPE
    SYNTAX  SEQUENCE OF VrrpCurCfgVirtRtrTableEntry
    MAX-ACCESS  not-accessible
    STATUS  current
    DESCRIPTION
        "The table of VRRP virtual routers configuration in current_config.
         Note:This mib is not supported for VX instance of Virtualization."
    ::= { vrrpCfg 3 }
 
vrrpCurCfgVirtRtrTableEntry OBJECT-TYPE
    SYNTAX  VrrpCurCfgVirtRtrTableEntry
    MAX-ACCESS  not-accessible
    STATUS  current
    DESCRIPTION
        "Information about a VRRP virtual router.
         Note:This mib is not supported for VX instance of Virtualization."
    INDEX   { vrrpCurCfgVirtRtrIndx }
    ::= { vrrpCurCfgVirtRtrTable 1 }
 
VrrpCurCfgVirtRtrTableEntry ::= SEQUENCE {
    vrrpCurCfgVirtRtrIndx         Integer32,
    vrrpCurCfgVirtRtrID           INTEGER,
    vrrpCurCfgVirtRtrAddr         IpAddress,
    vrrpCurCfgVirtRtrIfIndex      Integer32,
    vrrpCurCfgVirtRtrInterval     INTEGER,
    vrrpCurCfgVirtRtrPriority     INTEGER,
    vrrpCurCfgVirtRtrPreempt      INTEGER,
    vrrpCurCfgVirtRtrState        INTEGER,
    vrrpCurCfgVirtRtrSharing      INTEGER,
    vrrpCurCfgVirtRtrTckVirtRtr   INTEGER,
    vrrpCurCfgVirtRtrTckIpIntf    INTEGER,
    vrrpCurCfgVirtRtrTckL4Port    INTEGER,
    vrrpCurCfgVirtRtrTckRServer   INTEGER,
    vrrpCurCfgVirtRtrTckHsrp      INTEGER,
    vrrpCurCfgVirtRtrTckHsrv      INTEGER,
    vrrpCurCfgVirtRtrTckVlanPort  INTEGER,
    vrrpCurCfgVirtRtrVersion      INTEGER,
    vrrpCurCfgVirtRtrIpv6Addr     DisplayString,
    vrrpCurCfgVirtRtrIpv6Interval INTEGER,
    vrrpCurCfgVirtRtrOspfCost     INTEGER,
    vrrpCurCfgVirtRtrTckSwExt      INTEGER,
    vrrpCurCfgVirtRtrTckIslPort      INTEGER
    }

vrrpCurCfgVirtRtrIndx OBJECT-TYPE
    SYNTAX  Integer32
    MAX-ACCESS  read-only
    STATUS  current
    DESCRIPTION
        "The VRRP virtual router table index."
    ::= { vrrpCurCfgVirtRtrTableEntry 1 }

vrrpCurCfgVirtRtrID OBJECT-TYPE
    SYNTAX  INTEGER (1..1024)
    MAX-ACCESS  read-only
    STATUS  current 
    DESCRIPTION
        "The VRRP virtual router identifier."
    ::= { vrrpCurCfgVirtRtrTableEntry 2 }

vrrpCurCfgVirtRtrAddr OBJECT-TYPE
    SYNTAX  IpAddress
    MAX-ACCESS  read-only
    STATUS  current
    DESCRIPTION
        "The VRRP virtual router IP address."
    ::= { vrrpCurCfgVirtRtrTableEntry 3 }

vrrpCurCfgVirtRtrIfIndex OBJECT-TYPE
    SYNTAX  Integer32
    MAX-ACCESS  read-only
    STATUS  current
    DESCRIPTION
        "The IfIndex that the VRRP virtual router is representing."
    ::= { vrrpCurCfgVirtRtrTableEntry 4 }

vrrpCurCfgVirtRtrInterval OBJECT-TYPE
    SYNTAX  INTEGER (1..255)
    MAX-ACCESS  read-only
    STATUS  current
    DESCRIPTION
        "The time interval between VRRP advertisements in seconds."
    ::= { vrrpCurCfgVirtRtrTableEntry 5 }

vrrpCurCfgVirtRtrPriority OBJECT-TYPE
    SYNTAX  INTEGER (1..254)
    MAX-ACCESS  read-only
    STATUS  current
    DESCRIPTION
        "The priority value to be used by the specified VRRP virtual routers."
    ::= { vrrpCurCfgVirtRtrTableEntry 6 }

vrrpCurCfgVirtRtrPreempt OBJECT-TYPE
    SYNTAX  INTEGER {
        enabled(1),
        disabled(2),
        unsupported(2147483647)
        }
    MAX-ACCESS  read-only
    STATUS  current
    DESCRIPTION
        "This is for controlling whether a higher priority Backup
          VRRP virtual router preempts a low priority Master.

          enabled(1)  - allow preemption
          disabled(2) - prohibit preemption"
    ::= { vrrpCurCfgVirtRtrTableEntry 7 }

vrrpCurCfgVirtRtrState OBJECT-TYPE
    SYNTAX  INTEGER {
        enabled(1),
        disabled(2),
        unsupported(2147483647)
        }
    MAX-ACCESS  read-only
    STATUS  current
    DESCRIPTION
        "Enable or disable the VRRP virtual router."
    ::= { vrrpCurCfgVirtRtrTableEntry 8 }

vrrpCurCfgVirtRtrSharing OBJECT-TYPE
    SYNTAX  INTEGER {
        enabled(1),
        disabled(2),
        unsupported(2147483647)
        }
    MAX-ACCESS  read-only
    STATUS  current
    DESCRIPTION
        "Enable or disable load sharing of non-master virtual router."
    ::= { vrrpCurCfgVirtRtrTableEntry 9 }

vrrpCurCfgVirtRtrTckVirtRtr OBJECT-TYPE
    SYNTAX  INTEGER {
        enabled(1),
        disabled(2),
        unsupported(2147483647)
        }
    MAX-ACCESS  read-only
    STATUS  current
    DESCRIPTION
        "Enable or disable tracking other virtual routers for priority 
         adjustment. The priority increment is defined 
         in vrrpCurCfgGenTckVirtRtrInc."
    ::= { vrrpCurCfgVirtRtrTableEntry 10 }

vrrpCurCfgVirtRtrTckIpIntf OBJECT-TYPE
    SYNTAX  INTEGER {
        enabled(1),
        disabled(2),
        unsupported(2147483647)
        }
    MAX-ACCESS  read-only
    STATUS  current
    DESCRIPTION
        "Enable or disable tracking other router interfaces for 
	 priority adjustment. The priority increment is defined 
	 in vrrpCurCfgGenTckIpIntfInc."
    ::= { vrrpCurCfgVirtRtrTableEntry 11 }

vrrpCurCfgVirtRtrTckVlanPort OBJECT-TYPE
    SYNTAX  INTEGER {
        enabled(1),
        disabled(2),
        unsupported(2147483647)
        }
    MAX-ACCESS  read-only
    STATUS  current
    DESCRIPTION
        "Enable or disable tracking port state of VLAN ports 
	 for priority adjustment. The priority increment is 
	 defined in vrrpCurCfgGenTckVlanPortInc."
    ::= { vrrpCurCfgVirtRtrTableEntry 12 }

vrrpCurCfgVirtRtrTckL4Port OBJECT-TYPE
    SYNTAX  INTEGER {
        enabled(1),
        disabled(2),
        unsupported(2147483647)
        }
    MAX-ACCESS  read-only
    STATUS  current
    DESCRIPTION
        "Enable or disable tracking Layer 4 port states for 
	 priority adjustment.  the priority increment is defined 
	 in vrrpCurCfgGenTckL4PortInc.  This is applied when 
	 virtual server is configured as a VRRP virtual router."
    ::= { vrrpCurCfgVirtRtrTableEntry 13 }

vrrpCurCfgVirtRtrTckRServer OBJECT-TYPE
    SYNTAX  INTEGER {
        enabled(1),
        disabled(2),
        unsupported(2147483647)
        }
    MAX-ACCESS  read-only
    STATUS  current
    DESCRIPTION
        "Enable or disable tracking real server states for 
	 priority adjustment.  the priority increment is defined 
	 in vrrpCurCfgGenTckRServerInc.  This is applied when 
	 virtual server is configured as a VRRP virtual router."
    ::= { vrrpCurCfgVirtRtrTableEntry 14 }

vrrpCurCfgVirtRtrTckHsrp OBJECT-TYPE
    SYNTAX  INTEGER {
        enabled(1),
        disabled(2),
        unsupported(2147483647)
        }
    MAX-ACCESS  read-only
    STATUS  current
    DESCRIPTION
        "Enable or disable tracking HSRP advertisements for 
	 priority adjustment.  the priority increment is defined 
	 in vrrpCurCfgGenTckHsrpInc.  This is applied when 
	 virtual server is configured as a VRRP virtual router."
    ::= { vrrpCurCfgVirtRtrTableEntry 15 }

vrrpCurCfgVirtRtrTckHsrv OBJECT-TYPE
        SYNTAX  INTEGER {
                enabled(1),
                disabled(2),
                unsupported(2147483647)
                }
        MAX-ACCESS  read-only
        STATUS  current
        DESCRIPTION
                "Enable or disable tracking HSRP advertisements by VLAN for
                 priority adjustment.  The priority increment is defined
                 in vrrpCurCfgGenTckHsrvInc.  This is applied when
                 virtual server is configured as a VRRP virtual router."
        ::= { vrrpCurCfgVirtRtrTableEntry 16 }

vrrpCurCfgVirtRtrVersion OBJECT-TYPE
     SYNTAX  INTEGER {
         v4(1),
         v6(2),
         unsupported(2147483647)
        }
     MAX-ACCESS  read-only
     STATUS  current
     DESCRIPTION
         "The VRRP virtual router IP Version."
     ::= { vrrpCurCfgVirtRtrTableEntry 17 }

vrrpCurCfgVirtRtrIpv6Addr OBJECT-TYPE
    SYNTAX   DisplayString (SIZE(0..40))
    MAX-ACCESS  read-only
    STATUS  current
    DESCRIPTION
        "The IPv6 address of the virtual router. Address should be 4-byte
         haxadecimal colon notation.
         Valid IPv6 address should be in any of the following forms
         xxxx:xxxx:xxxx:xxxx:xxxx:xxxx:xxxx:xxxx or
         xxxx::xxxx:xxxx:xxxx:xxxx or ::xxxx"
    ::= { vrrpCurCfgVirtRtrTableEntry 18 }

vrrpCurCfgVirtRtrIpv6Interval OBJECT-TYPE
    SYNTAX  INTEGER (1..4095)
    MAX-ACCESS  read-only
    STATUS  current
    DESCRIPTION
        "The time interval between IPv6 VRRP advertisements in centiseconds."
    ::= { vrrpCurCfgVirtRtrTableEntry 19 }

vrrpCurCfgVirtRtrTckSwExt OBJECT-TYPE
    SYNTAX  INTEGER {
        enabled(1),
        disabled(2),
        unsupported(2147483647)
        }
    MAX-ACCESS  read-only
    STATUS  current
    DESCRIPTION
        "Enable or disable tracking the Switch Extension availability for
         priority adjustment. The priority increment is defined
         in vrrpCurCfgGenTckSwExtInc."
    ::= { vrrpCurCfgVirtRtrTableEntry 21 }

vrrpCurCfgVirtRtrOspfCost OBJECT-TYPE
    SYNTAX  INTEGER (1..65535)
    MAX-ACCESS  read-only
    STATUS  current
    DESCRIPTION
        "OSPF cost adjustment"
    ::= { vrrpCurCfgVirtRtrTableEntry 20 }

vrrpCurCfgVirtRtrTckIslPort OBJECT-TYPE
    SYNTAX  INTEGER {
        include(1),
        exclude(2),
        unsupported(2147483647)
        }
    MAX-ACCESS  read-only
    STATUS  current
    DESCRIPTION
        "Include or exclude ISL ports in tracking."
    ::= { vrrpCurCfgVirtRtrTableEntry 22 }

vrrpNewCfgVirtRtrTable OBJECT-TYPE
    SYNTAX  SEQUENCE OF VrrpNewCfgVirtRtrTableEntry
    MAX-ACCESS  not-accessible
    STATUS  current
    DESCRIPTION
        "The table of VRRP virtual routers configuration in current_config.
         Note:This mib is not supported for VX instance of Virtualization."
    ::= { vrrpCfg 4 }

vrrpNewCfgVirtRtrTableEntry OBJECT-TYPE
    SYNTAX  VrrpNewCfgVirtRtrTableEntry
    MAX-ACCESS  not-accessible
    STATUS  current
    DESCRIPTION
        "Information about a VRRP virtual router.
         Note:This mib is not supported for VX instance of Virtualization."
    INDEX   { vrrpNewCfgVirtRtrIndx }
    ::= { vrrpNewCfgVirtRtrTable 1 }

VrrpNewCfgVirtRtrTableEntry ::= SEQUENCE {
    vrrpNewCfgVirtRtrIndx         Integer32,
    vrrpNewCfgVirtRtrID           INTEGER,
    vrrpNewCfgVirtRtrAddr         IpAddress,
    vrrpNewCfgVirtRtrIfIndex      Integer32,
    vrrpNewCfgVirtRtrInterval     INTEGER,
    vrrpNewCfgVirtRtrPriority     INTEGER,
    vrrpNewCfgVirtRtrPreempt      INTEGER,
    vrrpNewCfgVirtRtrState        INTEGER,
    vrrpNewCfgVirtRtrDelete       INTEGER,
    vrrpNewCfgVirtRtrSharing      INTEGER,
    vrrpNewCfgVirtRtrTckVirtRtr   INTEGER,
    vrrpNewCfgVirtRtrTckIpIntf    INTEGER,
    vrrpNewCfgVirtRtrTckL4Port    INTEGER,
    vrrpNewCfgVirtRtrTckRServer   INTEGER,
    vrrpNewCfgVirtRtrTckHsrp      INTEGER,
    vrrpNewCfgVirtRtrTckHsrv      INTEGER,
    vrrpNewCfgVirtRtrTckVlanPort  INTEGER,
    vrrpNewCfgVirtRtrVersion      INTEGER,
    vrrpNewCfgVirtRtrIpv6Addr     DisplayString,
    vrrpNewCfgVirtRtrIpv6Interval INTEGER,
    vrrpNewCfgVirtRtrOspfCost     INTEGER,
    vrrpNewCfgVirtRtrTckSwExt      INTEGER,
    vrrpNewCfgVirtRtrTckIslPort    INTEGER
    }

vrrpNewCfgVirtRtrIndx OBJECT-TYPE
    SYNTAX  Integer32
    MAX-ACCESS  read-only
    STATUS  current
    DESCRIPTION
        "The VRRP virtual router table index."
    ::= { vrrpNewCfgVirtRtrTableEntry 1 }

vrrpNewCfgVirtRtrID OBJECT-TYPE
    SYNTAX  INTEGER (1..1024)
    MAX-ACCESS  read-create
    STATUS  current 
    DESCRIPTION
        "The VRRP virtual router identifier."
    ::= { vrrpNewCfgVirtRtrTableEntry 2 }

vrrpNewCfgVirtRtrAddr OBJECT-TYPE
    SYNTAX  IpAddress
    MAX-ACCESS  read-create
    STATUS  current
    DESCRIPTION
        "The VRRP virtual router IP address."
    ::= { vrrpNewCfgVirtRtrTableEntry 3 }

vrrpNewCfgVirtRtrIfIndex OBJECT-TYPE
    SYNTAX  Integer32
    MAX-ACCESS  read-create
    STATUS  current
    DESCRIPTION
        "The IfIndex that the VRRP virtual router is representing."
   ::= { vrrpNewCfgVirtRtrTableEntry 4 }

vrrpNewCfgVirtRtrInterval OBJECT-TYPE
    SYNTAX  INTEGER (1..255)
    MAX-ACCESS  read-create
    STATUS  current
    DESCRIPTION
        "The time interval between VRRP advertisements in seconds."
    ::= { vrrpNewCfgVirtRtrTableEntry 5 }

vrrpNewCfgVirtRtrPriority OBJECT-TYPE
    SYNTAX  INTEGER (1..254)
    MAX-ACCESS  read-create
    STATUS  current
    DESCRIPTION
        "The priority value to be used by the specified VRRP virtual router."
    ::= { vrrpNewCfgVirtRtrTableEntry 6 }

vrrpNewCfgVirtRtrPreempt OBJECT-TYPE
    SYNTAX  INTEGER {
        enabled(1),
        disabled(2),
        unsupported(2147483647)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrTableEntry 7 }

vrrpNewCfgVirtRtrState OBJECT-TYPE
    SYNTAX  INTEGER {
        enabled(1),
        disabled(2),
        unsupported(2147483647)
        }
    MAX-ACCESS  read-create
    STATUS  current
    DESCRIPTION
        "Enable or disable the VRRP virtual router."
    ::= { vrrpNewCfgVirtRtrTableEntry 8 }

vrrpNewCfgVirtRtrDelete OBJECT-TYPE
    SYNTAX  INTEGER { 
	other(1),
        delete(2),
        unsupported(2147483647)
	}
    MAX-ACCESS  read-create
    STATUS  current
    DESCRIPTION
        "When set to the value of 2 (delete), the entire row is deleted. 
         When read, other(1) is returned. Setting the value to anything 
         other than delete(2) has no effect on the state of the row."
    ::= { vrrpNewCfgVirtRtrTableEntry 9 }

vrrpNewCfgVirtRtrSharing OBJECT-TYPE
    SYNTAX  INTEGER {
        enabled(1),
        disabled(2),
        unsupported(2147483647)
        }
    MAX-ACCESS  read-create
    STATUS  current
    DESCRIPTION
        "Enable or disable load sharing of non-master virtual router."
    ::= { vrrpNewCfgVirtRtrTableEntry 10 }

vrrpNewCfgVirtRtrTckVirtRtr OBJECT-TYPE
    SYNTAX  INTEGER {
        enabled(1),
        disabled(2),
        unsupported(2147483647)
        }
    MAX-ACCESS  read-create
    STATUS  current
    DESCRIPTION
        "Enable or disable tracking other virtual routers for 
	 priority adjustment.  the priority increment is defined 
	 in vrrpNewCfgGenTckVirtRtrInc."
    ::= { vrrpNewCfgVirtRtrTableEntry 11 }

vrrpNewCfgVirtRtrTckIpIntf OBJECT-TYPE
    SYNTAX  INTEGER {
        enabled(1),
        disabled(2),
        unsupported(2147483647)
        }
     MAX-ACCESS  read-create
     STATUS  current
     DESCRIPTION
         "Enable or disable tracking other router interfaces for 
	  priority adjustment.  the priority increment is defined 
	  in vrrpNewCfgGenTckIpIntfInc."
    ::= { vrrpNewCfgVirtRtrTableEntry 12 }

vrrpNewCfgVirtRtrTckVlanPort OBJECT-TYPE
    SYNTAX  INTEGER {
        enabled(1),
        disabled(2),
        unsupported(2147483647)
        }
    MAX-ACCESS  read-create
    STATUS  current
    DESCRIPTION
        "Enable or disable tracking port state of VLAN ports 
	 for priority adjustment.  the priority increment is 
	 defined in vrrpNewCfgGenTckVlanPortInc."
    ::= { vrrpNewCfgVirtRtrTableEntry 13 }

vrrpNewCfgVirtRtrTckL4Port OBJECT-TYPE
    SYNTAX  INTEGER {
        enabled(1),
        disabled(2),
        unsupported(2147483647)
        }
     MAX-ACCESS  read-create
     STATUS  current
     DESCRIPTION
         "Enable or disable tracking Layer 4 port states for 
	  priority adjustment.  the priority increment is defined 
	  in vrrpNewCfgGenTckL4PortInc.  This is applied when 
	  virtual server is configured as a VRRP virtual router."
    ::= { vrrpNewCfgVirtRtrTableEntry 14 }

vrrpNewCfgVirtRtrTckRServer OBJECT-TYPE
    SYNTAX  INTEGER {
        enabled(1),
        disabled(2),
        unsupported(2147483647)
        }
    MAX-ACCESS  read-create
    STATUS  current
    DESCRIPTION
        "Enable or disable tracking real server states for 
	 priority adjustment.  the priority increment is defined 
	 in vrrpNewCfgGenTckRServerInc.  This is applied when 
	 virtual server is configured as a VRRP virtual router."
    ::= { vrrpNewCfgVirtRtrTableEntry 15 }

vrrpNewCfgVirtRtrTckHsrp OBJECT-TYPE
    SYNTAX  INTEGER {
        enabled(1),
        disabled(2),
        unsupported(2147483647)
        }
    MAX-ACCESS  read-create
    STATUS  current
    DESCRIPTION
        "Enable or disable tracking HSRP advertisements for 
	 priority adjustment.  the priority increment is defined 
	 in vrrpNewCfgGenTckHsrpInc.  This is applied when 
	 virtual server is configured as a VRRP virtual router."
    ::= { vrrpNewCfgVirtRtrTableEntry 16 }

vrrpNewCfgVirtRtrTckHsrv OBJECT-TYPE
        SYNTAX  INTEGER {
                enabled(1),
                disabled(2),
                unsupported(2147483647)
                }
        MAX-ACCESS  read-create
        STATUS  current
        DESCRIPTION
                "Enable or disable tracking HSRP by VLAN advertisements for
                 priority adjustment.  The priority increment is defined
                 in vrrpNewCfgGenTckHsrvInc.  This is applied when
                 virtual server is configured as a VRRP virtual router."
        ::= { vrrpNewCfgVirtRtrTableEntry 17 }

vrrpNewCfgVirtRtrVersion OBJECT-TYPE
     SYNTAX  INTEGER {
         v4(1),
         v6(2),
         unsupported(2147483647)
        }
     MAX-ACCESS  read-create
     STATUS  current
     DESCRIPTION
         "The VRRP virtual router IP Version."
     ::= { vrrpNewCfgVirtRtrTableEntry 18 }

vrrpNewCfgVirtRtrIpv6Addr OBJECT-TYPE
    SYNTAX   DisplayString (SIZE(0..40))
    MAX-ACCESS  read-create
    STATUS  current
    DESCRIPTION
        "The IPv6 address of the virtual router. Address should be 4-byte
         haxadecimal colon notation.
         Valid IPv6 address should be in any of the following forms
         xxxx:xxxx:xxxx:xxxx:xxxx:xxxx:xxxx:xxxx or
         xxxx::xxxx:xxxx:xxxx:xxxx or ::xxxx"
    ::= { vrrpNewCfgVirtRtrTableEntry 19 }

vrrpNewCfgVirtRtrIpv6Interval OBJECT-TYPE
    SYNTAX  INTEGER (1..4095)
    MAX-ACCESS  read-create
    STATUS  current
    DESCRIPTION
        "The time interval between IPv6 VRRP advertisements in centiseconds."
    ::= { vrrpNewCfgVirtRtrTableEntry 20 }

vrrpNewCfgVirtRtrOspfCost OBJECT-TYPE
    SYNTAX  INTEGER (0..65535)
    MAX-ACCESS  read-create
    STATUS  current
    DESCRIPTION
        "OSPF Cost Adjustment"
    ::= { vrrpNewCfgVirtRtrTableEntry 21 }

vrrpNewCfgVirtRtrTckSwExt OBJECT-TYPE
    SYNTAX  INTEGER {
        enabled(1),
        disabled(2),
        unsupported(2147483647)
        }
    MAX-ACCESS  read-create
    STATUS  current
    DESCRIPTION
        "Enable or disable tracking Switch Extension availability for
         priority adjustment. The priority increment is defined
         in vrrpNewCfgGenTckSwExtInc."
    ::= { vrrpNewCfgVirtRtrTableEntry 22 }

vrrpNewCfgVirtRtrTckIslPort OBJECT-TYPE
    SYNTAX  INTEGER {
        include(1),
        exclude(2),
        unsupported(2147483647)
        }
     MAX-ACCESS  read-create
     STATUS  current
     DESCRIPTION
        "Include or exclude ISL ports in tracking."
    ::= { vrrpNewCfgVirtRtrTableEntry 23 }
-- VRRP Interface Table

vrrpIfTableMaxSize OBJECT-TYPE
    SYNTAX Integer32
    MAX-ACCESS read-only
    STATUS current
    DESCRIPTION
        "The maximum number of entries in VRRP interface table.
         Note:This mib is not supported for VX instance of Virtualization."
    ::= { vrrpCfg 5 }

vrrpCurCfgIfTable OBJECT-TYPE
    SYNTAX  SEQUENCE OF VrrpCurCfgIfTableEntry
    MAX-ACCESS  not-accessible
    STATUS  current
    DESCRIPTION
        "The table of VRRP interface configuration in current_config.
         Note:This mib is not supported for VX instance of Virtualization."
    ::= { vrrpCfg 6 }
 
vrrpCurCfgIfTableEntry OBJECT-TYPE
    SYNTAX  VrrpCurCfgIfTableEntry
    MAX-ACCESS  not-accessible
    STATUS  current
    DESCRIPTION
        "Information about a VRRP interface.
         Note:This mib is not supported for VX instance of Virtualization."
    INDEX   { vrrpCurCfgIfIndx }
    ::= { vrrpCurCfgIfTable 1 }
 
VrrpCurCfgIfTableEntry ::= SEQUENCE {
    vrrpCurCfgIfIndx         Integer32,
    vrrpCurCfgIfAuthType     INTEGER,
    vrrpCurCfgIfPasswd       DisplayString,
    vrrpCurCfgIfIpAddr       IpAddress
    }

vrrpCurCfgIfIndx OBJECT-TYPE
    SYNTAX  Integer32
    MAX-ACCESS  read-only
    STATUS  current
    DESCRIPTION
        "The VRRP interface index.  This is equivalent to IfIndex."
    ::= { vrrpCurCfgIfTableEntry 1 }

vrrpCurCfgIfAuthType OBJECT-TYPE
    SYNTAX  INTEGER {
        none(1),
        simple-text-password(2),
        unsupported(2147483647)
        }
    MAX-ACCESS  read-only
    STATUS  current
    DESCRIPTION
        "Type of authentication being used.
	 none(1) - no authentication
	 simple-text-password(2) - use password specified in 
         vrrpCurCfgIfPasswd for authentication."
    ::= { vrrpCurCfgIfTableEntry 2 }

vrrpCurCfgIfPasswd OBJECT-TYPE
    SYNTAX  DisplayString (SIZE(0..8))
    MAX-ACCESS  read-only
    STATUS  current
    DESCRIPTION
        "The password for authentication."
    ::= { vrrpCurCfgIfTableEntry 3 }

vrrpCurCfgIfIpAddr OBJECT-TYPE
    SYNTAX IpAddress
    MAX-ACCESS read-only
    STATUS current
    DESCRIPTION
    "The IP address of the VRRP interface.This is equivalent to ipCurCfgIntfAddr."
    ::= { vrrpCurCfgIfTableEntry 4 }

vrrpNewCfgIfTable OBJECT-TYPE
    SYNTAX  SEQUENCE OF VrrpNewCfgIfTableEntry
    MAX-ACCESS  not-accessible
    STATUS  current
    DESCRIPTION
        "The table of VRRP interface configuration in current_config.
         Note:This mib is not supported for VX instance of Virtualization."
    ::= { vrrpCfg 7 }
 
vrrpNewCfgIfTableEntry OBJECT-TYPE
    SYNTAX  VrrpNewCfgIfTableEntry
    MAX-ACCESS  not-accessible
    STATUS  current
    DESCRIPTION
        "Information about a VRRP interface.
         Note:This mib is not supported for VX instance of Virtualization."
    INDEX   { vrrpNewCfgIfIndx }
    ::= { vrrpNewCfgIfTable 1 }
 
VrrpNewCfgIfTableEntry ::= SEQUENCE {
    vrrpNewCfgIfIndx         Integer32,
    vrrpNewCfgIfAuthType     INTEGER,
    vrrpNewCfgIfPasswd       DisplayString,
    vrrpNewCfgIfDelete       INTEGER
    }

vrrpNewCfgIfIndx OBJECT-TYPE
    SYNTAX  Integer32
    MAX-ACCESS  read-only
    STATUS  current
    DESCRIPTION
        "The VRRP interface index.  This is equivalent to IfIndex."
    ::= { vrrpNewCfgIfTableEntry 1 }

vrrpNewCfgIfAuthType OBJECT-TYPE
    SYNTAX  INTEGER {
        none(1),
        simple-text-password(2),
        unsupported(2147483647)
        }
    MAX-ACCESS  read-create
    STATUS  current
    DESCRIPTION
        "Type of authentication being used.
	 none(1) - no authentication
	 simple-text-password(2) - use password specified in 
         vrrpNewCfgIfPasswd for authentication."
    ::= { vrrpNewCfgIfTableEntry 2 }

vrrpNewCfgIfPasswd OBJECT-TYPE
    SYNTAX  DisplayString (SIZE(0..8))
    MAX-ACCESS  read-create
    STATUS  current
    DESCRIPTION
        "The password for authentication."
    ::= { vrrpNewCfgIfTableEntry 3 }

vrrpNewCfgIfDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than delete(2) has no effect on the state of the row."
    ::= { vrrpNewCfgIfTableEntry 4 }

-- Failover Virtual Router Groups
vrrpVirtRtrGrpTableMaxSize OBJECT-TYPE
    SYNTAX Integer32
    MAX-ACCESS read-only
    STATUS current
    DESCRIPTION
        "The maximum number of entries in VRRP Group table.
         Note:This mib is not supported for VX instance of Virtualization."
    ::= { vrrpCfg 8 }

vrrpCurCfgVirtRtrGrpTable OBJECT-TYPE
    SYNTAX  SEQUENCE OF VrrpCurCfgVirtRtrGrpTableEntry
    MAX-ACCESS  not-accessible
    STATUS  current
    DESCRIPTION
        "The table of VRRP virtual router group in current_config.
         Note:This mib is not supported for VX instance of Virtualization."
    ::= { vrrpCfg 9 }

vrrpCurCfgVirtRtrGrpTableEntry OBJECT-TYPE
    SYNTAX  VrrpCurCfgVirtRtrGrpTableEntry
    MAX-ACCESS  not-accessible
    STATUS  current
    DESCRIPTION
        "Information about a VRRP failover virtual router.
         Note:This mib is not supported for VX instance of Virtualization."
    INDEX   { vrrpCurCfgVirtRtrGrpIndx }
    ::= { vrrpCurCfgVirtRtrGrpTable 1 }

VrrpCurCfgVirtRtrGrpTableEntry ::= SEQUENCE {
    vrrpCurCfgVirtRtrGrpIndx         Integer32,
    vrrpCurCfgVirtRtrGrpID           INTEGER,
    vrrpCurCfgVirtRtrGrpIfIndex      Integer32,
    vrrpCurCfgVirtRtrGrpInterval     INTEGER,
    vrrpCurCfgVirtRtrGrpPriority     INTEGER,
    vrrpCurCfgVirtRtrGrpPreempt      INTEGER,
    vrrpCurCfgVirtRtrGrpState        INTEGER,
    vrrpCurCfgVirtRtrGrpSharing      INTEGER,
    vrrpCurCfgVirtRtrGrpTckVirtRtr   INTEGER,
    vrrpCurCfgVirtRtrGrpTckIpIntf    INTEGER,
    vrrpCurCfgVirtRtrGrpTckVlanPort  INTEGER,
    vrrpCurCfgVirtRtrGrpTckL4Port    INTEGER,
    vrrpCurCfgVirtRtrGrpTckRServer   INTEGER,
    vrrpCurCfgVirtRtrGrpTckHsrp      INTEGER,
    vrrpCurCfgVirtRtrGrpTckHsrv      INTEGER,
    vrrpCurCfgVirtRtrGrpVersion      INTEGER,
    vrrpCurCfgVirtRtrGrpIpv6Interval INTEGER,
    vrrpCurCfgVirtRtrGrpOspfCost     INTEGER,
    vrrpCurCfgVirtRtrGrpTckSwExt      INTEGER,
    vrrpCurCfgVirtRtrGrpTckIslPort    INTEGER
    }
 
vrrpCurCfgVirtRtrGrpIndx OBJECT-TYPE
    SYNTAX  Integer32
    MAX-ACCESS  read-only
    STATUS  current
    DESCRIPTION
        "The VRRP virtual router table index."
    ::= { vrrpCurCfgVirtRtrGrpTableEntry 1 }
 
vrrpCurCfgVirtRtrGrpID OBJECT-TYPE
    SYNTAX  INTEGER (1..1024)
    MAX-ACCESS  read-only
    STATUS  current 
    DESCRIPTION
        "The VRRP virtual router identifier."
    ::= { vrrpCurCfgVirtRtrGrpTableEntry 2 }
 
vrrpCurCfgVirtRtrGrpIfIndex OBJECT-TYPE
    SYNTAX  Integer32
    MAX-ACCESS  read-only
    STATUS  current
    DESCRIPTION
        "The IfIndex that the VRRP virtual router is representing."
    ::= { vrrpCurCfgVirtRtrGrpTableEntry 3 }

vrrpCurCfgVirtRtrGrpInterval OBJECT-TYPE
    SYNTAX  INTEGER (1..255)
    MAX-ACCESS  read-only
    STATUS  current
    DESCRIPTION
        "The time interval between VRRP advertisements in seconds."
    ::= { vrrpCurCfgVirtRtrGrpTableEntry 4 }

vrrpCurCfgVirtRtrGrpPriority OBJECT-TYPE
    SYNTAX  INTEGER (1..254)
    MAX-ACCESS  read-only
    STATUS  current
    DESCRIPTION
        "The priority value to be used by the specified VRRP virtual routers."
    ::= { vrrpCurCfgVirtRtrGrpTableEntry 5 }

vrrpCurCfgVirtRtrGrpPreempt OBJECT-TYPE
    SYNTAX  INTEGER {
        enabled(1),
        disabled(2),
        unsupported(2147483647)
        }
    MAX-ACCESS  read-only
    STATUS  current
    DESCRIPTION
        "This is for controlling whether a higher priority Backup
         VRRP virtual router preempts a low priority Master.

         enabled(1)  - allow preemption
         disabled(2) - prohibit preemption"
   ::= { vrrpCurCfgVirtRtrGrpTableEntry 6 }

vrrpCurCfgVirtRtrGrpState OBJECT-TYPE
    SYNTAX  INTEGER {
        enabled(1),
        disabled(2),
        unsupported(2147483647)
        }
    MAX-ACCESS  read-only
    STATUS  current
    DESCRIPTION
        "Enable or disable the VRRP virtual router."
    ::= { vrrpCurCfgVirtRtrGrpTableEntry 7 }

vrrpCurCfgVirtRtrGrpSharing OBJECT-TYPE
    SYNTAX  INTEGER {
        enabled(1),
        disabled(2),
        unsupported(2147483647)
        }
    MAX-ACCESS  read-only
    STATUS  current
    DESCRIPTION
        "Enable or disable load sharing of non-master virtual router."
    ::= { vrrpCurCfgVirtRtrGrpTableEntry 8 }

vrrpCurCfgVirtRtrGrpTckVirtRtr OBJECT-TYPE
    SYNTAX  INTEGER {
        enabled(1),
        disabled(2),
        unsupported(2147483647)
        }
    MAX-ACCESS  read-only
    STATUS  current
    DESCRIPTION
        "Enable or disable tracking other virtual routers for
         priority adjustment.  the priority increment is defined
         in vrrpCurCfgGenTckVirtRtrInc."
    ::= { vrrpCurCfgVirtRtrGrpTableEntry 9 }

vrrpCurCfgVirtRtrGrpTckIpIntf OBJECT-TYPE
    SYNTAX  INTEGER {
        enabled(1),
        disabled(2),
        unsupported(2147483647)
        }
    MAX-ACCESS  read-only
    STATUS  current
    DESCRIPTION
        "Enable or disable tracking other router interfaces for
         priority adjustment.  the priority increment is defined
         in vrrpCurCfgGenTckIpIntfInc."
    ::= { vrrpCurCfgVirtRtrGrpTableEntry 10 }

vrrpCurCfgVirtRtrGrpTckVlanPort OBJECT-TYPE
    SYNTAX  INTEGER {
        enabled(1),
        disabled(2),
        unsupported(2147483647)
        }
    MAX-ACCESS  read-only
    STATUS  current
    DESCRIPTION
        "Enable or disable tracking port state of VLAN ports
         for priority adjustment.  the priority increment is
         defined in vrrpCurCfgGenTckVlanPortInc."
    ::= { vrrpCurCfgVirtRtrGrpTableEntry 11 }

vrrpCurCfgVirtRtrGrpTckL4Port OBJECT-TYPE
    SYNTAX  INTEGER {
        enabled(1),
        disabled(2),
        unsupported(2147483647)
        }
    MAX-ACCESS  read-only
    STATUS  current
    DESCRIPTION
        "Enable or disable tracking Layer 4 port states for
         priority adjustment.  the priority increment is defined
         in vrrpCurCfgGenTckL4PortInc.  This is applied when
         virtual server is configured as a VRRP virtual router."
    ::= { vrrpCurCfgVirtRtrGrpTableEntry 12 }

vrrpCurCfgVirtRtrGrpTckRServer OBJECT-TYPE
    SYNTAX  INTEGER {
        enabled(1),
        disabled(2),
        unsupported(2147483647)
        }
    MAX-ACCESS  read-only
    STATUS  current
    DESCRIPTION
        "Enable or disable tracking real server states for
         priority adjustment.  the priority increment is defined
         in vrrpCurCfgGenTckRServerInc.  This is applied when
         virtual server is configured as a VRRP virtual router."
    ::= { vrrpCurCfgVirtRtrGrpTableEntry 13 }

vrrpCurCfgVirtRtrGrpTckHsrp OBJECT-TYPE
    SYNTAX  INTEGER {
        enabled(1),
        disabled(2),
        unsupported(2147483647)
        }
    MAX-ACCESS  read-only
    STATUS  current
    DESCRIPTION
        "Enable or disable tracking HSRP advertisements for
         priority adjustment.  the priority increment is defined
         in vrrpCurCfgGenTckHsrpInc.  This is applied when
         virtual server is configured as a VRRP virtual router."
    ::= { vrrpCurCfgVirtRtrGrpTableEntry 14 }

vrrpCurCfgVirtRtrGrpTckHsrv OBJECT-TYPE
        SYNTAX  INTEGER {
                enabled(1),
                disabled(2),
                unsupported(2147483647)
                }
        MAX-ACCESS  read-only
        STATUS  current
        DESCRIPTION
                "Enable or disable tracking HSRP by VLAN advertisements for
                 priority adjustment.  The priority increment is defined
                 in vrrpCurCfgGenTckHsrvInc.  This is applied when
                 virtual server is configured as a VRRP virtual router."
        ::= { vrrpCurCfgVirtRtrGrpTableEntry 15 }

vrrpCurCfgVirtRtrGrpVersion OBJECT-TYPE
    SYNTAX  INTEGER {
        v4(1),
        v6(2),
        unsupported(2147483647)
    }
    MAX-ACCESS  read-only
    STATUS  current
    DESCRIPTION
        "The VRRP virtual router group IP Version."
    ::= { vrrpCurCfgVirtRtrGrpTableEntry 16 }

vrrpCurCfgVirtRtrGrpIpv6Interval OBJECT-TYPE
    SYNTAX INTEGER (1..4095)
    MAX-ACCESS read-only
    STATUS current
    DESCRIPTION
        "The time interval between IPv6 VRRP advertisements in centiseconds."
    ::= { vrrpCurCfgVirtRtrGrpTableEntry 17 }

vrrpCurCfgVirtRtrGrpOspfCost OBJECT-TYPE
    SYNTAX INTEGER (0..65535)
    MAX-ACCESS read-only
    STATUS current
    DESCRIPTION
        "OSPF Cost Adjustment"
    ::= { vrrpCurCfgVirtRtrGrpTableEntry 18 }

vrrpCurCfgVirtRtrGrpTckSwExt OBJECT-TYPE
    SYNTAX  INTEGER {
        enabled(1),
        disabled(2),
        unsupported(2147483647)
        }
    MAX-ACCESS  read-only
    STATUS  current
    DESCRIPTION
        "Enable or disable tracking Switch Extension availability for
         priority adjustment. The priority increment is defined
         in vrrpNewCfgGenTckSwExtInc."
    ::= { vrrpCurCfgVirtRtrGrpTableEntry 19 }

vrrpCurCfgVirtRtrGrpTckIslPort OBJECT-TYPE
    SYNTAX  INTEGER {
        include(1),
        exclude(2),
        unsupported(2147483647)
        }
    MAX-ACCESS  read-only
    STATUS  current
    DESCRIPTION
        "Include or exclude ISL ports in tracking."
    ::= { vrrpCurCfgVirtRtrGrpTableEntry 20 }

vrrpNewCfgVirtRtrGrpTable OBJECT-TYPE
    SYNTAX  SEQUENCE OF VrrpNewCfgVirtRtrGrpTableEntry
    MAX-ACCESS  not-accessible
    STATUS  current
    DESCRIPTION
        "The table of VRRP virtual router group configuration in new_config.
         Note:This mib is not supported for VX instance of Virtualization."
    ::= { vrrpCfg 10 }

vrrpNewCfgVirtRtrGrpTableEntry OBJECT-TYPE
    SYNTAX  VrrpNewCfgVirtRtrGrpTableEntry
    MAX-ACCESS  not-accessible
    STATUS  current
    DESCRIPTION
        "Information about a VRRP failover virtual router.
         Note:This mib is not supported for VX instance of Virtualization."
    INDEX   { vrrpNewCfgVirtRtrGrpIndx }
    ::= { vrrpNewCfgVirtRtrGrpTable 1 }
 
VrrpNewCfgVirtRtrGrpTableEntry ::= SEQUENCE {
    vrrpNewCfgVirtRtrGrpIndx         Integer32,
    vrrpNewCfgVirtRtrGrpID           INTEGER,
    vrrpNewCfgVirtRtrGrpIfIndex      Integer32,
    vrrpNewCfgVirtRtrGrpInterval     INTEGER,
    vrrpNewCfgVirtRtrGrpPriority     INTEGER,
    vrrpNewCfgVirtRtrGrpPreempt      INTEGER,
    vrrpNewCfgVirtRtrGrpState        INTEGER,
    vrrpNewCfgVirtRtrGrpDelete       INTEGER,
    vrrpNewCfgVirtRtrGrpSharing      INTEGER,
    vrrpNewCfgVirtRtrGrpTckVirtRtr   INTEGER,
    vrrpNewCfgVirtRtrGrpTckIpIntf    INTEGER,
    vrrpNewCfgVirtRtrGrpTckVlanPort  INTEGER,
    vrrpNewCfgVirtRtrGrpTckL4Port    INTEGER,
    vrrpNewCfgVirtRtrGrpTckRServer   INTEGER,
    vrrpNewCfgVirtRtrGrpTckHsrp      INTEGER,
    vrrpNewCfgVirtRtrGrpTckHsrv      INTEGER,
    vrrpNewCfgVirtRtrGrpVersion      INTEGER,
    vrrpNewCfgVirtRtrGrpIpv6Interval INTEGER,
    vrrpNewCfgVirtRtrGrpOspfCost     INTEGER,
    vrrpNewCfgVirtRtrGrpTckSwExt     INTEGER,
    vrrpNewCfgVirtRtrGrpTckIslPort     INTEGER
    }
 
vrrpNewCfgVirtRtrGrpIndx OBJECT-TYPE
    SYNTAX  Integer32
    MAX-ACCESS  read-only
    STATUS  current
    DESCRIPTION
        "The VRRP virtual router table index."
    ::= { vrrpNewCfgVirtRtrGrpTableEntry 1 }
 
vrrpNewCfgVirtRtrGrpID OBJECT-TYPE
    SYNTAX  INTEGER (1..1024)
    MAX-ACCESS  read-create
    STATUS  current 
    DESCRIPTION
        "The VRRP virtual router identifier."
    ::= { vrrpNewCfgVirtRtrGrpTableEntry 2 }
 
vrrpNewCfgVirtRtrGrpIfIndex OBJECT-TYPE
    SYNTAX  Integer32
    MAX-ACCESS  read-create
    STATUS  current
    DESCRIPTION
        "The IfIndex that the VRRP virtual router is representing."
    ::= { vrrpNewCfgVirtRtrGrpTableEntry 3 }

vrrpNewCfgVirtRtrGrpInterval OBJECT-TYPE
    SYNTAX  INTEGER (1..255)
    MAX-ACCESS  read-create
    STATUS  current
    DESCRIPTION
        "The time interval between VRRP advertisements in seconds."
    ::= { vrrpNewCfgVirtRtrGrpTableEntry 4 }

vrrpNewCfgVirtRtrGrpPriority OBJECT-TYPE
    SYNTAX  INTEGER (1..254)
    MAX-ACCESS  read-create
    STATUS  current
    DESCRIPTION
        "The priority value to be used by the specified VRRP virtual router."
    ::= { vrrpNewCfgVirtRtrGrpTableEntry 5 }

vrrpNewCfgVirtRtrGrpPreempt OBJECT-TYPE
    SYNTAX  INTEGER {
        enabled(1),
        disabled(2),
        unsupported(2147483647)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrGrpTableEntry 6 }

vrrpNewCfgVirtRtrGrpState OBJECT-TYPE
    SYNTAX  INTEGER {
        enabled(1),
        disabled(2),
        unsupported(2147483647)
        }
    MAX-ACCESS  read-create
    STATUS  current
    DESCRIPTION
        "Enable or disable the VRRP virtual router."
    ::= { vrrpNewCfgVirtRtrGrpTableEntry 7 }

vrrpNewCfgVirtRtrGrpDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than delete(2) has no effect on the state of the row."
    ::= { vrrpNewCfgVirtRtrGrpTableEntry 8 }

vrrpNewCfgVirtRtrGrpSharing OBJECT-TYPE
    SYNTAX  INTEGER {
        enabled(1),
        disabled(2),
        unsupported(2147483647)
        }
    MAX-ACCESS  read-create
    STATUS  current
    DESCRIPTION
        "Enable or disable load sharing of non-master virtual router."
    ::= { vrrpNewCfgVirtRtrGrpTableEntry 9 }

vrrpNewCfgVirtRtrGrpTckVirtRtr OBJECT-TYPE
    SYNTAX  INTEGER {
        enabled(1),
        disabled(2),
        unsupported(2147483647)
        }
    MAX-ACCESS  read-create
    STATUS  current
    DESCRIPTION
        "Enable or disable tracking other virtual routers for
         priority adjustment.  the priority increment is defined
         in vrrpNewCfgGenTckVirtRtrInc."
    ::= { vrrpNewCfgVirtRtrGrpTableEntry 10 }

vrrpNewCfgVirtRtrGrpTckIpIntf OBJECT-TYPE
    SYNTAX  INTEGER {
        enabled(1),
        disabled(2),
        unsupported(2147483647)
        }
    MAX-ACCESS  read-create
    STATUS  current
    DESCRIPTION
        "Enable or disable tracking other router interfaces for
         priority adjustment.  the priority increment is defined
         in vrrpNewCfgGenTckIpIntfInc."
    ::= { vrrpNewCfgVirtRtrGrpTableEntry 11 }

vrrpNewCfgVirtRtrGrpTckVlanPort OBJECT-TYPE
    SYNTAX  INTEGER {
        enabled(1),
        disabled(2),
        unsupported(2147483647)
        }
    MAX-ACCESS  read-create
    STATUS  current
    DESCRIPTION
        "Enable or disable tracking port state of VLAN ports
         for priority adjustment.  the priority increment is
         defined in vrrpNewCfgGenTckVlanPortInc."
    ::= { vrrpNewCfgVirtRtrGrpTableEntry 12 }

vrrpNewCfgVirtRtrGrpTckL4Port OBJECT-TYPE
    SYNTAX  INTEGER {
        enabled(1),
        disabled(2),
        unsupported(2147483647)
        }
    MAX-ACCESS  read-create
    STATUS  current
    DESCRIPTION
        "Enable or disable tracking Layer 4 port states for
         priority adjustment.  the priority increment is defined
         in vrrpNewCfgGenTckL4PortInc.  This is applied when
         virtual server is configured as a VRRP virtual router."
    ::= { vrrpNewCfgVirtRtrGrpTableEntry 13 }

vrrpNewCfgVirtRtrGrpTckRServer OBJECT-TYPE
    SYNTAX  INTEGER {
        enabled(1),
        disabled(2),
        unsupported(2147483647)
        }
    MAX-ACCESS  read-create
    STATUS  current
    DESCRIPTION
        "Enable or disable tracking real server states for
         priority adjustment.  the priority increment is defined
         in vrrpNewCfgGenTckRServerInc.  This is applied when
         virtual server is configured as a VRRP virtual router."
    ::= { vrrpNewCfgVirtRtrGrpTableEntry 14 }

vrrpNewCfgVirtRtrGrpTckHsrp OBJECT-TYPE
    SYNTAX  INTEGER {
        enabled(1),
        disabled(2),
        unsupported(2147483647)
        }
    MAX-ACCESS  read-create
    STATUS  current
    DESCRIPTION
        "Enable or disable tracking HSRP advertisements for
         priority adjustment.  the priority increment is defined
         in vrrpNewCfgGenTckHsrpInc.  This is applied when
         virtual server is configured as a VRRP virtual router."
    ::= { vrrpNewCfgVirtRtrGrpTableEntry 15 }

vrrpNewCfgVirtRtrGrpTckHsrv OBJECT-TYPE
        SYNTAX  INTEGER {
                enabled(1),
                disabled(2),
                unsupported(2147483647)
                }
        MAX-ACCESS  read-create
        STATUS  current
        DESCRIPTION
                "Enable or disable tracking HSRP by VLAN advertisements for
                 priority adjustment.  The priority increment is defined
                 in vrrpNewCfgGenTckHsrvInc.  This is applied when
                 virtual server is configured as a VRRP virtual router."
        ::= { vrrpNewCfgVirtRtrGrpTableEntry 16 }

vrrpNewCfgVirtRtrGrpVersion OBJECT-TYPE
    SYNTAX  INTEGER {
        v4(1),
        v6(2),
        unsupported(2147483647)
    }
    MAX-ACCESS  read-create
    STATUS  current
    DESCRIPTION
        "The VRRP virtual router group IP Version."
    ::= { vrrpNewCfgVirtRtrGrpTableEntry 17 }

vrrpNewCfgVirtRtrGrpIpv6Interval OBJECT-TYPE
    SYNTAX INTEGER (1..4095)
    MAX-ACCESS read-create
    STATUS current
    DESCRIPTION
        "The time interval between IPv6 VRRP advertisements in centiseconds."
    ::= { vrrpNewCfgVirtRtrGrpTableEntry 18 }

vrrpNewCfgVirtRtrGrpOspfCost OBJECT-TYPE
    SYNTAX INTEGER (0..65535)
    MAX-ACCESS read-create
    STATUS current
    DESCRIPTION
        "OSPF Cost Adjustment"
    ::= { vrrpNewCfgVirtRtrGrpTableEntry 19 }

vrrpNewCfgVirtRtrGrpTckSwExt OBJECT-TYPE
    SYNTAX  INTEGER {
        enabled(1),
        disabled(2),
        unsupported(2147483647)
        }
    MAX-ACCESS  read-create
    STATUS  current
    DESCRIPTION
        "Enable or disable tracking Switch Extension availability for
         priority adjustment. The priority increment is defined
         in vrrpNewCfgGenTckSwExtInc."
    ::= { vrrpNewCfgVirtRtrGrpTableEntry 20 }
vrrpNewCfgVirtRtrGrpTckIslPort OBJECT-TYPE
    SYNTAX  INTEGER {
        include(1),
        exclude(2),
        unsupported(2147483647)
        }
    MAX-ACCESS  read-create
    STATUS  current
    DESCRIPTION
        "Include or exclude ISL ports in tracking."
    ::= { vrrpNewCfgVirtRtrGrpTableEntry 21 }

vrrpVirtRtrVrGrpTableMaxSize OBJECT-TYPE
    SYNTAX Integer32
    MAX-ACCESS read-only
    STATUS current
    DESCRIPTION
        "The maximum number of entries in VRRP VrGroup table.
         Note:This mib is not supported for VX instance of Virtualization."
    ::= { vrrpCfg 11 }

vrrpCurCfgVirtRtrVrGrpTable OBJECT-TYPE
    SYNTAX  SEQUENCE OF VrrpCurCfgVirtRtrVrGrpTableEntry
    MAX-ACCESS  not-accessible
    STATUS  current
    DESCRIPTION
        "The table of VRRP virtual router vrgroup configuration in
         the current config.
         Note:This mib is not supported for VX instance of Virtualization."
    ::= { vrrpCfg 12 }

vrrpCurCfgVirtRtrVrGrpTableEntry OBJECT-TYPE
    SYNTAX  VrrpCurCfgVirtRtrVrGrpTableEntry
    MAX-ACCESS  not-accessible
    STATUS  current
    DESCRIPTION
        "Information about setting VRRP virtual router vrgroup.
         Note:This mib is not supported for VX instance of Virtualization."
    INDEX   { vrrpCurCfgVirtRtrVrGrpIndx }
    ::= { vrrpCurCfgVirtRtrVrGrpTable 1 }

VrrpCurCfgVirtRtrVrGrpTableEntry ::= SEQUENCE {
    vrrpCurCfgVirtRtrVrGrpIndx          Integer32,
    vrrpCurCfgVirtRtrVrGrpName          DisplayString,
    vrrpCurCfgVirtRtrVrGrpState         INTEGER,
    vrrpCurCfgVirtRtrVrGrpBmap          OCTET STRING,
    vrrpCurCfgVirtRtrVrGrpPriority      INTEGER,
    vrrpCurCfgVirtRtrVrGrpTckIpIntf     INTEGER,
    vrrpCurCfgVirtRtrVrGrpTckVlanPort   INTEGER,
    vrrpCurCfgVirtRtrVrGrpTckL4Port     INTEGER,
    vrrpCurCfgVirtRtrVrGrpTckRServer    INTEGER,
    vrrpCurCfgVirtRtrVrGrpTckHsrp       INTEGER,
    vrrpCurCfgVirtRtrVrGrpTckHsrv       INTEGER,
    vrrpCurCfgVirtRtrVrGrpTckVirtRtrNo  INTEGER,
    vrrpCurCfgVirtRtrVrGrpAdd           INTEGER,
    vrrpCurCfgVirtRtrVrGrpAdverInterval INTEGER,
    vrrpCurCfgVirtRtrVrGrpPreemption    INTEGER,
    vrrpCurCfgVirtRtrVrGrpSharing       INTEGER,
    vrrpCurCfgVirtRtrVrGrpOspfCost      INTEGER,
    vrrpCurCfgVirtRtrVrGrpTckSwExt       INTEGER,
    vrrpCurCfgVirtRtrVrGrpTckIslPort     INTEGER
    }

vrrpCurCfgVirtRtrVrGrpIndx OBJECT-TYPE
    SYNTAX  Integer32
    MAX-ACCESS  read-only
    STATUS  current
    DESCRIPTION
        "The VRRP virtual router vrgroup table index."
    ::= { vrrpCurCfgVirtRtrVrGrpTableEntry 1 }

vrrpCurCfgVirtRtrVrGrpName OBJECT-TYPE
    SYNTAX  DisplayString (SIZE(0..8))
    MAX-ACCESS  read-only
    STATUS  current
    DESCRIPTION
        "The VRRP virtual router vrgroup name."
    ::= { vrrpCurCfgVirtRtrVrGrpTableEntry 2 }

vrrpCurCfgVirtRtrVrGrpState OBJECT-TYPE
    SYNTAX  INTEGER {
        enabled(1),
        disabled(2),
        unsupported(2147483647)
    }
    MAX-ACCESS  read-only
    STATUS  current
    DESCRIPTION
        "Enable or disable VRRP Vrgroup state "
    ::= { vrrpCurCfgVirtRtrVrGrpTableEntry 3 }

vrrpCurCfgVirtRtrVrGrpBmap OBJECT-TYPE
    SYNTAX  OCTET STRING
    MAX-ACCESS  read-only
    STATUS  current
    DESCRIPTION
        "The virtual routers added for to this VRRP vrgroup.
         The selected virtual routers are presented in a bitmap format.
         in receiving order:

             OCTET 1  OCTET 2  .....
             xxxxxxxx xxxxxxxx .....
             ||    || |_ Virtual Router 9
             ||    ||
             ||    ||___ Virtual Router 8
             ||    |____ Virtual Router 7
             ||      .    .   .
             ||_________ Virtual Router 2
             |__________ Virtual Router 1

             where x : 1 - The represented Virtual Router is added
                       0 - The represented Virtual Router is not added"
    ::= { vrrpCurCfgVirtRtrVrGrpTableEntry 4 }

vrrpCurCfgVirtRtrVrGrpPriority OBJECT-TYPE
    SYNTAX  INTEGER (1..254)
    MAX-ACCESS  read-only
    STATUS  current
    DESCRIPTION
        "The priority value to be used by the specified VRRP virtual routers."
    ::= { vrrpCurCfgVirtRtrVrGrpTableEntry 5 }

vrrpCurCfgVirtRtrVrGrpTckIpIntf OBJECT-TYPE
    SYNTAX  INTEGER {
        enabled(1),
        disabled(2),
        unsupported(2147483647)
        }
    MAX-ACCESS  read-only
    STATUS  current
    DESCRIPTION
        "Enable or disable tracking interfaces in vrgroup for
         priority adjustment. The priority increment is defined
         in vrrpCurCfgGenTckIpIntfInc."
    ::= { vrrpCurCfgVirtRtrVrGrpTableEntry 6 }

vrrpCurCfgVirtRtrVrGrpTckVlanPort OBJECT-TYPE
    SYNTAX  INTEGER {
        enabled(1),
        disabled(2),
        unsupported(2147483647)
        }
    MAX-ACCESS  read-only
    STATUS  current
    DESCRIPTION
        "Enable or disable tracking port state of VLAN ports
         for priority adjustment. The priority increment is
         defined in vrrpCurCfgGenTckVlanPortInc."
    ::= { vrrpCurCfgVirtRtrVrGrpTableEntry 7 }

vrrpCurCfgVirtRtrVrGrpTckL4Port OBJECT-TYPE
    SYNTAX  INTEGER {
        enabled(1),
        disabled(2),
        unsupported(2147483647)
        }
    MAX-ACCESS  read-only
    STATUS  current
    DESCRIPTION
        "Enable or disable tracking Layer 4 port states for
         priority adjustment.  the priority increment is defined
         in vrrpCurCfgGenTckL4PortInc.  This is applied when
         virtual server is configured as a VRRP virtual router."
    ::= { vrrpCurCfgVirtRtrVrGrpTableEntry 8 }

vrrpCurCfgVirtRtrVrGrpTckRServer OBJECT-TYPE
    SYNTAX  INTEGER {
        enabled(1),
        disabled(2),
        unsupported(2147483647)
        }
    MAX-ACCESS  read-only
    STATUS  current
    DESCRIPTION
        "Enable or disable tracking real server states for
         priority adjustment.  the priority increment is defined
         in vrrpCurCfgGenTckRServerInc.  This is applied when
         virtual server is configured as a VRRP virtual router."
    ::= { vrrpCurCfgVirtRtrVrGrpTableEntry 9 }

vrrpCurCfgVirtRtrVrGrpTckHsrp OBJECT-TYPE
    SYNTAX  INTEGER {
        enabled(1),
        disabled(2),
        unsupported(2147483647)
        }
    MAX-ACCESS  read-only
    STATUS  current
    DESCRIPTION
        "Enable or disable tracking HSRP advertisements for
         priority adjustment.  the priority increment is defined
         in vrrpCurCfgGenTckHsrpInc.  This is applied when
         virtual server is configured as a VRRP virtual router."
    ::= { vrrpCurCfgVirtRtrVrGrpTableEntry 10 }

vrrpCurCfgVirtRtrVrGrpTckHsrv OBJECT-TYPE
        SYNTAX  INTEGER {
                enabled(1),
                disabled(2),
                unsupported(2147483647)
                }
        MAX-ACCESS  read-only
        STATUS  current
        DESCRIPTION
                "Enable or disable tracking HSRP advertisements by VLAN for
                 priority adjustment.  The priority increment is defined
                 in vrrpCurCfgGenTckHsrvInc.  This is applied when
                 virtual server is configured as a VRRP virtual router."
        ::= { vrrpCurCfgVirtRtrVrGrpTableEntry 11 }

vrrpCurCfgVirtRtrVrGrpTckVirtRtrNo OBJECT-TYPE
    SYNTAX  INTEGER (0..1024)
    MAX-ACCESS  read-only 
    STATUS  current 
    DESCRIPTION
        "The track virtual router for group."
        ::= { vrrpCurCfgVirtRtrVrGrpTableEntry 12 }

vrrpCurCfgVirtRtrVrGrpAdd OBJECT-TYPE
    SYNTAX  INTEGER (0..1024)
    MAX-ACCESS  read-only
    STATUS  current
    DESCRIPTION
        "Specify virtual router number which needs to be added to group."
        ::= { vrrpCurCfgVirtRtrVrGrpTableEntry 13 }

vrrpCurCfgVirtRtrVrGrpAdverInterval OBJECT-TYPE
    SYNTAX  INTEGER (1..255)
    MAX-ACCESS  read-only
    STATUS  current
    DESCRIPTION
        "The advertisement interval for virtual router group."
        ::= { vrrpCurCfgVirtRtrVrGrpTableEntry 14 }


vrrpCurCfgVirtRtrVrGrpPreemption OBJECT-TYPE
    SYNTAX  INTEGER {
            enabled(1),
            disabled(2),
            unsupported(2147483647)
            }
    MAX-ACCESS  read-only
    STATUS  current
    DESCRIPTION
        "Enable/Disable preemption for virtual router group."
        ::= { vrrpCurCfgVirtRtrVrGrpTableEntry 15 }

vrrpCurCfgVirtRtrVrGrpSharing OBJECT-TYPE
    SYNTAX  INTEGER {
            enabled(1),
            disabled(2),
            unsupported(2147483647)
            }
    MAX-ACCESS  read-only
    STATUS  current
    DESCRIPTION
        "Enable/Disable sharing for virtual router group."
        ::= { vrrpCurCfgVirtRtrVrGrpTableEntry 16 }

vrrpCurCfgVirtRtrVrGrpOspfCost OBJECT-TYPE
    SYNTAX  INTEGER (1..65535)
    MAX-ACCESS  read-only
    STATUS  current
    DESCRIPTION
        "OSPF Cost Adjustment"
        ::= { vrrpCurCfgVirtRtrVrGrpTableEntry 17 }

vrrpCurCfgVirtRtrVrGrpTckSwExt OBJECT-TYPE
        SYNTAX  INTEGER {
                enabled(1),
                disabled(2),
                unsupported(2147483647)
                }
        MAX-ACCESS  read-only
        STATUS  current
        DESCRIPTION
                "Enable or disable tracking Switch Extension availability for
                 priority adjustment.  The priority increment is defined
                 in vrrpCurCfgGenTckSwExtInc."
        ::= { vrrpCurCfgVirtRtrVrGrpTableEntry 18 }

vrrpCurCfgVirtRtrVrGrpTckIslPort OBJECT-TYPE
        SYNTAX  INTEGER {
                include(1),
                exclude(2),
                unsupported(2147483647)
                }
        MAX-ACCESS  read-only
        STATUS  current
        DESCRIPTION
            "Include or exclude ISL ports in tracking."
        ::= { vrrpCurCfgVirtRtrVrGrpTableEntry 19 }

vrrpNewCfgVirtRtrVrGrpTable OBJECT-TYPE
    SYNTAX  SEQUENCE OF VrrpNewCfgVirtRtrVrGrpTableEntry
    MAX-ACCESS  not-accessible
    STATUS  current
    DESCRIPTION
        "The table of VRRP virtual router vrgroup configuration in new_config.
         Note:This mib is not supported for VX instance of Virtualization."
    ::= { vrrpCfg 13 }

vrrpNewCfgVirtRtrVrGrpTableEntry OBJECT-TYPE
    SYNTAX  VrrpNewCfgVirtRtrVrGrpTableEntry
    MAX-ACCESS  not-accessible
    STATUS  current
    DESCRIPTION
        "Information about setting VRRP virtual router Vrgroup.
         Note:This mib is not supported for VX instance of Virtualization."
    INDEX   { vrrpNewCfgVirtRtrVrGrpIndx }
    ::= { vrrpNewCfgVirtRtrVrGrpTable 1 }

VrrpNewCfgVirtRtrVrGrpTableEntry ::= SEQUENCE {
    vrrpNewCfgVirtRtrVrGrpIndx          Integer32,
    vrrpNewCfgVirtRtrVrGrpName          DisplayString,
    vrrpNewCfgVirtRtrVrGrpAdd           INTEGER,
    vrrpNewCfgVirtRtrVrGrpRem           INTEGER,
    vrrpNewCfgVirtRtrVrGrpState         INTEGER,
    vrrpNewCfgVirtRtrVrGrpDelete        INTEGER,
    vrrpNewCfgVirtRtrVrGrpBmap          OCTET STRING,
    vrrpNewCfgVirtRtrVrGrpPriority      INTEGER,
    vrrpNewCfgVirtRtrVrGrpTckIpIntf     INTEGER,
    vrrpNewCfgVirtRtrVrGrpTckVlanPort   INTEGER,
    vrrpNewCfgVirtRtrVrGrpTckL4Port     INTEGER,
    vrrpNewCfgVirtRtrVrGrpTckRServer    INTEGER,
    vrrpNewCfgVirtRtrVrGrpTckHsrp       INTEGER,
    vrrpNewCfgVirtRtrVrGrpTckHsrv       INTEGER,
    vrrpNewCfgVirtRtrVrGrpTckVirtRtrNo  INTEGER,
    vrrpNewCfgVirtRtrVrGrpAdverInterval INTEGER,
    vrrpNewCfgVirtRtrVrGrpPreemption    INTEGER,
    vrrpNewCfgVirtRtrVrGrpSharing       INTEGER,
    vrrpNewCfgVirtRtrVrGrpOspfCost      INTEGER,
    vrrpNewCfgVirtRtrVrGrpTckSwExt      INTEGER,
    vrrpNewCfgVirtRtrVrGrpTckIslPort      INTEGER
    }

vrrpNewCfgVirtRtrVrGrpIndx OBJECT-TYPE
    SYNTAX  Integer32
    MAX-ACCESS  read-only
    STATUS  current
    DESCRIPTION
        "The VRRP virtual router vrgroup table index."
    ::= { vrrpNewCfgVirtRtrVrGrpTableEntry 1 }

vrrpNewCfgVirtRtrVrGrpName OBJECT-TYPE
    SYNTAX  DisplayString (SIZE(0..8))
    MAX-ACCESS  read-create
    STATUS  current
    DESCRIPTION
        "The VRRP virtual router vrgroup name."
    ::= { vrrpNewCfgVirtRtrVrGrpTableEntry 2 }

vrrpNewCfgVirtRtrVrGrpAdd OBJECT-TYPE
    SYNTAX  INTEGER (1..1024)
    MAX-ACCESS  read-create
    STATUS  current
    DESCRIPTION
        "The VRRP virtual router to be added to this vrgroup table."
    ::= { vrrpNewCfgVirtRtrVrGrpTableEntry 3 }

vrrpNewCfgVirtRtrVrGrpRem OBJECT-TYPE
    SYNTAX  INTEGER (1..1024)
    MAX-ACCESS  read-create
    STATUS  current
    DESCRIPTION
        "The VRRP virtual router to be removed from this vrgroup table."
    ::= { vrrpNewCfgVirtRtrVrGrpTableEntry 4 }

vrrpNewCfgVirtRtrVrGrpState OBJECT-TYPE
        SYNTAX  INTEGER {
                enabled(1),
                disabled(2),
                unsupported(2147483647)
                }
        MAX-ACCESS  read-create
        STATUS  current
        DESCRIPTION
                "Enable or disable VRRP Vrgroup state "
        ::= { vrrpNewCfgVirtRtrVrGrpTableEntry 5 }

vrrpNewCfgVirtRtrVrGrpDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { vrrpNewCfgVirtRtrVrGrpTableEntry 6 }

vrrpNewCfgVirtRtrVrGrpBmap OBJECT-TYPE
    SYNTAX  OCTET STRING
    MAX-ACCESS  read-only
    STATUS  current
    DESCRIPTION
        "The virtual routers added to this VRRP vrgroup.
         The selected virtual routers are presented in a bitmap format.
         in receiving order:

             OCTET 1  OCTET 2  .....
             xxxxxxxx xxxxxxxx .....
             ||    || |_ Virtual Router 9
             ||    ||
             ||    ||___ Virtual Router 8
             ||    |____ Virtual Router 7
             ||      .    .   .
             ||_________ Virtual Router 2
             |__________ Virtual Router 1

             where x : 1 - The represented Virtual Router is added
                       0 - The represented Virtual Router is not added"
    ::= { vrrpNewCfgVirtRtrVrGrpTableEntry 7 }

vrrpNewCfgVirtRtrVrGrpPriority OBJECT-TYPE
    SYNTAX  INTEGER (1..254)
    MAX-ACCESS  read-create
    STATUS  current
    DESCRIPTION
        "The priority value to be used by the specified VRRP virtual routers."
    ::= { vrrpNewCfgVirtRtrVrGrpTableEntry 8 }

vrrpNewCfgVirtRtrVrGrpTckIpIntf OBJECT-TYPE
    SYNTAX  INTEGER {
        enabled(1),
        disabled(2),
        unsupported(2147483647)
        }
    MAX-ACCESS  read-create
    STATUS  current
    DESCRIPTION
        "Enable or disable tracking interfaces in vrgroup for
         priority adjustment. The priority increment is defined
         in vrrpCurCfgGenTckIpIntfInc."
    ::= { vrrpNewCfgVirtRtrVrGrpTableEntry 9 }

vrrpNewCfgVirtRtrVrGrpTckVlanPort OBJECT-TYPE
    SYNTAX  INTEGER {
        enabled(1),
        disabled(2),
        unsupported(2147483647)
        }
    MAX-ACCESS  read-create
    STATUS  current
    DESCRIPTION
        "Enable or disable tracking port state of VLAN ports
         for priority adjustment. The priority increment is
         defined in vrrpCurCfgGenTckVlanPortInc."
    ::= { vrrpNewCfgVirtRtrVrGrpTableEntry 10 }

vrrpNewCfgVirtRtrVrGrpTckL4Port OBJECT-TYPE
    SYNTAX  INTEGER {
        enabled(1),
        disabled(2),
        unsupported(2147483647)
        }
    MAX-ACCESS  read-create
    STATUS  current
    DESCRIPTION
        "Enable or disable tracking Layer 4 port states for
         priority adjustment.  the priority increment is defined
         in vrrpCurCfgGenTckL4PortInc.  This is applied when
         virtual server is configured as a VRRP virtual router."
    ::= { vrrpNewCfgVirtRtrVrGrpTableEntry 11 }

vrrpNewCfgVirtRtrVrGrpTckRServer OBJECT-TYPE
    SYNTAX  INTEGER {
        enabled(1),
        disabled(2),
        unsupported(2147483647)
        }
    MAX-ACCESS  read-create
    STATUS  current
    DESCRIPTION
        "Enable or disable tracking real server states for
         priority adjustment.  the priority increment is defined
         in vrrpCurCfgGenTckRServerInc.  This is applied when
         virtual server is configured as a VRRP virtual router."
    ::= { vrrpNewCfgVirtRtrVrGrpTableEntry 12 }

vrrpNewCfgVirtRtrVrGrpTckHsrp OBJECT-TYPE
    SYNTAX  INTEGER {
        enabled(1),
        disabled(2),
        unsupported(2147483647)
        }
    MAX-ACCESS  read-create
    STATUS  current
    DESCRIPTION
        "Enable or disable tracking HSRP advertisements for
         priority adjustment.  the priority increment is defined
         in vrrpCurCfgGenTckHsrpInc.  This is applied when
         virtual server is configured as a VRRP virtual router."
    ::= { vrrpNewCfgVirtRtrVrGrpTableEntry 13 }

vrrpNewCfgVirtRtrVrGrpTckHsrv OBJECT-TYPE
        SYNTAX  INTEGER {
                enabled(1),
                disabled(2),
                unsupported(2147483647)
                }
        MAX-ACCESS  read-create
        STATUS  current
        DESCRIPTION
                "Enable or disable tracking HSRP advertisements by VLAN for
                 priority adjustment.  The priority increment is defined
                 in vrrpCurCfgGenTckHsrvInc.  This is applied when
                 virtual server is configured as a VRRP virtual router."
        ::= { vrrpNewCfgVirtRtrVrGrpTableEntry 14 }

vrrpNewCfgVirtRtrVrGrpTckVirtRtrNo OBJECT-TYPE
    SYNTAX  INTEGER (0..1024)
    MAX-ACCESS  read-create 
    STATUS  current 
    DESCRIPTION
        "The track virtual router for group."
        ::= { vrrpNewCfgVirtRtrVrGrpTableEntry 15 }


vrrpNewCfgVirtRtrVrGrpAdverInterval OBJECT-TYPE
    SYNTAX  INTEGER (1..255)
    MAX-ACCESS  read-create
    STATUS  current
    DESCRIPTION
        "The advertisement interval for virtual router group."
        ::= { vrrpNewCfgVirtRtrVrGrpTableEntry 16 }


vrrpNewCfgVirtRtrVrGrpPreemption OBJECT-TYPE
    SYNTAX  INTEGER {
            enabled(1),
            disabled(2),
            unsupported(2147483647)
            }
    MAX-ACCESS  read-create
    STATUS  current
    DESCRIPTION
        "Enable/Disable preemption for virtual router group."
        ::= { vrrpNewCfgVirtRtrVrGrpTableEntry 17 }

vrrpNewCfgVirtRtrVrGrpSharing OBJECT-TYPE
    SYNTAX  INTEGER {
            enabled(1),
            disabled(2),
            unsupported(2147483647)
            }
    MAX-ACCESS  read-create
    STATUS  current
    DESCRIPTION
        "Enable/Disable sharing for virtual router group."
        ::= { vrrpNewCfgVirtRtrVrGrpTableEntry 18 }

vrrpNewCfgVirtRtrVrGrpOspfCost OBJECT-TYPE
    SYNTAX  INTEGER (0..65536)
    MAX-ACCESS  read-create 
    STATUS  current 
    DESCRIPTION
        "OSPF Cost Adjustment"
        ::= { vrrpNewCfgVirtRtrVrGrpTableEntry 19 }

vrrpNewCfgVirtRtrVrGrpTckSwExt OBJECT-TYPE
        SYNTAX  INTEGER {
                enabled(1),
                disabled(2),
        unsupported(2147483647)
                }
        MAX-ACCESS  read-create
        STATUS  current
        DESCRIPTION
                "Enable or disable tracking Switch Extension availability for
                 priority adjustment.  The priority increment is defined
                 in vrrpCurCfgGenTckSwExtInc."
        ::= { vrrpNewCfgVirtRtrVrGrpTableEntry 20 }

vrrpNewCfgVirtRtrVrGrpTckIslPort OBJECT-TYPE
        SYNTAX  INTEGER {
                include(1),
                exclude(2),
                unsupported(2147483647)
                }
        MAX-ACCESS  read-create
        STATUS  current
        DESCRIPTION
            "Include or exclude ISL ports in tracking."
        ::= { vrrpNewCfgVirtRtrVrGrpTableEntry 21 }

-- Domain Name Server Configuration

dnsCurCfgPrimaryIpAddr OBJECT-TYPE
    SYNTAX  IpAddress
    MAX-ACCESS  read-only
    STATUS  current
    DESCRIPTION
        "The DNS primary IP address in the current_configuration block.
        Note:This mib is not supported for VX instance of virtualization."
    ::= { dnsCfg 1 }

dnsNewCfgPrimaryIpAddr OBJECT-TYPE
    SYNTAX  IpAddress
    MAX-ACCESS  read-write
    STATUS  current
    DESCRIPTION
        "The DNS primary IP address in the new_configuration block.
        Note:This mib is not supported for VX instance of virtualization."
    ::= { dnsCfg 2 }

dnsCurCfgSecondaryIpAddr OBJECT-TYPE
    SYNTAX  IpAddress
    MAX-ACCESS  read-only
    STATUS  current
    DESCRIPTION
        "The DNS secondary IP address in the current_configuration block.
        Note:This mib is not supported for VX instance of virtualization."
    ::= { dnsCfg 3 }

dnsNewCfgSecondaryIpAddr OBJECT-TYPE
    SYNTAX  IpAddress
    MAX-ACCESS  read-write
    STATUS  current
    DESCRIPTION
        "The DNS secondary IP address in the new_configuration block.
        Note:This mib is not supported for VX instance of virtualization."
    ::= { dnsCfg 4 }

dnsCurCfgDomainName OBJECT-TYPE
    SYNTAX  DisplayString (SIZE(0..191))
    MAX-ACCESS  read-only
    STATUS  current
    DESCRIPTION
        "The DNS doamin name in the current_configuration block.
        Note:This mib is not supported for VX instance of virtualization."
    ::= { dnsCfg 5 }

dnsNewCfgDomainName OBJECT-TYPE
    SYNTAX  DisplayString (SIZE(0..191))
    MAX-ACCESS  read-write
    STATUS  current
    DESCRIPTION
        "The DNS doamin name in the new_configuration block.
        Note:This mib is not supported for VX instance of virtualization."
    ::= { dnsCfg 6 }

dnsCurCfgPrimaryIpv6Addr OBJECT-TYPE
    SYNTAX DisplayString (SIZE(0..40))
    MAX-ACCESS  read-only
    STATUS  current
    DESCRIPTION
        "The DNS primary IPv6 address in the current_configuration block.
        Note:This mib is not supported for VX instance of virtualization."
    ::= { dnsCfg 7 }

dnsNewCfgPrimaryIpv6Addr OBJECT-TYPE
    SYNTAX DisplayString (SIZE(0..40))
    MAX-ACCESS  read-write
    STATUS  current
    DESCRIPTION
        "The DNS primary IPv6 address in the new_configuration block.
        Note:This mib is not supported for VX instance of virtualization."
    ::= { dnsCfg 8 }

dnsCurCfgSecondaryIpv6Addr OBJECT-TYPE
    SYNTAX DisplayString (SIZE(0..40))
    MAX-ACCESS  read-only
    STATUS  current
    DESCRIPTION
        "The DNS secondary IPv6 address in the current_configuration block.
        Note:This mib is not supported for VX instance of virtualization."
    ::= { dnsCfg 9 }

dnsNewCfgSecondaryIpv6Addr OBJECT-TYPE
    SYNTAX DisplayString (SIZE(0..40))
    MAX-ACCESS  read-write
    STATUS  current
    DESCRIPTION
        "The DNS secondary IPv6 address in the new_configuration block.
        Note:This mib is not supported for VX instance of virtualization."
    ::= { dnsCfg 10 }

--
-- IP network filter configuration
--
ipNwfTableMax OBJECT-TYPE
    SYNTAX Integer32
    MAX-ACCESS read-only
    STATUS current
    DESCRIPTION
	"The maximum number of rows in the IP network filter table.
    Note:This mib is not supported for VX instance of Virtualization."
    ::= { ipNwfCfg 1 }

ipCurCfgNwfTable OBJECT-TYPE
    SYNTAX SEQUENCE OF IpCurCfgNwfEntry
    MAX-ACCESS not-accessible
    STATUS current
    DESCRIPTION
      "The table of IP network filter configuration in the current_config.
       Note:This mib is not supported for VX instance of Virtualization."
    ::= { ipNwfCfg 2 }

ipCurCfgNwfEntry OBJECT-TYPE
    SYNTAX IpCurCfgNwfEntry
    MAX-ACCESS not-accessible
    STATUS current
    DESCRIPTION
      "Information about an IP network filter.
       Note:This mib is not supported for VX instance of Virtualization."
    INDEX { ipCurCfgNwfIndex }
    ::= { ipCurCfgNwfTable 1 }
 
IpCurCfgNwfEntry ::= SEQUENCE {
    ipCurCfgNwfIndex     Integer32,
    ipCurCfgNwfAddr      IpAddress,
    ipCurCfgNwfMask      IpAddress,
    ipCurCfgNwfState     INTEGER,
    ipCurCfgNwfIpVer     INTEGER,
    ipCurCfgNwfIpv6Addr  DisplayString,
    ipCurCfgNwfIpv6Mask  INTEGER
    }
 
ipCurCfgNwfIndex OBJECT-TYPE
    SYNTAX Integer32
    MAX-ACCESS read-only
    STATUS current
    DESCRIPTION
	"The network filter number for which the NWF is related."
    ::= { ipCurCfgNwfEntry 1}

ipCurCfgNwfAddr OBJECT-TYPE
    SYNTAX IpAddress
    MAX-ACCESS read-only
    STATUS current
    DESCRIPTION
	"The IP address of the network filter."
    ::= { ipCurCfgNwfEntry 2 }

ipCurCfgNwfMask OBJECT-TYPE
    SYNTAX IpAddress
    MAX-ACCESS read-only
    STATUS current  
    DESCRIPTION
	"The subnet mask of the network filter."
    ::= { ipCurCfgNwfEntry 3 }

ipCurCfgNwfState OBJECT-TYPE
    SYNTAX INTEGER { 
        enabled(1),
        disabled(2),
        unsupported(2147483647)
	}
    MAX-ACCESS  read-only
    STATUS  current  
    DESCRIPTION
	"Enable or disable the network filter."
    ::= { ipCurCfgNwfEntry 4 }

ipCurCfgNwfIpVer OBJECT-TYPE
    SYNTAX INTEGER {
        v4(0),
        v6(1),
        unsupported(2147483647)
        }
    MAX-ACCESS read-only
    STATUS current
    DESCRIPTION
        "The type of IP address Version"
    ::= { ipCurCfgNwfEntry 5 }

ipCurCfgNwfIpv6Addr OBJECT-TYPE
    SYNTAX DisplayString (SIZE(0..40))
    MAX-ACCESS read-only
    STATUS current
    DESCRIPTION
        "The IPv6 address of the network filter."
    ::= { ipCurCfgNwfEntry 6 }

ipCurCfgNwfIpv6Mask OBJECT-TYPE
    SYNTAX  INTEGER (1..128)
    MAX-ACCESS read-only
    STATUS current
    DESCRIPTION
        "The IPv6 prefix mask of the network filter."
    ::= { ipCurCfgNwfEntry 7 }

ipNewCfgNwfTable OBJECT-TYPE
    SYNTAX SEQUENCE OF IpNewCfgNwfEntry
    MAX-ACCESS not-accessible
    STATUS current
    DESCRIPTION
      "The table of IP network filter configuration in the current_config.
       Note:This mib is not supported for VX instance of Virtualization."
    ::= { ipNwfCfg 3 }

ipNewCfgNwfEntry OBJECT-TYPE
    SYNTAX IpNewCfgNwfEntry
    MAX-ACCESS not-accessible
    STATUS current
    DESCRIPTION
      "Information about an IP network filter.
       Note:This mib is not supported for VX instance of Virtualization."
    INDEX { ipNewCfgNwfIndex }
    ::= { ipNewCfgNwfTable 1 }
 
IpNewCfgNwfEntry ::= SEQUENCE {
    ipNewCfgNwfIndex     Integer32,
    ipNewCfgNwfAddr      IpAddress,
    ipNewCfgNwfMask      IpAddress,
    ipNewCfgNwfState     INTEGER,
    ipNewCfgNwfDelete    INTEGER,
    ipNewCfgNwfIpVer    INTEGER,
    ipNewCfgNwfIpv6Addr  DisplayString,
    ipNewCfgNwfIpv6Mask  INTEGER
    }
 
ipNewCfgNwfIndex OBJECT-TYPE
    SYNTAX Integer32
    MAX-ACCESS read-only
    STATUS current
    DESCRIPTION
	"The network filter number for which the NWF is related."
    ::= { ipNewCfgNwfEntry 1}

ipNewCfgNwfAddr OBJECT-TYPE
    SYNTAX IpAddress
    MAX-ACCESS read-create
    STATUS current
    DESCRIPTION
	"The IP address of the network filter."
    ::= { ipNewCfgNwfEntry 2 }

ipNewCfgNwfMask OBJECT-TYPE
    SYNTAX IpAddress
    MAX-ACCESS read-create
    STATUS current  
    DESCRIPTION
	"The subnet mask of the network filter."
    ::= { ipNewCfgNwfEntry 3 }

ipNewCfgNwfState OBJECT-TYPE
    SYNTAX INTEGER { 
        enabled(1),
        disabled(2),
        unsupported(2147483647)
	}
    MAX-ACCESS  read-create
    STATUS  current  
    DESCRIPTION
	"Enable or disable the network filter."
    ::= { ipNewCfgNwfEntry 4 }

ipNewCfgNwfDelete OBJECT-TYPE
    SYNTAX INTEGER { 
        other(1),
        delete(2),
        unsupported(2147483647)
        }
    MAX-ACCESS read-create
    STATUS current
    DESCRIPTION
	"When set to the value of 2 (delete), the entire row is deleted. 
	 When read, other(1) is returned. Setting the value to anything 
	 other than 2(delete) has no effect on the state of the row."
    ::= { ipNewCfgNwfEntry 5 }

ipNewCfgNwfIpVer OBJECT-TYPE
    SYNTAX INTEGER {
        v4(0),
        v6(1),
        unsupported(2147483647)
        }
    MAX-ACCESS read-create
    STATUS current
    DESCRIPTION
        "The type of IP address Version"
    ::= { ipNewCfgNwfEntry 6 }

ipNewCfgNwfIpv6Addr OBJECT-TYPE
    SYNTAX DisplayString (SIZE(0..40))
    MAX-ACCESS read-create
    STATUS current
    DESCRIPTION
        "The IPv6 address of the network filter."
    ::= { ipNewCfgNwfEntry 7 }

ipNewCfgNwfIpv6Mask OBJECT-TYPE
    SYNTAX  INTEGER (1..128)
    MAX-ACCESS read-create
    STATUS current
    DESCRIPTION
        "The IPv6 prefix mask of the network filter."
    ::= { ipNewCfgNwfEntry 8 }

--
-- IP route map configuration
--
ipRmapTableMax OBJECT-TYPE
    SYNTAX Integer32
    MAX-ACCESS read-only
    STATUS current
    DESCRIPTION
	"The maximum number of rows in the IP route map table.
         Note:This mib is not supported for VX instance of Virtualization."
    ::= { ipRmapCfg 1 }

ipCurCfgRmapTable OBJECT-TYPE
    SYNTAX SEQUENCE OF IpCurCfgRmapEntry
    MAX-ACCESS not-accessible
    STATUS current
    DESCRIPTION
      "The table of IP route map configuration in the current_config.
      Note:This mib is not supported for VX instance of virtualization."
    ::= { ipRmapCfg 2 }

ipCurCfgRmapEntry OBJECT-TYPE
    SYNTAX IpCurCfgRmapEntry
    MAX-ACCESS not-accessible
    STATUS current
    DESCRIPTION
      "Information about an IP route map.
      Note:This mib is not supported for VX instance of virtualization."
    INDEX { ipCurCfgRmapIndex }
    ::= { ipCurCfgRmapTable 1 }
 
IpCurCfgRmapEntry ::= SEQUENCE {
    ipCurCfgRmapIndex		Integer32,
    ipCurCfgRmapLp	  	Unsigned32,
    ipCurCfgRmapMetric	  	Unsigned32,
    ipCurCfgRmapPrec	  	INTEGER,
    ipCurCfgRmapWeight	 	INTEGER, 
    ipCurCfgRmapState     	INTEGER,
    ipCurCfgRmapMetricType	INTEGER,
    ipCurCfgRmapAp		DisplayString
    }
 
ipCurCfgRmapIndex OBJECT-TYPE
    SYNTAX Integer32
    MAX-ACCESS read-only
    STATUS current
    DESCRIPTION
	"The route map number for which the RMAP is related.
    Note:This mib is not supported for VX instance of virtualization."
    ::= { ipCurCfgRmapEntry 1}

ipCurCfgRmapLp OBJECT-TYPE
    SYNTAX Unsigned32 (0..4294967295) 
    MAX-ACCESS read-only
    STATUS current
    DESCRIPTION
	"The local-preference of the route map. 0 means none.
    Note:This mib is not supported for VX instance of virtualization."
    ::= { ipCurCfgRmapEntry 2 }

ipCurCfgRmapMetric OBJECT-TYPE
    SYNTAX Unsigned32 (0..4294967295) 
    MAX-ACCESS read-only
    STATUS current
    DESCRIPTION
	"The metric of the route map. 0 means none.
    Note:This mib is not supported for VX instance of virtualization."
    ::= { ipCurCfgRmapEntry 3 }

ipCurCfgRmapPrec OBJECT-TYPE
    SYNTAX INTEGER (1..255) 
    MAX-ACCESS read-only
    STATUS current
    DESCRIPTION
	"The precedence of the route map.
    Note:This mib is not supported for VX instance of virtualization."
    ::= { ipCurCfgRmapEntry 4 }

ipCurCfgRmapWeight OBJECT-TYPE
    SYNTAX INTEGER (0..65535) 
    MAX-ACCESS read-only
    STATUS current
    DESCRIPTION
	"The weight of the route map. 0 means none.
    Note:This mib is not supported for VX instance of virtualization."
    ::= { ipCurCfgRmapEntry 5 }

ipCurCfgRmapState OBJECT-TYPE
    SYNTAX INTEGER { 
        enabled(1),
        disabled(2),
        unsupported(2147483647)
	}
    MAX-ACCESS  read-only
    STATUS  current  
    DESCRIPTION
	"Enable or disable the route map.
    Note:This mib is not supported for VX instance of virtualization."
    ::= { ipCurCfgRmapEntry 6 }

ipCurCfgRmapAp OBJECT-TYPE
    SYNTAX DisplayString (SIZE(0..18)) 
    MAX-ACCESS read-only
    STATUS current
    DESCRIPTION
	"The as-path prepend of the matched route. Up to 3 AS number can be 
	 displayed for the string. 
	 The usuage is:<AS number> [<AS number>][ <AS number>]
     Note:This mib is not supported for VX instance of virtualization."
    ::= { ipCurCfgRmapEntry 7 }

ipCurCfgRmapMetricType OBJECT-TYPE
    SYNTAX INTEGER {
        none(1),
        type1(2),
        type2(3),
        unsupported(2147483647)
        }
    MAX-ACCESS  read-only
    STATUS  current  
    DESCRIPTION
	"The OSPF metric-type of the matched route.
    Note:This mib is not supported for VX instance of virtualization."
    ::= { ipCurCfgRmapEntry 8 }

ipNewCfgRmapTable OBJECT-TYPE
    SYNTAX SEQUENCE OF IpNewCfgRmapEntry
    MAX-ACCESS not-accessible
    STATUS current
    DESCRIPTION
      "The table of IP route map configuration in the current_config.
      Note:This mib is not supported for VX instance of virtualization."
    ::= { ipRmapCfg 3 }

ipNewCfgRmapEntry OBJECT-TYPE
    SYNTAX IpNewCfgRmapEntry
    MAX-ACCESS not-accessible
    STATUS current
    DESCRIPTION
      "Information about an IP route map.
      Note:This mib is not supported for VX instance of virtualization."
    INDEX { ipNewCfgRmapIndex }
    ::= { ipNewCfgRmapTable 1 }
 
IpNewCfgRmapEntry ::= SEQUENCE {
    ipNewCfgRmapIndex		Integer32,
    ipNewCfgRmapLp	  	Unsigned32,
    ipNewCfgRmapMetric	  	Unsigned32,
    ipNewCfgRmapPrec	  	INTEGER,
    ipNewCfgRmapWeight	 	INTEGER, 
    ipNewCfgRmapState     	INTEGER,
    ipNewCfgRmapAp		DisplayString,
    ipNewCfgRmapMetricType	INTEGER,
    ipNewCfgRmapDelete		INTEGER
    }
 
ipNewCfgRmapIndex OBJECT-TYPE
    SYNTAX Integer32
    MAX-ACCESS read-only
    STATUS current
    DESCRIPTION
	"The route map number for which the RMAP is related.
    Note:This mib is not supported for VX instance of virtualization."
    ::= { ipNewCfgRmapEntry 1}

ipNewCfgRmapLp OBJECT-TYPE
    SYNTAX Unsigned32 (0..4294967295) 
    MAX-ACCESS read-create
    STATUS current
    DESCRIPTION
	"The local-preference of the route map. 0 means none.
    Note:This mib is not supported for VX instance of virtualization."
    ::= { ipNewCfgRmapEntry 2 }

ipNewCfgRmapMetric OBJECT-TYPE
    SYNTAX Unsigned32 (0..4294967295) 
    MAX-ACCESS read-create
    STATUS current
    DESCRIPTION
	"The metric of the route map. 0 means none.
    Note:This mib is not supported for VX instance of virtualization."
    ::= { ipNewCfgRmapEntry 3 }

ipNewCfgRmapPrec OBJECT-TYPE
    SYNTAX INTEGER (1..255) 
    MAX-ACCESS read-create
    STATUS current
    DESCRIPTION
	"The precedence of the route map.
    Note:This mib is not supported for VX instance of virtualization."
    ::= { ipNewCfgRmapEntry 4 }

ipNewCfgRmapWeight OBJECT-TYPE
    SYNTAX INTEGER (0..65535) 
    MAX-ACCESS read-create
    STATUS current
    DESCRIPTION
	"The weight of the route map. 0 means none.
    Note:This mib is not supported for VX instance of virtualization."
    ::= { ipNewCfgRmapEntry 5 }

ipNewCfgRmapState OBJECT-TYPE
    SYNTAX INTEGER { 
        enabled(1),
        disabled(2),
        unsupported(2147483647)
	}
    MAX-ACCESS  read-create
    STATUS  current  
    DESCRIPTION
	"Enable or disable the route map.
    Note:This mib is not supported for VX instance of virtualization."
    ::= { ipNewCfgRmapEntry 6 }

ipNewCfgRmapAp OBJECT-TYPE
    SYNTAX DisplayString (SIZE(0..32)) 
    MAX-ACCESS read-create
    STATUS current
    DESCRIPTION
	"The as-path prepend of the matched route. Up to 3 AS number can be 
	 displayed for the string. 
	 The usuage is:<AS number> [<AS number>][ <AS number>].
     Note:This mib is not supported for VX instance of virtualization."
    ::= { ipNewCfgRmapEntry 7 }

ipNewCfgRmapMetricType OBJECT-TYPE
    SYNTAX INTEGER {
        none(1),
        type1(2),
        type2(3),
        unsupported(2147483647)
        }
    MAX-ACCESS  read-create
    STATUS  current  
    DESCRIPTION
	"The OSPF metric-type of the matched route.
    Note:This mib is not supported for VX instance of virtualization."
    ::= { ipNewCfgRmapEntry 8 }

ipNewCfgRmapDelete OBJECT-TYPE
    SYNTAX  INTEGER {
	other(1),
	delete(2),
        unsupported(2147483647)
	}
    MAX-ACCESS  read-create
    STATUS  current
    DESCRIPTION
	"When set to the value of 2 (delete), the entire row is deleted. 
	 When read, other(1) is returned. Setting the value to anything 
	 other than 2(delete) has no effect on the state of the row.
     Note:This mib is not supported for VX instance of virtualization."
    ::= { ipNewCfgRmapEntry 9 }

ipAlistTableMax OBJECT-TYPE
    SYNTAX Integer32
    MAX-ACCESS read-only
    STATUS current
    DESCRIPTION
	"The maximum number of rows in the IP route map table.
    Note:This mib is not supported for VX instance of virtualization."
    ::= { ipRmapCfg 4 }

ipCurCfgAlistTable OBJECT-TYPE
    SYNTAX SEQUENCE OF IpCurCfgAlistEntry
    MAX-ACCESS not-accessible
    STATUS current
    DESCRIPTION
      "The table of IP route map access list configuration in the 
       current_config.
       Note:This mib is not supported for VX instance of virtualization."
    ::= { ipRmapCfg 5 }

ipCurCfgAlistEntry OBJECT-TYPE
    SYNTAX IpCurCfgAlistEntry
    MAX-ACCESS not-accessible
    STATUS current
    DESCRIPTION
      "Information about an IP route map.
      Note:This mib is not supported for VX instance of virtualization."
    INDEX { ipCurCfgAlistRmapIndex, ipCurCfgAlistIndex }
    ::= { ipCurCfgAlistTable 1 }
 
IpCurCfgAlistEntry ::= SEQUENCE {
    ipCurCfgAlistRmapIndex	Integer32,
    ipCurCfgAlistIndex		Integer32,
    ipCurCfgAlistNwf		INTEGER,
    ipCurCfgAlistMetric	  	Unsigned32,
    ipCurCfgAlistAction		INTEGER,
    ipCurCfgAlistState     	INTEGER,
    ipCurCfgAlistNwc            DisplayString
    }
 
ipCurCfgAlistRmapIndex OBJECT-TYPE
    SYNTAX Integer32
    MAX-ACCESS read-only
    STATUS current
    DESCRIPTION
	"The route map number for which the RMAP is related.
    Note:This mib is not supported for VX instance of virtualization."
    ::= { ipCurCfgAlistEntry 1 }

ipCurCfgAlistIndex OBJECT-TYPE
    SYNTAX Integer32
    MAX-ACCESS read-only
    STATUS current
    DESCRIPTION
	"The access list number for which the access list is related.
    Note:This mib is not supported for VX instance of virtualization."
    ::= { ipCurCfgAlistEntry 2 }

ipCurCfgAlistNwf OBJECT-TYPE
    SYNTAX INTEGER (0..256) 
    MAX-ACCESS read-only
    STATUS current
    DESCRIPTION
	"The network filter number of the route map access list. 
	 0 means none.
     Note:This mib is not supported for VX instance of virtualization"
    ::= { ipCurCfgAlistEntry 3 }

ipCurCfgAlistMetric OBJECT-TYPE
    SYNTAX Unsigned32 (0..4294967295) 
    MAX-ACCESS read-only
    STATUS current
    DESCRIPTION
	"The metric of the route map access list. 0 means none.
    Note:This mib is not supported for VX instance of virtualization."
    ::= { ipCurCfgAlistEntry 4 }

ipCurCfgAlistAction OBJECT-TYPE
    SYNTAX INTEGER {
	permit(1),
	deny(2),
        unsupported(2147483647)
	}
    MAX-ACCESS read-only
    STATUS current
    DESCRIPTION
	"Action of the route map access list.
    Note:This mib is not supported for VX instance of virtualization."
    ::= { ipCurCfgAlistEntry 5 }

ipCurCfgAlistState OBJECT-TYPE
    SYNTAX INTEGER { 
        enabled(1),
        disabled(2),
        unsupported(2147483647)
	}
    MAX-ACCESS  read-only
    STATUS  current  
    DESCRIPTION
	"Enable or disable the route map access list.
    Note:This mib is not supported for VX instance of virtualization."
    ::= { ipCurCfgAlistEntry 6 }

ipCurCfgAlistNwc OBJECT-TYPE
    SYNTAX  DisplayString  (SIZE(0..32))
    MAX-ACCESS  read-only
    STATUS  current
    DESCRIPTION
        "The network classifier of the route map access list.
         'none' means no network class configured.
         Note:This mib is not supported for VX instance of virtualization."
    ::= { ipCurCfgAlistEntry 7 }

ipNewCfgAlistTable OBJECT-TYPE
    SYNTAX SEQUENCE OF IpNewCfgAlistEntry
    MAX-ACCESS not-accessible
    STATUS current
    DESCRIPTION
      "The table of IP route map access list configuration in the 
       current_config.
       Note:This mib is not supported for VX instance of virtualization."
    ::= { ipRmapCfg 6 }

ipNewCfgAlistEntry OBJECT-TYPE
    SYNTAX IpNewCfgAlistEntry
    MAX-ACCESS not-accessible
    STATUS current
    DESCRIPTION
      "Information about an IP route map.
      Note:This mib is not supported for VX instance of virtualization."
    INDEX { ipNewCfgAlistRmapIndex, ipNewCfgAlistIndex }
    ::= { ipNewCfgAlistTable 1 }
 
IpNewCfgAlistEntry ::= SEQUENCE {
    ipNewCfgAlistRmapIndex	Integer32,
    ipNewCfgAlistIndex		Integer32,
    ipNewCfgAlistNwf		INTEGER,
    ipNewCfgAlistMetric	  	Unsigned32,
    ipNewCfgAlistAction		INTEGER,
    ipNewCfgAlistState     	INTEGER,
    ipNewCfgAlistDelete		INTEGER,
    ipNewCfgAlistNwc            DisplayString,
    ipNewCfgAlistNwType         INTEGER
    }
 
ipNewCfgAlistRmapIndex OBJECT-TYPE
    SYNTAX Integer32
    MAX-ACCESS read-only
    STATUS current
    DESCRIPTION
	"The route map number for which the RMAP is related.
    Note:This mib is not supported for VX instance of virtualization."
    ::= { ipNewCfgAlistEntry 1 }

ipNewCfgAlistIndex OBJECT-TYPE
    SYNTAX Integer32
    MAX-ACCESS read-only
    STATUS current
    DESCRIPTION
	"The access list number for which the access list is related.
    Note:This mib is not supported for VX instance of virtualization."
    ::= { ipNewCfgAlistEntry 2 }

ipNewCfgAlistNwf OBJECT-TYPE
    SYNTAX INTEGER (0..256) 
    MAX-ACCESS read-create
    STATUS current
    DESCRIPTION
	"The network filter number of the route map access list. 
	 0 means none.
     Note:This mib is not supported for VX instance of virtualization."
    ::= { ipNewCfgAlistEntry 3 }

ipNewCfgAlistMetric OBJECT-TYPE
    SYNTAX Unsigned32 (0..4294967295) 
    MAX-ACCESS read-create
    STATUS current
    DESCRIPTION
	"The metric of the route map access list. 0 means none.
    Note:This mib is not supported for VX instance of virtualization"
    ::= { ipNewCfgAlistEntry 4 }

ipNewCfgAlistAction OBJECT-TYPE
    SYNTAX INTEGER {
	permit(1),
	deny(2),
        unsupported(2147483647)
	}
    MAX-ACCESS read-create
    STATUS current
    DESCRIPTION
	"Action of the route map access list.
    Note:This mib is not supported for VX instance of virtualization."
    ::= { ipNewCfgAlistEntry 5 }

ipNewCfgAlistState OBJECT-TYPE
    SYNTAX INTEGER { 
        enabled(1),
        disabled(2),
        unsupported(2147483647)
	}
    MAX-ACCESS  read-create
    STATUS  current  
    DESCRIPTION
	"Enable or disable the route map access list.
    Note:This mib is not supported for VX instance of virtualization."
    ::= { ipNewCfgAlistEntry 6 }

ipNewCfgAlistDelete OBJECT-TYPE
    SYNTAX  INTEGER {
	other(1),
	delete(2),
        unsupported(2147483647)
	}
    MAX-ACCESS  read-create
    STATUS  current
    DESCRIPTION
	"When set to the value of 2 (delete), the entire row is deleted. 
	 When read, other(1) is returned. Setting the value to anything 
	 other than 2(delete) has no effect on the state of the row.
     Note:This mib is not supported for VX instance of virtualization."
    ::= { ipNewCfgAlistEntry 7 }

ipNewCfgAlistNwc OBJECT-TYPE
    SYNTAX  DisplayString  (SIZE(0..32))
    MAX-ACCESS  read-create
    STATUS  current
    DESCRIPTION
        "The network classifier of the route map access list.
         'none' means no network class configured.
         Note:This mib is not supported for VX instance of virtualization."
    ::= { ipNewCfgAlistEntry 8 }

ipNewCfgAlistNwType OBJECT-TYPE
    SYNTAX INTEGER {
        network-filter(1),
        network-class(2),
        unsupported(2147483647)
        }
    MAX-ACCESS  read-create
    STATUS  current
    DESCRIPTION
        "Is the alist configured to network filter type or network class type.
        Note:This mib is not supported for VX instance of virtualization."
    ::= { ipNewCfgAlistEntry 9 }

ipAspathTableMax OBJECT-TYPE
    SYNTAX Integer32
    MAX-ACCESS read-only
    STATUS current
    DESCRIPTION
	"The maximum number of rows in the IP route map table.
    Note:This mib is not supported for VX instance of virtualization."
    ::= { ipRmapCfg 7 }

ipCurCfgAspathTable OBJECT-TYPE
    SYNTAX SEQUENCE OF IpCurCfgAspathEntry
    MAX-ACCESS not-accessible
    STATUS current
    DESCRIPTION
      "The table of IP route map access path configuration.
      Note:This mib is not supported for VX instance of virtualization."
    ::= { ipRmapCfg 8 }

ipCurCfgAspathEntry OBJECT-TYPE
    SYNTAX IpCurCfgAspathEntry
    MAX-ACCESS not-accessible
    STATUS current
    DESCRIPTION
      "Information about an IP route map.
      Note:This mib is not supported for VX instance of virtualization."
    INDEX { ipCurCfgAspathRmapIndex, ipCurCfgAlistIndex }
    ::= { ipCurCfgAspathTable 1 }
 
IpCurCfgAspathEntry ::= SEQUENCE {
    ipCurCfgAspathRmapIndex	Integer32,
    ipCurCfgAspathIndex		Integer32,
    ipCurCfgAspathAS		INTEGER,
    ipCurCfgAspathAction	INTEGER,
    ipCurCfgAspathState     	INTEGER
    }
 
ipCurCfgAspathRmapIndex OBJECT-TYPE
    SYNTAX Integer32
    MAX-ACCESS read-only
    STATUS current
    DESCRIPTION
	"The route map number for which the RMAP is related.
    Note:This mib is not supported for VX instance of virtualization."
    ::= { ipCurCfgAspathEntry 1 }

ipCurCfgAspathIndex OBJECT-TYPE
    SYNTAX Integer32
    MAX-ACCESS read-only
    STATUS current
    DESCRIPTION
	"The access path number for which the access list is related.
    Note:This mib is not supported for VX instance of virtualization."
    ::= { ipCurCfgAspathEntry 2 }

ipCurCfgAspathAS OBJECT-TYPE
    SYNTAX INTEGER (0..65535) 
    MAX-ACCESS read-only
    STATUS current
    DESCRIPTION
	"The AS number of the route map access path. 
	 0 means none.
     Note:This mib is not supported for VX instance of virtualization"
    ::= { ipCurCfgAspathEntry 3 }

ipCurCfgAspathAction OBJECT-TYPE
    SYNTAX INTEGER {
	permit(1),
	deny(2),
        unsupported(2147483647)
	}
    MAX-ACCESS read-only
    STATUS current
    DESCRIPTION
	"Action of the route map access path.
    Note:This mib is not supported for VX instance of virtualization."
    ::= { ipCurCfgAspathEntry 4 }

ipCurCfgAspathState OBJECT-TYPE
    SYNTAX INTEGER { 
        enabled(1),
        disabled(2),
        unsupported(2147483647)
	}
    MAX-ACCESS  read-only
    STATUS  current  
    DESCRIPTION
	"Enable or disable the route map access path.
    Note:This mib is not supported for VX instance of virtualization."
    ::= { ipCurCfgAspathEntry 5 }

ipNewCfgAspathTable OBJECT-TYPE
    SYNTAX SEQUENCE OF IpNewCfgAspathEntry
    MAX-ACCESS not-accessible
    STATUS current
    DESCRIPTION
      "The table of IP route map access path configuration.
      Note:This mib is not supported for VX instance of virtualization"
    ::= { ipRmapCfg 9 }

ipNewCfgAspathEntry OBJECT-TYPE
    SYNTAX IpNewCfgAspathEntry
    MAX-ACCESS not-accessible
    STATUS current
    DESCRIPTION
      "Information about an IP route map.
      Note:This mib is not supported for VX instance of virtualization."
    INDEX { ipNewCfgAspathRmapIndex, ipNewCfgAspathIndex }
    ::= { ipNewCfgAspathTable 1 }
 
IpNewCfgAspathEntry ::= SEQUENCE {
    ipNewCfgAspathRmapIndex	Integer32,
    ipNewCfgAspathIndex		Integer32,
    ipNewCfgAspathAS		Unsigned32,
    ipNewCfgAspathAction	INTEGER,
    ipNewCfgAspathState     	INTEGER,
    ipNewCfgAspathDelete	INTEGER
    }
 
ipNewCfgAspathRmapIndex OBJECT-TYPE
    SYNTAX Integer32
    MAX-ACCESS read-only
    STATUS current
    DESCRIPTION
	"The route map number for which the RMAP is related.
    Note:This mib is not supported for VX instance of virtualization."
    ::= { ipNewCfgAspathEntry 1 }

ipNewCfgAspathIndex OBJECT-TYPE
    SYNTAX Integer32
    MAX-ACCESS read-only
    STATUS current
    DESCRIPTION
	"The access path number for which the access list is related.
    Note:This mib is not supported for VX instance of virtualization."
    ::= { ipNewCfgAspathEntry 2 }

ipNewCfgAspathAS OBJECT-TYPE
    SYNTAX Unsigned32 (0..4294967294) 
    MAX-ACCESS read-create
    STATUS current
    DESCRIPTION
	"The AS number of the route map access path. 
	 0 means none.
     Note:This mib is not supported for VX instance of virtualization."
    ::= { ipNewCfgAspathEntry 3 }

ipNewCfgAspathAction OBJECT-TYPE
    SYNTAX INTEGER {
	permit(1),
	deny(2),
        unsupported(2147483647)
	}
    MAX-ACCESS read-create
    STATUS current
    DESCRIPTION
	"Action of the route map access path.
    Note:This mib is not supported for VX instance of virtualization."
    ::= { ipNewCfgAspathEntry 4 }

ipNewCfgAspathState OBJECT-TYPE
    SYNTAX INTEGER { 
        enabled(1),
        disabled(2),
        unsupported(2147483647)
	}
    MAX-ACCESS  read-create
    STATUS  current  
    DESCRIPTION
	"Enable or disable the route map access path.
    Note:This mib is not supported for VX instance of virtualization."
    ::= { ipNewCfgAspathEntry 5 }

ipNewCfgAspathDelete OBJECT-TYPE
    SYNTAX  INTEGER {
	other(1),
	delete(2),
        unsupported(2147483647)
	}
    MAX-ACCESS  read-create
    STATUS  current
    DESCRIPTION
	"When set to the value of 2 (delete), the entire row is deleted. 
	 When read, other(1) is returned. Setting the value to anything 
	 other than 2(delete) has no effect on the state of the row.
     Note:This mib is not supported for VX instance of virtualization."
    ::= { ipNewCfgAspathEntry 6 }

--
-- IP BGP configuration
--
bgpGeneral	OBJECT IDENTIFIER ::= { bgpCfg 1 }

bgpCurCfgState OBJECT-TYPE
    SYNTAX INTEGER {
        on(1),
        off(2),
        unsupported(2147483647)
        }
    MAX-ACCESS read-only
    STATUS current
    DESCRIPTION
	"BGP global state.
    Note:This mib is not supported for VX instance of virtualization."
    ::= { bgpGeneral 1 }

bgpNewCfgState OBJECT-TYPE
    SYNTAX INTEGER {
        on(1),
        off(2),
        unsupported(2147483647)
        }
    MAX-ACCESS read-write
    STATUS current
    DESCRIPTION
	"Globally turn BGP on or off.
    Note:This mib is not supported for VX instance of virtualization."
    ::= { bgpGeneral 2 }

bgpCurCfgLocalPref OBJECT-TYPE
    SYNTAX Unsigned32 (0..4294967294) 
    MAX-ACCESS  read-only
    STATUS  current
    DESCRIPTION
        "Local preference value.
        Note:This mib is not supported for VX instance of virtualization."
      ::= { bgpGeneral 3 }

bgpNewCfgLocalPref OBJECT-TYPE
    SYNTAX Unsigned32 (0..4294967294) 
    MAX-ACCESS  read-write
    STATUS  current
    DESCRIPTION
        "Local Preference value.
        Note:This mib is not supported for VX instance of virtualization."
      ::= { bgpGeneral 4 }

bgpCurCfgMaxASPath OBJECT-TYPE
    SYNTAX Unsigned32 (1..127)
    MAX-ACCESS  read-only
    STATUS  current
    DESCRIPTION
        "Maximum AS Path Length.
        Note:This mib is not supported for VX instance of virtualization."
      ::= { bgpGeneral 5 }
  
bgpNewCfgMaxASPath OBJECT-TYPE 
    SYNTAX Unsigned32 (1..127)
    MAX-ACCESS  read-write   
    STATUS  current
    DESCRIPTION
        "Maximum AS Path Length.
        Note:This mib is not supported for VX instance of virtualization."
      ::= { bgpGeneral 6 }

bgpCurCfgASNumber OBJECT-TYPE
    SYNTAX Unsigned32 (0..65535)
    MAX-ACCESS  read-only
    STATUS  current
    DESCRIPTION
        "Current autonomous system number.
        Note:This mib is not supported for VX instance of virtualization."
      ::= { bgpGeneral 7 }

bgpNewCfgASNumber OBJECT-TYPE
    SYNTAX Unsigned32 (0..4294967295)
    MAX-ACCESS  read-write
    STATUS  current
    DESCRIPTION
        "New autonomous system number.Enter 0 to delete this number.
        Note:This mib is not supported for VX instance of virtualization."
      ::= { bgpGeneral 8 }

bgpCurCfgStopVipAdv OBJECT-TYPE
    SYNTAX INTEGER {
        enabled(1),
        disabled(2),
        unsupported(2147483647)
        }
    MAX-ACCESS  read-only
    STATUS  current
    DESCRIPTION
        "Stop VIP advertisement.
        Note:This mib is not supported for VX instance of virtualization."
      ::= { bgpGeneral 9 }

bgpNewCfgStopVipAdv OBJECT-TYPE
    SYNTAX INTEGER {
        enabled(1),
        disabled(2),
        unsupported(2147483647)
        }
    MAX-ACCESS  read-write
    STATUS  current
    DESCRIPTION
        "Stop VIP advertisement.
        Note:This mib is not supported for VX instance of virtualization."
      ::= { bgpGeneral 10 }

bgpCurCfgAdvFip OBJECT-TYPE
    SYNTAX INTEGER {
        on(1),
        off(2),
        unsupported(2147483647)
        }
    MAX-ACCESS read-only
    STATUS current
    DESCRIPTION
	"Advertise floating IP state.
    Note:This mib is not supported for VX instance of virtualization."
    ::= { bgpGeneral 11 }

bgpNewCfgAdvFip OBJECT-TYPE
    SYNTAX INTEGER {
        on(1),
        off(2),
        unsupported(2147483647)
        }
    MAX-ACCESS read-write
    STATUS current
    DESCRIPTION
	"Advertising floating IP : on or off.
    Note:This mib is not supported for VX instance of virtualization."
    ::= { bgpGeneral 12 }

bgpPeerTableMax OBJECT-TYPE
    SYNTAX Integer32
    MAX-ACCESS read-only
    STATUS current
    DESCRIPTION
	"The maximum number of rows in the BGP peer table.
    Note:This mib is not supported for VX instance of virtualization."
    ::= { bgpCfg 2 }

bgpCurCfgPeerTable OBJECT-TYPE
    SYNTAX SEQUENCE OF BgpCurCfgPeerEntry
    MAX-ACCESS not-accessible
    STATUS current
    DESCRIPTION
      "The table of BGP peer configuration in the current_config.
      Note:This mib is not supported for VX instance of virtualization."
    ::= { bgpCfg 3 }

bgpCurCfgPeerEntry OBJECT-TYPE
    SYNTAX BgpCurCfgPeerEntry
    MAX-ACCESS not-accessible
    STATUS current
    DESCRIPTION
      "Information about a BGP peer.
      Note:This mib is not supported for VX instance of virtualization."
    INDEX { bgpCurCfgPeerIndex }
    ::= { bgpCurCfgPeerTable 1 }
 
BgpCurCfgPeerEntry ::= SEQUENCE {
    bgpCurCfgPeerIndex     	Integer32,
    bgpCurCfgPeerRemoteAddr	IpAddress,
    bgpCurCfgPeerRemoteAs	INTEGER,
    bgpCurCfgPeerTtl		INTEGER,
    bgpCurCfgPeerState     	INTEGER,
    bgpCurCfgPeerMetric		Unsigned32,
    bgpCurCfgPeerDefaultAction	INTEGER,
    bgpCurCfgPeerOspfState	INTEGER,
    bgpCurCfgPeerFixedState     INTEGER,
    bgpCurCfgPeerStaticState    INTEGER,
    bgpCurCfgPeerVipState       INTEGER,
    bgpCurCfgPeerInRmapList 	OCTET STRING,
    bgpCurCfgPeerOutRmapList	OCTET STRING,
    bgpCurCfgPeerHoldTime       INTEGER,
    bgpCurCfgPeerKeepAlive      INTEGER,
    bgpCurCfgPeerMinTime        INTEGER,
    bgpCurCfgPeerConRetry       INTEGER,
    bgpCurCfgPeerMinAS          INTEGER,
    bgpCurCfgPeerRipState       INTEGER,
    bgpCurCfgPeerDenyState      INTEGER,
    bgpCurCfgPeerNextHop        IpAddress,
    bgpCurCfgPeerBfdState       INTEGER
    }
 
bgpCurCfgPeerIndex OBJECT-TYPE
    SYNTAX Integer32
    MAX-ACCESS read-only
    STATUS current
    DESCRIPTION
	"The BGP peer number for which the BGP peer table is related.
    Note:This mib is not supported for VX instance of virtualization."
    ::= { bgpCurCfgPeerEntry 1 }

bgpCurCfgPeerRemoteAddr OBJECT-TYPE
    SYNTAX IpAddress 
    MAX-ACCESS read-only
    STATUS current
    DESCRIPTION
	"The remote IP address of the BGP peer.
    Note:This mib is not supported for VX instance of virtualization." 
    ::= { bgpCurCfgPeerEntry 2 }

bgpCurCfgPeerRemoteAs OBJECT-TYPE
    SYNTAX INTEGER (0..65535) 
    MAX-ACCESS read-only
    STATUS current
    DESCRIPTION
	"The remote AS number of the BGP peer.  0 means none.
    Note:This mib is not supported for VX instance of virtualization." 
    ::= { bgpCurCfgPeerEntry 3 }

bgpCurCfgPeerTtl OBJECT-TYPE
    SYNTAX INTEGER (1..255) 
    MAX-ACCESS read-only
    STATUS current
    DESCRIPTION
	"The time-to-live value of the BGP peer IP datagram.
    Note:This mib is not supported for VX instance of virtualization."
    ::= { bgpCurCfgPeerEntry 4 }

bgpCurCfgPeerState OBJECT-TYPE
    SYNTAX INTEGER { 
        enabled(1),
        disabled(2),
        unsupported(2147483647)
	}
    MAX-ACCESS  read-only
    STATUS  current  
    DESCRIPTION
	"Enable or disable the peer.
    Note:This mib is not supported for VX instance of virtualization."
    ::= { bgpCurCfgPeerEntry 5 }

bgpCurCfgPeerMetric OBJECT-TYPE
    SYNTAX Unsigned32 (0..4294967294) 
    MAX-ACCESS read-only
    STATUS current
    DESCRIPTION
	"The metric value of the BGP peer.  A value of '0' means none.
    Note:This mib is not supported for VX instance of virtualization."
    ::= { bgpCurCfgPeerEntry 10 }

bgpCurCfgPeerDefaultAction OBJECT-TYPE
    SYNTAX INTEGER { 
        none(1),
        import(2),
	originate(3),
	redistribute(4),
        unsupported(2147483647)
	}
    MAX-ACCESS  read-only
    STATUS  current  
    DESCRIPTION
	"The value of default route action.
    Note:This mib is not supported for VX instance of virtualization."
    ::= { bgpCurCfgPeerEntry 11 }

bgpCurCfgPeerOspfState OBJECT-TYPE
    SYNTAX INTEGER { 
        enabled(1),
        disabled(2),
        unsupported(2147483647)
	}
    MAX-ACCESS  read-only
    STATUS  current  
    DESCRIPTION
	"Enable or disable advertising OSPF routes.
    Note:This mib is not supported for VX instance of virtualization."
    ::= { bgpCurCfgPeerEntry 12 }

bgpCurCfgPeerFixedState OBJECT-TYPE
    SYNTAX INTEGER { 
        enabled(1),
        disabled(2),
        unsupported(2147483647)
	}
    MAX-ACCESS  read-only
    STATUS  current  
    DESCRIPTION
	"Enable or disable advertising fixed routes.
    Note:This mib is not supported for VX instance of virtualization."
    ::= { bgpCurCfgPeerEntry 13 }

bgpCurCfgPeerStaticState OBJECT-TYPE
    SYNTAX INTEGER { 
        enabled(1),
        disabled(2),
        unsupported(2147483647)
	}
    MAX-ACCESS  read-only
    STATUS  current  
    DESCRIPTION
	"Enable or disable advertising static routes.
    Note:This mib is not supported for VX instance of virtualization."
    ::= { bgpCurCfgPeerEntry 14 }

bgpCurCfgPeerVipState OBJECT-TYPE
    SYNTAX INTEGER { 
        enabled(1),
        disabled(2),
        unsupported(2147483647)
	}
    MAX-ACCESS  read-only
    STATUS  current  
    DESCRIPTION
	"Enable or disable VIP static routes.
    Note:This mib is not supported for VX instance of virtualization."
    ::= { bgpCurCfgPeerEntry 15 }

bgpCurCfgPeerInRmapList OBJECT-TYPE
    SYNTAX OCTET STRING
    MAX-ACCESS read-only
    STATUS current
    DESCRIPTION
        "The route maps present in the in route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { bgpCurCfgPeerEntry 16 }

bgpCurCfgPeerOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { bgpCurCfgPeerEntry 17 }

bgpCurCfgPeerHoldTime OBJECT-TYPE
    SYNTAX INTEGER (1..255)
    MAX-ACCESS read-only
    STATUS current
    DESCRIPTION
        "The Hold Time value of the BGP peer IP datagram.
        Note:This mib is not supported for VX instance of virtualization."
    ::= { bgpCurCfgPeerEntry 18 }

bgpCurCfgPeerKeepAlive OBJECT-TYPE
    SYNTAX INTEGER (1..21845)
    MAX-ACCESS read-only
    STATUS current
    DESCRIPTION
        "The KeepAlive Time value of the BGP peer IP datagram.
      Note:This mib is not supported for VX instance of virtualization."
    ::= { bgpCurCfgPeerEntry 19 }

bgpCurCfgPeerMinTime OBJECT-TYPE
    SYNTAX INTEGER (1..65535)
    MAX-ACCESS read-only
    STATUS current
    DESCRIPTION
        "The min time between advertisements  of the BGP peer IP datagram.
        Note:This mib is not supported for VX instance of virtualization."
    ::= { bgpCurCfgPeerEntry 20 }


bgpCurCfgPeerConRetry OBJECT-TYPE
    SYNTAX INTEGER (1..65535)
    MAX-ACCESS read-only
    STATUS current
    DESCRIPTION
        "The Connect Retry Timer Interval value of the BGP peer IP datagram.
        Note:This mib is not supported for VX instance of virtualization."
    ::= { bgpCurCfgPeerEntry 21 }

bgpCurCfgPeerMinAS OBJECT-TYPE
    SYNTAX INTEGER (1..65535)
    MAX-ACCESS read-only
    STATUS current
    DESCRIPTION
        "The minimum time between route originations of the BGP peer IP datagram.
        Note:This mib is not supported for VX instance of virtualization."
    ::= { bgpCurCfgPeerEntry 22 }

bgpCurCfgPeerRipState OBJECT-TYPE
    SYNTAX INTEGER {
        enabled(1),
        disabled(2),
        unsupported(2147483647)
        }
    MAX-ACCESS  read-only
    STATUS  current
    DESCRIPTION
        "Enable or disable RIP static routes.
        Note:This mib is not supported for VX instance of virtualization."
    ::= { bgpCurCfgPeerEntry 23 }

bgpCurCfgPeerDenyState OBJECT-TYPE
    SYNTAX INTEGER {
        enabled(1),
        disabled(2),
        unsupported(2147483647)
        }
    MAX-ACCESS  read-only
    STATUS  current
    DESCRIPTION
        "Enable or disable DENY route advertisement.
        Note:This mib is not supported for VX instance of virtualization."
    ::= { bgpCurCfgPeerEntry 24 }

bgpCurCfgPeerNextHop OBJECT-TYPE
    SYNTAX IpAddress 
    MAX-ACCESS read-only
    STATUS current
    DESCRIPTION
        "The value will be used by BGP peer as nexthop.
      Note:This mib is not supported for VX instance of virtualization."
    ::= { bgpCurCfgPeerEntry 25 }

bgpCurCfgPeerBfdState OBJECT-TYPE
    SYNTAX INTEGER {
        on(1),
        off(2),
        unsupported(2147483647)
        }
    MAX-ACCESS  read-only
    STATUS  current
    DESCRIPTION
        "Turn BFD on/off for the peer.
        Note:This mib is not supported for VX instance of virtualization."
    ::= { bgpCurCfgPeerEntry 26 }

bgpNewCfgPeerTable OBJECT-TYPE
    SYNTAX SEQUENCE OF BgpNewCfgPeerEntry
    MAX-ACCESS not-accessible
    STATUS current
    DESCRIPTION
      "The table of BGP peer configuration in the current_config.
      Note:This mib is not supported for VX instance of virtualization."
    ::= { bgpCfg 4 }

bgpNewCfgPeerEntry OBJECT-TYPE
    SYNTAX BgpNewCfgPeerEntry
    MAX-ACCESS not-accessible
    STATUS current
    DESCRIPTION
      "Information about a BGP peer.
      Note:This mib is not supported for VX instance of virtualization."
    INDEX { bgpNewCfgPeerIndex }
    ::= { bgpNewCfgPeerTable 1 }
 
BgpNewCfgPeerEntry ::= SEQUENCE {
    bgpNewCfgPeerIndex     	Integer32,
    bgpNewCfgPeerRemoteAddr	IpAddress,
    bgpNewCfgPeerRemoteAs	Unsigned32,
    bgpNewCfgPeerTtl		INTEGER,
    bgpNewCfgPeerState     	INTEGER,
    bgpNewCfgPeerDelete		INTEGER,
    bgpNewCfgPeerMetric		Unsigned32,
    bgpNewCfgPeerDefaultAction	INTEGER,
    bgpNewCfgPeerOspfState	INTEGER,
    bgpNewCfgPeerFixedState     INTEGER,
    bgpNewCfgPeerStaticState    INTEGER,
    bgpNewCfgPeerVipState       INTEGER,
    bgpNewCfgPeerInRmapList	OCTET STRING,
    bgpNewCfgPeerOutRmapList	OCTET STRING,
    bgpNewCfgPeerAddInRmap	Integer32,
    bgpNewCfgPeerAddOutRmap	Integer32,
    bgpNewCfgPeerRemoveInRmap	Integer32,
    bgpNewCfgPeerRemoveOutRmap	Integer32,
    bgpNewCfgPeerHoldTime       INTEGER,
    bgpNewCfgPeerKeepAlive      INTEGER,
    bgpNewCfgPeerMinTime        INTEGER,
    bgpNewCfgPeerConRetry       INTEGER,
    bgpNewCfgPeerMinAS          INTEGER,
    bgpNewCfgPeerRipState       INTEGER,
    bgpNewCfgPeerDenyState      INTEGER,
    bgpNewCfgPeerNextHop        IpAddress,
    bgpNewCfgPeerBfdState       INTEGER
    }
 
bgpNewCfgPeerIndex OBJECT-TYPE
    SYNTAX Integer32
    MAX-ACCESS read-only
    STATUS current
    DESCRIPTION
	"The BGP peer number for which the BGP peer table is related.
    Note:This mib is not supported for VX instance of virtualization."
    ::= { bgpNewCfgPeerEntry 1}

bgpNewCfgPeerRemoteAddr OBJECT-TYPE
    SYNTAX IpAddress 
    MAX-ACCESS read-create
    STATUS current
    DESCRIPTION
	"The remote IP address of the BGP peer.
    Note:This mib is not supported for VX instance of virtualization." 
    ::= { bgpNewCfgPeerEntry 2 }

bgpNewCfgPeerRemoteAs OBJECT-TYPE
    SYNTAX Unsigned32 (0..4294967295) 
    MAX-ACCESS read-create
    STATUS current
    DESCRIPTION
	"The remote AS number of the BGP peer.  0 means none.
    Note:This mib is not supported for VX instance of virtualization." 
    ::= { bgpNewCfgPeerEntry 3 }

bgpNewCfgPeerTtl OBJECT-TYPE
    SYNTAX INTEGER (1..255) 
    MAX-ACCESS read-create
    STATUS current
    DESCRIPTION
	"The time-to-live value of the BGP peer IP datagram.
    Note:This mib is not supported for VX instance of virtualization."
    ::= { bgpNewCfgPeerEntry 4 }

bgpNewCfgPeerState OBJECT-TYPE
    SYNTAX INTEGER { 
        enabled(1),
        disabled(2),
        unsupported(2147483647)
	}
    MAX-ACCESS  read-create
    STATUS  current  
    DESCRIPTION
	"Enable or disable the peer.
    Note:This mib is not supported for VX instance of virtualization."
    ::= { bgpNewCfgPeerEntry 5 }

bgpNewCfgPeerDelete OBJECT-TYPE
    SYNTAX INTEGER { 
        other(1),
        delete(2),
        unsupported(2147483647)
        }
    MAX-ACCESS read-create
    STATUS current
    DESCRIPTION
	"When set to the value of 2 (delete), the entire row is deleted. 
	 When read, other(1) is returned. Setting the value to anything 
	 other than 2(delete) has no effect on the state of the row.
     Note:This mib is not supported for VX instance of virtualization."
    ::= { bgpNewCfgPeerEntry 6 }

bgpNewCfgPeerMetric OBJECT-TYPE
    SYNTAX Unsigned32 (0..4294967294) 
    MAX-ACCESS read-create
    STATUS current
    DESCRIPTION
	"The metric value of the BGP peer. A value of '0' means none.
    Note:This mib is not supported for VX instance of virtualization" 
    ::= { bgpNewCfgPeerEntry 10 }

bgpNewCfgPeerDefaultAction OBJECT-TYPE
    SYNTAX INTEGER { 
        none(1),
        import(2),
	originate(3),
	redistribute(4),
        unsupported(2147483647)
	}
    MAX-ACCESS  read-create
    STATUS  current  
    DESCRIPTION
	"The value of default route action.
    Note:This mib is not supported for VX instance of virtualization."
    ::= { bgpNewCfgPeerEntry 11 }

bgpNewCfgPeerOspfState OBJECT-TYPE
    SYNTAX INTEGER { 
        enabled(1),
        disabled(2),
        unsupported(2147483647)
	}
    MAX-ACCESS  read-create
    STATUS  current  
    DESCRIPTION
	"Enable or disable advertising OSPF routes.
    Note:This mib is not supported for VX instance of virtualization."
    ::= { bgpNewCfgPeerEntry 12 }

bgpNewCfgPeerFixedState OBJECT-TYPE
    SYNTAX INTEGER { 
        enabled(1),
        disabled(2),
        unsupported(2147483647)
	}
    MAX-ACCESS  read-create
    STATUS  current  
    DESCRIPTION
	"Enable or disable advertising fixed routes.
    Note:This mib is not supported for VX instance of virtualization."
    ::= { bgpNewCfgPeerEntry 13 }

bgpNewCfgPeerStaticState OBJECT-TYPE
    SYNTAX INTEGER { 
        enabled(1),
        disabled(2),
        unsupported(2147483647)
	}
    MAX-ACCESS  read-create
    STATUS  current  
    DESCRIPTION
	"Enable or disable advertising static routes.
    Note:This mib is not supported for VX instance of virtualization."
    ::= { bgpNewCfgPeerEntry 14 }

bgpNewCfgPeerVipState OBJECT-TYPE
    SYNTAX INTEGER { 
        enabled(1),
        disabled(2),
        unsupported(2147483647)
	}
    MAX-ACCESS  read-create
    STATUS  current  
    DESCRIPTION
	"Enable or disable VIP static routes.
    Note:This mib is not supported for VX instance of virtualization."
    ::= { bgpNewCfgPeerEntry 15 }

bgpNewCfgPeerInRmapList OBJECT-TYPE
    SYNTAX OCTET STRING
    MAX-ACCESS read-only
    STATUS current
    DESCRIPTION
        "The route maps present in the in route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { bgpNewCfgPeerEntry 16 }

bgpNewCfgPeerOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { bgpNewCfgPeerEntry 17 }

bgpNewCfgPeerAddInRmap OBJECT-TYPE
    SYNTAX Integer32 
    MAX-ACCESS  read-create
    STATUS  current  
    DESCRIPTION
	"The route map to be add into in-rmap list. When read,
	 0 is returned.
     Note:This mib is not supported for VX instance of virtualization."
    ::= { bgpNewCfgPeerEntry 18 }

bgpNewCfgPeerAddOutRmap OBJECT-TYPE
    SYNTAX Integer32 
    MAX-ACCESS  read-create
    STATUS  current  
    DESCRIPTION
	"The route map to be add into out-rmap list. When read,
	 0 is returned.
     Note:This mib is not supported for VX instance of virtualization."
    ::= { bgpNewCfgPeerEntry 19 }

bgpNewCfgPeerRemoveInRmap OBJECT-TYPE
    SYNTAX Integer32 
    MAX-ACCESS  read-create
    STATUS  current  
    DESCRIPTION
	"The route map to be removed from out-rmap list. When read,
	 0 is returned.
     Note:This mib is not supported for VX instance of virtualization."
    ::= { bgpNewCfgPeerEntry 20 }

bgpNewCfgPeerRemoveOutRmap OBJECT-TYPE
    SYNTAX Integer32 
    MAX-ACCESS  read-create
    STATUS  current  
    DESCRIPTION
	"The route map to be removed from out-rmap list. When read,
	 0 is returned.
     Note:This mib is not supported for VX instance of virtualization."
    ::= { bgpNewCfgPeerEntry 21 }

bgpNewCfgPeerHoldTime OBJECT-TYPE
    SYNTAX INTEGER (0..65535)
    MAX-ACCESS read-create
    STATUS current
    DESCRIPTION
        "The Hold Time value of the BGP peer IP datagram.
        Note:This mib is not supported for VX instance of virtualization."
    ::= { bgpNewCfgPeerEntry 22 }

bgpNewCfgPeerKeepAlive OBJECT-TYPE
    SYNTAX INTEGER (0..21845)
    MAX-ACCESS read-create
    STATUS current
    DESCRIPTION
        "The KeepAlive Time value of the BGP peer IP datagram.
        Note:This mib is not supported for VX instance of virtualization."
    ::= { bgpNewCfgPeerEntry 23 }

bgpNewCfgPeerMinTime OBJECT-TYPE
    SYNTAX INTEGER (1..65535)
    MAX-ACCESS read-create
    STATUS current
    DESCRIPTION
        "The mininum time between advertisements of the BGP peer IP datagram.
        Note:This mib is not supported for VX instance of virtualization."
    ::= { bgpNewCfgPeerEntry 24 }


bgpNewCfgPeerConRetry OBJECT-TYPE
    SYNTAX INTEGER (1..65535)
    MAX-ACCESS read-create
    STATUS current
    DESCRIPTION
        "The Connect Retry Timer Interval value of the BGP peer IP datagram.
        Note:This mib is not supported for VX instance of virtualization."
    ::= { bgpNewCfgPeerEntry 25 }

bgpNewCfgPeerMinAS OBJECT-TYPE
    SYNTAX INTEGER (1..65535)
    MAX-ACCESS read-create
    STATUS current
    DESCRIPTION
        "The minimum time between route originations of the BGP peer IP datagram.
        Note:This mib is not supported for VX instance of virtualization."
    ::= { bgpNewCfgPeerEntry 26 }

bgpNewCfgPeerRipState OBJECT-TYPE
    SYNTAX INTEGER {
        enabled(1),
        disabled(2),
        unsupported(2147483647)
        }
    MAX-ACCESS  read-create
    STATUS  current
    DESCRIPTION
        "Enable or disable RIP static routes.
        Note:This mib is not supported for VX instance of virtualization."
    ::= { bgpNewCfgPeerEntry 27 }

bgpNewCfgPeerDenyState OBJECT-TYPE
    SYNTAX INTEGER {
        enabled(1),
        disabled(2),
        unsupported(2147483647)
        }
    MAX-ACCESS  read-create
    STATUS  current
    DESCRIPTION
        "Enable or disable DENY route advertisement.
        Note:This mib is not supported for VX instance of virtualization."
    ::= { bgpNewCfgPeerEntry 28 }

bgpNewCfgPeerNextHop OBJECT-TYPE
    SYNTAX IpAddress 
    MAX-ACCESS read-create
    STATUS current
    DESCRIPTION
        "The value will be used by BGP peer as nexthop.
        Note:This mib is not supported for VX instance of virtualization."
    ::= { bgpNewCfgPeerEntry 29 }

bgpNewCfgPeerBfdState OBJECT-TYPE
    SYNTAX INTEGER {
        on(1),
        off(2),
        unsupported(2147483647)
        }
    MAX-ACCESS  read-create
    STATUS  current
    DESCRIPTION
        "Turn BFD on/off for the peer.
        Note:This mib is not supported for VX instance of virtualization."
    ::= { bgpNewCfgPeerEntry 30 }

--
-- BGP Aggregation Table
--
bgpAggrTableMax OBJECT-TYPE
    SYNTAX Integer32
    MAX-ACCESS read-only
    STATUS current
    DESCRIPTION
	"The maximum number of rows in the BGP aggregation table.
    Note:This mib is not supported for VX instance of virtualization."
    ::= { bgpCfg 5 }

bgpCurCfgAggrTable OBJECT-TYPE
    SYNTAX SEQUENCE OF BgpCurCfgAggrEntry
    MAX-ACCESS not-accessible
    STATUS current
    DESCRIPTION
      "The table of BGP aggregation configuration.
      Note:This mib is not supported for VX instance of virtualization."
    ::= { bgpCfg 6 }

bgpCurCfgAggrEntry OBJECT-TYPE
    SYNTAX BgpCurCfgAggrEntry
    MAX-ACCESS not-accessible
    STATUS current
    DESCRIPTION
      "Information about a BGP aggregation.
      Note:This mib is not supported for VX instance of virtualization."
    INDEX { bgpCurCfgAggrIndex }
    ::= { bgpCurCfgAggrTable 1 }
 
BgpCurCfgAggrEntry ::= SEQUENCE {
    bgpCurCfgAggrIndex     Integer32,
    bgpCurCfgAggrAddr      IpAddress,
    bgpCurCfgAggrMask      IpAddress,
    bgpCurCfgAggrState     INTEGER
    }
 
bgpCurCfgAggrIndex OBJECT-TYPE
    SYNTAX Integer32
    MAX-ACCESS read-only
    STATUS current
    DESCRIPTION
	"The aggregation number for which the BGP aggregation is related.
    Note:This mib is not supported for VX instance of virtualization."
    ::= { bgpCurCfgAggrEntry 1}

bgpCurCfgAggrAddr OBJECT-TYPE
    SYNTAX IpAddress
    MAX-ACCESS read-only
    STATUS current
    DESCRIPTION
	"The IP address of the BGP aggregation.
    Note:This mib is not supported for VX instance of virtualization."
    ::= { bgpCurCfgAggrEntry 2 }

bgpCurCfgAggrMask OBJECT-TYPE
    SYNTAX IpAddress
    MAX-ACCESS read-only
    STATUS current  
    DESCRIPTION
	"The subnet mask of the BGP aggregation.
    Note:This mib is not supported for VX instance of virtualization."
    ::= { bgpCurCfgAggrEntry 3 }

bgpCurCfgAggrState OBJECT-TYPE
    SYNTAX INTEGER { 
        enabled(1),
        disabled(2),
        unsupported(2147483647)
	}
    MAX-ACCESS  read-only
    STATUS  current  
    DESCRIPTION
	"Enable or disable the BGP aggregation.
    Note:This mib is not supported for VX instance of virtualization."
    ::= { bgpCurCfgAggrEntry 4 }

bgpNewCfgAggrTable OBJECT-TYPE
    SYNTAX SEQUENCE OF BgpNewCfgAggrEntry
    MAX-ACCESS not-accessible
    STATUS current
    DESCRIPTION
      "The table of BGP aggregation configuration.
      Note:This mib is not supported for VX instance of virtualization."
    ::= { bgpCfg 7 }

bgpNewCfgAggrEntry OBJECT-TYPE
    SYNTAX BgpNewCfgAggrEntry
    MAX-ACCESS not-accessible
    STATUS current
    DESCRIPTION
      "Information about an BGP aggregation.
      Note:This mib is not supported for VX instance of virtualization."
    INDEX { bgpNewCfgAggrIndex }
    ::= { bgpNewCfgAggrTable 1 }
 
BgpNewCfgAggrEntry ::= SEQUENCE {
    bgpNewCfgAggrIndex     Integer32,
    bgpNewCfgAggrAddr      IpAddress,
    bgpNewCfgAggrMask      IpAddress,
    bgpNewCfgAggrState     INTEGER,
    bgpNewCfgAggrDelete    INTEGER
    }
 
bgpNewCfgAggrIndex OBJECT-TYPE
    SYNTAX Integer32
    MAX-ACCESS read-only
    STATUS current
    DESCRIPTION
	"The aggregation number for which the BGP aggregation is related.
    Note:This mib is not supported for VX instance of virtualization."
    ::= { bgpNewCfgAggrEntry 1}

bgpNewCfgAggrAddr OBJECT-TYPE
    SYNTAX IpAddress
    MAX-ACCESS read-create
    STATUS current
    DESCRIPTION
	"The IP address of the BGP aggregation.
    Note:This mib is not supported for VX instance of virtualization."
    ::= { bgpNewCfgAggrEntry 2 }

bgpNewCfgAggrMask OBJECT-TYPE
    SYNTAX IpAddress
    MAX-ACCESS read-create
    STATUS current  
    DESCRIPTION
	"The subnet mask of the BGP aggregation.
	Note:This mib is not supported for VX instance of virtualization."
    ::= { bgpNewCfgAggrEntry 3 }

bgpNewCfgAggrState OBJECT-TYPE
    SYNTAX INTEGER { 
        enabled(1),
        disabled(2),
        unsupported(2147483647)
	}
    MAX-ACCESS  read-create
    STATUS  current  
    DESCRIPTION
	"Enable or disable the BGP aggregation.
	Note:This mib is not supported for VX instance of virtualization."
    ::= { bgpNewCfgAggrEntry 4 }

bgpNewCfgAggrDelete OBJECT-TYPE
    SYNTAX INTEGER { 
        other(1),
        delete(2),
        unsupported(2147483647)
        }
    MAX-ACCESS read-create
    STATUS current
    DESCRIPTION
	"When set to the value of 2 (delete), the entire row is deleted. 
	 When read, other(1) is returned. Setting the value to anything 
	 other than 2(delete) has no effect on the state of the row.
     Note:This mib is not supported for VX instance of virtualization."
    ::= { bgpNewCfgAggrEntry 5 }

--
-- IP OSPF configuration
--
ospfGeneral	OBJECT IDENTIFIER ::= { ospfCfg 1 }

ospfCurCfgDefaultRouteMetric OBJECT-TYPE
    SYNTAX INTEGER (0..16777215)
    MAX-ACCESS read-only
    STATUS current
    DESCRIPTION
	"Specify the metric to be assigned.
    Note:This mib is not supported for VX instance of virtualization."
    ::= { ospfGeneral 1 }

ospfNewCfgDefaultRouteMetric OBJECT-TYPE
    SYNTAX INTEGER (0..16777215)
    MAX-ACCESS read-write
    STATUS current
    DESCRIPTION
	"Specify the metric to be assigned.
	Note:This mib is not supported for VX instance of virtualization."
    ::= { ospfGeneral 2 }

ospfCurCfgDefaultRouteMetricType OBJECT-TYPE
    SYNTAX INTEGER {
        none(1),
        type1(2),
        type2(3),
        unsupported(2147483647)
        }
    MAX-ACCESS read-only
    STATUS current
    DESCRIPTION
	"Specify the AS External metric type to be assigned.
	Note:This mib is not supported for VX instance of virtualization."
    ::= { ospfGeneral 3 }

ospfNewCfgDefaultRouteMetricType OBJECT-TYPE
    SYNTAX INTEGER {
        none(1),
        type1(2),
        type2(3),
        unsupported(2147483647)
        }
    MAX-ACCESS read-write
    STATUS current
    DESCRIPTION
	"Specify the AS External metric type to be assigned.
	Note:This mib is not supported for VX instance of virtualization."
    ::= { ospfGeneral 4 }

ospfIntfTableMaxSize OBJECT-TYPE
    SYNTAX Integer32
    MAX-ACCESS read-only
    STATUS current
    DESCRIPTION
        "The maximum number of rows in the OSPF Interface table.
        Note:This mib is not supported for VX instance of virtualization."
    ::= { ospfGeneral 5 }

ospfAreaTableMaxSize OBJECT-TYPE
    SYNTAX Integer32
    MAX-ACCESS read-only
    STATUS current
    DESCRIPTION
        "The maximum number of rows in the OSPF Area table.
        Note:This mib is not supported for VX instance of virtualization."
    ::= { ospfGeneral 6 }

ospfRangeTableMaxSize OBJECT-TYPE
    SYNTAX Integer32
    MAX-ACCESS read-only
    STATUS current
    DESCRIPTION
        "The maximum number of rows in the OSPF Range table.
        Note:This mib is not supported for VX instance of virtualization."
    ::= { ospfGeneral 7 }

ospfVirtIntfTableMaxSize OBJECT-TYPE
    SYNTAX Integer32
    MAX-ACCESS read-only
    STATUS current
    DESCRIPTION
        "The maximum number of rows in the OSPF Virtual Interface
         table.
         Note:This mib is not supported for VX instance of virtualization."
    ::= { ospfGeneral 8 }

ospfHostTableMaxSize OBJECT-TYPE
    SYNTAX Integer32
    MAX-ACCESS read-only
    STATUS current
    DESCRIPTION
        "The maximum number of rows in the OSPF Host table.
        Note:This mib is not supported for VX instance of virtualization."
    ::= { ospfGeneral 9 }

ospfCurCfgState OBJECT-TYPE
    SYNTAX INTEGER {
        on(1),
        off(2),
        unsupported(2147483647)
        }
    MAX-ACCESS read-only
    STATUS current
    DESCRIPTION
	"OSPF global state.
    Note:This mib is not supported for VX instance of virtualization."
    ::= { ospfGeneral 10 }

ospfNewCfgState OBJECT-TYPE
    SYNTAX INTEGER {
        on(1),
        off(2),
        unsupported(2147483647)
        }
    MAX-ACCESS read-write
    STATUS current
    DESCRIPTION
	"Globally turn OSPF on or off.
    Note:This mib is not supported for VX instance of virtualization."
    ::= { ospfGeneral 11 }

ospfCurCfgLsdb OBJECT-TYPE
    SYNTAX INTEGER (0..2000)
    MAX-ACCESS read-only
    STATUS current
    DESCRIPTION
        "Specify the LSDB limit for external LSA.
        Note:This mib is not supported for VX instance of virtualization."
    ::= { ospfGeneral 12 }

ospfNewCfgLsdb OBJECT-TYPE
    SYNTAX INTEGER (0..2000)
    MAX-ACCESS read-write
    STATUS current
    DESCRIPTION
        "Specify the LSDB limit for external LSA.
        Note:This mib is not supported for VX instance of virtualization."
    ::= { ospfGeneral 13 }

ospfCurCfgAreaTable OBJECT-TYPE
    SYNTAX SEQUENCE OF OspfCurCfgAreaEntry
    MAX-ACCESS not-accessible
    STATUS current
    DESCRIPTION
      "The table of OSPF Area configuration in the current_config.
      Note:This mib is not supported for VX instance of virtualization."
    ::= { ospfCfg 2 }

ospfCurCfgAreaEntry OBJECT-TYPE
    SYNTAX OspfCurCfgAreaEntry
    MAX-ACCESS not-accessible
    STATUS current
    DESCRIPTION
      "Information about a OSPF area.
      Note:This mib is not supported for VX instance of virtualization."
    INDEX { ospfCurCfgAreaIndex, ospfCurCfgAreaId }
    ::= { ospfCurCfgAreaTable 1 }
 
OspfCurCfgAreaEntry ::= SEQUENCE {
    ospfCurCfgAreaIndex         Integer32,
    ospfCurCfgAreaId            IpAddress,
    ospfCurCfgAreaSpfInterval   INTEGER,
    ospfCurCfgAreaAuthType      INTEGER,
    ospfCurCfgAreaType          INTEGER,
    ospfCurCfgAreaMetric        INTEGER,
    ospfCurCfgAreaState         INTEGER
    }
 
ospfCurCfgAreaIndex OBJECT-TYPE
    SYNTAX Integer32
    MAX-ACCESS read-only
    STATUS current
    DESCRIPTION
	"The OSPF area number for which the OSPF area table is related.
    Note:This mib is not supported for VX instance of virtualization."
    ::= { ospfCurCfgAreaEntry 1}

ospfCurCfgAreaId OBJECT-TYPE
    SYNTAX IpAddress 
    MAX-ACCESS read-only
    STATUS current
    DESCRIPTION
	"The IP Address of the OSPF area.
    Note:This mib is not supported for VX instance of virtualization." 
    ::= { ospfCurCfgAreaEntry 2 }

ospfCurCfgAreaSpfInterval OBJECT-TYPE
    SYNTAX INTEGER (0..255) 
    MAX-ACCESS read-only
    STATUS current
    DESCRIPTION
	"The SPF interval for the OSPF area.
	Note:This mib is not supported for VX instance of virtualization." 
    ::= { ospfCurCfgAreaEntry 3 }

ospfCurCfgAreaAuthType OBJECT-TYPE
    SYNTAX  INTEGER {
        none(1),
        password(2),
	md5(3),
        unsupported(2147483647)
        }
    MAX-ACCESS  read-only
    STATUS  current
    DESCRIPTION
        "Type of authentication being used.
	 none(1) - no authentication
	 password(2) - use password
	 md5(3) - use MD5 authentication.
     Note:This mib is not supported for VX instance of virtualization."
	
    ::= { ospfCurCfgAreaEntry 4 }

ospfCurCfgAreaType OBJECT-TYPE
    SYNTAX  INTEGER {
        transit(1),
        stub(2),
        nssa(3),
        unsupported(2147483647)
        }
    MAX-ACCESS  read-only
    STATUS  current
    DESCRIPTION
        "Type of area being used.
        Note:This mib is not supported for VX instance of virtualization."
    ::= { ospfCurCfgAreaEntry 5 }

ospfCurCfgAreaMetric OBJECT-TYPE
    SYNTAX INTEGER (1..65535)
    MAX-ACCESS read-only
    STATUS current
    DESCRIPTION
        "The Stub area metric for the OSPF area.
        Note:This mib is not supported for VX instance of virtualization."
    ::= { ospfCurCfgAreaEntry 6 }

ospfCurCfgAreaState OBJECT-TYPE
    SYNTAX INTEGER {
        on(1),
        off(2),
        unsupported(2147483647)
        }
    MAX-ACCESS read-only
    STATUS current
    DESCRIPTION
        "Globally turn OSPF on or off.
        Note:This mib is not supported for VX instance of virtualization."
    ::= { ospfCurCfgAreaEntry 7 }

ospfNewCfgAreaTable OBJECT-TYPE
    SYNTAX SEQUENCE OF OspfNewCfgAreaEntry
    MAX-ACCESS not-accessible
    STATUS current
    DESCRIPTION
      "The table of OSPF Area configuration in the new_config.
      Note:This mib is not supported for VX instance of virtualization."
    ::= { ospfCfg 3 }

ospfNewCfgAreaEntry OBJECT-TYPE
    SYNTAX OspfNewCfgAreaEntry
    MAX-ACCESS not-accessible
    STATUS current
    DESCRIPTION
      "Information about a OSPF area.
      Note:This mib is not supported for VX instance of virtualization."
    INDEX { ospfNewCfgAreaIndex, ospfNewCfgAreaId }
    ::= { ospfNewCfgAreaTable 1 }
 
OspfNewCfgAreaEntry ::= SEQUENCE {
    ospfNewCfgAreaIndex         Integer32,
    ospfNewCfgAreaId            IpAddress, 
    ospfNewCfgAreaSpfInterval   INTEGER,
    ospfNewCfgAreaAuthType      INTEGER,
    ospfNewCfgAreaType          INTEGER,
    ospfNewCfgAreaMetric        INTEGER,
    ospfNewCfgAreaState         INTEGER,
    ospfNewCfgAreaDelete        INTEGER
    }
 
ospfNewCfgAreaIndex OBJECT-TYPE
    SYNTAX Integer32
    MAX-ACCESS read-only 
    STATUS current
    DESCRIPTION
	"The OSPF area number for which the OSPF area table is related.
    Note:This mib is not supported for VX instance of virtualization."
    ::= { ospfNewCfgAreaEntry 1}

ospfNewCfgAreaId OBJECT-TYPE
    SYNTAX IpAddress 
    MAX-ACCESS read-only
    STATUS current
    DESCRIPTION
	"The IP Address of the OSPF area.
    Note:This mib is not supported for VX instance of virtualization." 
    ::= { ospfNewCfgAreaEntry 2 }

ospfNewCfgAreaSpfInterval OBJECT-TYPE
    SYNTAX INTEGER (0..255) 
    MAX-ACCESS read-create
    STATUS current
    DESCRIPTION
	"The SPF interval for the OSPF area.
    Note:This mib is not supported for VX instance of virtualization." 
    ::= { ospfNewCfgAreaEntry 3 }

ospfNewCfgAreaAuthType OBJECT-TYPE
    SYNTAX  INTEGER {
        none(1),
        password(2),
	md5(3),
        unsupported(2147483647)
        }
    MAX-ACCESS  read-create
    STATUS  current
    DESCRIPTION
        "Type of authentication being used.
	 none(1) - no authentication
	 password(2) - use password.
         md5(3) - use MD5 authentication.
         Note:This mib is not supported for VX instance of virtualization."
    ::= { ospfNewCfgAreaEntry 4 }

ospfNewCfgAreaType OBJECT-TYPE
    SYNTAX  INTEGER {
        transit(1),
        stub(2),
        nssa(3),
        unsupported(2147483647)
        }
    MAX-ACCESS  read-create
    STATUS  current
    DESCRIPTION
        "Type of area being used.
        Note:This mib is not supported for VX instance of virtualization."
    ::= { ospfNewCfgAreaEntry 5 }

ospfNewCfgAreaMetric OBJECT-TYPE
    SYNTAX INTEGER (1..65535)
    MAX-ACCESS read-create
    STATUS current
    DESCRIPTION
        "The Stub area metric for the OSPF area.
        Note:This mib is not supported for VX instance of virtualization."
    ::= { ospfNewCfgAreaEntry 6 }

ospfNewCfgAreaState OBJECT-TYPE
    SYNTAX INTEGER {
        enabled(1),
        disabled(2),
        unsupported(2147483647)
        }
    MAX-ACCESS read-create
    STATUS current
    DESCRIPTION
        "Enable or disable OSPF Area.
        Note:This mib is not supported for VX instance of virtualization."
    ::= { ospfNewCfgAreaEntry 7 }

ospfNewCfgAreaDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row.
         Note:This mib is not supported for VX instance of virtualization."
    ::= { ospfNewCfgAreaEntry 8 }



ospfNewCfgVisionAreaTable OBJECT-TYPE
    SYNTAX SEQUENCE OF OspfNewCfgVisionAreaEntry
    MAX-ACCESS not-accessible
    STATUS current
    DESCRIPTION
      "The table of OSPF Area configuration in the new_config.
      Note:This mib is not supported for VX instance of virtualization."
    ::= { ospfCfg 16 }

ospfNewCfgVisionAreaEntry OBJECT-TYPE
    SYNTAX OspfNewCfgVisionAreaEntry
    MAX-ACCESS not-accessible
    STATUS current
    DESCRIPTION
      "Information about a OSPF area.
      Note:This mib is not supported for VX instance of virtualization."
    INDEX { ospfNewCfgVisionAreaIndex }
    ::= { ospfNewCfgVisionAreaTable 1 }

OspfNewCfgVisionAreaEntry ::= SEQUENCE {
    ospfNewCfgVisionAreaIndex         Integer32,
    ospfNewCfgVisionAreaId            IpAddress,
    ospfNewCfgVisionAreaSpfInterval   INTEGER,
    ospfNewCfgVisionAreaAuthType      INTEGER,
    ospfNewCfgVisionAreaType          INTEGER,
    ospfNewCfgVisionAreaMetric        INTEGER,
    ospfNewCfgVisionAreaState         INTEGER,
    ospfNewCfgVisionAreaDelete        INTEGER
    }

ospfNewCfgVisionAreaIndex OBJECT-TYPE
    SYNTAX Integer32
    MAX-ACCESS read-only
    STATUS current
    DESCRIPTION
    "The OSPF area number for which the OSPF area table is related.
    Note:This mib is not supported for VX instance of virtualization."
    ::= { ospfNewCfgVisionAreaEntry 1}

ospfNewCfgVisionAreaId OBJECT-TYPE
    SYNTAX IpAddress
    MAX-ACCESS read-write
    STATUS current
    DESCRIPTION
    "The IP Address of the OSPF area.
    Note:This mib is not supported for VX instance of virtualization."
    ::= { ospfNewCfgVisionAreaEntry 2 }

ospfNewCfgVisionAreaSpfInterval OBJECT-TYPE
    SYNTAX INTEGER (0..255)
    MAX-ACCESS read-create
    STATUS current
    DESCRIPTION
    "The SPF interval for the OSPF area.
    Note:This mib is not supported for VX instance of virtualization."
    ::= { ospfNewCfgVisionAreaEntry 3 }

ospfNewCfgVisionAreaAuthType OBJECT-TYPE
    SYNTAX  INTEGER {
        none(1),
        password(2),
    md5(3),
        unsupported(2147483647)
        }
    MAX-ACCESS  read-create
    STATUS  current
    DESCRIPTION
        "Type of authentication being used.
     none(1) - no authentication
     password(2) - use password.
         md5(3) - use MD5 authentication.
         Note:This mib is not supported for VX instance of virtualization."
    ::= { ospfNewCfgVisionAreaEntry 4 }

ospfNewCfgVisionAreaType OBJECT-TYPE
    SYNTAX  INTEGER {
        transit(1),
        stub(2),
        nssa(3),
        unsupported(2147483647)
        }
    MAX-ACCESS  read-create
    STATUS  current
    DESCRIPTION
        "Type of area being used.
        Note:This mib is not supported for VX instance of virtualization."
    ::= { ospfNewCfgVisionAreaEntry 5 }

ospfNewCfgVisionAreaMetric OBJECT-TYPE
    SYNTAX INTEGER (1..65535)
    MAX-ACCESS read-create
    STATUS current
    DESCRIPTION
        "The Stub area metric for the OSPF area.
        Note:This mib is not supported for VX instance of virtualization."
    ::= { ospfNewCfgVisionAreaEntry 6 }

ospfNewCfgVisionAreaState OBJECT-TYPE
    SYNTAX INTEGER {
        enabled(1),
        disabled(2),
        unsupported(2147483647)
        }
    MAX-ACCESS read-create
    STATUS current
    DESCRIPTION
        "Enable or disable OSPF Area.
        Note:This mib is not supported for VX instance of virtualization."
    ::= { ospfNewCfgVisionAreaEntry 7 }

ospfNewCfgVisionAreaDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row.
         Note:This mib is not supported for VX instance of virtualization."
    ::= { ospfNewCfgVisionAreaEntry 8 }


-- OSPF Host Table

ospfCurCfgHostTable OBJECT-TYPE
    SYNTAX SEQUENCE OF OspfCurCfgHostEntry
    MAX-ACCESS not-accessible
    STATUS current
    DESCRIPTION
      "The table of OSPF Host configuration.
      Note:This mib is not supported for VX instance of virtualization."
    ::= { ospfCfg 12 }

ospfCurCfgHostEntry OBJECT-TYPE
    SYNTAX OspfCurCfgHostEntry
    MAX-ACCESS not-accessible
    STATUS current
    DESCRIPTION
      "Information about a OSPF host.
      Note:This mib is not supported for VX instance of virtualization."
    INDEX { ospfCurCfgHostIndex }
    ::= { ospfCurCfgHostTable 1 }
 
OspfCurCfgHostEntry ::= SEQUENCE {
    ospfCurCfgHostIndex         Integer32,
    ospfCurCfgHostIpAddr        IpAddress,
    ospfCurCfgHostAreaIndex     Integer32,
    ospfCurCfgHostCost		INTEGER,
    ospfCurCfgHostState		INTEGER
    }
 
ospfCurCfgHostIndex OBJECT-TYPE
    SYNTAX Integer32
    MAX-ACCESS read-only
    STATUS current
    DESCRIPTION
	"The OSPF host number for which the OSPF host table is related.
    Note:This mib is not supported for VX instance of virtualization."
    ::= { ospfCurCfgHostEntry 1}

ospfCurCfgHostIpAddr OBJECT-TYPE
    SYNTAX IpAddress 
    MAX-ACCESS read-only
    STATUS current
    DESCRIPTION
	"The IP Address of the OSPF host.
    Note:This mib is not supported for VX instance of virtualization." 
    ::= { ospfCurCfgHostEntry 2 }

ospfCurCfgHostAreaIndex OBJECT-TYPE
    SYNTAX Integer32
    MAX-ACCESS read-only
    STATUS current
    DESCRIPTION
	"The area index.
    Note:This mib is not supported for VX instance of virtualization."
    ::= { ospfCurCfgHostEntry 3 }

ospfCurCfgHostCost OBJECT-TYPE
    SYNTAX INTEGER (1..65535)
    MAX-ACCESS read-only
    STATUS current
    DESCRIPTION
        "Cost of the host entry.
        Note:This mib is not supported for VX instance of virtualization."
    ::= { ospfCurCfgHostEntry 4 }

ospfCurCfgHostState OBJECT-TYPE
    SYNTAX INTEGER {
        enabled(1),
        disabled(2),
        unsupported(2147483647)
        }
    MAX-ACCESS read-only
    STATUS current
    DESCRIPTION
        "Enable or disable Host Entry.
        Note:This mib is not supported for VX instance of virtualization."
    ::= { ospfCurCfgHostEntry 5 }

ospfNewCfgHostTable OBJECT-TYPE
    SYNTAX SEQUENCE OF OspfNewCfgHostEntry
    MAX-ACCESS not-accessible
    STATUS current
    DESCRIPTION
      "The table of OSPF Host configuration.
      Note:This mib is not supported for VX instance of virtualization."
    ::= { ospfCfg 13 }

ospfNewCfgHostEntry OBJECT-TYPE
    SYNTAX OspfNewCfgHostEntry
    MAX-ACCESS not-accessible
    STATUS current
    DESCRIPTION
      "Information about a OSPF host.
      Note:This mib is not supported for VX instance of virtualization."
    INDEX { ospfNewCfgHostIndex }
    ::= { ospfNewCfgHostTable 1 }
 
OspfNewCfgHostEntry ::= SEQUENCE {
    ospfNewCfgHostIndex         Integer32,
    ospfNewCfgHostIpAddr        IpAddress, 
    ospfNewCfgHostAreaIndex     Integer32,
    ospfNewCfgHostCost          INTEGER,
    ospfNewCfgHostState         INTEGER,
    ospfNewCfgHostDelete        INTEGER
    }
 
ospfNewCfgHostIndex OBJECT-TYPE
    SYNTAX Integer32
    MAX-ACCESS read-only 
    STATUS current
    DESCRIPTION
	"The OSPF host number for which the OSPF host table is related.
    Note:This mib is not supported for VX instance of virtualization."
    ::= { ospfNewCfgHostEntry 1}

ospfNewCfgHostIpAddr OBJECT-TYPE
    SYNTAX IpAddress 
    MAX-ACCESS read-create
    STATUS current
    DESCRIPTION
	"The IP Address of the OSPF host.
    Note:This mib is not supported for VX instance of virtualization." 
    ::= { ospfNewCfgHostEntry 2 }

ospfNewCfgHostAreaIndex OBJECT-TYPE
    SYNTAX Integer32 
    MAX-ACCESS read-create
    STATUS current
    DESCRIPTION
	"The OSPF area index.
    Note:This mib is not supported for VX instance of virtualization."
    ::= { ospfNewCfgHostEntry 3 }

ospfNewCfgHostCost OBJECT-TYPE
    SYNTAX INTEGER (1..65535)
    MAX-ACCESS read-create
    STATUS current
    DESCRIPTION
        "Cost of the host entry.
        Note:This mib is not supported for VX instance of virtualization."
    ::= { ospfNewCfgHostEntry 4 }

ospfNewCfgHostState OBJECT-TYPE
    SYNTAX INTEGER {
        enabled(1),
        disabled(2),
        unsupported(2147483647)
        }
    MAX-ACCESS read-create
    STATUS current
    DESCRIPTION
        "Enable or disable Host Entry.
        Note:This mib is not supported for VX instance of virtualization."
    ::= { ospfNewCfgHostEntry 5 }

ospfNewCfgHostDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row.
         Note:This mib is not supported for VX instance of virtualization."
    ::= { ospfNewCfgHostEntry 6 }

ospfMdkeyTableMaxSize OBJECT-TYPE
    SYNTAX  Integer32
    MAX-ACCESS  read-only
    STATUS  current
    DESCRIPTION
        "The maximum number of rows in the OSPF Mdkey table.
        Note:This mib is not supported for VX instance of virtualization."
    ::= { ospfCfg 11 }

ospfCurCfgMdkeyTable OBJECT-TYPE
    SYNTAX SEQUENCE OF OspfCurCfgMdkeyEntry
    MAX-ACCESS not-accessible
    STATUS current
    DESCRIPTION
      "The table of OSPF MD5 keys in the current_config.
      Note:This mib is not supported for VX instance of virtualization."
    ::= { ospfCfg 5 }

ospfCurCfgMdkeyEntry OBJECT-TYPE
    SYNTAX OspfCurCfgMdkeyEntry
    MAX-ACCESS not-accessible
    STATUS current
    DESCRIPTION
      "Information about an OSPF MD keys table.
      Note:This mib is not supported for VX instance of virtualization."
    INDEX { ospfCurCfgMdkeyIndex }
    ::= { ospfCurCfgMdkeyTable 1 }
 
OspfCurCfgMdkeyEntry ::= SEQUENCE {
    ospfCurCfgMdkeyIndex        Integer32,
    ospfCurCfgMdkeyKey          DisplayString
    }
 
ospfCurCfgMdkeyIndex OBJECT-TYPE
    SYNTAX Integer32
    MAX-ACCESS read-only 
    STATUS current
    DESCRIPTION
	"The OSPF MD5 Key number for which the OSPF MdKey table is related.
    Note:This mib is not supported for VX instance of virtualization."
    ::= { ospfCurCfgMdkeyEntry 1}

ospfCurCfgMdkeyKey OBJECT-TYPE
    SYNTAX DisplayString (SIZE(0..16)) 
    MAX-ACCESS read-only
    STATUS current
    DESCRIPTION
	"The character string representing the MD5 Key.
    Note:This mib is not supported for VX instance of virtualization." 
    ::= { ospfCurCfgMdkeyEntry 2 }

ospfNewCfgMdkeyTable OBJECT-TYPE
    SYNTAX SEQUENCE OF OspfNewCfgMdkeyEntry
    MAX-ACCESS not-accessible
    STATUS current
    DESCRIPTION
      "The table of OSPF MD5 keys in the new_config.
      Note:This mib is not supported for VX instance of virtualization."
    ::= { ospfCfg 6 }

ospfNewCfgMdkeyEntry OBJECT-TYPE
    SYNTAX OspfNewCfgMdkeyEntry
    MAX-ACCESS not-accessible
    STATUS current
    DESCRIPTION
      "Information about an OSPF MD keys table.
      Note:This mib is not supported for VX instance of virtualization."
    INDEX { ospfNewCfgMdkeyIndex }
    ::= { ospfNewCfgMdkeyTable 1 }
 
OspfNewCfgMdkeyEntry ::= SEQUENCE {
    ospfNewCfgMdkeyIndex        Integer32,
    ospfNewCfgMdkeyKey          DisplayString,
    ospfNewCfgMdkeyDelete       INTEGER 
    }
 
ospfNewCfgMdkeyIndex OBJECT-TYPE
    SYNTAX Integer32
    MAX-ACCESS read-only 
    STATUS current
    DESCRIPTION
	"The OSPF MD5 Key number for which the OSPF MdKey table is related.
    Note:This mib is not supported for VX instance of virtualization."
    ::= { ospfNewCfgMdkeyEntry 1}

ospfNewCfgMdkeyKey OBJECT-TYPE
    SYNTAX DisplayString (SIZE(0..16)) 
    MAX-ACCESS read-create
    STATUS current
    DESCRIPTION
	"The character string representing the MD5 Key.
    Note:This mib is not supported for VX instance of virtualization." 
    ::= { ospfNewCfgMdkeyEntry 2 }

ospfNewCfgMdkeyDelete OBJECT-TYPE
    SYNTAX  INTEGER { 
        other(1),
        delete(2),
        unsupported(2147483647)
    }
    MAX-ACCESS read-create 
    STATUS current
    DESCRIPTION
	"When set to the value of 2 (delete), the entire row is deleted. 
	 When read, other(1) is returned. Setting the value to anything 
         other than 2(delete) has no effect on the state of the row.
         Note:This mib is not supported for VX instance of virtualization."
    ::= { ospfNewCfgMdkeyEntry 3}


ospfCurCfgIntfTable OBJECT-TYPE
    SYNTAX SEQUENCE OF OspfCurCfgIntfEntry
    MAX-ACCESS not-accessible
    STATUS current
    DESCRIPTION
      "The table of OSPF Interface configuration in the current_config.
      Note:This mib is not supported for VX instance of virtualization."
    ::= { ospfCfg 7 }

ospfCurCfgIntfEntry OBJECT-TYPE
    SYNTAX OspfCurCfgIntfEntry
    MAX-ACCESS not-accessible
    STATUS current
    DESCRIPTION
      "Information about an OSPF Interface.
      Note:This mib is not supported for VX instance of virtualization."
    INDEX { ospfCurCfgIntfIndex }
    ::= { ospfCurCfgIntfTable 1 }
 
OspfCurCfgIntfEntry ::= SEQUENCE {
    ospfCurCfgIntfIndex         Integer32,
    ospfCurCfgIntfId            IpAddress,
    ospfCurCfgIntfMdkey         INTEGER,
    ospfCurCfgIntfAreaId        INTEGER,
    ospfCurCfgIntfPriority      INTEGER,
    ospfCurCfgIntfCost          INTEGER,
    ospfCurCfgIntfHello         INTEGER,
    ospfCurCfgIntfDead          INTEGER,
    ospfCurCfgIntfTransit       INTEGER,
    ospfCurCfgIntfRetrans       INTEGER,
    ospfCurCfgIntfKey           DisplayString,
    ospfCurCfgIntfState         INTEGER,
    ospfCurCfgIntfBfd           INTEGER
    }
 
ospfCurCfgIntfIndex OBJECT-TYPE
    SYNTAX Integer32
    MAX-ACCESS read-only
    STATUS current
    DESCRIPTION
	"The OSPF Interface number for which the OSPF Interface table is 
         related.
         Note:This mib is not supported for VX instance of virtualization."
    ::= { ospfCurCfgIntfEntry 1}

ospfCurCfgIntfId OBJECT-TYPE
    SYNTAX IpAddress 
    MAX-ACCESS read-only
    STATUS current
    DESCRIPTION
    "The IP Address of the OSPF interface.
    Note:This mib is not supported for VX instance of virtualization." 
    ::= { ospfCurCfgIntfEntry 2 }

ospfCurCfgIntfMdkey OBJECT-TYPE
    SYNTAX INTEGER (0..255) 
    MAX-ACCESS read-only
    STATUS current
    DESCRIPTION
	"The MD5 key for the OSPF interface
         0 (none) no MD5 authentication.
         Note:This mib is not supported for VX instance of virtualization." 
    ::= { ospfCurCfgIntfEntry 3 }

ospfCurCfgIntfAreaId OBJECT-TYPE
    SYNTAX INTEGER (0..2)
    MAX-ACCESS read-only
    STATUS current
    DESCRIPTION
        "Specify Area Index.
        Note:This mib is not supported for VX instance of virtualization."
    ::= { ospfCurCfgIntfEntry 4 }

ospfCurCfgIntfPriority OBJECT-TYPE
    SYNTAX INTEGER (1..65535)
    MAX-ACCESS read-only
    STATUS current
    DESCRIPTION
        "Specify interface router priority.
        Note:This mib is not supported for VX instance of virtualization."
    ::= { ospfCurCfgIntfEntry 5 }

ospfCurCfgIntfCost OBJECT-TYPE
    SYNTAX INTEGER (1..65535)
    MAX-ACCESS read-only
    STATUS current
    DESCRIPTION
        "Interface Cost.
        Note:This mib is not supported for VX instance of virtualization."
    ::= { ospfCurCfgIntfEntry 6 }

ospfCurCfgIntfHello OBJECT-TYPE
    SYNTAX INTEGER (1..65535)
    MAX-ACCESS read-only
    STATUS current
    DESCRIPTION
        "Hello interval in seconds.
        Note:This mib is not supported for VX instance of virtualization."
    ::= { ospfCurCfgIntfEntry 7 }

ospfCurCfgIntfDead OBJECT-TYPE
    SYNTAX INTEGER (1..65535)
    MAX-ACCESS read-only
    STATUS current
    DESCRIPTION
        "Dead interval in seconds.
        Note:This mib is not supported for VX instance of virtualization."
    ::= { ospfCurCfgIntfEntry 8 }

ospfCurCfgIntfTransit OBJECT-TYPE
    SYNTAX INTEGER (0..3600)
    MAX-ACCESS read-only
    STATUS current
    DESCRIPTION
        "Transit delay in seconds.
        Note:This mib is not supported for VX instance of virtualization."
    ::= { ospfCurCfgIntfEntry 9 }

ospfCurCfgIntfRetrans OBJECT-TYPE
    SYNTAX INTEGER (0..3600)
    MAX-ACCESS read-only
    STATUS current
    DESCRIPTION
        "Retransmit interval in seconds.
        Note:This mib is not supported for VX instance of virtualization."
    ::= { ospfCurCfgIntfEntry 10 }

ospfCurCfgIntfKey  OBJECT-TYPE
    SYNTAX   DisplayString (SIZE(0..8))
    MAX-ACCESS  read-only
    STATUS  current
    DESCRIPTION
        "Specify Authentication Key.
        Note:This mib is not supported for VX instance of virtualization."
    ::= { ospfCurCfgIntfEntry 11 }

ospfCurCfgIntfState OBJECT-TYPE
    SYNTAX INTEGER {
        enabled(1),
        disabled(2),
        unsupported(2147483647)
        }
    MAX-ACCESS read-only
    STATUS current
    DESCRIPTION
        "Enable or disable OSPF Interface.
        Note:This mib is not supported for VX instance of virtualization."
    ::= { ospfCurCfgIntfEntry 12 }

ospfCurCfgIntfBfd OBJECT-TYPE
    SYNTAX INTEGER {
        on(1),
        off(2),
        unsupported(2147483647)
        }
    MAX-ACCESS  read-only
    STATUS  current
    DESCRIPTION
        "Turn BFD on/off for the OSPF interface.
        Note:This mib is not supported for VX instance of virtualization."
    ::= { ospfCurCfgIntfEntry 13 }

ospfNewCfgIntfTable OBJECT-TYPE
    SYNTAX SEQUENCE OF OspfNewCfgIntfEntry
    MAX-ACCESS not-accessible
    STATUS current
    DESCRIPTION
      "The table of OSPF Interface configuration in the new_config.
      Note:This mib is not supported for VX instance of virtualization."
    ::= { ospfCfg 8 }

ospfNewCfgIntfEntry OBJECT-TYPE
    SYNTAX OspfNewCfgIntfEntry
    MAX-ACCESS not-accessible
    STATUS current
    DESCRIPTION
      "Information about an OSPF Interface.
      Note:This mib is not supported for VX instance of virtualization."
    INDEX { ospfNewCfgIntfIndex }
    ::= { ospfNewCfgIntfTable 1 }
 
OspfNewCfgIntfEntry ::= SEQUENCE {
    ospfNewCfgIntfIndex         Integer32,
    ospfNewCfgIntfId            IpAddress,
    ospfNewCfgIntfMdkey         INTEGER,
    ospfNewCfgIntfAreaId        INTEGER,
    ospfNewCfgIntfPriority      INTEGER,
    ospfNewCfgIntfCost          INTEGER,
    ospfNewCfgIntfHello         INTEGER,
    ospfNewCfgIntfDead          INTEGER,
    ospfNewCfgIntfTransit       INTEGER,
    ospfNewCfgIntfRetrans       INTEGER,
    ospfNewCfgIntfKey           DisplayString,
    ospfNewCfgIntfState         INTEGER,
    ospfNewCfgIntfDelete        INTEGER,
    ospfNewCfgIntfBfd           INTEGER
    }
 
ospfNewCfgIntfIndex OBJECT-TYPE
    SYNTAX Integer32
    MAX-ACCESS read-only
    STATUS current
    DESCRIPTION
	"The OSPF Interface number for which the OSPF Interface table is 
         related.
         Note:This mib is not supported for VX instance of virtualization."
    ::= { ospfNewCfgIntfEntry 1}

ospfNewCfgIntfId OBJECT-TYPE
    SYNTAX IpAddress 
    MAX-ACCESS read-only
    STATUS current
    DESCRIPTION
    "The IP Address of the OSPF interface.
    Note:This mib is not supported for VX instance of virtualization." 
    ::= { ospfNewCfgIntfEntry 2 }

ospfNewCfgIntfMdkey OBJECT-TYPE
    SYNTAX INTEGER (0..255) 
    MAX-ACCESS read-create
    STATUS current
    DESCRIPTION
	"The MD5 key for the OSPF interface
         0 (none) no MD5 authentication.
         Note:This mib is not supported for VX instance of virtualization." 
    ::= { ospfNewCfgIntfEntry 3 }

ospfNewCfgIntfAreaId OBJECT-TYPE
    SYNTAX INTEGER (0..2)
    MAX-ACCESS read-create
    STATUS current
    DESCRIPTION
        "Specify Area Index.
        Note:This mib is not supported for VX instance of virtualization."
    ::= { ospfNewCfgIntfEntry 4 }

ospfNewCfgIntfPriority OBJECT-TYPE
    SYNTAX INTEGER (1..65535)
    MAX-ACCESS read-create
    STATUS current
    DESCRIPTION
        "Specify interface router priority.
        Note:This mib is not supported for VX instance of virtualization."
    ::= { ospfNewCfgIntfEntry 5 }

ospfNewCfgIntfCost OBJECT-TYPE
    SYNTAX INTEGER (1..65535)
    MAX-ACCESS read-create
    STATUS current
    DESCRIPTION
        "Specify interface cost.
        Note:This mib is not supported for VX instance of virtualization."
    ::= { ospfNewCfgIntfEntry 6 }

ospfNewCfgIntfHello OBJECT-TYPE
    SYNTAX INTEGER (1..65535)
    MAX-ACCESS read-create
    STATUS current
    DESCRIPTION
        "Hello interval in seconds.
        Note:This mib is not supported for VX instance of virtualization."
    ::= { ospfNewCfgIntfEntry 7 }

ospfNewCfgIntfDead OBJECT-TYPE
    SYNTAX INTEGER (1..65535)
    MAX-ACCESS read-create
    STATUS current
    DESCRIPTION
        "Dead interval in seconds.
        Note:This mib is not supported for VX instance of virtualization."
    ::= { ospfNewCfgIntfEntry 8 }

ospfNewCfgIntfTransit OBJECT-TYPE
    SYNTAX INTEGER (0..3600)
    MAX-ACCESS read-create
    STATUS current
    DESCRIPTION
        "Transit delay in seconds.
        Note:This mib is not supported for VX instance of virtualization."
    ::= { ospfNewCfgIntfEntry 9 }

ospfNewCfgIntfRetrans OBJECT-TYPE
    SYNTAX INTEGER (0..3600)
    MAX-ACCESS read-create
    STATUS current
    DESCRIPTION
        "Retransmit interval in seconds.
        Note:This mib is not supported for VX instance of virtualization."
    ::= { ospfNewCfgIntfEntry 10 }

ospfNewCfgIntfKey  OBJECT-TYPE
    SYNTAX   DisplayString (SIZE(0..8))
    MAX-ACCESS  read-create
    STATUS  current
    DESCRIPTION
        "Specify Authentication Key.
        Note:This mib is not supported for VX instance of virtualization."
    ::= { ospfNewCfgIntfEntry 11 }

ospfNewCfgIntfState OBJECT-TYPE
    SYNTAX INTEGER {
        enabled(1),
        disabled(2),
        unsupported(2147483647)
        }
    MAX-ACCESS read-create
    STATUS current
    DESCRIPTION
        "Enable or disable OSPF Interface.
        Note:This mib is not supported for VX instance of virtualization."
    ::= { ospfNewCfgIntfEntry 12 }

ospfNewCfgIntfDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
         Note:This mib is not supported for VX instance of virtualization."
    ::= { ospfNewCfgIntfEntry 13 }

ospfNewCfgIntfBfd OBJECT-TYPE
    SYNTAX INTEGER {
        on(1),
        off(2),
        unsupported(2147483647)
        }
    MAX-ACCESS  read-create
    STATUS  current
    DESCRIPTION
        "Turn BFD on/off for the OSPF interface.
        Note:This mib is not supported for VX instance of virtualization."
    ::= { ospfNewCfgIntfEntry 14 }

ospfCurCfgVirtIntfTable OBJECT-TYPE
    SYNTAX SEQUENCE OF OspfCurCfgVirtIntfEntry
    MAX-ACCESS not-accessible
    STATUS current
    DESCRIPTION
      "The table of OSPF Virtual Interface configuration in the current 
       configuration.
       Note:This mib is not supported for VX instance of virtualization."
    ::= { ospfCfg 9 }

ospfCurCfgVirtIntfEntry OBJECT-TYPE
    SYNTAX OspfCurCfgVirtIntfEntry
    MAX-ACCESS not-accessible
    STATUS current
    DESCRIPTION
      "Information about an OSPF virtual Interface.
      Note:This mib is not supported for VX instance of virtualization."
    INDEX { ospfCurCfgVirtIntfIndex }
    ::= { ospfCurCfgVirtIntfTable 1 }
 
OspfCurCfgVirtIntfEntry ::= SEQUENCE {
    ospfCurCfgVirtIntfIndex         Integer32,
    ospfCurCfgVirtIntfAreaId        INTEGER,
    ospfCurCfgVirtIntfNbr           IpAddress,
    ospfCurCfgVirtIntfMdkey         INTEGER,
    ospfCurCfgVirtIntfHello         INTEGER,
    ospfCurCfgVirtIntfDead          INTEGER,
    ospfCurCfgVirtIntfTransit       INTEGER,
    ospfCurCfgVirtIntfRetrans       INTEGER,
    ospfCurCfgVirtIntfKey           DisplayString,
    ospfCurCfgVirtIntfState         INTEGER    
    }
 
ospfCurCfgVirtIntfIndex OBJECT-TYPE
    SYNTAX Integer32
    MAX-ACCESS read-only
    STATUS current
    DESCRIPTION
	"The OSPF Virtual Interface number for which the OSPF 
         Virtual Interface table is related.
         Note:This mib is not supported for VX instance of virtualization."
    ::= { ospfCurCfgVirtIntfEntry 1}

ospfCurCfgVirtIntfAreaId OBJECT-TYPE
    SYNTAX INTEGER (0..2)
    MAX-ACCESS read-only
    STATUS current
    DESCRIPTION
         "The OSPF Area Id.
         Note:This mib is not supported for VX instance of virtualization." 
    ::= { ospfCurCfgVirtIntfEntry 2 }

ospfCurCfgVirtIntfNbr OBJECT-TYPE
    SYNTAX IpAddress 
    MAX-ACCESS read-only
    STATUS current
    DESCRIPTION
	"The IP Address of the OSPF neighbour for this virtual interface.
    Note:This mib is not supported for VX instance of virtualization."
    ::= { ospfCurCfgVirtIntfEntry 3 }

ospfCurCfgVirtIntfMdkey OBJECT-TYPE
    SYNTAX INTEGER (0..255) 
    MAX-ACCESS read-only
    STATUS current
    DESCRIPTION
	"The MD5 key for the OSPF virtual interface
         0 (none) no MD5 authentication.
         Note:This mib is not supported for VX instance of virtualization." 
    ::= { ospfCurCfgVirtIntfEntry 4 }

ospfCurCfgVirtIntfHello OBJECT-TYPE
    SYNTAX INTEGER (1..65535)
    MAX-ACCESS read-only
    STATUS current
    DESCRIPTION
        "Hello interval in seconds.
        Note:This mib is not supported for VX instance of virtualization."
    ::= { ospfCurCfgVirtIntfEntry 5 }

ospfCurCfgVirtIntfDead OBJECT-TYPE
    SYNTAX INTEGER (1..65535)
    MAX-ACCESS read-only
    STATUS current
    DESCRIPTION
        "Dead interval in seconds.
        Note:This mib is not supported for VX instance of virtualization."
    ::= { ospfCurCfgVirtIntfEntry 6 }

ospfCurCfgVirtIntfTransit OBJECT-TYPE
    SYNTAX INTEGER (0..3600)
    MAX-ACCESS read-only
    STATUS current
    DESCRIPTION
        "Transit delay in seconds.
        Note:This mib is not supported for VX instance of virtualization."
    ::= { ospfCurCfgVirtIntfEntry 7 }

ospfCurCfgVirtIntfRetrans OBJECT-TYPE
    SYNTAX INTEGER (0..3600)
    MAX-ACCESS read-only
    STATUS current
    DESCRIPTION
        "Retransmit interval in seconds.
        Note:This mib is not supported for VX instance of virtualization."
    ::= { ospfCurCfgVirtIntfEntry 8 }

ospfCurCfgVirtIntfKey  OBJECT-TYPE
    SYNTAX   DisplayString (SIZE(0..8))
    MAX-ACCESS  read-only
    STATUS  current
    DESCRIPTION
        "Specify Authentication Key.
        Note:This mib is not supported for VX instance of virtualization."
    ::= { ospfCurCfgVirtIntfEntry 9 }

ospfCurCfgVirtIntfState OBJECT-TYPE
    SYNTAX INTEGER {
        enabled(1),
        disabled(2),
        unsupported(2147483647)
        }
    MAX-ACCESS read-only
    STATUS current
    DESCRIPTION
        "Enable or disable OSPF Interface.
        Note:This mib is not supported for VX instance of virtualization."
    ::= { ospfCurCfgVirtIntfEntry 10 }

ospfNewCfgVirtIntfTable OBJECT-TYPE
    SYNTAX SEQUENCE OF OspfNewCfgVirtIntfEntry
    MAX-ACCESS not-accessible
    STATUS current
    DESCRIPTION
      "The table of OSPF Virtual Interface configuration in the new_config.
      Note:This mib is not supported for VX instance of virtualization."
    ::= { ospfCfg 10 }

ospfNewCfgVirtIntfEntry OBJECT-TYPE
    SYNTAX OspfNewCfgVirtIntfEntry
    MAX-ACCESS not-accessible
    STATUS current
    DESCRIPTION
      "Information about an OSPF virtual Interface.
      Note:This mib is not supported for VX instance of virtualization."
    INDEX { ospfNewCfgVirtIntfIndex }
    ::= { ospfNewCfgVirtIntfTable 1 }
 
OspfNewCfgVirtIntfEntry ::= SEQUENCE {
    ospfNewCfgVirtIntfIndex         Integer32,
    ospfNewCfgVirtIntfAreaId        INTEGER,
    ospfNewCfgVirtIntfNbr           IpAddress,
    ospfNewCfgVirtIntfMdkey         INTEGER,
    ospfNewCfgVirtIntfHello         INTEGER,
    ospfNewCfgVirtIntfDead          INTEGER,
    ospfNewCfgVirtIntfTransit       INTEGER,
    ospfNewCfgVirtIntfRetrans       INTEGER,
    ospfNewCfgVirtIntfKey           DisplayString,
    ospfNewCfgVirtIntfState         INTEGER,
    ospfNewCfgVirtIntfDelete        INTEGER
    }
 
ospfNewCfgVirtIntfIndex OBJECT-TYPE
    SYNTAX Integer32
    MAX-ACCESS read-only
    STATUS current
    DESCRIPTION
	"The OSPF Virtual Interface number for which the OSPF 
         Virtual Interface table is related.
         Note:This mib is not supported for VX instance of virtualization."
    ::= { ospfNewCfgVirtIntfEntry 1}

ospfNewCfgVirtIntfAreaId OBJECT-TYPE
    SYNTAX INTEGER (0..2)
    MAX-ACCESS read-create
    STATUS current
    DESCRIPTION
  	    "The OSPF Area Id.
        Note:This mib is not supported for VX instance of virtualization." 
    ::= { ospfNewCfgVirtIntfEntry 2 }

ospfNewCfgVirtIntfNbr OBJECT-TYPE
    SYNTAX IpAddress 
    MAX-ACCESS read-create
    STATUS current
    DESCRIPTION
	"The IP Address of the OSPF neighbour for this virtual interface.
    Note:This mib is not supported for VX instance of virtualization."
    ::= { ospfNewCfgVirtIntfEntry 3 }

ospfNewCfgVirtIntfMdkey OBJECT-TYPE
    SYNTAX INTEGER (0..255) 
    MAX-ACCESS read-create
    STATUS current
    DESCRIPTION
	"The MD5 key for the OSPF virtual interface
         0 (none) no MD5 authentication.
         Note:This mib is not supported for VX instance of virtualization." 
    ::= { ospfNewCfgVirtIntfEntry 4 }

ospfNewCfgVirtIntfHello OBJECT-TYPE
    SYNTAX INTEGER (1..65535)
    MAX-ACCESS read-create
    STATUS current
    DESCRIPTION
        "Hello interval in seconds.
        Note:This mib is not supported for VX instance of virtualization."
    ::= { ospfNewCfgVirtIntfEntry 5 }

ospfNewCfgVirtIntfDead OBJECT-TYPE
    SYNTAX INTEGER (1..65535)
    MAX-ACCESS read-create
    STATUS current
    DESCRIPTION
        "Dead interval in seconds.
        Note:This mib is not supported for VX instance of virtualization."
    ::= { ospfNewCfgVirtIntfEntry 6 }

ospfNewCfgVirtIntfTransit OBJECT-TYPE
    SYNTAX INTEGER (0..3600)
    MAX-ACCESS read-create
    STATUS current
    DESCRIPTION
        "Transit delay in seconds.
        Note:This mib is not supported for VX instance of virtualization."
    ::= { ospfNewCfgVirtIntfEntry 7 }

ospfNewCfgVirtIntfRetrans OBJECT-TYPE
    SYNTAX INTEGER (0..3600)
    MAX-ACCESS read-create
    STATUS current
    DESCRIPTION
        "Retransmit interval in seconds.
        Note:This mib is not supported for VX instance of virtualization."
    ::= { ospfNewCfgVirtIntfEntry 8 }

ospfNewCfgVirtIntfKey  OBJECT-TYPE
    SYNTAX   DisplayString (SIZE(0..8)) 
    MAX-ACCESS  read-create
    STATUS  current
    DESCRIPTION
        "Specify Authentication Key.
         Enter string of 8 characters or None.
         Note:This mib is not supported for VX instance of virtualization."
    ::= { ospfNewCfgVirtIntfEntry 9 }

ospfNewCfgVirtIntfState OBJECT-TYPE
    SYNTAX INTEGER {
        enabled(1),
        disabled(2),
        unsupported(2147483647)
        }
    MAX-ACCESS read-create
    STATUS current
    DESCRIPTION
        "Enable or disable OSPF Interface.
        Note:This mib is not supported for VX instance of virtualization."
    ::= { ospfNewCfgVirtIntfEntry 10 }

ospfNewCfgVirtIntfDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
         Note:This mib is not supported for VX instance of virtualization."
    ::= { ospfNewCfgVirtIntfEntry 11 }

-- ospf range

ospfCurCfgRangeTable OBJECT-TYPE
    SYNTAX SEQUENCE OF OspfCurCfgRangeEntry
    MAX-ACCESS not-accessible
    STATUS current
    DESCRIPTION
      "The table of OSPF summary range in the current configuration.
      Note:This mib is not supported for VX instance of virtualization." 
    ::= { ospfCfg 14 }

ospfCurCfgRangeEntry OBJECT-TYPE
    SYNTAX OspfCurCfgRangeEntry 
    MAX-ACCESS not-accessible
    STATUS current
    DESCRIPTION
      "Information about an OSPF summary range.
      Note:This mib is not supported for VX instance of virtualization."
    INDEX { ospfCurCfgRangeIndex }
    ::= { ospfCurCfgRangeTable 1 }
 
OspfCurCfgRangeEntry ::= SEQUENCE {
    ospfCurCfgRangeIndex            Integer32,
    ospfCurCfgRangeAddr             IpAddress,
    ospfCurCfgRangeMask             IpAddress,
    ospfCurCfgRangeAreaIndex        Integer32,
    ospfCurCfgRangeHideState        INTEGER,
    ospfCurCfgRangeState            INTEGER
    }
 
ospfCurCfgRangeIndex OBJECT-TYPE
    SYNTAX Integer32
    MAX-ACCESS read-only
    STATUS current
    DESCRIPTION
	"The range number for which the OSPF summary range table is related.
    Note:This mib is not supported for VX instance of virtualization." 
    ::= { ospfCurCfgRangeEntry 1}

ospfCurCfgRangeAddr OBJECT-TYPE
    SYNTAX IpAddress 
    MAX-ACCESS read-only
    STATUS current
    DESCRIPTION
	"The IP Address of the range.
    Note:This mib is not supported for VX instance of virtualization." 
    ::= { ospfCurCfgRangeEntry 2 }

ospfCurCfgRangeMask OBJECT-TYPE
    SYNTAX IpAddress 
    MAX-ACCESS read-only
    STATUS current
    DESCRIPTION
	"The mask of the range.
    Note:This mib is not supported for VX instance of virtualization."
    ::= { ospfCurCfgRangeEntry 3 }

ospfCurCfgRangeAreaIndex OBJECT-TYPE
    SYNTAX Integer32
    MAX-ACCESS read-only
    STATUS current
    DESCRIPTION
        "The area index.
        Note:This mib is not supported for VX instance of virtualization."
    ::= { ospfCurCfgRangeEntry 4 }

ospfCurCfgRangeHideState OBJECT-TYPE
    SYNTAX  INTEGER {
        enabled(1),
        disabled(2),
        unsupported(2147483647)
        }
    MAX-ACCESS  read-only
    STATUS  current
    DESCRIPTION
        "The state of the hide range.
        Note:This mib is not supported for VX instance of virtualization."
    ::= { ospfCurCfgRangeEntry 5 }

ospfCurCfgRangeState OBJECT-TYPE
    SYNTAX  INTEGER {
        enabled(1),
        disabled(2),
        unsupported(2147483647)
        }
    MAX-ACCESS  read-only
    STATUS  current
    DESCRIPTION
        "The state of the range.
        Note:This mib is not supported for VX instance of virtualization."
    ::= { ospfCurCfgRangeEntry 6 }

ospfNewCfgRangeTable OBJECT-TYPE
    SYNTAX SEQUENCE OF OspfNewCfgRangeEntry
    MAX-ACCESS not-accessible
    STATUS current
    DESCRIPTION
      "The table of OSPF summary range in the new configuration.
      Note:This mib is not supported for VX instance of virtualization." 
    ::= { ospfCfg 15 }

ospfNewCfgRangeEntry OBJECT-TYPE
    SYNTAX OspfNewCfgRangeEntry 
    MAX-ACCESS not-accessible
    STATUS current
    DESCRIPTION
      "Information about an OSPF summary range.
      Note:This mib is not supported for VX instance of virtualization."
    INDEX { ospfNewCfgRangeIndex }
    ::= { ospfNewCfgRangeTable 1 }
 
OspfNewCfgRangeEntry ::= SEQUENCE {
    ospfNewCfgRangeIndex            Integer32,
    ospfNewCfgRangeAddr             IpAddress,
    ospfNewCfgRangeMask             IpAddress,
    ospfNewCfgRangeAreaIndex        Integer32,
    ospfNewCfgRangeHideState        INTEGER,
    ospfNewCfgRangeState            INTEGER,
    ospfNewCfgRangeDelete           INTEGER
    }
 
ospfNewCfgRangeIndex OBJECT-TYPE
    SYNTAX Integer32
    MAX-ACCESS read-only
    STATUS current
    DESCRIPTION
	"The range number for which the OSPF summary range table is related.
    Note:This mib is not supported for VX instance of virtualization." 
    ::= { ospfNewCfgRangeEntry 1}

ospfNewCfgRangeAddr OBJECT-TYPE
    SYNTAX IpAddress 
    MAX-ACCESS read-create 
    STATUS current
    DESCRIPTION
	"The IP Address of the range.
    Note:This mib is not supported for VX instance of virtualization." 
    ::= { ospfNewCfgRangeEntry 2 }

ospfNewCfgRangeMask OBJECT-TYPE
    SYNTAX IpAddress 
    MAX-ACCESS read-create 
    STATUS current
    DESCRIPTION
	"The mask of the range.
    Note:This mib is not supported for VX instance of virtualization."
    ::= { ospfNewCfgRangeEntry 3 }

ospfNewCfgRangeAreaIndex OBJECT-TYPE
    SYNTAX Integer32
    MAX-ACCESS read-create 
    STATUS current
    DESCRIPTION
        "The area index.
        Note:This mib is not supported for VX instance of virtualization."
    ::= { ospfNewCfgRangeEntry 4 }

ospfNewCfgRangeHideState OBJECT-TYPE
    SYNTAX  INTEGER {
        enabled(1),
        disabled(2),
        unsupported(2147483647)
        }
    MAX-ACCESS read-create 
    STATUS  current
    DESCRIPTION
        "The state of the hide range.
        Note:This mib is not supported for VX instance of virtualization."
    ::= { ospfNewCfgRangeEntry 5 }

ospfNewCfgRangeState OBJECT-TYPE
    SYNTAX  INTEGER {
        enabled(1),
        disabled(2),
        unsupported(2147483647)
        }
    MAX-ACCESS read-create 
    STATUS  current
    DESCRIPTION
        "The state of the range.
        Note:This mib is not supported for VX instance of virtualization."
    ::= { ospfNewCfgRangeEntry 6 }

ospfNewCfgRangeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
         Note:This mib is not supported for VX instance of virtualization."
    ::= { ospfNewCfgRangeEntry 7 }


ospfRouteRedistribution   OBJECT IDENTIFIER ::= { ospfCfg 4 }

ospfRedistributeStatic    OBJECT IDENTIFIER ::= { ospfRouteRedistribution 1 }

ospfCurCfgStaticMetric OBJECT-TYPE
    SYNTAX INTEGER (0..16777215)
    MAX-ACCESS read-only
    STATUS current
    DESCRIPTION
	"The metric to be assigned to static routes. 
         A value of 0 indicates none.
         Note:This mib is not supported for VX instance of virtualization."
    ::= { ospfRedistributeStatic 1 }

ospfNewCfgStaticMetric OBJECT-TYPE
    SYNTAX INTEGER (0..16777215)
    MAX-ACCESS read-write
    STATUS current
    DESCRIPTION
	"The metric to be assigned to static routes. 
         A value of 0 indicates none.
         Note:This mib is not supported for VX instance of virtualization."
    ::= { ospfRedistributeStatic 2 }

ospfCurCfgStaticMetricType OBJECT-TYPE
    SYNTAX INTEGER {
        none(1),
        type1(2),
        type2(3),
        unsupported(2147483647)
        }
    MAX-ACCESS read-only
    STATUS current
    DESCRIPTION
	"The AS External metric type for static routes.
    Note:This mib is not supported for VX instance of virtualization."
    ::= { ospfRedistributeStatic 3 }

ospfNewCfgStaticMetricType OBJECT-TYPE
    SYNTAX INTEGER {
        none(1),
        type1(2),
        type2(3),
        unsupported(2147483647)
        }
    MAX-ACCESS read-write
    STATUS current
    DESCRIPTION
	"The AS External metric type for static routes.
    Note:This mib is not supported for VX instance of virtualization."
    ::= { ospfRedistributeStatic 4 }

ospfCurCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeStatic 5 }

ospfNewCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeStatic 6 }

ospfNewCfgStaticAddOutRmap OBJECT-TYPE
    SYNTAX Integer32 
    MAX-ACCESS read-write
    STATUS current  
    DESCRIPTION
	"The route map to be add into out-rmap list. When read, 0 is returned.
	Note:This mib is not supported for VX instance of virtualization."
    ::= { ospfRedistributeStatic 7 }

ospfNewCfgStaticRemoveOutRmap OBJECT-TYPE
    SYNTAX Integer32 
    MAX-ACCESS read-write
    STATUS current  
    DESCRIPTION
	"The route map to be removed from out-rmap list. When read, 
         0 is returned.
         Note:This mib is not supported for VX instance of virtualization."
    ::= { ospfRedistributeStatic 8 }

ospfRedistributeEbgp    OBJECT IDENTIFIER ::= { ospfRouteRedistribution 2 }

ospfCurCfgEbgpMetric OBJECT-TYPE
    SYNTAX INTEGER (0..16777215)
    MAX-ACCESS read-only
    STATUS current
    DESCRIPTION
	"The export metric to be assigned to External BGP routes.
         A value of 0 indicates none.
         Note:This mib is not supported for VX instance of virtualization."
    ::= { ospfRedistributeEbgp 1 }

ospfNewCfgEbgpMetric OBJECT-TYPE
    SYNTAX INTEGER (0..16777215)
    MAX-ACCESS read-write
    STATUS current
    DESCRIPTION
	"The export metric to be assigned to External BGP routes.
         A value of 0 indicates none.
         Note:This mib is not supported for VX instance of virtualization."
    ::= { ospfRedistributeEbgp 2 }

ospfCurCfgEbgpMetricType OBJECT-TYPE
    SYNTAX INTEGER {
        none(1),
        type1(2),
        type2(3),
        unsupported(2147483647)
        }
    MAX-ACCESS read-only
    STATUS current
    DESCRIPTION
	"The AS External metric type for External BGP routes.
    Note:This mib is not supported for VX instance of virtualization."
    ::= { ospfRedistributeEbgp 3 }

ospfNewCfgEbgpMetricType OBJECT-TYPE
    SYNTAX INTEGER {
        none(1),
        type1(2),
        type2(3),
        unsupported(2147483647)
        }
    MAX-ACCESS read-write
    STATUS current
    DESCRIPTION
	"The AS External metric type for External BGP routes.
	Note:This mib is not supported for VX instance of virtualization."
    ::= { ospfRedistributeEbgp 4 }

ospfCurCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeEbgp 5 }

ospfNewCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeEbgp 6 }

ospfNewCfgEbgpAddOutRmap OBJECT-TYPE
    SYNTAX Integer32 
    MAX-ACCESS read-write
    STATUS current  
    DESCRIPTION
	"The route map to be added into out-rmap list. When read, 0 is returned.
	Note:This mib is not supported for VX instance of virtualization."
    ::= { ospfRedistributeEbgp 7 }

ospfNewCfgEbgpRemoveOutRmap OBJECT-TYPE
    SYNTAX Integer32 
    MAX-ACCESS read-write
    STATUS current  
    DESCRIPTION
	"The route map to be removed from out-rmap list. When read, 
         0 is returned.
         Note:This mib is not supported for VX instance of virtualization."
    ::= { ospfRedistributeEbgp 8 }

ospfRedistributeIbgp    OBJECT IDENTIFIER ::= { ospfRouteRedistribution 3 }

ospfCurCfgIbgpMetric OBJECT-TYPE
    SYNTAX INTEGER (0..16777215)
    MAX-ACCESS read-only
    STATUS current
    DESCRIPTION
	"The export metric for Internal BGP routes.
         A value of 0 indicates none.
	Note:This mib is not supported for VX instance of virtualization."
    ::= { ospfRedistributeIbgp 1 }

ospfNewCfgIbgpMetric OBJECT-TYPE
    SYNTAX INTEGER (0..16777215)
    MAX-ACCESS read-write
    STATUS current
    DESCRIPTION
	"The export metric for Internal BGP routes.
         A value of 0 indicates none.
	Note:This mib is not supported for VX instance of virtualization."
    ::= { ospfRedistributeIbgp 2 }

ospfCurCfgIbgpMetricType OBJECT-TYPE
    SYNTAX INTEGER {
        none(1),
        type1(2),
        type2(3),
        unsupported(2147483647)
        }
    MAX-ACCESS read-only
    STATUS current
    DESCRIPTION
	"The AS External metric type for Internal BGP routes.
	Note:This mib is not supported for VX instance of virtualization."
    ::= { ospfRedistributeIbgp 3 }

ospfNewCfgIbgpMetricType OBJECT-TYPE
    SYNTAX INTEGER {
        none(1),
        type1(2),
        type2(3),
        unsupported(2147483647)
        }
    MAX-ACCESS read-write
    STATUS current
    DESCRIPTION
	"The AS External metric type for Internal BGP routes.
	Note:This mib is not supported for VX instance of virtualization."
    ::= { ospfRedistributeIbgp 4 }

ospfCurCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeIbgp 5 }

ospfNewCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeIbgp 6 }

ospfNewCfgIbgpAddOutRmap OBJECT-TYPE
    SYNTAX Integer32 
    MAX-ACCESS read-write
    STATUS current  
    DESCRIPTION
	"The route map to be add into out-rmap list. When read, 0 is returned.
	Note:This mib is not supported for VX instance of virtualization."
    ::= { ospfRedistributeIbgp 7 }

ospfNewCfgIbgpRemoveOutRmap OBJECT-TYPE
    SYNTAX Integer32 
    MAX-ACCESS read-write
    STATUS current  
    DESCRIPTION
	"The route map to be removed from out-rmap list. When read, 
         0 is returned.
	Note:This mib is not supported for VX instance of virtualization."
    ::= { ospfRedistributeIbgp 8 }

ospfRedistributeFixed    OBJECT IDENTIFIER ::= { ospfRouteRedistribution 4 }

ospfCurCfgFixedMetric OBJECT-TYPE
    SYNTAX INTEGER (0..16777215)
    MAX-ACCESS read-only
    STATUS current
    DESCRIPTION
	"The export metric for fixed routes. A value of 0 indicates none.
    Note:This mib is not supported for VX instance of virtualization."
    ::= { ospfRedistributeFixed 1 }

ospfNewCfgFixedMetric OBJECT-TYPE
    SYNTAX INTEGER (0..16777215)
    MAX-ACCESS read-write
    STATUS current
    DESCRIPTION
	"The export metric for fixed routes. A value of 0 indicates none.
    Note:This mib is not supported for VX instance of virtualization."
    ::= { ospfRedistributeFixed 2 }

ospfCurCfgFixedMetricType OBJECT-TYPE
    SYNTAX INTEGER {
        none(1),
        type1(2),
        type2(3),
        unsupported(2147483647)
        }
    MAX-ACCESS read-only
    STATUS current
    DESCRIPTION
	"The AS External metric type for fixed routes.
	Note:This mib is not supported for VX instance of virtualization."
    ::= { ospfRedistributeFixed 3 }

ospfNewCfgFixedMetricType OBJECT-TYPE
    SYNTAX INTEGER {
        none(1),
        type1(2),
        type2(3),
        unsupported(2147483647)
        }
    MAX-ACCESS read-write
    STATUS current
    DESCRIPTION
	"The AS External metric type for fixed routes.
	Note:This mib is not supported for VX instance of virtualization."
    ::= { ospfRedistributeFixed 4 }

ospfCurCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeFixed 5 }

ospfNewCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeFixed 6 }

ospfNewCfgFixedAddOutRmap OBJECT-TYPE
    SYNTAX Integer32 
    MAX-ACCESS read-write
    STATUS current  
    DESCRIPTION
	"The route map to be add into out-rmap list. When read, 0 is returned.
	Note:This mib is not supported for VX instance of virtualization."
    ::= { ospfRedistributeFixed 7 }

ospfNewCfgFixedRemoveOutRmap OBJECT-TYPE
    SYNTAX Integer32 
    MAX-ACCESS read-write
    STATUS current  
    DESCRIPTION
	"The route map to be removed from out-rmap list. When read, 
         0 is returned.
	Note:This mib is not supported for VX instance of virtualization."
    ::= { ospfRedistributeFixed 8 }

ospfRedistributeRip    OBJECT IDENTIFIER ::= { ospfRouteRedistribution 5 }

ospfCurCfgRipMetric OBJECT-TYPE
    SYNTAX INTEGER (0..16777215)
    MAX-ACCESS read-only
    STATUS current
    DESCRIPTION
	"The export metric for RIP routes. A value of 0 indicates none.
	Note:This mib is not supported for VX instance of virtualization."
    ::= { ospfRedistributeRip 1 }

ospfNewCfgRipMetric OBJECT-TYPE
    SYNTAX INTEGER (0..16777215)
    MAX-ACCESS read-write
    STATUS current
    DESCRIPTION
	"The export metric for RIP routes. A value of 0 indicates none.
	Note:This mib is not supported for VX instance of virtualization."
    ::= { ospfRedistributeRip 2 }

ospfCurCfgRipMetricType OBJECT-TYPE
    SYNTAX INTEGER {
        none(1),
        type1(2),
        type2(3),
        unsupported(2147483647)
        }
    MAX-ACCESS read-only
    STATUS current
    DESCRIPTION
	"The AS External metric type for RIP routes.
	Note:This mib is not supported for VX instance of virtualization."
    ::= { ospfRedistributeRip 3 }

ospfNewCfgRipMetricType OBJECT-TYPE
    SYNTAX INTEGER {
        none(1),
        type1(2),
        type2(3),
        unsupported(2147483647)
        }
    MAX-ACCESS read-write
    STATUS current
    DESCRIPTION
	"The AS External metric type for RIP routes.
	Note:This mib is not supported for VX instance of virtualization."
    ::= { ospfRedistributeRip 4 }

ospfCurCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeRip 5 }

ospfNewCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfRedistributeRip 6 }

ospfNewCfgRipAddOutRmap OBJECT-TYPE
    SYNTAX Integer32 
    MAX-ACCESS read-write
    STATUS current  
    DESCRIPTION
	"The route map to be add into out-rmap list. When read, 0 is returned.
	Note:This mib is not supported for VX instance of virtualization."
    ::= { ospfRedistributeRip 7 }

ospfNewCfgRipRemoveOutRmap OBJECT-TYPE
    SYNTAX Integer32 
    MAX-ACCESS read-write
    STATUS current  
    DESCRIPTION
	"The route map to be removed from out-rmap list. When read, 
         0 is returned.
	Note:This mib is not supported for VX instance of virtualization."
    ::= { ospfRedistributeRip 8 }
--
-- IP OSPFv3 configuration
--
ospfv3General   OBJECT IDENTIFIER ::= { ospfv3Cfg 1 }

ospfv3CurCfgDefaultRouteMetric OBJECT-TYPE
    SYNTAX INTEGER (0..16777215)
    MAX-ACCESS read-only
    STATUS current
    DESCRIPTION
    "Specify the metric to be assigned.
	Note:This mib is not supported for VX instance of virtualization."
    ::= { ospfv3General 1 }

ospfv3NewCfgDefaultRouteMetric OBJECT-TYPE
    SYNTAX INTEGER (0..16777215)
    MAX-ACCESS read-write
    STATUS current
    DESCRIPTION
    "Specify the metric to be assigned.
	Note:This mib is not supported for VX instance of virtualization."
    ::= { ospfv3General 2 }

ospfv3CurCfgDefaultRouteMetricType OBJECT-TYPE
    SYNTAX INTEGER {
        none(1),
        type1(2),
        type2(3),
        unsupported(2147483647)
        }
    MAX-ACCESS read-only
    STATUS current
    DESCRIPTION
    "Specify the AS External metric type to be assigned.
	Note:This mib is not supported for VX instance of virtualization."
    ::= { ospfv3General 3 }

ospfv3NewCfgDefaultRouteMetricType OBJECT-TYPE
    SYNTAX INTEGER {
        none(1),
        type1(2),
        type2(3),
        unsupported(2147483647)
        }
    MAX-ACCESS read-write
    STATUS current
    DESCRIPTION
    "Specify the AS External metric type to be assigned.
	Note:This mib is not supported for VX instance of virtualization."
    ::= { ospfv3General 4 }

ospfv3IntfTableMaxSize OBJECT-TYPE
    SYNTAX Integer32
    MAX-ACCESS read-only
    STATUS current
    DESCRIPTION
        "The maximum number of rows in the OSPF Interface table.
        Note:This mib is not supported for VX instance of virtualization."
    ::= { ospfv3General 5 }

ospfv3AreaTableMaxSize OBJECT-TYPE
    SYNTAX Integer32
    MAX-ACCESS read-only
    STATUS current
    DESCRIPTION
        "The maximum number of rows in the OSPF Area table.
        Note:This mib is not supported for VX instance of virtualization."
    ::= { ospfv3General 6 }

ospfv3RangeTableMaxSize OBJECT-TYPE
    SYNTAX Integer32
    MAX-ACCESS read-only
    STATUS current
    DESCRIPTION
        "The maximum number of rows in the OSPF Range table.
        Note:This mib is not supported for VX instance of virtualization."
    ::= { ospfv3General 7 }

ospfv3VirtIntfTableMaxSize OBJECT-TYPE
    SYNTAX Integer32
    MAX-ACCESS read-only
    STATUS current
    DESCRIPTION
        "The maximum number of rows in the OSPF Virtual Interface
         table.
         Note:This mib is not supported for VX instance of virtualization."
    ::= { ospfv3General 8 }

ospfv3HostTableMaxSize OBJECT-TYPE
    SYNTAX Integer32
    MAX-ACCESS read-only
    STATUS current
    DESCRIPTION
        "The maximum number of rows in the OSPF Host table.
        Note:This mib is not supported for VX instance of virtualization."
    ::= { ospfv3General 9 }

ospfv3CurCfgState OBJECT-TYPE
    SYNTAX INTEGER {
        on(1),
        off(2),
        unsupported(2147483647)
        }
    MAX-ACCESS read-only
    STATUS current
    DESCRIPTION
    "OSPF global state.
    Note:This mib is not supported for VX instance of virtualization."
    ::= { ospfv3General 10 }

ospfv3NewCfgState OBJECT-TYPE
    SYNTAX INTEGER {
        on(1),
        off(2),
        unsupported(2147483647)
        }
    MAX-ACCESS read-write
    STATUS current
    DESCRIPTION
    "Globally turn OSPF on or off.
    Note:This mib is not supported for VX instance of virtualization."
    ::= { ospfv3General 11 }

ospfv3CurCfgLsdb OBJECT-TYPE
    SYNTAX INTEGER (0..2000)
    MAX-ACCESS read-only
    STATUS current
    DESCRIPTION
        "Specify the LSDB limit for external LSA.
        Note:This mib is not supported for VX instance of virtualization."
    ::= { ospfv3General 12 }

ospfv3NewCfgLsdb OBJECT-TYPE
    SYNTAX INTEGER (0..2000)
    MAX-ACCESS read-write
    STATUS current
    DESCRIPTION
        "Specify the LSDB limit for external LSA.
        Note:This mib is not supported for VX instance of virtualization."
    ::= { ospfv3General 13 }

ospfv3CurCfgAreaTable OBJECT-TYPE
    SYNTAX SEQUENCE OF Ospfv3CurCfgAreaEntry
    MAX-ACCESS not-accessible
    STATUS current
    DESCRIPTION
      "The table of OSPFv3 Area configuration in the current_config.
      Note:This mib is not supported for VX instance of virtualization."
    ::= { ospfv3Cfg 2 }

ospfv3CurCfgAreaEntry OBJECT-TYPE
    SYNTAX Ospfv3CurCfgAreaEntry
    MAX-ACCESS not-accessible
    STATUS current
    DESCRIPTION
      "Information about a OSPFv3 area.
      Note:This mib is not supported for VX instance of virtualization."
    INDEX { ospfv3CurCfgAreaIndex, ospfv3CurCfgAreaId }
    ::= { ospfv3CurCfgAreaTable 1 }
 
Ospfv3CurCfgAreaEntry ::= SEQUENCE {
    ospfv3CurCfgAreaIndex         Integer32,
    ospfv3CurCfgAreaId            IpAddress,
    ospfv3CurCfgAreaSpfInterval   INTEGER,
    ospfv3CurCfgAreaType          INTEGER,
    ospfv3CurCfgAreaMetric        INTEGER,
    ospfv3CurCfgAreaMType         INTEGER,
    ospfv3CurCfgAreaSummary       INTEGER,
    ospfv3CurCfgAreaTrRole        INTEGER,  
    ospfv3CurCfgAreaState         INTEGER,
    ospfv3CurCfgAreaIDRW          IpAddress
    }
 
ospfv3CurCfgAreaIndex OBJECT-TYPE
    SYNTAX Integer32
    MAX-ACCESS read-only
    STATUS current
    DESCRIPTION
    "The OSPFv3 area number for which the OSPF area table is related.
	Note:This mib is not supported for VX instance of virtualization."
    ::= { ospfv3CurCfgAreaEntry 1}

ospfv3CurCfgAreaId OBJECT-TYPE
    SYNTAX IpAddress 
    MAX-ACCESS read-only
    STATUS current
    DESCRIPTION
    "The IP Address of the OSPFv3 area.
	Note:This mib is not supported for VX instance of virtualization." 
    ::= { ospfv3CurCfgAreaEntry 2 }

ospfv3CurCfgAreaSpfInterval OBJECT-TYPE
    SYNTAX INTEGER (0..255) 
    MAX-ACCESS read-only
    STATUS current
    DESCRIPTION
    "The SPF interval for the OSPFv3 area.
	Note:This mib is not supported for VX instance of virtualization." 
    ::= { ospfv3CurCfgAreaEntry 3 }

ospfv3CurCfgAreaType OBJECT-TYPE
    SYNTAX  INTEGER {
        transit(1),
        stub(2),
        nssa(3),
        unsupported(2147483647)
        }
    MAX-ACCESS  read-only
    STATUS  current
    DESCRIPTION
        "Type of area being used.
        Note:This mib is not supported for VX instance of virtualization."
    ::= { ospfv3CurCfgAreaEntry 4 }

ospfv3CurCfgAreaMetric OBJECT-TYPE
    SYNTAX INTEGER (1..65535)
    MAX-ACCESS read-only
    STATUS current
    DESCRIPTION
        "The Stub area metric for the OSPFv3 area.
        Note:This mib is not supported for VX instance of virtualization."
    ::= { ospfv3CurCfgAreaEntry 5 }
    
ospfv3CurCfgAreaMType OBJECT-TYPE
    SYNTAX INTEGER {
        v3(1),
        compare-cost(2),
        non-compare(3),
        unsupported(2147483647)
        }
    MAX-ACCESS read-only
    STATUS current
    DESCRIPTION
        "Metric type.
        Note:This mib is not supported for VX instance of virtualization."
    ::= { ospfv3CurCfgAreaEntry 6 }
    
ospfv3CurCfgAreaSummary OBJECT-TYPE
    SYNTAX INTEGER {
        ena(1),
        dis(2),
        unsupported(2147483647)
        }
    MAX-ACCESS read-only
    STATUS current
    DESCRIPTION
        "Area summary import ena/dis.
        Note:This mib is not supported for VX instance of virtualization."
    ::= { ospfv3CurCfgAreaEntry 7 }
    
ospfv3CurCfgAreaTrRole OBJECT-TYPE
    SYNTAX INTEGER {
        always(1),
        candidate(2),
        unsupported(2147483647)
        }
    MAX-ACCESS read-only
    STATUS current
    DESCRIPTION
        "Translator role.
        Note:This mib is not supported for VX instance of virtualization."
    ::= { ospfv3CurCfgAreaEntry 8 }

ospfv3CurCfgAreaState OBJECT-TYPE
    SYNTAX INTEGER {
        on(1),
        off(2),
        unsupported(2147483647)
        }
    MAX-ACCESS read-only
    STATUS current
    DESCRIPTION
        "Globally turn OSPFv3 on or off.
        Note:This mib is not supported for VX instance of virtualization."
    ::= { ospfv3CurCfgAreaEntry 9 }

ospfv3CurCfgAreaIDRW OBJECT-TYPE
    SYNTAX IpAddress
    MAX-ACCESS read-only
    STATUS current
    DESCRIPTION
    "The IP Address of the OSPFv3 area.
    Note:This mib is not supported for VX instance of virtualization."
    ::= { ospfv3CurCfgAreaEntry 10 }

ospfv3NewCfgAreaTable OBJECT-TYPE
    SYNTAX SEQUENCE OF Ospfv3NewCfgAreaEntry
    MAX-ACCESS not-accessible
    STATUS current
    DESCRIPTION
      "The table of OSPFv3 Area configuration in the new_config.
      Note:This mib is not supported for VX instance of virtualization."
    ::= { ospfv3Cfg 3 }

ospfv3NewCfgAreaEntry OBJECT-TYPE
    SYNTAX Ospfv3NewCfgAreaEntry
    MAX-ACCESS not-accessible
    STATUS current
    DESCRIPTION
      "Information about a OSPFv3 area.
	Note:This mib is not supported for VX instance of virtualization."
    INDEX { ospfv3NewCfgAreaIndex, ospfv3NewCfgAreaId }
    ::= { ospfv3NewCfgAreaTable 1 }
 
Ospfv3NewCfgAreaEntry ::= SEQUENCE {
    ospfv3NewCfgAreaIndex         Integer32,
    ospfv3NewCfgAreaId            IpAddress, 
    ospfv3NewCfgAreaSpfInterval   INTEGER,
    ospfv3NewCfgAreaType          INTEGER,
    ospfv3NewCfgAreaMetric        INTEGER,
    ospfv3NewCfgAreaMType         INTEGER,
    ospfv3NewCfgAreaSummary       INTEGER,
    ospfv3NewCfgAreaTrRole        INTEGER,
    ospfv3NewCfgAreaState         INTEGER,
    ospfv3NewCfgAreaDelete        INTEGER,
    ospfv3NewCfgAreaIDRW          IpAddress
    }
 
ospfv3NewCfgAreaIndex OBJECT-TYPE
    SYNTAX Integer32
    MAX-ACCESS read-only 
    STATUS current
    DESCRIPTION
    "The OSPFv3 area number for which the area table is related.
	Note:This mib is not supported for VX instance of virtualization."
    ::= { ospfv3NewCfgAreaEntry 1}

ospfv3NewCfgAreaId OBJECT-TYPE
    SYNTAX IpAddress 
    MAX-ACCESS read-only
    STATUS current
    DESCRIPTION
    "The octal notation of the OSPFv3 area.
	Note:This mib is not supported for VX instance of virtualization." 
    ::= { ospfv3NewCfgAreaEntry 2 }

ospfv3NewCfgAreaSpfInterval OBJECT-TYPE
    SYNTAX INTEGER (0..255) 
    MAX-ACCESS read-create
    STATUS current
    DESCRIPTION
    "The SPF interval for the OSPFv3 area.
	Note:This mib is not supported for VX instance of virtualization." 
    ::= { ospfv3NewCfgAreaEntry 3 }

ospfv3NewCfgAreaType OBJECT-TYPE
    SYNTAX  INTEGER {
        transit(1),
        stub(2),
        nssa(3),
        unsupported(2147483647)
        }
    MAX-ACCESS  read-create
    STATUS  current
    DESCRIPTION
        "Type of area being used.
        Note:This mib is not supported for VX instance of virtualization."
    ::= { ospfv3NewCfgAreaEntry 4 }

ospfv3NewCfgAreaMetric OBJECT-TYPE
    SYNTAX INTEGER (1..65535)
    MAX-ACCESS read-create
    STATUS current
    DESCRIPTION
        "The Stub area metric for the OSPFv3 area.
        Note:This mib is not supported for VX instance of virtualization."
    ::= { ospfv3NewCfgAreaEntry 5 }
    
ospfv3NewCfgAreaMType OBJECT-TYPE
    SYNTAX INTEGER {
        v3(1),
        compare-cost(2),
        non-compare(3),
        unsupported(2147483647)
        }
    MAX-ACCESS read-create
    STATUS current
    DESCRIPTION
    "Metric type.
	Note:This mib is not supported for VX instance of virtualization."
    ::= { ospfv3NewCfgAreaEntry 6}
    
ospfv3NewCfgAreaSummary OBJECT-TYPE
    SYNTAX INTEGER {
        enabled(1),
        disabled(2),
        unsupported(2147483647)
        }
    MAX-ACCESS read-create 
    STATUS current
    DESCRIPTION
    "Ospfv3 summary import ena/dis.
	Note:This mib is not supported for VX instance of virtualization."
    ::= { ospfv3NewCfgAreaEntry 7}
    
ospfv3NewCfgAreaTrRole OBJECT-TYPE
    SYNTAX INTEGER {
        always(1),
        candidate(2),
        unsupported(2147483647)
        }
    MAX-ACCESS read-create 
    STATUS current
    DESCRIPTION
    "Translator role.
	Note:This mib is not supported for VX instance of virtualization."
    ::= { ospfv3NewCfgAreaEntry 8}

ospfv3NewCfgAreaState OBJECT-TYPE
    SYNTAX INTEGER {
        enabled(1),
        disabled(2),
        unsupported(2147483647)
        }
    MAX-ACCESS read-create
    STATUS current
    DESCRIPTION
        "Enable or disable OSPFv3 Area.
        Note:This mib is not supported for VX instance of virtualization."
    ::= { ospfv3NewCfgAreaEntry 9 }

ospfv3NewCfgAreaDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row.
         Note:This mib is not supported for VX instance of virtualization."
    ::= { ospfv3NewCfgAreaEntry 10 }

ospfv3NewCfgAreaIDRW OBJECT-TYPE
    SYNTAX IpAddress
    MAX-ACCESS read-create
    STATUS current
    DESCRIPTION
    "The octal notation of the OSPFv3 area.
    Note:This mib is not supported for VX instance of virtualization."
    ::= { ospfv3NewCfgAreaEntry 11 }

-- OSPFv3 Host Table

ospfv3CurCfgHostTable OBJECT-TYPE
    SYNTAX SEQUENCE OF Ospfv3CurCfgHostEntry
    MAX-ACCESS not-accessible
    STATUS current
    DESCRIPTION
      "The table of OSPFv3 Host configuration.
      Note:This mib is not supported for VX instance of virtualization."
    ::= { ospfv3Cfg 12 }

ospfv3CurCfgHostEntry OBJECT-TYPE
    SYNTAX Ospfv3CurCfgHostEntry
    MAX-ACCESS not-accessible
    STATUS current
    DESCRIPTION
      "Information about a OSPFv3 host.
      Note:This mib is not supported for VX instance of virtualization."
    INDEX { ospfv3CurCfgHostIndex }
    ::= { ospfv3CurCfgHostTable 1 }
 
Ospfv3CurCfgHostEntry ::= SEQUENCE {
    ospfv3CurCfgHostIndex         Integer32,
    ospfv3CurCfgHostIp6Addr       DisplayString,
    ospfv3CurCfgHostAreaIndex     Integer32,
    ospfv3CurCfgHostCost          INTEGER,
    ospfv3CurCfgHostState         INTEGER
    }
 
ospfv3CurCfgHostIndex OBJECT-TYPE
    SYNTAX Integer32
    MAX-ACCESS read-only
    STATUS current
    DESCRIPTION
    "The OSPFv3 host number for which the OSPF host table is related.
	Note:This mib is not supported for VX instance of virtualization."
    ::= { ospfv3CurCfgHostEntry 1}

ospfv3CurCfgHostIp6Addr OBJECT-TYPE
    SYNTAX DisplayString (SIZE(0..40)) 
    MAX-ACCESS read-only
    STATUS current
    DESCRIPTION
    "The IP Address of the OSPFv3 host.
	Note:This mib is not supported for VX instance of virtualization." 
    ::= { ospfv3CurCfgHostEntry 2 }

ospfv3CurCfgHostAreaIndex OBJECT-TYPE
    SYNTAX Integer32
    MAX-ACCESS read-only
    STATUS current
    DESCRIPTION
    "The area index.
	Note:This mib is not supported for VX instance of virtualization."
    ::= { ospfv3CurCfgHostEntry 3 }

ospfv3CurCfgHostCost OBJECT-TYPE
    SYNTAX INTEGER (1..65535)
    MAX-ACCESS read-only
    STATUS current
    DESCRIPTION
        "Cost of the host entry.
        Note:This mib is not supported for VX instance of virtualization."
    ::= { ospfv3CurCfgHostEntry 4 }

ospfv3CurCfgHostState OBJECT-TYPE
    SYNTAX INTEGER {
        enabled(1),
        disabled(2),
        unsupported(2147483647)
        }
    MAX-ACCESS read-only
    STATUS current
    DESCRIPTION
        "Enable or disable Host Entry.
        Note:This mib is not supported for VX instance of virtualization."
    ::= { ospfv3CurCfgHostEntry 5 }

ospfv3NewCfgHostTable OBJECT-TYPE
    SYNTAX SEQUENCE OF Ospfv3NewCfgHostEntry
    MAX-ACCESS not-accessible
    STATUS current
    DESCRIPTION
      "The table of OSPFv3 Host configuration.
      Note:This mib is not supported for VX instance of virtualization."
    ::= { ospfv3Cfg 13 }

ospfv3NewCfgHostEntry OBJECT-TYPE
    SYNTAX Ospfv3NewCfgHostEntry
    MAX-ACCESS not-accessible
    STATUS current
    DESCRIPTION
      "Information about a OSPFv3 host.
      Note:This mib is not supported for VX instance of virtualization."
    INDEX { ospfv3NewCfgHostIndex }
    ::= { ospfv3NewCfgHostTable 1 }
 
Ospfv3NewCfgHostEntry ::= SEQUENCE {
    ospfv3NewCfgHostIndex         Integer32,
    ospfv3NewCfgHostIp6Addr       DisplayString, 
    ospfv3NewCfgHostAreaIndex     Integer32,
    ospfv3NewCfgHostCost          INTEGER,
    ospfv3NewCfgHostState         INTEGER,
    ospfv3NewCfgHostDelete        INTEGER
    }
 
ospfv3NewCfgHostIndex OBJECT-TYPE
    SYNTAX Integer32
    MAX-ACCESS read-only 
    STATUS current
    DESCRIPTION
    "The OSPFv3 host number for which the OSPFv3 host table is related.
    Note:This mib is not supported for VX instance of virtualization."
    ::= { ospfv3NewCfgHostEntry 1}

ospfv3NewCfgHostIp6Addr OBJECT-TYPE
    SYNTAX DisplayString (SIZE(0..40)) 
    MAX-ACCESS read-create
    STATUS current
    DESCRIPTION
    "The IP Address of the OSPFv3 host.
    Note:This mib is not supported for VX instance of virtualization." 
    ::= { ospfv3NewCfgHostEntry 2 }

ospfv3NewCfgHostAreaIndex OBJECT-TYPE
    SYNTAX Integer32 
    MAX-ACCESS read-create
    STATUS current
    DESCRIPTION
    "The OSPFv3 area index.
	Note:This mib is not supported for VX instance of virtualization."
    ::= { ospfv3NewCfgHostEntry 3 }

ospfv3NewCfgHostCost OBJECT-TYPE
    SYNTAX INTEGER (1..65535)
    MAX-ACCESS read-create
    STATUS current
    DESCRIPTION
        "Cost of the host entry.
        Note:This mib is not supported for VX instance of virtualization."
    ::= { ospfv3NewCfgHostEntry 4 }

ospfv3NewCfgHostState OBJECT-TYPE
    SYNTAX INTEGER {
        enabled(1),
        disabled(2),
        unsupported(2147483647)
        }
    MAX-ACCESS read-create
    STATUS current
    DESCRIPTION
        "Enable or disable Host Entry.
        Note:This mib is not supported for VX instance of virtualization."
    ::= { ospfv3NewCfgHostEntry 5 }

ospfv3NewCfgHostDelete OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row.
         Note:This mib is not supported for VX instance of virtualization."
    ::= { ospfv3NewCfgHostEntry 6 }

ospfv3CurCfgIntfTable OBJECT-TYPE
    SYNTAX SEQUENCE OF Ospfv3CurCfgIntfEntry
    MAX-ACCESS not-accessible
    STATUS current
    DESCRIPTION
      "The table of OSPFv3 Interface configuration in the current_config.
      Note:This mib is not supported for VX instance of virtualization."
    ::= { ospfv3Cfg 7 }

ospfv3CurCfgIntfEntry OBJECT-TYPE
    SYNTAX Ospfv3CurCfgIntfEntry
    MAX-ACCESS not-accessible
    STATUS current
    DESCRIPTION
      "Information about an OSPFv3 Interface.
      Note:This mib is not supported for VX instance of virtualization."
    INDEX { ospfv3CurCfgIntfIndex }
    ::= { ospfv3CurCfgIntfTable 1 }
 
Ospfv3CurCfgIntfEntry ::= SEQUENCE {
    ospfv3CurCfgIntfIndex         Integer32,
    ospfv3CurCfgIntfId            IpAddress,    
    ospfv3CurCfgIntfAreaId        INTEGER,
    ospfv3CurCfgIntfPriority      INTEGER,
    ospfv3CurCfgIntfCost          INTEGER,
    ospfv3CurCfgIntfHello         INTEGER,
    ospfv3CurCfgIntfDead          INTEGER,
    ospfv3CurCfgIntfTransit       INTEGER,
    ospfv3CurCfgIntfRetrans       INTEGER,    
    ospfv3CurCfgIntfState         INTEGER
    }
 
ospfv3CurCfgIntfIndex OBJECT-TYPE
    SYNTAX Integer32
    MAX-ACCESS read-only
    STATUS current
    DESCRIPTION
    "The OSPFv3 Interface number for which the OSPFv3 Interface table is 
         related.
	Note:This mib is not supported for VX instance of virtualization."
    ::= { ospfv3CurCfgIntfEntry 1}

ospfv3CurCfgIntfId OBJECT-TYPE
    SYNTAX IpAddress 
    MAX-ACCESS read-only
    STATUS current
    DESCRIPTION
    "The IP Address of the OSPFv3 interface.
	Note:This mib is not supported for VX instance of virtualization." 
    ::= { ospfv3CurCfgIntfEntry 2 }

ospfv3CurCfgIntfAreaId OBJECT-TYPE
    SYNTAX INTEGER (0..2)
    MAX-ACCESS read-only
    STATUS current
    DESCRIPTION
        "Specify Area Index.
        Note:This mib is not supported for VX instance of virtualization."
    ::= { ospfv3CurCfgIntfEntry 3 }

ospfv3CurCfgIntfPriority OBJECT-TYPE
    SYNTAX INTEGER (1..65535)
    MAX-ACCESS read-only
    STATUS current
    DESCRIPTION
        "Specify interface router priority.
        Note:This mib is not supported for VX instance of virtualization."
    ::= { ospfv3CurCfgIntfEntry 4 }

ospfv3CurCfgIntfCost OBJECT-TYPE
    SYNTAX INTEGER (1..65535)
    MAX-ACCESS read-only
    STATUS current
    DESCRIPTION
        "Interface Cost.
        Note:This mib is not supported for VX instance of virtualization."
    ::= { ospfv3CurCfgIntfEntry 5 }

ospfv3CurCfgIntfHello OBJECT-TYPE
    SYNTAX INTEGER (1..65535)
    MAX-ACCESS read-only
    STATUS current
    DESCRIPTION
        "Hello interval in seconds.
        Note:This mib is not supported for VX instance of virtualization."
    ::= { ospfv3CurCfgIntfEntry 6 }

ospfv3CurCfgIntfDead OBJECT-TYPE
    SYNTAX INTEGER (1..65535)
    MAX-ACCESS read-only
    STATUS current
    DESCRIPTION
        "Dead interval in seconds.
        Note:This mib is not supported for VX instance of virtualization."
    ::= { ospfv3CurCfgIntfEntry 7 }

ospfv3CurCfgIntfTransit OBJECT-TYPE
    SYNTAX INTEGER (0..3600)
    MAX-ACCESS read-only
    STATUS current
    DESCRIPTION
        "Transit delay in seconds.
        Note:This mib is not supported for VX instance of virtualization."
    ::= { ospfv3CurCfgIntfEntry 8 }

ospfv3CurCfgIntfRetrans OBJECT-TYPE
    SYNTAX INTEGER (0..3600)
    MAX-ACCESS read-only
    STATUS current
    DESCRIPTION
        "Retransmit interval in seconds.
        Note:This mib is not supported for VX instance of virtualization."
    ::= { ospfv3CurCfgIntfEntry 9 }

ospfv3CurCfgIntfState OBJECT-TYPE
    SYNTAX INTEGER {
        enabled(1),
        disabled(2),
        unsupported(2147483647)
        }
    MAX-ACCESS read-only
    STATUS current
    DESCRIPTION
        "OSPFv3 Interface Enabled/disabled.
        Note:This mib is not supported for VX instance of virtualization."
    ::= { ospfv3CurCfgIntfEntry 12 }

ospfv3NewCfgIntfTable OBJECT-TYPE
    SYNTAX SEQUENCE OF Ospfv3NewCfgIntfEntry
    MAX-ACCESS not-accessible
    STATUS current
    DESCRIPTION
      "The table of OSPFv3 Interface configuration in the new_config.
      Note:This mib is not supported for VX instance of virtualization."
    ::= { ospfv3Cfg 8 }

ospfv3NewCfgIntfEntry OBJECT-TYPE
    SYNTAX Ospfv3NewCfgIntfEntry
    MAX-ACCESS not-accessible
    STATUS current
    DESCRIPTION
      "Information about an OSPFv3 Interface.
      Note:This mib is not supported for VX instance of virtualization."
    INDEX { ospfv3NewCfgIntfIndex }
    ::= { ospfv3NewCfgIntfTable 1 }
 
Ospfv3NewCfgIntfEntry ::= SEQUENCE {
    ospfv3NewCfgIntfIndex           Integer32,
    ospfv3NewCfgIntfId              IpAddress,
    ospfv3NewCfgIntfAreaId          INTEGER,
    ospfv3NewCfgIntfPriority        INTEGER,
    ospfv3NewCfgIntfCost            INTEGER,
    ospfv3NewCfgIntfHello           INTEGER,
    ospfv3NewCfgIntfDead            INTEGER,
    ospfv3NewCfgIntfTransit         INTEGER,
    ospfv3NewCfgIntfRetrans         INTEGER,    
    ospfv3NewCfgIntfState           INTEGER,
    ospfv3NewCfgIntfDelete          INTEGER
    }
 
ospfv3NewCfgIntfIndex OBJECT-TYPE
    SYNTAX Integer32
    MAX-ACCESS read-only
    STATUS current
    DESCRIPTION
    "The OSPFv3 Interface number for which the OSPFv3 Interface table is 
         related.
	Note:This mib is not supported for VX instance of virtualization."
    ::= { ospfv3NewCfgIntfEntry 1}

ospfv3NewCfgIntfId OBJECT-TYPE
    SYNTAX IpAddress 
    MAX-ACCESS read-only
    STATUS current
    DESCRIPTION
    "The IP Address of the OSPF interface.
	Note:This mib is not supported for VX instance of virtualization." 
    ::= { ospfv3NewCfgIntfEntry 2 }

ospfv3NewCfgIntfAreaId OBJECT-TYPE
    SYNTAX INTEGER (0..2)
    MAX-ACCESS read-create
    STATUS current
    DESCRIPTION
        "Specify Area Index.
        Note:This mib is not supported for VX instance of virtualization."
    ::= { ospfv3NewCfgIntfEntry 3 }

ospfv3NewCfgIntfPriority OBJECT-TYPE
    SYNTAX INTEGER (1..65535)
    MAX-ACCESS read-create
    STATUS current
    DESCRIPTION
        "Specify interface router priority.
        Note:This mib is not supported for VX instance of virtualization."
    ::= { ospfv3NewCfgIntfEntry 4 }

ospfv3NewCfgIntfCost OBJECT-TYPE
    SYNTAX INTEGER (1..65535)
    MAX-ACCESS read-create
    STATUS current
    DESCRIPTION
        "Specify interface cost.
        Note:This mib is not supported for VX instance of virtualization."
    ::= { ospfv3NewCfgIntfEntry 5 }

ospfv3NewCfgIntfHello OBJECT-TYPE
    SYNTAX INTEGER (1..65535)
    MAX-ACCESS read-create
    STATUS current
    DESCRIPTION
        "Hello interval in seconds.
        Note:This mib is not supported for VX instance of virtualization."
    ::= { ospfv3NewCfgIntfEntry 6 }

ospfv3NewCfgIntfDead OBJECT-TYPE
    SYNTAX INTEGER (1..65535)
    MAX-ACCESS read-create
    STATUS current
    DESCRIPTION
        "Dead interval in seconds.
        Note:This mib is not supported for VX instance of virtualization."
    ::= { ospfv3NewCfgIntfEntry 7 }

ospfv3NewCfgIntfTransit OBJECT-TYPE
    SYNTAX INTEGER (0..3600)
    MAX-ACCESS read-create
    STATUS current
    DESCRIPTION
        "Transit delay in seconds.
        Note:This mib is not supported for VX instance of virtualization."
    ::= { ospfv3NewCfgIntfEntry 8 }

ospfv3NewCfgIntfRetrans OBJECT-TYPE
    SYNTAX INTEGER (0..3600)
    MAX-ACCESS read-create
    STATUS current
    DESCRIPTION
        "Retransmit interval in seconds.
        Note:This mib is not supported for VX instance of virtualization."
    ::= { ospfv3NewCfgIntfEntry 9 }

ospfv3NewCfgIntfState OBJECT-TYPE
    SYNTAX INTEGER {
        enabled(1),
        disabled(2),
        unsupported(2147483647)
        }
    MAX-ACCESS read-create
    STATUS current
    DESCRIPTION
        "Enable or disable OSPFv3 Interface.
        Note:This mib is not supported for VX instance of virtualization."
    ::= { ospfv3NewCfgIntfEntry 12 }

ospfv3NewCfgIntfDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
         Note:This mib is not supported for VX instance of virtualization."
    ::= { ospfv3NewCfgIntfEntry 13 }

ospfv3CurCfgVirtIntfTable OBJECT-TYPE
    SYNTAX SEQUENCE OF Ospfv3CurCfgVirtIntfEntry
    MAX-ACCESS not-accessible
    STATUS current
    DESCRIPTION
      "The table of OSPFv3 Virtual Interface configuration in the current 
       configuration.
       Note:This mib is not supported for VX instance of virtualization."
    ::= { ospfv3Cfg 9 }

ospfv3CurCfgVirtIntfEntry OBJECT-TYPE
    SYNTAX Ospfv3CurCfgVirtIntfEntry
    MAX-ACCESS not-accessible
    STATUS current
    DESCRIPTION
      "Information about an OSPFv3 virtual Interface.
      Note:This mib is not supported for VX instance of virtualization."
    INDEX { ospfv3CurCfgVirtIntfIndex }
    ::= { ospfv3CurCfgVirtIntfTable 1 }
 
Ospfv3CurCfgVirtIntfEntry ::= SEQUENCE {
    ospfv3CurCfgVirtIntfIndex         Integer32,
    ospfv3CurCfgVirtIntfAreaId        INTEGER,
    ospfv3CurCfgVirtIntfNbr           IpAddress,
    ospfv3CurCfgVirtIntfHello         INTEGER,
    ospfv3CurCfgVirtIntfDead          INTEGER,
    ospfv3CurCfgVirtIntfTransit       INTEGER,
    ospfv3CurCfgVirtIntfRetrans       INTEGER,
    ospfv3CurCfgVirtIntfState         INTEGER    
    }
 
ospfv3CurCfgVirtIntfIndex OBJECT-TYPE
    SYNTAX Integer32
    MAX-ACCESS read-only
    STATUS current
    DESCRIPTION
    "The OSPFv3 Virtual Interface number for which the OSPFv3 
         Virtual Interface table is related.
         Note:This mib is not supported for VX instance of virtualization."
    ::= { ospfv3CurCfgVirtIntfEntry 1}

ospfv3CurCfgVirtIntfAreaId OBJECT-TYPE
    SYNTAX INTEGER (0..2)
    MAX-ACCESS read-only
    STATUS current
    DESCRIPTION
         "The OSPFv3 Area Id.
         Note:This mib is not supported for VX instance of virtualization." 
    ::= { ospfv3CurCfgVirtIntfEntry 2 }

ospfv3CurCfgVirtIntfNbr OBJECT-TYPE
    SYNTAX IpAddress 
    MAX-ACCESS read-only
    STATUS current
    DESCRIPTION
    "The IP Address of the OSPFv3 neighbour for this virtual interface.
	Note:This mib is not supported for VX instance of virtualization."
    ::= { ospfv3CurCfgVirtIntfEntry 3 }

ospfv3CurCfgVirtIntfHello OBJECT-TYPE
    SYNTAX INTEGER (1..65535)
    MAX-ACCESS read-only
    STATUS current
    DESCRIPTION
        "Hello interval in seconds.
        Note:This mib is not supported for VX instance of virtualization."
    ::= { ospfv3CurCfgVirtIntfEntry 4 }

ospfv3CurCfgVirtIntfDead OBJECT-TYPE
    SYNTAX INTEGER (1..65535)
    MAX-ACCESS read-only
    STATUS current
    DESCRIPTION
        "Dead interval in seconds.
        Note:This mib is not supported for VX instance of virtualization."
    ::= { ospfv3CurCfgVirtIntfEntry 5 }

ospfv3CurCfgVirtIntfTransit OBJECT-TYPE
    SYNTAX INTEGER (0..3600)
    MAX-ACCESS read-only
    STATUS current
    DESCRIPTION
        "Transit delay in seconds.
        Note:This mib is not supported for VX instance of virtualization."
    ::= { ospfv3CurCfgVirtIntfEntry 6 }

ospfv3CurCfgVirtIntfRetrans OBJECT-TYPE
    SYNTAX INTEGER (0..3600)
    MAX-ACCESS read-only
    STATUS current
    DESCRIPTION
        "Retransmit interval in seconds.
        Note:This mib is not supported for VX instance of virtualization."
    ::= { ospfv3CurCfgVirtIntfEntry 7 }

ospfv3CurCfgVirtIntfState OBJECT-TYPE
    SYNTAX INTEGER {
        enabled(1),
        disabled(2),
        unsupported(2147483647)
        }
    MAX-ACCESS read-only
    STATUS current
    DESCRIPTION
        "OSPFv3 Interface Enabled/disabled .
        Note:This mib is not supported for VX instance of virtualization."
    ::= { ospfv3CurCfgVirtIntfEntry 8 }

ospfv3NewCfgVirtIntfTable OBJECT-TYPE
    SYNTAX SEQUENCE OF Ospfv3NewCfgVirtIntfEntry
    MAX-ACCESS not-accessible
    STATUS current
    DESCRIPTION
      "The table of OSPFv3 Virtual Interface configuration in the new_config.
      Note:This mib is not supported for VX instance of virtualization."
    ::= { ospfv3Cfg 10 }

ospfv3NewCfgVirtIntfEntry OBJECT-TYPE
    SYNTAX Ospfv3NewCfgVirtIntfEntry
    MAX-ACCESS not-accessible
    STATUS current
    DESCRIPTION
      "Information about an OSPFv3 virtual Interface.
      Note:This mib is not supported for VX instance of virtualization."
    INDEX { ospfv3NewCfgVirtIntfIndex }
    ::= { ospfv3NewCfgVirtIntfTable 1 }
 
Ospfv3NewCfgVirtIntfEntry ::= SEQUENCE {
    ospfv3NewCfgVirtIntfIndex         Integer32,
    ospfv3NewCfgVirtIntfAreaId        INTEGER,
    ospfv3NewCfgVirtIntfNbr           IpAddress,
    ospfv3NewCfgVirtIntfHello         INTEGER,
    ospfv3NewCfgVirtIntfDead          INTEGER,
    ospfv3NewCfgVirtIntfTransit       INTEGER,
    ospfv3NewCfgVirtIntfRetrans       INTEGER,
    ospfv3NewCfgVirtIntfState         INTEGER,
    ospfv3NewCfgVirtIntfDelete        INTEGER
    }
 
ospfv3NewCfgVirtIntfIndex OBJECT-TYPE
    SYNTAX Integer32
    MAX-ACCESS read-only
    STATUS current
    DESCRIPTION
    "The OSPFv3 Virtual Interface number for which the OSPF v3
         Virtual Interface table is related.
	Note:This mib is not supported for VX instance of virtualization."
    ::= { ospfv3NewCfgVirtIntfEntry 1}

ospfv3NewCfgVirtIntfAreaId OBJECT-TYPE
    SYNTAX INTEGER (0..2)
    MAX-ACCESS read-create
    STATUS current
    DESCRIPTION
        "The OSPFv3 Area Id.
	Note:This mib is not supported for VX instance of virtualization." 
    ::= { ospfv3NewCfgVirtIntfEntry 2 }

ospfv3NewCfgVirtIntfNbr OBJECT-TYPE
    SYNTAX IpAddress 
    MAX-ACCESS read-create
    STATUS current
    DESCRIPTION
    "The IP Address of the OSPFv3 neighbour for this virtual interface.
	Note:This mib is not supported for VX instance of virtualization."
    ::= { ospfv3NewCfgVirtIntfEntry 3 }

ospfv3NewCfgVirtIntfHello OBJECT-TYPE
    SYNTAX INTEGER (1..65535)
    MAX-ACCESS read-create
    STATUS current
    DESCRIPTION
        "Hello interval in seconds.
	Note:This mib is not supported for VX instance of virtualization."
    ::= { ospfv3NewCfgVirtIntfEntry 4 }

ospfv3NewCfgVirtIntfDead OBJECT-TYPE
    SYNTAX INTEGER (1..65535)
    MAX-ACCESS read-create
    STATUS current
    DESCRIPTION
        "Dead interval in seconds.
	Note:This mib is not supported for VX instance of virtualization."
    ::= { ospfv3NewCfgVirtIntfEntry 5 }

ospfv3NewCfgVirtIntfTransit OBJECT-TYPE
    SYNTAX INTEGER (0..3600)
    MAX-ACCESS read-create
    STATUS current
    DESCRIPTION
        "Transit delay in seconds.
	Note:This mib is not supported for VX instance of virtualization."
    ::= { ospfv3NewCfgVirtIntfEntry 6 }

ospfv3NewCfgVirtIntfRetrans OBJECT-TYPE
    SYNTAX INTEGER (0..3600)
    MAX-ACCESS read-create
    STATUS current
    DESCRIPTION
        "Retransmit interval in seconds.
	Note:This mib is not supported for VX instance of virtualization."
    ::= { ospfv3NewCfgVirtIntfEntry 7 }
    
ospfv3NewCfgVirtIntfState OBJECT-TYPE
    SYNTAX INTEGER {
        enabled(1),
        disabled(2),
        unsupported(2147483647)
        }
    MAX-ACCESS read-create
    STATUS current
    DESCRIPTION
        "Enable or disable OSPFv3 Interface.
	Note:This mib is not supported for VX instance of virtualization."
    ::= { ospfv3NewCfgVirtIntfEntry 8 }

ospfv3NewCfgVirtIntfDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
	Note:This mib is not supported for VX instance of virtualization."
    ::= { ospfv3NewCfgVirtIntfEntry 9 }

-- ospfv3 range

ospfv3CurCfgRangeTable OBJECT-TYPE
    SYNTAX SEQUENCE OF Ospfv3CurCfgRangeEntry
    MAX-ACCESS not-accessible
    STATUS current
    DESCRIPTION
      "The table of OSPFv3 summary range in the current configuration.
	Note:This mib is not supported for VX instance of virtualization." 
    ::= { ospfv3Cfg 14 }

ospfv3CurCfgRangeEntry OBJECT-TYPE
    SYNTAX Ospfv3CurCfgRangeEntry 
    MAX-ACCESS not-accessible
    STATUS current
    DESCRIPTION
      "Information about an OSPFv3 summary range.
	Note:This mib is not supported for VX instance of virtualization."
    INDEX { ospfv3CurCfgRangeIndex }
    ::= { ospfv3CurCfgRangeTable 1 }
 
Ospfv3CurCfgRangeEntry ::= SEQUENCE {
    ospfv3CurCfgRangeIndex            Integer32,
    ospfv3CurCfgRangeAddr             DisplayString,
    ospfv3CurCfgRangePrefix           INTEGER,
    ospfv3CurCfgRangeAreaIndex        Integer32,
    ospfv3CurCfgRangeHideState        INTEGER,
    ospfv3CurCfgRangeState            INTEGER
    }
 
ospfv3CurCfgRangeIndex OBJECT-TYPE
    SYNTAX Integer32
    MAX-ACCESS read-only
    STATUS current
    DESCRIPTION
    "The range number for which the OSPFv3 summary range table is related.
	Note:This mib is not supported for VX instance of virtualization." 
    ::= { ospfv3CurCfgRangeEntry 1}

ospfv3CurCfgRangeAddr OBJECT-TYPE
    SYNTAX DisplayString (SIZE(0..40)) 
    MAX-ACCESS read-only
    STATUS current
    DESCRIPTION
    "The IP Address of the range.
	Note:This mib is not supported for VX instance of virtualization." 
    ::= { ospfv3CurCfgRangeEntry 2 }

ospfv3CurCfgRangePrefix OBJECT-TYPE
    SYNTAX INTEGER (1..128) 
    MAX-ACCESS read-only
    STATUS current
    DESCRIPTION
    "The mask of the range.
	Note:This mib is not supported for VX instance of virtualization."
    ::= { ospfv3CurCfgRangeEntry 3 }

ospfv3CurCfgRangeAreaIndex OBJECT-TYPE
    SYNTAX Integer32
    MAX-ACCESS read-only
    STATUS current
    DESCRIPTION
        "The area index.
	Note:This mib is not supported for VX instance of virtualization."
    ::= { ospfv3CurCfgRangeEntry 4 }

ospfv3CurCfgRangeHideState OBJECT-TYPE
    SYNTAX  INTEGER {
        enabled(1),
        disabled(2),
        unsupported(2147483647)
        }
    MAX-ACCESS  read-only
    STATUS  current
    DESCRIPTION
        "The state of the hide range.
	Note:This mib is not supported for VX instance of virtualization."
    ::= { ospfv3CurCfgRangeEntry 5 }

ospfv3CurCfgRangeState OBJECT-TYPE
    SYNTAX  INTEGER {
        enabled(1),
        disabled(2),
        unsupported(2147483647)
        }
    MAX-ACCESS  read-only
    STATUS  current
    DESCRIPTION
        "The state of the range.
	Note:This mib is not supported for VX instance of virtualization."
    ::= { ospfv3CurCfgRangeEntry 6 }

ospfv3NewCfgRangeTable OBJECT-TYPE
    SYNTAX SEQUENCE OF Ospfv3NewCfgRangeEntry
    MAX-ACCESS not-accessible
    STATUS current
    DESCRIPTION
      "The table of OSPFv3 summary range in the new configuration.
	Note:This mib is not supported for VX instance of virtualization." 
    ::= { ospfv3Cfg 15 }

ospfv3NewCfgRangeEntry OBJECT-TYPE
    SYNTAX Ospfv3NewCfgRangeEntry 
    MAX-ACCESS not-accessible
    STATUS current
    DESCRIPTION
      "Information about an OSPFv3 summary range.
	Note:This mib is not supported for VX instance of virtualization."
    INDEX { ospfv3NewCfgRangeIndex }
    ::= { ospfv3NewCfgRangeTable 1 }
 
Ospfv3NewCfgRangeEntry ::= SEQUENCE {
    ospfv3NewCfgRangeIndex            Integer32,
    ospfv3NewCfgRangeAddr             DisplayString,
    ospfv3NewCfgRangePrefix           INTEGER,
    ospfv3NewCfgRangeAreaIndex        Integer32,
    ospfv3NewCfgRangeHideState        INTEGER,
    ospfv3NewCfgRangeState            INTEGER,
    ospfv3NewCfgRangeDelete           INTEGER
    }
 
ospfv3NewCfgRangeIndex OBJECT-TYPE
    SYNTAX Integer32
    MAX-ACCESS read-only
    STATUS current
    DESCRIPTION
    "The range number for which the OSPFv3 summary range table is related.
	Note:This mib is not supported for VX instance of virtualization." 
    ::= { ospfv3NewCfgRangeEntry 1}

ospfv3NewCfgRangeAddr OBJECT-TYPE
    SYNTAX DisplayString (SIZE(0..40)) 
    MAX-ACCESS read-create
    STATUS current
    DESCRIPTION
    "The IP Address of the range.
	Note:This mib is not supported for VX instance of virtualization." 
    ::= { ospfv3NewCfgRangeEntry 2 }

ospfv3NewCfgRangePrefix OBJECT-TYPE
    SYNTAX INTEGER (1..128)
    MAX-ACCESS read-create 
    STATUS current
    DESCRIPTION
    "The prefix length of the range.
	Note:This mib is not supported for VX instance of virtualization."
    ::= { ospfv3NewCfgRangeEntry 3 }

ospfv3NewCfgRangeAreaIndex OBJECT-TYPE
    SYNTAX Integer32
    MAX-ACCESS read-create 
    STATUS current
    DESCRIPTION
        "The area index.
	Note:This mib is not supported for VX instance of virtualization."
    ::= { ospfv3NewCfgRangeEntry 4 }

ospfv3NewCfgRangeHideState OBJECT-TYPE
    SYNTAX  INTEGER {
        enabled(1),
        disabled(2),
        unsupported(2147483647)
        }
    MAX-ACCESS read-create 
    STATUS  current
    DESCRIPTION
        "The state of the hide range.
	Note:This mib is not supported for VX instance of virtualization."
    ::= { ospfv3NewCfgRangeEntry 5 }

ospfv3NewCfgRangeState OBJECT-TYPE
    SYNTAX  INTEGER {
        enabled(1),
        disabled(2),
        unsupported(2147483647)
        }
    MAX-ACCESS read-create 
    STATUS  current
    DESCRIPTION
        "The state of the range.
	Note:This mib is not supported for VX instance of virtualization."
    ::= { ospfv3NewCfgRangeEntry 6 }

ospfv3NewCfgRangeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row.
	Note:This mib is not supported for VX instance of virtualization."
    ::= { ospfv3NewCfgRangeEntry 7 }

ospfv3RouteRedistribution   OBJECT IDENTIFIER ::= { ospfv3Cfg 4 }

ospfv3RedistributeStatic    OBJECT IDENTIFIER ::= { ospfv3RouteRedistribution 1 }

ospfv3CurCfgStaticMetric OBJECT-TYPE
    SYNTAX INTEGER (0..16777215)
    MAX-ACCESS read-only
    STATUS current
    DESCRIPTION
    "The metric to be assigned to static routes. 
         A value of 0 indicates none.
	Note:This mib is not supported for VX instance of virtualization."
    ::= { ospfv3RedistributeStatic 1 }

ospfv3NewCfgStaticMetric OBJECT-TYPE
    SYNTAX INTEGER (0..16777215)
    MAX-ACCESS read-write
    STATUS current
    DESCRIPTION
    "The metric to be assigned to static routes. 
         A value of 0 indicates none.
	Note:This mib is not supported for VX instance of virtualization."
    ::= { ospfv3RedistributeStatic 2 }

ospfv3CurCfgStaticMetricType OBJECT-TYPE
    SYNTAX INTEGER {
        none(1),
        type1(2),
        type2(3),
        unsupported(2147483647)
        }
    MAX-ACCESS read-only
    STATUS current
    DESCRIPTION
    "The AS External metric type for static routes.
	Note:This mib is not supported for VX instance of virtualization."
    ::= { ospfv3RedistributeStatic 3 }

ospfv3NewCfgStaticMetricType OBJECT-TYPE
    SYNTAX INTEGER {
        none(1),
        type1(2),
        type2(3),
        unsupported(2147483647)
        }
    MAX-ACCESS read-write
    STATUS current
    DESCRIPTION
    "The AS External metric type for static routes.
	Note:This mib is not supported for VX instance of virtualization."
    ::= { ospfv3RedistributeStatic 4 }

ospfv3CurCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeStatic 5 }

ospfv3NewCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeStatic 6 }

ospfv3NewCfgStaticAddOutRmap OBJECT-TYPE
    SYNTAX Integer32 
    MAX-ACCESS read-write
    STATUS current  
    DESCRIPTION
    "The route map to be add into out-rmap list. When read, 0 is returned.
	Note:This mib is not supported for VX instance of virtualization."
    ::= { ospfv3RedistributeStatic 7 }

ospfv3NewCfgStaticRemoveOutRmap OBJECT-TYPE
    SYNTAX Integer32 
    MAX-ACCESS read-write
    STATUS current  
    DESCRIPTION
    "The route map to be removed from out-rmap list. When read, 
         0 is returned.
	Note:This mib is not supported for VX instance of virtualization."
    ::= { ospfv3RedistributeStatic 8 }

ospfv3RedistributeEbgp    OBJECT IDENTIFIER ::= { ospfv3RouteRedistribution 2 }

ospfv3CurCfgEbgpMetric OBJECT-TYPE
    SYNTAX INTEGER (0..16777215)
    MAX-ACCESS read-only
    STATUS current
    DESCRIPTION
    "The export metric to be assigned to External BGP routes.
         A value of 0 indicates none.
	Note:This mib is not supported for VX instance of virtualization."
    ::= { ospfv3RedistributeEbgp 1 }

ospfv3NewCfgEbgpMetric OBJECT-TYPE
    SYNTAX INTEGER (0..16777215)
    MAX-ACCESS read-write
    STATUS current
    DESCRIPTION
    "The export metric to be assigned to External BGP routes.
         A value of 0 indicates none.
	Note:This mib is not supported for VX instance of virtualization."
    ::= { ospfv3RedistributeEbgp 2 }

ospfv3CurCfgEbgpMetricType OBJECT-TYPE
    SYNTAX INTEGER {
        none(1),
        type1(2),
        type2(3),
        unsupported(2147483647)
        }
    MAX-ACCESS read-only
    STATUS current
    DESCRIPTION
    "The AS External metric type for External BGP routes.
	Note:This mib is not supported for VX instance of virtualization."
    ::= { ospfv3RedistributeEbgp 3 }

ospfv3NewCfgEbgpMetricType OBJECT-TYPE
    SYNTAX INTEGER {
        none(1),
        type1(2),
        type2(3),
        unsupported(2147483647)
        }
    MAX-ACCESS read-write
    STATUS current
    DESCRIPTION
    "The AS External metric type for External BGP routes.
	Note:This mib is not supported for VX instance of virtualization."
    ::= { ospfv3RedistributeEbgp 4 }

ospfv3CurCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeEbgp 5 }

ospfv3NewCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeEbgp 6 }

ospfv3NewCfgEbgpAddOutRmap OBJECT-TYPE
    SYNTAX Integer32 
    MAX-ACCESS read-write
    STATUS current  
    DESCRIPTION
    "The route map to be added into out-rmap list. When read, 0 is returned.
	Note:This mib is not supported for VX instance of virtualization."
    ::= { ospfv3RedistributeEbgp 7 }

ospfv3NewCfgEbgpRemoveOutRmap OBJECT-TYPE
    SYNTAX Integer32 
    MAX-ACCESS read-write
    STATUS current  
    DESCRIPTION
    "The route map to be removed from out-rmap list. When read, 
         0 is returned.
	Note:This mib is not supported for VX instance of virtualization."
    ::= { ospfv3RedistributeEbgp 8 }

ospfv3RedistributeIbgp    OBJECT IDENTIFIER ::= { ospfv3RouteRedistribution 3 }

ospfv3CurCfgIbgpMetric OBJECT-TYPE
    SYNTAX INTEGER (0..16777215)
    MAX-ACCESS read-only
    STATUS current
    DESCRIPTION
    "The export metric for Internal BGP routes.
         A value of 0 indicates none.
	Note:This mib is not supported for VX instance of virtualization."
    ::= { ospfv3RedistributeIbgp 1 }

ospfv3NewCfgIbgpMetric OBJECT-TYPE
    SYNTAX INTEGER (0..16777215)
    MAX-ACCESS read-write
    STATUS current
    DESCRIPTION
    "The export metric for Internal BGP routes.
         A value of 0 indicates none.
	Note:This mib is not supported for VX instance of virtualization."
    ::= { ospfv3RedistributeIbgp 2 }

ospfv3CurCfgIbgpMetricType OBJECT-TYPE
    SYNTAX INTEGER {
        none(1),
        type1(2),
        type2(3),
        unsupported(2147483647)
        }
    MAX-ACCESS read-only
    STATUS current
    DESCRIPTION
    "The AS External metric type for Internal BGP routes.
	Note:This mib is not supported for VX instance of virtualization."
    ::= { ospfv3RedistributeIbgp 3 }

ospfv3NewCfgIbgpMetricType OBJECT-TYPE
    SYNTAX INTEGER {
        none(1),
        type1(2),
        type2(3),
        unsupported(2147483647)
        }
    MAX-ACCESS read-write
    STATUS current
    DESCRIPTION
    "The AS External metric type for Internal BGP routes.
	Note:This mib is not supported for VX instance of virtualization."
    ::= { ospfv3RedistributeIbgp 4 }

ospfv3CurCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeIbgp 5 }

ospfv3NewCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeIbgp 6 }

ospfv3NewCfgIbgpAddOutRmap OBJECT-TYPE
    SYNTAX Integer32 
    MAX-ACCESS read-write
    STATUS current  
    DESCRIPTION
    "The route map to be add into out-rmap list. When read, 0 is returned.
	Note:This mib is not supported for VX instance of virtualization."
    ::= { ospfv3RedistributeIbgp 7 }

ospfv3NewCfgIbgpRemoveOutRmap OBJECT-TYPE
    SYNTAX Integer32 
    MAX-ACCESS read-write
    STATUS current  
    DESCRIPTION
    "The route map to be removed from out-rmap list. When read, 
         0 is returned.
	Note:This mib is not supported for VX instance of virtualization."
    ::= { ospfv3RedistributeIbgp 8 }

ospfv3RedistributeFixed    OBJECT IDENTIFIER ::= { ospfv3RouteRedistribution 4 }

ospfv3CurCfgFixedMetric OBJECT-TYPE
    SYNTAX INTEGER (0..16777215)
    MAX-ACCESS read-only
    STATUS current
    DESCRIPTION
    "The export metric for fixed routes. A value of 0 indicates none.
    Note:This mib is not supported for VX instance of virtualization."
    ::= { ospfv3RedistributeFixed 1 }

ospfv3NewCfgFixedMetric OBJECT-TYPE
    SYNTAX INTEGER (0..16777215)
    MAX-ACCESS read-write
    STATUS current
    DESCRIPTION
    "The export metric for fixed routes. A value of 0 indicates none.
    Note:This mib is not supported for VX instance of virtualization."
    ::= { ospfv3RedistributeFixed 2 }

ospfv3CurCfgFixedMetricType OBJECT-TYPE
    SYNTAX INTEGER {
        none(1),
        type1(2),
        type2(3),
        unsupported(2147483647)
        }
    MAX-ACCESS read-only
    STATUS current
    DESCRIPTION
    "The AS External metric type for fixed routes.
	Note:This mib is not supported for VX instance of virtualization."
    ::= { ospfv3RedistributeFixed 3 }

ospfv3NewCfgFixedMetricType OBJECT-TYPE
    SYNTAX INTEGER {
        none(1),
        type1(2),
        type2(3),
        unsupported(2147483647)
        }
    MAX-ACCESS read-write
    STATUS current
    DESCRIPTION
    "The AS External metric type for fixed routes.
	Note:This mib is not supported for VX instance of virtualization."
    ::= { ospfv3RedistributeFixed 4 }

ospfv3CurCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeFixed 5 }

ospfv3NewCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeFixed 6 }

ospfv3NewCfgFixedAddOutRmap OBJECT-TYPE
    SYNTAX Integer32 
    MAX-ACCESS read-write
    STATUS current  
    DESCRIPTION
    "The route map to be add into out-rmap list. When read, 0 is returned.
	Note:This mib is not supported for VX instance of virtualization."
    ::= { ospfv3RedistributeFixed 7 }

ospfv3NewCfgFixedRemoveOutRmap OBJECT-TYPE
    SYNTAX Integer32 
    MAX-ACCESS read-write
    STATUS current  
    DESCRIPTION
    "The route map to be removed from out-rmap list. When read, 
         0 is returned.
	Note:This mib is not supported for VX instance of virtualization."
    ::= { ospfv3RedistributeFixed 8 }

ospfv3RedistributeRip    OBJECT IDENTIFIER ::= { ospfv3RouteRedistribution 5 }

ospfv3CurCfgRipMetric OBJECT-TYPE
    SYNTAX INTEGER (0..16777215)
    MAX-ACCESS read-only
    STATUS current
    DESCRIPTION
    "The export metric for RIP routes. A value of 0 indicates none.
    Note:This mib is not supported for VX instance of virtualization."
    ::= { ospfv3RedistributeRip 1 }

ospfv3NewCfgRipMetric OBJECT-TYPE
    SYNTAX INTEGER (0..16777215)
    MAX-ACCESS read-write
    STATUS current
    DESCRIPTION
    "The export metric for RIP routes. A value of 0 indicates none.
    Note:This mib is not supported for VX instance of virtualization."
    ::= { ospfv3RedistributeRip 2 }

ospfv3CurCfgRipMetricType OBJECT-TYPE
    SYNTAX INTEGER {
        none(1),
        type1(2),
        type2(3),
        unsupported(2147483647)
        }
    MAX-ACCESS read-only
    STATUS current
    DESCRIPTION
    "The AS External metric type for RIP routes.
	Note:This mib is not supported for VX instance of virtualization."
    ::= { ospfv3RedistributeRip 3 }

ospfv3NewCfgRipMetricType OBJECT-TYPE
    SYNTAX INTEGER {
        none(1),
        type1(2),
        type2(3),
        unsupported(2147483647)
        }
    MAX-ACCESS read-write
    STATUS current
    DESCRIPTION
    "The AS External metric type for RIP routes.
	Note:This mib is not supported for VX instance of virtualization."
    ::= { ospfv3RedistributeRip 4 }

ospfv3CurCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeRip 5 }

ospfv3NewCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected.
         Note:This mib is not supported for VX instance of virtualization."
    ::= { ospfv3RedistributeRip 6 }

ospfv3NewCfgRipAddOutRmap OBJECT-TYPE
    SYNTAX Integer32 
    MAX-ACCESS read-write
    STATUS current  
    DESCRIPTION
    "The route map to be add into out-rmap list. When read, 0 is returned.
	Note:This mib is not supported for VX instance of virtualization."
    ::= { ospfv3RedistributeRip 7 }

ospfv3NewCfgRipRemoveOutRmap OBJECT-TYPE
    SYNTAX Integer32 
    MAX-ACCESS read-write
    STATUS current  
    DESCRIPTION
    "The route map to be removed from out-rmap list. When read, 
         0 is returned.
	Note:This mib is not supported for VX instance of virtualization."
    ::= { ospfv3RedistributeRip 8 }

ipCurCfgRouterID OBJECT-TYPE
    SYNTAX IpAddress 
    MAX-ACCESS read-only
    STATUS current
    DESCRIPTION
	"The router ID of the switch.
	Note:This mib is not supported for VX instance of virtualization." 
    ::= { ipGeneralCfg 1 }

ipNewCfgRouterID OBJECT-TYPE
    SYNTAX IpAddress 
    MAX-ACCESS read-write
    STATUS current
    DESCRIPTION
	"The router ID of the switch.
	Note:This mib is not supported for VX instance of virtualization." 
    ::= { ipGeneralCfg 2 }

ipCurCfgASNumber OBJECT-TYPE
    SYNTAX INTEGER (1..65535)
    MAX-ACCESS read-only
    STATUS current
    DESCRIPTION
	"The autonomous system (AS) number.
	Note:This mib is not supported for VX instance of virtualization." 
    ::= { ipGeneralCfg 3 }

ipNewCfgASNumber OBJECT-TYPE
    SYNTAX INTEGER (1..65535)
    MAX-ACCESS read-write
    STATUS current
    DESCRIPTION
	"The autonomous system (AS) number.
	Note:This mib is not supported for VX instance of virtualization." 
    ::= { ipGeneralCfg 4 }


ipCurCfgFragTblSize OBJECT-TYPE
    SYNTAX DisplayString (SIZE(0..4))
    MAX-ACCESS read-only
    STATUS current
    DESCRIPTION
        "The IP Fragmentation table size in 20k|40k|60k format.
	Note:This mib is not supported for VX instance of virtualization."
    ::= { ipGeneralCfg 5 }

ipNewCfgFragTblSize OBJECT-TYPE
    SYNTAX DisplayString (SIZE(0..4))
    MAX-ACCESS read-write
    STATUS current
    DESCRIPTION
        "The IP Fragmentation table size in 20k|40k|60k format.
	Note:This mib is not supported for VX instance of virtualization."
    ::= { ipGeneralCfg 6 }

ipCurCfgTnlTblSize OBJECT-TYPE
    SYNTAX DisplayString (SIZE(0..4))
    MAX-ACCESS read-only
    STATUS current
    DESCRIPTION
        "The IP Tunnel table size in 1k|8k format.
        Note:This mib is not supported for VX instance of virtualization."
    ::= { ipGeneralCfg 7 }

ipNewCfgTnlTblSize OBJECT-TYPE
    SYNTAX DisplayString (SIZE(0..4))
    MAX-ACCESS read-write
    STATUS current
    DESCRIPTION
        "The IP Tunnel table size in 1k|8k format.
        Note:This mib is not supported for VX instance of virtualization."
    ::= { ipGeneralCfg 8 }
--
-- IPMC Static Route Configuration
--
-- Static ARP Configuration
--
ipStaticArpTableMaxSize OBJECT-TYPE
    SYNTAX  Integer32
    MAX-ACCESS  read-only
    STATUS  current
    DESCRIPTION
        "The maximum number of rows in the Static ARP table.
	Note:This mib is not supported for VX instance of virtualization."
    ::= { ipStaticArpCfg 1 }

ipCurCfgStaticArpTable OBJECT-TYPE
    SYNTAX  SEQUENCE OF IpCurCfgStaticArpEntry
    MAX-ACCESS  not-accessible
    STATUS  current
    DESCRIPTION
        "The table of static ARPs in the current configuration block.
	Note:This mib is not supported for VX instance of virtualization."
    ::= { ipStaticArpCfg 2 }

ipCurCfgStaticArpEntry OBJECT-TYPE
    SYNTAX  IpCurCfgStaticArpEntry
    MAX-ACCESS  not-accessible
    STATUS  current
    DESCRIPTION
        "A row in the static ARP table.
         Note:This mib is not supported for VX instance of virtualization."
    INDEX   { ipCurCfgStaticArpIndx }
    ::= { ipCurCfgStaticArpTable 1 }

IpCurCfgStaticArpEntry ::= SEQUENCE {
    ipCurCfgStaticArpIndx         Integer32,
    ipCurCfgStaticArpIp           IpAddress,
    ipCurCfgStaticArpMAC          PhysAddress,
    ipCurCfgStaticArpVlan         Integer32,
    ipCurCfgStaticArpPort         Integer32
    }

ipCurCfgStaticArpIndx OBJECT-TYPE
    SYNTAX  Integer32
    MAX-ACCESS  read-only
    STATUS  current
    DESCRIPTION
        "The index of the static ARP table.
	Note:This mib is not supported for VX instance of virtualization."
    ::= { ipCurCfgStaticArpEntry 1}

ipCurCfgStaticArpIp OBJECT-TYPE
    SYNTAX  IpAddress
    MAX-ACCESS  read-only
    STATUS  current
    DESCRIPTION
        "The IP address for the ARP entry.
	Note:This mib is not supported for VX instance of virtualization."
    ::= { ipCurCfgStaticArpEntry 2}

ipCurCfgStaticArpMAC OBJECT-TYPE
    SYNTAX  PhysAddress
    MAX-ACCESS  read-only
    STATUS  current
    DESCRIPTION
        "The MAC address for the ARP entry.
	Note:This mib is not supported for VX instance of virtualization."
    ::= { ipCurCfgStaticArpEntry 3 }

ipCurCfgStaticArpVlan OBJECT-TYPE 
    SYNTAX  Integer32
    MAX-ACCESS  read-only 
    STATUS  current 
    DESCRIPTION 
        "The VLAN for the ARP entry.
	Note:This mib is not supported for VX instance of virtualization."
    ::= { ipCurCfgStaticArpEntry 4}

ipCurCfgStaticArpPort OBJECT-TYPE 
    SYNTAX  Integer32
    MAX-ACCESS  read-only 
    STATUS  current 
    DESCRIPTION 
        "The port for the ARP entry.
	Note:This mib is not supported for VX instance of virtualization."
    ::= { ipCurCfgStaticArpEntry 5}

ipNewCfgStaticArpTable OBJECT-TYPE
    SYNTAX  SEQUENCE OF IpNewCfgStaticArpEntry
    MAX-ACCESS  not-accessible
    STATUS  current
    DESCRIPTION
        "The table of static ARPs in the new configuration block.
	Note:This mib is not supported for VX instance of virtualization."
    ::= { ipStaticArpCfg 3 }

ipNewCfgStaticArpEntry OBJECT-TYPE
    SYNTAX  IpNewCfgStaticArpEntry
    MAX-ACCESS  not-accessible
    STATUS  current
    DESCRIPTION
        "A row in the static ARP table.
         Note:This mib is not supported for VX instance of virtualization."
    INDEX   { ipNewCfgStaticArpIndx }
    ::= { ipNewCfgStaticArpTable 1 }

IpNewCfgStaticArpEntry ::= SEQUENCE {
    ipNewCfgStaticArpIndx         Integer32,
    ipNewCfgStaticArpIp           IpAddress,
    ipNewCfgStaticArpMAC          PhysAddress,
    ipNewCfgStaticArpVlan         Integer32,
    ipNewCfgStaticArpPort         Integer32,
    ipNewCfgStaticArpAction       INTEGER
    }

ipNewCfgStaticArpIndx OBJECT-TYPE
    SYNTAX  Integer32
    MAX-ACCESS  read-only
    STATUS  current
    DESCRIPTION
        "The index of the static ARP table.
	Note:This mib is not supported for VX instance of virtualization."
    ::= { ipNewCfgStaticArpEntry 1}

ipNewCfgStaticArpIp OBJECT-TYPE
    SYNTAX  IpAddress
    MAX-ACCESS  read-create
    STATUS  current
    DESCRIPTION
        "The IP address for the ARP entry.
	Note:This mib is not supported for VX instance of virtualization."
    ::= { ipNewCfgStaticArpEntry 2}

ipNewCfgStaticArpMAC OBJECT-TYPE
    SYNTAX  PhysAddress
    MAX-ACCESS  read-create
    STATUS  current
    DESCRIPTION
        "The MAC address for the ARP entry.
	Note:This mib is not supported for VX instance of virtualization."
    ::= { ipNewCfgStaticArpEntry 3 }

ipNewCfgStaticArpVlan OBJECT-TYPE 
    SYNTAX  Integer32
    MAX-ACCESS  read-create 
    STATUS  current 
    DESCRIPTION 
        "The VLAN for the ARP entry.
	Note:This mib is not supported for VX instance of virtualization."
    ::= { ipNewCfgStaticArpEntry 4}

ipNewCfgStaticArpPort OBJECT-TYPE 
    SYNTAX  Integer32
    MAX-ACCESS  read-create 
    STATUS  current 
    DESCRIPTION 
        "The port for the ARP entry.
	Note:This mib is not supported for VX instance of virtualization."
    ::= { ipNewCfgStaticArpEntry 5}

ipNewCfgStaticArpAction OBJECT-TYPE
    SYNTAX  INTEGER {
        other(1),
        delete(2),
        unsupported(2147483647)
       }  
    MAX-ACCESS  read-create
    STATUS  current
    DESCRIPTION
        "When set to the value of 2 (delete), the entire row is deleted. 
         When read, other is returned. Setting the value to anything other 
         than 2(delete) has no effect on the state of the row.
	Note:This mib is not supported for VX instance of virtualization."
    ::= { ipNewCfgStaticArpEntry 6 }

ipStaticArpTableNextAvailableIndex OBJECT-TYPE
    SYNTAX  Integer32
    MAX-ACCESS  read-only
    STATUS  current
    DESCRIPTION
        "The next available index in the Static ARP table.
	Note:This mib is not supported for VX instance of virtualization."
    ::= { ipStaticArpCfg 4 }

--
-- IPv6 Static Neighbor Configuration
--
-- ipv6StaticNbrCfg    OBJECT IDENTIFIER ::= { layer3Configs 22 }
ipv6StaticNbrTableMaxSize OBJECT-TYPE
    SYNTAX  Integer32
    MAX-ACCESS  read-only
    STATUS  current
    DESCRIPTION
        "The maximum number of rows in the IPv6 Static Neighbor table.
	Note:This mib is not supported for VX instance of virtualization."
    ::= { ipv6StaticNbrCfg 1 }

ipv6CurCfgStaticNbrTable OBJECT-TYPE
    SYNTAX  SEQUENCE OF Ipv6CurCfgStaticNbrEntry
    MAX-ACCESS  not-accessible
    STATUS  current
    DESCRIPTION
        "The table of static IPv6 Neighbors in the current configuration block.
	Note:This mib is not supported for VX instance of virtualization."
    ::= { ipv6StaticNbrCfg 2 }

ipv6CurCfgStaticNbrEntry OBJECT-TYPE
    SYNTAX  Ipv6CurCfgStaticNbrEntry
    MAX-ACCESS  not-accessible
    STATUS  current
    DESCRIPTION
        "A row in the static IPv6 NBR table.
         Note:This mib is not supported for VX instance of virtualization."
    INDEX   { ipv6CurCfgStaticNbrIndx }
    ::= { ipv6CurCfgStaticNbrTable 1 }

Ipv6CurCfgStaticNbrEntry ::= SEQUENCE {
    ipv6CurCfgStaticNbrIndx       Integer32,
    ipv6CurCfgStaticNbrIpv6Addr   DisplayString,
    ipv6CurCfgStaticNbrMAC        PhysAddress,
    ipv6CurCfgStaticNbrVlan       Integer32,
    ipv6CurCfgStaticNbrPort       Integer32
    }

ipv6CurCfgStaticNbrIndx OBJECT-TYPE
    SYNTAX  Integer32
    MAX-ACCESS  read-only
    STATUS  current
    DESCRIPTION
        "The index of static IPv6 NBR table.
	Note:This mib is not supported for VX instance of virtualization."
    ::= { ipv6CurCfgStaticNbrEntry 1}

ipv6CurCfgStaticNbrIpv6Addr OBJECT-TYPE
    SYNTAX  DisplayString
    MAX-ACCESS  read-only
    STATUS  current
    DESCRIPTION
        "The IPv6 address for the static IPv6 NBR entry.
	Note:This mib is not supported for VX instance of virtualization."
    ::= { ipv6CurCfgStaticNbrEntry 2}

ipv6CurCfgStaticNbrMAC OBJECT-TYPE
    SYNTAX  PhysAddress
    MAX-ACCESS  read-only
    STATUS  current
    DESCRIPTION
        "The MAC address for the static IPv6 NBR entry.
	Note:This mib is not supported for VX instance of virtualization."
    ::= { ipv6CurCfgStaticNbrEntry 3 }

ipv6CurCfgStaticNbrVlan OBJECT-TYPE 
    SYNTAX  Integer32
    MAX-ACCESS  read-only 
    STATUS  current 
    DESCRIPTION 
        "The VLAN for the static IPv6 NBR entry.
	Note:This mib is not supported for VX instance of virtualization."
    ::= { ipv6CurCfgStaticNbrEntry 4}

ipv6CurCfgStaticNbrPort OBJECT-TYPE 
    SYNTAX  Integer32
    MAX-ACCESS  read-only 
    STATUS  current 
    DESCRIPTION 
        "The port for the static IPv6 NBR entry.
	Note:This mib is not supported for VX instance of virtualization."
    ::= { ipv6CurCfgStaticNbrEntry 5}

ipv6NewCfgStaticNbrTable OBJECT-TYPE
    SYNTAX  SEQUENCE OF Ipv6NewCfgStaticNbrEntry
    MAX-ACCESS  not-accessible
    STATUS  current
    DESCRIPTION
        "The table of static IPv6 Neighbors in the New configuration block.
	Note:This mib is not supported for VX instance of virtualization."
    ::= { ipv6StaticNbrCfg 3 }

ipv6NewCfgStaticNbrEntry OBJECT-TYPE
    SYNTAX  Ipv6NewCfgStaticNbrEntry
    MAX-ACCESS  not-accessible
    STATUS  current
    DESCRIPTION
        "A row in the static IPv6 NBR table.
         Note:This mib is not supported for VX instance of virtualization."
    INDEX   { ipv6NewCfgStaticNbrIndx }
    ::= { ipv6NewCfgStaticNbrTable 1 }

Ipv6NewCfgStaticNbrEntry ::= SEQUENCE {
    ipv6NewCfgStaticNbrIndx       Integer32,
    ipv6NewCfgStaticNbrIpv6Addr   DisplayString,
    ipv6NewCfgStaticNbrMAC        PhysAddress,
    ipv6NewCfgStaticNbrVlan       Integer32,
    ipv6NewCfgStaticNbrPort       Integer32,
    ipv6NewCfgStaticNbrAction     INTEGER
    }

ipv6NewCfgStaticNbrIndx OBJECT-TYPE
    SYNTAX  Integer32
    MAX-ACCESS  read-create
    STATUS  current
    DESCRIPTION
        "The index of static IPv6 NBR table.
	Note:This mib is not supported for VX instance of virtualization."
    ::= { ipv6NewCfgStaticNbrEntry 1}

ipv6NewCfgStaticNbrIpv6Addr OBJECT-TYPE
    SYNTAX  DisplayString
    MAX-ACCESS  read-create
    STATUS  current
    DESCRIPTION
        "The IPv6 address for the static IPv6 NBR entry.
	Note:This mib is not supported for VX instance of virtualization."
    ::= { ipv6NewCfgStaticNbrEntry 2}

ipv6NewCfgStaticNbrMAC OBJECT-TYPE
    SYNTAX  PhysAddress
    MAX-ACCESS  read-create
    STATUS  current
    DESCRIPTION
        "The MAC address for the static IPv6 NBR entry.
	Note:This mib is not supported for VX instance of virtualization."
    ::= { ipv6NewCfgStaticNbrEntry 3 }

ipv6NewCfgStaticNbrVlan OBJECT-TYPE 
    SYNTAX  Integer32
    MAX-ACCESS  read-create
    STATUS  current 
    DESCRIPTION 
        "The VLAN for the static IPv6 NBR entry.
	Note:This mib is not supported for VX instance of virtualization."
    ::= { ipv6NewCfgStaticNbrEntry 4}

ipv6NewCfgStaticNbrPort OBJECT-TYPE 
    SYNTAX  Integer32
    MAX-ACCESS  read-create
    STATUS  current 
    DESCRIPTION 
        "The port for the static IPv6 NBR entry.
	Note:This mib is not supported for VX instance of virtualization."
    ::= { ipv6NewCfgStaticNbrEntry 5}

ipv6NewCfgStaticNbrAction OBJECT-TYPE
    SYNTAX  INTEGER {
        other(1),
        delete(2),
        unsupported(2147483647)
       }  
    MAX-ACCESS  read-create
    STATUS  current
    DESCRIPTION
        "When set to the value of 2 (delete), the entire row is deleted. 
         When read, other is returned. Setting the value to anything other 
         than 2(delete) has no effect on the state of the row.
	Note:This mib is not supported for VX instance of virtualization."
    ::= { ipv6NewCfgStaticNbrEntry 6 }

ipv6StaticNbrTableNextAvailableIndex OBJECT-TYPE
    SYNTAX  Integer32
    MAX-ACCESS  read-only
    STATUS  current
    DESCRIPTION
        "The next available index in the static IPv6 NBR table.
	Note:This mib is not supported for VX instance of virtualization."
    ::= { ipv6StaticNbrCfg 4 }

-- IP tunnel

ipTunnelCurCfgTable OBJECT-TYPE
    SYNTAX  SEQUENCE OF IpTunnelCurCfgEntry
    MAX-ACCESS  not-accessible
    STATUS  current
    DESCRIPTION
        "The table of ip tunnels configuration in the Current Configuration Block.
        Note:This mib is not supported for VX instance of virtualization."
    ::= { ipTunnelCfg 2 }


ipTunnelCurCfgEntry OBJECT-TYPE
  SYNTAX  IpTunnelCurCfgEntry
  MAX-ACCESS  not-accessible
  STATUS  current
  DESCRIPTION                   
          "A row in the IP tunnel table.
          Note:This mib is not supported for VX instance of virtualization."
  INDEX   { ipTunnelCurCfgId } ::= { ipTunnelCurCfgTable 1 }                         
                                                                  
IpTunnelCurCfgEntry ::= SEQUENCE {
  ipTunnelCurCfgId		DisplayString,
  ipTunnelCurCfgIndex		Integer32,
  ipTunnelCurCfgState		INTEGER,
	ipTunnelCurCfgLocalMode		INTEGER,
  ipTunnelCurCfgLocalIfId		Integer32,
  ipTunnelCurCfgLocalVrId		Integer32,
  ipTunnelCurCfgLocalHaName	DisplayString,
	ipTunnelCurCfgIpVer		INTEGER,
	ipTunnelCurCfgIpVerMatch	INTEGER,
  ipTunnelCurCfgRemoteAddr4	IpAddress,
  ipTunnelCurCfgRemoteAddr6	DisplayString,
  ipTunnelCurCfgMatch		IpAddress,
	ipTunnelCurCfgMatch6		DisplayString,
  ipTunnelCurCfgType		INTEGER,
	ipTunnelCurCfgDescription	DisplayString,
  ipTunnelCurCfgGreKey            DisplayString,
  ipTunnelCurCfgInnerLocalIfId		Integer32
  
}
 
ipTunnelCurCfgId OBJECT-TYPE
    SYNTAX  DisplayString (SIZE(0..31))
    MAX-ACCESS  read-only
    STATUS  current
    DESCRIPTION
	"The IP tunnel number for which the information is related.
        Note:This mib is not supported for VX instance of virtualization."
    ::= { ipTunnelCurCfgEntry 1 }

ipTunnelCurCfgIndex OBJECT-TYPE
    SYNTAX  Integer32 
    MAX-ACCESS  read-only
    STATUS  current  
    DESCRIPTION
        "The tunnel local index.
        Note:This mib is not supported for VX instance of virtualization."
    ::= { ipTunnelCurCfgEntry 2 }

ipTunnelCurCfgState OBJECT-TYPE
    SYNTAX  INTEGER {
		enabled(2),
		disabled(3),
                unsupported(2147483647)
  }
  MAX-ACCESS  read-only
  STATUS  current
  DESCRIPTION
        "Enable or Disable the IP tunnel interface.
        Note:This mib is not supported for VX instance of virtualization."
    ::= { ipTunnelCurCfgEntry 3 }

ipTunnelCurCfgLocalMode OBJECT-TYPE
    SYNTAX  INTEGER{
          disabled(1),
          if(2),
          floating(3),
          vr(4),
          unsupported(2147483647)
    }
    MAX-ACCESS  read-only
    STATUS  current  
    DESCRIPTION
        "The tunnel local address mode.
        Note:This mib is not supported for VX instance of virtualization."
    ::= { ipTunnelCurCfgEntry 4 }

ipTunnelCurCfgLocalIfId OBJECT-TYPE
    SYNTAX  Integer32 
    MAX-ACCESS  read-only
    STATUS  current  
    DESCRIPTION
        "The tunnel local address.
        Note:This mib is not supported for VX instance of virtualization."
    ::= { ipTunnelCurCfgEntry 5 }

ipTunnelCurCfgLocalVrId OBJECT-TYPE
    SYNTAX  Integer32 
    MAX-ACCESS  read-only
    STATUS  current  
    DESCRIPTION
        "The tunnel local address.
        Note:This mib is not supported for VX instance of virtualization."
    ::= { ipTunnelCurCfgEntry 6 }

ipTunnelCurCfgLocalHaName OBJECT-TYPE
    SYNTAX  DisplayString (SIZE(0..31))
    MAX-ACCESS  read-only
    STATUS  current  
    DESCRIPTION
        "The tunnel local HA id.
        Note:This mib is not supported for VX instance of virtualization."
    ::= { ipTunnelCurCfgEntry 7 }

ipTunnelCurCfgIpVer OBJECT-TYPE
    SYNTAX  INTEGER{
        ipv4(1),
        ipv6(2),
        unsupported(2147483647)
	}
    MAX-ACCESS  read-only
    STATUS  current  
    DESCRIPTION
        "The type of IP address.
        Note:This mib is not supported for VX instance of virtualization."
    ::= { ipTunnelCurCfgEntry 8 }

ipTunnelCurCfgIpVerMatch OBJECT-TYPE
    SYNTAX  INTEGER{
        ipv4(1),
        ipv6(2),
        unsupported(2147483647)
	}
    MAX-ACCESS  read-only
    STATUS  current  
    DESCRIPTION
        "The type of IP address of the egress match criteria.
        Note:This mib is not supported for VX instance of virtualization."
    ::= { ipTunnelCurCfgEntry 9 }


ipTunnelCurCfgRemoteAddr4 OBJECT-TYPE
    SYNTAX  IpAddress
    MAX-ACCESS  read-only
    STATUS  current  
    DESCRIPTION
        "The remote tunnel IP address.
        Note:This mib is not supported for VX instance of virtualization."
    ::= { ipTunnelCurCfgEntry 10 }

ipTunnelCurCfgRemoteAddr6 OBJECT-TYPE
    SYNTAX  DisplayString  (SIZE(0..40))
    MAX-ACCESS read-only
    STATUS  current
    DESCRIPTION
        "The remote tunnel IPv6 address. Address should be 4-byte 
         haxadecimal colon notation.
         Valid IPv6 address should be in any of the following forms
           xxxx:xxxx:xxxx:xxxx:xxxx:xxxx:xxxx:xxxx or
           xxxx::xxxx:xxxx:xxxx:xxxx or ::xxxx.
           Note:This mib is not supported for VX instance of virtualization."
    ::= { ipTunnelCurCfgEntry 11 }

ipTunnelCurCfgMatch OBJECT-TYPE
    SYNTAX  IpAddress
    MAX-ACCESS  read-only
    STATUS  current  
    DESCRIPTION
        "The match criteria IP address.
        Note:This mib is not supported for VX instance of virtualization."
    ::= { ipTunnelCurCfgEntry 12 }

ipTunnelCurCfgMatch6 OBJECT-TYPE
    SYNTAX  DisplayString  (SIZE(0..40))
    MAX-ACCESS read-only
    STATUS  current
    DESCRIPTION
        "The match criteria IPv6 address. Address should be 4-byte 
         haxadecimal colon notation.
         Valid IPv6 address should be in any of the following forms
           xxxx:xxxx:xxxx:xxxx:xxxx:xxxx:xxxx:xxxx or
           xxxx::xxxx:xxxx:xxxx:xxxx or ::xxxx.
           Note:This mib is not supported for VX instance of virtualization."
    ::= { ipTunnelCurCfgEntry 13 }	
	
ipTunnelCurCfgType OBJECT-TYPE
  SYNTAX  INTEGER {
		disabled(1),
--        vxlan(2),
          ipinip(3),
          gre(4),
          unsupported(2147483647)
  }
    MAX-ACCESS read-only
    STATUS  current
    DESCRIPTION
        "The type of IP tunnel interface.
        Note:This mib is not supported for VX instance of virtualization."
    ::= { ipTunnelCurCfgEntry 14 }

ipTunnelCurCfgDescription OBJECT-TYPE
    SYNTAX  DisplayString (SIZE(1..32))
    MAX-ACCESS read-only
    STATUS  current
    DESCRIPTION
        "The descriptive tunnel name.
        Note:This mib is not supported for VX instance of virtualization."
    ::= { ipTunnelCurCfgEntry 15 }

ipTunnelCurCfgGreKey OBJECT-TYPE
    SYNTAX  DisplayString (SIZE(1..32))
    MAX-ACCESS read-only
    STATUS  current
    DESCRIPTION
        "The GRE tunnel key param.
        Note:This mib is not supported for VX instance of virtualization."
    ::= { ipTunnelCurCfgEntry 16 }

 ipTunnelCurCfgInnerLocalIfId OBJECT-TYPE
     SYNTAX  Integer32
     MAX-ACCESS  read-only
     STATUS  current
     DESCRIPTION
         "The tunnel local address.
        Note:This mib is not supported for VX instance of virtualization."
     ::= { ipTunnelCurCfgEntry 17 }


ipTunnelNewCfgTable OBJECT-TYPE
    SYNTAX  SEQUENCE OF IpTunnelNewCfgEntry
    MAX-ACCESS  not-accessible
    STATUS  current
    DESCRIPTION
        "The table of ip tunnels configuration in the New Configuration Block.
        Note:This mib is not supported for VX instance of virtualization."
    ::= { ipTunnelCfg 3 }


ipTunnelNewCfgEntry OBJECT-TYPE
  SYNTAX  IpTunnelNewCfgEntry
  MAX-ACCESS  not-accessible
  STATUS  current
  DESCRIPTION                   
          "A row in the IP tunnel table.
          Note:This mib is not supported for VX instance of virtualization."
  INDEX   { ipTunnelNewCfgId } ::= { ipTunnelNewCfgTable 1 }                         
                                                                  
IpTunnelNewCfgEntry ::= SEQUENCE {
  ipTunnelNewCfgId		DisplayString,
  ipTunnelNewCfgIndex		Integer32,
  ipTunnelNewCfgState		INTEGER,
	ipTunnelNewCfgLocalMode		INTEGER,
  ipTunnelNewCfgLocalIfId		Integer32,
  ipTunnelNewCfgLocalVrId		Integer32,
  ipTunnelNewCfgLocalHaName	DisplayString,
	ipTunnelNewCfgIpVer		INTEGER,
	ipTunnelNewCfgIpVerMatch	INTEGER,
  ipTunnelNewCfgRemoteAddr4	IpAddress,
  ipTunnelNewCfgRemoteAddr6	DisplayString,
	ipTunnelNewCfgDelete		INTEGER,
  ipTunnelNewCfgMatch		IpAddress,
	ipTunnelNewCfgMatch6		DisplayString,
  ipTunnelNewCfgType		INTEGER,
	ipTunnelNewCfgDescription	DisplayString,
  ipTunnelNewCfgGreKey		DisplayString,
  ipTunnelNewCfgInnerLocalIfId		Integer32

  
}
 
ipTunnelNewCfgId OBJECT-TYPE
    SYNTAX  DisplayString (SIZE(0..31))
    MAX-ACCESS  read-only
    STATUS  current
    DESCRIPTION
	"The IP tunnel number for which the information is related.
        Note:This mib is not supported for VX instance of virtualization."
    ::= { ipTunnelNewCfgEntry 1 }

ipTunnelNewCfgIndex OBJECT-TYPE
    SYNTAX  Integer32 
    MAX-ACCESS  read-create
    STATUS  current  
    DESCRIPTION
        "The tunnel Index.
        Note:This mib is not supported for VX instance of virtualization."
    ::= { ipTunnelNewCfgEntry 2 }

ipTunnelNewCfgState OBJECT-TYPE
    SYNTAX  INTEGER {
		enabled(2),
		disabled(3),
                unsupported(2147483647)
	}
    MAX-ACCESS  read-create
    STATUS  current
    DESCRIPTION
        "Enable or Disable the IP tunnel interface.
        Note:This mib is not supported for VX instance of virtualization."
    ::= { ipTunnelNewCfgEntry 3 }

ipTunnelNewCfgLocalMode OBJECT-TYPE
  SYNTAX  INTEGER{
          disabled(1),
          if(2),
          floating(3),
          vr(4),
          unsupported(2147483647)
  }
    MAX-ACCESS  read-create
    STATUS  current  
    DESCRIPTION
        "The tunnel local address mode.
        Note:This mib is not supported for VX instance of virtualization."
    ::= { ipTunnelNewCfgEntry 4 }

ipTunnelNewCfgLocalIfId OBJECT-TYPE
    SYNTAX  Integer32 
    MAX-ACCESS  read-create
    STATUS  current  
    DESCRIPTION
        "The tunnel local address.
        Note:This mib is not supported for VX instance of virtualization."
    ::= { ipTunnelNewCfgEntry 5 }

ipTunnelNewCfgLocalVrId OBJECT-TYPE
    SYNTAX  Integer32 
    MAX-ACCESS  read-create
    STATUS  current  
    DESCRIPTION
        "The tunnel local address.
        Note:This mib is not supported for VX instance of virtualization."
    ::= { ipTunnelNewCfgEntry 6 }

ipTunnelNewCfgLocalHaName OBJECT-TYPE
    SYNTAX  DisplayString (SIZE(0..31))
    MAX-ACCESS  read-create
    STATUS  current  
    DESCRIPTION
        "The tunnel local HA id.
        Note:This mib is not supported for VX instance of virtualization."
    ::= { ipTunnelNewCfgEntry 7 }

ipTunnelNewCfgIpVer OBJECT-TYPE
    SYNTAX  INTEGER{
        ipv4(1),
        ipv6(2),
        unsupported(2147483647)
	}
    MAX-ACCESS  read-create
    STATUS  current  
    DESCRIPTION
        "The type of IP address.
        Note:This mib is not supported for VX instance of virtualization."
    ::= { ipTunnelNewCfgEntry 8 }

ipTunnelNewCfgIpVerMatch OBJECT-TYPE
    SYNTAX  INTEGER{
        ipv4(1),
        ipv6(2),
        unsupported(2147483647)
	}
    MAX-ACCESS  read-create
    STATUS  current  
    DESCRIPTION
        "The type of IP address of the egress match criteria.
        Note:This mib is not supported for VX instance of virtualization."
    ::= { ipTunnelNewCfgEntry 9 }

ipTunnelNewCfgDelete OBJECT-TYPE
    SYNTAX  INTEGER { 
	        other(1),
          delete(2),
          unsupported(2147483647)
	}
    MAX-ACCESS  read-create
    STATUS  current
    DESCRIPTION
        "When set to the value of 2 (delete), the entire row is deleted. 
         When read, other(1) is returned. Setting the value to anything 
         other than 2(delete) has no effect on the state of the row.
        Note:This mib is not supported for VX instance of virtualization."
    ::= { ipTunnelNewCfgEntry 10 }

ipTunnelNewCfgRemoteAddr4 OBJECT-TYPE
    SYNTAX  IpAddress
    MAX-ACCESS  read-create
    STATUS  current  
    DESCRIPTION
        "The remote tunnel IP address.
        Note:This mib is not supported for VX instance of virtualization."
    ::= { ipTunnelNewCfgEntry 11 }

ipTunnelNewCfgRemoteAddr6 OBJECT-TYPE
    SYNTAX  DisplayString  (SIZE(0..40))
    MAX-ACCESS read-create
    STATUS  current
    DESCRIPTION
        "The remote tunnel IPv6 address. Address should be 4-byte 
         haxadecimal colon notation.
         Valid IPv6 address should be in any of the following forms
           xxxx:xxxx:xxxx:xxxx:xxxx:xxxx:xxxx:xxxx or
           xxxx::xxxx:xxxx:xxxx:xxxx or ::xxxx.
           Note:This mib is not supported for VX instance of virtualization."
    ::= { ipTunnelNewCfgEntry 12 }

ipTunnelNewCfgMatch OBJECT-TYPE
    SYNTAX  IpAddress
    MAX-ACCESS  read-create
    STATUS  current  
    DESCRIPTION
        "The match criteria IP address.
        Note:This mib is not supported for VX instance of virtualization."
    ::= { ipTunnelNewCfgEntry 13 }

ipTunnelNewCfgMatch6 OBJECT-TYPE
    SYNTAX  DisplayString  (SIZE(0..40))
    MAX-ACCESS read-create
    STATUS  current
    DESCRIPTION
        "The match criteria IPv6 address. Address should be 4-byte 
         haxadecimal colon notation.
         Valid IPv6 address should be in any of the following forms
           xxxx:xxxx:xxxx:xxxx:xxxx:xxxx:xxxx:xxxx or
           xxxx::xxxx:xxxx:xxxx:xxxx or ::xxxx.
           Note:This mib is not supported for VX instance of virtualization."
    ::= { ipTunnelNewCfgEntry 14 }	
	
ipTunnelNewCfgType OBJECT-TYPE
  SYNTAX  INTEGER {
          disabled(1),
--        vxlan(2),
          ipinip(3),
          gre(4),
          unsupported(2147483647)
  }
    MAX-ACCESS read-create
    STATUS  current
    DESCRIPTION
        "The type of IP tunnel interface.
        Note:This mib is not supported for VX instance of virtualization."
    ::= { ipTunnelNewCfgEntry 15 }

ipTunnelNewCfgDescription OBJECT-TYPE
    SYNTAX  DisplayString (SIZE(1..32))
    MAX-ACCESS read-create
    STATUS  current
    DESCRIPTION
        "The descriptive tunnel name.
        Note:This mib is not supported for VX instance of virtualization."
    ::= { ipTunnelNewCfgEntry 16 }
    
ipTunnelNewCfgGreKey OBJECT-TYPE
    SYNTAX  DisplayString (SIZE(1..32))
    MAX-ACCESS read-create
    STATUS  current
    DESCRIPTION
        "The GRE tunnel key param.
        Note:This mib is not supported for VX instance of virtualization."
    ::= { ipTunnelNewCfgEntry 17 }	

ipTunnelNewCfgInnerLocalIfId OBJECT-TYPE
    SYNTAX  Integer32
    MAX-ACCESS  read-create
    STATUS  current
    DESCRIPTION
        "The tunnel local inner address.
        Note:This mib is not supported for VX instance of virtualization."
    ::= { ipTunnelNewCfgEntry 18 }

-- Statistics

-- RIP Statistics Group

ripStatInPkts OBJECT-TYPE
    SYNTAX  Counter32
    MAX-ACCESS  read-only
    STATUS  current
    DESCRIPTION
        "The total number of good RIPv1 packets received.
         RIPv1 mibs are not supported anymore.
	Note:This mib is not supported for VX instance of virtualization."
    ::= { ripStats 1 }

ripStatOutPkts OBJECT-TYPE
    SYNTAX  Counter32
    MAX-ACCESS  read-only
    STATUS  current
    DESCRIPTION
        "The total number of RIPv1 packets transmitted.
         RIPv1 mibs are not supported anymore.
	Note:This mib is not supported for VX instance of virtualization."
    ::= { ripStats 2 }

ripStatInErrorPkts OBJECT-TYPE
    SYNTAX  Counter32
    MAX-ACCESS  read-only
    STATUS  current
    DESCRIPTION
        "The total number of error RIPv1 packets received.
         RIPv1 mibs are not supported anymore.
	Note:This mib is not supported for VX instance of virtualization."
    ::= { ripStats 3 }

ripStatRoutesAgedOut OBJECT-TYPE
    SYNTAX  Counter32
    MAX-ACCESS  read-only
    STATUS  current
    DESCRIPTION
        "The total number of RIPv1 routes which have aged out.
         RIPv1 mibs are not supported anymore.
	Note:This mib is not supported for VX instance of virtualization."
    ::= { ripStats 4 }


-- RIPv2 Statistics

ripStatInPackets OBJECT-TYPE
    SYNTAX  Counter32
    MAX-ACCESS  read-only
    STATUS  current
    DESCRIPTION
        "The total number of RIPv2 packets received.
	Note:This mib is not supported for VX instance of virtualization."
    ::= { rip2Stats 1 }

ripStatOutPackets OBJECT-TYPE
    SYNTAX  Counter32
    MAX-ACCESS  read-only
    STATUS  current
    DESCRIPTION
        "The total number of RIPv2 packets transmitted.
	Note:This mib is not supported for VX instance of virtualization."
    ::= { rip2Stats 2 }

ripStatInRequestPkts OBJECT-TYPE
    SYNTAX  Counter32
    MAX-ACCESS  read-only
    STATUS  current
    DESCRIPTION
        "The total number of RIPv2 requests received.
	Note:This mib is not supported for VX instance of virtualization."
    ::= { rip2Stats 3 }

ripStatInResponsePkts OBJECT-TYPE
    SYNTAX  Counter32
    MAX-ACCESS  read-only
    STATUS  current
    DESCRIPTION
        "The total number of RIPv2 response received.
	Note:This mib is not supported for VX instance of virtualization."
    ::= { rip2Stats 4 }

ripStatOutRequestPkts OBJECT-TYPE
    SYNTAX  Counter32
    MAX-ACCESS  read-only
    STATUS  current
    DESCRIPTION
        "The total number of RIPv2 requests transmitted.
	Note:This mib is not supported for VX instance of virtualization."
    ::= { rip2Stats 5 }

ripStatOutResponsePkts OBJECT-TYPE
    SYNTAX  Counter32
    MAX-ACCESS  read-only
    STATUS  current
    DESCRIPTION
        "The total number of RIPv2 responses transmitted.
	Note:This mib is not supported for VX instance of virtualization."
    ::= { rip2Stats 6 }

ripStatRouteTimeout OBJECT-TYPE
    SYNTAX  Counter32
    MAX-ACCESS  read-only
    STATUS  current
    DESCRIPTION
        "The total number of RIPv2 route timeouts.
	Note:This mib is not supported for VX instance of virtualization."
    ::= { rip2Stats 7 }

ripStatInBadSizePkts OBJECT-TYPE
    SYNTAX  Counter32
    MAX-ACCESS  read-only
    STATUS  current
    DESCRIPTION
        "The total number of bad size RIPv2 packets received.
	Note:This mib is not supported for VX instance of virtualization."
    ::= { rip2Stats 8 }

ripStatInBadVersion OBJECT-TYPE
    SYNTAX  Counter32
    MAX-ACCESS  read-only
    STATUS  current
    DESCRIPTION
        "The total number of RIPv2 bad versions received.
	Note:This mib is not supported for VX instance of virtualization."
    ::= { rip2Stats 9 }

ripStatInBadZeros OBJECT-TYPE
    SYNTAX  Counter32
    MAX-ACCESS  read-only
    STATUS  current
    DESCRIPTION
        "The total number of RIPv2 bad zeros received.
	Note:This mib is not supported for VX instance of virtualization."
    ::= { rip2Stats 10 }

ripStatInBadSourcePort OBJECT-TYPE
    SYNTAX  Counter32
    MAX-ACCESS  read-only
    STATUS  current
    DESCRIPTION
        "The total number of RIPv2 bad source port received.
	Note:This mib is not supported for VX instance of virtualization."
    ::= { rip2Stats 11 }

ripStatInBadSourceIP OBJECT-TYPE
    SYNTAX  Counter32
    MAX-ACCESS  read-only
    STATUS  current
    DESCRIPTION
        "The total number of RIPv2 bad source IP received.
	Note:This mib is not supported for VX instance of virtualization."
    ::= { rip2Stats 12 }

ripStatInSelfRcvPkts OBJECT-TYPE
    SYNTAX  Counter32
    MAX-ACCESS  read-only
    STATUS  current
    DESCRIPTION
        "The total number of RIPv2 packets from self received.
	Note:This mib is not supported for VX instance of virtualization."
    ::= { rip2Stats 13 }

-- TCP Statistics Group

tcpStatCurConn OBJECT-TYPE
    SYNTAX  Counter32
    MAX-ACCESS  read-only
    STATUS  current
    DESCRIPTION
        "The total number of outstanding TCP sessions that are currently opened.
	Note:This mib is not supported for VX instance of virtualization."
    ::= { tcpStats 1 }

tcpStatCurInConn OBJECT-TYPE
    SYNTAX  Counter32
    MAX-ACCESS  read-only
    STATUS  current
    DESCRIPTION
        "The total number of remotely-initiated TCP connections.
	Note:This mib is not supported for VX instance of virtualization."
    ::= { tcpStats 2 }

tcpStatCurOutConn OBJECT-TYPE
    SYNTAX  Counter32
    MAX-ACCESS  read-only
    STATUS  current
    DESCRIPTION
        "The total number of switch-originated TCP connection requests.
	Note:This mib is not supported for VX instance of virtualization."
    ::= { tcpStats 3 }

-- ARP Statistics Group

arpStatEntries OBJECT-TYPE
    SYNTAX  Gauge32 
    MAX-ACCESS  read-only
    STATUS  current
    DESCRIPTION
        "The current number of ARP entries.
	Note:This mib is not supported for VX instance of virtualization."
    ::= { arpStats 1 }

arpStatHighWater OBJECT-TYPE
    SYNTAX  Gauge32 
    MAX-ACCESS  read-only
    STATUS  current
    DESCRIPTION
        "The highest number of ARP entries.
	Note:This mib is not supported for VX instance of virtualization."
    ::= { arpStats 2 }

arpStatMaxEntries OBJECT-TYPE
    SYNTAX  Gauge32 
    MAX-ACCESS  read-only
    STATUS  current
    DESCRIPTION
        "The maximum number of ARP entries.
	Note:This mib is not supported for VX instance of virtualization."
    ::= { arpStats 3 }

-- ARP SP Statistics Group

arpSpStatsTable OBJECT-TYPE
    SYNTAX  SEQUENCE OF ArpSpStatsTableEntry
    MAX-ACCESS  not-accessible
    STATUS  current
    DESCRIPTION
        "The table of ARP SP Stats.
	Note:This mib is not supported for VX instance of virtualization."
    ::= { arpStats 4 }

arpSpStatsTableEntry OBJECT-TYPE
    SYNTAX  ArpSpStatsTableEntry
    MAX-ACCESS  not-accessible
    STATUS  current
    DESCRIPTION
        "A row in the ARP SP stats table.
	Note:This mib is not supported for VX instance of virtualization."
    INDEX   { arpSpStatSpIndex }
    ::= { arpSpStatsTable 1 }

ArpSpStatsTableEntry ::= SEQUENCE {
    arpSpStatSpIndex     Integer32,
    arpSpStatEntries     Gauge32,
    arpSpStatHighWater   Gauge32,
    arpSpStatMaxEntries  Gauge32
    }

arpSpStatSpIndex OBJECT-TYPE
    SYNTAX  Integer32
    MAX-ACCESS  read-only
    STATUS  current
    DESCRIPTION
        "The SP index.
	Note:This mib is not supported for VX instance of virtualization."
    ::= { arpSpStatsTableEntry 1 }

arpSpStatEntries OBJECT-TYPE
    SYNTAX  Gauge32
    MAX-ACCESS  read-only
    STATUS  current
    DESCRIPTION
        "The current number of SP ARP entries.
	Note:This mib is not supported for VX instance of virtualization."
    ::= { arpSpStatsTableEntry 2 }

arpSpStatHighWater OBJECT-TYPE
    SYNTAX  Gauge32
    MAX-ACCESS  read-only
    STATUS  current
    DESCRIPTION
        "The highest number of SP ARP entries.
	Note:This mib is not supported for VX instance of virtualization."
    ::= { arpSpStatsTableEntry 3 }

arpSpStatMaxEntries OBJECT-TYPE
    SYNTAX  Gauge32
    MAX-ACCESS  read-only
    STATUS  current
    DESCRIPTION
        "The maximum number of SP ARP entries.
	Note:This mib is not supported for VX instance of virtualization."
    ::= { arpSpStatsTableEntry 4 }

-- ROUTE Statistics Group

routeStatEntries OBJECT-TYPE
    SYNTAX  Gauge32 
    MAX-ACCESS  read-only
    STATUS  current
    DESCRIPTION
        "The current number of IP routes.
	Note:This mib is not supported for VX instance of virtualization."
    ::= { routeStats 1 }

routeStatHighWater OBJECT-TYPE
    SYNTAX  Gauge32 
    MAX-ACCESS  read-only
    STATUS  current
    DESCRIPTION
        "The highest number of IP routes.
	Note:This mib is not supported for VX instance of virtualization."
    ::= { routeStats 2 }

routeStatMaxEntries OBJECT-TYPE
    SYNTAX  Gauge32 
    MAX-ACCESS  read-only
    STATUS  current
    DESCRIPTION
        "The maximum number of IP routes.
	Note:This mib is not supported for VX instance of virtualization."
    ::= { routeStats 3 }

-- DNS Statistics

dnsStatInGoodDnsRequests OBJECT-TYPE 
    SYNTAX  Counter32 
    MAX-ACCESS  read-only
    STATUS  current 
    DESCRIPTION 
        "The total number of DNS request packets which are received.
	Note:This mib is not supported for VX instance of virtualization."
    ::= { dnsStats 1 }

dnsStatInBadDnsRequests OBJECT-TYPE 
    SYNTAX  Counter32 
    MAX-ACCESS  read-only
    STATUS  current 
    DESCRIPTION 
        "The total number of DNS request packets received that were dropped.
	Note:This mib is not supported for VX instance of virtualization."
    ::= { dnsStats 2 }

dnsStatOutDnsRequests OBJECT-TYPE 
    SYNTAX  Counter32 
    MAX-ACCESS  read-only
    STATUS  current 
    DESCRIPTION 
        "The total number of DNS response packets that have been transmitted.
	Note:This mib is not supported for VX instance of virtualization."
    ::= { dnsStats 3 }

-- The VRRP Statistics

vrrpStatInAdvers OBJECT-TYPE 
    SYNTAX  Counter32 
    MAX-ACCESS  read-only
    STATUS  current 
    DESCRIPTION 
        "The number of good VRRP advertisements which are received.
	Note:This mib is not supported for VX instance of virtualization."
    ::= { vrrpStats 1 }

vrrpStatOutAdvers OBJECT-TYPE 
    SYNTAX  Counter32 
    MAX-ACCESS  read-only
    STATUS  current 
    DESCRIPTION 
        "The number of good VRRP advertisements which are transmitted.
	Note:This mib is not supported for VX instance of virtualization."
    ::= { vrrpStats 2 }

vrrpStatOutBadAdvers OBJECT-TYPE 
    SYNTAX  Counter32 
    MAX-ACCESS  read-only
    STATUS  current 
    DESCRIPTION 
        "The number of bad VRRP advertisements which are received.
	Note:This mib is not supported for VX instance of virtualization."
    ::= { vrrpStats 3 }

vrrpStatBadPassword OBJECT-TYPE
    SYNTAX  Counter32
    MAX-ACCESS  read-only
    STATUS  current
    DESCRIPTION
        "The number of bad VRRP password.
	Note:This mib is not supported for VX instance of virtualization."
    ::= { vrrpStats 4 }

vrrpStatBadVersion OBJECT-TYPE
    SYNTAX  Counter32
    MAX-ACCESS  read-only
    STATUS  current
    DESCRIPTION
        "The number of bad VRRP version which are received.
	Note:This mib is not supported for VX instance of virtualization."
    ::= { vrrpStats 5 }

vrrpStatBadVrid OBJECT-TYPE
    SYNTAX  Counter32
    MAX-ACCESS  read-only
    STATUS  current
    DESCRIPTION
        "The number of bad VRRP VR id which are received.
	Note:This mib is not supported for VX instance of virtualization."
    ::= { vrrpStats 6 }

vrrpStatBadAddress OBJECT-TYPE
    SYNTAX  Counter32
    MAX-ACCESS  read-only
    STATUS  current
    DESCRIPTION
        "The number of bad VRRP address which are received.
	Note:This mib is not supported for VX instance of virtualization."
    ::= { vrrpStats 7 }

vrrpStatBadData OBJECT-TYPE
    SYNTAX  Counter32
    MAX-ACCESS  read-only
    STATUS  current
    DESCRIPTION
        "The number of bad VRRP data which are received.
	Note:This mib is not supported for VX instance of virtualization."
    ::= { vrrpStats 8 }

vrrpStatBadInterval OBJECT-TYPE
    SYNTAX  Counter32
    MAX-ACCESS  read-only
    STATUS  current
    DESCRIPTION
        "The number of bad VRRP Interval which are received.
	Note:This mib is not supported for VX instance of virtualization."
    ::= { vrrpStats 9 }

vrrpStatBadHaid OBJECT-TYPE
   SYNTAX  Counter32
    MAX-ACCESS  read-only
    STATUS  current
    DESCRIPTION
        "The number of bad VRRP Haid which are received.
	Note:This mib is not supported for VX instance of virtualization."
    ::= { vrrpStats 10 }

-- Clear Statistics  for ip and ip interface
ipClearStats OBJECT-TYPE
    SYNTAX  INTEGER { 
	ok(1),
	clear(2),
        unsupported(2147483647)
	}
    MAX-ACCESS  read-write
    STATUS  current  
    DESCRIPTION
        "Setting this to clear(2) results in clearing the IP statistics.
	Note:This mib is not supported for VX instance of virtualization." 
    ::= { clearStats 1 }

ifStatsTable OBJECT-TYPE
    SYNTAX SEQUENCE OF IfStatsEntry
    MAX-ACCESS not-accessible
    STATUS current
    DESCRIPTION
      "The table of Interface Statistics.
	Note:This mib is not supported for VX instance of virtualization."
    ::= { clearStats 2 }

ifStatsEntry OBJECT-TYPE
    SYNTAX IfStatsEntry
    MAX-ACCESS not-accessible
    STATUS current
    DESCRIPTION
      "IP Interface statistics.
	Note:This mib is not supported for VX instance of virtualization."
    INDEX { ifStatsIndex }
    ::= { ifStatsTable 1 }
 
IfStatsEntry ::= SEQUENCE {
    ifStatsIndex               Integer32,
    ifClearStats               INTEGER
    }

ifStatsIndex OBJECT-TYPE
    SYNTAX  Integer32
    MAX-ACCESS  read-only
    STATUS  current
    DESCRIPTION
        "The index of the IP interface for which these statistics apply.
	Note:This mib is not supported for VX instance of virtualization."
    ::= { ifStatsEntry 1 }

ifClearStats OBJECT-TYPE
    SYNTAX  INTEGER { 
	ok(1),
	clear(2),
        unsupported(2147483647)
	}
    MAX-ACCESS  read-write
    STATUS  current  
    DESCRIPTION
        "Setting this to clear(2) results in clearing the statistics for this
         IP interface (if) stats.
	Note:This mib is not supported for VX instance of virtualization." 
    ::= { ifStatsEntry 2 }

urlfClearStats OBJECT-TYPE
    SYNTAX  INTEGER { 
	ok(1),
	clear(2),
        unsupported(2147483647)
	}
    MAX-ACCESS  read-write
    STATUS  current  
    DESCRIPTION
        "Setting this to clear(2) results in clearing the URL Filtering statistics.
	Note:This mib is not supported for VX instance of virtualization." 
    ::= { clearStats 3 }
tunelClearStats OBJECT-TYPE
    SYNTAX  INTEGER {
        ok(1),
        clear(2),
        unsupported(2147483647)
        }
    MAX-ACCESS  read-write
    STATUS  current
    DESCRIPTION
        "Setting this to clear(2) results in clearing the IP Tunnel statistics.
        Note:This mib is not supported for VX instance of virtualization."
    ::= { clearStats 4 }
-- Ospf Statistics 

-- Ospf Statistics for all interfaces and OSPF areas 
ospfGeneralStats       OBJECT IDENTIFIER ::= { ospfStats  1 }
ospfCumRxTxStats       OBJECT IDENTIFIER ::= { ospfGeneralStats  1 }
ospfCumNbrChangeStats  OBJECT IDENTIFIER ::= { ospfGeneralStats  2 }
ospfCumIntfChangeStats OBJECT IDENTIFIER ::= { ospfGeneralStats  3 }
ospfTimersKickOffStats OBJECT IDENTIFIER ::= { ospfGeneralStats  4 }

-- Ospf Statistics / Area
ospfArea	       OBJECT IDENTIFIER ::= { ospfStats  2 }

ospfAreaRxTxStats OBJECT-TYPE
    SYNTAX SEQUENCE OF OspfAreaRxTxStatsEntry
    MAX-ACCESS not-accessible
    STATUS current
    DESCRIPTION
      "The table of OSPF Area Rx/Tx Statistics.
	Note:This mib is not supported for VX instance of virtualization."
    ::= { ospfArea 1 }

ospfAreaRxTxStatsEntry OBJECT-TYPE
    SYNTAX OspfAreaRxTxStatsEntry
    MAX-ACCESS not-accessible
    STATUS current
    DESCRIPTION
      "Rx Tx packet Statistics about a OSPF area.
	Note:This mib is not supported for VX instance of virtualization."
    INDEX { ospfAreaRxTxIndex }
    ::= { ospfAreaRxTxStats 1 }
 
OspfAreaRxTxStatsEntry ::= SEQUENCE {
    ospfAreaRxTxIndex          Integer32,
    ospfAreaRxPkts             Counter32,
    ospfAreaTxPkts             Counter32,
    ospfAreaRxHello            Counter32,
    ospfAreaTxHello            Counter32,
    ospfAreaRxDatabase         Counter32,
    ospfAreaTxDatabase         Counter32,
    ospfAreaRxlsReqs           Counter32,
    ospfAreaTxlsReqs           Counter32,
    ospfAreaRxlsAcks           Counter32,
    ospfAreaTxlsAcks           Counter32,
    ospfAreaRxlsUpdates        Counter32,
    ospfAreaTxlsUpdates        Counter32
    }

ospfAreaRxTxIndex OBJECT-TYPE
    SYNTAX  Integer32
    MAX-ACCESS  read-only
    STATUS  current
    DESCRIPTION
        "The index of the ospf Area for which these statistics apply.
	Note:This mib is not supported for VX instance of virtualization."
    ::= { ospfAreaRxTxStatsEntry 1 }

ospfAreaRxPkts OBJECT-TYPE
    SYNTAX  Counter32
    MAX-ACCESS  read-only
    STATUS  current
    DESCRIPTION
        "The total number of OSPF packets received in this OSPF area.
	Note:This mib is not supported for VX instance of virtualization."
    ::= { ospfAreaRxTxStatsEntry 2 }
 
ospfAreaTxPkts OBJECT-TYPE
    SYNTAX  Counter32
    MAX-ACCESS  read-only
    STATUS  current
    DESCRIPTION
        "The total number of OSPF packets transmitted in this OSPF area.
	Note:This mib is not supported for VX instance of virtualization."
    ::= { ospfAreaRxTxStatsEntry 3 }
 
ospfAreaRxHello OBJECT-TYPE
    SYNTAX  Counter32 
    MAX-ACCESS  read-only
    STATUS  current
    DESCRIPTION
        "The total number of Hello packets received in this OSPF area.
	Note:This mib is not supported for VX instance of virtualization."
    ::= { ospfAreaRxTxStatsEntry 4 }

ospfAreaTxHello OBJECT-TYPE
    SYNTAX  Counter32
    MAX-ACCESS  read-only
    STATUS  current
    DESCRIPTION
        "The total number of Hello packets transmitted in this OSPF
         area.
	Note:This mib is not supported for VX instance of virtualization."
    ::= { ospfAreaRxTxStatsEntry 5 }
 
ospfAreaRxDatabase OBJECT-TYPE
    SYNTAX  Counter32 
    MAX-ACCESS  read-only
    STATUS  current
    DESCRIPTION
        "The total number of Database Description packets transmitted 
         for this OSPF area.
	Note:This mib is not supported for VX instance of virtualization."
    ::= { ospfAreaRxTxStatsEntry 6 }

ospfAreaTxDatabase OBJECT-TYPE
    SYNTAX  Counter32
    MAX-ACCESS  read-only
    STATUS  current
    DESCRIPTION
        "The total number of Database Description packets transmitted 
         for this OSPF area.
	Note:This mib is not supported for VX instance of virtualization."
    ::= { ospfAreaRxTxStatsEntry 7 }
 
ospfAreaRxlsReqs OBJECT-TYPE
    SYNTAX  Counter32 
    MAX-ACCESS  read-only
    STATUS  current
    DESCRIPTION
        "The total number of Link State Request packets received for 
         this OSPF area.
	Note:This mib is not supported for VX instance of virtualization."
    ::= { ospfAreaRxTxStatsEntry 8 }

ospfAreaTxlsReqs OBJECT-TYPE
    SYNTAX  Counter32 
    MAX-ACCESS  read-only
    STATUS  current
    DESCRIPTION
        "The total number of Link State Request packets transmitted for 
         this OSPF area.
	Note:This mib is not supported for VX instance of virtualization."
    ::= { ospfAreaRxTxStatsEntry 9 }

ospfAreaRxlsAcks OBJECT-TYPE
    SYNTAX  Counter32
    MAX-ACCESS  read-only
    STATUS  current
    DESCRIPTION
        "The total number of Link State Acknowledgement packets received for 
         this OSPF area.
	Note:This mib is not supported for VX instance of virtualization."
    ::= { ospfAreaRxTxStatsEntry 10 }
 
ospfAreaTxlsAcks OBJECT-TYPE
    SYNTAX  Counter32 
    MAX-ACCESS  read-only
    STATUS  current
    DESCRIPTION
        "The total number of Link State Acknowledgement packets transmitted
         for this OSPF area.
	Note:This mib is not supported for VX instance of virtualization."
    ::= { ospfAreaRxTxStatsEntry 11 }

ospfAreaRxlsUpdates OBJECT-TYPE
    SYNTAX  Counter32
    MAX-ACCESS  read-only
    STATUS  current
    DESCRIPTION
        "The total number of Link State Update packets received for 
         this OSPF area.
	Note:This mib is not supported for VX instance of virtualization."
    ::= { ospfAreaRxTxStatsEntry 12 }
 
ospfAreaTxlsUpdates OBJECT-TYPE
    SYNTAX  Counter32 
    MAX-ACCESS  read-only
    STATUS  current
    DESCRIPTION
        "The total number of Link State Update packets transmitted for 
         this OSPF area.
	Note:This mib is not supported for VX instance of virtualization."
    ::= { ospfAreaRxTxStatsEntry 13 }


ospfAreaNbrChangeStats OBJECT-TYPE
    SYNTAX SEQUENCE OF OspfAreaNbrChangeStatsEntry
    MAX-ACCESS not-accessible
    STATUS current
    DESCRIPTION
      "The table of OSPF Area Neighbour Statistics.
	Note:This mib is not supported for VX instance of virtualization."
    ::= { ospfArea 2 }

ospfAreaNbrChangeStatsEntry OBJECT-TYPE
    SYNTAX OspfAreaNbrChangeStatsEntry
    MAX-ACCESS not-accessible
    STATUS current
    DESCRIPTION
      "Area Neighbour Change Statistics about a OSPF area.
	Note:This mib is not supported for VX instance of virtualization."
    INDEX { ospfAreaNbrIndex }
    ::= { ospfAreaNbrChangeStats 1 }
 
OspfAreaNbrChangeStatsEntry ::= SEQUENCE {
    ospfAreaNbrIndex  	       	Integer32,
    ospfAreaNbrhello           	Counter32,
    ospfAreaNbrStart           	Counter32,
    ospfAreaNbrAdjointOk       	Counter32,
    ospfAreaNbrNegotiationDone 	Counter32,
    ospfAreaNbrExchangeDone     Counter32,
    ospfAreaNbrBadRequests      Counter32,
    ospfAreaNbrBadSequence      Counter32,
    ospfAreaNbrLoadingDone      Counter32,
    ospfAreaNbrN1way        	Counter32,
    ospfAreaNbrRstAd        	Counter32,
    ospfAreaNbrDown        	Counter32,
    ospfAreaNbrN2way           	Counter32
    }

ospfAreaNbrIndex OBJECT-TYPE
    SYNTAX  Integer32
    MAX-ACCESS  read-only
    STATUS  current
    DESCRIPTION
        "The index of the ospf Area for which these statistics apply.
	Note:This mib is not supported for VX instance of virtualization."
    ::= { ospfAreaNbrChangeStatsEntry 1 }

ospfAreaNbrhello OBJECT-TYPE
    SYNTAX  Counter32
    MAX-ACCESS  read-only
    STATUS  current
    DESCRIPTION
        "The total number of Hello packets received from neighbours
         in this OSPF area.
	Note:This mib is not supported for VX instance of virtualization."
    ::= { ospfAreaNbrChangeStatsEntry 2 }

ospfAreaNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF area.
	Note:This mib is not supported for VX instance of virtualization."
    ::= { ospfAreaNbrChangeStatsEntry 3 }

ospfAreaNbrAdjointOk OBJECT-TYPE
    SYNTAX  Counter32
    MAX-ACCESS  read-only
    STATUS  current
    DESCRIPTION
        "The total number of decisions to be made (again) as to whether
         an adjacency should be established/maintained with the neighbour.
         for this OSPF area.
	Note:This mib is not supported for VX instance of virtualization."
    ::= { ospfAreaNbrChangeStatsEntry 4 }

ospfAreaNbrNegotiationDone OBJECT-TYPE
    SYNTAX  Counter32
    MAX-ACCESS  read-only
    STATUS  current
    DESCRIPTION
        "The total number of neighbours in this state wherein the 
         Master/slave relationship has been negotiated, and sequence
         numbers have been exchanged, for this OSPF area.
	Note:This mib is not supported for VX instance of virtualization."
    ::= { ospfAreaNbrChangeStatsEntry 5 }

ospfAreaNbrExchangeDone OBJECT-TYPE
    SYNTAX  Counter32
    MAX-ACCESS  read-only
    STATUS  current
    DESCRIPTION
        "The total number of neighbours in this state (i.e. in an
         adjacency's final state) having transimitted a full sequence 
         of Database Description packets, for this OSPF area.
	Note:This mib is not supported for VX instance of virtualization."
    ::= { ospfAreaNbrChangeStatsEntry 6 }

ospfAreaNbrBadRequests OBJECT-TYPE
    SYNTAX  Counter32
    MAX-ACCESS  read-only
    STATUS  current
    DESCRIPTION
        "The sum total number of Link State Requests which have been received
         for a link state advertisement not contained in the database across
         this OSPF area.
	Note:This mib is not supported for VX instance of virtualization."
    ::= { ospfAreaNbrChangeStatsEntry 7 }

ospfAreaNbrBadSequence OBJECT-TYPE
    SYNTAX  Counter32
    MAX-ACCESS  read-only
    STATUS  current
    DESCRIPTION
        "The total number of Database Description packets which have been
         received that either 
         a) has an unexpected DD sequence number
         b) Unexpectedly has the init bit set
         c) Has an options field differing from the last Options field
            received in a Database Description packet.
         Any of these conditions indicate that some error has occured during
         adjacency establishment for this OSPF area.
	Note:This mib is not supported for VX instance of virtualization."
    ::= { ospfAreaNbrChangeStatsEntry 8 }

ospfAreaNbrLoadingDone OBJECT-TYPE
    SYNTAX  Counter32
    MAX-ACCESS  read-only
    STATUS  current
    DESCRIPTION
        "The total number of link state updates received for all 
         out-of-date portions of the database in this OSPF area.
	Note:This mib is not supported for VX instance of virtualization."
    ::= { ospfAreaNbrChangeStatsEntry 9 }

ospfAreaNbrN1way OBJECT-TYPE
    SYNTAX  Counter32
    MAX-ACCESS  read-only
    STATUS  current
    DESCRIPTION
        "The total number of Hello packets received from neighbours, in
         which this router is not mentioned in this OSPF area.
	Note:This mib is not supported for VX instance of virtualization."
    ::= { ospfAreaNbrChangeStatsEntry 10 }

ospfAreaNbrRstAd OBJECT-TYPE
    SYNTAX  Counter32
    MAX-ACCESS  read-only
    STATUS  current
    DESCRIPTION
        "The total number of times the Neighbour adjacency has been reset
         across this OPSF area.
	Note:This mib is not supported for VX instance of virtualization."
    ::= { ospfAreaNbrChangeStatsEntry 11 }

ospfAreaNbrDown OBJECT-TYPE
    SYNTAX  Counter32
    MAX-ACCESS  read-only
    STATUS  current
    DESCRIPTION
        "The total number of Neighbouring routers down (i.e. in the initial
         state of a neighbour conversation.) in this OSPF area.
	Note:This mib is not supported for VX instance of virtualization."
    ::= { ospfAreaNbrChangeStatsEntry 12 }

ospfAreaNbrN2way OBJECT-TYPE
    SYNTAX  Counter32
    MAX-ACCESS  read-only
    STATUS  current
    DESCRIPTION
        "The total number of Hello packets received from neighbours, in
         which this router is mentioned in this OSPF area.
	Note:This mib is not supported for VX instance of virtualization."
    ::= { ospfAreaNbrChangeStatsEntry 13 }

ospfAreaChangeStats OBJECT-TYPE
    SYNTAX SEQUENCE OF OspfAreaChangeStatsEntry
    MAX-ACCESS not-accessible
    STATUS current
    DESCRIPTION
      "The table of OSPF Area Change Statistics.
	Note:This mib is not supported for VX instance of virtualization."
    ::= { ospfArea 3 }

ospfAreaChangeStatsEntry OBJECT-TYPE
    SYNTAX OspfAreaChangeStatsEntry
    MAX-ACCESS not-accessible
    STATUS current
    DESCRIPTION
      "Area  Change Statistics about a OSPF area.
	Note:This mib is not supported for VX instance of virtualization."
    INDEX { ospfAreaIntfIndex }
    ::= { ospfAreaChangeStats 1 }
 
OspfAreaChangeStatsEntry ::= SEQUENCE {
    ospfAreaIntfIndex     	Integer32,
    ospfAreaIntfHello           Counter32,
    ospfAreaIntfDown           	Counter32,
    ospfAreaIntfLoop       	Counter32,
    ospfAreaIntfUnloop 		Counter32,
    ospfAreaIntfWaitTimer     	Counter32,
    ospfAreaIntfBackup	        Counter32,
    ospfAreaIntfNbrChange       Counter32
    }

ospfAreaIntfIndex OBJECT-TYPE
    SYNTAX    Integer32
    MAX-ACCESS    read-only
    STATUS    current
    DESCRIPTION
        "The index of the OSPF Area for which these statistics apply.
	Note:This mib is not supported for VX instance of virtualization."
    ::= { ospfAreaChangeStatsEntry 1 }

ospfAreaIntfHello OBJECT-TYPE
    SYNTAX    Counter32
    MAX-ACCESS    read-only
    STATUS    current
    DESCRIPTION
        "The total number of Hello packets sent on this OSPF area.
	Note:This mib is not supported for VX instance of virtualization."
    ::= { ospfAreaChangeStatsEntry 2 }

ospfAreaIntfDown OBJECT-TYPE
    SYNTAX   Counter32
    MAX-ACCESS   read-only
    STATUS   current
    DESCRIPTION
        "The total number of interfaces down in this OSPF area.
	Note:This mib is not supported for VX instance of virtualization."
    ::= { ospfAreaChangeStatsEntry 3 }

ospfAreaIntfLoop OBJECT-TYPE
    SYNTAX    Counter32
    MAX-ACCESS    read-only
    STATUS    current
    DESCRIPTION
        "The total number of interfaces no longer connected to 
         the attatched network in this OSPF area.
	Note:This mib is not supported for VX instance of virtualization."
    ::= { ospfAreaChangeStatsEntry 4 }

ospfAreaIntfUnloop OBJECT-TYPE
    SYNTAX   Counter32
    MAX-ACCESS   read-only
    STATUS   current
    DESCRIPTION
        "The total number of interfaces connected to the attatched
	 network in this OSPF area..
	Note:This mib is not supported for VX instance of virtualization."
    ::= { ospfAreaChangeStatsEntry 5 }


ospfAreaIntfWaitTimer OBJECT-TYPE
    SYNTAX        Counter32
    MAX-ACCESS        read-only
    STATUS        current
    DESCRIPTION
        "The total number of times the Wait Timer has been fired,
         (indicating the end of the waiting period that is required
          before electing a (Backup) Designated Router) for this 
          OSPF area.
	Note:This mib is not supported for VX instance of virtualization."
    ::= { ospfAreaChangeStatsEntry 6 }

ospfAreaIntfBackup OBJECT-TYPE
    SYNTAX     Counter32
    MAX-ACCESS     read-only
    STATUS     current
    DESCRIPTION
        "The total number of Backup Designated Routers on the attatched
         network for this OSPF area.
	Note:This mib is not supported for VX instance of virtualization."
    ::= { ospfAreaChangeStatsEntry 7 }


ospfAreaIntfNbrChange OBJECT-TYPE
    SYNTAX     Counter32
    MAX-ACCESS     read-only
    STATUS     current
    DESCRIPTION
        "The total number of changes in the set of bidirectional neighbours
         associated with the interface in this OSPF area.
	Note:This mib is not supported for VX instance of virtualization."
    ::= { ospfAreaChangeStatsEntry 8 }

ospfAreaErrorStats OBJECT-TYPE
    SYNTAX SEQUENCE OF OspfAreaErrorStatsEntry
    MAX-ACCESS not-accessible
    STATUS current
    DESCRIPTION
      "The table of OSPF Area Error Statistics.
	Note:This mib is not supported for VX instance of virtualization."
    ::= { ospfArea 4 }

ospfAreaErrorStatsEntry OBJECT-TYPE
    SYNTAX OspfAreaErrorStatsEntry
    MAX-ACCESS not-accessible
    STATUS current
    DESCRIPTION
      "Error Statistics for an OSPF area.
	Note:This mib is not supported for VX instance of virtualization."
    INDEX { ospfAreaErrIndex }
    ::= { ospfAreaErrorStats 1 }
 
OspfAreaErrorStatsEntry ::= SEQUENCE {
    ospfAreaErrIndex     	Integer32,
    ospfAreaErrAuthFailure      Counter32,
    ospfAreaErrNetmaskMismatch  Counter32,
    ospfAreaErrHelloMismatch    Counter32,
    ospfAreaErrDeadMismatch     Counter32,
    ospfAreaErrOptionsMismatch  Counter32,
    ospfAreaErrUnknownNbr       Counter32
    }

ospfAreaErrIndex OBJECT-TYPE
    SYNTAX    Integer32
    MAX-ACCESS    read-only
    STATUS    current
    DESCRIPTION
        "The index of the OSPF Area for which these statistics apply.
	Note:This mib is not supported for VX instance of virtualization."
    ::= { ospfAreaErrorStatsEntry 1 }

ospfAreaErrAuthFailure OBJECT-TYPE
    SYNTAX    Counter32
    MAX-ACCESS    read-only
    STATUS    current
    DESCRIPTION
        "The total number of packets received with a wrong password in 
         this area.
	Note:This mib is not supported for VX instance of virtualization."
    ::= { ospfAreaErrorStatsEntry 2 }

ospfAreaErrNetmaskMismatch OBJECT-TYPE
    SYNTAX    Counter32
    MAX-ACCESS    read-only
    STATUS    current
    DESCRIPTION
        "The total number of packets received with a wrong netmask in 
         this area.
	Note:This mib is not supported for VX instance of virtualization."
    ::= { ospfAreaErrorStatsEntry 3 }

ospfAreaErrHelloMismatch OBJECT-TYPE
    SYNTAX    Counter32
    MAX-ACCESS    read-only
    STATUS    current
    DESCRIPTION
        "The total number of packets received with a different hello interval
         in this area.
	Note:This mib is not supported for VX instance of virtualization."
    ::= { ospfAreaErrorStatsEntry 4 }

ospfAreaErrDeadMismatch OBJECT-TYPE
    SYNTAX    Counter32
    MAX-ACCESS    read-only
    STATUS    current
    DESCRIPTION
        "The total number of packets received with a different dead interval
         in this area.
	Note:This mib is not supported for VX instance of virtualization."
    ::= { ospfAreaErrorStatsEntry 5 }

ospfAreaErrOptionsMismatch OBJECT-TYPE
    SYNTAX    Counter32
    MAX-ACCESS    read-only
    STATUS    current
    DESCRIPTION
        "The total number of packets received with a different options
         in this area.
	Note:This mib is not supported for VX instance of virtualization."
    ::= { ospfAreaErrorStatsEntry 6 }

ospfAreaErrUnknownNbr OBJECT-TYPE
    SYNTAX    Counter32
    MAX-ACCESS    read-only
    STATUS    current
    DESCRIPTION
        "The total number of packets received from an unknown neighbour
         in this area.
	Note:This mib is not supported for VX instance of virtualization."
    ::= { ospfAreaErrorStatsEntry 7 }

-- Ospf Statistics / Interface
ospfInterface	       OBJECT IDENTIFIER ::= { ospfStats  3 }

ospfIntfRxTxStats OBJECT-TYPE
    SYNTAX SEQUENCE OF OspfIntfRxTxStatsEntry
    MAX-ACCESS not-accessible
    STATUS current
    DESCRIPTION
      "The table of OSPF Interface Rx/Tx packet Statistics.
	Note:This mib is not supported for VX instance of virtualization."
    ::= { ospfInterface 1 }

ospfIntfRxTxStatsEntry OBJECT-TYPE
    SYNTAX OspfIntfRxTxStatsEntry
    MAX-ACCESS not-accessible
    STATUS current
    DESCRIPTION
      "OSPF interface Rx/Tx packet statistics.
	Note:This mib is not supported for VX instance of virtualization."
    INDEX { ospfIntfRxTxIndex }
    ::= { ospfIntfRxTxStats 1 }

OspfIntfRxTxStatsEntry ::= SEQUENCE {
    ospfIntfRxTxIndex          Integer32,
    ospfIntfRxPkts             Counter32,
    ospfIntfTxPkts             Counter32,
    ospfIntfRxHello            Counter32,
    ospfIntfTxHello            Counter32,
    ospfIntfRxDatabase         Counter32,
    ospfIntfTxDatabase         Counter32,
    ospfIntfRxlsReqs           Counter32,
    ospfIntfTxlsReqs           Counter32,
    ospfIntfRxlsAcks           Counter32,
    ospfIntfTxlsAcks           Counter32,
    ospfIntfRxlsUpdates        Counter32,
    ospfIntfTxlsUpdates        Counter32
    }

ospfIntfRxTxIndex OBJECT-TYPE
    SYNTAX  Integer32
    MAX-ACCESS  read-only
    STATUS  current
    DESCRIPTION
        "The OSPF interface for which these statistics apply.
	Note:This mib is not supported for VX instance of virtualization."
    ::= { ospfIntfRxTxStatsEntry 1 }

ospfIntfRxPkts OBJECT-TYPE
    SYNTAX  Counter32
    MAX-ACCESS  read-only
    STATUS  current
    DESCRIPTION
        "The total number of OSPF packets received for this OSPF interface.
	Note:This mib is not supported for VX instance of virtualization."
    ::= { ospfIntfRxTxStatsEntry 2 }
 
ospfIntfTxPkts OBJECT-TYPE
    SYNTAX  Counter32
    MAX-ACCESS  read-only
    STATUS  current
    DESCRIPTION
        "The total number of OSPF packets transmitted for this OSPF interface.
	Note:This mib is not supported for VX instance of virtualization."
    ::= { ospfIntfRxTxStatsEntry 3 }
 
ospfIntfRxHello OBJECT-TYPE
    SYNTAX  Counter32 
    MAX-ACCESS  read-only
    STATUS  current
    DESCRIPTION
        "The total number of Hello packets received 
         for this OSPF interface.
	Note:This mib is not supported for VX instance of virtualization."
    ::= { ospfIntfRxTxStatsEntry 4 }

ospfIntfTxHello OBJECT-TYPE
    SYNTAX  Counter32
    MAX-ACCESS  read-only
    STATUS  current
    DESCRIPTION
        "The total number of Hello packets transmitted 
         for this OSPF interface.
	Note:This mib is not supported for VX instance of virtualization."
    ::= { ospfIntfRxTxStatsEntry 5 }
 
ospfIntfRxDatabase OBJECT-TYPE
    SYNTAX  Counter32 
    MAX-ACCESS  read-only
    STATUS  current
    DESCRIPTION
        "The total number of Database Description packets received 
         for this OSPF interface.
	Note:This mib is not supported for VX instance of virtualization."
    ::= { ospfIntfRxTxStatsEntry 6 }

ospfIntfTxDatabase OBJECT-TYPE
    SYNTAX  Counter32
    MAX-ACCESS  read-only
    STATUS  current
    DESCRIPTION
        "The total number of Database Description packets transmitted 
         for this OSPF interface.
	Note:This mib is not supported for VX instance of virtualization."
    ::= { ospfIntfRxTxStatsEntry 7 }
 
ospfIntfRxlsReqs OBJECT-TYPE
    SYNTAX  Counter32 
    MAX-ACCESS  read-only
    STATUS  current
    DESCRIPTION
        "The total number of Link State Request packets received
         for this OSPF interface.
	Note:This mib is not supported for VX instance of virtualization."
    ::= { ospfIntfRxTxStatsEntry 8 }

ospfIntfTxlsReqs OBJECT-TYPE
    SYNTAX  Counter32 
    MAX-ACCESS  read-only
    STATUS  current
    DESCRIPTION
        "The total number of Link State Request packets transmitted
         for this OSPF interface.
	Note:This mib is not supported for VX instance of virtualization."
    ::= { ospfIntfRxTxStatsEntry 9 }

ospfIntfRxlsAcks OBJECT-TYPE
    SYNTAX  Counter32
    MAX-ACCESS  read-only
    STATUS  current
    DESCRIPTION
        "The total number of Link State Acknowledgement packets received
         for this OSPF interface.
	Note:This mib is not supported for VX instance of virtualization."
    ::= { ospfIntfRxTxStatsEntry 10 }
 
ospfIntfTxlsAcks OBJECT-TYPE
    SYNTAX  Counter32 
    MAX-ACCESS  read-only
    STATUS  current
    DESCRIPTION
        "The total number of Link State Acknowledgement packets transmitted
         for this OSPF interface.
	Note:This mib is not supported for VX instance of virtualization."
    ::= { ospfIntfRxTxStatsEntry 11 }

ospfIntfRxlsUpdates OBJECT-TYPE
    SYNTAX  Counter32
    MAX-ACCESS  read-only
    STATUS  current
    DESCRIPTION
        "The total number of Link State Update packets received for 
         this OSPF interface.
	Note:This mib is not supported for VX instance of virtualization."
    ::= { ospfIntfRxTxStatsEntry 12 }
 
ospfIntfTxlsUpdates OBJECT-TYPE
    SYNTAX  Counter32 
    MAX-ACCESS  read-only
    STATUS  current
    DESCRIPTION
        "The total number of Link State Update packets transmitted for 
         this OSPF interface.
	Note:This mib is not supported for VX instance of virtualization."
    ::= { ospfIntfRxTxStatsEntry 13 }


ospfIntfNbrChangeStats OBJECT-TYPE
    SYNTAX SEQUENCE OF OspfIntfNbrChangeStatsEntry
    MAX-ACCESS not-accessible
    STATUS current
    DESCRIPTION
      "The table of OSPF Interface Neighbour change Statistics.
	Note:This mib is not supported for VX instance of virtualization."
    ::= { ospfInterface 2 }

ospfIntfNbrChangeStatsEntry OBJECT-TYPE
    SYNTAX OspfIntfNbrChangeStatsEntry
    MAX-ACCESS not-accessible
    STATUS current
    DESCRIPTION
      "OSPF interface Neighbour Change statistics.
	Note:This mib is not supported for VX instance of virtualization."
    INDEX { ospfIntfNbrIndex }
    ::= { ospfIntfNbrChangeStats 1 }

OspfIntfNbrChangeStatsEntry ::= SEQUENCE {
    ospfIntfNbrIndex     	Integer32,
    ospfIntfNbrhello           	Counter32,
    ospfIntfNbrStart           	Counter32,
    ospfIntfNbrAdjointOk       	Counter32,
    ospfIntfNbrNegotiationDone 	Counter32,
    ospfIntfNbrExchangeDone     Counter32,
    ospfIntfNbrBadRequests      Counter32,
    ospfIntfNbrBadSequence      Counter32,
    ospfIntfNbrLoadingDone      Counter32,
    ospfIntfNbrN1way        	Counter32,
    ospfIntfNbrRstAd        	Counter32,
    ospfIntfNbrDown        	Counter32,
    ospfIntfNbrN2way        	Counter32
    }

ospfIntfNbrIndex OBJECT-TYPE
    SYNTAX  Integer32
    MAX-ACCESS  read-only
    STATUS  current
    DESCRIPTION
        "The index of the OSPF Interface for which these statistics apply.
	Note:This mib is not supported for VX instance of virtualization."
    ::= { ospfIntfNbrChangeStatsEntry 1 }

ospfIntfNbrhello OBJECT-TYPE
    SYNTAX  Counter32
    MAX-ACCESS  read-only
    STATUS  current
    DESCRIPTION
        "The total number of Hello packets received from neighbours
         in this OSPF interface.
	Note:This mib is not supported for VX instance of virtualization."
    ::= { ospfIntfNbrChangeStatsEntry 2 }

ospfIntfNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF interface.
	Note:This mib is not supported for VX instance of virtualization."
    ::= { ospfIntfNbrChangeStatsEntry  3 }

ospfIntfNbrAdjointOk OBJECT-TYPE
    SYNTAX  Counter32
    MAX-ACCESS  read-only
    STATUS  current
    DESCRIPTION
        "The total number of decisions to be made (again) as to whether
         an adjacency should be established/maintained with the neighbour.
         for this OSPF interface.
	Note:This mib is not supported for VX instance of virtualization."
    ::= { ospfIntfNbrChangeStatsEntry 4 }

ospfIntfNbrNegotiationDone OBJECT-TYPE
    SYNTAX  Counter32
    MAX-ACCESS  read-only
    STATUS  current
    DESCRIPTION
        "The total number of neighbours in this state wherein the 
         Master/slave relationship has been negotiated, and sequence
         numbers have been exchanged, for this OSPF interface.
	Note:This mib is not supported for VX instance of virtualization."
    ::= { ospfIntfNbrChangeStatsEntry 5 }

ospfIntfNbrExchangeDone OBJECT-TYPE
    SYNTAX  Counter32
    MAX-ACCESS  read-only
    STATUS  current
    DESCRIPTION
        "The total number of neighbours in this state (i.e. in an
         adjacency's final state) having transimitted a full sequence 
         of Database Description packets, for this OSPF interface.
	Note:This mib is not supported for VX instance of virtualization."
    ::= { ospfIntfNbrChangeStatsEntry 6 }

ospfIntfNbrBadRequests OBJECT-TYPE
    SYNTAX  Counter32
    MAX-ACCESS  read-only
    STATUS  current
    DESCRIPTION
        "The total number of Link State Requests which have been received
         for a link state advertisement not contained in the database for
         this interface.
	Note:This mib is not supported for VX instance of virtualization."
    ::= { ospfIntfNbrChangeStatsEntry 7 }

ospfIntfNbrBadSequence OBJECT-TYPE
    SYNTAX  Counter32
    MAX-ACCESS  read-only
    STATUS  current
    DESCRIPTION
        "The total number of Database Description packets which have been
         received that either 
         a) has an unexpected DD sequence number
         b) Unexpectedly has the init bit set
         c) Has an options field differing from the last Options field
            received in a Database Description packet.
         Any of these conditions indicate that some error has occured during
         adjacency establishment for this interface.
	Note:This mib is not supported for VX instance of virtualization."
    ::= { ospfIntfNbrChangeStatsEntry 8 }

ospfIntfNbrLoadingDone OBJECT-TYPE
    SYNTAX  Counter32
    MAX-ACCESS  read-only
    STATUS  current
    DESCRIPTION
        "The total number of link state updates received for all 
         out-of-date portions of the database for this OSPF interface.
	Note:This mib is not supported for VX instance of virtualization."
    ::= { ospfIntfNbrChangeStatsEntry 9 }

ospfIntfNbrN1way OBJECT-TYPE
    SYNTAX  Counter32
    MAX-ACCESS  read-only
    STATUS  current
    DESCRIPTION
        "The total number of Hello packets received from neighbours, in
         which this router is not mentioned for this OSPF interface.
	Note:This mib is not supported for VX instance of virtualization."
    ::= { ospfIntfNbrChangeStatsEntry 10 }

ospfIntfNbrRstAd OBJECT-TYPE
    SYNTAX  Counter32
    MAX-ACCESS  read-only
    STATUS  current
    DESCRIPTION
        "The sum total number of times the Neighbour adjacency has been reset
         on this interface.
	Note:This mib is not supported for VX instance of virtualization."
    ::= { ospfIntfNbrChangeStatsEntry 11 }

ospfIntfNbrDown OBJECT-TYPE
    SYNTAX  Counter32
    MAX-ACCESS  read-only
    STATUS  current
    DESCRIPTION
        "The total number of Neighbouring routers down (i.e. in the initial
         state of a neighbour conversation.) for this interface.
	Note:This mib is not supported for VX instance of virtualization."
    ::= { ospfIntfNbrChangeStatsEntry 12 }

ospfIntfNbrN2way OBJECT-TYPE
    SYNTAX  Counter32
    MAX-ACCESS  read-only
    STATUS  current
    DESCRIPTION
        "The total number of Hello packets received from neighbours, in
         which this router is mentioned for this OSPF interface.
	Note:This mib is not supported for VX instance of virtualization."
    ::= { ospfIntfNbrChangeStatsEntry 13 }

ospfIntfChangeStats OBJECT-TYPE
    SYNTAX SEQUENCE OF OspfIntfChangeStatsEntry
    MAX-ACCESS not-accessible
    STATUS current
    DESCRIPTION
      "The table of OSPF Interface change Statistics.
	Note:This mib is not supported for VX instance of virtualization."
    ::= { ospfInterface 3 }

ospfIntfChangeStatsEntry OBJECT-TYPE
    SYNTAX OspfIntfChangeStatsEntry
    MAX-ACCESS not-accessible
    STATUS current
    DESCRIPTION
      "OSPF interface Change statistics.
	Note:This mib is not supported for VX instance of virtualization."
    INDEX { ospfIntfIndex }
    ::= { ospfIntfChangeStats 1 }

OspfIntfChangeStatsEntry ::= SEQUENCE {
    ospfIntfIndex     	       	Integer32,
    ospfIntfHello           	Counter32,
    ospfIntfDown           	Counter32,
    ospfIntfLoop       		Counter32,
    ospfIntfUnloop 		Counter32,
    ospfIntfWaitTimer     	Counter32,
    ospfIntfBackup	        Counter32,
    ospfIntfNbrChange       	Counter32
    }

ospfIntfIndex OBJECT-TYPE
    SYNTAX  Integer32
    MAX-ACCESS  read-only
    STATUS  current
    DESCRIPTION
        "The index of the OSPF Interface for which these statistics apply.
	Note:This mib is not supported for VX instance of virtualization."
    ::= { ospfIntfChangeStatsEntry 1 }

ospfIntfHello OBJECT-TYPE
    SYNTAX    Counter32
    MAX-ACCESS    read-only
    STATUS    current
    DESCRIPTION
        "The total number of Hello packets sent by this interface.
	Note:This mib is not supported for VX instance of virtualization."
    ::= { ospfIntfChangeStatsEntry 2 }

ospfIntfDown OBJECT-TYPE
    SYNTAX   Counter32
    MAX-ACCESS   read-only
    STATUS   current
    DESCRIPTION
        "The total number of times the interface was down.
	Note:This mib is not supported for VX instance of virtualization."
    ::= { ospfIntfChangeStatsEntry 3 }

ospfIntfLoop OBJECT-TYPE
    SYNTAX    Counter32
    MAX-ACCESS    read-only
    STATUS    current
    DESCRIPTION
        "The total number of times the interface was no longer connected to 
         the attatched network.
	Note:This mib is not supported for VX instance of virtualization."
    ::= { ospfIntfChangeStatsEntry 4 }

ospfIntfUnloop OBJECT-TYPE
    SYNTAX   Counter32
    MAX-ACCESS   read-only
    STATUS   current
    DESCRIPTION
        "The total number of times the interface, connected back to
         the attatched network.
	Note:This mib is not supported for VX instance of virtualization."
    ::= { ospfIntfChangeStatsEntry 5 }

ospfIntfWaitTimer OBJECT-TYPE
    SYNTAX        Counter32
    MAX-ACCESS        read-only
    STATUS        current
    DESCRIPTION
        "The total number of times the Wait Timer has been fired,
         (indicating the end of the waiting period that is required
          before electing a (Backup) Designated Router) for this 
          OSPF interface.
	Note:This mib is not supported for VX instance of virtualization."
    ::= { ospfIntfChangeStatsEntry 6 }

ospfIntfBackup OBJECT-TYPE
    SYNTAX     Counter32
    MAX-ACCESS     read-only
    STATUS     current
    DESCRIPTION
        "The total number of Backup Designated Routers on the attatched
         network for this OSPF interface.
	Note:This mib is not supported for VX instance of virtualization."
    ::= { ospfIntfChangeStatsEntry 7 }

ospfIntfNbrChange OBJECT-TYPE
    SYNTAX     Counter32
    MAX-ACCESS     read-only
    STATUS     current
    DESCRIPTION
        "The total number of changes in the set of bidirectional neighbours
         associated with the interface for this OSPF interface.
	Note:This mib is not supported for VX instance of virtualization."
    ::= { ospfIntfChangeStatsEntry 8 }

ospfIntfErrorStats OBJECT-TYPE
    SYNTAX SEQUENCE OF OspfIntfErrorStatsEntry
    MAX-ACCESS not-accessible
    STATUS current
    DESCRIPTION
      "The table of OSPF Interface Error Statistics.
	Note:This mib is not supported for VX instance of virtualization."
    ::= { ospfInterface 4 }

ospfIntfErrorStatsEntry OBJECT-TYPE
    SYNTAX OspfIntfErrorStatsEntry
    MAX-ACCESS not-accessible
    STATUS current
    DESCRIPTION
      "Error Statistics for an OSPF area.
	Note:This mib is not supported for VX instance of virtualization."
    INDEX { ospfIntfErrIndex }
    ::= { ospfIntfErrorStats 1 }
 
OspfIntfErrorStatsEntry ::= SEQUENCE {
    ospfIntfErrIndex     	Integer32,
    ospfIntfErrAuthFailure      Counter32,
    ospfIntfErrNetmaskMismatch  Counter32,
    ospfIntfErrHelloMismatch    Counter32,
    ospfIntfErrDeadMismatch     Counter32,
    ospfIntfErrOptionsMismatch  Counter32,
    ospfIntfErrUnknownNbr       Counter32
    }

ospfIntfErrIndex OBJECT-TYPE
    SYNTAX    Integer32
    MAX-ACCESS    read-only
    STATUS    current
    DESCRIPTION
        "The index of the OSPF Intf for which these statistics apply.
	Note:This mib is not supported for VX instance of virtualization."
    ::= { ospfIntfErrorStatsEntry 1 }

ospfIntfErrAuthFailure OBJECT-TYPE
    SYNTAX    Counter32
    MAX-ACCESS    read-only
    STATUS    current
    DESCRIPTION
        "The total number of packets received with a wrong password in 
         this area.
	Note:This mib is not supported for VX instance of virtualization."
    ::= { ospfIntfErrorStatsEntry 2 }

ospfIntfErrNetmaskMismatch OBJECT-TYPE
    SYNTAX    Counter32
    MAX-ACCESS    read-only
    STATUS    current
    DESCRIPTION
        "The total number of packets received with a wrong netmask in 
         this area.
	Note:This mib is not supported for VX instance of virtualization."
    ::= { ospfIntfErrorStatsEntry 3 }

ospfIntfErrHelloMismatch OBJECT-TYPE
    SYNTAX    Counter32
    MAX-ACCESS    read-only
    STATUS    current
    DESCRIPTION
        "The total number of packets received with a different hello interval
         in this area.
	Note:This mib is not supported for VX instance of virtualization."
    ::= { ospfIntfErrorStatsEntry 4 }

ospfIntfErrDeadMismatch OBJECT-TYPE
    SYNTAX    Counter32
    MAX-ACCESS    read-only
    STATUS    current
    DESCRIPTION
        "The total number of packets received with a different dead interval
         in this area.
	Note:This mib is not supported for VX instance of virtualization."
    ::= { ospfIntfErrorStatsEntry 5 }

ospfIntfErrOptionsMismatch OBJECT-TYPE
    SYNTAX    Counter32
    MAX-ACCESS    read-only
    STATUS    current
    DESCRIPTION
        "The total number of packets received with a different options
         in this area.
	Note:This mib is not supported for VX instance of virtualization."
    ::= { ospfIntfErrorStatsEntry 6 }

ospfIntfErrUnknownNbr OBJECT-TYPE
    SYNTAX    Counter32
    MAX-ACCESS    read-only
    STATUS    current
    DESCRIPTION
        "The total number of packets received from an unknown neighbour
         in this area.
	Note:This mib is not supported for VX instance of virtualization."
    ::= { ospfIntfErrorStatsEntry 7 }

-- Ospf General Statistics contains the cumulative stats for all
-- areas / interfaces
ospfCumRxPkts OBJECT-TYPE
    SYNTAX  Counter32
    MAX-ACCESS  read-only
    STATUS  current
    DESCRIPTION
        "The sum total of all OSPF packets received on all OSPF areas
         and interfaces.
	Note:This mib is not supported for VX instance of virtualization."
    ::= { ospfCumRxTxStats 1 }
 
ospfCumTxPkts OBJECT-TYPE
    SYNTAX  Counter32
    MAX-ACCESS  read-only
    STATUS  current
    DESCRIPTION
        "The sum total of all OSPF packets transmitted on all OSPF areas
         and interfaces.
	Note:This mib is not supported for VX instance of virtualization."
    ::= { ospfCumRxTxStats 2 }
 
ospfCumRxHello OBJECT-TYPE
    SYNTAX  Counter32 
    MAX-ACCESS  read-only
    STATUS  current
    DESCRIPTION
        "The sum total of all Hello packets received on all OSPF areas
         and interfaces.
	Note:This mib is not supported for VX instance of virtualization."
    ::= { ospfCumRxTxStats 3 }

ospfCumTxHello OBJECT-TYPE
    SYNTAX  Counter32
    MAX-ACCESS  read-only
    STATUS  current
    DESCRIPTION
        "The sum total of all Hello packets transmitted on all OSPF areas
         and interfaces.
	Note:This mib is not supported for VX instance of virtualization."
    ::= { ospfCumRxTxStats 4 }
 
ospfCumRxDatabase OBJECT-TYPE
    SYNTAX  Counter32 
    MAX-ACCESS  read-only
    STATUS  current
    DESCRIPTION
        "The sum total of all Database Description packets received on
         all OSPF areas and interfaces.
	Note:This mib is not supported for VX instance of virtualization."
    ::= { ospfCumRxTxStats 5 }

ospfCumTxDatabase OBJECT-TYPE
    SYNTAX  Counter32
    MAX-ACCESS  read-only
    STATUS  current
    DESCRIPTION
        "The sum total of all Database Description packets transmitted on
         all OSPF areas and interfaces.
	Note:This mib is not supported for VX instance of virtualization."
    ::= { ospfCumRxTxStats 6 }
 
ospfCumRxlsReqs OBJECT-TYPE
    SYNTAX  Counter32 
    MAX-ACCESS  read-only
    STATUS  current
    DESCRIPTION
        "The sum total of all Link State Request packets received on
         all OSPF areas and interfaces.
	Note:This mib is not supported for VX instance of virtualization."
    ::= { ospfCumRxTxStats 7 }

ospfCumTxlsReqs OBJECT-TYPE
    SYNTAX  Counter32 
    MAX-ACCESS  read-only
    STATUS  current
    DESCRIPTION
        "The sum total of all Link State Request packets transmitted on
         all OSPF areas and interfaces.
	Note:This mib is not supported for VX instance of virtualization."
    ::= { ospfCumRxTxStats 8 }

ospfCumRxlsAcks OBJECT-TYPE
    SYNTAX  Counter32
    MAX-ACCESS  read-only
    STATUS  current
    DESCRIPTION
        "The sum total of all Link State Acknowledgement packets received
         on all OSPF areas and interfaces.
	Note:This mib is not supported for VX instance of virtualization."
    ::= { ospfCumRxTxStats 9 }
 
ospfCumTxlsAcks OBJECT-TYPE
    SYNTAX  Counter32 
    MAX-ACCESS  read-only
    STATUS  current
    DESCRIPTION
        "The sum total of all Link State Acknowledgement packets transmitted
         on all OSPF areas and interfaces.
	Note:This mib is not supported for VX instance of virtualization."
    ::= { ospfCumRxTxStats 10 }

ospfCumRxlsUpdates OBJECT-TYPE
    SYNTAX  Counter32
    MAX-ACCESS  read-only
    STATUS  current
    DESCRIPTION
        "The sum total of all Link State Update packets received
         on all OSPF areas and interfaces.
	Note:This mib is not supported for VX instance of virtualization."
    ::= { ospfCumRxTxStats 11 }
 
ospfCumTxlsUpdates OBJECT-TYPE
    SYNTAX  Counter32 
    MAX-ACCESS  read-only
    STATUS  current
    DESCRIPTION
        "The sum total of all Link State Update packets transmitted
         on all OSPF areas and interfaces.
	Note:This mib is not supported for VX instance of virtualization."
    ::= { ospfCumRxTxStats 12 }

ospfCumNbrhello OBJECT-TYPE
    SYNTAX  Counter32
    MAX-ACCESS  read-only
    STATUS  current
    DESCRIPTION
        "The sum total of all Hello packets received from neighbours
         on all OSPF areas and interfaces.
	Note:This mib is not supported for VX instance of virtualization."
    ::= { ospfCumNbrChangeStats 1 }

ospfCumNbrStart OBJECT-TYPE
    SYNTAX  Counter32
    MAX-ACCESS  read-only
    STATUS  current
    DESCRIPTION
        "The sum total number of neighbours in this state (i.e. an indication
         that  Hello packets should now be sent to the neighbour at intervals
         of HelloInterval seconds.) across all OSPF areas and interfaces.
	Note:This mib is not supported for VX instance of virtualization."
    ::= { ospfCumNbrChangeStats 2 }

ospfCumNbrAdjointOk OBJECT-TYPE
    SYNTAX  Counter32
    MAX-ACCESS  read-only
    STATUS  current
    DESCRIPTION
        "The sum total number of decisions to be made (again) as to whether
         an adjacency should be established/maintained with the neighbour
         across all OSPF areas and interfaces.
	Note:This mib is not supported for VX instance of virtualization."
    ::= { ospfCumNbrChangeStats 3 }

ospfCumNbrNegotiationDone OBJECT-TYPE
    SYNTAX  Counter32
    MAX-ACCESS  read-only
    STATUS  current
    DESCRIPTION
        "The sum total number of neighbours in this state wherein the 
         Master/slave relationship has been negotiated, and sequence
         numbers have been exchanged, across all OSPF areas and 
         interfaces.
	Note:This mib is not supported for VX instance of virtualization."
    ::= { ospfCumNbrChangeStats 4 }

ospfCumNbrExchangeDone OBJECT-TYPE
    SYNTAX  Counter32
    MAX-ACCESS  read-only
    STATUS  current
    DESCRIPTION
        "The sum total number of neighbours in this state (i.e. in an
         adjacency's final state) having transimitted a full sequence 
         of Database Description packets, across all OSPF areas
         and interfaces.
	Note:This mib is not supported for VX instance of virtualization."
    ::= { ospfCumNbrChangeStats 5 }

ospfCumNbrBadRequests OBJECT-TYPE
    SYNTAX  Counter32
    MAX-ACCESS  read-only
    STATUS  current
    DESCRIPTION
        "The sum total number of Link State Requests which have been received
         for a link state advertisement not contained in the database across
         all interfaces and OSPF areas.
	Note:This mib is not supported for VX instance of virtualization."
    ::= { ospfCumNbrChangeStats 6 }

ospfCumNbrBadSequence OBJECT-TYPE
    SYNTAX  Counter32
    MAX-ACCESS  read-only
    STATUS  current
    DESCRIPTION
        "The sum total number of Database Description packets which have been
         received that either 
         a) has an unexpected DD sequence number
         b) Unexpectedly has the init bit set
         c) Has an options field differing from the last Options field
            received in a Database Description packet.
         Any of these conditions indicate that some error has occured during
         adjacency establishment for all OSPF areas and interfaces.
	Note:This mib is not supported for VX instance of virtualization."
    ::= { ospfCumNbrChangeStats 7 }

ospfCumNbrLoadingDone OBJECT-TYPE
    SYNTAX  Counter32
    MAX-ACCESS  read-only
    STATUS  current
    DESCRIPTION
        "The sum total number of link state updates received for all 
         out-of-date portions of the database across all OSPF areas
         and interfaces.
	Note:This mib is not supported for VX instance of virtualization."
    ::= { ospfCumNbrChangeStats 8 }

ospfCumNbrN1way OBJECT-TYPE
    SYNTAX  Counter32
    MAX-ACCESS  read-only
    STATUS  current
    DESCRIPTION
        "The sum total number of Hello packets received from neighbours, in
         which this router is not mentioned across all OSPF interfaces
         and areas.
	Note:This mib is not supported for VX instance of virtualization."
    ::= { ospfCumNbrChangeStats 9 }

ospfCumNbrRstAd OBJECT-TYPE
    SYNTAX  Counter32
    MAX-ACCESS  read-only
    STATUS  current
    DESCRIPTION
        "The sum total number of times the Neighbour adjacency has been reset
         across all OPSF areas and interfaces.
	Note:This mib is not supported for VX instance of virtualization."
    ::= { ospfCumNbrChangeStats 10 }

ospfCumNbrDown OBJECT-TYPE
    SYNTAX  Counter32
    MAX-ACCESS  read-only
    STATUS  current
    DESCRIPTION
        "The total number of Neighbouring routers down (i.e. in the initial
         state of a neighbour conversation.) across all OSPF areas and 
         interfaces.
	Note:This mib is not supported for VX instance of virtualization."
    ::= { ospfCumNbrChangeStats 11 }

ospfCumNbrN2way OBJECT-TYPE
    SYNTAX  Counter32
    MAX-ACCESS  read-only
    STATUS  current
    DESCRIPTION
        "The sum total number of Hello packets received from neighbours, in
         which this router is mentioned across all OSPF interfaces
         and areas.
	Note:This mib is not supported for VX instance of virtualization."
    ::= { ospfCumNbrChangeStats 12 }

ospfCumIntfHello OBJECT-TYPE
    SYNTAX    Counter32
    MAX-ACCESS    read-only
    STATUS    current
    DESCRIPTION
        "The sum total number of Hello packets sent on all interfaces 
         and areas.
         Note:This mib is not supported for VX instance of virtualization."
    ::= { ospfCumIntfChangeStats 1 }

ospfCumIntfDown OBJECT-TYPE
    SYNTAX   Counter32
    MAX-ACCESS   read-only
    STATUS   current
    DESCRIPTION
        "The sum total number of interfaces down in all OSPF areas.
	Note:This mib is not supported for VX instance of virtualization."
    ::= { ospfCumIntfChangeStats 2 }

ospfCumIntfLoop OBJECT-TYPE
    SYNTAX    Counter32
    MAX-ACCESS    read-only
    STATUS    current
    DESCRIPTION
        "The sum total of interfaces no longer connected to 
         the attatched network across all OSPF areas and interfaces.
	Note:This mib is not supported for VX instance of virtualization."
    ::= { ospfCumIntfChangeStats 3 }

ospfCumIntfUnloop OBJECT-TYPE
    SYNTAX   Counter32
    MAX-ACCESS   read-only
    STATUS   current
    DESCRIPTION
        "The sum total number of interfaces, connected to
         the attatched network in all OSPF areas.
	Note:This mib is not supported for VX instance of virtualization."
    ::= { ospfCumIntfChangeStats 4 }

ospfCumIntfWaitTimer OBJECT-TYPE
    SYNTAX        Counter32
    MAX-ACCESS        read-only
    STATUS        current
    DESCRIPTION
        "The sum total number of times the Wait Timer has been fired,
         (indicating the end of the waiting period that is required
          before electing a (Backup) Designated Router) across all 
          OSPF areas and interfaces.
	Note:This mib is not supported for VX instance of virtualization."
    ::= { ospfCumIntfChangeStats 5 }

ospfCumIntfBackup OBJECT-TYPE
    SYNTAX     Counter32
    MAX-ACCESS     read-only
    STATUS     current
    DESCRIPTION
        "The sum total number of Backup Designated Routers on the attatched
         network for all OSPF areas and interfaces.
	Note:This mib is not supported for VX instance of virtualization."
    ::= { ospfCumIntfChangeStats 6 }

ospfCumIntfNbrChange OBJECT-TYPE
    SYNTAX     Counter32
    MAX-ACCESS     read-only
    STATUS     current
    DESCRIPTION
        "The sum total number of changes in the set of bidirectional
         neighbours associated with any interface across all OSPF areas.
	Note:This mib is not supported for VX instance of virtualization."
    ::= { ospfCumIntfChangeStats 7 }

ospfTmrsKckOffHello OBJECT-TYPE
    SYNTAX    Counter32
    MAX-ACCESS    read-only
    STATUS    current
    DESCRIPTION
        "The sum total number of times the Hello timer has been fired
         (which triggers the send of a Hello packet) across all OPSF 
         areas and interfaces.
	Note:This mib is not supported for VX instance of virtualization."
    ::= { ospfTimersKickOffStats 1 }

ospfTmrsKckOffRetransmit OBJECT-TYPE
    SYNTAX   Counter32
    MAX-ACCESS   read-only
    STATUS   current
    DESCRIPTION
        "The sum total number of times the Retransmit timer has been
         fired across all OPSF areas and interfaces.
	Note:This mib is not supported for VX instance of virtualization."
    ::= { ospfTimersKickOffStats 2 }

ospfTmrsKckOffLsaLock OBJECT-TYPE
    SYNTAX    Counter32
    MAX-ACCESS    read-only
    STATUS    current
    DESCRIPTION
        "The sum total number of times the Lsa Lock timer has been 
         fired across all OSPF areas and interfaces.
	Note:This mib is not supported for VX instance of virtualization."
    ::= { ospfTimersKickOffStats 3 }

ospfTmrsKckOffLsaAck OBJECT-TYPE
    SYNTAX   Counter32
    MAX-ACCESS   read-only
    STATUS   current
    DESCRIPTION
        "The sum total number of times the Lsa Ack timer has been 
         fired across all ospf areas and interfaces.
	Note:This mib is not supported for VX instance of virtualization."
    ::= { ospfTimersKickOffStats 4 }

ospfTmrsKckOffDbage OBJECT-TYPE
    SYNTAX        Counter32
    MAX-ACCESS        read-only
    STATUS        current
    DESCRIPTION
        "The total number of times the Dbage has been fired.
	Note:This mib is not supported for VX instance of virtualization."
    ::= { ospfTimersKickOffStats 5 }

ospfTmrsKckOffSummary OBJECT-TYPE
    SYNTAX     Counter32
    MAX-ACCESS     read-only
    STATUS     current
    DESCRIPTION
        "The total number of times the Summary timer has been fired.
	Note:This mib is not supported for VX instance of virtualization."
    ::= { ospfTimersKickOffStats 6 }

ospfTmrsKckOffAseExport OBJECT-TYPE
    SYNTAX     Counter32
    MAX-ACCESS     read-only
    STATUS     current
    DESCRIPTION
        "The total number of times the ASE Export timer has been fired.
	Note:This mib is not supported for VX instance of virtualization."
    ::= { ospfTimersKickOffStats 7 }


-- Ospfv3 Statistics

-- Ospf Statistics for all interfaces and OSPF areas
ospfv3GeneralStats       OBJECT IDENTIFIER ::= { ospfv3Stats  1 }

ospfv3StatsPackSent OBJECT-TYPE
    SYNTAX  Integer32
    MAX-ACCESS  read-only
    STATUS  current
    DESCRIPTION
        "No of packets sent.
	Note:This mib is not supported for VX instance of virtualization."
    ::= { ospfv3GeneralStats 1 }

ospfv3PacketRx OBJECT-TYPE
    SYNTAX Integer32
    MAX-ACCESS  read-only
    STATUS  current
    DESCRIPTION
        "PacketRx stats.
	Note:This mib is not supported for VX instance of virtualization."
    ::= { ospfv3GeneralStats 2 }

ospfv3RxPacketDrop OBJECT-TYPE
    SYNTAX Integer32
    MAX-ACCESS  read-only
    STATUS  current
    DESCRIPTION
        "Num_rx_drop_packet.
	Note:This mib is not supported for VX instance of virtualization."
    ::= { ospfv3GeneralStats 3 }

ospfv3TxPacketDrop OBJECT-TYPE
    SYNTAX Integer32
    MAX-ACCESS  read-only
    STATUS  current
    DESCRIPTION
        "Ospfv3 Num_Tx_drop_packet.
	Note:This mib is not supported for VX instance of virtualization."
    ::= { ospfv3GeneralStats 4 }

ospfv3RxBadPacket OBJECT-TYPE
    SYNTAX  Integer32
    MAX-ACCESS  read-only
    STATUS  current
    DESCRIPTION
        "Ospfv3 num_rx_bad_packet.
	Note:This mib is not supported for VX instance of virtualization."
    ::= { ospfv3GeneralStats 5 }

ospfv3SpfRunCount OBJECT-TYPE
    SYNTAX  Integer32
    MAX-ACCESS  read-only
    STATUS  current
    DESCRIPTION
        "SPF stats.
	Note:This mib is not supported for VX instance of virtualization."
    ::= { ospfv3GeneralStats 6 }

ospfv3LastSpfRun OBJECT-TYPE
    SYNTAX  Integer32
    MAX-ACCESS  read-only
    STATUS  current
    DESCRIPTION
        "SPF stats for ospfv3.
	Note:This mib is not supported for VX instance of virtualization."
    ::= { ospfv3GeneralStats 7 }

ospfv3LSDBtableSize OBJECT-TYPE
    SYNTAX  Integer32
    MAX-ACCESS  read-only
    STATUS  current
    DESCRIPTION
        "LSDB size for ospfv3.
	Note:This mib is not supported for VX instance of virtualization."
    ::= { ospfv3GeneralStats 8 }

ospfv3BadLSReqCnt OBJECT-TYPE
    SYNTAX  Integer32
    MAX-ACCESS  read-only
    STATUS  current
    DESCRIPTION
        "Bad LS req stats for ospfv3.
	Note:This mib is not supported for VX instance of virtualization."
    ::= { ospfv3GeneralStats 9 }

ospfv3SeqMismatchCnt OBJECT-TYPE
    SYNTAX  Integer32
    MAX-ACCESS  read-only
    STATUS  current
    DESCRIPTION
        "Seq mismatch stats for ospfv3.
	Note:This mib is not supported for VX instance of virtualization."
    ::= { ospfv3GeneralStats 10 }



-- VRRP6 Stats

vrrp6StatInAdvers OBJECT-TYPE
    SYNTAX  Counter32
    MAX-ACCESS  read-only
    STATUS  current
    DESCRIPTION
        "The number of good VRRP6 advertisements which are received.
	Note:This mib is not supported for VX instance of virtualization."
    ::= { vrrp6Stats 1 }

vrrp6StatOutAdvers OBJECT-TYPE
    SYNTAX  Counter32
    MAX-ACCESS  read-only
    STATUS  current
    DESCRIPTION
        "The number of good VRRP6 advertisements which are transmitted.
	Note:This mib is not supported for VX instance of virtualization."
    ::= { vrrp6Stats 2 }

vrrp6StatOutBadAdvers OBJECT-TYPE
    SYNTAX  Counter32
    MAX-ACCESS  read-only
    STATUS  current
    DESCRIPTION
        "The number of bad VRRP6 advertisements which are received.
	Note:This mib is not supported for VX instance of virtualization."
    ::= { vrrp6Stats 3 }

vrrp6StatBadVersion OBJECT-TYPE
    SYNTAX  Counter32
    MAX-ACCESS  read-only
    STATUS  current
    DESCRIPTION
        "The number of bad VRRP6 version which are received.
	Note:This mib is not supported for VX instance of virtualization."
    ::= { vrrp6Stats 4 }

vrrp6StatBadVrid OBJECT-TYPE
    SYNTAX  Counter32
    MAX-ACCESS  read-only
    STATUS  current
    DESCRIPTION
        "The number of bad VRRP6 VR id which are received.
	Note:This mib is not supported for VX instance of virtualization."
    ::= { vrrp6Stats 5 }

vrrp6StatBadAddress OBJECT-TYPE
    SYNTAX  Counter32
    MAX-ACCESS  read-only
    STATUS  current
    DESCRIPTION
        "The number of bad VRRP6 address which are received.
	Note:This mib is not supported for VX instance of virtualization."
    ::= { vrrp6Stats 6 }

vrrp6StatBadData OBJECT-TYPE
    SYNTAX  Counter32
    MAX-ACCESS  read-only
    STATUS  current
    DESCRIPTION
        "The number of bad VRRP7 data which are received.
	Note:This mib is not supported for VX instance of virtualization."
    ::= { vrrp6Stats 7 }

vrrp6StatBadInterval OBJECT-TYPE
    SYNTAX  Counter32
    MAX-ACCESS  read-only
    STATUS  current
    DESCRIPTION
        "The number of bad VRRP6 Interval which are received.
	Note:This mib is not supported for VX instance of virtualization."
    ::= { vrrp6Stats 8 }

vrrp6StatBadHaid OBJECT-TYPE
   SYNTAX  Counter32
    MAX-ACCESS  read-only
    STATUS  current
    DESCRIPTION
        "The number of bad VRRP6 Haid which are received.
	Note:This mib is not supported for VX instance of virtualization."
    ::= { vrrp6Stats 9 }

-- End of VRRP6 stats

-- IP Tunnel stats
ipTunnelStatTable OBJECT-TYPE
    SYNTAX  SEQUENCE OF IpTunnelStatEntry
    MAX-ACCESS  not-accessible
    STATUS  current
    DESCRIPTION
        "The IP Tunnel statistics table.
        Note:This mib is not supported for VX instance of virtualization."
    ::= { ipTunnelStats 1 }

ipTunnelStatEntry OBJECT-TYPE
  SYNTAX  IpTunnelStatEntry 
  MAX-ACCESS  not-accessible
  STATUS  current
  DESCRIPTION
          "The statistics of IP Tunnel entry.
          Note:This mib is not supported for VX instance of virtualization."
  INDEX   { ipTunnelStatId } ::= { ipTunnelStatTable 1 }

IpTunnelStatEntry ::= SEQUENCE {
  ipTunnelStatId              DisplayString,
  ipTunnelStatIndex           Integer32,
  ipTunnelStatState           INTEGER,
  ipTunnelStatType            INTEGER,
  ipTunnelStatDescription     DisplayString,
  ipTunnelStatCurrSess        Gauge32,
  ipTunnelStatTotSess         Gauge32,
  ipTunnelStatHighSess        Gauge32,
  ipTunnelStatOctets          Counter64
}

ipTunnelStatId OBJECT-TYPE
    SYNTAX  DisplayString (SIZE(0..31))
    MAX-ACCESS  read-only
    STATUS  current
    DESCRIPTION
        "The IP tunnel number for which the information is related.
        Note:This mib is not supported for VX instance of virtualization."
    ::= { ipTunnelStatEntry 1 }

ipTunnelStatIndex OBJECT-TYPE
    SYNTAX  Integer32
    MAX-ACCESS  read-only
    STATUS  current
    DESCRIPTION
        "The tunnel local index.
        Note:This mib is not supported for VX instance of virtualization."
    ::= { ipTunnelStatEntry 2 }

ipTunnelStatState OBJECT-TYPE
    SYNTAX  INTEGER {
                enabled(2),
                disabled(3),
                unsupported(2147483647)
  }
  MAX-ACCESS  read-only
  STATUS  current
  DESCRIPTION
        "Enable or Disable the IP tunnel interface.
        Note:This mib is not supported for VX instance of virtualization."
    ::= { ipTunnelStatEntry 3 }

ipTunnelStatType OBJECT-TYPE
  SYNTAX  INTEGER {
          disabled(1),
--        vxlan(2),
          ipinip(3),
          gre(4),
          unsupported(2147483647)
  }
    MAX-ACCESS read-only
    STATUS  current
    DESCRIPTION
        "The type of IP tunnel interface.
        Note:This mib is not supported for VX instance of virtualization."
    ::= { ipTunnelStatEntry 4 }

ipTunnelStatDescription OBJECT-TYPE
    SYNTAX  DisplayString (SIZE(1..32))
    MAX-ACCESS read-only
    STATUS  current
    DESCRIPTION
        "The descriptive tunnel name.
        Note:This mib is not supported for VX instance of virtualization."
    ::= { ipTunnelStatEntry 5 }

ipTunnelStatCurrSess OBJECT-TYPE
    SYNTAX  Gauge32
    MAX-ACCESS  read-only
    STATUS  current
    DESCRIPTION
        "The number of sessions that are currently handled by IP Tunnel entry.
        Note:This mib is not supported for VX instance of virtualization."
    ::= { ipTunnelStatEntry 6 }

ipTunnelStatTotSess OBJECT-TYPE
    SYNTAX  Gauge32
    MAX-ACCESS  read-only
    STATUS  current
    DESCRIPTION
        "Total number of sessions that are handled by this IP Tunnel entry.
        Note:This mib is not supported for VX instance of virtualization."
    ::= { ipTunnelStatEntry 7 }

ipTunnelStatHighSess OBJECT-TYPE
    SYNTAX  Gauge32
    MAX-ACCESS  read-only
    STATUS  current
    DESCRIPTION
        "The highest number of sessions that are handled by this IP Tunnel entry.
        Note:This mib is not supported for VX instance of virtualization."
    ::= { ipTunnelStatEntry 8 }

ipTunnelStatOctets OBJECT-TYPE
    SYNTAX  Counter64
    MAX-ACCESS  read-only
    STATUS  current
    DESCRIPTION
        "The total octets that are handled by this IP Tunnel entry.
        Note:This mib is not supported for VX instance of virtualization."
    ::= { ipTunnelStatEntry 9}

-- End of IP Tunnel stats


ip6InReceives OBJECT-TYPE
    SYNTAX  Counter32
    MAX-ACCESS  read-only
    STATUS  current
    DESCRIPTION
        "The total number of input datagrams received from
         interfaces, including those received in error.
	Note:This mib is not supported for VX instance of virtualization."
    ::= { ip6Stats 1 }

ip6ForwDatagrams OBJECT-TYPE
    SYNTAX  Counter32
    MAX-ACCESS  read-only
    STATUS  current
    DESCRIPTION
        "The number of input datagrams for which this entity was not
         their final IP destination, as a result of which an attempt
         was made to find a route to forward them to that final
         destination.
	Note:This mib is not supported for VX instance of virtualization."
    ::= { ip6Stats 2 }

ip6InDelivers OBJECT-TYPE
    SYNTAX  Counter32
    MAX-ACCESS  read-only
    STATUS  current
    DESCRIPTION
        "The total number of input datagrams successfully
         delivered to IP user-protocols (including ICMP).
	Note:This mib is not supported for VX instance of virtualization."
    ::= { ip6Stats 3 }

ip6InDiscards OBJECT-TYPE
    SYNTAX  Counter32
    MAX-ACCESS  read-only
    STATUS  current
    DESCRIPTION
        "The number of input IP datagrams for which no problems were
         encountered to prevent their continued processing, but which were
         discarded (e.g., for lack of buffer space).  Note that this counter
         does not include any datagrams discarded while awaiting re-assembly.
	Note:This mib is not supported for VX instance of virtualization."
         ::= { ip6Stats 4 }

ip6InUnknownProtos OBJECT-TYPE
    SYNTAX  Counter32
    MAX-ACCESS  read-only
    STATUS  current
    DESCRIPTION
        "The number of locally-addressed datagrams received successfully
         but discarded because of an unknown or unsupported protocol.
	Note:This mib is not supported for VX instance of virtualization."
    ::= { ip6Stats 5 }

ip6InAddrErrors OBJECT-TYPE
    SYNTAX  Counter32
    MAX-ACCESS  read-only
    STATUS  current
    DESCRIPTION
        "The number of input datagrams discarded because the IP address
         in their IP header's destination field was not a valid address
         to be received at this entity.
	Note:This mib is not supported for VX instance of virtualization."
    ::= { ip6Stats 6 }

ip6OutRequests OBJECT-TYPE
    SYNTAX  Counter32
    MAX-ACCESS  read-only
    STATUS  current
    DESCRIPTION
        "The total number of IP datagrams which local IP
         user-protocols (including ICMP) supplied to IP in
         requests for transmission.  Note that this counter does not
         include any datagrams counted in ipForwDatagrams.
	Note:This mib is not supported for VX instance of virtualization."
    ::= { ip6Stats 7 }

ip6OutNoRoutes OBJECT-TYPE
    SYNTAX  Counter32
    MAX-ACCESS  read-only
    STATUS  current
    DESCRIPTION
        "The number of IP datagrams discarded because no route 
        could be found to transmit them to their destination.
        Note that this Counter32 includes any packets counted in 
        ipForwDatagrams which meet this`no-route' criterion. 
        Note that this includes any datagrams which a host cannot 
        route because all of its default gateways are down.
	Note:This mib is not supported for VX instance of virtualization."
    ::= { ip6Stats 8 }

ip6ReasmOKs OBJECT-TYPE
    SYNTAX  Counter32
    MAX-ACCESS  read-only
    STATUS  current
    DESCRIPTION
        "The number of IP datagrams successfully re-assembled.
	Note:This mib is not supported for VX instance of virtualization."
    ::= { ip6Stats 9 }

ip6ReasmFails OBJECT-TYPE
    SYNTAX  Counter32
    MAX-ACCESS  read-only
    STATUS  current
    DESCRIPTION
        "The number of failures detected by the IP re-assembly.
	Note:This mib is not supported for VX instance of virtualization."
    ::= { ip6Stats 10 }

ip6icmpInMsgs OBJECT-TYPE
    SYNTAX  Counter32
    MAX-ACCESS  read-only
    STATUS  current
    DESCRIPTION
        "The total number of ICMP messages received.  
         Note that this Counter32 includes all those counted by 
         icmpInErrors.
	Note:This mib is not supported for VX instance of virtualization."
    ::= { ip6Stats 11 }

ip6icmpOutMsgs OBJECT-TYPE
    SYNTAX  Counter32
    MAX-ACCESS  read-only
    STATUS  current
    DESCRIPTION
        "The total number of ICMP messages attempted to send.  Note that 
         this Counter32 includes all those counted by icmp6OutErrors.
	Note:This mib is not supported for VX instance of virtualization."
    ::= { ip6Stats 12}

ip6icmpInErrors OBJECT-TYPE
    SYNTAX  Counter32
    MAX-ACCESS  read-only
    STATUS  current
    DESCRIPTION
        "The number of ICMP messages received but determined as having 
         ICMP-specific errors (bad ICMP checksums, bad length, etc.).
	Note:This mib is not supported for VX instance of virtualization."
    ::= { ip6Stats 13 }

ip6icmpOutErrors OBJECT-TYPE
    SYNTAX  Counter32
    MAX-ACCESS  read-only
    STATUS  current
    DESCRIPTION
        "The number of ICMP messages did not send due to problems 
         discovered within ICMP such as a lack of buffers.
	Note:This mib is not supported for VX instance of virtualization."
    ::= { ip6Stats 14}

icmp6StatsTable  OBJECT-TYPE
    SYNTAX SEQUENCE OF Icmp6StatsEntry
    MAX-ACCESS not-accessible
    STATUS current
    DESCRIPTION
        "Statistics for ICMP6.
	Note:This mib is not supported for VX instance of virtualization."
    ::= { icmp6Stats 1 }

icmp6StatsEntry  OBJECT-TYPE
    SYNTAX  Icmp6StatsEntry 
    MAX-ACCESS not-accessible
    STATUS current
    DESCRIPTION
      "Statistics for IGMP Snooping.
	Note:This mib is not supported for VX instance of virtualization."
    INDEX { icmp6StatsIndx}
    ::= { icmp6StatsTable 1 }
 
Icmp6StatsEntry ::= SEQUENCE {
    icmp6StatsIndx         Integer32,
    icmp6IntfIndex         Integer32,
    icmp6InMsgs            Counter32,
    icmp6InErrors          Counter32,
    icmp6InEchos           Counter32,
    icmp6InEchoReps        Counter32,
    icmp6InNSs             Counter32,
    icmp6InNAs             Counter32,
    icmp6InRSs             Counter32,
    icmp6InRAs             Counter32,
    icmp6InDestUnreachs    Counter32,
    icmp6InTimeExcds       Counter32,
    icmp6InTooBigs         Counter32,
    icmp6InParmProbs       Counter32,
    icmp6InRedirects       Counter32,
    icmp6OutMsgs           Counter32,
    icmp6OutErrors         Counter32,
    icmp6OutEchos          Counter32,
    icmp6OutEchoReps       Counter32,
    icmp6OutNSs            Counter32,
    icmp6OutNAs            Counter32,
    icmp6OutRSs            Counter32,
    icmp6OutRAs            Counter32,
    icmp6OutRedirects      Counter32    
    }

icmp6StatsIndx   OBJECT-TYPE
    SYNTAX    Integer32
    MAX-ACCESS    read-only
    STATUS    current
    DESCRIPTION
        "The index of this statistics table.
	Note:This mib is not supported for VX instance of virtualization."
    ::= { icmp6StatsEntry 1 }

icmp6IntfIndex   OBJECT-TYPE
    SYNTAX    Integer32 
    MAX-ACCESS    read-only
    STATUS    current
    DESCRIPTION
        "IP interface index in interface configuration table.
	Note:This mib is not supported for VX instance of virtualization."
    ::= { icmp6StatsEntry 2 }

icmp6InMsgs OBJECT-TYPE
    SYNTAX  Counter32
    MAX-ACCESS  read-only
    STATUS  current
    DESCRIPTION
        "The total number of ICMP messages received.  Note that this 
         Counter32 includes all those counted by icmpInErrors.
	Note:This mib is not supported for VX instance of virtualization."
    ::= { icmp6StatsEntry 3 }

icmp6InErrors OBJECT-TYPE
    SYNTAX  Counter32
    MAX-ACCESS  read-only
    STATUS  current
    DESCRIPTION
        "The number of ICMP messages received but determined as having 
         ICMP-specific errors (bad ICMP checksums, bad length, etc.).
	Note:This mib is not supported for VX instance of virtualization."
    ::= { icmp6StatsEntry 4 }

icmp6InEchos OBJECT-TYPE
    SYNTAX  Counter32
    MAX-ACCESS  read-only
    STATUS  current
    DESCRIPTION
        "The number of ICMP Echo request messages received.
	Note:This mib is not supported for VX instance of virtualization."
    ::= { icmp6StatsEntry 5 }

icmp6InEchoReps OBJECT-TYPE
    SYNTAX  Counter32
    MAX-ACCESS  read-only
    STATUS  current
    DESCRIPTION
        "The number of ICMP Echo Reply messages received.
	Note:This mib is not supported for VX instance of virtualization."
    ::= { icmp6StatsEntry 6 }

icmp6InNSs OBJECT-TYPE
    SYNTAX  Counter32
    MAX-ACCESS  read-only
    STATUS  current
    DESCRIPTION
        "The number of neighbour solicitations received.
	Note:This mib is not supported for VX instance of virtualization."
    ::= { icmp6StatsEntry 7 }

icmp6InNAs OBJECT-TYPE
    SYNTAX  Counter32
    MAX-ACCESS  read-only
    STATUS  current
    DESCRIPTION
        "The number of neighbour advertisements received.
	Note:This mib is not supported for VX instance of virtualization."
    ::= { icmp6StatsEntry 8 }

icmp6InRSs OBJECT-TYPE
    SYNTAX  Counter32
    MAX-ACCESS  read-only
    STATUS  current
    DESCRIPTION
        "The number of router solicitations received.
	Note:This mib is not supported for VX instance of virtualization."
    ::= { icmp6StatsEntry 9 }

icmp6InRAs OBJECT-TYPE
    SYNTAX  Counter32
    MAX-ACCESS  read-only
    STATUS  current
    DESCRIPTION
        "The number of router advertisements received.
	Note:This mib is not supported for VX instance of virtualization."
    ::= { icmp6StatsEntry 10 }

icmp6InDestUnreachs OBJECT-TYPE
    SYNTAX  Counter32
    MAX-ACCESS  read-only
    STATUS  current 
    DESCRIPTION
        "The number of ICMP Destination Unreachable messages received.
	Note:This mib is not supported for VX instance of virtualization."
    ::= { icmp6StatsEntry 11 }

icmp6InTimeExcds OBJECT-TYPE
    SYNTAX  Counter32
    MAX-ACCESS  read-only
    STATUS  current 
    DESCRIPTION
        "The number of ICMP Time Exceeded messages received.
	Note:This mib is not supported for VX instance of virtualization."
    ::= { icmp6StatsEntry 12 }

icmp6InTooBigs  OBJECT-TYPE
    SYNTAX  Counter32
    MAX-ACCESS  read-only
    STATUS  current
    DESCRIPTION
        "The number of ICMP too big messages received.
	Note:This mib is not supported for VX instance of virtualization."
    ::= { icmp6StatsEntry 13 }

icmp6InParmProbs OBJECT-TYPE
    SYNTAX  Counter32
    MAX-ACCESS  read-only
    STATUS  current
    DESCRIPTION
        "The number of ICMP Parameter Problem messages received.
	Note:This mib is not supported for VX instance of virtualization."
    ::= { icmp6StatsEntry 14 }

icmp6InRedirects OBJECT-TYPE
    SYNTAX  Counter32
    MAX-ACCESS  read-only
    STATUS  current
    DESCRIPTION
        "The number of ICMP Redirect messages received.
	Note:This mib is not supported for VX instance of virtualization."
    ::= { icmp6StatsEntry 15 }

icmp6OutMsgs OBJECT-TYPE
    SYNTAX  Counter32
    MAX-ACCESS  read-only
    STATUS  current
    DESCRIPTION
        "The total number of ICMP messages which this entity 
         attempted to send.  Note that this Counter32 includes 
         all those counted by icmp6OutErrors.
	Note:This mib is not supported for VX instance of virtualization."
    ::= { icmp6StatsEntry 16 }

icmp6OutErrors OBJECT-TYPE
    SYNTAX  Counter32
    MAX-ACCESS  read-only
    STATUS  current
    DESCRIPTION
        "The number of ICMP messages which this entity did not 
         send due to problems discovered within ICMP
         such as a lack of buffers.
	Note:This mib is not supported for VX instance of virtualization."
    ::= { icmp6StatsEntry 17 }

icmp6OutEchos OBJECT-TYPE
    SYNTAX  Counter32
    MAX-ACCESS  read-only
    STATUS  current
    DESCRIPTION
        "The number of ICMP Echo request messages sent.
	Note:This mib is not supported for VX instance of virtualization."
    ::= { icmp6StatsEntry 18 }

icmp6OutEchoReps OBJECT-TYPE
    SYNTAX  Counter32
    MAX-ACCESS  read-only
    STATUS  current
    DESCRIPTION
        "The number of ICMP Echo Reply messages sent.
	Note:This mib is not supported for VX instance of virtualization."
    ::= { icmp6StatsEntry 19 }

icmp6OutNSs OBJECT-TYPE
    SYNTAX  Counter32
    MAX-ACCESS  read-only
    STATUS  current
    DESCRIPTION
        "The number of neighbour solicitations sent.
	Note:This mib is not supported for VX instance of virtualization."
    ::= { icmp6StatsEntry 20 }

icmp6OutNAs OBJECT-TYPE
    SYNTAX  Counter32
    MAX-ACCESS  read-only
    STATUS  current
    DESCRIPTION
        "The number of neighbour advertisements sent.
	Note:This mib is not supported for VX instance of virtualization."
    ::= { icmp6StatsEntry 21 }

icmp6OutRSs OBJECT-TYPE
    SYNTAX  Counter32
    MAX-ACCESS  read-only
    STATUS  current
    DESCRIPTION
        "The number of router solicitations sent.
	Note:This mib is not supported for VX instance of virtualization."
    ::= { icmp6StatsEntry 22 }

icmp6OutRAs OBJECT-TYPE
    SYNTAX  Counter32
    MAX-ACCESS  read-only
    STATUS  current
    DESCRIPTION
        "The number of router advertisements sent.
	Note:This mib is not supported for VX instance of virtualization."
    ::= { icmp6StatsEntry 23 }

icmp6OutRedirects OBJECT-TYPE
    SYNTAX  Counter32
    MAX-ACCESS  read-only
    STATUS  current
    DESCRIPTION
        "The number of ICMP Redirect messages sent.  For a host, this 
         object will always be zero, since hosts do not send redirects.
	Note:This mib is not supported for VX instance of virtualization."
    ::= { icmp6StatsEntry 24 }

ip6GwStatsTable OBJECT-TYPE
    SYNTAX SEQUENCE OF Ip6GwStatsEntry
    MAX-ACCESS not-accessible
    STATUS current
    DESCRIPTION
        "Statistics for IP6 Gateway.
	Note:This mib is not supported for VX instance of virtualization."
    ::= { ip6gwStats 1 }

ip6GwStatsEntry OBJECT-TYPE
    SYNTAX Ip6GwStatsEntry
    MAX-ACCESS not-accessible
    STATUS current
    DESCRIPTION
      "Statistics for IP6 Gateway.
	Note:This mib is not supported for VX instance of virtualization."
    INDEX { ip6GwStatsIndex}
    ::= { ip6GwStatsTable 1 }
 
Ip6GwStatsEntry ::= SEQUENCE {
    ip6GwStatsIndex       Integer32,
    ip6GwIndex            Integer32,
    ip6GwEchoreq          Counter32,
    ip6GwEchoresp         Counter32,
    ip6GwFails            Counter32,
    ip6GwMaster           Integer32,
    ip6IfIndex            Integer32,
    ip6GwRetry            Counter32
}

ip6GwStatsIndex  OBJECT-TYPE
    SYNTAX Integer32
    MAX-ACCESS  read-only
    STATUS  current
    DESCRIPTION
        "The index of Gw6 statistics.
	Note:This mib is not supported for VX instance of virtualization."
    ::= { ip6GwStatsEntry 1}

ip6GwIndex  OBJECT-TYPE
    SYNTAX Integer32 
    MAX-ACCESS  read-only
    STATUS  current
    DESCRIPTION
        "Gateway index in gateway configuration table.
	Note:This mib is not supported for VX instance of virtualization."
    ::= { ip6GwStatsEntry 2}

ip6GwEchoreq  OBJECT-TYPE
    SYNTAX    Counter32 
    MAX-ACCESS    read-only
    STATUS    current
    DESCRIPTION
        "The number of GW Echo request messages .
	Note:This mib is not supported for VX instance of virtualization."
    ::= { ip6GwStatsEntry 3 }

ip6GwEchoresp  OBJECT-TYPE
    SYNTAX   Counter32 
    MAX-ACCESS    read-only
    STATUS    current
    DESCRIPTION
        "The number of GW Echo response messages .
	Note:This mib is not supported for VX instance of virtualization."
    ::= { ip6GwStatsEntry 4 }

ip6GwFails  OBJECT-TYPE 
    SYNTAX   Counter32
    MAX-ACCESS    read-only
    STATUS    current
    DESCRIPTION
        "The number of GWs fails.
	Note:This mib is not supported for VX instance of virtualization."
    ::= { ip6GwStatsEntry 5 }

ip6GwMaster  OBJECT-TYPE
    SYNTAX  Integer32
    MAX-ACCESS    read-only
    STATUS    current
    DESCRIPTION
        "The master gateway.
	Note:This mib is not supported for VX instance of virtualization."
    ::= { ip6GwStatsEntry 6 }

ip6IfIndex  OBJECT-TYPE
    SYNTAX  Integer32
    MAX-ACCESS    read-only
    STATUS    current
    DESCRIPTION
        "The IP6 interface.
	Note:This mib is not supported for VX instance of virtualization."
    ::= { ip6GwStatsEntry 7 }

ip6GwRetry OBJECT-TYPE
    SYNTAX Counter32 
    MAX-ACCESS    read-only
    STATUS    current
    DESCRIPTION
        "The number of retries.
	Note:This mib is not supported for VX instance of virtualization."
    ::= { ip6GwStatsEntry 8 }


-- Information - Run-time IP Route Table 


ipIntfInfoTable OBJECT-TYPE
    SYNTAX  SEQUENCE OF IntfInfoEntry
    MAX-ACCESS not-accessible
    STATUS current 
    DESCRIPTION
        "The table of IP interface information.
	Note:This mib is not supported for VX instance of virtualization."
    ::= {ipIntfInfo 1 }

intfInfoEntry OBJECT-TYPE
    SYNTAX  IntfInfoEntry 
    MAX-ACCESS not-accessible
    STATUS  current 
    DESCRIPTION
        "A row in IP interface information table.
	Note:This mib is not supported for VX instance of virtualization."
    INDEX   { intfInfoIndex }
    ::= { ipIntfInfoTable 1 }

IntfInfoEntry ::= SEQUENCE {
    intfInfoIndex        Integer32,
    intfInfoIpver         INTEGER,
    intfInfoAddr          DisplayString,
    intfInfoNetMask       DisplayString,
    intfInfoBcastAddr     DisplayString,
    intfInfoVlan          Integer32,
    intfInfoLinkLocalAddr DisplayString,
    intfInfoStatus        INTEGER,
    intfInfoBfd           INTEGER
    }

intfInfoIndex OBJECT-TYPE
    SYNTAX  Integer32
    MAX-ACCESS  read-only
    STATUS  current
    DESCRIPTION
	"The interface number for which the information is related.
	Note:This mib is not supported for VX instance of virtualization."
    ::= { intfInfoEntry 1}


intfInfoIpver  OBJECT-TYPE
    SYNTAX   INTEGER {
        ipv4(1),
        ipv6(2),
        unsupported(2147483647)
    } 
    MAX-ACCESS  read-only
    STATUS  current
    DESCRIPTION
        "The type of IP address.
	Note:This mib is not supported for VX instance of virtualization."
    ::= { intfInfoEntry 2 }


intfInfoAddr  OBJECT-TYPE
    SYNTAX   DisplayString 
    MAX-ACCESS  read-only
    STATUS  current
    DESCRIPTION
	"The IP address of the interface.
	Note:This mib is not supported for VX instance of virtualization."
    ::= { intfInfoEntry 3 }

intfInfoNetMask OBJECT-TYPE
    SYNTAX   DisplayString 
    MAX-ACCESS  read-only
    STATUS  current
    DESCRIPTION
        "The subnet mask of the interface.
	Note:This mib is not supported for VX instance of virtualization."
    ::= { intfInfoEntry 4 }

intfInfoBcastAddr OBJECT-TYPE
    SYNTAX   DisplayString 
    MAX-ACCESS  read-only
    STATUS  current
    DESCRIPTION
        "The broadcast address of the interface.
	Note:This mib is not supported for VX instance of virtualization."
    ::= { intfInfoEntry 5 }

intfInfoVlan OBJECT-TYPE
    SYNTAX  Integer32
    MAX-ACCESS  read-only
    STATUS  current
    DESCRIPTION
        "The VLAN number for this interface.
	Note:This mib is not supported for VX instance of virtualization."
    ::= { intfInfoEntry 6 }

intfInfoStatus OBJECT-TYPE
    SYNTAX  INTEGER {
	up(1),
	down(2),
        disabled(3),
        unsupported(2147483647)
    }  
    MAX-ACCESS  read-only
    STATUS  current
    DESCRIPTION
	"The status of the interface.
	Note:This mib is not supported for VX instance of virtualization."
    ::= { intfInfoEntry 7 }


intfInfoLinkLocalAddr OBJECT-TYPE
    SYNTAX   DisplayString
    MAX-ACCESS  read-only
    STATUS  current
    DESCRIPTION
        "The site local address of the interface.
	Note:This mib is not supported for VX instance of virtualization."
    ::= { intfInfoEntry 8 }

intfInfoBfd OBJECT-TYPE
    SYNTAX INTEGER {
        on(1),
        off(2),
        unsupported(2147483647)
        }
    MAX-ACCESS  read-only
    STATUS  current
    DESCRIPTION
        "Gives information whether BFD is on/off on the interface.
	Note:This mib is not supported for VX instance of virtualization."
    ::= { intfInfoEntry 9 }

ipRouteInfoTable OBJECT-TYPE
    SYNTAX  SEQUENCE OF IpRouteInfoEntry
    MAX-ACCESS  not-accessible
    STATUS  current
    DESCRIPTION
        "The table of run-time IP routes.
	Note:This mib is not supported for VX instance of virtualization."
    ::= { ipRoutingInfo 1 }

ipRouteInfoEntry OBJECT-TYPE
    SYNTAX  IpRouteInfoEntry
    MAX-ACCESS  not-accessible
    STATUS  current
    DESCRIPTION
        "A row in the run-time IP route table.
         Note:This mib is not supported for VX instance of virtualization."
    INDEX   { ipRouteInfoIndx }
    ::= { ipRouteInfoTable 1 }

IpRouteInfoEntry ::= SEQUENCE {
    ipRouteInfoIndx	        Integer32,
    ipRouteInfoDestIp           IpAddress,
    ipRouteInfoMask             IpAddress,
    ipRouteInfoGateway          IpAddress,
    ipRouteInfoTag       	INTEGER,
    ipRouteInfoType       	INTEGER,
    ipRouteInfoInterface        Integer32,
    ipRouteInfoGateway1         IpAddress,
    ipRouteInfoGateway2         IpAddress,
    ipRouteInfoMetric           Integer32,
    ipRouteInfoTunnelId         DisplayString,
    ipRouteInfoMode             INTEGER
    }

ipRouteInfoIndx OBJECT-TYPE
    SYNTAX  Integer32
    MAX-ACCESS  read-only
    STATUS  current
    DESCRIPTION
        "The index of this route table.
	Note:This mib is not supported for VX instance of virtualization."
    ::= { ipRouteInfoEntry 1 }

ipRouteInfoDestIp OBJECT-TYPE
    SYNTAX  IpAddress
    MAX-ACCESS  read-only
    STATUS  current
    DESCRIPTION
        "The destination IP address of this route.
	Note:This mib is not supported for VX instance of virtualization."
    ::= { ipRouteInfoEntry 2 }

ipRouteInfoMask OBJECT-TYPE
    SYNTAX  IpAddress
    MAX-ACCESS  read-only
    STATUS  current
    DESCRIPTION
        "The destination IP mask of this route.
	Note:This mib is not supported for VX instance of virtualization."
    ::= { ipRouteInfoEntry 3 }
 
ipRouteInfoGateway OBJECT-TYPE
    SYNTAX  IpAddress
    MAX-ACCESS  read-only
    STATUS  current
    DESCRIPTION
        "The next-hop router address for this route.
	Note:This mib is not supported for VX instance of virtualization."
    ::= { ipRouteInfoEntry 4 }

ipRouteInfoTag OBJECT-TYPE
    SYNTAX  INTEGER {
	fixed(1),
  	static(2),
	addr(3),
	rip(4),
	broadcast(5),
	martian(6),
	multicast(7),
        vip(8),
        bgp(9),
        ospf(10),
        none(11),
        unsupported(2147483647)
	}
    MAX-ACCESS  read-only
    STATUS  current
    DESCRIPTION
        "The tag-type for this route.
	Note:This mib is not supported for VX instance of virtualization."
    ::= { ipRouteInfoEntry 5 }

ipRouteInfoType OBJECT-TYPE 
    SYNTAX  INTEGER {
	indirect(1),
	direct(2),
	local(3),
	broadcast(4),
	martian(5),
	multicast(6),
	other(7),
        unsupported(2147483647)
	}
    MAX-ACCESS  read-only 
    STATUS  current 
    DESCRIPTION 
        "The type of the route.
	Note:This mib is not supported for VX instance of virtualization." 
    ::= { ipRouteInfoEntry 6 }

ipRouteInfoInterface OBJECT-TYPE 
    SYNTAX  Integer32
    MAX-ACCESS  read-only 
    STATUS  current 
    DESCRIPTION 
        "The interface number for which the destination	address is applicable.
	Note:This mib is not supported for VX instance of virtualization."
    ::= { ipRouteInfoEntry 7 }
    
ipRouteInfoGateway1 OBJECT-TYPE
    SYNTAX  IpAddress
    MAX-ACCESS  read-only
    STATUS  current
    DESCRIPTION
        "The next-hop router address for this route.
	Note:This mib is not supported for VX instance of virtualization."
    ::= { ipRouteInfoEntry 8 }
    
ipRouteInfoGateway2 OBJECT-TYPE
    SYNTAX  IpAddress
    MAX-ACCESS  read-only
    STATUS  current
    DESCRIPTION
        "The next-hop router address for this route.
	Note:This mib is not supported for VX instance of virtualization."
    ::= { ipRouteInfoEntry 9 }
    
ipRouteInfoMetric OBJECT-TYPE
    SYNTAX Integer32 
    MAX-ACCESS  read-only
    STATUS  current
    DESCRIPTION
        "The Metric for this route.
	Note:This mib is not supported for VX instance of virtualization."
    ::= { ipRouteInfoEntry 10 }

ipRouteInfoTunnelId OBJECT-TYPE
    SYNTAX  DisplayString (SIZE(0..31))
    MAX-ACCESS  read-only
    STATUS  current
    DESCRIPTION
        "Tunnel Id for this route.
        Note:This mib is not supported for VX instance of virtualization."
    ::= { ipRouteInfoEntry 11 }

ipRouteInfoMode OBJECT-TYPE
    SYNTAX  INTEGER {
        gateway(1),
        tunnel(2),
        unsupported(2147483647)
        }
    MAX-ACCESS  read-only
    STATUS  current
    DESCRIPTION
        "Route mode - gateway or tunnel route.
        Note:This mib is not supported for VX instance of virtualization."
    ::= { ipRouteInfoEntry 12 }

routeTableClear OBJECT-TYPE
    SYNTAX  INTEGER {
        ok(1),
        clear(2),
        unsupported(2147483647)
        }
    MAX-ACCESS  read-write
    STATUS  current 
    DESCRIPTION
        "Setting this value to clear(2) clears the route table.
	Note:This mib is not supported for VX instance of virtualization."
    ::= { ipRoutingInfo 2 }

-- Run Time ARP Table

arpInfoTable OBJECT-TYPE
    SYNTAX  SEQUENCE OF AgArpInfoEntry
    MAX-ACCESS  not-accessible
    STATUS  current
    DESCRIPTION
        "The table of ARP entries.
	Note:This mib is not supported for VX instance of virtualization."
    ::= { arpInfo 1 }

arpInfoEntry OBJECT-TYPE
    SYNTAX  AgArpInfoEntry
    MAX-ACCESS  not-accessible
    STATUS  current
    DESCRIPTION
        "A row in the ARP table.
         Note:This mib is not supported for VX instance of virtualization."
    INDEX   { arpInfoDestIp }
    ::= { arpInfoTable 1 }

AgArpInfoEntry ::= SEQUENCE {
    arpInfoDestIp         IpAddress,
    arpInfoMacAddr        PhysAddress,
    arpInfoVLAN        	  Integer32,
    arpInfoSrcPort        Integer32,
    arpInfoRefPorts       Integer32,
    arpInfoFlag           INTEGER,
    arpInfoRefSPs         DisplayString
    }

arpInfoDestIp OBJECT-TYPE
    SYNTAX  IpAddress
    MAX-ACCESS  read-only
    STATUS  current
    DESCRIPTION
        "The destination IP address of the ARP entry.
	Note:This mib is not supported for VX instance of virtualization."
    ::= { arpInfoEntry 1 }

arpInfoMacAddr OBJECT-TYPE
    SYNTAX  PhysAddress
    MAX-ACCESS  read-only
    STATUS  current
    DESCRIPTION
        "The MAC address for the ARP entry.
	Note:This mib is not supported for VX instance of virtualization."
    ::= { arpInfoEntry 2 }

arpInfoVLAN OBJECT-TYPE 
    SYNTAX  Integer32 
    MAX-ACCESS  read-only 
    STATUS  current 
    DESCRIPTION 
        "The VLAN identifier for the ARP entry.
	Note:This mib is not supported for VX instance of virtualization." 
    ::= { arpInfoEntry 3 }

arpInfoSrcPort OBJECT-TYPE  
    SYNTAX  Integer32 
    MAX-ACCESS  read-only  
    STATUS  current  
    DESCRIPTION  
        "The  port number on which this entry's equivalence is effective.
	Note:This mib is not supported for VX instance of virtualization."  
    ::= { arpInfoEntry 4 }

arpInfoRefPorts OBJECT-TYPE   
    SYNTAX  Integer32
    MAX-ACCESS  read-only   
    STATUS  current   
    DESCRIPTION   
        "The mask of reference SPs associated with this ARP entry.
	Note:This mib is not supported for VX instance of virtualization."   
    ::= { arpInfoEntry 5 }

arpInfoFlag OBJECT-TYPE   
    SYNTAX  INTEGER {
	clear(1),
	unresolved(2),
	permanent(3),
	indirect(4),
	layer4(5),
        unsupported(2147483647)
	}
    MAX-ACCESS  read-only   
    STATUS  current   
    DESCRIPTION   
        "The flag associated with this ARP entry.
	Note:This mib is not supported for VX instance of virtualization."   
    ::= { arpInfoEntry 6 }

arpInfoRefSPs OBJECT-TYPE   
    SYNTAX  DisplayString
    MAX-ACCESS  read-only   
    STATUS  current   
    DESCRIPTION   
        "The reference SPs associated with this ARP entry.
	Note:This mib is not supported for VX instance of virtualization."   
    ::= { arpInfoEntry 7 }

arpCacheClear OBJECT-TYPE
    SYNTAX  INTEGER {
        ok(1),
        clear(2),
        unsupported(2147483647)
        }
    MAX-ACCESS  read-write
    STATUS  current 
    DESCRIPTION
        "Setting this value to clear(2) clears the ARP cache.
	Note:This mib is not supported for VX instance of virtualization."
    ::= { arpInfo 2 }

-- VRRP Information

vrrpInfoVirtRtrTable OBJECT-TYPE
    SYNTAX  SEQUENCE OF VrrpInfoVirtRtrTableEntry
    MAX-ACCESS  not-accessible
    STATUS  current
    DESCRIPTION
        "The table of VRRP virtual router run-time information.
	Note:This mib is not supported for VX instance of virtualization."
    ::= { vrrpInfo 1 }

vrrpInfoVirtRtrTableEntry OBJECT-TYPE
    SYNTAX  VrrpInfoVirtRtrTableEntry
    MAX-ACCESS  not-accessible
    STATUS  current
    DESCRIPTION
        "The run-time information about a VRRP virtual router.
	Note:This mib is not supported for VX instance of virtualization."
    INDEX   { vrrpInfoVirtRtrIndex }
    ::= { vrrpInfoVirtRtrTable 1 }
 
VrrpInfoVirtRtrTableEntry ::= SEQUENCE {
    vrrpInfoVirtRtrIndex      Integer32,
    vrrpInfoVirtRtrState      INTEGER,
    vrrpInfoVirtRtrOwnership  INTEGER,
    vrrpInfoVirtRtrServer     INTEGER,
    vrrpInfoVirtRtrProxy      INTEGER,
    vrrpInfoVirtRtrPriority   Integer32
    }

vrrpInfoVirtRtrIndex OBJECT-TYPE
    SYNTAX  Integer32
    MAX-ACCESS  read-only
    STATUS  current
    DESCRIPTION
        "The VRRP virtual router index.
	Note:This mib is not supported for VX instance of virtualization." 
    ::= { vrrpInfoVirtRtrTableEntry 1 }

vrrpInfoVirtRtrState OBJECT-TYPE   
    SYNTAX  INTEGER {
	init(1),
	master(2),
	backup(3),
	holdoff(4),
        unsupported(2147483647)
	}
    MAX-ACCESS  read-only   
    STATUS  current   
    DESCRIPTION   
        "The VRRP virtual router state.
	Note:This mib is not supported for VX instance of virtualization."   
    ::= { vrrpInfoVirtRtrTableEntry 2 }

vrrpInfoVirtRtrOwnership OBJECT-TYPE   
    SYNTAX  INTEGER {
	owner(1),
	renter(2),
        unsupported(2147483647)
	}
    MAX-ACCESS  read-only   
    STATUS  current   
    DESCRIPTION   
        "The VRRP virtual router ownership status.
	Note:This mib is not supported for VX instance of virtualization."   
    ::= { vrrpInfoVirtRtrTableEntry 3 }

vrrpInfoVirtRtrServer OBJECT-TYPE   
    SYNTAX  INTEGER {
	yes(1),
	no(2),
        unsupported(2147483647)
	}
    MAX-ACCESS  read-only   
    STATUS  current   
    DESCRIPTION   
        "The VRRP server state identifies virtual routers that support 
         Layer 4 services.
	Note:This mib is not supported for VX instance of virtualization."   
    ::= { vrrpInfoVirtRtrTableEntry 4 }

vrrpInfoVirtRtrProxy OBJECT-TYPE   
    SYNTAX  INTEGER {
	yes(1),
	no(2),
        unsupported(2147483647)
	}
    MAX-ACCESS  read-only   
    STATUS  current   
    DESCRIPTION   
        "The VRRP proxy state identifies virtual proxy routers.
	Note:This mib is not supported for VX instance of virtualization."
    ::= { vrrpInfoVirtRtrTableEntry 5 }

vrrpInfoVirtRtrPriority OBJECT-TYPE
    SYNTAX  Integer32
    MAX-ACCESS  read-only
    STATUS  current
    DESCRIPTION
        "The VRRP virtual router priority.
	Note:This mib is not supported for VX instance of virtualization."
    ::= { vrrpInfoVirtRtrTableEntry 6 }	

vrrpInfoHAState OBJECT-TYPE
    SYNTAX  DisplayString 
    MAX-ACCESS  read-only 
    STATUS  current
    DESCRIPTION
        "The global VRRP or HA state.
         Note:This mib is not supported for VX instance of virtualization."
    ::= { vrrpInfo 2 }
-- Ospf Information 

ospfGeneralInfo  OBJECT IDENTIFIER ::= { ospfinfo 1 }

ospfStartTime OBJECT-TYPE   
    SYNTAX  Integer32 
    MAX-ACCESS  read-only   
    STATUS  current   
    DESCRIPTION   
        "The time when ospf has been started.
	Note:This mib is not supported for VX instance of virtualization."   
    ::= { ospfGeneralInfo 1 }

ospfProcessUptime OBJECT-TYPE   
    SYNTAX  Counter32 
    MAX-ACCESS  read-only   
    STATUS  current   
    DESCRIPTION   
        "The time since ospf has been started.
	Note:This mib is not supported for VX instance of virtualization."   
    ::= { ospfGeneralInfo 2 }

ospfLsTypesSupported OBJECT-TYPE   
    SYNTAX  Integer32 
    MAX-ACCESS  read-only   
    STATUS  current   
    DESCRIPTION   
        "The Link State Types that are supported.
	Note:This mib is not supported for VX instance of virtualization."   
    ::= { ospfGeneralInfo 3 }

ospfIntfCountForRouter OBJECT-TYPE   
    SYNTAX  Integer32 
    MAX-ACCESS  read-only   
    STATUS  current   
    DESCRIPTION   
        "The number of interfaces for this router.
	Note:This mib is not supported for VX instance of virtualization." 
    ::= { ospfGeneralInfo 4 }

ospfVlinkCountForRouter OBJECT-TYPE   
    SYNTAX  Integer32 
    MAX-ACCESS  read-only   
    STATUS  current   
    DESCRIPTION   
        "The number of virtual links for this router.
	Note:This mib is not supported for VX instance of virtualization." 
    ::= { ospfGeneralInfo 5 }

ospfTotalNeighbours OBJECT-TYPE   
    SYNTAX  Integer32 
    MAX-ACCESS  read-only   
    STATUS  current   
    DESCRIPTION   
        "The total number of OSPF neighbours.
	Note:This mib is not supported for VX instance of virtualization." 
    ::= { ospfGeneralInfo 6 }

ospfNbrInInitState OBJECT-TYPE   
    SYNTAX  Integer32 
    MAX-ACCESS  read-only   
    STATUS  current   
    DESCRIPTION   
        "The number of neighbours in the initial state of exchange.
	Note:This mib is not supported for VX instance of virtualization." 
    ::= { ospfGeneralInfo 7 }

ospfNbrInExchState OBJECT-TYPE   
    SYNTAX  Integer32 
    MAX-ACCESS  read-only   
    STATUS  current   
    DESCRIPTION   
        "The number of neighbours in the exchange state.
	Note:This mib is not supported for VX instance of virtualization." 
    ::= { ospfGeneralInfo 8 }

ospfNbrInFullState OBJECT-TYPE   
    SYNTAX  Integer32 
    MAX-ACCESS  read-only   
    STATUS  current   
    DESCRIPTION   
        "The number of neighbours in the Full state of exchange.
	Note:This mib is not supported for VX instance of virtualization." 
    ::= { ospfGeneralInfo 9 }

ospfTotalAreas OBJECT-TYPE   
    SYNTAX  Integer32 
    MAX-ACCESS  read-only   
    STATUS  current   
    DESCRIPTION   
        "The Total number of areas.
	Note:This mib is not supported for VX instance of virtualization." 
    ::= { ospfGeneralInfo 10 }

ospfTotalTransitAreas OBJECT-TYPE   
    SYNTAX  Integer32 
    MAX-ACCESS  read-only   
    STATUS  current   
    DESCRIPTION   
        "The Total number of Transit areas.
	Note:This mib is not supported for VX instance of virtualization." 
    ::= { ospfGeneralInfo 11 }

ospfTotalNssaAreas OBJECT-TYPE   
    SYNTAX  Integer32 
    MAX-ACCESS  read-only   
    STATUS  current   
    DESCRIPTION   
        "The Total number of NSSA areas.
	Note:This mib is not supported for VX instance of virtualization." 
    ::= { ospfGeneralInfo 12 }

ospfAreaInfoTable OBJECT-TYPE
    SYNTAX SEQUENCE OF OspfAreaInfoEntry
    MAX-ACCESS not-accessible
    STATUS current
    DESCRIPTION
      "The table of OSPF Area information.
	Note:This mib is not supported for VX instance of virtualization."
    ::= { ospfinfo 2 }

ospfAreaInfoEntry OBJECT-TYPE
    SYNTAX OspfAreaInfoEntry
    MAX-ACCESS not-accessible
    STATUS current
    DESCRIPTION
      "Information about a OSPF area.
	Note:This mib is not supported for VX instance of virtualization."
    INDEX { ospfAreaInfoIndex }
    ::= { ospfAreaInfoTable 1 }
 
OspfAreaInfoEntry ::= SEQUENCE {
    ospfAreaInfoIndex             Integer32,
    ospfTotalNumberOfInterfaces   Integer32,
    ospfNumberOfInterfacesUp   	  Integer32,
    ospfNumberOfLsdbEntries   	  Integer32,
    ospfAreaInfoId   	          IpAddress

    }
 
ospfAreaInfoIndex OBJECT-TYPE
    SYNTAX Integer32
    MAX-ACCESS read-only
    STATUS current
    DESCRIPTION
	"The OSPF area number for which the OSPF info table is related.
	Note:This mib is not supported for VX instance of virtualization."
    ::= { ospfAreaInfoEntry 1}

ospfTotalNumberOfInterfaces OBJECT-TYPE
    SYNTAX Integer32
    MAX-ACCESS read-only
    STATUS current
    DESCRIPTION
	"The total number of interfaces for this OSPF area.
	Note:This mib is not supported for VX instance of virtualization." 
    ::= { ospfAreaInfoEntry 2}

ospfNumberOfInterfacesUp OBJECT-TYPE
    SYNTAX Integer32
    MAX-ACCESS read-only
    STATUS current
    DESCRIPTION
	"The number of interfaces UP in area.
	Note:This mib is not supported for VX instance of virtualization." 
    ::= { ospfAreaInfoEntry 3}

ospfNumberOfLsdbEntries OBJECT-TYPE
    SYNTAX Integer32
    MAX-ACCESS read-only
    STATUS current
    DESCRIPTION
	"The number of Link State Database entries for this OSPF area.
	Note:This mib is not supported for VX instance of virtualization." 
    ::= { ospfAreaInfoEntry 4}

ospfAreaInfoId OBJECT-TYPE
    SYNTAX IpAddress
    MAX-ACCESS read-only
    STATUS current
    DESCRIPTION
	"The IP address of the OSPF area.
	Note:This mib is not supported for VX instance of virtualization." 
    ::= { ospfAreaInfoEntry 5}

ospfIntfInfoTable OBJECT-TYPE
    SYNTAX SEQUENCE OF OspfIntfInfoEntry
    MAX-ACCESS not-accessible
    STATUS current
    DESCRIPTION
      "The table of OSPF Interface information.
	Note:This mib is not supported for VX instance of virtualization."
    ::= { ospfinfo 3 }

ospfIntfInfoEntry OBJECT-TYPE
    SYNTAX OspfIntfInfoEntry
    MAX-ACCESS not-accessible
    STATUS current
    DESCRIPTION
      "Information about a OSPF interface.
	Note:This mib is not supported for VX instance of virtualization."
    INDEX { ospfIfInfoIndex }
    ::= { ospfIntfInfoTable 1 }
 
OspfIntfInfoEntry ::= SEQUENCE {
    ospfIfInfoIndex               	Integer32,
    ospfIfDesignatedRouterIP   	  	IpAddress,
    ospfIfBackupDesignatedRouterIP  	IpAddress,
    ospfIfWaitInterval   	        Integer32,
    ospfIfTotalNeighbours   	  	Integer32,
    ospfIfInfoIpAddress   	  	IpAddress
    }
 
ospfIfInfoIndex OBJECT-TYPE
    SYNTAX Integer32
    MAX-ACCESS read-only
    STATUS current
    DESCRIPTION
	"The OSPF interface number for which the OSPF info table is related.
	Note:This mib is not supported for VX instance of virtualization."
    ::= { ospfIntfInfoEntry 1}

ospfIfDesignatedRouterIP OBJECT-TYPE
    SYNTAX IpAddress
    MAX-ACCESS read-only
    STATUS current
    DESCRIPTION
	"The OSPF Designated Router ID (IP Address) for this OSPF interface.
	Note:This mib is not supported for VX instance of virtualization." 
    ::= { ospfIntfInfoEntry 2}

ospfIfBackupDesignatedRouterIP OBJECT-TYPE
    SYNTAX IpAddress
    MAX-ACCESS read-only
    STATUS current
    DESCRIPTION
	"The OSPF Backup Designated Router ID (IP Address) for this OSPF
         interface.
	Note:This mib is not supported for VX instance of virtualization." 
    ::= { ospfIntfInfoEntry 3}

ospfIfWaitInterval OBJECT-TYPE
    SYNTAX Integer32
    MAX-ACCESS read-only
    STATUS current
    DESCRIPTION
	"The OSPF Wait interval for this OSPF interface.
	Note:This mib is not supported for VX instance of virtualization." 
    ::= { ospfIntfInfoEntry 4}

ospfIfTotalNeighbours OBJECT-TYPE
    SYNTAX Integer32
    MAX-ACCESS read-only
    STATUS current
    DESCRIPTION
	"The Total number of neighbours for this OSPF interface.
	Note:This mib is not supported for VX instance of virtualization." 
    ::= { ospfIntfInfoEntry 5}

ospfIfInfoIpAddress OBJECT-TYPE
    SYNTAX IpAddress
    MAX-ACCESS read-only
    STATUS current
    DESCRIPTION
	"The IP address of the OSPF interface.
	Note:This mib is not supported for VX instance of virtualization." 
    ::= { ospfIntfInfoEntry 6}

-- OSPF Interface/Nbr Info Table

ospfIfNbrTable OBJECT-TYPE
    SYNTAX SEQUENCE OF OspfIfNbrEntry
    MAX-ACCESS not-accessible
    STATUS current
    DESCRIPTION
      "The table of OSPF Interface Neighbour information.
	Note:This mib is not supported for VX instance of virtualization."
    ::= { ospfinfo 5 }

ospfIfNbrEntry OBJECT-TYPE
    SYNTAX OspfIfNbrEntry
    MAX-ACCESS not-accessible
    STATUS current
    DESCRIPTION
      "Information about a OSPF interface, neighbour pair.
	Note:This mib is not supported for VX instance of virtualization."
    INDEX { ospfIfNbrIntfIndex, ospfIfNbrIpAddr }
    ::= { ospfIfNbrTable 1 }
 
OspfIfNbrEntry ::= SEQUENCE {
    ospfIfNbrIntfIndex               Integer32,
    ospfIfNbrIpAddr                  IpAddress,
    ospfIfNbrPriority                Integer32,
    ospfIfNbrState                   INTEGER,
    ospfIfNbrDesignatedRtr     	     IpAddress,
    ospfIfNbrBackupDesignatedRtr     IpAddress,
    ospfIfNbrIpAddress               IpAddress 
    }
 
ospfIfNbrIntfIndex OBJECT-TYPE
    SYNTAX Integer32
    MAX-ACCESS read-only
    STATUS current
    DESCRIPTION
	"The OSPF Interface number for which this Interface/Nbr table is 
         related.
	Note:This mib is not supported for VX instance of virtualization."
    ::= { ospfIfNbrEntry 1}

ospfIfNbrIpAddr OBJECT-TYPE
    SYNTAX IpAddress 
    MAX-ACCESS read-only
    STATUS current
    DESCRIPTION
	"The OSPF Neighbour ID .
	Note:This mib is not supported for VX instance of virtualization." 
    ::= { ospfIfNbrEntry 2 }

ospfIfNbrPriority OBJECT-TYPE
    SYNTAX Integer32
    MAX-ACCESS read-only
    STATUS current
    DESCRIPTION
	"The priority of the OSPF neighbour.
	Note:This mib is not supported for VX instance of virtualization."
    ::= { ospfIfNbrEntry 3 }

ospfIfNbrState OBJECT-TYPE
    SYNTAX  INTEGER { 
	down(1),
	attempt(2),
	init(3),
	twoway(4),
	exStart(5),
	exchange(6),
	loading(7),
	full(8),
        unsupported(2147483647)
	}
    MAX-ACCESS read-only
    STATUS current
    DESCRIPTION
	"The state of the OSPF neighbour.
	Note:This mib is not supported for VX instance of virtualization."
    ::= { ospfIfNbrEntry 4 }

ospfIfNbrDesignatedRtr OBJECT-TYPE
    SYNTAX IpAddress 
    MAX-ACCESS read-only
    STATUS current
    DESCRIPTION
	"The IP Address of the Designated Router for this OSPF Neighbour.
	Note:This mib is not supported for VX instance of virtualization." 
    ::= { ospfIfNbrEntry 5 }

ospfIfNbrBackupDesignatedRtr OBJECT-TYPE
    SYNTAX IpAddress 
    MAX-ACCESS read-only
    STATUS current
    DESCRIPTION
	"The IP Address of the backup designated Router for this OSPF Neighbour.
	Note:This mib is not supported for VX instance of virtualization." 
    ::= { ospfIfNbrEntry 6 }

ospfIfNbrIpAddress OBJECT-TYPE
    SYNTAX IpAddress 
    MAX-ACCESS read-only
    STATUS current
    DESCRIPTION
	"The IP Address of the OSPF Neighbour.
	Note:This mib is not supported for VX instance of virtualization." 
    ::= { ospfIfNbrEntry 7 }

-- Gateway Information
gatewayInfoTable OBJECT-TYPE
    SYNTAX  SEQUENCE OF GatewayInfoEntry
    MAX-ACCESS  not-accessible
    STATUS  current
    DESCRIPTION
        "The table containing information for the default gateways.
	Note:This mib is not supported for VX instance of virtualization."
    ::= { gatewayInfo 1 }

gatewayInfoEntry OBJECT-TYPE
    SYNTAX  GatewayInfoEntry
    MAX-ACCESS  not-accessible
    STATUS  current
    DESCRIPTION
        "A row in the gateway information table.
         Note:This mib is not supported for VX instance of virtualization."
    INDEX   { gatewayInfoIndex }
    ::= { gatewayInfoTable 1 }

GatewayInfoEntry ::= SEQUENCE {
    gatewayInfoIndex         Integer32,
    gatewayInfoAddr          IpAddress,
    gatewayInfoVlan          Integer32,
    gatewayInfoAddr6         DisplayString,
    gatewayInfoStatus        INTEGER
    }

gatewayInfoIndex OBJECT-TYPE
    SYNTAX  Integer32
    MAX-ACCESS  read-only
    STATUS  current
    DESCRIPTION
        "The gateway number for which the information is related.
	Note:This mib is not supported for VX instance of virtualization."
    ::= { gatewayInfoEntry 1}

gatewayInfoAddr OBJECT-TYPE
    SYNTAX  IpAddress
    MAX-ACCESS  read-only
    STATUS  current
    DESCRIPTION
        "The IP address of the default gateway.
	Note:This mib is not supported for VX instance of virtualization."
    ::= { gatewayInfoEntry 2 }

gatewayInfoVlan OBJECT-TYPE
    SYNTAX  Integer32
    MAX-ACCESS  read-only
    STATUS  current
    DESCRIPTION
        "The VLAN number for this gateway.
	Note:This mib is not supported for VX instance of virtualization."
    ::= { gatewayInfoEntry 3 }

gatewayInfoStatus OBJECT-TYPE
    SYNTAX  INTEGER {
        up(1),
        failed(2),
        unsupported(2147483647)
	}  
    MAX-ACCESS  read-only
    STATUS  current
    DESCRIPTION
        "The status of the default gateway.
	Note:This mib is not supported for VX instance of virtualization."
    ::= { gatewayInfoEntry 4 }


gatewayInfoAddr6 OBJECT-TYPE
    SYNTAX  DisplayString 
    MAX-ACCESS  read-only
    STATUS  current
    DESCRIPTION
        "The IP6 address of the default gateway.
	Note:This mib is not supported for VX instance of virtualization."
    ::= { gatewayInfoEntry 5 }



-- nbrcache Info Table

nbrcacheInfoTable OBJECT-TYPE
    SYNTAX SEQUENCE OF NbrcacheInfoEntry
    MAX-ACCESS not-accessible
    STATUS current
    DESCRIPTION
        "The table of nbrcache information.
	Note:This mib is not supported for VX instance of virtualization."
    ::= { nbrcacheInfo 1 }

nbrcacheInfoEntry OBJECT-TYPE
    SYNTAX NbrcacheInfoEntry
    MAX-ACCESS not-accessible
    STATUS current
    DESCRIPTION
        "Information about neighbour discovery protocol.
	Note:This mib is not supported for VX instance of virtualization."
    INDEX { nbrcacheInfoIndex }
    ::= { nbrcacheInfoTable 1 }

NbrcacheInfoEntry ::= SEQUENCE {
    nbrcacheInfoIndex         Integer32,
    nbrcacheInfoDestIp        DisplayString,
    nbrcacheInfoState         INTEGER,
    nbrcacheInfoType          INTEGER,
    nbrcacheInfoMacAddr       PhysAddress,
    nbrcacheInfoVlanId        Integer32,
    nbrcacheInfoPortNum       Integer32
    }

nbrcacheInfoIndex  OBJECT-TYPE
    SYNTAX  Integer32
    MAX-ACCESS  read-only
    STATUS  current
    DESCRIPTION
        "The index of the nbrcache entry.
	Note:This mib is not supported for VX instance of virtualization."
    ::= { nbrcacheInfoEntry 1 }

nbrcacheInfoDestIp OBJECT-TYPE
    SYNTAX   DisplayString 
    MAX-ACCESS  read-only
    STATUS  current
    DESCRIPTION
        "The destination IP address of the nbrcache entry.
	Note:This mib is not supported for VX instance of virtualization."
    ::= { nbrcacheInfoEntry 2 }

nbrcacheInfoState  OBJECT-TYPE
    SYNTAX  INTEGER  {
        undef(1),
        reach(2),
        stale(3),
        delay(4),
        probe(5),
        inval(6),
        unknown(7),
        incmp(8),
        unsupported(2147483647)
    }
    MAX-ACCESS  read-only
    STATUS  current
    DESCRIPTION
        "The state of the nbrcache entry.
	Note:This mib is not supported for VX instance of virtualization."
    ::= { nbrcacheInfoEntry 3 }

nbrcacheInfoType  OBJECT-TYPE
    SYNTAX  INTEGER {
        undef(1),
        other(2),
        invalid(3),
        dynamic(4),
        static(5),
        local(6),
        unsupported(2147483647)
    }
    MAX-ACCESS  read-only
    STATUS  current
    DESCRIPTION
        "The type of the nbrcache entry.
	Note:This mib is not supported for VX instance of virtualization."
    ::= { nbrcacheInfoEntry 4 }

nbrcacheInfoMacAddr OBJECT-TYPE
    SYNTAX  PhysAddress
    MAX-ACCESS  read-only
    STATUS  current
    DESCRIPTION
        "The MAC address for the nbrcache entry.
	Note:This mib is not supported for VX instance of virtualization."
    ::= { nbrcacheInfoEntry 5 }

nbrcacheInfoVlanId  OBJECT-TYPE 
    SYNTAX  Integer32 
    MAX-ACCESS  read-only 
    STATUS  current 
    DESCRIPTION 
        "The VLAN identifier for the nbrcache entry.
	Note:This mib is not supported for VX instance of virtualization." 
    ::= { nbrcacheInfoEntry 6 }

nbrcacheInfoPortNum   OBJECT-TYPE
    SYNTAX  Integer32
    MAX-ACCESS  read-only
    STATUS  current
    DESCRIPTION
        "The  port number on which this entry's equivalence is effective.
	Note:This mib is not supported for VX instance of virtualization."  
    ::= { nbrcacheInfoEntry 7 }

nbrcacheClear OBJECT-TYPE
    SYNTAX  INTEGER {
        ok(1),
        clear(2),
        unsupported(2147483647)
        }
    MAX-ACCESS  read-write
    STATUS  current 
    DESCRIPTION
        "Setting this value to clear(2) clears the Nbr cache,
         When read ok(1) is  returned.
	Note:This mib is not supported for VX instance of virtualization."
    ::= { nbrcacheInfo 2 }

nbrcacheInfoTotDynamicEntries OBJECT-TYPE
    SYNTAX  Integer32
    MAX-ACCESS  read-only
    STATUS  current
    DESCRIPTION
        "The total number of dynamic neighbour cache entries.
	Note:This mib is not supported for VX instance of virtualization."
    ::= { nbrcacheInfo 3 }

nbrcacheInfoTotLocalEntries OBJECT-TYPE
    SYNTAX  Integer32
    MAX-ACCESS  read-only
    STATUS  current
    DESCRIPTION
        "The total number of local neighbour cache entries.
	Note:This mib is not supported for VX instance of virtualization."
    ::= { nbrcacheInfo 4 }

nbrcacheInfoTotOtherEntries  OBJECT-TYPE
    SYNTAX  Integer32
    MAX-ACCESS  read-only
    STATUS  current
    DESCRIPTION
        "The total number of other neighbour cache entries.
	Note:This mib is not supported for VX instance of virtualization."
    ::= { nbrcacheInfo 5 }

nbrcacheInfoTotStaticEntries  OBJECT-TYPE
    SYNTAX  Integer32
    MAX-ACCESS  read-only
    STATUS  current
    DESCRIPTION
        "The total number of static neighbour cache entries.
	Note:This mib is not supported for VX instance of virtualization."
    ::= { nbrcacheInfo 6 }

ipRoute6InfoTable OBJECT-TYPE
    SYNTAX  SEQUENCE OF IpRoute6InfoEntry
    MAX-ACCESS  not-accessible
    STATUS  current
    DESCRIPTION
        "The table of run-time IP6 routes.
	Note:This mib is not supported for VX instance of virtualization."
    ::= { ipRoute6Info 1 }

ipRoute6InfoEntry OBJECT-TYPE
    SYNTAX  IpRoute6InfoEntry
    MAX-ACCESS  not-accessible
    STATUS  current
    DESCRIPTION
        "A row in the run-time IP6 route table.
	Note:This mib is not supported for VX instance of virtualization."
    INDEX   { ipRoute6InfoIndx }
    ::= { ipRoute6InfoTable 1 }

IpRoute6InfoEntry ::= SEQUENCE {
    ipRoute6InfoIndx            Integer32,
    ipRoute6InfoDestIp6         DisplayString,
    ipRoute6InfoInterface       Integer32,
    ipRoute6InfoNextHop         DisplayString,
    ipRoute6InfoProto           INTEGER,
    ipRoute6InfoTunnelId        DisplayString,
    ipRoute6InfoMode            INTEGER
    }

ipRoute6InfoIndx OBJECT-TYPE
    SYNTAX  Integer32
    MAX-ACCESS  read-only
    STATUS  current
    DESCRIPTION
        "The index of this route6 table.
	Note:This mib is not supported for VX instance of virtualization."
    ::= { ipRoute6InfoEntry 1 }

ipRoute6InfoDestIp6 OBJECT-TYPE
    SYNTAX  DisplayString
    MAX-ACCESS  read-only
    STATUS  current
    DESCRIPTION
        "The destination of the route.
	Note:This mib is not supported for VX instance of virtualization."
    ::= { ipRoute6InfoEntry 2 }

ipRoute6InfoInterface OBJECT-TYPE
    SYNTAX  Integer32
    MAX-ACCESS  read-only
    STATUS  current
    DESCRIPTION
        "The interface of the route.
	Note:This mib is not supported for VX instance of virtualization."
    ::= { ipRoute6InfoEntry 3 }

ipRoute6InfoNextHop  OBJECT-TYPE
    SYNTAX  DisplayString
    MAX-ACCESS  read-only
    STATUS  current
    DESCRIPTION
        "The next hop of the route.
	Note:This mib is not supported for VX instance of virtualization."
    ::= { ipRoute6InfoEntry 4 }

ipRoute6InfoProto  OBJECT-TYPE
    SYNTAX  INTEGER {
        isis(1),
        rip(2),
        ospf(3),
        static(4),
        local(5),
        bgp(6),
        stlow(7),
        ospfi(8),
        ospfe(9),
        ospfe2(10),
        ospfa(11),
        ripa(12),
        bgpa(13),
        igmp(14),
        unknown(15),
        natpt(16),
        unsupported(2147483647)
        }
    MAX-ACCESS  read-only
    STATUS  current
    DESCRIPTION
        "The protocol type of the route.
	Note:This mib is not supported for VX instance of virtualization."
    ::= { ipRoute6InfoEntry 5 }

ipRoute6InfoTunnelId OBJECT-TYPE
    SYNTAX  DisplayString (SIZE(0..31))
    MAX-ACCESS  read-only
    STATUS  current
    DESCRIPTION
        "Tunnel Id for this route.
        Note:This mib is not supported for VX instance of virtualization."
    ::= { ipRoute6InfoEntry 6 }

ipRoute6InfoMode OBJECT-TYPE
    SYNTAX  INTEGER {
        gateway(1),
        tunnel(2),
        unsupported(2147483647)
        }
    MAX-ACCESS  read-only
    STATUS  current
    DESCRIPTION
        "Route mode - gateway or tunnel route.
        Note:This mib is not supported for VX instance of virtualization."
    ::= { ipRoute6InfoEntry 7 }

rip2GeneralInfo	OBJECT IDENTIFIER ::= { rip2Info 1 }

ripInfoState OBJECT-TYPE
    SYNTAX INTEGER {
        on(1),
        off(2),
        unsupported(2147483647)
        }
    MAX-ACCESS read-only
    STATUS current
    DESCRIPTION
	"RIP global state.
	Note:This mib is not supported for VX instance of virtualization."
    ::= { rip2GeneralInfo 1 }

ripInfoUpdatePeriod OBJECT-TYPE
    SYNTAX  INTEGER  (1..120)
    MAX-ACCESS  read-only
    STATUS  current
    DESCRIPTION
        "Update Period in seconds.
	Note:This mib is not supported for VX instance of virtualization."
    ::= { rip2GeneralInfo 2 }

ripInfoVip OBJECT-TYPE
    SYNTAX  INTEGER {
        enabled(2),
        disabled(3),
        unsupported(2147483647)
        }
    MAX-ACCESS  read-only
    STATUS  current
    DESCRIPTION
        "Advertise VIP Host Routes.
	Note:This mib is not supported for VX instance of virtualization."
    ::= { rip2GeneralInfo 3 }

ripInfoStaticSupply OBJECT-TYPE
    SYNTAX  INTEGER {
        enabled(2),
        disabled(3),
        unsupported(2147483647)
        }
    MAX-ACCESS  read-only
    STATUS  current
    DESCRIPTION
        "Advertise Static Routes.
	Note:This mib is not supported for VX instance of virtualization."
    ::= { rip2GeneralInfo 4 }

rip2InfoIntfTable OBJECT-TYPE
    SYNTAX SEQUENCE OF RipInfoIntfEntry
    MAX-ACCESS not-accessible
    STATUS current
    DESCRIPTION
      "The information table of RIP.
	Note:This mib is not supported for VX instance of virtualization."
    ::= { rip2Info 2 }

ripInfoIntfEntry OBJECT-TYPE
    SYNTAX RipInfoIntfEntry
    MAX-ACCESS not-accessible
    STATUS current
    DESCRIPTION
      "Information about  RIP on IP interface.
	Note:This mib is not supported for VX instance of virtualization."
    INDEX { ripInfoIntfIndex }
    ::= { rip2InfoIntfTable 1 }
 
RipInfoIntfEntry ::= SEQUENCE {
    ripInfoIntfIndex  	      Integer32,
    ripInfoIntfVersion	      INTEGER,
    ripInfoIntfAddress        IpAddress,
    ripInfoIntfState	      INTEGER,
    ripInfoIntfListen	      INTEGER,
    ripInfoIntfTrigUpdate     INTEGER,
    ripInfoIntfMcastUpdate    INTEGER,
    ripInfoIntfPoisonReverse  INTEGER,
    ripInfoIntfSupply         INTEGER,
    ripInfoIntfMetric         INTEGER, 
    ripInfoIntfAuth           INTEGER, 
    ripInfoIntfKey            DisplayString,
    ripInfoIntfDefault	      INTEGER
    }
 
ripInfoIntfIndex OBJECT-TYPE
    SYNTAX Integer32
    MAX-ACCESS read-only
    STATUS current
    DESCRIPTION
	"The interface number for which the RIP information is related.
	Note:This mib is not supported for VX instance of virtualization."
    ::= { ripInfoIntfEntry 1 }

ripInfoIntfVersion OBJECT-TYPE
    SYNTAX INTEGER {
        ripVersion1(1),
        ripVersion2(2),
        unsupported(2147483647)
        }
    MAX-ACCESS read-only
    STATUS current
    DESCRIPTION
        "RIP version.
	Note:This mib is not supported for VX instance of virtualization."
    ::= { ripInfoIntfEntry 2 }

ripInfoIntfAddress OBJECT-TYPE
    SYNTAX  IpAddress 
    MAX-ACCESS read-only
    STATUS current
    DESCRIPTION
        "The interface address.
	Note:This mib is not supported for VX instance of virtualization."
    ::= { ripInfoIntfEntry 3 } 

ripInfoIntfState OBJECT-TYPE
    SYNTAX INTEGER {
        enabled(1),
        disabled(2),
        unsupported(2147483647)
        }
    MAX-ACCESS read-only
    STATUS current
    DESCRIPTION
        "The status of RIP protocol.
	Note:This mib is not supported for VX instance of virtualization."
    ::= { ripInfoIntfEntry 4 }

ripInfoIntfListen OBJECT-TYPE
    SYNTAX INTEGER {
        enabled(1),
        disabled(2),
        unsupported(2147483647)
        }
    MAX-ACCESS read-only
    STATUS current
    DESCRIPTION
        "The status of listening to route updates.
	Note:This mib is not supported for VX instance of virtualization."
    ::= { ripInfoIntfEntry 5 }
 
ripInfoIntfTrigUpdate OBJECT-TYPE
    SYNTAX INTEGER {
        enabled(1),
        disabled(2),
        unsupported(2147483647)
        }
    MAX-ACCESS read-only
    STATUS current
    DESCRIPTION
	"The status of triggered updates.
	Note:This mib is not supported for VX instance of virtualization."
    ::= { ripInfoIntfEntry 6 }

ripInfoIntfMcastUpdate OBJECT-TYPE
    SYNTAX INTEGER {
        enabled(1),
        disabled(2),
        unsupported(2147483647)
        }
    MAX-ACCESS read-only
    STATUS current
    DESCRIPTION
	"The status of multicast updates.
	Note:This mib is not supported for VX instance of virtualization."
    ::= { ripInfoIntfEntry 7 }

ripInfoIntfPoisonReverse OBJECT-TYPE
    SYNTAX  INTEGER {
        enabled(1),
        disabled(2),
        unsupported(2147483647)
        }
    MAX-ACCESS read-only
    STATUS current
    DESCRIPTION
	"The status of RIP poison reverse.
	Note:This mib is not supported for VX instance of virtualization."
    ::= { ripInfoIntfEntry 8 }

ripInfoIntfSupply OBJECT-TYPE
    SYNTAX INTEGER {
        enabled(1),
        disabled(2),
        unsupported(2147483647)
        }
    MAX-ACCESS read-only
    STATUS current
    DESCRIPTION
        "The status of supplying route updates.
	Note:This mib is not supported for VX instance of virtualization."
    ::= { ripInfoIntfEntry 9 }

ripInfoIntfMetric OBJECT-TYPE
    SYNTAX  INTEGER (1..15)
    MAX-ACCESS read-only
    STATUS current
    DESCRIPTION
        "RIP route metric for this interface.
	Note:This mib is not supported for VX instance of virtualization."
    ::= { ripInfoIntfEntry 10 }

ripInfoIntfAuth OBJECT-TYPE
    SYNTAX INTEGER {
        none(1),
        password(2),
        unsupported(2147483647)
        }
    MAX-ACCESS read-only
    STATUS current
    DESCRIPTION
        "The type of Authentication used on this interface.
	Note:This mib is not supported for VX instance of virtualization."
    ::= { ripInfoIntfEntry 11 }

ripInfoIntfKey OBJECT-TYPE
    SYNTAX  DisplayString (SIZE(0..16))
    MAX-ACCESS  read-only
    STATUS  current
    DESCRIPTION
        "RIP update authentication password.
	Note:This mib is not supported for VX instance of virtualization."
    ::= { ripInfoIntfEntry 12 }

ripInfoIntfDefault OBJECT-TYPE
    SYNTAX  INTEGER {
        both(1),
        listen(2),
        supply(3),
        none(4),
        unsupported(2147483647)
        }
    MAX-ACCESS read-only
    STATUS current
    DESCRIPTION
	"Specifies what RIP does with default routes.
	Note:This mib is not supported for VX instance of virtualization."
    ::= { ripInfoIntfEntry 13 }


rip2RoutesInfoTable OBJECT-TYPE
    SYNTAX SEQUENCE OF Rip2RoutesInfoEntry 
    MAX-ACCESS not-accessible
    STATUS current
    DESCRIPTION
        "The table of rip routes.
	Note:This mib is not supported for VX instance of virtualization."
    ::= { rip2RoutesInfo 1 }

rip2RoutesInfoEntry OBJECT-TYPE
    SYNTAX Rip2RoutesInfoEntry 
    MAX-ACCESS not-accessible
    STATUS current
    DESCRIPTION
        "Information about rip routes.
	Note:This mib is not supported for VX instance of virtualization."
    INDEX { rip2RoutesInfoDestIndex, rip2RoutesInfoNxtHopIndex }
    ::= { rip2RoutesInfoTable 1 }

Rip2RoutesInfoEntry ::= SEQUENCE {
    rip2RoutesInfoDestIndex     Integer32,
    rip2RoutesInfoNxtHopIndex   Integer32,
    rip2RoutesInfoDestination   DisplayString,
    rip2RoutesInfoIpAddress     IpAddress,
    rip2RoutesInfoMetric        INTEGER 
    }

rip2RoutesInfoDestIndex  OBJECT-TYPE
    SYNTAX  Integer32
    MAX-ACCESS  read-only
    STATUS  current
    DESCRIPTION
        "The index of the rip routes.
	Note:This mib is not supported for VX instance of virtualization."
    ::= { rip2RoutesInfoEntry 1 }

rip2RoutesInfoNxtHopIndex  OBJECT-TYPE
    SYNTAX  Integer32
    MAX-ACCESS  read-only
    STATUS  current
    DESCRIPTION
        "The index of the next hop.
	Note:This mib is not supported for VX instance of virtualization."
    ::= { rip2RoutesInfoEntry 2 }

rip2RoutesInfoDestination  OBJECT-TYPE
    SYNTAX   DisplayString
    MAX-ACCESS  read-only
    STATUS  current
    DESCRIPTION
        "The destination of the rip route.
	Note:This mib is not supported for VX instance of virtualization."
    ::= { rip2RoutesInfoEntry 3 }

rip2RoutesInfoIpAddress  OBJECT-TYPE
    SYNTAX  IpAddress
    MAX-ACCESS  read-only
    STATUS  current
    DESCRIPTION
        "The ipaddress of the next hop.
	Note:This mib is not supported for VX instance of virtualization."
    ::= { rip2RoutesInfoEntry  4 }

rip2RoutesInfoMetric  OBJECT-TYPE
    SYNTAX   INTEGER ( 1..15 )
    MAX-ACCESS  read-only
    STATUS  current
    DESCRIPTION
        "RIP route metric for this route.
	Note:This mib is not supported for VX instance of virtualization."
    ::= { rip2RoutesInfoEntry  5 }

allowedNwInfoTable OBJECT-TYPE
    SYNTAX  SEQUENCE OF AllowedNwInfoEntry
    MAX-ACCESS  not-accessible
    STATUS  current
    DESCRIPTION
        "The table of allowed network run-time information.
	Note:This mib is not supported for VX instance of virtualization."
    ::= { allowedNwInfo 1 }

allowedNwInfoEntry OBJECT-TYPE
    SYNTAX  AllowedNwInfoEntry
    MAX-ACCESS  not-accessible
    STATUS  current
    DESCRIPTION
        "A row in the allowed network information table.
	Note:This mib is not supported for VX instance of virtualization."
    INDEX   { allowedNwInfoIndex }
    ::= { allowedNwInfoTable 1 }

AllowedNwInfoEntry ::= SEQUENCE {
    allowedNwInfoIndex           Integer32,
    allowedNwInfoIpver           INTEGER,
    allowedNwInfoVlan            Integer32,
    allowedNwInfoBeginIpAddr     DisplayString,
    allowedNwInfoEndIpAddr       DisplayString,
    allowedNwInfoNetMask         DisplayString,
    allowedNwInfoIp6Prefix       Integer32
    }

allowedNwInfoIndex OBJECT-TYPE
    SYNTAX  Integer32
    MAX-ACCESS  read-only
    STATUS  current
    DESCRIPTION
        "The allowed network index.
         Note:This mib is not supported for VX instance of virtualization."
    ::= { allowedNwInfoEntry 1 }

allowedNwInfoIpver  OBJECT-TYPE
    SYNTAX   INTEGER {
        ipv4(1),
        ipv6(2),
        unsupported(2147483647)
        }
    MAX-ACCESS  read-only
    STATUS  current
    DESCRIPTION
        "The type of IP address.
	Note:This mib is not supported for VX instance of virtualization."
    ::= { allowedNwInfoEntry 2 }

allowedNwInfoVlan OBJECT-TYPE
    SYNTAX  Integer32
    MAX-ACCESS  read-only
    STATUS  current
    DESCRIPTION
        "The VLAN that the allowed network belongs to.
	Note:This mib is not supported for VX instance of virtualization."
    ::= { allowedNwInfoEntry 3 }

allowedNwInfoBeginIpAddr  OBJECT-TYPE
    SYNTAX   DisplayString
    MAX-ACCESS  read-only
    STATUS  current
    DESCRIPTION
        "The begin IP address of the allowed network.
	Note:This mib is not supported for VX instance of virtualization."
    ::= { allowedNwInfoEntry 4 }

allowedNwInfoEndIpAddr  OBJECT-TYPE
    SYNTAX   DisplayString
    MAX-ACCESS  read-only
    STATUS  current
    DESCRIPTION
        "The begin IP address of the allowed network.
	Note:This mib is not supported for VX instance of virtualization."
    ::= { allowedNwInfoEntry 5 }

allowedNwInfoNetMask OBJECT-TYPE
    SYNTAX   DisplayString
    MAX-ACCESS  read-only
    STATUS  current
    DESCRIPTION
        "The subnet mask of the allowed network.
	Note:This mib is not supported for VX instance of virtualization."
    ::= { allowedNwInfoEntry 6 }

allowedNwInfoIp6Prefix OBJECT-TYPE
    SYNTAX  Integer32
    MAX-ACCESS  read-only
    STATUS  current
    DESCRIPTION
        "The prefix length of the IP6 allowed network.
	Note:This mib is not supported for VX instance of virtualization."
    ::= { allowedNwInfoEntry 7 }

-- Ospfv3 Information

ospfv3GeneralInfo  OBJECT IDENTIFIER ::= { ospfv3info 1 }

ospfv3RouterID OBJECT-TYPE
    SYNTAX  IpAddress 
    MAX-ACCESS  read-only
    STATUS  current
    DESCRIPTION
        "The Router ID for ospfv3.
	Note:This mib is not supported for VX instance of virtualization."
    ::= { ospfv3GeneralInfo 1 }

ospfv3AdminState OBJECT-TYPE
    SYNTAX INTEGER {
        on(1),
        off(2),
        unsupported(2147483647)
        }
    MAX-ACCESS  read-only
    STATUS  current
    DESCRIPTION
        "Ospfv3 ena/dis state.
	Note:This mib is not supported for VX instance of virtualization."
    ::= { ospfv3GeneralInfo 2 }

ospfv3ASBRstatus OBJECT-TYPE
    SYNTAX INTEGER {
        on(1),
        off(2),
        unsupported(2147483647)
        }
    MAX-ACCESS  read-only
    STATUS  current
    DESCRIPTION
        "ASBR status for ospfv3.
	Note:This mib is not supported for VX instance of virtualization."
    ::= { ospfv3GeneralInfo 3 }

ospfv3ABRStatus OBJECT-TYPE
    SYNTAX INTEGER {
        on(1),
        off(2),
        unsupported(2147483647)
        }
    MAX-ACCESS  read-only
    STATUS  current
    DESCRIPTION
        "Ospfv3 ABR status.
	Note:This mib is not supported for VX instance of virtualization."
    ::= { ospfv3GeneralInfo 4 }

ospfv3ASscopeLSAcnt OBJECT-TYPE
    SYNTAX  Integer32
    MAX-ACCESS  read-only
    STATUS  current
    DESCRIPTION
        "Count for AS scope LSA.
	Note:This mib is not supported for VX instance of virtualization."
    ::= { ospfv3GeneralInfo 5 }

ospfv3RcvLSAcnt OBJECT-TYPE
    SYNTAX  Integer32
    MAX-ACCESS  read-only
    STATUS  current
    DESCRIPTION
        "Received LSA count for ospfv3.
	Note:This mib is not supported for VX instance of virtualization."
    ::= { ospfv3GeneralInfo 6 }

ospfv3NewLSAcnt OBJECT-TYPE
    SYNTAX  Integer32
    MAX-ACCESS  read-only
    STATUS  current
    DESCRIPTION
        "New LSA count for ospfv3.
	Note:This mib is not supported for VX instance of virtualization."
    ::= { ospfv3GeneralInfo 7 }

ospfv3MulticstExt OBJECT-TYPE
    SYNTAX  Integer32
    MAX-ACCESS  read-only
    STATUS  current
    DESCRIPTION
        "Multicast extentions for ospfv3.
	Note:This mib is not supported for VX instance of virtualization."
    ::= { ospfv3GeneralInfo 8 }

ospfv3AreaInfoTable OBJECT-TYPE
    SYNTAX SEQUENCE OF Ospfv3AreaInfoEntry
    MAX-ACCESS not-accessible
    STATUS current
    DESCRIPTION
      "The table of OSPFv3 Area information.
	Note:This mib is not supported for VX instance of virtualization."
    ::= { ospfv3info 2 }

ospfv3AreaInfoEntry OBJECT-TYPE
    SYNTAX Ospfv3AreaInfoEntry
    MAX-ACCESS not-accessible
    STATUS current
    DESCRIPTION
      "Information about a OSPFv3 area.
	Note:This mib is not supported for VX instance of virtualization."
    INDEX { ospfv3AreaInfoIndex }
    ::= { ospfv3AreaInfoTable 1 }
 
Ospfv3AreaInfoEntry ::= SEQUENCE {
    ospfv3AreaInfoIndex             Integer32,
    ospfv3AreaInfoID             IpAddress,
    ospfv3AreaInfoImportAsExtern   INTEGER,
    ospfv3AreaInfoSPF   	  Integer32,
    ospfv3AreaInfoABRs   	  Integer32,
    ospfv3AreaInfoASBRs  	          Integer32,
    ospfv3AreaInfoLSAS   	  Integer32,
    ospfv3AreaInfoSummary   	  Integer32,
    ospfv3AreaInfoStubMetric  	          Integer32,
    ospfv3AreaInfoAreaTableCounter   	  Integer32,
    ospfv3AreaInfoAreaLSDBTabletCounter          Integer32
    }

ospfv3AreaInfoIndex OBJECT-TYPE
    SYNTAX Integer32
    MAX-ACCESS read-only
    STATUS current
    DESCRIPTION
	"The OSPFv3 area number for which the OSPF info table is 
related.
	Note:This mib is not supported for VX instance of virtualization."
    ::= { ospfv3AreaInfoEntry 1}

ospfv3AreaInfoID OBJECT-TYPE
    SYNTAX IpAddress
    MAX-ACCESS read-only
    STATUS current
    DESCRIPTION
	"The IP address of the OSPFv3 area.
	Note:This mib is not supported for VX instance of virtualization." 
    ::= { ospfv3AreaInfoEntry 2}

ospfv3AreaInfoImportAsExtern   OBJECT-TYPE
        SYNTAX  INTEGER {
	importExternal(0),
	importNoExternal(1),
	importNssa(2),
        unsupported(2147483647)
	}
    MAX-ACCESS read-only
    STATUS current
    DESCRIPTION
	"The OSPFv3 area Import as Extern status.
	Note:This mib is not supported for VX instance of virtualization."
    ::= { ospfv3AreaInfoEntry 3}

ospfv3AreaInfoSPF   OBJECT-TYPE
    SYNTAX Integer32
    MAX-ACCESS read-only
    STATUS current
    DESCRIPTION
	"Number of SPF Runs.
	Note:This mib is not supported for VX instance of virtualization."
    ::= { ospfv3AreaInfoEntry 4}

ospfv3AreaInfoABRs   OBJECT-TYPE
    SYNTAX Integer32
    MAX-ACCESS read-only
    STATUS current
    DESCRIPTION
	"Number of Reachable ABRs.
	Note:This mib is not supported for VX instance of virtualization."
    ::= { ospfv3AreaInfoEntry 5}

ospfv3AreaInfoASBRs  OBJECT-TYPE
    SYNTAX Integer32
    MAX-ACCESS read-only
    STATUS current
    DESCRIPTION
	"Number of Reachable ASBRs.
	Note:This mib is not supported for VX instance of virtualization."
    ::= { ospfv3AreaInfoEntry 6}

ospfv3AreaInfoLSAS   OBJECT-TYPE
    SYNTAX Integer32
    MAX-ACCESS read-only
    STATUS current
    DESCRIPTION
	"Number of Area Scope LSAs.
	Note:This mib is not supported for VX instance of virtualization."
    ::= { ospfv3AreaInfoEntry 7}

ospfv3AreaInfoSummary   OBJECT-TYPE
    SYNTAX Integer32
    MAX-ACCESS read-only
    STATUS current
    DESCRIPTION
	"Area Summary.
	Note:This mib is not supported for VX instance of virtualization."
    ::= { ospfv3AreaInfoEntry 8}

ospfv3AreaInfoStubMetric  OBJECT-TYPE
    SYNTAX Integer32
    MAX-ACCESS read-only
    STATUS current
    DESCRIPTION
	"Stub Metric.
	Note:This mib is not supported for VX instance of virtualization."
    ::= { ospfv3AreaInfoEntry 9}

ospfv3AreaInfoAreaTableCounter   OBJECT-TYPE
    SYNTAX Integer32
    MAX-ACCESS read-only
    STATUS current
    DESCRIPTION
	"Area Table counter .
	Note:This mib is not supported for VX instance of virtualization."
    ::= { ospfv3AreaInfoEntry 10}

ospfv3AreaInfoAreaLSDBTabletCounter        OBJECT-TYPE
    SYNTAX Integer32
    MAX-ACCESS read-only
    STATUS current
    DESCRIPTION
	"Area Table counter .
	Note:This mib is not supported for VX instance of virtualization."
    ::= { ospfv3AreaInfoEntry 11}

 ospfv3IfInfoTable OBJECT-TYPE
     SYNTAX SEQUENCE OF Ospfv3IfInfoEntry
     MAX-ACCESS not-accessible
     STATUS current
     DESCRIPTION
       "The table of OSPFv3 Interface information.
	Note:This mib is not supported for VX instance of virtualization."
     ::= { ospfv3info 3 }

 ospfv3IfInfoEntry OBJECT-TYPE
     SYNTAX Ospfv3IfInfoEntry
     MAX-ACCESS not-accessible
     STATUS current
     DESCRIPTION
       "Information about a OSPFv3 Interface.
	Note:This mib is not supported for VX instance of virtualization."
     INDEX { ospfv3IfInfoIndex }
     ::= { ospfv3IfInfoTable 1 }

 Ospfv3IfInfoEntry ::= SEQUENCE {
     ospfv3IfInfoIndex             Integer32,
     ospfv3IfInfoVlan             Integer32,
     ospfv3IfInfoAreaID             IpAddress,
     ospfv3IfInfoAdminStat   INTEGER,
     ospfv3IfInfoPrio           Integer32,
     ospfv3IfInfoTransitDelay          Integer32,
     ospfv3IfInfoRetransInterval                 Integer32,
     ospfv3IfInfoRtrDeadInterval          Integer32,
     ospfv3IfInfoHelloInterval       Integer32,
     ospfv3IfInfoPollInterval                    Integer32,
     ospfv3IfInfoCost      Integer32,
     ospfv3IfInfoDrid          IpAddress,
     ospfv3IfInfoBdrid          IpAddress,
     ospfv3IfInfoIfState          INTEGER
     }

 ospfv3IfInfoIndex OBJECT-TYPE
     SYNTAX Integer32
     MAX-ACCESS read-only
     STATUS current
     DESCRIPTION
       "The OSPFv3 interface number for which the OSPF info table is related.
	Note:This mib is not supported for VX instance of virtualization."
     ::= { ospfv3IfInfoEntry 1}

 ospfv3IfInfoVlan OBJECT-TYPE
     SYNTAX Integer32
     MAX-ACCESS read-only
     STATUS current
     DESCRIPTION
       "The OSPFv3 interface VLAN for which the OSPF info table is related.
	Note:This mib is not supported for VX instance of virtualization."
     ::= { ospfv3IfInfoEntry 2}

 ospfv3IfInfoAreaID OBJECT-TYPE
     SYNTAX IpAddress
     MAX-ACCESS read-only
     STATUS current
     DESCRIPTION
       "The IP address of the OSPFv3 info .
	Note:This mib is not supported for VX instance of virtualization."
     ::= { ospfv3IfInfoEntry 3}

 ospfv3IfInfoAdminStat   OBJECT-TYPE
         SYNTAX  INTEGER {
       enabled(1),
       disabled(2),
       unsupported(2147483647)
       }
     MAX-ACCESS read-only
     STATUS current
     DESCRIPTION
       "The OSPFv3 Info admin state.
	Note:This mib is not supported for VX instance of virtualization."
     ::= { ospfv3IfInfoEntry 4}

 ospfv3IfInfoPrio OBJECT-TYPE
     SYNTAX Integer32
     MAX-ACCESS read-only
     STATUS current
     DESCRIPTION
       "The OSPFv3 interface priority.
	Note:This mib is not supported for VX instance of virtualization."
     ::= { ospfv3IfInfoEntry 5}
     
 ospfv3IfInfoTransitDelay OBJECT-TYPE
     SYNTAX Integer32
     MAX-ACCESS read-only
     STATUS current
     DESCRIPTION
       "The OSPFv3 interface transit delay .
	Note:This mib is not supported for VX instance of virtualization."
     ::= { ospfv3IfInfoEntry 6}
     
 ospfv3IfInfoRetransInterval OBJECT-TYPE
     SYNTAX Integer32
     MAX-ACCESS read-only
     STATUS current
     DESCRIPTION
       "The OSPFv3 interface retransit interval.
	Note:This mib is not supported for VX instance of virtualization."
     ::= { ospfv3IfInfoEntry 7}     

 ospfv3IfInfoRtrDeadInterval OBJECT-TYPE
     SYNTAX Integer32
     MAX-ACCESS read-only
     STATUS current
     DESCRIPTION
       "The OSPFv3 interface dead interval .
	Note:This mib is not supported for VX instance of virtualization."
     ::= { ospfv3IfInfoEntry 8}
     
 ospfv3IfInfoHelloInterval OBJECT-TYPE
     SYNTAX Integer32
     MAX-ACCESS read-only
     STATUS current
     DESCRIPTION
       "The OSPFv3 interface hello interval.
	Note:This mib is not supported for VX instance of virtualization."
     ::= { ospfv3IfInfoEntry 9}     

 ospfv3IfInfoPollInterval OBJECT-TYPE
     SYNTAX Integer32
     MAX-ACCESS read-only
     STATUS current
     DESCRIPTION
       "The OSPFv3 interface poll interval .
	Note:This mib is not supported for VX instance of virtualization."
     ::= { ospfv3IfInfoEntry 10}
     
 ospfv3IfInfoCost OBJECT-TYPE
     SYNTAX Integer32
     MAX-ACCESS read-only
     STATUS current
     DESCRIPTION
       "The OSPFv3 interface cost.
	Note:This mib is not supported for VX instance of virtualization."
     ::= { ospfv3IfInfoEntry 11}     

 ospfv3IfInfoDrid OBJECT-TYPE
     SYNTAX IpAddress
     MAX-ACCESS read-only
     STATUS current
     DESCRIPTION
       "The OSPFv3 interface cost.
	Note:This mib is not supported for VX instance of virtualization."
     ::= { ospfv3IfInfoEntry 12}     

 ospfv3IfInfoBdrid OBJECT-TYPE
     SYNTAX IpAddress
     MAX-ACCESS read-only
     STATUS current
     DESCRIPTION
       "The OSPFv3 interface cost.
	Note:This mib is not supported for VX instance of virtualization."
     ::= { ospfv3IfInfoEntry 13}       

 ospfv3IfInfoIfState   OBJECT-TYPE
         SYNTAX  INTEGER {
	     unkn(0),
	     down(1),
	     lpbk(2),
	     wtng(3),
	     ppp (4),
	     dr  (5),
	     bdr(6),
	     other(7),
             unsupported(2147483647)
       }
     MAX-ACCESS read-only
     STATUS current
     DESCRIPTION
       "The OSPFv3 Info interface state.
	Note:This mib is not supported for VX instance of virtualization."
     ::= { ospfv3IfInfoEntry 14}

-- OSPFv3 Interface/Nbr Info Table

ospfv3IfNbrTable OBJECT-TYPE
        SYNTAX SEQUENCE OF Ospfv3IfNbrEntry
        MAX-ACCESS not-accessible
        STATUS current
        DESCRIPTION
          "The table of OSPFv3 Interface Neighbour information.
	Note:This mib is not supported for VX instance of virtualization."
        ::= { ospfv3info 4 }

ospfv3IfNbrEntry OBJECT-TYPE
        SYNTAX Ospfv3IfNbrEntry
        MAX-ACCESS not-accessible
        STATUS current
        DESCRIPTION
          "Information about a OSPFv3 interface, neighbour pair.
	Note:This mib is not supported for VX instance of virtualization."
        INDEX { ospfv3IfNbrVlanID, ospfv3IfNbrIpAddr }
        ::= { ospfv3IfNbrTable 1 }

Ospfv3IfNbrEntry ::= SEQUENCE {
    	ospfv3IfNbrVlanID                    	 Integer32,
        ospfv3IfNbrIpAddr                        IpAddress,
        ospfv3IfNbrAddr                          DisplayString,
        ospfv3IfNbrAreaID                        IpAddress,
        ospfv3IfNbrIntfIndex                     Integer32,
	ospfv3IfNbrOption                   	 Integer32,
        ospfv3IfNbrPriority                      Integer32,
        ospfv3IfNbrState                         INTEGER,
        ospfv3IfNbrNo    			 Integer32
        }

ospfv3IfNbrVlanID OBJECT-TYPE
    SYNTAX Integer32
    MAX-ACCESS read-only
    STATUS current
    DESCRIPTION
        "The VlanID to which the OSPFv3 neighbour is associated.
	Note:This mib is not supported for VX instance of virtualization."
    ::= { ospfv3IfNbrEntry 1 }

ospfv3IfNbrIpAddr OBJECT-TYPE
    SYNTAX IpAddress
    MAX-ACCESS read-only
    STATUS current
    DESCRIPTION
        "The OSPFv3 Neighbour ID .
	Note:This mib is not supported for VX instance of virtualization."
    ::= { ospfv3IfNbrEntry 2 }

ospfv3IfNbrAddr OBJECT-TYPE
    SYNTAX DisplayString
    MAX-ACCESS read-only
    STATUS current
    DESCRIPTION
        "The IPv6 address of the neighbor associated with
                the local link.
	Note:This mib is not supported for VX instance of virtualization."
    ::= { ospfv3IfNbrEntry 3 }

ospfv3IfNbrAreaID OBJECT-TYPE
    SYNTAX IpAddress 
    MAX-ACCESS read-only
    STATUS current
    DESCRIPTION
        "The area ID of the OSPFv3 neighbour.
	Note:This mib is not supported for VX instance of virtualization."
    ::= { ospfv3IfNbrEntry 4 }

ospfv3IfNbrIntfIndex OBJECT-TYPE
    SYNTAX Integer32
    MAX-ACCESS read-only
    STATUS current
    DESCRIPTION
        "The OSPFv3 Interface number for which this Interface/Nbr table is
         related.
	Note:This mib is not supported for VX instance of virtualization."
    ::= { ospfv3IfNbrEntry 5}

ospfv3IfNbrOption OBJECT-TYPE
    SYNTAX Integer32
    MAX-ACCESS read-only
    STATUS current
    DESCRIPTION
        "A bit mask corresponding to the neighbor's
                options field.
	Note:This mib is not supported for VX instance of virtualization."
    ::= { ospfv3IfNbrEntry 6 }

ospfv3IfNbrPriority OBJECT-TYPE
    SYNTAX Integer32
    MAX-ACCESS read-only
    STATUS current
    DESCRIPTION
        "The priority of the OSPFv3 neighbour.
	Note:This mib is not supported for VX instance of virtualization."
    ::= { ospfv3IfNbrEntry 7 }

ospfv3IfNbrState OBJECT-TYPE
    SYNTAX  INTEGER {
        down(1),
        attempt(2),
        init(3),
        twoway(4),
        exStart(5),
        exchange(6),
        loading(7),
        full(8),
        unsupported(2147483647)
        }
        MAX-ACCESS read-only
        STATUS current
        DESCRIPTION
                "The state of the OSPFv3 neighbour.
                Note:This mib is not supported for VX instance of virtualization."
        ::= { ospfv3IfNbrEntry 8 }

ospfv3IfNbrNo OBJECT-TYPE
        SYNTAX Integer32
        MAX-ACCESS read-only
        STATUS current
        DESCRIPTION
                "Number of OSPFv3 Neighbour.
                Note:This mib is not supported for VX instance of virtualization."
        ::= { ospfv3IfNbrEntry 9 }

-- HA Informations

haServiceInfo  OBJECT IDENTIFIER ::= { haInfo 1 }

haServiceInfoTable OBJECT-TYPE
    SYNTAX  SEQUENCE OF HaServiceInfoEntry
    MAX-ACCESS  not-accessible
    STATUS  current
    DESCRIPTION
        "The table of HA Service informations.
	Note:This mib is not supported for VX instance of virtualization."
    ::= { haServiceInfo 1 }

haServiceInfoEntry OBJECT-TYPE
    SYNTAX  HaServiceInfoEntry
    MAX-ACCESS  not-accessible
    STATUS  current
    DESCRIPTION
        "Information about a particular HA Service.
	Note:This mib is not supported for VX instance of virtualization."
    INDEX   { haServiceInfoIndex }
    ::= { haServiceInfoTable 1 }

HaServiceInfoEntry ::= SEQUENCE {
    haServiceInfoIndex           DisplayString,
    haServiceInfoState           INTEGER,
    haGroupInfoState		 DisplayString
}

haServiceInfoIndex OBJECT-TYPE
    SYNTAX DisplayString (SIZE(1..32))
    MAX-ACCESS  read-only
    STATUS  current
    DESCRIPTION
        "The service index in alphanumeric.
	Note:This mib is not supported for VX instance of virtualization."
    ::= { haServiceInfoEntry 1 }

haServiceInfoState OBJECT-TYPE
    SYNTAX  INTEGER {
        enabled(1),
        disabled(2),
        unsupported(2147483647)
        }
    MAX-ACCESS  read-only
    STATUS  current
    DESCRIPTION
            "Enable/disable HA service group.
	Note:This mib is not supported for VX instance of virtualization."
    ::= { haServiceInfoEntry 2 }

haGroupInfoState OBJECT-TYPE
    SYNTAX  DisplayString
    MAX-ACCESS  read-only
    STATUS  current
    DESCRIPTION
        "The HA service group state Init/Backup/Master/Holdoff.
	Note:This mib is not supported for VX instance of virtualization."
    ::= { haServiceInfoEntry 3 }

-- HA Switch Info
haSwitchInfo  OBJECT IDENTIFIER ::= { haInfo 2 }

haSwitchInfoState OBJECT-TYPE 
    SYNTAX  DisplayString
    MAX-ACCESS  read-only
    STATUS  current
    DESCRIPTION
        "The HA switch state Init/Backup/Master/Holdoff.
	Note:This mib is not supported for VX instance of virtualization."
    ::= {  haSwitchInfo 1 }

-- HA command menu

haCurCfgMode OBJECT-TYPE
    SYNTAX  INTEGER {
        disabled(1),
        vrrp(2),
        switch(3),
        service(4),
	extendedHA(5),
        unsupported(2147483647)
        }
    MAX-ACCESS  read-only
    STATUS  current
    DESCRIPTION
        "The high availability mode.
	Note:This mib is not supported for VX instance of virtualization."
    ::= { haCfg 1 }

haNewCfgMode OBJECT-TYPE
    SYNTAX  INTEGER {
        disabled(1),
        vrrp(2),
        switch(3),
        service(4),
	extendedHA(5),
        unsupported(2147483647)
        }
    MAX-ACCESS  read-write
    STATUS  current
    DESCRIPTION
        "The high availability mode.
	Note:This mib is not supported for VX instance of virtualization."
    ::= { haCfg 2 }

haCurCfgHoldoffTime OBJECT-TYPE
    SYNTAX  INTEGER (0..255)
    MAX-ACCESS  read-only
    STATUS  current
    DESCRIPTION
        "The holdoff time.
	Note:This mib is not supported for VX instance of virtualization."
    ::= { haCfg 3 }

haNewCfgHoldoffTime OBJECT-TYPE
    SYNTAX  INTEGER (0..255)
    MAX-ACCESS  read-write
    STATUS  current
    DESCRIPTION
        "The holdoff time.
	Note:This mib is not supported for VX instance of virtualization."
    ::= { haCfg 4 }

-- HA Switch menu

haSwitch       OBJECT IDENTIFIER ::= { haCfg 5 }

haSwitchCurCfgPref OBJECT-TYPE
    SYNTAX  INTEGER {
        active(1),
        standby(2),
        unsupported(2147483647)
        }
    MAX-ACCESS  read-only
    STATUS  current
    DESCRIPTION
        "The preferred initial state.
	Note:This mib is not supported for VX instance of virtualization."
    ::= { haSwitch 1 }

haSwitchNewCfgPref OBJECT-TYPE
    SYNTAX  INTEGER {
        active(1),
        standby(2),
        unsupported(2147483647)
        }
    MAX-ACCESS  read-write
    STATUS  current
    DESCRIPTION
        "The preferred initial state.
	Note:This mib is not supported for VX instance of virtualization."
    ::= { haSwitch 2 }
    
    
haSwitchCurCfgFailBackMode OBJECT-TYPE
    SYNTAX  INTEGER {
        onfailure(1),
        always(2),
        unsupported(2147483647)
        }
    MAX-ACCESS  read-only
    STATUS  current
    DESCRIPTION
            "The fail back mode.
	Note:This mib is not supported for VX instance of virtualization."
    ::= { haSwitch 3 }
    
haSwitchNewCfgFailBackMode OBJECT-TYPE
    SYNTAX  INTEGER {
            onfailure(1),
            always(2),
            unsupported(2147483647)
            }
    MAX-ACCESS  read-write
    STATUS  current
    DESCRIPTION
            "The fail back mode.
	Note:This mib is not supported for VX instance of virtualization."
    ::= { haSwitch 4 }

haSwitchCurCfgAdvIfsMapList OBJECT-TYPE
    SYNTAX OCTET STRING
    MAX-ACCESS read-only
    STATUS current
    DESCRIPTION
        "The advertisement interfaces present in the out map list.
         The advertisement interfaces maps are presented in a bitmap format.

         in receiving order:

         OCTET 1  OCTET 2  .....
         xxxxxxxx xxxxxxxx .....
         ||    || |_ Ifmap 9
         ||    ||
         ||    ||___ Ifmap 8
         ||    |____ Ifmap 7
         ||      .    .   .
         ||_________ Ifmap 2
         |__________ Ifmap 1

         where x : 1 - The represented advertisement interface map is selected
         0 - The represented advertisement interface map is not selected.
	Note:This mib is not supported for VX instance of virtualization."
    ::= {  haSwitch 5 }

haSwitchNewCfgAdvIfsMapList OBJECT-TYPE
    SYNTAX OCTET STRING
    MAX-ACCESS read-only
    STATUS current
    DESCRIPTION
        "The advertisement interfaces present in the out map list.
         The advertisement interfaces maps are presented in a bitmap format.

         in receiving order:

         OCTET 1  OCTET 2  .....
         xxxxxxxx xxxxxxxx .....
         ||    || |_ Ifmap 9
         ||    ||
         ||    ||___ Ifmap 8
         ||    |____ Ifmap 7
         ||      .    .   .
         ||_________ Ifmap 2
         |__________ Ifmap 1

         where x : 1 - The represented advertisement interfaces map is selected
         0 - The represented advertisement interfaces map is not selected.
	Note:This mib is not supported for VX instance of virtualization."
    ::= {  haSwitch 6 }

haSwitchNewCfgAddIf OBJECT-TYPE
    SYNTAX  INTEGER (1..256)
    MAX-ACCESS  read-write
    STATUS  current
    DESCRIPTION
             "Add interface for HA communication between the devices.
	Note:This mib is not supported for VX instance of virtualization."
    ::= { haSwitch 7 }

haSwitchNewCfgRemIf OBJECT-TYPE
    SYNTAX  INTEGER (1..256)
    MAX-ACCESS  read-write
    STATUS  current
    DESCRIPTION
             "Remove interface for HA communication between the devices.
	Note:This mib is not supported for VX instance of virtualization."
        ::= { haSwitch 8 }        
        
haSwitchCurCfgAdver OBJECT-TYPE
    SYNTAX  INTEGER (1..255)
    MAX-ACCESS  read-only
    STATUS  current
    DESCRIPTION
            "The advertisement Interval.
	Note:This mib is not supported for VX instance of virtualization."
    ::= { haSwitch 9 }

haSwitchNewCfgAdver OBJECT-TYPE
    SYNTAX  INTEGER (1..255)
    MAX-ACCESS  read-write
    STATUS  current
    DESCRIPTION
             "The advertisement Interval.
	Note:This mib is not supported for VX instance of virtualization."
    ::= { haSwitch 10 } 
     

haSwitchCurCfgOrder OBJECT-TYPE
    SYNTAX  INTEGER (0..255)
    MAX-ACCESS  read-only
    STATUS  current
    DESCRIPTION
            "The failover order group.
	Note:This mib is not supported for VX instance of virtualization."
    ::= { haSwitch 12 }

haSwitchNewCfgOrder OBJECT-TYPE
    SYNTAX  INTEGER (0..255)
    MAX-ACCESS  read-write
    STATUS  current
    DESCRIPTION
             "The failover order group.
	Note:This mib is not supported for VX instance of virtualization."
    ::= { haSwitch 13 }       

-- HA Trigger menu

haTrigger       OBJECT IDENTIFIER ::= { haSwitch 11 }

        
haSwitchCurCfgTriggerl4Reals OBJECT-TYPE
    SYNTAX  INTEGER {
               enabled(1),
               disabled(2),
               unsupported(2147483647)
            }
    MAX-ACCESS  read-only
    STATUS  current
    DESCRIPTION
            "Enable or disable tracking L4 real servers.
	Note:This mib is not supported for VX instance of virtualization."
    ::= { haTrigger 1 }
haSwitchNewCfgTriggerl4Reals OBJECT-TYPE
    SYNTAX  INTEGER {
              enabled(1),
              disabled(2),
              unsupported(2147483647)
            }
    MAX-ACCESS  read-write
    STATUS  current
    DESCRIPTION
             "Enable or disable tracking L4 real servers.
	Note:This mib is not supported for VX instance of virtualization."
    ::= { haTrigger 2 }          

-- HA Trigger Ifs menu

haTriggerIfs       OBJECT IDENTIFIER ::= { haTrigger 3 }

haSwitchNewCfgTrigIfTrackAdd OBJECT-TYPE
    SYNTAX  INTEGER (1..256)
    MAX-ACCESS  read-write
    STATUS  current
    DESCRIPTION
             "Add interface to tracking list.
	Note:This mib is not supported for VX instance of virtualization."
    ::= { haTriggerIfs 1 }

haSwitchNewCfgTrigIfTrackExclude OBJECT-TYPE
    SYNTAX  INTEGER (1..256)
    MAX-ACCESS  read-write
    STATUS  current
    DESCRIPTION
             "Exclude interface from tracking list.
	Note:This mib is not supported for VX instance of virtualization."
    ::= { haTriggerIfs 2 }

haSwitchCurCfgTrackIfsMapList OBJECT-TYPE
    SYNTAX OCTET STRING
    MAX-ACCESS read-only
    STATUS current
    DESCRIPTION
        "The tracking interfaces present in the out map list.
         The tracking interfaces maps are presented in a bitmap format.

         in receiving order:

         OCTET 1  OCTET 2  .....
         xxxxxxxx xxxxxxxx .....
         ||    || |_ Ifmap 9
         ||    ||
         ||    ||___ Ifmap 8
         ||    |____ Ifmap 7
         ||      .    .   .
         ||_________ Ifmap 2
         |__________ Ifmap 1

         where x : 1 - The represented tracking interfaces map is selected
         0 - The represented tracking interfaces map is not selected.
	Note:This mib is not supported for VX instance of virtualization."
    ::= {  haTriggerIfs 3 }

haSwitchNewCfgTrackIfsMapList OBJECT-TYPE
    SYNTAX OCTET STRING
    MAX-ACCESS read-only
    STATUS current
    DESCRIPTION
        "The tracking interfaces present in the out map list.
         The tracking interfaces maps are presented in a bitmap format.

         in receiving order:

         OCTET 1  OCTET 2  .....
         xxxxxxxx xxxxxxxx .....
         ||    || |_ Ifmap 9
         ||    ||
         ||    ||___ Ifmap 8
         ||    |____ Ifmap 7
         ||      .    .   .
         ||_________ Ifmap 2
         |__________ Ifmap 1

         where x : 1 - The represented tracking interface map is selected
         0 - The represented tracking interface map is not selected.
	Note:This mib is not supported for VX instance of virtualization."
    ::= {  haTriggerIfs 4 }


-- HA for Azure

haAzure       OBJECT IDENTIFIER ::= { haSwitch 14 }

-- HA Floating NIC Table (current)

haAzureCurCfgNicTable OBJECT-TYPE
    SYNTAX  SEQUENCE OF HaAzureCurCfgNicEntry
    MAX-ACCESS  not-accessible
    STATUS  current
    DESCRIPTION
        "The table of Floating NICs configurations.
        Note:This mib is only supported for VA instance."
    ::= { haAzure 1 }

haAzureCurCfgNicEntry OBJECT-TYPE
    SYNTAX  HaAzureCurCfgNicEntry
    MAX-ACCESS  not-accessible
    STATUS  current
    DESCRIPTION
        "Information about a particular Floating NIC configuration.
        Note:This mib is only supported for VA instance."
    INDEX   { haAzureCurCfgNicIndex }
    ::= { haAzureCurCfgNicTable 1 }

HaAzureCurCfgNicEntry ::= SEQUENCE {
    haAzureCurCfgNicIndex          DisplayString,
    haAzureCurCfgNicPeerId         DisplayString
}

haAzureCurCfgNicIndex OBJECT-TYPE
    SYNTAX DisplayString (SIZE(1..80))
    MAX-ACCESS  read-only
    STATUS  current
    DESCRIPTION
        "The floating NIC ID.
        Note:This mib is only supported for VA instance."
    ::= { haAzureCurCfgNicEntry 1 }

haAzureCurCfgNicPeerId OBJECT-TYPE
    SYNTAX DisplayString (SIZE(1..80))
    MAX-ACCESS  read-only
    STATUS  current
    DESCRIPTION
        "The floating peer's NIC ID.
        Note:This mib is only supported for VA instance."
    ::= { haAzureCurCfgNicEntry 2 }      
        
-- HA Floating NIC Table (new)
        
haAzureNewCfgNicTable OBJECT-TYPE
    SYNTAX  SEQUENCE OF HaAzureNewCfgNicEntry
    MAX-ACCESS  not-accessible
    STATUS  current
    DESCRIPTION
        "The table of Floating NIC configurations.
        Note:This mib is only supported for VA instance."
    ::= { haAzure 2 }

haAzureNewCfgNicEntry OBJECT-TYPE
    SYNTAX  HaAzureNewCfgNicEntry
    MAX-ACCESS  not-accessible
    STATUS  current
    DESCRIPTION
        "Information about a particular Floating NIC configuration.
        Note:This mib is only supported for VA instance."
    INDEX   { haAzureNewCfgNicIndex }
    ::= { haAzureNewCfgNicTable 1 }

HaAzureNewCfgNicEntry ::= SEQUENCE {
    haAzureNewCfgNicIndex           DisplayString,
    haAzureNewCfgNicPeerId          DisplayString,
    haAzureNewCfgNicDelete          INTEGER
}

haAzureNewCfgNicIndex OBJECT-TYPE
    SYNTAX DisplayString (SIZE(1..80))
    MAX-ACCESS  read-only
    STATUS  current
    DESCRIPTION
        "The floating NIC ID.
        Note:This mib is only supported for VA instance."
    ::= { haAzureNewCfgNicEntry 1 }

haAzureNewCfgNicPeerId OBJECT-TYPE
    SYNTAX DisplayString (SIZE(1..80))
    MAX-ACCESS  read-create
    STATUS  current
    DESCRIPTION
        "The floating peer's NIC ID.
        Note:This mib is only supported for VA instance."
    ::= { haAzureNewCfgNicEntry 2 }

haAzureNewCfgNicDelete OBJECT-TYPE
    SYNTAX  INTEGER {
        other(1),
        delete(2),
        unsupported(2147483647)
        }
    MAX-ACCESS  read-create
    STATUS  current
    DESCRIPTION
        "By setting the value to delete(2), the entire NIC object is deleted.
        Note:This mib is only supported for VA instance."
    ::= { haAzureNewCfgNicEntry 3 }

-- HA Floating NIC IPs Table (current)

haAzureCurCfgNicIpsTable OBJECT-TYPE
    SYNTAX  SEQUENCE OF HaAzureCurCfgNicIpsEntry
    MAX-ACCESS  not-accessible
    STATUS  current
    DESCRIPTION
        "The table of Floating NIC IPs configurations.
        Note:This mib is only supported for VA instance."
    ::= { haAzure 3 }

haAzureCurCfgNicIpsEntry OBJECT-TYPE
    SYNTAX  HaAzureCurCfgNicIpsEntry
    MAX-ACCESS  not-accessible
    STATUS  current
    DESCRIPTION
        "Information about a particular Floating NIC's IPs list configuration.
        Note:This mib is only supported for VA instance."
    INDEX   { haAzureCurCfgNicIdIndex, haAzureCurCfgNicIpIndex }
    ::= { haAzureCurCfgNicIpsTable 1 }

HaAzureCurCfgNicIpsEntry ::= SEQUENCE {
    haAzureCurCfgNicIdIndex        DisplayString,
    haAzureCurCfgNicIpIndex        Integer32,
    haAzureCurCfgNicIpAddress      IpAddress
}

haAzureCurCfgNicIdIndex OBJECT-TYPE
    SYNTAX DisplayString (SIZE(1..80))
    MAX-ACCESS  read-only
    STATUS  current
    DESCRIPTION
        "The floating NIC ID.
        Note:This mib is only supported for VA instance."
    ::= { haAzureCurCfgNicIpsEntry 1 }

haAzureCurCfgNicIpIndex OBJECT-TYPE
    SYNTAX  Integer32
    MAX-ACCESS  read-only
    STATUS  current
    DESCRIPTION
        "The floating NIC IP index.
        Note:This mib is only supported for VA instance."
    ::= { haAzureCurCfgNicIpsEntry 2 }

haAzureCurCfgNicIpAddress OBJECT-TYPE
    SYNTAX  IpAddress
    MAX-ACCESS  read-only
    STATUS  current
    DESCRIPTION
        "The floating NIC IP Adress.
        Note:This mib is only supported for VA instance."
    ::= { haAzureCurCfgNicIpsEntry 3 }

-- HA Floating NIC IPs Table (new)
        
haAzureNewCfgNicIpsTable OBJECT-TYPE
    SYNTAX  SEQUENCE OF HaAzureNewCfgNicIpsEntry
    MAX-ACCESS  not-accessible
    STATUS  current
    DESCRIPTION
        "The table of Floating NIC IPs configurations.
        Note:This mib is only supported for VA instance."
    ::= { haAzure 4 }

haAzureNewCfgNicIpsEntry OBJECT-TYPE
    SYNTAX  HaAzureNewCfgNicIpsEntry
    MAX-ACCESS  not-accessible
    STATUS  current
    DESCRIPTION
        "Information about a particular Floating NIC configuration.
        Note:This mib is only supported for VA instance."
    INDEX   { haAzureNewCfgNicIdIndex, haAzureNewCfgNicIpIndex }
    ::= { haAzureNewCfgNicIpsTable 1 }

HaAzureNewCfgNicIpsEntry ::= SEQUENCE {
    haAzureNewCfgNicIdIndex           DisplayString,
    haAzureNewCfgNicIpIndex           Integer32,
    haAzureNewCfgNicIpAddress         IpAddress,
    haAzureNewCfgNicIpDelete          INTEGER
}

haAzureNewCfgNicIdIndex OBJECT-TYPE
    SYNTAX DisplayString (SIZE(1..80))
    MAX-ACCESS  read-only
    STATUS  current
    DESCRIPTION
        "The floating NIC ID.
        Note:This mib is only supported for VA instance."
    ::= { haAzureNewCfgNicIpsEntry 1 }

haAzureNewCfgNicIpIndex OBJECT-TYPE
    SYNTAX  Integer32
    MAX-ACCESS  read-only
    STATUS  current
    DESCRIPTION
        "The floating NIC IP index.
        Note:This mib is only supported for VA instance."
    ::= { haAzureNewCfgNicIpsEntry 2 }

haAzureNewCfgNicIpAddress OBJECT-TYPE
    SYNTAX  IpAddress
    MAX-ACCESS  read-create
    STATUS  current
    DESCRIPTION
        "The floating NIC IP Adress.
        Note:This mib is only supported for VA instance."
    ::= { haAzureNewCfgNicIpsEntry 3 }

haAzureNewCfgNicIpDelete OBJECT-TYPE
    SYNTAX  INTEGER {
        other(1),
        delete(2),
        unsupported(2147483647)
        }
    MAX-ACCESS  read-create
    STATUS  current
    DESCRIPTION
        "By setting the value to delete(2), the IP is deleted.
        Note:This mib is only supported for VA instance."
    ::= { haAzureNewCfgNicIpsEntry 4 }


-- HA Gateway track menu

haGwTrack       OBJECT IDENTIFIER ::= { haTrigger 4 }

haSwitchCurCfgTrigGwTrackState OBJECT-TYPE
    SYNTAX  INTEGER {
               enabled(1),
               disabled(2),
               unsupported(2147483647)
            }
    MAX-ACCESS  read-only
    STATUS  current
    DESCRIPTION
            "Enable or disable gateway tracking.
	Note:This mib is not supported for VX instance of virtualization."
    ::= { haGwTrack 1 }

haSwitchNewCfgTrigGwTrackState OBJECT-TYPE
    SYNTAX  INTEGER {
              enabled(1),
              disabled(2),
              unsupported(2147483647)
            }
    MAX-ACCESS  read-write
    STATUS  current
    DESCRIPTION
             "Enable or disable gateway tracking.
	Note:This mib is not supported for VX instance of virtualization."
    ::= { haGwTrack 2 } 
        
haSwitchNewCfgTrigGwTrackAdd OBJECT-TYPE
    SYNTAX  INTEGER (1..259)
    MAX-ACCESS  read-write
    STATUS  current
    DESCRIPTION
             "Add gateway to tracking list.
	Note:This mib is not supported for VX instance of virtualization."
    ::= { haGwTrack 3 }    
        
haSwitchNewCfgTrigGwTrackExclude OBJECT-TYPE
    SYNTAX  INTEGER (1..259)
    MAX-ACCESS  read-write
    STATUS  current
    DESCRIPTION
             "Exclude gateway to tracking list.
	Note:This mib is not supported for VX instance of virtualization."
    ::= { haGwTrack 4 }   

haSwitchCurCfgTrackGwsMapList OBJECT-TYPE
    SYNTAX OCTET STRING
    MAX-ACCESS read-only
    STATUS current
    DESCRIPTION
        "The tracking gateways present in the out map list.
         The tracking gateways maps are presented in a bitmap format.

         in receiving order:

         OCTET 1  OCTET 2  .....
         xxxxxxxx xxxxxxxx .....
         ||    || |_ Gwmap 9
         ||    ||
         ||    ||___ Gwmap 8
         ||    |____ Gwmap 7
         ||      .    .   .
         ||_________ Gwmap 2
         |__________ Gwmap 1

         where x : 1 - The represented tracking gateways is selected
         0 - The represented tracking gateways map is not selected.
	Note:This mib is not supported for VX instance of virtualization."
    ::= {  haGwTrack 5 }

haSwitchNewCfgTrackGwsMapList OBJECT-TYPE
    SYNTAX OCTET STRING
    MAX-ACCESS read-only
    STATUS current
    DESCRIPTION
        "The tracking gateways present in the out map list.
         The tracking gateways maps are presented in a bitmap format.

         in receiving order:

         OCTET 1  OCTET 2  .....
         xxxxxxxx xxxxxxxx .....
         ||    || |_ Gwmap 9
         ||    ||
         ||    ||___ Gwmap 8
         ||    |____ Gwmap 7
         ||      .    .   .
         ||_________ Gwmap 2
         |__________ Gwmap 1

         where x : 1 - The represented tracking gateways map is selected
         0 - The represented tracking gateways map is not selected.
	Note:This mib is not supported for VX instance of virtualization."
    ::= {  haGwTrack 6 }

-- HA Switch Real track menu

haTriggerReals       OBJECT IDENTIFIER ::= { haTrigger 5 }

haSwitchCurCfgTriggerNewl4Reals OBJECT-TYPE
    SYNTAX  INTEGER {
               enabled(1),
               disabled(2),
               unsupported(2147483647)
            }
    MAX-ACCESS  read-only
    STATUS  current
    DESCRIPTION
            "Enable or disable real server tracking.
	Note:This mib is not supported for VX instance of virtualization."
    ::= { haTriggerReals 1 }

haSwitchNewCfgTriggerNewl4Reals OBJECT-TYPE
    SYNTAX  INTEGER {
              enabled(1),
              disabled(2),
              unsupported(2147483647)
            }
    MAX-ACCESS  read-write
    STATUS  current
    DESCRIPTION
             "Enable or disable real server tracking.
	Note:This mib is not supported for VX instance of virtualization."
    ::= { haTriggerReals 2 }

haSwitchCurCfgTriggerAllReml4Reals OBJECT-TYPE
    SYNTAX  INTEGER {
               aadd(1),
               arem(2),
               unsupported(2147483647)
            }
    MAX-ACCESS  read-only
    STATUS  current
    DESCRIPTION
             "aadd - to add all the real servers to tracking.
              arem - to remove all the real servers from tracking.
	Note:This mib is not supported for VX instance of virtualization."
    ::= { haTriggerReals 3 }

haSwitchNewCfgTriggerAllReml4Reals OBJECT-TYPE
    SYNTAX  INTEGER {
              aadd(1),
              arem(2),
              unsupported(2147483647)
            }
    MAX-ACCESS  read-write
    STATUS  current
    DESCRIPTION
             "aadd - to add all the real servers to tracking.
              arem - to remove all the real servers from tracking.
	Note:This mib is not supported for VX instance of virtualization."
    ::= { haTriggerReals 4 }

haSwitchCurCfgTriggerListl4Reals    OBJECT-TYPE
    SYNTAX  OCTET STRING
    MAX-ACCESS  read-only
    STATUS  current
    DESCRIPTION
        "The Real servers in the group.  The servers are presented
         in bitmap format.

         in receiving order:

             OCTET 1  OCTET 2  .....
             xxxxxxxx xxxxxxxx .....
             |     || |_ server 9
             |     ||
             |     ||___ server 8
             |     |____ server 7
             |       .    .   .
             |__________ server 1

         where x : 1 - The represented server belongs to the group
                   0 - The represented server does not belong to the group.
	Note:This mib is not supported for VX instance of virtualization."
    ::= { haTriggerReals 5 }

haSwitchNewCfgTriggerListl4Reals    OBJECT-TYPE
    SYNTAX  OCTET STRING
    MAX-ACCESS  read-only
    STATUS  current
    DESCRIPTION
        "The Real servers in the group.  The servers are presented
         in bitmap format.

         in receiving order:

             OCTET 1  OCTET 2  .....
             xxxxxxxx xxxxxxxx .....
             |     || |_ server 9
             |     ||
             |     ||___ server 8
             |     |____ server 7
             |       .    .   .
             |__________ server 1

         where x : 1 - The represented server belongs to the group
                   0 - The represented server does not belong to the group.
	Note:This mib is not supported for VX instance of virtualization."
    ::= { haTriggerReals 6 }

haSwitchNewCfgTriggerAddl4Reals OBJECT-TYPE
    SYNTAX DisplayString (SIZE(1..255))
    MAX-ACCESS  read-create
    STATUS  current
    DESCRIPTION
        "The real server to be added to the group. When read, 0 is returned.
	Note:This mib is not supported for VX instance of virtualization."
    ::= { haTriggerReals 7 }

haSwitchNewCfgTriggerRemovel4Reals OBJECT-TYPE
    SYNTAX DisplayString (SIZE(1..255))
    MAX-ACCESS  read-create
    STATUS  current
    DESCRIPTION
        "The real server to be removed from the group. When read, 0 is returned.
	Note:This mib is not supported for VX instance of virtualization."
    ::= { haTriggerReals 8 }

haSwitchNewCfgTrigRealIdxAdd OBJECT-TYPE
    SYNTAX Integer32
    MAX-ACCESS read-write
    STATUS current
    DESCRIPTION
        "Add a Real server into tracking list. To add a real into tracking
         list using this MIB object, we should use only internal index
         of the real server. When read, 0 is returned.
         This MIB object is intended to be used only in WEBUI functionality 
         implementation. For REST and SNMP functionalities, users should use the MIB
         object haSwitchNewCfgTriggerAddl4Reals to add a real into tracking list. 
         Note: This MIB object is not supported for VX instance of virtualization."
    ::= { haTriggerReals 9 }

haSwitchNewCfgTrigRealIdxRemove OBJECT-TYPE
    SYNTAX Integer32
    MAX-ACCESS read-write
    STATUS current
    DESCRIPTION
        "Remove a Real server from tracking list. To remove a real from tracking
         list using this MIB object, we should use only internal index
         of the real server. When read, 0 is returned.
         This MIB object is intended to be used only in WEBUI functionality 
         implementation. For REST and SNMP functionalities, users should use the MIB
         object haSwitchNewCfgTriggerRemovel4Reals to remove a real from tracking list. 
         Note: This MIB object is not supported for VX instance of virtualization."
    ::= { haTriggerReals 10 }

-- Real association to the switch HA Group

haSwitchRealTrkTable OBJECT-TYPE
    SYNTAX  SEQUENCE OF HaSwitchRealTrkEntry
    MAX-ACCESS  not-accessible
    STATUS current
    DESCRIPTION
        "The table of Real to HA switch group.
	Note:This mib is not supported for VX instance of virtualization."
    ::= { haTrigger 6 }

haSwitchRealTrkEntry OBJECT-TYPE
    SYNTAX  HaSwitchRealTrkEntry
    MAX-ACCESS  not-accessible
    STATUS current
    DESCRIPTION
        "Information about a real to HA group.
	Note:This mib is not supported for VX instance of virtualization."
    INDEX   { haSwitchRealTrkIndex }
    ::= { haSwitchRealTrkTable 1 }

HaSwitchRealTrkEntry ::= SEQUENCE {
    haSwitchRealTrkIndex  DisplayString
}

haSwitchRealTrkIndex OBJECT-TYPE
    SYNTAX DisplayString (SIZE(1..32))
    MAX-ACCESS  read-only
    STATUS current
    DESCRIPTION
        "The Real ID number in alphanumeric.
	Note:This mib is not supported for VX instance of virtualization."
    ::= { haSwitchRealTrkEntry 1 }

 -- HA VIP track menu
 haSwitchVipTrack       OBJECT IDENTIFIER ::= { haTrigger 7 }
 
 haSwitchCurCfgTrigVipTrackState OBJECT-TYPE
     SYNTAX  INTEGER {
               enabled(1),
               disabled(2)
             }
     MAX-ACCESS  read-only
     STATUS  current
     DESCRIPTION
              "Enable or disable VIP tracking."
     ::= { haSwitchVipTrack 1 }
 
 haSwitchNewCfgTrigVipTrackState OBJECT-TYPE
     SYNTAX  INTEGER {
               enabled(1),
               disabled(2)
             }
     MAX-ACCESS  read-write
     STATUS  current
     DESCRIPTION
              "Enable or disable VIP tracking."
     ::= { haSwitchVipTrack 2 }
 
 -- CUR CFG HA VIP - VIRT SERV track menu
 haSwitchTriggerVipServCurCfgTable OBJECT-TYPE
     SYNTAX  SEQUENCE OF HaSwitchTriggerVipServCurCfgEntry
     MAX-ACCESS  not-accessible
     STATUS current
     DESCRIPTION
         "The table of VIP tracking configurations."
     ::= { haSwitchVipTrack 3 }
 
 haSwitchTriggerVipServCurCfgEntry OBJECT-TYPE
     SYNTAX  HaSwitchTriggerVipServCurCfgEntry
     MAX-ACCESS  not-accessible
     STATUS current
     DESCRIPTION
         "Information about a particular gateway tracking configuration."
     INDEX   { haSwitchTriggerVipServCurCfgVirtIndex }
     ::= { haSwitchTriggerVipServCurCfgTable 1 }
 
 HaSwitchTriggerVipServCurCfgEntry ::= SEQUENCE {
     haSwitchTriggerVipServCurCfgVirtIndex  DisplayString,
     haSwitchCurCfgTrigVipServTrackState    INTEGER,
     haSwitchCurCfgTrigVipServTrackType     INTEGER
 }
 
 haSwitchTriggerVipServCurCfgVirtIndex OBJECT-TYPE
     SYNTAX  DisplayString (SIZE(1..255))
     MAX-ACCESS  read-only
     STATUS  current
     DESCRIPTION
         "The service ID number in alphanumeric."
     ::= { haSwitchTriggerVipServCurCfgEntry 1 }
 
 haSwitchCurCfgTrigVipServTrackState OBJECT-TYPE
     SYNTAX  INTEGER {
               enabled(1),
               disabled(2)
             }
     MAX-ACCESS  read-only
     STATUS  current
     DESCRIPTION
              "Enable or disable VIP tracking."
     ::= { haSwitchTriggerVipServCurCfgEntry 2 }
 
 haSwitchCurCfgTrigVipServTrackType OBJECT-TYPE
     SYNTAX  INTEGER {
         any(1),
         all(2)
         }
     MAX-ACCESS  read-only
     STATUS  current
     DESCRIPTION
         "Defines tracking type for services (vports) configured under specific virt any(default)/all."
     ::= { haSwitchTriggerVipServCurCfgEntry 3 }
 
 
 -- NEW CFG HA VIP track menu
 
 haSwitchTriggerVipServNewCfgTable OBJECT-TYPE
     SYNTAX  SEQUENCE OF HaSwitchTriggerVipServNewCfgEntry
     MAX-ACCESS  not-accessible
     STATUS current
     DESCRIPTION
         "The table of trigger VIP configurations."
     ::= { haSwitchVipTrack 4 }
 
 haSwitchTriggerVipServNewCfgEntry OBJECT-TYPE
     SYNTAX  HaSwitchTriggerVipServNewCfgEntry
     MAX-ACCESS  not-accessible
     STATUS current
     DESCRIPTION
         "Information about a particular gateway tracking configuration."
    INDEX   { haSwitchTriggerVipServNewCfgVirtIndex }
     ::= { haSwitchTriggerVipServNewCfgTable 1 }
 
 HaSwitchTriggerVipServNewCfgEntry ::= SEQUENCE {
     haSwitchTriggerVipServNewCfgVirtIndex  DisplayString,
     haSwitchNewCfgTrigVipServTrackState    INTEGER,
     haSwitchNewCfgTrigVipServTrackAddSrv   Integer32,
     haSwitchNewCfgTrigVipServTrackRemSrv   Integer32,
     haSwitchNewCfgTrigVipServTrackType     INTEGER,
	 haSwitchNewCfgTrigVipServTrackMapList OCTET STRING
 }
 
 haSwitchTriggerVipServNewCfgVirtIndex OBJECT-TYPE
     SYNTAX  DisplayString (SIZE(1..255))
     MAX-ACCESS  read-only
     STATUS  current
     DESCRIPTION
         "The service ID number in alphanumeric."
     ::= { haSwitchTriggerVipServNewCfgEntry 1 }
 
 haSwitchNewCfgTrigVipServTrackState OBJECT-TYPE
     SYNTAX  INTEGER {
               enabled(1),
               disabled(2)
             }
     MAX-ACCESS  read-write
     STATUS  current
     DESCRIPTION
              "Enable or disable VIP tracking."
     ::= { haSwitchTriggerVipServNewCfgEntry 2 }
 
 haSwitchNewCfgTrigVipServTrackAddSrv OBJECT-TYPE
     SYNTAX  Integer32 (1..65534)
     MAX-ACCESS  read-write
     STATUS  current
     DESCRIPTION
         "The service port added for VIP trigger."
     ::= { haSwitchTriggerVipServNewCfgEntry 3 }
 
 haSwitchNewCfgTrigVipServTrackRemSrv OBJECT-TYPE
     SYNTAX  Integer32 (1..65534)
     MAX-ACCESS  read-write
     STATUS  current
     DESCRIPTION
         "The service port added for VIP trigger."
     ::= { haSwitchTriggerVipServNewCfgEntry 4 }
 
 haSwitchNewCfgTrigVipServTrackType OBJECT-TYPE
     SYNTAX  INTEGER {
         any(1),
         all(2)
         }
    MAX-ACCESS  read-write
     STATUS  current
     DESCRIPTION
         "Defines tracking type for services (vports) configured under specific virt any(default)/all."
     ::= { haSwitchTriggerVipServNewCfgEntry 5 }

 haSwitchNewCfgTrigVipServTrackMapList OBJECT-TYPE
    SYNTAX OCTET STRING
    MAX-ACCESS read-only
    STATUS current
    DESCRIPTION
        "The services present in the vip of HA service. 
         The services are presented in a bitmap format.

         in receiving order:

         OCTET 1 
         xxxxxxxx
         ||    ||___ Rmap 8
         ||    |____ Rmap 7
         ||      .    .   .
         ||_________ Rmap 2
         |__________ Rmap 1

         where x : 1 - The represented service is selected
         0 - The represented service is not selected.
         Note:This mib is not supported for VX instance of virtualization.
            Defines tracking type for services (vports) selected or not under specific virt."
	::= { haSwitchTriggerVipServNewCfgEntry 6 }
	
 haSwitchTrackVipTable OBJECT-TYPE
     SYNTAX  SEQUENCE OF HaSwitchTrackVipsEntry
     MAX-ACCESS  not-accessible
     STATUS current
     DESCRIPTION
         "The table of VIP tracking list."
     ::= { haSwitchVipTrack 5 }
 
 haSwitchTrackVipsEntry OBJECT-TYPE
     SYNTAX  HaSwitchTrackVipsEntry
     MAX-ACCESS  not-accessible
     STATUS current
     DESCRIPTION
         "Information about a Real to HA group."
     INDEX   { haSwitchVirtIndex,haSwitchVirtSrvIndex }
     ::= { haSwitchTrackVipTable 1 }
 
 HaSwitchTrackVipsEntry ::= SEQUENCE {
     haSwitchVirtIndex       DisplayString,
     haSwitchVirtSrvIndex    DisplayString
 }
 
 haSwitchVirtIndex OBJECT-TYPE
     SYNTAX DisplayString (SIZE(1..255))
     MAX-ACCESS  read-only
     STATUS current
     DESCRIPTION
         "The service ID number in alphanumeric."
     ::= { haSwitchTrackVipsEntry 1 }
 
 haSwitchVirtSrvIndex OBJECT-TYPE
     SYNTAX DisplayString (SIZE(1..255))
     MAX-ACCESS  read-only
     STATUS current
     DESCRIPTION
         "The Real ID number in alphanumeric."
     ::= { haSwitchTrackVipsEntry 2 }

-- NEW CFG HA VIP track scalar mib menu
  
 haSwitchTriggerVipServIdxTable OBJECT-TYPE
     SYNTAX  SEQUENCE OF HaSwitchTriggerVipServIdxTableEntry
     MAX-ACCESS  not-accessible
     STATUS current
     DESCRIPTION
         "The table of trigger VIP configuration."
     ::= { haSwitchVipTrack 6 }
 
 haSwitchTriggerVipServIdxTableEntry OBJECT-TYPE
     SYNTAX  HaSwitchTriggerVipServIdxTableEntry
     MAX-ACCESS  not-accessible
     STATUS current
     DESCRIPTION
         "Information about a particular vip tracking configuration."
    INDEX   { haSwitchTriggerVipServIdxTableIndex }
     ::= { haSwitchTriggerVipServIdxTable 1 }
 
 HaSwitchTriggerVipServIdxTableEntry ::= SEQUENCE {
     haSwitchTriggerVipServIdxTableIndex	Integer32,
     haSwitchTriggerVipServIdxName		DisplayString,
     haSwitchTriggerVipServIdxVport		INTEGER,
     haSwitchTriggerVipServIdxTrackType     	INTEGER
 }

  haSwitchTriggerVipServIdxTableIndex OBJECT-TYPE
     SYNTAX Integer32
     MAX-ACCESS  read-only
     STATUS  current
     DESCRIPTION
		"The internal index of a VIP and service.
		 Note: This MIB object is not supported for VX instance of virtualization."
     ::= { haSwitchTriggerVipServIdxTableEntry 1 }
 
 haSwitchTriggerVipServIdxName OBJECT-TYPE
    SYNTAX  DisplayString (SIZE(1..255))
    MAX-ACCESS  read-only
    STATUS  current
    DESCRIPTION
        "The alphanumeric id of the virtual server."
    ::= { haSwitchTriggerVipServIdxTableEntry 2 }
	
 haSwitchTriggerVipServIdxVport OBJECT-TYPE
    SYNTAX  INTEGER (1..65534)
    MAX-ACCESS  read-only
    STATUS  current
    DESCRIPTION
        "The virtual port number of the service."
    ::= { haSwitchTriggerVipServIdxTableEntry 3 }
    
 haSwitchTriggerVipServIdxTrackType OBJECT-TYPE
     SYNTAX  INTEGER {
         any(1),
         all(2)
         }
    MAX-ACCESS  read-only
     STATUS  current
     DESCRIPTION
         "Defines tracking type for services (vports) configured under specific virt any(default)/all."
     ::= { haSwitchTriggerVipServIdxTableEntry 4 }
     
 haSwitchNewCfgTrigVipTrackIdxAdd OBJECT-TYPE
     SYNTAX  Integer32
     MAX-ACCESS  read-write
     STATUS current
     DESCRIPTION
              "Add a Vip and service into tracking list. To add a vip and service into 
			  tracking list using this MIB object. This MIB object is intended to be
			  used only in WEBUI functionality implementation.
			  Note: This MIB object is not supported for VX instance of virtualization."
     ::= { haSwitchVipTrack 7 }	

 haSwitchNewCfgTrigVipTrackIdxRemove OBJECT-TYPE
     SYNTAX  Integer32
     MAX-ACCESS  read-write
     STATUS current
     DESCRIPTION
              "Remove a Vip and service into tracking list. To remove a vip and service from  
			  tracking list using this MIB object. This MIB object is intended to be
			  used only in WEBUI functionality implementation.
			  Note: This MIB object is not supported for VX instance of virtualization."
     ::= { haSwitchVipTrack 8 }
	 
 haSwitchCurCfgTrigVipServList    OBJECT-TYPE
    SYNTAX  OCTET STRING
    MAX-ACCESS  read-only
    STATUS  current
    DESCRIPTION
        "The Layer 4 groups configured for tracking in switch HA mode.The servers are presented
         in bitmap format. This bitmap shows the vip and services that are being tracked after applying the configuration.

         in receiving order:

             OCTET 1  OCTET 2  .....
             xxxxxxxx xxxxxxxx .....
             |     || |_ vipServ 9
             |     ||
             |     ||___ vipServ 8
             |     |____ vipServ 7
             |       .    .   .
             |__________ vipServ 1

         where x : 1 - The represented virtual service is tracked
                   0 - The represented virtual service is NOT tracked.
	     Note:This mib is not supported for VX instance of virtualization."
    ::= { haSwitchVipTrack 9 }

haSwitchNewCfgTrigVipServList    OBJECT-TYPE
    SYNTAX  OCTET STRING
    MAX-ACCESS  read-only
    STATUS  current
    DESCRIPTION
        "The Layer 4 groups configured for tracking in switch HA mode.The servers are presented
         in bitmap format. This bitmap shows the vip and services that are being tracked before applying the configuration.

         in receiving order:

             OCTET 1  OCTET 2  .....
             xxxxxxxx xxxxxxxx .....
             |     || |_ vipServ 9
             |     ||
             |     ||___ vipServ 8
             |     |____ vipServ 7
             |       .    .   .
             |__________ vipServ 1

         where x : 1 - The represented virtual service is tracked
                   0 - The represented virtual service is NOT tracked.
	     Note:This mib is not supported for VX instance of virtualization."
    ::= { haSwitchVipTrack 10 }

-- Switch HA Group Track Menu

haGrpTrack  OBJECT IDENTIFIER ::= { haTrigger 8 }

haSwitchCurCfgTrigL4GrpTrackState OBJECT-TYPE
    SYNTAX INTEGER {
            enabled(1),
            disabled(2),
            unsupported(2147483647)
        }
    MAX-ACCESS read-only
    STATUS current
    DESCRIPTION
        "Current Config state of Group Tracking in Switch HA mode. It will show 
         the current group track state that was applied by the user.
	     Note:This mib is not supported for VX instance of virtualization."
    ::= { haGrpTrack 1 }

haSwitchNewCfgTrigL4GrpTrackState OBJECT-TYPE
    SYNTAX INTEGER {
            enabled(1),
            disabled(2),
            unsupported(2147483647)
        }
    MAX-ACCESS read-write
    STATUS current
    DESCRIPTION
        "Enable or Disable Group Tracking in switch HA mode.
	     Note:This mib is not supported for VX instance of virtualization."
    ::= { haGrpTrack 2 }

haSwitchNewCfgTrigL4GrpTrackAdd OBJECT-TYPE
    SYNTAX DisplayString (SIZE(1..255))
    MAX-ACCESS read-create
    STATUS current
    DESCRIPTION
        "The layer 4 group to be added to the tracking list. When read, NULL string
         is returned.
	     Note:This mib is not supported for VX instance of virtualization."
    ::= { haGrpTrack 3 }

haSwitchNewCfgTrigL4GrpTrackRemove OBJECT-TYPE
    SYNTAX DisplayString (SIZE(1..255))
    MAX-ACCESS read-create
    STATUS current
    DESCRIPTION
        "The layer 4 group to be removed from the tracking list. When read, NULL string
         is returned.
	     Note:This mib is not supported for VX instance of virtualization."
    ::= { haGrpTrack 4 }

haSwitchCurCfgTrigL4GrpList    OBJECT-TYPE
    SYNTAX  OCTET STRING
    MAX-ACCESS  read-only
    STATUS  current
    DESCRIPTION
        "The Layer 4 groups configured for tracking in switch HA mode.The servers are presented
         in bitmap format. This bitmap shows the groups that are being tracked after applying the configuration.

         in receiving order:

             OCTET 1  OCTET 2  .....
             xxxxxxxx xxxxxxxx .....
             |     || |_ group 9
             |     ||
             |     ||___ group 8
             |     |____ group 7
             |       .    .   .
             |__________ group 1

         where x : 1 - The represented group is tracked
                   0 - The represented group is NOT tracked.
	     Note:This mib is not supported for VX instance of virtualization."
    ::= { haGrpTrack 5 }

haSwitchNewCfgTrigL4GrpList    OBJECT-TYPE
    SYNTAX  OCTET STRING
    MAX-ACCESS  read-only
    STATUS  current
    DESCRIPTION
        "The Layer 4 groups configured for tracking in switch HA mode.The servers are presented
         in bitmap format. This bitmap shows the groups that are being tracked before applying the configuration.

         in receiving order:

             OCTET 1  OCTET 2  .....
             xxxxxxxx xxxxxxxx .....
             |     || |_ group 9
             |     ||
             |     ||___ group 8
             |     |____ group 7
             |       .    .   .
             |__________ group 1

         where x : 1 - The represented group is tracked
                   0 - The represented group is NOT tracked.
	     Note:This mib is not supported for VX instance of virtualization."
    ::= { haGrpTrack 6 }

haSwitchNewCfgTrigL4GrpTrkIdxAdd OBJECT-TYPE
    SYNTAX  Integer32
    MAX-ACCESS read-write
    STATUS current
    DESCRIPTION
        "Add a Layer 4 group into tracking list. To add a group into tracking
         list using this MIB object, we should use only internal index
         of the group. When read, 0 is returned.
         This MIB object is intended to be used only in WEBUI functionality 
         implementation. For REST and SNMP functionalities, users should use the MIB
         object haSwitchNewCfgTrigL4GrpTrackAdd to add a group into tracking list. 
         Note: This MIB object is not supported for VX instance of virtualization."
    ::= { haGrpTrack 7 }

haSwitchNewCfgTrigL4GrpTrkIdxRemove OBJECT-TYPE
    SYNTAX  Integer32
    MAX-ACCESS read-write
    STATUS current
    DESCRIPTION
        "Remove a Layer 4 group from tracking list. To remove a group using this MIB
         object, user should use only internal index of the group that needs to be 
         removed from tracking list. When read, 0 is returned.
         This MIB object is intended to be used only in WEBUI functionality 
         implementation. For REST and SNMP functionalities, users should use the MIB
         object haSwitchNewCfgTrigL4GrpTrackRemove to remove a group from tracking list. 
         Note: This MIB object is not supported for VX instance of virtualization."
    ::= { haGrpTrack 8 }

-- Group Tracking association to the switch HA Group

haSwitchGrpTrkTable OBJECT-TYPE
    SYNTAX  SEQUENCE OF HaSwitchGrpTrkEntry
    MAX-ACCESS  not-accessible
    STATUS current
    DESCRIPTION
        "The table of L4 groups added for tracking to HA switch group trigger.
	Note:This mib is not supported for VX instance of virtualization."
    ::= { haTrigger 9 }

haSwitchGrpTrkEntry OBJECT-TYPE
    SYNTAX  HaSwitchGrpTrkEntry
    MAX-ACCESS  not-accessible
    STATUS current
    DESCRIPTION
        "Information about L4 group association to HA group for failover trigger.
	Note:This mib is not supported for VX instance of virtualization."
    INDEX   { haSwitchGrpTrkIndex }
    ::= { haSwitchGrpTrkTable 1 }

HaSwitchGrpTrkEntry ::= SEQUENCE {
    haSwitchGrpTrkIndex  DisplayString
}

haSwitchGrpTrkIndex OBJECT-TYPE
    SYNTAX DisplayString (SIZE(1..255))
    MAX-ACCESS  read-only
    STATUS current
    DESCRIPTION
        "The Group ID in alphanumeric which is configured for tracking in switch 
        HA failover trigger.
	Note:This mib is not supported for VX instance of virtualization."
    ::= { haSwitchGrpTrkEntry 1 }

-- Table to list the Layer 4 groups with group's internal index as key

haSwitchGrpIdxTable OBJECT-TYPE
    SYNTAX SEQUENCE OF HaSwitchGrpIdxTableEntry
    MAX-ACCESS not-accessible
    STATUS current
    DESCRIPTION
        "The table of Layer 4 groups configured in Alteon. This table lists group's internal
         index and its alphanumeric name.
         Note: This MIB object is not supported for VX instance of virtualization."
    ::= { haTrigger 10 }

haSwitchGrpIdxTableEntry OBJECT-TYPE
    SYNTAX HaSwitchGrpIdxTableEntry
    MAX-ACCESS not-accessible
    STATUS current
    DESCRIPTION
        "Tabluar entry to list Layer 4 group with its internal index.
         Note: This MIB object is not supported for VX instance of virtualization."
    INDEX { haSwitchL4GrpIndex, haSwitchL4GrpName }
    ::= { haSwitchGrpIdxTable 1 }

HaSwitchGrpIdxTableEntry ::= SEQUENCE {
    haSwitchL4GrpIndex Integer32,
    haSwitchL4GrpName DisplayString
}

haSwitchL4GrpIndex OBJECT-TYPE
    SYNTAX Integer32
    MAX-ACCESS read-only
    STATUS current
    DESCRIPTION
        "The internal index of a Layer 4 Group.
         Note: This MIB object is not supported for VX instance of virtualization."
    ::= { haSwitchGrpIdxTableEntry 1 }

haSwitchL4GrpName OBJECT-TYPE
    SYNTAX DisplayString(SIZE(1..255))
    MAX-ACCESS read-only
    STATUS current
    DESCRIPTION
        "The alphanumeric name of a Layer4 group.
         Note: This MIB object is not supported for VX instance of virtualization."
    ::= { haSwitchGrpIdxTableEntry 2 }

-- Table to list the Real Server with its internal index, alphanumeric ID and Real IP 

haSwitchRealIdxTable OBJECT-TYPE
    SYNTAX SEQUENCE OF HaSwitchRealIdxTableEntry
    MAX-ACCESS not-accessible
    STATUS current
    DESCRIPTION
        "This table lists the alphanumeric ID of Real servers with its internal index
         and Real IP address.
         Note: This MIB object is not supported for VX instance of virtualization."
    ::= { haTrigger 11 }

haSwitchRealIdxTableEntry OBJECT-TYPE
    SYNTAX HaSwitchRealIdxTableEntry
    MAX-ACCESS not-accessible
    STATUS current
    DESCRIPTION
        "Tabular entry to list Real server with its internal index, alphanumeric ID and
         Real server IP address.
         Note: This MIB object is not supported for VX instance of virtualization."
    INDEX { haSwitchRealIndex, haSwitchRealName }
    ::= { haSwitchRealIdxTable 1 }

HaSwitchRealIdxTableEntry ::= SEQUENCE {
    haSwitchRealIndex       Integer32,
    haSwitchRealName        DisplayString,
    haSwitchRealIpVer       INTEGER,
    haSwitchRealIpAddr      IpAddress,
    haSwitchRealIpv6Addr    DisplayString
}

haSwitchRealIndex  OBJECT-TYPE
    SYNTAX Integer32
    MAX-ACCESS read-only
    STATUS current
    DESCRIPTION
        "The internal index of a real server.
         Note: This MIB object is not supported for VX instance of virtualization."
    ::= { haSwitchRealIdxTableEntry 1 }

haSwitchRealName OBJECT-TYPE
    SYNTAX DisplayString(SIZE(1..255))
    MAX-ACCESS read-only
    STATUS current
    DESCRIPTION
        "The alphanumeric ID of a real server.
         Note: This MIB object is not supported for VX instance of virtualization."
    ::= { haSwitchRealIdxTableEntry 2 }

haSwitchRealIpVer OBJECT-TYPE
    SYNTAX INTEGER{
        ipv4(1),
        ipv6(2),
        unsupported(2147483647)
    }
    MAX-ACCESS read-only
    STATUS current
    DESCRIPTION
        "Version of the real server IP address.
         Note: This MIB object is not supported for VX instance of virtualization."
    ::= { haSwitchRealIdxTableEntry 3 }

haSwitchRealIpAddr OBJECT-TYPE
    SYNTAX IpAddress 
    MAX-ACCESS read-only
    STATUS current
    DESCRIPTION
        "IP address of the Real server.
         Note: This MIB object is not supported for VX instance of virtualization."
    ::= { haSwitchRealIdxTableEntry 4 }

haSwitchRealIpv6Addr OBJECT-TYPE
    SYNTAX DisplayString(SIZE(0..40))
    MAX-ACCESS read-only
    STATUS current
    DESCRIPTION
        "IPV6 address of the real server. Address should be 4-byte hexadecimal 
         colon notation. Valid IPv6 address should be in any of the following forms
         xxxx:xxxx:xxxx:xxxx:xxxx:xxxx:xxxx:xxxx or xxxx::xxxx:xxxx:xxxx:xxxx or 
         ::xxxx.
         Note: This MIB object is not supported for VX instance of virtualization."
     ::= { haSwitchRealIdxTableEntry 5 }

-- HA Floating IP Table

haFloatIpCurCfgTable OBJECT-TYPE
    SYNTAX  SEQUENCE OF HaFloatIpCurCfgEntry
    MAX-ACCESS  not-accessible
    STATUS  current
    DESCRIPTION
        "The table of Floating IP configurations.
	Note:This mib is not supported for VX instance of virtualization."
    ::= { haCfg 6 }

haFloatIpCurCfgEntry OBJECT-TYPE
    SYNTAX  HaFloatIpCurCfgEntry
    MAX-ACCESS  not-accessible
    STATUS  current
    DESCRIPTION
        "Information about a particular Floating IP configuration.
	Note:This mib is not supported for VX instance of virtualization."
    INDEX   { haFloatIpCurCfgIndex }
    ::= { haFloatIpCurCfgTable 1 }

HaFloatIpCurCfgEntry ::= SEQUENCE {
    haFloatIpCurCfgIndex           DisplayString,
    haFloatIpCurCfgIpVer           INTEGER,
    haFloatIpCurCfgIpAddr          IpAddress,
    haFloatIpCurCfgIpv6Addr        DisplayString,
    haFloatIpCurCfgIf              INTEGER,
    haFloatIpCurCfgState           INTEGER
}

haFloatIpCurCfgIndex OBJECT-TYPE
    SYNTAX DisplayString (SIZE(1..32))
    MAX-ACCESS  read-only
    STATUS  current
    DESCRIPTION
        "The floating IP number in alphanumeric.
	Note:This mib is not supported for VX instance of virtualization."
    ::= { haFloatIpCurCfgEntry 1 }

haFloatIpCurCfgIpVer OBJECT-TYPE
    SYNTAX  INTEGER{
        ipv4(1),
        ipv6(2),
        unsupported(2147483647)
    }
    MAX-ACCESS  read-only
    STATUS  current
    DESCRIPTION
        "The floating IP version.
	Note:This mib is not supported for VX instance of virtualization."
    ::= { haFloatIpCurCfgEntry 2 }      

haFloatIpCurCfgIpAddr OBJECT-TYPE
    SYNTAX  IpAddress
    MAX-ACCESS  read-only
    STATUS  current
    DESCRIPTION
        "The floating IP address.
	Note:This mib is not supported for VX instance of virtualization."
    ::= { haFloatIpCurCfgEntry 3 }

haFloatIpCurCfgIpv6Addr OBJECT-TYPE
    SYNTAX DisplayString (SIZE(0..40))
    MAX-ACCESS  read-only
    STATUS  current
    DESCRIPTION
        "  IPV6 address of the floating IP identified by the instance of the haFloatIpCurCfgIndex.
        Address should be 4-byte haxadecimal colon notation. Valid IPv6 address should be in
        any of the following forms xxxx:xxxx:xxxx:xxxx:xxxx:xxxx:xxxx:xxxx or xxxx::xxxx:xxxx:xxxx:xxxx or ::xxxx 
	Note:This mib is not supported for VX instance of virtualization."
    ::= { haFloatIpCurCfgEntry 4 }

haFloatIpCurCfgIf OBJECT-TYPE
    SYNTAX  INTEGER (1..256)
    MAX-ACCESS  read-only
    STATUS  current
    DESCRIPTION
        "Floating IP interface.
	Note:This mib is not supported for VX instance of virtualization."
    ::= { haFloatIpCurCfgEntry 5 }

haFloatIpCurCfgState OBJECT-TYPE
    SYNTAX  INTEGER {
        enabled(1),
        disabled(2),
        unsupported(2147483647)
        }
    MAX-ACCESS  read-only
    STATUS  current
    DESCRIPTION
        "Enable or disable floating IP.
	Note:This mib is not supported for VX instance of virtualization."
    ::= { haFloatIpCurCfgEntry 6 }    
        
haFloatIpNewCfgTable OBJECT-TYPE
    SYNTAX  SEQUENCE OF HaFloatIpNewCfgEntry
    MAX-ACCESS  not-accessible
    STATUS  current
    DESCRIPTION
        "The table of Floating IP configurations.
	Note:This mib is not supported for VX instance of virtualization."
    ::= { haCfg 7 }

haFloatIpNewCfgEntry OBJECT-TYPE
    SYNTAX  HaFloatIpNewCfgEntry
    MAX-ACCESS  not-accessible
    STATUS  current
    DESCRIPTION
        "Information about a particular Floating IP configuration.
	Note:This mib is not supported for VX instance of virtualization."
    INDEX   { haFloatIpNewCfgIndex }
    ::= { haFloatIpNewCfgTable 1 }

HaFloatIpNewCfgEntry ::= SEQUENCE {
    haFloatIpNewCfgIndex           DisplayString,
    haFloatIpNewCfgIpVer           INTEGER,
    haFloatIpNewCfgIpAddr          IpAddress,
    haFloatIpNewCfgIpv6Addr        DisplayString,
    haFloatIpNewCfgIf              INTEGER,
    haFloatIpNewCfgDelete          INTEGER,
    haFloatIpNewCfgState           INTEGER
}

haFloatIpNewCfgIndex OBJECT-TYPE
    SYNTAX DisplayString (SIZE(1..32))
    MAX-ACCESS  read-only
    STATUS  current
    DESCRIPTION
        "The floating IP number in alphanumeric.
	Note:This mib is not supported for VX instance of virtualization."
    ::= { haFloatIpNewCfgEntry 1 }

haFloatIpNewCfgIpVer OBJECT-TYPE
    SYNTAX  INTEGER{
        ipv4(1),
        ipv6(2),
        unsupported(2147483647)
    }
    MAX-ACCESS  read-create
    STATUS  current
    DESCRIPTION
        "The floating IP version.
	Note:This mib is not supported for VX instance of virtualization."
    ::= { haFloatIpNewCfgEntry 2 }

haFloatIpNewCfgIpAddr OBJECT-TYPE
    SYNTAX  IpAddress
    MAX-ACCESS  read-create
    STATUS  current
    DESCRIPTION
        "The floating IP address.
	Note:This mib is not supported for VX instance of virtualization."
    ::= { haFloatIpNewCfgEntry 3 }

haFloatIpNewCfgIpv6Addr OBJECT-TYPE
    SYNTAX DisplayString (SIZE(0..40))
    MAX-ACCESS  read-create
    STATUS  current
    DESCRIPTION
        "IPV6 address of the floating IP identified by the instance of the haFloatIpNewCfgIndex.
        Address should be 4-byte haxadecimal colon notation. Valid IPv6 address should be in
        any of the following forms xxxx:xxxx:xxxx:xxxx:xxxx:xxxx:xxxx:xxxx or xxxx::xxxx:xxxx:xxxx:xxxx or ::xxxx
	Note:This mib is not supported for VX instance of virtualization."
    ::= { haFloatIpNewCfgEntry 4 }

haFloatIpNewCfgIf OBJECT-TYPE
    SYNTAX  INTEGER (1..256)
    MAX-ACCESS  read-create
    STATUS  current
    DESCRIPTION
        "Floating IP interface.
	Note:This mib is not supported for VX instance of virtualization."
    ::= { haFloatIpNewCfgEntry 5 }
        
haFloatIpNewCfgDelete OBJECT-TYPE
    SYNTAX  INTEGER {
        other(1),
        delete(2),
        unsupported(2147483647)
        }
    MAX-ACCESS  read-create
    STATUS  current
    DESCRIPTION
        "By setting the value to delete(2), the entire row is deleted.
	Note:This mib is not supported for VX instance of virtualization."
    ::= { haFloatIpNewCfgEntry 6 }

haFloatIpNewCfgState OBJECT-TYPE
    SYNTAX  INTEGER {
        enabled(1),
        disabled(2),
        unsupported(2147483647)
        }
    MAX-ACCESS  read-create
    STATUS  current
    DESCRIPTION
        "Enable or disable floating IP.
	Note:This mib is not supported for VX instance of virtualization."
    ::= { haFloatIpNewCfgEntry 7 }   

-- HA Service menu

haService OBJECT IDENTIFIER ::= { haCfg 8 }

haServiceCurCfgTable OBJECT-TYPE
    SYNTAX  SEQUENCE OF HaServiceCurCfgEntry
    MAX-ACCESS  not-accessible
    STATUS  current
    DESCRIPTION
        "The table of HA Service configurations.
	Note:This mib is not supported for VX instance of virtualization."
    ::= { haService 1 }

haServiceCurCfgEntry OBJECT-TYPE
    SYNTAX  HaServiceCurCfgEntry
    MAX-ACCESS  not-accessible
    STATUS  current
    DESCRIPTION
        "Information about a particular HA Service configuration.
	Note:This mib is not supported for VX instance of virtualization."
    INDEX   { haServiceCurCfgIndex }
    ::= { haServiceCurCfgTable 1 }

HaServiceCurCfgEntry ::= SEQUENCE {
    haServiceCurCfgIndex           DisplayString,
    haServiceCurCfgPref            INTEGER,
    haServiceCurCfgPref		   INTEGER,
    haServiceCurCfgFailBackMode    INTEGER,
    haServiceCurCfgAdver           INTEGER,
    haServiceCurCfgState           INTEGER
   
}

haServiceCurCfgIndex OBJECT-TYPE
    SYNTAX DisplayString (SIZE(1..32))
    MAX-ACCESS  read-only
    STATUS  current
    DESCRIPTION
        "The service index in alphanumeric.
	Note:This mib is not supported for VX instance of virtualization."
    ::= { haServiceCurCfgEntry 1 }


haServiceCurCfgPref OBJECT-TYPE
    SYNTAX  INTEGER {
        active(1),
        standby(2),
        unsupported(2147483647)
        }
    MAX-ACCESS  read-only
    STATUS  current
    DESCRIPTION
        "The preferred initial state.
	Note:This mib is not supported for VX instance of virtualization."
    ::= { haServiceCurCfgEntry 2 }

haServiceCurCfgFailBackMode OBJECT-TYPE
    SYNTAX  INTEGER {
        onfailure(1),
        always(2),
        unsupported(2147483647)
        }
    MAX-ACCESS  read-only
    STATUS  current
    DESCRIPTION
            "The fail back mode.
	Note:This mib is not supported for VX instance of virtualization."
    ::= { haServiceCurCfgEntry 3 }

haServiceCurCfgAdver OBJECT-TYPE
    SYNTAX  INTEGER (1..255)
    MAX-ACCESS  read-only
    STATUS  current
    DESCRIPTION
            "The advertisement Interval.
	Note:This mib is not supported for VX instance of virtualization."
    ::= { haServiceCurCfgEntry 4 }

haServiceCurCfgState OBJECT-TYPE
    SYNTAX  INTEGER {
        enabled(1),
        disabled(2),
        unsupported(2147483647)
        }
    MAX-ACCESS  read-only
    STATUS  current
    DESCRIPTION
            "Enable/disable HA service group.
	Note:This mib is not supported for VX instance of virtualization."
    ::= { haServiceCurCfgEntry 5 }

haServiceNewCfgTable OBJECT-TYPE
    SYNTAX  SEQUENCE OF HaServiceNewCfgEntry
    MAX-ACCESS  not-accessible
    STATUS current
    DESCRIPTION
        "The table of HA Service configurations.
	Note:This mib is not supported for VX instance of virtualization."
    ::= { haService 2 }

haServiceNewCfgEntry OBJECT-TYPE
    SYNTAX  HaServiceNewCfgEntry
    MAX-ACCESS  not-accessible
    STATUS current 
    DESCRIPTION
        "Information about a particular HA Service configuration.
	Note:This mib is not supported for VX instance of virtualization."
    INDEX   { haServiceNewCfgIndex }
    ::= { haServiceNewCfgTable 1 }

HaServiceNewCfgEntry ::= SEQUENCE {
    haServiceNewCfgIndex            DisplayString,
    haServiceNewCfgPref             INTEGER,
    haServiceNewCfgPref		    INTEGER,
    haServiceNewCfgFailBackMode     INTEGER,
    haServiceNewCfgAddIf            INTEGER,
    haServiceNewCfgRemIf            INTEGER,
    haServiceNewCfgAddFip           DisplayString,
    haServiceNewCfgRemFip           DisplayString,
    haServiceNewCfgAddVip           DisplayString,
    haServiceNewCfgRemVip           DisplayString,
    haServiceNewCfgAdver            INTEGER,
    haServiceNewCfgDelete           INTEGER,
    haServiceNewCfgState            INTEGER
   
}

haServiceNewCfgIndex OBJECT-TYPE
    SYNTAX DisplayString (SIZE(1..32))
    MAX-ACCESS  read-only
    STATUS current 
    DESCRIPTION
        "The service ID number in alphanumeric.
	Note:This mib is not supported for VX instance of virtualization."
    ::= { haServiceNewCfgEntry 1 }


haServiceNewCfgPref OBJECT-TYPE
    SYNTAX  INTEGER {
        active(1),
        standby(2),
        unsupported(2147483647)
        }
    MAX-ACCESS  read-create
    STATUS current  
    DESCRIPTION
        "The preferred initial state.
	Note:This mib is not supported for VX instance of virtualization."
    ::= { haServiceNewCfgEntry 2 }

haServiceNewCfgFailBackMode OBJECT-TYPE
    SYNTAX  INTEGER {
        onfailure(1),
        always(2),
        unsupported(2147483647)
        }
    MAX-ACCESS  read-create
    STATUS current  
    DESCRIPTION
            "The fail back mode.
	Note:This mib is not supported for VX instance of virtualization."
    ::= { haServiceNewCfgEntry 3 }

haServiceNewCfgAddIf OBJECT-TYPE
    SYNTAX  INTEGER (1..256)
    MAX-ACCESS  read-create
    STATUS  current
    DESCRIPTION
             "Add interface for HA communication between the devices.
	Note:This mib is not supported for VX instance of virtualization."
    ::= { haServiceNewCfgEntry 4 }

haServiceNewCfgRemIf OBJECT-TYPE
    SYNTAX  INTEGER (1..256)
    MAX-ACCESS  read-create
    STATUS  current
    DESCRIPTION
             "Remove interface from HA communication between the devices.
	Note:This mib is not supported for VX instance of virtualization."
        ::= { haServiceNewCfgEntry 5 }

haServiceNewCfgAddFip OBJECT-TYPE
    SYNTAX DisplayString (SIZE(1..32))
    MAX-ACCESS  read-create
    STATUS  current
    DESCRIPTION
             "Add Floating IP to HA group.
	Note:This mib is not supported for VX instance of virtualization."
    ::= { haServiceNewCfgEntry 6 }

haServiceNewCfgRemFip OBJECT-TYPE
    SYNTAX DisplayString (SIZE(1..32))
    MAX-ACCESS  read-create
    STATUS  current
    DESCRIPTION
             "Remove Floating IP from HA group.
	Note:This mib is not supported for VX instance of virtualization."
        ::= { haServiceNewCfgEntry 7 }

haServiceNewCfgAddVip OBJECT-TYPE
    SYNTAX DisplayString (SIZE(1..255))
    MAX-ACCESS  read-create
    STATUS  current
    DESCRIPTION
             "Add VIP to HA group.
	Note:This mib is not supported for VX instance of virtualization."
    ::= { haServiceNewCfgEntry 8 }

haServiceNewCfgRemVip OBJECT-TYPE
    SYNTAX DisplayString (SIZE(1..255))
    MAX-ACCESS  read-create
    STATUS  current
    DESCRIPTION
             "Remove VIP from HA group.
	Note:This mib is not supported for VX instance of virtualization."
        ::= { haServiceNewCfgEntry 9 }

haServiceNewCfgAdver OBJECT-TYPE
    SYNTAX  INTEGER (1..255)
    MAX-ACCESS  read-create
    STATUS current 
    DESCRIPTION
    "The advertisement Interval.
	Note:This mib is not supported for VX instance of virtualization."
    ::= { haServiceNewCfgEntry 10 }

haServiceNewCfgDelete OBJECT-TYPE
    SYNTAX  INTEGER {
	    other(1),
	    delete(2),
            unsupported(2147483647)
    }
    MAX-ACCESS  read-create
    STATUS  current
    DESCRIPTION
    "By setting the value to delete(2), the entire HA group is deleted.
	Note:This mib is not supported for VX instance of virtualization."
::= { haServiceNewCfgEntry 11 }

haServiceNewCfgState OBJECT-TYPE
    SYNTAX  INTEGER {
        enabled(1),
        disabled(2),
        unsupported(2147483647)
        }
    MAX-ACCESS  read-create
    STATUS  current
    DESCRIPTION
            "Enable/disable HA service group.
	Note:This mib is not supported for VX instance of virtualization."
    ::= { haServiceNewCfgEntry 12 }


haServiceVipTable OBJECT-TYPE
    SYNTAX  SEQUENCE OF HaServiceVipEntry
    MAX-ACCESS  not-accessible
    STATUS current
    DESCRIPTION
        "The table of VIP to HA group.
	Note:This mib is not supported for VX instance of virtualization."
    ::= { haService 3 }

haServiceVipEntry OBJECT-TYPE
    SYNTAX  HaServiceVipEntry
    MAX-ACCESS  not-accessible
    STATUS current
    DESCRIPTION
        "Information about a VIP to HA group.
	Note:This mib is not supported for VX instance of virtualization."
    INDEX   { haServiceIndex,haServiceVipIndex }
    ::= { haServiceVipTable 1 }

HaServiceVipEntry ::= SEQUENCE {
    haServiceIndex       DisplayString,
    haServiceVipIndex    DisplayString
    

}

haServiceIndex OBJECT-TYPE
    SYNTAX DisplayString (SIZE(1..32))
    MAX-ACCESS  read-only
    STATUS current
    DESCRIPTION
        "The service ID number in alphanumeric.
	Note:This mib is not supported for VX instance of virtualization."
    ::= { haServiceVipEntry 1 }

haServiceVipIndex OBJECT-TYPE
    SYNTAX DisplayString (SIZE(1..255))
    MAX-ACCESS  read-only
    STATUS current
    DESCRIPTION
        "The virtual ID number in alphanumeric.
	Note:This mib is not supported for VX instance of virtualization."
    ::= { haServiceVipEntry 2 }    
    

haServiceFipTable OBJECT-TYPE
    SYNTAX  SEQUENCE OF HaServiceFipEntry
    MAX-ACCESS  not-accessible
    STATUS current
    DESCRIPTION
        "The table of FIP to HA group.
	Note:This mib is not supported for VX instance of virtualization."
    ::= { haService 4 }

haServiceFipEntry OBJECT-TYPE
    SYNTAX  HaServiceFipEntry
    MAX-ACCESS  not-accessible
    STATUS current
    DESCRIPTION
        "Information about a FIP to HA group.
	Note:This mib is not supported for VX instance of virtualization."
    INDEX   { haServiceFipIndex,haFipIndex }
    ::= { haServiceFipTable 1 }

HaServiceFipEntry ::= SEQUENCE {
    haServiceFipIndex       DisplayString,
    haFipIndex    	    DisplayString
}

haServiceFipIndex OBJECT-TYPE
    SYNTAX DisplayString (SIZE(1..32))
    MAX-ACCESS  read-only
    STATUS current
    DESCRIPTION
        "The service ID number in alphanumeric.
	Note:This mib is not supported for VX instance of virtualization."
    ::= { haServiceFipEntry 1 }

haFipIndex OBJECT-TYPE
    SYNTAX DisplayString (SIZE(1..32))
    MAX-ACCESS  read-only
    STATUS current
    DESCRIPTION
        "The Floating IP ID number in alphanumeric.
	Note:This mib is not supported for VX instance of virtualization."
    ::= { haServiceFipEntry 2 }    

haServiceAdvIfsTable OBJECT-TYPE
    SYNTAX  SEQUENCE OF HaServiceAdvIfsEntry
    MAX-ACCESS  not-accessible
    STATUS current
    DESCRIPTION
        "The table of advertisement interface.
	Note:This mib is not supported for VX instance of virtualization."
    ::= { haService 5 }

haServiceAdvIfsEntry OBJECT-TYPE
    SYNTAX  HaServiceAdvIfsEntry
    MAX-ACCESS  not-accessible
    STATUS current
    DESCRIPTION
        "Information about a advertisement interface.
	Note:This mib is not supported for VX instance of virtualization."
    INDEX   { haServiceAdvIfIndex,haAdvIfIndex }
    ::= { haServiceAdvIfsTable 1 }

HaServiceAdvIfsEntry ::= SEQUENCE {
    haServiceAdvIfIndex        DisplayString,
    haAdvIfIndex               INTEGER 
}

haServiceAdvIfIndex OBJECT-TYPE
    SYNTAX DisplayString (SIZE(1..32))
    MAX-ACCESS  read-only
    STATUS current
    DESCRIPTION
        "The service ID number in alphanumeric.
	Note:This mib is not supported for VX instance of virtualization."
    ::= { haServiceAdvIfsEntry 1 }

haAdvIfIndex OBJECT-TYPE
    SYNTAX  INTEGER (1..256)
    MAX-ACCESS  read-only
    STATUS current
    DESCRIPTION
        "The advertisement interface number.
	Note:This mib is not supported for VX instance of virtualization."
    ::= { haServiceAdvIfsEntry 2 }

-- HA Service Trigger menu

haServiceTrigger       OBJECT IDENTIFIER ::= { haService 6 }

haServiceTriggerCurCfgTable OBJECT-TYPE
    SYNTAX  SEQUENCE OF HaServiceTriggerCurCfgEntry
    MAX-ACCESS  not-accessible
    STATUS current
    DESCRIPTION
        "The table of trigger configurations.
	Note:This mib is not supported for VX instance of virtualization."
    ::= { haServiceTrigger 1 }

haServiceTriggerCurCfgEntry OBJECT-TYPE
    SYNTAX  HaServiceTriggerCurCfgEntry
    MAX-ACCESS  not-accessible
    STATUS current
    DESCRIPTION
        "Information about a particular trigger configuration.
	Note:This mib is not supported for VX instance of virtualization."
    INDEX   { haServiceTriggerCurCfgIndex }
    ::= { haServiceTriggerCurCfgTable 1 }

HaServiceTriggerCurCfgEntry ::= SEQUENCE {
    haServiceTriggerCurCfgIndex            DisplayString,
    haServiceTriggerCurCfgl4Reals          INTEGER
}

haServiceTriggerCurCfgIndex OBJECT-TYPE
    SYNTAX DisplayString (SIZE(1..32))
    MAX-ACCESS  read-only
    STATUS current
    DESCRIPTION
        "The service ID number in alphanumeric.
	Note:This mib is not supported for VX instance of virtualization."
    ::= { haServiceTriggerCurCfgEntry 1 }

haServiceTriggerCurCfgl4Reals OBJECT-TYPE
    SYNTAX  INTEGER {
               enabled(1),
               disabled(2),
               unsupported(2147483647)
            }
    MAX-ACCESS  read-only
    STATUS  current
    DESCRIPTION
            "Enable or disable tracking L4 real servers.
	Note:This mib is not supported for VX instance of virtualization."
    ::= { haServiceTriggerCurCfgEntry 2 }

haServiceTriggerNewCfgTable OBJECT-TYPE
    SYNTAX  SEQUENCE OF HaServiceTriggerNewCfgEntry
    MAX-ACCESS  not-accessible
    STATUS current
    DESCRIPTION
        "The table of trigger configurations.
	Note:This mib is not supported for VX instance of virtualization."
    ::= { haServiceTrigger 2 }

haServiceTriggerNewCfgEntry OBJECT-TYPE
    SYNTAX  HaServiceTriggerNewCfgEntry
    MAX-ACCESS  not-accessible
    STATUS current
    DESCRIPTION
        "Information about a particular trigger configuration.
	Note:This mib is not supported for VX instance of virtualization."
    INDEX   { haServiceTriggerNewCfgIndex }
    ::= { haServiceTriggerNewCfgTable 1 }

HaServiceTriggerNewCfgEntry ::= SEQUENCE {
    haServiceTriggerNewCfgIndex            DisplayString,
    haServiceTriggerNewCfgl4Reals          INTEGER
}

haServiceTriggerNewCfgIndex OBJECT-TYPE
    SYNTAX DisplayString (SIZE(1..32))
    MAX-ACCESS  read-only
    STATUS current
    DESCRIPTION
        "The service ID number in alphanumeric.
	Note:This mib is not supported for VX instance of virtualization."
    ::= { haServiceTriggerNewCfgEntry 1 }

haServiceTriggerNewCfgl4Reals OBJECT-TYPE
    SYNTAX  INTEGER {
               enabled(1),
               disabled(2),
               unsupported(2147483647)
            }
    MAX-ACCESS  read-create
    STATUS  current
    DESCRIPTION
            "Enable or disable tracking L4 real servers.
	Note:This mib is not supported for VX instance of virtualization."
    ::= { haServiceTriggerNewCfgEntry 2 }

-- HA Service Trigger Ifs menu

haServiceTriggerIfs       OBJECT IDENTIFIER ::= { haServiceTrigger 3 }

haServiceTriggerIfsNewCfgTable OBJECT-TYPE
    SYNTAX  SEQUENCE OF HaServiceTriggerIfsNewCfgEntry
    MAX-ACCESS  not-accessible
    STATUS current
    DESCRIPTION
        "The table of tracking interface configurations.
	Note:This mib is not supported for VX instance of virtualization."
    ::= { haServiceTriggerIfs 1 }

haServiceTriggerIfsNewCfgEntry OBJECT-TYPE
    SYNTAX  HaServiceTriggerIfsNewCfgEntry
    MAX-ACCESS  not-accessible
    STATUS current
    DESCRIPTION
        "Information about a particular tracking interface configuration.
	Note:This mib is not supported for VX instance of virtualization."
    INDEX   { haServiceTriggerIfsNewCfgIndex }
    ::= { haServiceTriggerIfsNewCfgTable 1 }

HaServiceTriggerIfsNewCfgEntry ::= SEQUENCE {
    haServiceTriggerIfsNewCfgIndex                DisplayString,
    haServiceNewCfgTrigIfTrackAdd              INTEGER,
    haServiceNewCfgTrigIfTrackExclude          INTEGER
}

haServiceTriggerIfsNewCfgIndex OBJECT-TYPE
    SYNTAX DisplayString (SIZE(1..32))
    MAX-ACCESS  read-only
    STATUS current
    DESCRIPTION
        "The service ID number in alphanumeric.
	Note:This mib is not supported for VX instance of virtualization."
    ::= { haServiceTriggerIfsNewCfgEntry 1 }


haServiceNewCfgTrigIfTrackAdd OBJECT-TYPE
    SYNTAX  INTEGER (1..256)
    MAX-ACCESS  read-create
    STATUS  current
    DESCRIPTION
             "Add interface to tracking list.
	Note:This mib is not supported for VX instance of virtualization."
    ::= { haServiceTriggerIfsNewCfgEntry 2 }

haServiceTrackIfsTable OBJECT-TYPE
    SYNTAX  SEQUENCE OF HaServiceTrackIfsEntry
    MAX-ACCESS  not-accessible
    STATUS current
    DESCRIPTION
        "The table of tracking interface.
	Note:This mib is not supported for VX instance of virtualization."
    ::= { haServiceTriggerIfs 2 }

haServiceTrackIfsEntry OBJECT-TYPE
    SYNTAX  HaServiceTrackIfsEntry
    MAX-ACCESS  not-accessible
    STATUS current
    DESCRIPTION
        "Information about a tracking interface.
	Note:This mib is not supported for VX instance of virtualization."
    INDEX   { haServiceTrackIfIndex,haTrackIfIndex }
    ::= { haServiceTrackIfsTable 1 }

HaServiceTrackIfsEntry ::= SEQUENCE {
    haServiceTrackIfIndex        DisplayString,
    haTrackIfIndex               INTEGER 
}

haServiceTrackIfIndex OBJECT-TYPE
    SYNTAX DisplayString (SIZE(1..32))
    MAX-ACCESS  read-only
    STATUS current
    DESCRIPTION
        "The service ID number in alphanumeric.
	Note:This mib is not supported for VX instance of virtualization."
    ::= { haServiceTrackIfsEntry 1 }

haTrackIfIndex OBJECT-TYPE
    SYNTAX  INTEGER (1..256)
    MAX-ACCESS  read-only
    STATUS current
    DESCRIPTION
        "The tracking interface number.
	Note:This mib is not supported for VX instance of virtualization."
    ::= { haServiceTrackIfsEntry 2 }

-- HA Gateway track menu

haServiceGwTrack       OBJECT IDENTIFIER ::= { haServiceTrigger 4 }

haServiceTriggerGwCurCfgTable OBJECT-TYPE
    SYNTAX  SEQUENCE OF HaServiceTriggerGwCurCfgEntry
    MAX-ACCESS  not-accessible
    STATUS current
    DESCRIPTION
        "The table of gateway tracking configurations.
	Note:This mib is not supported for VX instance of virtualization."
    ::= { haServiceGwTrack 1 }

haServiceTriggerGwCurCfgEntry OBJECT-TYPE
    SYNTAX  HaServiceTriggerGwCurCfgEntry
    MAX-ACCESS  not-accessible
    STATUS current
    DESCRIPTION
        "Information about a particular gateway tracking configuration.
	Note:This mib is not supported for VX instance of virtualization."
    INDEX   { haServiceTriggerGwCurCfgIndex }
    ::= { haServiceTriggerGwCurCfgTable 1 }

HaServiceTriggerGwCurCfgEntry ::= SEQUENCE {
    haServiceTriggerGwCurCfgIndex              DisplayString,
    haServiceCurCfgTrigGwTrackState            INTEGER
}

haServiceTriggerGwCurCfgIndex OBJECT-TYPE
    SYNTAX DisplayString (SIZE(1..32))
    MAX-ACCESS  read-only
    STATUS current
    DESCRIPTION
        "The service ID number in alphanumeric.
	Note:This mib is not supported for VX instance of virtualization."
    ::= { haServiceTriggerGwCurCfgEntry 1 }


haServiceCurCfgTrigGwTrackState OBJECT-TYPE
    SYNTAX  INTEGER {
              enabled(1),
              disabled(2),
              unsupported(2147483647)
            }
    MAX-ACCESS  read-only
    STATUS  current
    DESCRIPTION
             "Enable or disable gateway tracking.
	Note:This mib is not supported for VX instance of virtualization."
    ::= { haServiceTriggerGwCurCfgEntry 2 }

haServiceTriggerGwNewCfgTable OBJECT-TYPE
    SYNTAX  SEQUENCE OF HaServiceTriggerGwNewCfgEntry
    MAX-ACCESS  not-accessible
    STATUS current
    DESCRIPTION
        "The table of trigger gateway configurations.
	Note:This mib is not supported for VX instance of virtualization."
    ::= { haServiceGwTrack 2 }

haServiceTriggerGwNewCfgEntry OBJECT-TYPE
    SYNTAX  HaServiceTriggerGwNewCfgEntry
    MAX-ACCESS  not-accessible
    STATUS current
    DESCRIPTION
        "Information about a trigger gateway configuration.
	Note:This mib is not supported for VX instance of virtualization."
    INDEX   { haServiceTriggerGwNewCfgIndex }
    ::= { haServiceTriggerGwNewCfgTable 1 }

HaServiceTriggerGwNewCfgEntry ::= SEQUENCE {
    haServiceTriggerGwNewCfgIndex              DisplayString,
    haServiceNewCfgTrigGwTrackState            INTEGER,
    haServiceNewCfgTrigGwTrackAdd              INTEGER,
    haServiceNewCfgTrigGwTrackExclude          INTEGER
}

haServiceTriggerGwNewCfgIndex OBJECT-TYPE
    SYNTAX DisplayString (SIZE(1..32))
    MAX-ACCESS  read-only
    STATUS current
    DESCRIPTION
        "The service ID number in alphanumeric.
	Note:This mib is not supported for VX instance of virtualization."
    ::= { haServiceTriggerGwNewCfgEntry 1 }

haServiceNewCfgTrigGwTrackState OBJECT-TYPE
    SYNTAX  INTEGER {
              enabled(1),
              disabled(2),
              unsupported(2147483647)
            }
    MAX-ACCESS  read-write
    STATUS  current
    DESCRIPTION
             "Enable or disable gateway tracking.
	Note:This mib is not supported for VX instance of virtualization."
    ::= { haServiceTriggerGwNewCfgEntry 2 }

haServiceNewCfgTrigGwTrackAdd OBJECT-TYPE
    SYNTAX  INTEGER (1..259)
    MAX-ACCESS  read-write
    STATUS  current
    DESCRIPTION
             "Add gateway to tracking list.
	Note:This mib is not supported for VX instance of virtualization."
    ::= { haServiceTriggerGwNewCfgEntry 3 }

haServiceNewCfgTrigGwTrackExclude OBJECT-TYPE
    SYNTAX  INTEGER (1..259)
    MAX-ACCESS  read-write
    STATUS  current
    DESCRIPTION
             "Exclude gateway to tracking list.
	Note:This mib is not supported for VX instance of virtualization."
    ::= { haServiceTriggerGwNewCfgEntry 4 }

haServiceNewCfgTrigIfTrackExclude OBJECT-TYPE
    SYNTAX  INTEGER (1..256)
    MAX-ACCESS  read-create
    STATUS  current
    DESCRIPTION
             "Exclude interface from tracking list.
	Note:This mib is not supported for VX instance of virtualization."
    ::= { haServiceTriggerIfsNewCfgEntry 3 }

haServiceTrackGwsTable OBJECT-TYPE
    SYNTAX  SEQUENCE OF HaServiceTrackGwsEntry
    MAX-ACCESS  not-accessible
    STATUS current
    DESCRIPTION
        "The table of gateway tracking list.
	Note:This mib is not supported for VX instance of virtualization."
    ::= { haServiceGwTrack 3 }

haServiceTrackGwsEntry OBJECT-TYPE
    SYNTAX  HaServiceTrackGwsEntry
    MAX-ACCESS  not-accessible
    STATUS current
    DESCRIPTION
        "Information about gateway tracking list.
	Note:This mib is not supported for VX instance of virtualization."
    INDEX   { haServiceTrackGwIndex,haTrackGwIndex }
    ::= { haServiceTrackGwsTable 1 }

HaServiceTrackGwsEntry ::= SEQUENCE {
    haServiceTrackGwIndex        DisplayString,
    haTrackGwIndex               INTEGER 
}

haServiceTrackGwIndex OBJECT-TYPE
    SYNTAX DisplayString (SIZE(1..32))
    MAX-ACCESS  read-only
    STATUS current
    DESCRIPTION
        "The service ID number in alphanumeric.
	Note:This mib is not supported for VX instance of virtualization."
    ::= { haServiceTrackGwsEntry 1 }

haTrackGwIndex OBJECT-TYPE
    SYNTAX  INTEGER (1..256)
    MAX-ACCESS  read-only
    STATUS current
    DESCRIPTION
        " Added gateway to tracking list.
	Note:This mib is not supported for VX instance of virtualization."
    ::= { haServiceTrackGwsEntry 2 }

-- HA Real Tracking

haServiceRealTrack OBJECT IDENTIFIER ::= { haServiceTrigger 5 }

haServiceTriggerRealCurCfgTable OBJECT-TYPE
    SYNTAX SEQUENCE OF HaServiceTriggerRealCurCfgEntry 
    MAX-ACCESS  not-accessible
    STATUS current
    DESCRIPTION
        "The table of real tracking configurations.
	Note:This mib is not supported for VX instance of virtualization."
    ::= { haServiceRealTrack 1 }

haServiceTriggerRealCurCfgEntry OBJECT-TYPE
    SYNTAX HaServiceTriggerRealCurCfgEntry 
    MAX-ACCESS  not-accessible
    STATUS current
    DESCRIPTION
        "Information about a particular real tracking configuration.
	Note:This mib is not supported for VX instance of virtualization."

    INDEX   { haServiceTriggerRealCurCfgIndex }
    ::= { haServiceTriggerRealCurCfgTable 1 }

HaServiceTriggerRealCurCfgEntry ::= SEQUENCE {
    haServiceTriggerRealCurCfgIndex              DisplayString,
    haServiceCurCfgTrigRealTrkState            INTEGER,
    haServiceCurCfgTrigAllRemRealState      INTEGER,
    haServiceCurCfgTrigRealTrkAutoOptState  INTEGER
}

haServiceTriggerRealCurCfgIndex OBJECT-TYPE
    SYNTAX DisplayString (SIZE(1..32))
    MAX-ACCESS  read-only
    STATUS current
    DESCRIPTION
        "The service ID number in alphanumeric.
	Note:This mib is not supported for VX instance of virtualization."
    ::= { haServiceTriggerRealCurCfgEntry 1 }

haServiceCurCfgTrigRealTrkState OBJECT-TYPE
    SYNTAX  INTEGER {
              enabled(1),
              disabled(2),
              unsupported(2147483647)
            }
    MAX-ACCESS  read-only
    STATUS  current
    DESCRIPTION
             "Enable or disable real tracking.
	Note:This mib is not supported for VX instance of virtualization."
    ::= { haServiceTriggerRealCurCfgEntry 2 }

haServiceCurCfgTrigAllRemRealState OBJECT-TYPE
    SYNTAX  INTEGER {
              aadd(1),
              arem(2),
              unsupported(2147483647)
            }
    MAX-ACCESS  read-only
    STATUS  current
    DESCRIPTION
             "aadd - to add all the real servers to tracking.
              arem - to remove all the real servers from tracking.
	Note:This mib is not supported for VX instance of virtualization."
    ::= { haServiceTriggerRealCurCfgEntry 3 }

haServiceCurCfgTrigRealTrkAutoOptState OBJECT-TYPE
    SYNTAX  INTEGER {
              enabled(1),
              disabled(2),
              unsupported(2147483647)
            }
    MAX-ACCESS  read-only
    STATUS  current
    DESCRIPTION
        "The AutoOpt Flag.
	Note:This mib is not supported for VX instance of virtualization."
    ::= { haServiceTriggerRealCurCfgEntry 4 }
    
haServiceTriggerRealNewCfgTable OBJECT-TYPE
    SYNTAX SEQUENCE OF HaServiceTriggerRealNewCfgEntry 
    MAX-ACCESS  not-accessible
    STATUS current
    DESCRIPTION
        "The table of trigger real configurations.
	Note:This mib is not supported for VX instance of virtualization."
    ::= { haServiceRealTrack 2 }

haServiceTriggerRealNewCfgEntry OBJECT-TYPE
    SYNTAX  HaServiceTriggerRealNewCfgEntry
    MAX-ACCESS  not-accessible
    STATUS current
    DESCRIPTION
        "Information about a trigger real configuration.
	Note:This mib is not supported for VX instance of virtualization."
    INDEX   { haServiceTriggerRealNewCfgIndex }
    ::= { haServiceTriggerRealNewCfgTable 1 }

HaServiceTriggerRealNewCfgEntry ::= SEQUENCE {
    haServiceTriggerRealNewCfgIndex              DisplayString,
    haServiceNewCfgTrigRealTrkState              INTEGER,
    haServiceNewCfgTrigAllRemRealState           INTEGER,
    haServiceNewCfgTrigAddReals                  DisplayString,
    haServiceNewCfgTrigRemReals                  DisplayString,
    haServiceNewCfgTrigRealTrkAutoOptState  	 INTEGER
}

haServiceTriggerRealNewCfgIndex OBJECT-TYPE
    SYNTAX DisplayString (SIZE(1..32))
    MAX-ACCESS  read-only
    STATUS current
    DESCRIPTION
        "The service ID number in alphanumeric.
	Note:This mib is not supported for VX instance of virtualization."
    ::= { haServiceTriggerRealNewCfgEntry 1 }


haServiceNewCfgTrigRealTrkState OBJECT-TYPE
    SYNTAX  INTEGER {
              enabled(1),
              disabled(2),
              unsupported(2147483647)
            }
    MAX-ACCESS  read-write
    STATUS  current
    DESCRIPTION
             "Enable or disable real tracking.
	Note:This mib is not supported for VX instance of virtualization."
    ::= { haServiceTriggerRealNewCfgEntry 2 }

haServiceNewCfgTrigAllRemRealState OBJECT-TYPE
    SYNTAX  INTEGER {
              aadd(1),
              arem(2),
              unsupported(2147483647)
            }
    MAX-ACCESS  read-write
    STATUS  current
    DESCRIPTION
             "Select aadd - to add all the real servers to tracking.
              Select arem - to remove all the real servers from tracking.
	Note:This mib is not supported for VX instance of virtualization."
    ::= { haServiceTriggerRealNewCfgEntry 3 }


haServiceNewCfgTrigAddReals OBJECT-TYPE
    SYNTAX DisplayString (SIZE(1..255))
    MAX-ACCESS  read-create
    STATUS  current
    DESCRIPTION
        "The real server to be added to the group. When read, 0 is returned.
	Note:This mib is not supported for VX instance of virtualization."
    ::= { haServiceTriggerRealNewCfgEntry 4 }

haServiceNewCfgTrigRemReals OBJECT-TYPE
    SYNTAX DisplayString (SIZE(1..255))
    MAX-ACCESS  read-create
    STATUS  current
    DESCRIPTION
        "The real server to be removed to the group. When read, 0 is returned.
	Note:This mib is not supported for VX instance of virtualization."
    ::= { haServiceTriggerRealNewCfgEntry 5 }

haServiceNewCfgTrigRealTrkAutoOptState OBJECT-TYPE
    SYNTAX  INTEGER {
              enabled(1),
              disabled(2),
              unsupported(2147483647)
            }
    MAX-ACCESS  read-only
    STATUS  current
    DESCRIPTION
        "The AutoOpt Flag.
	Note:This mib is not supported for VX instance of virtualization."
    ::= { haServiceTriggerRealNewCfgEntry 6 }
    
    
-- HA Real association to the HA Group

haServiceRealTable OBJECT-TYPE
    SYNTAX  SEQUENCE OF HaServiceRealEntry
    MAX-ACCESS  not-accessible
    STATUS current
    DESCRIPTION
        "The table of Real to HA group.
	Note:This mib is not supported for VX instance of virtualization."
    ::= { haServiceTrigger 6 }

haServiceRealEntry OBJECT-TYPE
    SYNTAX  HaServiceRealEntry
    MAX-ACCESS  not-accessible
    STATUS current
    DESCRIPTION
        "Information about a Real to HA group.
	Note:This mib is not supported for VX instance of virtualization."
    INDEX   { haServiceGrpIndex,haServiceRealIndex }
    ::= { haServiceRealTable 1 }

HaServiceRealEntry ::= SEQUENCE {
    haServiceGrpIndex       DisplayString,
    haServiceRealIndex    DisplayString
}

haServiceGrpIndex OBJECT-TYPE
    SYNTAX DisplayString (SIZE(1..32))
    MAX-ACCESS  read-only
    STATUS current
    DESCRIPTION
        "The service ID number in alphanumeric.
	Note:This mib is not supported for VX instance of virtualization."
    ::= { haServiceRealEntry 1 }

haServiceRealIndex OBJECT-TYPE
    SYNTAX DisplayString (SIZE(1..255))
    MAX-ACCESS  read-only
    STATUS current
    DESCRIPTION
        "The Real ID number in alphanumeric.
	Note:This mib is not supported for VX instance of virtualization."
    ::= { haServiceRealEntry 2 }

-- HA Service VIP trigger
haServiceVipTrack       OBJECT IDENTIFIER ::= { haServiceTrigger 7 }

-- CUR HA Service VIP trigger
haServiceTriggerVipCurCfgTable OBJECT-TYPE
    SYNTAX  SEQUENCE OF HaServiceTriggerVipCurCfgEntry
    MAX-ACCESS  not-accessible
    STATUS current
    DESCRIPTION
        "The table of HA service VIP tracking configurations."
    ::= { haServiceVipTrack 1 } 

haServiceTriggerVipCurCfgEntry OBJECT-TYPE
    SYNTAX  HaServiceTriggerVipCurCfgEntry
    MAX-ACCESS  not-accessible
    STATUS current
    DESCRIPTION
        "Information about a particular HA service VIP tracking configuration."
    INDEX   { haServiceTriggerVipCurCfgIndex }
    ::= { haServiceTriggerVipCurCfgTable 1 }
    
HaServiceTriggerVipCurCfgEntry ::= SEQUENCE {
    haServiceTriggerVipCurCfgIndex      DisplayString,
    haServiceCurCfgTrigVipTrackState    INTEGER
}

haServiceTriggerVipCurCfgIndex OBJECT-TYPE
    SYNTAX  DisplayString (SIZE(1..32))
    MAX-ACCESS  read-only
    STATUS  current
    DESCRIPTION
        "The service ID number in alphanumeric."
    ::= { haServiceTriggerVipCurCfgEntry 1 }

haServiceCurCfgTrigVipTrackState OBJECT-TYPE
    SYNTAX  INTEGER {
              enabled(1),
              disabled(2)
            }
    MAX-ACCESS  read-only
    STATUS  current
    DESCRIPTION
             "Enable or disable VIP tracking."
    ::= { haServiceTriggerVipCurCfgEntry 2 }
    
-- NEW CFG HA Service VIP trigger
haServiceTriggerVipNewCfgTable OBJECT-TYPE
    SYNTAX  SEQUENCE OF HaServiceTriggerVipNewCfgEntry
    MAX-ACCESS  not-accessible
    STATUS current
    DESCRIPTION
        "The table of HA service VIP tracking configurations."
    ::= { haServiceVipTrack 2 }
    
haServiceTriggerVipNewCfgEntry OBJECT-TYPE
    SYNTAX  HaServiceTriggerVipNewCfgEntry
    MAX-ACCESS  not-accessible
    STATUS current
    DESCRIPTION
        "Information about a particular HA service VIP tracking  configuration."
    INDEX   { haServiceTriggerVipNewCfgIndex }
    ::= { haServiceTriggerVipNewCfgTable 1 }

HaServiceTriggerVipNewCfgEntry ::= SEQUENCE {
    haServiceTriggerVipNewCfgIndex      DisplayString,
    haServiceNewCfgTrigVipTrackState    INTEGER
}

haServiceTriggerVipNewCfgIndex OBJECT-TYPE
    SYNTAX  DisplayString (SIZE(1..32))
    MAX-ACCESS  read-only
    STATUS  current
    DESCRIPTION
        "The service ID number in alphanumeric."
    ::= { haServiceTriggerVipNewCfgEntry 1 }

haServiceNewCfgTrigVipTrackState OBJECT-TYPE
    SYNTAX  INTEGER {
              enabled(1),
              disabled(2)
            }
    MAX-ACCESS  read-write
    STATUS  current
    DESCRIPTION
             "Enable or disable VIP tracking."
    ::= { haServiceTriggerVipNewCfgEntry 2 }
    
-- CUR HA service VIP - adding VIRT & its services
haServiceTriggerVipServCurCfgTable OBJECT-TYPE
    SYNTAX  SEQUENCE OF HaServiceTriggerVipServCurCfgEntry
    MAX-ACCESS  not-accessible
    STATUS current
    DESCRIPTION
        "The table of VIP - virt service tracking configurations."
    ::= { haServiceVipTrack 3 } 

haServiceTriggerVipServCurCfgEntry OBJECT-TYPE
    SYNTAX  HaServiceTriggerVipServCurCfgEntry
    MAX-ACCESS  not-accessible
    STATUS current
    DESCRIPTION
        "Information about a particular VIP - virt service tracking configuration."
    INDEX   { haServiceTriggerVipServCurCfgIndex, haServiceTriggerVipServCurCfgVirtIndex }
    ::= { haServiceTriggerVipServCurCfgTable 1 }
    
HaServiceTriggerVipServCurCfgEntry ::= SEQUENCE {
    haServiceTriggerVipServCurCfgIndex      DisplayString,
    haServiceTriggerVipServCurCfgVirtIndex  DisplayString,
    haServiceCurCfgTrigVipServTrackState    INTEGER,
    haServiceCurCfgTrigVipServTrackType     INTEGER
}

haServiceTriggerVipServCurCfgIndex OBJECT-TYPE
    SYNTAX  DisplayString (SIZE(1..32))
    MAX-ACCESS  read-only
    STATUS  current
    DESCRIPTION
        "The service ID number in alphanumeric."
    ::= { haServiceTriggerVipServCurCfgEntry 1 }

haServiceTriggerVipServCurCfgVirtIndex OBJECT-TYPE
    SYNTAX  DisplayString (SIZE(1..255))
    MAX-ACCESS  read-only
    STATUS  current
    DESCRIPTION
        "The virt ID number in alphanumeric."
    ::= { haServiceTriggerVipServCurCfgEntry 2 }
    
haServiceCurCfgTrigVipServTrackState OBJECT-TYPE
    SYNTAX  INTEGER {
              enabled(1),
              disabled(2)
            }
    MAX-ACCESS  read-only
    STATUS  current
    DESCRIPTION
             "Enable or disable VIP - virt tracking."
    ::= { haServiceTriggerVipServCurCfgEntry 3 }
    
haServiceCurCfgTrigVipServTrackType OBJECT-TYPE
    SYNTAX  INTEGER {
        any(1),
        all(2)
        }
    MAX-ACCESS  read-only
    STATUS  current
    DESCRIPTION
        "Defines tracking type for services (vports) configured under specific virt any(default)/all."
    ::= { haServiceTriggerVipServCurCfgEntry 4 }
    

-- NEW CFG HA VIP track menu    
haServiceTriggerVipServNewCfgTable OBJECT-TYPE
    SYNTAX  SEQUENCE OF HaServiceTriggerVipServNewCfgEntry
    MAX-ACCESS  not-accessible
    STATUS current
    DESCRIPTION
        "The table of trigger VIP configurations."
    ::= { haServiceVipTrack 4 }
    
haServiceTriggerVipServNewCfgEntry OBJECT-TYPE
    SYNTAX  HaServiceTriggerVipServNewCfgEntry
    MAX-ACCESS  not-accessible
    STATUS current
    DESCRIPTION
        "Information about a particular HA service VIP tracking configuration."
    INDEX   { haServiceTriggerVipServNewCfgIndex, haServiceTriggerVipServNewCfgVirtIndex }
    ::= { haServiceTriggerVipServNewCfgTable 1 }

HaServiceTriggerVipServNewCfgEntry ::= SEQUENCE {
    haServiceTriggerVipServNewCfgIndex      DisplayString,
    haServiceTriggerVipServNewCfgVirtIndex  DisplayString,
    haServiceNewCfgTrigVipServTrackState    INTEGER,
    haServiceNewCfgTrigVipServTrackAddSrv   Integer32,
    haServiceNewCfgTrigVipServTrackRemSrv   Integer32,
    haServiceNewCfgTrigVipServTrackType     INTEGER,
	haServiceNewCfgTrigVipServTrackMapList OCTET STRING
}

haServiceTriggerVipServNewCfgIndex OBJECT-TYPE
    SYNTAX  DisplayString (SIZE(1..32))
    MAX-ACCESS  read-only
    STATUS  current
    DESCRIPTION
        "The service ID number in alphanumeric."
    ::= { haServiceTriggerVipServNewCfgEntry 1 }

haServiceTriggerVipServNewCfgVirtIndex OBJECT-TYPE
    SYNTAX  DisplayString (SIZE(1..255))
    MAX-ACCESS  read-only
    STATUS  current
    DESCRIPTION
        "The virt ID number in alphanumeric."
    ::= { haServiceTriggerVipServNewCfgEntry 2 }    

haServiceNewCfgTrigVipServTrackState OBJECT-TYPE
    SYNTAX  INTEGER {
              enabled(1),
              disabled(2)
            }
    MAX-ACCESS  read-write
    STATUS  current
    DESCRIPTION
             "Enable or disable virt - VIP tracking."
    ::= { haServiceTriggerVipServNewCfgEntry 3 }

haServiceNewCfgTrigVipServTrackAddSrv OBJECT-TYPE
    SYNTAX  Integer32
    MAX-ACCESS  read-write
    STATUS  current
    DESCRIPTION
        "The service port add for VIP trigger."
    ::= { haServiceTriggerVipServNewCfgEntry 4 }

haServiceNewCfgTrigVipServTrackRemSrv OBJECT-TYPE
    SYNTAX  Integer32
    MAX-ACCESS  read-write
    STATUS  current
    DESCRIPTION
        "The service port remove for VIP trigger."
    ::= { haServiceTriggerVipServNewCfgEntry 5 }
    
haServiceNewCfgTrigVipServTrackType OBJECT-TYPE
    SYNTAX  INTEGER {
        any(1),
        all(2)
        }
    MAX-ACCESS  read-write
    STATUS  current
    DESCRIPTION
        "Defines tracking type for services (vports) configured under specific virt any(default)/all."
    ::= { haServiceTriggerVipServNewCfgEntry 6 }
    
haServiceNewCfgTrigVipServTrackMapList OBJECT-TYPE
    SYNTAX OCTET STRING
    MAX-ACCESS read-only
    STATUS current
    DESCRIPTION
        "The services present in the vip of HA service. 
         The services are presented in a bitmap format.

         in receiving order:

         OCTET 1 
         xxxxxxxx
         ||    ||___ Rmap 8
         ||    |____ Rmap 7
         ||      .    .   .
         ||_________ Rmap 2
         |__________ Rmap 1

         where x : 1 - The represented service is selected
         0 - The represented service is not selected.
         Note:This mib is not supported for VX instance of virtualization.
        Defines tracking type for services (vports) selected or not under specific virt."
    ::= { haServiceTriggerVipServNewCfgEntry 7 }

haServiceTrackVipTable OBJECT-TYPE
    SYNTAX  SEQUENCE OF HaServiceTrackVipsEntry
    MAX-ACCESS  not-accessible
    STATUS current
    DESCRIPTION
        "The table of VIP tracking list."
    ::= { haServiceVipTrack 5 } 

haServiceTrackVipsEntry OBJECT-TYPE
    SYNTAX  HaServiceTrackVipsEntry
    MAX-ACCESS  not-accessible
    STATUS current
    DESCRIPTION
        "Information about a VIP to HA service group."
    INDEX   { haServiceVirtGrpIndex,haServiceVirtIndex,haServiceVirtSrvIndex }
    ::= { haServiceTrackVipTable 1 }
    
HaServiceTrackVipsEntry ::= SEQUENCE {
    haServiceVirtGrpIndex       DisplayString,
    haServiceVirtIndex       DisplayString,
    haServiceVirtSrvIndex    DisplayString
}

haServiceVirtGrpIndex OBJECT-TYPE
    SYNTAX DisplayString (SIZE(1..32))
    MAX-ACCESS  read-only
    STATUS current
    DESCRIPTION
        "The service ID number in alphanumeric."
    ::= { haServiceTrackVipsEntry 1 }
    
haServiceVirtIndex OBJECT-TYPE
    SYNTAX DisplayString (SIZE(1..255))
    MAX-ACCESS  read-only
    STATUS current
    DESCRIPTION
        "The virt ID number in alphanumeric."
    ::= { haServiceTrackVipsEntry 2 }

haServiceVirtSrvIndex OBJECT-TYPE
    SYNTAX DisplayString (SIZE(1..32))
    MAX-ACCESS  read-only
    STATUS current
    DESCRIPTION
        "The virt service port number."
    ::= { haServiceTrackVipsEntry 3 }

-- NEW CFG service HA VIP track scalar mib menu
  
 haServiceTriggerVipServIdxTable OBJECT-TYPE
     SYNTAX  SEQUENCE OF HaServiceTriggerVipServIdxTableEntry
     MAX-ACCESS  not-accessible
     STATUS current
     DESCRIPTION
         "The table of trigger VIP configuration."
     ::= { haServiceVipTrack 6 }
 
 haServiceTriggerVipServIdxTableEntry OBJECT-TYPE
     SYNTAX  HaServiceTriggerVipServIdxTableEntry
     MAX-ACCESS  not-accessible
     STATUS current
     DESCRIPTION
         "Information about a particular gateway tracking configuration."
    INDEX   {haServiceTriggerVipServIdxCfgIndex, haServiceTriggerVipServIdxTableIndex }
     ::= { haServiceTriggerVipServIdxTable 1 }
 
 HaServiceTriggerVipServIdxTableEntry ::= SEQUENCE {
     haServiceTriggerVipServIdxCfgIndex     DisplayString,
     haServiceTriggerVipServIdxTableIndex   Integer32,
     haServiceTriggerVipServIdxName         DisplayString,
     haServiceTriggerVipServIdxVport        INTEGER,
     haServiceTriggerVipServIdxTrackType    INTEGER
 }
 
   haServiceTriggerVipServIdxCfgIndex OBJECT-TYPE
    SYNTAX DisplayString (SIZE(1..32))
    MAX-ACCESS read-only
    STATUS current
    DESCRIPTION
        "The HA service ID number in alphanumeric.
         Note:This mib is not supported for VX instance of virtualization."
    ::= { haServiceTriggerVipServIdxTableEntry 1 }
    
   haServiceTriggerVipServIdxTableIndex OBJECT-TYPE
     SYNTAX Integer32
     MAX-ACCESS  read-only
     STATUS  current
     DESCRIPTION
        "The internal index of a VIP and service for service ha.
         Note: This MIB object is not supported for VX instance of virtualization."
     ::= { haServiceTriggerVipServIdxTableEntry 2 }

 haServiceTriggerVipServIdxName OBJECT-TYPE
    SYNTAX  DisplayString (SIZE(1..255))
    MAX-ACCESS  read-only
    STATUS  current
    DESCRIPTION
        "The alphanumeric id of the virtual server.
         Note: This MIB object is not supported for VX instance of virtualization."        
    ::= { haServiceTriggerVipServIdxTableEntry 3 }
    
 haServiceTriggerVipServIdxVport OBJECT-TYPE
    SYNTAX  INTEGER (1..65534)
    MAX-ACCESS  read-only
    STATUS  current
    DESCRIPTION
        "The virtual port number of the service."
    ::= { haServiceTriggerVipServIdxTableEntry 4 }    

 haServiceTriggerVipServIdxTrackType  OBJECT-TYPE
    SYNTAX  INTEGER {
        any(1),
        all(2)
        }
    MAX-ACCESS  read-only
    STATUS  current
    DESCRIPTION
        "Defines tracking type for services (vports) configured under specific virt any(default)/all."
    ::= { haServiceTriggerVipServIdxTableEntry 5 }
-- NEW Cfg Table for vip tracking in service HA mode to add/remove.

haServiceTriggerVipServAddRmvTable OBJECT-TYPE
    SYNTAX SEQUENCE OF HaServiceTriggerVipServAddRmvEntry
    MAX-ACCESS not-accessible
    STATUS current
    DESCRIPTION
        "The configuration table for vip and service tracking in service HA mode.
         Note:This mib is not supported for VX instance of virtualization."
    ::= { haServiceVipTrack 7 }

haServiceTriggerVipServAddRmvEntry OBJECT-TYPE
    SYNTAX HaServiceTriggerVipServAddRmvEntry
    MAX-ACCESS not-accessible
    STATUS current
    DESCRIPTION
        "Tabular entry for the new configuration of the vip tracking in service HA mode.
         Note:This mib is not supported for VX instance of virtualization."
    INDEX { haServiceTriggerVipServIndex }
    ::= { haServiceTriggerVipServAddRmvTable 1 }

HaServiceTriggerVipServAddRmvEntry ::= SEQUENCE {
    haServiceTriggerVipServIndex      DisplayString,
    haServiceNewCfgTriggerVipServAdd      Integer32,
    haServiceNewCfgTriggerVipServRem      Integer32
}

haServiceTriggerVipServIndex OBJECT-TYPE
    SYNTAX  DisplayString (SIZE(1..32))
    MAX-ACCESS  read-only
    STATUS  current
    DESCRIPTION
        "The service ID number in alphanumeric."
    ::= { haServiceTriggerVipServAddRmvEntry 1 }
    
haServiceNewCfgTriggerVipServAdd OBJECT-TYPE
    SYNTAX  Integer32
    MAX-ACCESS  read-write
    STATUS  current
    DESCRIPTION
        "The service port add for VIP trigger."
    ::= { haServiceTriggerVipServAddRmvEntry 2 }

haServiceNewCfgTriggerVipServRem OBJECT-TYPE
    SYNTAX  Integer32
    MAX-ACCESS  read-write
    STATUS  current
    DESCRIPTION
        "The service port remove for VIP trigger."
    ::= { haServiceTriggerVipServAddRmvEntry 3 }

haServiceTrackVipServsTable OBJECT-TYPE
    SYNTAX  SEQUENCE OF HaServiceTrackVipServsEntry
    MAX-ACCESS  not-accessible
    STATUS current
    DESCRIPTION
        "The table of VIP tracking list."
    ::= { haServiceVipTrack 8 } 
    
haServiceTrackVipServsEntry OBJECT-TYPE
    SYNTAX  HaServiceTrackVipServsEntry
    MAX-ACCESS  not-accessible
    STATUS current
    DESCRIPTION
        "Information about a VIP to HA service group."
    INDEX   { haServiceVirtGrpServsIndex,haServiceVirtServsIndex }
    ::= { haServiceTrackVipServsTable 1 }

HaServiceTrackVipServsEntry ::= SEQUENCE {
    haServiceVirtGrpServsIndex       DisplayString,
    haServiceVirtServsIndex       Integer32
}

haServiceVirtGrpServsIndex OBJECT-TYPE
    SYNTAX DisplayString (SIZE(1..32))
    MAX-ACCESS  read-only
    STATUS current
    DESCRIPTION
        "The service ID number in alphanumeric.
        Note: This MIB object is not supported for VX instance of virtualization."
    ::= { haServiceTrackVipServsEntry 1 }
    
haServiceVirtServsIndex OBJECT-TYPE
    SYNTAX Integer32
    MAX-ACCESS  read-only
    STATUS current
    DESCRIPTION
        "The internal index of a VIP and service for service ha.
        Note: This MIB object is not supported for VX instance of virtualization."
    ::= { haServiceTrackVipServsEntry 2 }
        
-- HA Service Group Tracking

haServiceGrpTrk OBJECT IDENTIFIER ::= { haServiceTrigger 8 }

-- CUR HA Service Group Tracking Table

haServiceTriggerGrpCurCfgTable OBJECT-TYPE
    SYNTAX SEQUENCE OF HaServiceTriggerGrpCurCfgEntry
    MAX-ACCESS not-accessible
    STATUS current
    DESCRIPTION
        "The configuration table for the group tracking in service HA mode corresponding
         to the current configuration block. It will show the currently existing group
         tracking configurations which are applied by the user.
         Note:This mib is not supported for VX instance of virtualization."
    ::= { haServiceGrpTrk 1 }

haServiceTriggerGrpCurCfgEntry OBJECT-TYPE
    SYNTAX HaServiceTriggerGrpCurCfgEntry
    MAX-ACCESS not-accessible
    STATUS current
    DESCRIPTION
        "Tabular entry for the current configuration of the group tracking in service HA mode.
         Note:This mib is not supported for VX instance of virtualization."
    INDEX { haServiceTriggerGrpCurCfgIndex }
    ::= { haServiceTriggerGrpCurCfgTable 1 }

HaServiceTriggerGrpCurCfgEntry ::= SEQUENCE {
    haServiceTriggerGrpCurCfgIndex     DisplayString,
    haServiceCurCfgTriggerGrpTrkState  INTEGER
}

haServiceTriggerGrpCurCfgIndex OBJECT-TYPE
    SYNTAX DisplayString (SIZE(1..32))
    MAX-ACCESS read-only
    STATUS current
    DESCRIPTION
        "The HA Service ID number in alphanumeric.
         Note:This mib is not supported for VX instance of virtualization."
    ::= { haServiceTriggerGrpCurCfgEntry 1 }

haServiceCurCfgTriggerGrpTrkState OBJECT-TYPE
    SYNTAX INTEGER {
        enabled(1),
        disabled(2),
        unsupported(2147483647)
       }
    MAX-ACCESS read-only
    STATUS current
    DESCRIPTION
        "The current configuration state of group tracking for a particular HA service.
         It will show the current group track state that was applied by the user.
         Note:This mib is not supported for VX instance of virtualization."
    ::= { haServiceTriggerGrpCurCfgEntry 2 }

-- NEW Cfg Table for group tracking in service HA mode.

haServiceTriggerGrpNewCfgTable OBJECT-TYPE
    SYNTAX SEQUENCE OF HaServiceTriggerGrpNewCfgEntry
    MAX-ACCESS not-accessible
    STATUS current
    DESCRIPTION
        "The configuration table for group tracking in service HA mode. It will show
         the group tracking configurations that are pending for apply.
         Note:This mib is not supported for VX instance of virtualization."
    ::= { haServiceGrpTrk 2 }

haServiceTriggerGrpNewCfgEntry OBJECT-TYPE
    SYNTAX HaServiceTriggerGrpNewCfgEntry
    MAX-ACCESS not-accessible
    STATUS current
    DESCRIPTION
        "Tabular entry for the new configuration of the group tracking in service HA mode.
         Note:This mib is not supported for VX instance of virtualization."
    INDEX { haServiceTriggerGrpNewCfgIndex }
    ::= { haServiceTriggerGrpNewCfgTable 1 }

HaServiceTriggerGrpNewCfgEntry ::= SEQUENCE {
    haServiceTriggerGrpNewCfgIndex      DisplayString,
    haServiceNewCfgTriggerGrpTrkState   INTEGER,
    haServiceNewCfgTriggerGroupAdd      DisplayString,
    haServiceNewCfgTriggerGroupRem      DisplayString
}

haServiceTriggerGrpNewCfgIndex OBJECT-TYPE
    SYNTAX DisplayString (SIZE(1..32))
    MAX-ACCESS read-only
    STATUS current
    DESCRIPTION
        "The HA service ID number in alphanumeric.
         Note:This mib is not supported for VX instance of virtualization."
    ::= { haServiceTriggerGrpNewCfgEntry 1 }

haServiceNewCfgTriggerGrpTrkState OBJECT-TYPE
    SYNTAX INTEGER {
        enabled(1),
        disabled(2),
        unsupported(2147483647)
       }
    MAX-ACCESS read-write
    STATUS current
    DESCRIPTION
        "To enable or disable the group tracking for a particular HA service.
         Note:This mib is not supported for VX instance of virtualization."
    ::= { haServiceTriggerGrpNewCfgEntry 2 }

haServiceNewCfgTriggerGroupAdd OBJECT-TYPE
    SYNTAX DisplayString (SIZE(1..255))
    MAX-ACCESS read-create
    STATUS current
    DESCRIPTION
        "To add an L4 group to the group tracking list in a particular HA service.
         When read, NULL string is returned.
         Note:This mib is not supported for VX instance of virtualization."
    ::= { haServiceTriggerGrpNewCfgEntry 3 }

haServiceNewCfgTriggerGroupRem OBJECT-TYPE
    SYNTAX DisplayString(SIZE(1..255))
    MAX-ACCESS read-create
    STATUS current
    DESCRIPTION
        "To remove an L4 group from the group tracking list of an HA service.
         When read, NULL string is returned.
         Note:This mib is not supported for VX instance of virtualization."
    ::= { haServiceTriggerGrpNewCfgEntry 4 }

-- Group tracking association to the HA service

haServiceTriggerGrpTable OBJECT-TYPE
    SYNTAX SEQUENCE OF HaServiceTriggerGrpEntry
    MAX-ACCESS not-accessible
    STATUS current
    DESCRIPTION
        "The table to list down the tracked groups in each HA service.
         Note: This mib object is not supported for VX instance of virtualization."
    ::= { haServiceTrigger 9 }

haServiceTriggerGrpEntry OBJECT-TYPE
    SYNTAX HaServiceTriggerGrpEntry
    MAX-ACCESS not-accessible
    STATUS current
    DESCRIPTION
        "Tabular entry to show the association of L4 group to an HA service.
         Note: This mib object is not supported for VX instance of virtualization."
    INDEX { haServiceGroupIndex,haServiceRealGrpIndex }
    ::= { haServiceTriggerGrpTable 1 }

HaServiceTriggerGrpEntry ::= SEQUENCE {
    haServiceGroupIndex       DisplayString,
    haServiceRealGrpIndex   DisplayString
}

haServiceGroupIndex OBJECT-TYPE
    SYNTAX DisplayString (SIZE(1..32))
    MAX-ACCESS read-only
    STATUS current
    DESCRIPTION
        "The HA Service ID number in alphanumeric.
         Note: This mib object is not supported for VX instance of virtualization."
    ::= { haServiceTriggerGrpEntry 1 }

haServiceRealGrpIndex OBJECT-TYPE
    SYNTAX DisplayString(SIZE(1..255))
    MAX-ACCESS read-only
    STATUS current
    DESCRIPTION
        "The Layer 4 Real Group ID number in alphanumeric.
         Note: This mib object is not supported for VX instance of virtualization."
    ::= { haServiceTriggerGrpEntry 2 }

-- HA Trunk/LACP up criteria
haTrunk OBJECT IDENTIFIER ::= { haCfg 9 }

haTrunkTableMaxSize OBJECT-TYPE
    SYNTAX  Integer32
    MAX-ACCESS  read-only
    STATUS  current
    DESCRIPTION
        "The maximum number of entries in HA trunk table.
	Note:This mib is not supported for VX instance of virtualization."
    ::= { haTrunk 100 } -- I am sorry!!

haTrunkCurCfgTable OBJECT-TYPE
    SYNTAX  SEQUENCE OF HaTrunkCurCfgTableEntry
    MAX-ACCESS  not-accessible
    STATUS  current
    DESCRIPTION
        "The table of HA Trunk UP criteria configuration.
	Note:This mib is not supported for VX instance of virtualization."
    ::= { haTrunk 2 }

haTrunkCurCfgTableEntry OBJECT-TYPE
    SYNTAX  HaTrunkCurCfgTableEntry
    MAX-ACCESS  not-accessible
    STATUS  current
    DESCRIPTION
        "A row in the HA Trunk UP criteria configuration table.
	Note:This mib is not supported for VX instance of virtualization."
    INDEX   { haTrunkCurCfgIndex }
    ::= { haTrunkCurCfgTable 1 }

HaTrunkCurCfgTableEntry ::= SEQUENCE {
    haTrunkCurCfgIndex           Integer32,
    haTrunkCurCfgTrunkUpCriteria DisplayString
}

haTrunkCurCfgIndex OBJECT-TYPE
    SYNTAX  Integer32
    MAX-ACCESS  read-only
    STATUS  current
    DESCRIPTION 
        "The Trunk id.
	Note:This mib is not supported for VX instance of virtualization."
    ::= { haTrunkCurCfgTableEntry 1 }

haTrunkCurCfgTrunkUpCriteria OBJECT-TYPE
    SYNTAX DisplayString (SIZE(1..32))
    MAX-ACCESS  read-only
    STATUS  current
    DESCRIPTION
        "The minimum number of port up criteria for the trunk.
	Note:This mib is not supported for VX instance of virtualization."
    ::= { haTrunkCurCfgTableEntry 2 }

haTrunkNewCfgTable OBJECT-TYPE
    SYNTAX  SEQUENCE OF HaTrunkNewCfgTableEntry
    MAX-ACCESS  not-accessible
    STATUS current
    DESCRIPTION
        "The table of HA Trunk UP criteria configuration.
	Note:This mib is not supported for VX instance of virtualization."
    ::= { haTrunk 3 }

haTrunkNewCfgTableEntry OBJECT-TYPE
    SYNTAX  HaTrunkNewCfgTableEntry
    MAX-ACCESS  not-accessible
    STATUS current
    DESCRIPTION
        "A row in the HA Trunk UP criteria configuration table.
	Note:This mib is not supported for VX instance of virtualization."
    INDEX   { haTrunkNewCfgIndex }
    ::= { haTrunkNewCfgTable 1 }

HaTrunkNewCfgTableEntry ::= SEQUENCE {
    haTrunkNewCfgIndex           Integer32,
    haTrunkNewCfgTrunkUpCriteria DisplayString,
    haTrunkNewCfgTrunkRemove     INTEGER
}

haTrunkNewCfgIndex OBJECT-TYPE
    SYNTAX  Integer32
    MAX-ACCESS  read-only
    STATUS  current
    DESCRIPTION
        "The Trunk id.
	Note:This mib is not supported for VX instance of virtualization."
    ::= { haTrunkNewCfgTableEntry 1 }

haTrunkNewCfgTrunkUpCriteria OBJECT-TYPE
    SYNTAX  DisplayString (SIZE(1..32))
    MAX-ACCESS  read-create
    STATUS  current
    DESCRIPTION
        "The minimum number of port up criteria for the trunk.
	Note:This mib is not supported for VX instance of virtualization."
    ::= { haTrunkNewCfgTableEntry 2 }

haTrunkNewCfgTrunkRemove OBJECT-TYPE
    SYNTAX  INTEGER {
        other(1),
        delete(2),
        unsupported(2147483647)
    }
    MAX-ACCESS  read-create
    STATUS  current
    DESCRIPTION
        "Remove the minimum number of port up criteria for the trunk.
	Note:This mib is not supported for VX instance of virtualization."
    ::= { haTrunkNewCfgTableEntry 3 }

haLacp OBJECT IDENTIFIER ::= { haCfg 10 }

haLacpTableMaxSize OBJECT-TYPE
    SYNTAX  Integer32
    MAX-ACCESS  read-only
    STATUS  current
    DESCRIPTION
        "The maximum number of entries in the HA LACP adminkey configuration table.
	Note:This mib is not supported for VX instance of virtualization"
    ::= { haLacp 101 } -- I am so sorry!!

haLacpMaxAdminKey OBJECT-TYPE
    SYNTAX  Integer32
    MAX-ACCESS  read-only
    STATUS  current
    DESCRIPTION
        "The maximum possible LACP admin key value.
	Note:This mib is not supported for VX instance of virtualization"
    ::= { haLacp 102 } -- I am so so sorry!!

haLacpCurCfgTable OBJECT-TYPE
    SYNTAX  SEQUENCE OF HaLacpCurCfgTableEntry
    MAX-ACCESS  not-accessible
    STATUS  current
    DESCRIPTION
        "The table of HA Lacp UP criteria configuration.
	Note:This mib is not supported for VX instance of virtualization"
    ::= { haLacp 3 }

haLacpCurCfgTableEntry OBJECT-TYPE
    SYNTAX  HaLacpCurCfgTableEntry
    MAX-ACCESS  not-accessible
    STATUS  current
    DESCRIPTION
        "A row in the HA Lacp UP criteria configuration table."
    INDEX   { haLacpCurCfgAdminKey }
    ::= { haLacpCurCfgTable 1 }

HaLacpCurCfgTableEntry ::= SEQUENCE {
    haLacpCurCfgAdminKey       Integer32,
    haLacpCurCfgLacpUpCriteria DisplayString
}

haLacpCurCfgAdminKey OBJECT-TYPE
    SYNTAX  Integer32
    MAX-ACCESS  read-only
    STATUS  current
    DESCRIPTION
        "The Lacp Admin key id."
    ::= { haLacpCurCfgTableEntry 1 }

haLacpCurCfgLacpUpCriteria OBJECT-TYPE
    SYNTAX DisplayString (SIZE(1..32))
    MAX-ACCESS  read-only
    STATUS  current
    DESCRIPTION
        "The minimum number of port up criteria for the LACP admin key."
    ::= { haLacpCurCfgTableEntry 2 }

haLacpNewCfgTable OBJECT-TYPE
    SYNTAX  SEQUENCE OF HaLacpNewCfgTableEntry
    MAX-ACCESS  not-accessible
    STATUS current
    DESCRIPTION
        "The table of HA Lacp UP criteria configuration.
	Note:This mib is not supported for VX instance of virtualization"
    ::= { haLacp 4 }

haLacpNewCfgTableEntry OBJECT-TYPE
    SYNTAX  HaLacpNewCfgTableEntry
    MAX-ACCESS  not-accessible
    STATUS current
    DESCRIPTION
        "A row in the HA Lacp UP criteria configuration table."
    INDEX   { haLacpNewCfgAdminKey }
    ::= { haLacpNewCfgTable 1 }

HaLacpNewCfgTableEntry ::= SEQUENCE {
    haLacpNewCfgAdminKey       Integer32,
    haLacpNewCfgLacpUpCriteria DisplayString,
    haLacpNewCfgLacpRemove     INTEGER
}

haLacpNewCfgAdminKey OBJECT-TYPE
    SYNTAX  Integer32
    MAX-ACCESS  read-only
    STATUS  current
    DESCRIPTION
        "The Lacp Admin key id."
    ::= { haLacpNewCfgTableEntry 1 }

haLacpNewCfgLacpUpCriteria OBJECT-TYPE
    SYNTAX  DisplayString (SIZE(1..32))
    MAX-ACCESS  read-create
    STATUS  current
    DESCRIPTION
        "The minimum number of port up criteria for the LACP admin key."
    ::= { haLacpNewCfgTableEntry 2 }

haLacpNewCfgLacpRemove OBJECT-TYPE
    SYNTAX  INTEGER {
        other(1),
        delete(2),
        unsupported(2147483647)
    }
    MAX-ACCESS  read-create
    STATUS  current
    DESCRIPTION
        "Remove the minimum number of port up criteria for the LACP admin key."
    ::= { haLacpNewCfgTableEntry 3 }

haCurLPWizardCfgMode OBJECT-TYPE
     SYNTAX  INTEGER {
        disabled(1),
        vrrp(2),
        switch(3),
        service(4),
	extendedHA(5),
        unsupported(2147483647)
        }
    MAX-ACCESS  read-only
    STATUS  current
    DESCRIPTION
        "Change the High Availability Mode from the LP startup wizard.
	Note:This mib is not supported for VX instance of virtualization"
    ::= { haCfg 11 }   
    
haNewLPWizardCfgMode OBJECT-TYPE
     SYNTAX  INTEGER {
        disabled(1),
        vrrp(2),
        switch(3),
        service(4),
	extendedHA(5),
        unsupported(2147483647)
        }
    MAX-ACCESS  read-write
    STATUS  current
    DESCRIPTION
        "Change the High Availability Mode from the LP startup wizard.
	Note:This mib is not supported for VX instance of virtualization"
    ::= { haCfg 12 }

haCurCfgHAID OBJECT-TYPE
    SYNTAX  INTEGER (0..255)
    MAX-ACCESS  read-write
    STATUS  current
    DESCRIPTION
        "The HA ID for standalone and VA devices.
         Note:This mib is not supported for virtualization"
    ::= { haCfg 13 }
  
haNewCfgHAID OBJECT-TYPE
    SYNTAX  INTEGER (0..255)
    MAX-ACCESS  read-write
    STATUS  current
    DESCRIPTION
        "The HA ID for standalone and VA devices.
	Note:This mib is not supported for virtualization"
    ::= { haCfg 14 }

haCurCfgBkpVipRt OBJECT-TYPE
    SYNTAX  INTEGER {
               enabled(1),
               disabled(2),
               unsupported(2147483647)
            }
    MAX-ACCESS  read-only
    STATUS  current
    DESCRIPTION
            "Enable or disable adding vip routes in backup device.
	Note:This mib is not supported for VX instance of virtualization"
    ::= { haCfg 15 }

haNewCfgBkpVipRt OBJECT-TYPE
    SYNTAX  INTEGER {
              enabled(1),
              disabled(2),
              unsupported(2147483647)
            }
    MAX-ACCESS  read-write
    STATUS  current
    DESCRIPTION
             "Enable or disable adding vip routes in backup device.
	Note:This mib is not supported for VX instance of virtualization"
    ::= { haCfg 16 }
    
haCurCfgFmac OBJECT-TYPE
    SYNTAX  INTEGER {
               enabled(1),
               disabled(2),
	       extended(3),
               unsupported(2147483647)
            }
    MAX-ACCESS  read-only
    STATUS  current
    DESCRIPTION
        "Enable or Disable floating mac.
         Note: This mib is supported only on VA Platform."
    ::= { haCfg 17 }

haNewCfgFmac OBJECT-TYPE
    SYNTAX  INTEGER {
	       enabled(1),
	       disabled(2),
	       extended(3),
               unsupported(2147483647)
	    }
    MAX-ACCESS  read-write
    STATUS  current
    DESCRIPTION
        "Enable or Disable floating mac.
         Note: This mib is supported only on VA Platform."
    ::= { haCfg 18 }     

haCurCfgNwClGarp OBJECT-TYPE
    SYNTAX  INTEGER {
               enabled(1),
               disabled(2),
               unsupported(2147483647)
            }
    MAX-ACCESS  read-only
    STATUS  current
    DESCRIPTION
            "Enable or disable sending GARP for all the proxy IPs in the network class range.
	Note:This mib is not supported for VX instance of virtualization"
    ::= { haCfg 19 }

haNewCfgNwClGarp OBJECT-TYPE
    SYNTAX  INTEGER {
              enabled(1),
              disabled(2),
              unsupported(2147483647)
            }
    MAX-ACCESS  read-write
    STATUS  current
    DESCRIPTION
             "Enable or disable sending GARP for all the proxy IPs in the network class range.
	Note:This mib is not supported for VX instance of virtualization"
    ::= { haCfg 20 }

haCurCfgFailoverTime OBJECT-TYPE
    SYNTAX  INTEGER (0..255)
    MAX-ACCESS  read-only
    STATUS  current
    DESCRIPTION
        "The Failover delay time."
    ::= { haCfg 21 }

haNewCfgFailoverTime OBJECT-TYPE
    SYNTAX  INTEGER (0..255)
    MAX-ACCESS  read-write
    STATUS  current
    DESCRIPTION
        "The Failover delay time."
    ::= { haCfg 22 }

haCurCfgGarpIntrvl OBJECT-TYPE
    SYNTAX  INTEGER (30..600)
    MAX-ACCESS  read-only
    STATUS  current
    DESCRIPTION
        "Current garp sending interval.
    Note:This scalar is not supported for VX instance of virtualization"
    ::= { haCfg 23 }

haNewCfgGarpIntrvl OBJECT-TYPE
    SYNTAX  INTEGER (30..600)
    MAX-ACCESS  read-write
    STATUS  current
    DESCRIPTION
        "Set garp sending interval.
    Note:This scalar is not supported for VX instance of virtualization"
    ::= { haCfg 24 }
    
haCurCfgfiltpbkp OBJECT-TYPE
    SYNTAX  INTEGER {
              enabled(1),
              disabled(2),
              unsupported(2147483647)
            }
    MAX-ACCESS  read-only
    STATUS  current
    DESCRIPTION
             "Enable/disable filter processing on backup in SWITCH mode."
    ::= { haCfg 25 }

haNewCfgfiltpbkp OBJECT-TYPE
    SYNTAX  INTEGER {
              enabled(1),
              disabled(2),
              unsupported(2147483647)
            }
    MAX-ACCESS  read-write
    STATUS  current
    DESCRIPTION
             "Enable/disable filter processing on backup in SWITCH mode."
    ::= { haCfg 26 }

-- BFD MIBS START

bfdCurCfgState OBJECT-TYPE
    SYNTAX  INTEGER {
        on(1),
        off(2),
        unsupported(2147483647)
        }
    MAX-ACCESS  read-only
    STATUS  current
    DESCRIPTION
        "BFD global state.
	Note:This mib is not supported for VX instance of virtualization"
    ::= { bfdCfg 1 }

bfdNewCfgState OBJECT-TYPE
    SYNTAX  INTEGER {
        on(1),
        off(2),
        unsupported(2147483647)
        }
    MAX-ACCESS  read-write
    STATUS  current
    DESCRIPTION
        "Globally turn BFD on or off.
	Note:This mib is not supported for VX instance of virtualization"
    ::= { bfdCfg 2 }

bfdCurCfgRxInterval OBJECT-TYPE
    SYNTAX  INTEGER (100..1000)
    MAX-ACCESS  read-only
    STATUS current
    DESCRIPTION
    "BFD control packets Rx interval (in milliseconds).
    Note:This mib is not supported for VX instance of virtualization"
    ::= { bfdCfg 3 }

bfdNewCfgRxInterval OBJECT-TYPE
    SYNTAX  INTEGER (100..1000)
    MAX-ACCESS  read-write
    STATUS current
    DESCRIPTION
    "BFD control packets Rx interval (in milliseconds).
    Note:This mib is not supported for VX instance of virtualization"
    ::= { bfdCfg 4 }

bfdCurCfgMultiplier OBJECT-TYPE
    SYNTAX  INTEGER(1..10)
    MAX-ACCESS  read-only
    STATUS  current
    DESCRIPTION
        "Number of retries to declare the BFD neighbour DOWN.
	Note:This mib is not supported for VX instance of virtualization"
    ::= { bfdCfg 5 }

bfdNewCfgMultiplier OBJECT-TYPE
    SYNTAX  INTEGER(1..10)
    MAX-ACCESS  read-write
    STATUS  current
    DESCRIPTION
        "Number of retries to declare the BFD neighbour DOWN.
	Note:This mib is not supported for VX instance of virtualization"
    ::= { bfdCfg 6 }

bfdCurCfgIfBmap OBJECT-TYPE
    SYNTAX OCTET STRING
    MAX-ACCESS read-only
    STATUS current
    DESCRIPTION
        "Bitmap of interfaces currently configured for BFD in the device.

         OCTET 1  OCTET 2  .....
         xxxxxxxx xxxxxxxx .....
         ||    || |_ If 9
         ||    ||
         ||    ||___ If 8
         ||    |____ If 7
         ||      .    .   .
         ||_________ If 2
         |__________ If 1

         where x : 1 - The represented interface is selected,
         0 - The represented interface is not selected
	 Note:This mib is not supported for VX instance of virtualization"
    ::= {  bfdCfg 7 }

bfdNewCfgIfBmap OBJECT-TYPE
    SYNTAX OCTET STRING
    MAX-ACCESS read-only
    STATUS current
    DESCRIPTION
        "Bitmap of interfaces newly configured for BFD in the device i.e
         in new config (before apply).

         OCTET 1  OCTET 2  .....
         xxxxxxxx xxxxxxxx .....
         ||    || |_ If 9
         ||    ||
         ||    ||___ If 8
         ||    |____ If 7
         ||      .    .   .
         ||_________ If 2
         |__________ If 1

         where x : 1 - The represented interface is selected
         0 - The represented interface is not selected
	 Note:This mib is not supported for VX instance of virtualization"
    ::= {  bfdCfg 8 }

bfdNewCfgAddIf OBJECT-TYPE
    SYNTAX  INTEGER (1..256)
    MAX-ACCESS  read-write
    STATUS  current
    DESCRIPTION
             "Add BFD interface. Returns 0 on SNMPGET.
	     Note:This mib is not supported for VX instance of virtualization"
    ::= { bfdCfg 9 }

bfdNewCfgRemIf OBJECT-TYPE
    SYNTAX  INTEGER (1..256)
    MAX-ACCESS  read-write
    STATUS  current
    DESCRIPTION
             "Remove BFD interface. Returns 0 on SNMPGET.
	     Note:This mib is not supported for VX instance of virtualization"
    ::= { bfdCfg 10 }

-- BFD MIBS END

-- L3 Operational commands

vrrpOperVirtRtrTable OBJECT-TYPE
    SYNTAX  SEQUENCE OF VrrpOperVirtRtrEntry
    MAX-ACCESS  not-accessible
    STATUS  current
    DESCRIPTION
        "An entry in the table of virtual routers.
       Note:This mib is not supported for VX instance of virtualization"
    ::= { vrrpOper 1 }

vrrpOperVirtRtrEntry OBJECT-TYPE
    SYNTAX  VrrpOperVirtRtrEntry
    MAX-ACCESS  not-accessible
    STATUS  current
    DESCRIPTION
        "A row in the vrrpOperVirtRtrTable "
    INDEX   { vrrpOperVirtRtrIndex }
    ::= { vrrpOperVirtRtrTable 1 }

VrrpOperVirtRtrEntry ::= SEQUENCE {
    vrrpOperVirtRtrIndex              Integer32,
    vrrpOperVirtRtrBackup             INTEGER
    }

vrrpOperVirtRtrIndex OBJECT-TYPE
    SYNTAX  Integer32
    MAX-ACCESS  read-only
    STATUS  current
    DESCRIPTION
        "The index for the  VRRP virtual router." 
    ::= { vrrpOperVirtRtrEntry 1 }

vrrpOperVirtRtrBackup OBJECT-TYPE
    SYNTAX  INTEGER {
	ok(1),
	backup(2),
        unsupported(2147483647)
	}
    MAX-ACCESS  read-write
    STATUS  current
    DESCRIPTION
        "When set to a value of 'backup(2)' it forces the specified 
         master virtual router into backup mode.
         'ok(1)' is returned when the object is read."
    ::= { vrrpOperVirtRtrEntry 2 }

vrrpOperVirtRtrGroupBackup OBJECT-TYPE
    SYNTAX  INTEGER {
	ok(1),
	backup(2),
        unsupported(2147483647)
	}
    MAX-ACCESS  read-write
    STATUS  current
    DESCRIPTION
        "When set to a value of 'backup(2)' it forces the specified 
         master virtual router group into backup mode.
         'ok(1)' is returned when the object is read."
    ::= { vrrpOper 2 }

bgpOper             OBJECT IDENTIFIER ::= { ipOper 1 }
garpOper            OBJECT IDENTIFIER ::= { ipOper 2 }

bgpOperStart        OBJECT IDENTIFIER ::= { bgpOper 1 }
bgpOperStop         OBJECT IDENTIFIER ::= { bgpOper 2 }

bgpOperStartPeerNum OBJECT-TYPE
    SYNTAX INTEGER (1..16)
    MAX-ACCESS  read-write
    STATUS  current
    DESCRIPTION
      "Enter BGP peer Number.Value 1 is returned when object is read.
       Note:This mib is not supported for VX instance of virtualization"
    ::= { bgpOperStart 1 }

bgpOperStartSess OBJECT-TYPE
    SYNTAX INTEGER {
        ok(1),
        start(2),
        unsupported(2147483647)
    }
    MAX-ACCESS  read-write
    STATUS  current
    DESCRIPTION
      "This is the action object,start(2) is to Start BGP peer session.
       ok(1) is returned when object is read
       Note:This mib is not supported for VX instance of virtualization"
    ::= { bgpOperStart 2 }

bgpOperStopPeerNum OBJECT-TYPE
    SYNTAX INTEGER (1..16)
    MAX-ACCESS  read-write
    STATUS  current
    DESCRIPTION
      "Enter BGP peer Number.Value 1 is returned when object is read.
       Note:This mib is not supported for VX instance of virtualization"
    ::= { bgpOperStop 1 }

bgpOperStopSess OBJECT-TYPE
    SYNTAX INTEGER {
        ok(1),
        stop(2),
        unsupported(2147483647)
    }
    MAX-ACCESS  read-write
    STATUS  current
    DESCRIPTION
      "This is an action object,stop(2) is to Stop BGP peer session.
       ok(1) is returned when object is read
       This mib is not supported for VX instance of virtualization"
    ::= { bgpOperStop 2 }

garpOperIpAddr OBJECT-TYPE
    SYNTAX IpAddress
    MAX-ACCESS  read-write
    STATUS  current
    DESCRIPTION
      "Ip Address to Send gratuitous arp.Value 0.0.0.0 is returned when object is read.
       Note:This mib is not supported for VX instance of virtualization"
    ::= { garpOper 1 }

garpOperVlanNumber OBJECT-TYPE
    SYNTAX INTEGER (1..4090)
    MAX-ACCESS  read-write
    STATUS  current
    DESCRIPTION
      "Vlan Number to Send gratuitous arp.Value 1 is returned when object is read.
       Note:This mib is not supported for VX instance of virtualization"
    ::= { garpOper 2 }

garpOperSend OBJECT-TYPE
    SYNTAX INTEGER {
        ok(1),
        send(2),
        error(3),
        unsupported(2147483647)
    }
    MAX-ACCESS  read-write
    STATUS  current
    DESCRIPTION
      "This is an action object,When set to value of send(2),
       it sends gratuitous arp.ok(1) is returned when garp
       request is sent successfully.Otherwise error(3) is returned.
       Note:This mib is not supported for VX instance of virtualization"
    ::= { garpOper 3 }

haOperServiceTable OBJECT-TYPE
    SYNTAX  SEQUENCE OF HaOperServiceEntry
    MAX-ACCESS  not-accessible
    STATUS  current
    DESCRIPTION
        "An entry in the table of HA group. 
         This mib is not supported for VX instance of virtualization"
    ::= { haOper 1 }

haOperServiceEntry OBJECT-TYPE
    SYNTAX  HaOperServiceEntry
    MAX-ACCESS  not-accessible
    STATUS  current
    DESCRIPTION
        "A row in the haOperServiceTable."
    INDEX   { haOperServiceIndex }
    ::= { haOperServiceTable 1 }

HaOperServiceEntry ::= SEQUENCE {
    haOperServiceIndex              DisplayString,
    haOperServiceBackup             INTEGER
    }

haOperServiceIndex OBJECT-TYPE
    SYNTAX DisplayString (SIZE(1..32)) 
    MAX-ACCESS  read-only
    STATUS  current
    DESCRIPTION
        "The index for the  ha service group in alphanumeric." 
    ::= { haOperServiceEntry 1 }

haOperServiceBackup OBJECT-TYPE
    SYNTAX  INTEGER {
	ok(1),
	backup(2),
        unsupported(2147483647)
	}
    MAX-ACCESS  read-write
    STATUS  current
    DESCRIPTION
        "When set to a value of 'backup(2)' it forces the specified 
         HA service group master into backup mode.
         'ok(1)' is returned when the object is read."
    ::= { haOperServiceEntry 2 }

haOperSwitchBackup OBJECT-TYPE
        SYNTAX  INTEGER {
            ok(1),
            backup(2),
            unsupported(2147483647)
            }
        MAX-ACCESS  read-write
        STATUS  current
        DESCRIPTION
            "When set to a value of 'backup(2)' it forces the specified
             HA switch master into backup mode.
             'ok(1)' is returned when the object is read."
        ::= { haOper 2 }
END
