-- COPYRIGHT NOTICE
-- Copyright (c) Radware Ltd. 2009
-- All rights reserved


ALTEON-CHEETAH-LAYER4-MIB DEFINITIONS ::= BEGIN

IMPORTS
    MODULE-IDENTITY, OBJECT-TYPE, Integer32, Counter32, Gauge32, Counter64,
    IpAddress, Unsigned32
        FROM SNMPv2-SMI
    DisplayString, PhysAddress
        FROM SNMPv2-TC
    aws-switch 
        FROM ALTEON-ROOT-MIB;

layer4 MODULE-IDENTITY
    LAST-UPDATED "201207120000Z" --  12 July, 2012
    ORGANIZATION "Radware Ltd"
    CONTACT-INFO "Lobby 1 (Visitors) and Lobby 2 (Deliveries)
                  575 Corporate Drive
                  Mahwah, NJ 07430
                  support@radware.com"
    DESCRIPTION
        "The MIB module for the Alteon OS Layer 4 configuration, statistics
         and information ."
    REVISION "200908050000Z"     -- 5 August, 2009
    DESCRIPTION
        "Added revision clause for SMIv2 compliance."
    ::= { aws-switch 4 }

-- Define RadwareLongDisplayString
RadwareLongDisplayString ::= TEXTUAL-CONVENTION
    DISPLAY-HINT "10000a"
    STATUS current
    DESCRIPTION "A longer version of SNMPv2-TC::DisplayString"
    SYNTAX OCTET STRING (SIZE (0..10000))

layer4Configs     OBJECT IDENTIFIER ::= { layer4 1 }
layer4Stats       OBJECT IDENTIFIER ::= { layer4 2 }
layer4Info        OBJECT IDENTIFIER ::= { layer4 3 }
layer4Oper        OBJECT IDENTIFIER ::= { layer4 4 }

slbCfg  	  OBJECT IDENTIFIER ::= { layer4Configs 1 }
filterCfg  	  OBJECT IDENTIFIER ::= { layer4Configs 2 }
gslbCfg           OBJECT IDENTIFIER ::= { layer4Configs 3 }
layer4TableSize   OBJECT IDENTIFIER ::= { layer4Configs 4 }
wlmCfg            OBJECT IDENTIFIER ::= { layer4Configs 6 }

slbGeneralCfg  	  OBJECT IDENTIFIER ::= { slbCfg 1 }
realServerCfg  	  OBJECT IDENTIFIER ::= { slbCfg 2 }
realServerGroupCfg OBJECT IDENTIFIER ::= { slbCfg 3 }
virtualServerCfg  OBJECT IDENTIFIER ::= { slbCfg 4 }
portCfg           OBJECT IDENTIFIER ::= { slbCfg 5 }
syncCfg           OBJECT IDENTIFIER ::= { slbCfg 6 }
wapCfg            OBJECT IDENTIFIER ::= { slbCfg 7 }
waphcCfg          OBJECT IDENTIFIER ::= { slbCfg 8 }
synAttackDetCfg   OBJECT IDENTIFIER ::= { slbCfg 9 }
hcsCfg            OBJECT IDENTIFIER ::= { slbCfg 13 }
snmphcCfg         OBJECT IDENTIFIER ::= { slbCfg 14 }
pipTblCfg         OBJECT IDENTIFIER ::= { slbCfg 15 }
linklbCfg         OBJECT IDENTIFIER ::= { slbCfg 16 }
smtportCfg        OBJECT IDENTIFIER ::= { slbCfg 17 }
acclCfg           OBJECT IDENTIFIER ::= { slbCfg 18 }
caching           OBJECT IDENTIFIER ::= { acclCfg 1}
compression       OBJECT IDENTIFIER ::= { acclCfg 2}
fastview          OBJECT IDENTIFIER ::= { acclCfg 3}
http2          	  OBJECT IDENTIFIER ::= { acclCfg 4}

sslCfg            OBJECT IDENTIFIER ::= { slbCfg 19 }
sslPol            OBJECT IDENTIFIER ::= { sslCfg 3 }
authPol           OBJECT IDENTIFIER ::= { sslCfg 4 }
certs             OBJECT IDENTIFIER ::= { sslCfg 5 }
cdpGrp            OBJECT IDENTIFIER ::= { sslCfg 6 }
inspect           OBJECT IDENTIFIER ::= { sslCfg 7 }
sslInspectionFlow OBJECT IDENTIFIER ::= { sslCfg 8 }  
sslAdvCfg         OBJECT IDENTIFIER ::= { sslCfg 9 }

secCfg            OBJECT IDENTIFIER ::= { slbCfg 30 }
secPol            OBJECT IDENTIFIER ::= { secCfg 1}

overlayCfg        OBJECT IDENTIFIER ::= { slbCfg 31 }
icapPolCfg       OBJECT IDENTIFIER ::= { slbCfg 32 }
filtsetCfg        OBJECT IDENTIFIER ::= { slbCfg 33 }

overlayCfgGeneral OBJECT IDENTIFIER ::= { overlayCfg 1 }

dataclassCfg         OBJECT IDENTIFIER ::= { slbCfg 25 }

sapCfg            OBJECT IDENTIFIER ::= { slbCfg 20 }
peerpipTblCfg     OBJECT IDENTIFIER ::= { slbCfg 21 }

nwclssCfg         OBJECT IDENTIFIER ::= { slbCfg 22 }

appShapeCfg        OBJECT IDENTIFIER ::= { slbCfg 23 }
advhcCfg          OBJECT IDENTIFIER ::= { slbCfg 24 }

appwallCfg         OBJECT IDENTIFIER ::= { slbCfg 27 }
tcpOptPolCfg       OBJECT IDENTIFIER ::= { slbCfg 28 }

lpConfig           OBJECT IDENTIFIER ::= { slbCfg 29 }

slbClusterCfg     OBJECT IDENTIFIER ::= { slbCfg 34 }

trafficEventCfg   OBJECT IDENTIFIER ::= { slbCfg 35 }
remoteLoggingCfg   OBJECT IDENTIFIER ::= { slbCfg 36 }

syncGeneralCfg    OBJECT IDENTIFIER ::= { syncCfg 1 }

gslbGeneralCfg    OBJECT IDENTIFIER ::= { gslbCfg 1 }
gslbSitesCfg      OBJECT IDENTIFIER ::= { gslbCfg 2 }
gslbEnhNetworkCfg OBJECT IDENTIFIER ::= { gslbCfg 4 }
gslbRuleCfg       OBJECT IDENTIFIER ::= { gslbCfg 5 }
gslbDnsSecCfg     OBJECT IDENTIFIER ::= { gslbCfg 6 }
gslbDnsResVipCfg  OBJECT IDENTIFIER ::= { gslbCfg 7 }
gslbLLBProximityCfg  OBJECT IDENTIFIER ::= { gslbCfg 8 }
gslbLPWizardDnsRespCfg  OBJECT IDENTIFIER ::= { gslbCfg 9 }

gslbDnsSecGlobalCfg    OBJECT IDENTIFIER ::= { gslbDnsSecCfg 1 }
gslbDnsSecKeyCfg       OBJECT IDENTIFIER ::= { gslbDnsSecCfg 2 }
gslbDnsSecZoneCfg      OBJECT IDENTIFIER ::= { gslbDnsSecCfg 3 }
gslbDnsSecImportExport OBJECT IDENTIFIER ::= { gslbDnsSecCfg 4 }
gslbDnsProxyCfg        OBJECT IDENTIFIER ::= { gslbCfg 10 }
gslbDnsSoaCfg          OBJECT IDENTIFIER ::= { gslbCfg 11 }
gslbDnsCaaCfg          OBJECT IDENTIFIER ::= { gslbCfg 12 }
gslbDnsNsCfg           OBJECT IDENTIFIER ::= { gslbCfg 13 }

slbSpStats  	  OBJECT IDENTIFIER ::= { layer4Stats  1 }
slbMaintStats     OBJECT IDENTIFIER ::= { layer4Stats  5 }
filterStats  	  OBJECT IDENTIFIER ::= { layer4Stats  6 }
gslbStats  	  OBJECT IDENTIFIER ::= { layer4Stats  7 }
wapStats          OBJECT IDENTIFIER ::= { layer4Stats  8 }
ftpStats          OBJECT IDENTIFIER ::= { layer4Stats  10 }
rtspStats	  OBJECT IDENTIFIER ::= { layer4Stats  11 }
tcpLimitStats     OBJECT IDENTIFIER ::= { layer4Stats  12 }
dnsSlbStats       OBJECT IDENTIFIER ::= { layer4Stats  13 }
sslSlbStats       OBJECT IDENTIFIER ::= { layer4Stats  16 }
sipStats	  OBJECT IDENTIFIER ::= { layer4Stats  20 }
sessMirrorStats          OBJECT IDENTIFIER ::= { layer4Stats  22 }

accelStats           OBJECT IDENTIFIER ::= { layer4Stats  23 } 
cachStats            OBJECT IDENTIFIER ::= { accelStats  1 }
compStats            OBJECT IDENTIFIER ::= { accelStats  2 }
fastviewStats        OBJECT IDENTIFIER ::= { accelStats  3 }
http2Stats           OBJECT IDENTIFIER ::= { accelStats  4 }
httpStats            OBJECT IDENTIFIER ::= { layer4Stats 24 }
connmngStats         OBJECT IDENTIFIER ::= { httpStats 17 }

sapStats            OBJECT IDENTIFIER ::= { layer4Stats 25 }
appShapeStats       OBJECT IDENTIFIER ::= { layer4Stats 26 }
pipStats            OBJECT IDENTIFIER ::= { layer4Stats 27 }
secSlbStats       OBJECT IDENTIFIER ::= { layer4Stats  39 }
tcpConnmngStats      OBJECT IDENTIFIER ::= { layer4Stats  41 }
cdpGrpStats	    OBJECT IDENTIFIER ::= { layer4Stats  42 }
slbOverlayStats     OBJECT IDENTIFIER ::= { layer4Stats  43 }
slbOverlaySpStats   OBJECT IDENTIFIER ::= { slbSpStats  8 }
fltStatPsess        OBJECT IDENTIFIER ::= { filterStats 3 }
trafficEventStats   OBJECT IDENTIFIER ::= { layer4Stats  47 }
trafficEventSummaryStats OBJECT IDENTIFIER ::= { trafficEventStats 3 }

-- Real Server Table - Current Configuration

slbRealServerMaxSize OBJECT-TYPE
    SYNTAX Integer32 
    MAX-ACCESS read-only 
    STATUS current 
    DESCRIPTION 
        "The maximum number of entries in SLB RealServerTable.
         Note:This mib is not supported on VX instance of Virtualization." 
    ::= { realServerCfg 1 }

slbCurCfgRealServerTable OBJECT-TYPE
    SYNTAX SEQUENCE OF SlbCurCfgRealServerEntry
    MAX-ACCESS not-accessible
    STATUS current
    DESCRIPTION
        "The table of Real Server configuration in the current_config.
         Note:This mib is not supported on VX instance of Virtualization."
    ::= { realServerCfg 2 }

slbCurCfgRealServerEntry OBJECT-TYPE
    SYNTAX SlbCurCfgRealServerEntry
    MAX-ACCESS not-accessible
    STATUS current
    DESCRIPTION
        "Information about a particular Real Server configuration."
    INDEX { slbCurCfgRealServerIndex }
    ::= { slbCurCfgRealServerTable 1 }
 
SlbCurCfgRealServerEntry ::= SEQUENCE {
    slbCurCfgRealServerIndex           Integer32,
    slbCurCfgRealServerIpAddr          IpAddress,
    slbCurCfgRealServerWeight          INTEGER,
    slbCurCfgRealServerMaxConns        INTEGER,
    slbCurCfgRealServerTimeOut         INTEGER,
    slbCurCfgRealServerBackUp          Integer32,
    slbCurCfgRealServerPingInterval    INTEGER,
    slbCurCfgRealServerFailRetry       INTEGER,
    slbCurCfgRealServerSuccRetry       INTEGER,
    slbCurCfgRealServerState           INTEGER,
    slbCurCfgRealServerType            INTEGER,
    slbCurCfgRealServerName            DisplayString,
    slbCurCfgRealServerUrlBmap         OCTET STRING,
    slbCurCfgRealServerCookie          INTEGER,
    slbCurCfgRealServerExcludeStr      INTEGER,
    slbCurCfgRealServerSubmac          INTEGER,
    slbCurCfgRealServerProxy           INTEGER,
    slbCurCfgRealServerLdapwr          INTEGER,
    slbCurCfgRealServerOid             DisplayString,
    slbCurCfgRealServerCommString      DisplayString,
    slbCurCfgRealServerIdsvlan         INTEGER,
    slbCurCfgRealServerIdsport         Integer32,
    slbCurCfgRealServerAvail           INTEGER,
    slbCurCfgRealServerFastHealthCheck INTEGER,
    slbCurCfgRealServerSubdmac         INTEGER,
    slbCurCfgRealServerBkpPreempt      INTEGER,
    slbCurCfgRealServerOverflow        INTEGER,
    slbCurCfgRealServerIpVer           INTEGER,
    slbCurCfgRealServerIpv6Addr        DisplayString,
    slbCurCfgRealServerMode            INTEGER,
    slbCurCfgRealServerProxyIpMode   INTEGER,
    slbCurCfgRealServerProxyIpAddr   IpAddress,
    slbCurCfgRealServerProxyIpMask   IpAddress, 
    slbCurCfgRealServerProxyIpv6Addr DisplayString,
    slbCurCfgRealServerProxyIpv6Prefix INTEGER,
    slbCurCfgRealServerProxyIpPersistency   INTEGER,
    slbCurCfgRealServerProxyIpNWclass   DisplayString,
    slbCurCfgRealServerProxyIpNWclassPersistency   INTEGER,
    slbCurCfgRealServerHealthID        DisplayString
    }

slbCurCfgRealServerIndex OBJECT-TYPE
    SYNTAX  Integer32
    MAX-ACCESS  read-only
    STATUS  current
    DESCRIPTION
        "The real server number" 
    ::= { slbCurCfgRealServerEntry 1 }

slbCurCfgRealServerIpAddr OBJECT-TYPE
    SYNTAX  IpAddress
    MAX-ACCESS  read-only
    STATUS  current
    DESCRIPTION
        "IP address of the real server identified by the instance of the 
         slbRealServerIndex." 
    ::= { slbCurCfgRealServerEntry 2 }

slbCurCfgRealServerWeight OBJECT-TYPE
    SYNTAX  INTEGER (1..48)
    MAX-ACCESS  read-only
    STATUS  current
    DESCRIPTION
        "The server weight." 
    ::= { slbCurCfgRealServerEntry 3 }

slbCurCfgRealServerMaxConns OBJECT-TYPE
    SYNTAX  INTEGER (0..1000000)
    MAX-ACCESS  read-only
    STATUS  current
    DESCRIPTION
        "The maximum number of connections that are allowed." 
    ::= { slbCurCfgRealServerEntry 4 }

slbCurCfgRealServerTimeOut OBJECT-TYPE
    SYNTAX  INTEGER (2..32768)
    MAX-ACCESS  read-only
    STATUS  current
    DESCRIPTION
        "The maximum number of minutes an inactive connection remains open." 
    ::= { slbCurCfgRealServerEntry 5 }

slbCurCfgRealServerBackUp OBJECT-TYPE
    SYNTAX Integer32
    MAX-ACCESS  read-only
    STATUS  current
    DESCRIPTION
        "The backup server number for this server." 
    ::= { slbCurCfgRealServerEntry 6 }

slbCurCfgRealServerPingInterval OBJECT-TYPE
    SYNTAX  INTEGER (0..60)
    MAX-ACCESS  read-only
    STATUS  current
    DESCRIPTION
	"The interval between keep-alive (ping) attempts in number of seconds.
         Zero means disabling ping attempt."
    ::= { slbCurCfgRealServerEntry 7 }

slbCurCfgRealServerFailRetry OBJECT-TYPE
    SYNTAX  INTEGER  (1..63)
    MAX-ACCESS  read-only
    STATUS  current
    DESCRIPTION
        "The number of failed attempts to declare this server DOWN." 
    ::= { slbCurCfgRealServerEntry 8 }

slbCurCfgRealServerSuccRetry OBJECT-TYPE
    SYNTAX  INTEGER (1..63)
    MAX-ACCESS  read-only
    STATUS  current
    DESCRIPTION
        "The number of successful attempts to declare a server UP." 
    ::= { slbCurCfgRealServerEntry 9 }

slbCurCfgRealServerState OBJECT-TYPE
    SYNTAX  INTEGER {
	enabled(2),
	disabled(3),
	disabled-with-fastage(4),
        unsupported(2147483647)
	}
    MAX-ACCESS  read-only
    STATUS  current
    DESCRIPTION
        "Enable or disable the server and remove the existing sessions using disabled-with-fastage option." 
    ::= { slbCurCfgRealServerEntry 10 }

slbCurCfgRealServerType OBJECT-TYPE
    SYNTAX  INTEGER {
	local-server(1),
	remote-server(2),
        unsupported(2147483647)
	}
    MAX-ACCESS  read-only
    STATUS  current
    DESCRIPTION
        "The server type.  It participates in global server
	 load balancing when it is configured as remote-server." 
    ::= { slbCurCfgRealServerEntry 11 }

slbCurCfgRealServerName OBJECT-TYPE 
    SYNTAX  DisplayString (SIZE(0..255))
    MAX-ACCESS  read-only 
    STATUS  current 
    DESCRIPTION 
        "The name of the real server."  
    ::= { slbCurCfgRealServerEntry 12 }

slbCurCfgRealServerUrlBmap OBJECT-TYPE
    SYNTAX  OCTET STRING
    MAX-ACCESS  read-only
    STATUS  current
    DESCRIPTION
        "The URL Paths selected for URL load balancing for by the real 
         server.  The selected URL Paths are presented in a bitmap format.
         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

             where x : 1 - The represented URL Path is selected
                       0 - The represented URL Path is not selected"
    ::= { slbCurCfgRealServerEntry 13 }

slbCurCfgRealServerCookie OBJECT-TYPE
    SYNTAX  INTEGER {
        enabled(1),
        disabled(2),
        unsupported(2147483647)
        }
    MAX-ACCESS  read-only
    STATUS  current
    DESCRIPTION
        "The real server that will handle client requests that doesn't 
         contain an URL cookie if Cookie loadbalance is enabled." 
    ::= { slbCurCfgRealServerEntry 14 }

slbCurCfgRealServerExcludeStr OBJECT-TYPE
    SYNTAX  INTEGER {
	enabled(1),
	disabled(2),
        unsupported(2147483647)
	}
    MAX-ACCESS  read-only
    STATUS  current
    DESCRIPTION
        "The real server will handle requests that don't match the 
         loadbalance string if it is enabled."
    ::= { slbCurCfgRealServerEntry 15 }

slbCurCfgRealServerSubmac OBJECT-TYPE
    SYNTAX  INTEGER {
	enabled(1),
	disabled(2),
        unsupported(2147483647)
	}
    MAX-ACCESS  read-only
    STATUS  current
    DESCRIPTION
        "The real server config to enable/disable MAC SA substitution for 
         L4 traffic. If disabled (the default) we will NOT substitute the 
         MAC SA of client-to-server frames.  If enabled, we will substitute 
         the MAC SA."
    ::= { slbCurCfgRealServerEntry 16 }

slbCurCfgRealServerProxy OBJECT-TYPE
    SYNTAX  INTEGER {
	enabled(1),
	disabled(2),
        unsupported(2147483647)
	}
    MAX-ACCESS  read-only
    STATUS  current
    DESCRIPTION
        "The real server config to enable/disable client proxy operation."
    ::= { slbCurCfgRealServerEntry 17 }

slbCurCfgRealServerLdapwr OBJECT-TYPE
    SYNTAX  INTEGER {
        enabled(1),
        disabled(2),
        unsupported(2147483647)
        }
    MAX-ACCESS  read-only
    STATUS  current
    DESCRIPTION
        "The real server config to enable/disable LDAP write server."
    ::= { slbCurCfgRealServerEntry 18 }

slbCurCfgRealServerOid OBJECT-TYPE
    SYNTAX DisplayString (SIZE(0..128))
    MAX-ACCESS read-only
    STATUS current
    DESCRIPTION
        "The OID to be sent in the SNMP get request packet."
    ::= { slbCurCfgRealServerEntry 19 }

slbCurCfgRealServerCommString OBJECT-TYPE
    SYNTAX DisplayString (SIZE(0..32))
    MAX-ACCESS read-only
    STATUS current
    DESCRIPTION
        "The community string to be used in the SNMP get request packet."
    ::= { slbCurCfgRealServerEntry 20 }

slbCurCfgRealServerIdsvlan OBJECT-TYPE
    SYNTAX  INTEGER (0..4090)
    MAX-ACCESS  read-only
    STATUS  current
    DESCRIPTION
        "The VLAN to be associated with the IDS server."
    ::= { slbCurCfgRealServerEntry 21 }

slbCurCfgRealServerIdsport OBJECT-TYPE
    SYNTAX  Integer32
    MAX-ACCESS  read-only
    STATUS  current
    DESCRIPTION
        "The port to be connected to the IDS server."
    ::= { slbCurCfgRealServerEntry 22 }

slbCurCfgRealServerAvail OBJECT-TYPE
    SYNTAX  INTEGER (1..48)
    MAX-ACCESS  read-only
    STATUS  current
    DESCRIPTION
        "The remote real server Global SLB availability."
    ::= { slbCurCfgRealServerEntry 23 }

slbCurCfgRealServerFastHealthCheck OBJECT-TYPE
    SYNTAX  INTEGER {
        enabled(1),
        disabled(2),
        unsupported(2147483647)
        }
    MAX-ACCESS  read-only
    STATUS  current
    DESCRIPTION
        "The real server config to enable/disable Fast Health Check Operation."
    ::= { slbCurCfgRealServerEntry 24 }

slbCurCfgRealServerSubdmac OBJECT-TYPE
    SYNTAX  INTEGER {
        enabled(1),
        disabled(2),
        unsupported(2147483647)
        }
    MAX-ACCESS  read-only
    STATUS  current
    DESCRIPTION
        "The real server config to enable/disable MAC DA substitution for
         L4 traffic. If disabled, we will NOT substitute the MAC DA of
         client-to-server frames.  If enabled(default), we will substitute
         the MAC DA."
    ::= { slbCurCfgRealServerEntry 25 }

slbCurCfgRealServerOverflow OBJECT-TYPE
    SYNTAX  INTEGER {
        enabled(1),
        disabled(2),
        unsupported(2147483647)
        }
    MAX-ACCESS  read-only
    STATUS  current
    DESCRIPTION
        "The real server config to enable/disable Overflow. If enabled(default)
         allows Backup server to kick in if real server reaches maximum
         connections."
    ::= { slbCurCfgRealServerEntry 26 }

slbCurCfgRealServerBkpPreempt OBJECT-TYPE
    SYNTAX  INTEGER {
        enabled(1),
        disabled(2),
        unsupported(2147483647)
        }
    MAX-ACCESS  read-only
    STATUS  current
    DESCRIPTION
        "The real server config to enable/disable backup preemption. If enabled
         (default)allows to preempt the backup server when the primary server 
         comes up. If disabled the backup server will continue to serve the 
         traffic even when primary server comes up." 
    ::= { slbCurCfgRealServerEntry 27 }
slbCurCfgRealServerIpVer OBJECT-TYPE
    SYNTAX  INTEGER{
        ipv4(1),
        ipv6(2),
        unsupported(2147483647)
        }
    MAX-ACCESS  read-only
    STATUS  current
    DESCRIPTION
        "The type of IP address."
    ::= { slbCurCfgRealServerEntry 28 }

slbCurCfgRealServerIpv6Addr OBJECT-TYPE
   SYNTAX DisplayString (SIZE(0..40))
    MAX-ACCESS  read-only
    STATUS  current
    DESCRIPTION
    "  IPV6 address of the real server identified by the instance of the slbRealServerIndex.
       Address should be 4-byte hexadecimal colon notation. Valid IPv6 address should be in
       any of the following forms xxxx:xxxx:xxxx:xxxx:xxxx:xxxx:xxxx:xxxx or xxxx::xxxx:xxxx:xxxx:xxxx or ::xxxx "
   ::= { slbCurCfgRealServerEntry 29 }

slbCurCfgRealServerMode OBJECT-TYPE
    SYNTAX  INTEGER {
        physical(1),
	logical(2),
        unsupported(2147483647)
	}
    MAX-ACCESS  read-only
    STATUS  current
    DESCRIPTION
        "The mode of the real server. By default it is set to physical."
    ::= { slbCurCfgRealServerEntry 30 }	

-- Cur Real server Proxy IP start
slbCurCfgRealServerProxyIpMode OBJECT-TYPE   
    SYNTAX INTEGER {
        enable(0),
	 address(2),
	 nwclss(3),
        disable(4),
        unsupported(2147483647)
        }
    MAX-ACCESS  read-only
    STATUS  current
    DESCRIPTION
        " the real server Proxy IP mode "
    ::= { slbCurCfgRealServerEntry 31 }

slbCurCfgRealServerProxyIpAddr OBJECT-TYPE
    SYNTAX  IpAddress
    MAX-ACCESS  read-only
    STATUS  current
    DESCRIPTION
        "This object ID shows current configuration of real server proxy IP address .
              Returns 0 when slbCurCfgRealServerProxyIpMode is not set to address.
              Returns 0 if IP version is IPv6." 
    ::= { slbCurCfgRealServerEntry 32 }

slbCurCfgRealServerProxyIpMask OBJECT-TYPE
    SYNTAX  IpAddress
    MAX-ACCESS  read-only
    STATUS  current
    DESCRIPTION
        "This object ID shows current configuration of real server proxy IP subnet mask. 
              Returns 0 when slbCurCfgRealServerProxyIpMode is not set to address.
              Returns 0 if IP version is IPv6." 
    ::= { slbCurCfgRealServerEntry 33 }

slbCurCfgRealServerProxyIpv6Addr OBJECT-TYPE
    SYNTAX  DisplayString (SIZE(0..40))
    MAX-ACCESS  read-only
    STATUS  current
    DESCRIPTION
        "This object ID shows current configuration of real server proxy IPv6 address . 
		The IP version for addr must be the same as the real server IP version.
              Returns 0 when slbCurCfgRealServerProxyIpMode is not set to address.
              Returns 0 if IP version is IPv4. 
		When a subnet is configured, user has the ability to select PIP persistency mode.
		Persistency is relevant only if the PIP is configured as subnet. If PIP is not configured or
		not subnet, the persistency configuration value is disable."
    ::= { slbCurCfgRealServerEntry 34 }

slbCurCfgRealServerProxyIpv6Prefix OBJECT-TYPE
    SYNTAX  INTEGER (1..128)
    MAX-ACCESS  read-only
    STATUS  current
    DESCRIPTION
        "This object ID allows configuration of real server proxy IPv6 Mask. 
		The IP version for addr must be the same as the real server IP version.
              Returns 0 when slbCurCfgRealServerProxyIpMode is not set to address.
              Returns 0 if IP version is IPv6. 
		When a subnet is configured user has the ability to select PIP persistency mode.
		Persistency is relevant only if the PIP is configured as subnet. If PIP is not configured or
		not subnet, the persistency configuration value is disable."
    ::= { slbCurCfgRealServerEntry 35 }

slbCurCfgRealServerProxyIpPersistency OBJECT-TYPE   
    SYNTAX INTEGER {
        disable(0),
        client(1),
	 host(2),
         unsupported(2147483647)
        }
    MAX-ACCESS  read-only  
    STATUS  current
    DESCRIPTION
        "This object ID shows current configuration of real server proxy IP persistency mode.
		Persistency is relevant only if a PIP class is configured. If PIP is not configured the
		persistency configuration is disable."
    ::= { slbCurCfgRealServerEntry 36 }

slbCurCfgRealServerProxyIpNWclass OBJECT-TYPE
    SYNTAX  DisplayString  (SIZE(0..32)) 
    MAX-ACCESS  read-only
    STATUS  current
    DESCRIPTION
        "This  object ID allows configuration of real server proxy IP IPv4 or IPv6 Network Class as PIP.
		Network Class PIP Persistency is relevant only if a PIP class is configured. If PIP is not configured the
		persistency configuration is disable.
              Returns 0 when slbCurCfgRealServerProxyIpMode is not set to nwclss(3)." 
    ::= { slbCurCfgRealServerEntry 37 }

slbCurCfgRealServerProxyIpNWclassPersistency OBJECT-TYPE   
    SYNTAX INTEGER {
        disable(0),
        client(1),
        unsupported(2147483647)
        }
    MAX-ACCESS  read-only
    STATUS  current
    DESCRIPTION
        "This object ID allows configuration of real server Network Class PIP persistency mode.
		Persistency is relevant only if a PIP class is configured. If PIP is not configured the
		persistency configuration is disable. 
              Returns 0 when slbCurCfgRealServerProxyIpMode is not set to nwclss(3)." 		
    ::= { slbCurCfgRealServerEntry 38 }   
    

slbCurCfgRealServerHealthID OBJECT-TYPE
    SYNTAX DisplayString (SIZE(0..32))
    MAX-ACCESS read-only
    STATUS current
    DESCRIPTION
        "The Advanced HC ID."
    ::= { slbCurCfgRealServerEntry 39 }

-- Cur Real server Proxy IP end

-- Real Server Table - New Configuration

slbNewCfgRealServerTable OBJECT-TYPE
    SYNTAX  SEQUENCE OF SlbNewCfgRealServerEntry
    MAX-ACCESS  not-accessible
    STATUS  current
    DESCRIPTION
        "The table of Real Server configuration in the new_config.
         Note:This mib is not supported on VX instance of Virtualization."
    ::= { realServerCfg 3 }

slbNewCfgRealServerEntry OBJECT-TYPE
    SYNTAX  SlbNewCfgRealServerEntry
    MAX-ACCESS  not-accessible
    STATUS  current
    DESCRIPTION
        "Information about a particular Real Server configuration."
    INDEX   { slbNewCfgRealServerIndex }
    ::= { slbNewCfgRealServerTable 1 }
 
SlbNewCfgRealServerEntry ::= SEQUENCE {
    slbNewCfgRealServerIndex           Integer32,
    slbNewCfgRealServerIpAddr          IpAddress,
    slbNewCfgRealServerWeight          INTEGER,
    slbNewCfgRealServerMaxConns        INTEGER,
    slbNewCfgRealServerTimeOut         INTEGER,
    slbNewCfgRealServerBackUp          Integer32,
    slbNewCfgRealServerPingInterval    INTEGER,
    slbNewCfgRealServerFailRetry       INTEGER,
    slbNewCfgRealServerSuccRetry       INTEGER,
    slbNewCfgRealServerState           INTEGER,
    slbNewCfgRealServerDelete          INTEGER,
    slbNewCfgRealServerType            INTEGER,
    slbNewCfgRealServerName            DisplayString,
    slbNewCfgRealServerUrlBmap         OCTET STRING,
    slbNewCfgRealServerAddUrl          Integer32,
    slbNewCfgRealServerRemUrl          Integer32,
    slbNewCfgRealServerCookie          INTEGER,
    slbNewCfgRealServerExcludeStr      INTEGER,
    slbNewCfgRealServerSubmac          INTEGER,
    slbNewCfgRealServerProxy           INTEGER,
    slbNewCfgRealServerLdapwr          INTEGER,
    slbNewCfgRealServerOid             DisplayString,
    slbNewCfgRealServerCommString      DisplayString,
    slbNewCfgRealServerIdsvlan         INTEGER,
    slbNewCfgRealServerIdsport         Integer32,
    slbNewCfgRealServerAvail           INTEGER,
    slbNewCfgRealServerFastHealthCheck INTEGER,
    slbNewCfgRealServerSubdmac         INTEGER,
    slbNewCfgRealServerBkpPreempt      INTEGER,
    slbNewCfgRealServerOverflow        INTEGER,
    slbNewCfgRealServerIpVer           INTEGER,
    slbNewCfgRealServerIpv6Addr        DisplayString,
    slbNewCfgRealServerNxtRportIdx     INTEGER,
    slbNewCfgRealServerNxtBuddyIdx     INTEGER,
    slbNewCfgRealServerMode            INTEGER,
    slbNewCfgUpdateAllRealServers      INTEGER,
    slbNewCfgRealServerProxyIpMode   INTEGER,
    slbNewCfgRealServerProxyIpAddr   IpAddress,
    slbNewCfgRealServerProxyIpMask   IpAddress,
    slbNewCfgRealServerProxyIpv6Addr   DisplayString,
    slbNewCfgRealServerProxyIpv6Prefix   INTEGER,
    slbNewCfgRealServerProxyIpPersistency   INTEGER,
    slbNewCfgRealServerProxyIpNWclass   DisplayString,
    slbNewCfgRealServerProxyIpNWclassPersistency   INTEGER,
    slbNewCfgRealServerHealthID        DisplayString
    }

slbNewCfgRealServerIndex OBJECT-TYPE
    SYNTAX  Integer32
    MAX-ACCESS  read-only
    STATUS  current
    DESCRIPTION
        "The real server number" 
    ::= { slbNewCfgRealServerEntry 1 }

slbNewCfgRealServerIpAddr OBJECT-TYPE
    SYNTAX  IpAddress
    MAX-ACCESS  read-create
    STATUS  current
    DESCRIPTION
        "IP address of the real server identified by the instance of 
         slbRealServerIndex." 
    ::= { slbNewCfgRealServerEntry 2 }

slbNewCfgRealServerWeight OBJECT-TYPE
    SYNTAX  INTEGER (1..48)
    MAX-ACCESS  read-create
    STATUS  current
    DESCRIPTION
        "The server weight." 
    ::= { slbNewCfgRealServerEntry 3 }

slbNewCfgRealServerMaxConns OBJECT-TYPE
    SYNTAX  INTEGER (0..1000000)
    MAX-ACCESS  read-create
    STATUS  current
    DESCRIPTION
        "The maximum number of connections that are allowed." 
    ::= { slbNewCfgRealServerEntry 4 }

slbNewCfgRealServerTimeOut OBJECT-TYPE
    SYNTAX  INTEGER (2..32768)
    MAX-ACCESS  read-create
    STATUS  current
    DESCRIPTION
        "The maximum number of minutes an inactive connection remains open." 
    ::= { slbNewCfgRealServerEntry 5 }

slbNewCfgRealServerBackUp OBJECT-TYPE
    SYNTAX Integer32
    MAX-ACCESS  read-create
    STATUS  current
    DESCRIPTION
        "The backup server number for this server." 
    ::= { slbNewCfgRealServerEntry 6 }

slbNewCfgRealServerPingInterval OBJECT-TYPE
    SYNTAX  INTEGER (0..600)
    MAX-ACCESS  read-create
    STATUS  current
    DESCRIPTION
        "The interval between keep-alive (ping) attempts in number of 
         seconds. Zero means disabling ping attempt."
    ::= { slbNewCfgRealServerEntry 7 }

slbNewCfgRealServerFailRetry OBJECT-TYPE
    SYNTAX  INTEGER  (0..63)
    MAX-ACCESS  read-create
    STATUS  current
    DESCRIPTION
        "The number of failed attempts to declare this server DOWN." 
    ::= { slbNewCfgRealServerEntry 8 }

slbNewCfgRealServerSuccRetry OBJECT-TYPE
    SYNTAX  INTEGER (0..63)
    MAX-ACCESS  read-create
    STATUS  current
    DESCRIPTION
        "The number of successful attempts to declare a server UP." 
    ::= { slbNewCfgRealServerEntry 9 }

slbNewCfgRealServerState OBJECT-TYPE
    SYNTAX  INTEGER {
	enabled(2),
	disabled(3),
	disabled-with-fastage(4),
        unsupported(2147483647)
	}
    MAX-ACCESS  read-create
    STATUS  current
    DESCRIPTION
        "Enable or disable the server and remove the existing sessions using disabled-with-fastage option." 
    ::= { slbNewCfgRealServerEntry 10 }

slbNewCfgRealServerDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgRealServerEntry 11 }

slbNewCfgRealServerType OBJECT-TYPE
    SYNTAX  INTEGER {
        local-server(1),
	remote-server(2),
        unsupported(2147483647)
	}
    MAX-ACCESS  read-create
    STATUS  current
    DESCRIPTION
        "The server type.  It participates in global server load balancing 
         when it is configured as remote-server." 
    ::= { slbNewCfgRealServerEntry 12 }

slbNewCfgRealServerName OBJECT-TYPE 
    SYNTAX  DisplayString (SIZE(0..255))
    MAX-ACCESS  read-create 
    STATUS  current 
    DESCRIPTION 
        "The name of the real server."  
    ::= { slbNewCfgRealServerEntry 13 }

slbNewCfgRealServerUrlBmap OBJECT-TYPE
    SYNTAX  OCTET STRING
    MAX-ACCESS  read-only
    STATUS  current
    DESCRIPTION
        "The URL Paths selected for URL load balancing for by the
	 real server.  The selected URL Paths are presented in 
	 a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL Path is selected
                   0 - The represented URL Path is not selected"
    ::= { slbNewCfgRealServerEntry 14 }

slbNewCfgRealServerAddUrl OBJECT-TYPE
    SYNTAX  Integer32
    MAX-ACCESS  read-create
    STATUS  current
    DESCRIPTION
        "The URL Path (slbCurCfgUrlLbPathIndex) to be added to the 
         real server. A zero is returned when read."
    ::= { slbNewCfgRealServerEntry 15 }

slbNewCfgRealServerRemUrl OBJECT-TYPE
    SYNTAX  Integer32
    MAX-ACCESS  read-create
    STATUS  current
    DESCRIPTION
        "The URL Path (slbCurCfgUrlLbPathIndex) to be removed from 
         the real server. A zero is returned when read."
    ::= { slbNewCfgRealServerEntry 16 }

slbNewCfgRealServerCookie OBJECT-TYPE
    SYNTAX  INTEGER {
	enabled(1),
	disabled(2),
        unsupported(2147483647)
	}
    MAX-ACCESS  read-create
    STATUS  current
    DESCRIPTION
        "Enable or disable real server to handle client requests
         that don't contain a cookie if cookie loadbalance is enabled." 
    ::= { slbNewCfgRealServerEntry 17 }

slbNewCfgRealServerExcludeStr OBJECT-TYPE
    SYNTAX  INTEGER {
	enabled(1),
	disabled(2),
        unsupported(2147483647)
	}
    MAX-ACCESS  read-create
    STATUS  current
    DESCRIPTION
        "Enable or disable exclusionary matching string on real server."
    ::= { slbNewCfgRealServerEntry 18 }

slbNewCfgRealServerSubmac OBJECT-TYPE
    SYNTAX  INTEGER {
	enabled(1),
	disabled(2),
        unsupported(2147483647)
	}
    MAX-ACCESS  read-create
    STATUS  current
    DESCRIPTION
        "The real server config to enable/disable MAC SA substitution for 
         L4 traffic. If disabled (the default) we will NOT substitute the 
         MAC SA of client-to-server frames.  If enabled, we will substitute 
         the MAC SA."
    ::= { slbNewCfgRealServerEntry 19 }

slbNewCfgRealServerProxy OBJECT-TYPE
    SYNTAX  INTEGER {
	enabled(1),
	disabled(2),
        unsupported(2147483647)
	}
    MAX-ACCESS  read-create
    STATUS  current
    DESCRIPTION
        "The real server config to enable/disable client proxy operation."
    ::= { slbNewCfgRealServerEntry 20 }

slbNewCfgRealServerLdapwr OBJECT-TYPE
    SYNTAX  INTEGER {
        enabled(1),
        disabled(2),
        unsupported(2147483647)
        }
    MAX-ACCESS  read-create
    STATUS  current
    DESCRIPTION
        "The real server config to enable/disable LDAP write server."
    ::= { slbNewCfgRealServerEntry 21 }

slbNewCfgRealServerOid OBJECT-TYPE
    SYNTAX DisplayString (SIZE(0..128))
    MAX-ACCESS read-create
    STATUS current
    DESCRIPTION
        "The OID to be sent in the SNMP get request packet."
    ::= { slbNewCfgRealServerEntry 22 }

slbNewCfgRealServerCommString OBJECT-TYPE
    SYNTAX DisplayString (SIZE(0..32))
    MAX-ACCESS read-create
    STATUS current
    DESCRIPTION
        "The community string to be used in the SNMP get request packet."
    ::= { slbNewCfgRealServerEntry 23 }

slbNewCfgRealServerIdsvlan OBJECT-TYPE
    SYNTAX  INTEGER (0..4090)
    MAX-ACCESS  read-create
    STATUS  current
    DESCRIPTION
        "The VLAN to be associated with IDS server."
    ::= { slbNewCfgRealServerEntry 24 }

slbNewCfgRealServerIdsport OBJECT-TYPE
    SYNTAX  Integer32
    MAX-ACCESS  read-create
    STATUS  current
    DESCRIPTION
        "The port to be connected to IDS server."
    ::= { slbNewCfgRealServerEntry 25 }

slbNewCfgRealServerAvail OBJECT-TYPE
    SYNTAX  INTEGER (1..48)
    MAX-ACCESS  read-create
    STATUS  current
    DESCRIPTION
        "The remote real server Global SLB availability."
    ::= { slbNewCfgRealServerEntry 26 }

slbNewCfgRealServerFastHealthCheck OBJECT-TYPE
    SYNTAX  INTEGER {
        enabled(1),
        disabled(2),
        unsupported(2147483647)
        }
    MAX-ACCESS  read-create
    STATUS  current
    DESCRIPTION
        "The real server config to enable/disable Fast Health Check Operation."
    ::= { slbNewCfgRealServerEntry 27 }

slbNewCfgRealServerSubdmac OBJECT-TYPE
    SYNTAX  INTEGER {
        enabled(1),
        disabled(2),
        unsupported(2147483647)
        }
    MAX-ACCESS  read-create
    STATUS  current
    DESCRIPTION
        "The real server config to enable/disable MAC DA substitution for
         L4 traffic. If disabled, we will NOT substitute the MAC DA of
         client-to-server frames.  If enabled(default), we will substitute
         the MAC DA."
    ::= { slbNewCfgRealServerEntry 28 }

slbNewCfgRealServerOverflow OBJECT-TYPE
    SYNTAX  INTEGER {
        enabled(1),
        disabled(2),
        unsupported(2147483647)
        }
    MAX-ACCESS  read-create
    STATUS  current
    DESCRIPTION
        "The real server config to enable/disable Overflow. If enabled(default)
         allows Backup server to kick in if real server reaches maximum
         connections."
    ::= { slbNewCfgRealServerEntry 29 }

slbNewCfgRealServerBkpPreempt OBJECT-TYPE
    SYNTAX  INTEGER {
        enabled(1),
        disabled(2),
        unsupported(2147483647)
        }
    MAX-ACCESS  read-create
    STATUS  current
    DESCRIPTION
        "The real server config to enable/disable backup preemption. If enabled
         (default)allows to preempt the backup server when the primary server
         comes up. If disabled the backup server will continue to serve the
         traffic even when primary server comes up."
    ::= { slbNewCfgRealServerEntry 30 }

slbNewCfgRealServerIpVer OBJECT-TYPE
    SYNTAX  INTEGER{
        ipv4(1),
        ipv6(2),
        unsupported(2147483647)
        }
    MAX-ACCESS  read-create
    STATUS  current
    DESCRIPTION
        "The type of IP address."
    ::= { slbNewCfgRealServerEntry 31 }

slbNewCfgRealServerIpv6Addr OBJECT-TYPE
   SYNTAX DisplayString (SIZE(0..40))
    MAX-ACCESS  read-create
    STATUS  current
    DESCRIPTION
    "  IPV6 address of the real server identified by the instance of the slbRealServerIndex.
       Address should be 4-byte hexadecimal colon notation. Valid IPv6 address should be in
       any of the following forms xxxx:xxxx:xxxx:xxxx:xxxx:xxxx:xxxx:xxxx or xxxx::xxxx:xxxx:xxxx:xxxx or ::xxxx "
   ::= { slbNewCfgRealServerEntry 32 }

slbNewCfgRealServerNxtRportIdx OBJECT-TYPE
    SYNTAX  INTEGER (0..64)
    MAX-ACCESS  read-only
    STATUS  current
    DESCRIPTION
        "The next available free slot index number, to add the real port
         to the server. Value 0 will be returned if no free slot available."
    ::= { slbNewCfgRealServerEntry 33 }

slbNewCfgRealServerNxtBuddyIdx OBJECT-TYPE
    SYNTAX  INTEGER (0..4)
    MAX-ACCESS  read-only
    STATUS  current
    DESCRIPTION
    "The next available free slot Buddy index number, to add the Buddy Server
    to the Real server. Value 0 will be returned if no free slot available."
    ::= { slbNewCfgRealServerEntry 34 }

slbNewCfgRealServerMode OBJECT-TYPE
    SYNTAX  INTEGER {
        physical(1),
	logical(2),
        unsupported(2147483647)
	}
    MAX-ACCESS  read-create
    STATUS  current
    DESCRIPTION
        "Set the mode of the real server. By default the mode is set to physical."
    ::= { slbNewCfgRealServerEntry 35 }

slbNewCfgUpdateAllRealServers OBJECT-TYPE
    SYNTAX  INTEGER {
        none(0),
	mode(1),
	maxcon(2),
	weight(3),
	all(4),
        unsupported(2147483647)
	}
    MAX-ACCESS  read-create
    STATUS  current
    DESCRIPTION
        "Set all the real servers having the same RIP address as this real server
	with the mode and/or maximum connection value (if mode is physical) that is
	set in this real server. When read, none(0) is returned.
	mode   - set only the mode to all real servers with same RIP address.
	maxcon - set only the max connections to all real servers with same RIP address.
	weight - set only the weight to all real servers with same RIP address.
	all    - set mode, max connections and weight to all real servers with same RIP address."
    ::= { slbNewCfgRealServerEntry 36 }	

-- Real server Proxy IP start
slbNewCfgRealServerProxyIpMode OBJECT-TYPE   
    SYNTAX INTEGER {
        enable(0),
        address(2),
        nwclss(3),
        disable(4),
        unsupported(2147483647)
        }
    MAX-ACCESS  read-create
    STATUS  current
    DESCRIPTION
        "Set the real server Proxy IP mode. 
          Changing from address(2) to any other mode will clear the configured IPv4/IPv6 address,prefix and persistancy.
          Changing from  nwclass(3) to any other mode will clear the configured NWclass and NWpersistancy."
    ::= { slbNewCfgRealServerEntry 37 }

slbNewCfgRealServerProxyIpAddr OBJECT-TYPE
    SYNTAX  IpAddress
    MAX-ACCESS  read-create
    STATUS  current
    DESCRIPTION
        "This object ID allows configuration of real server proxy IP v4 address .
		The IP version for addr must be the same as the real server IP version.
		This object ID can be set only if slbNewCfgRealServerIpVer is set to ipv4 & slbNewCfgRealServerProxyIpMode is address else return failure.
		Returns 0 if IP version is IPv6 or slbNewCfgRealServerProxyIpMode is not set to address.
		When a subnet is configured, user has the ability to select PIP persistency mode.
		Persistency is relevant only if the PIP is configured as subnet. If PIP is not configured or
		not subnet, the persistency configuration value is disable." 
    ::= { slbNewCfgRealServerEntry 38 }

slbNewCfgRealServerProxyIpMask OBJECT-TYPE
    SYNTAX  IpAddress
    MAX-ACCESS  read-create
    STATUS  current
    DESCRIPTION
        "This object ID allows configuration of real server proxy IP Mask. 
	        The IP version for addr must be the same as the real server IP version.
       	 This object ID can be set only if slbNewCfgRealServerIpVer is set to ipv4  & slbNewCfgRealServerProxyIpMode is address else return failure.
		 Returns 0 if IP version is IPv6 or slbNewCfgRealServerProxyIpMode is not set to address.
		 When a subnet is configured user has the ability to select PIP persistency mode.
	 	 Persistency is relevant only if the PIP is configured as subnet. If PIP is not configured or
		 not subnet, the persistency configuration value is disable." 
    ::= { slbNewCfgRealServerEntry 39 }

slbNewCfgRealServerProxyIpv6Addr OBJECT-TYPE
    SYNTAX  DisplayString (SIZE(0..40))
    MAX-ACCESS  read-create
    STATUS  current
    DESCRIPTION
        "This object ID allows configuration of real server proxy IPv6 address . 
		The IP version for addr must be the same as the real server IP version. 
		Returns emply if IP version is IPv4 or slbNewCfgRealServerProxyIpMode is not set to address.
		This object ID can be set only if slbNewCfgRealServerIpVer is set to ipv6  & slbNewCfgRealServerProxyIpMode is address else return failure.		
		When a subnet is configured, user has the ability to select PIP persistency mode.
		Persistency is relevant only if the PIP is configured as subnet. If PIP is not configured or
		not subnet, the persistency configuration value is disable.
		Address should be 4-byte hexadecimal colon notation.
		Valid IPv6 address should be in any of the following forms
           xxxx:xxxx:xxxx:xxxx:xxxx:xxxx:xxxx:xxxx or
           xxxx::xxxx:xxxx:xxxx:xxxx or ::xxxx." 
    ::= { slbNewCfgRealServerEntry 40 }

slbNewCfgRealServerProxyIpv6Prefix OBJECT-TYPE
    SYNTAX  INTEGER (1..128)
    MAX-ACCESS  read-create
    STATUS  current
    DESCRIPTION
        "This object ID allows configuration of real server proxy IPv6 Mask. 
		The IP version for addr must be the same as the real server IP version.
		This object ID can be set only if slbNewCfgRealServerIpVer is set to ipv6  & slbNewCfgRealServerProxyIpMode is address else return failure.		
		Returns 0 if IP version is IPv4 or slbNewCfgRealServerProxyIpMode is set other than address.
		When a subnet is configured user has the ability to select PIP persistency mode.
		Persistency is relevant only if the PIP is configured as subnet. If PIP is not configured or
		not subnet, the persistency configuration value is disable." 
    ::= { slbNewCfgRealServerEntry 41 }

slbNewCfgRealServerProxyIpPersistency OBJECT-TYPE   
    SYNTAX INTEGER {
        disable(0),
        client(1),
	 host(2),
         unsupported(2147483647)
        }
    MAX-ACCESS  read-create  
    STATUS  current
    DESCRIPTION
        "When a subnet is configured user has the ability to select PIP persistency mode.
		This object ID can be set only if slbNewCfgRealServerProxyIpMode is address else return failure.		
		Persistency is relevant only if a PIP class is configured. If PIP is not configured the
		persistency configuration is disable."
    ::= { slbNewCfgRealServerEntry 42 }

slbNewCfgRealServerProxyIpNWclass OBJECT-TYPE
    SYNTAX  DisplayString  (SIZE(0..32)) 
    MAX-ACCESS  read-create
    STATUS  current
    DESCRIPTION
        "This  object ID allows configuration of real server proxy IP IPv4 or IPv6 Network Class as PIP.
		This object ID can be set only if slbNewCfgRealServerProxyIpMode is nwclss else return failure.		
		Persistency is relevant only if a PIP class is configured. If PIP is not configured the
		persistency configuration is disable.
              Returns empty string when slbNewCfgRealServerProxyIpMode is not set to nwclss(3)." 
    ::= { slbNewCfgRealServerEntry 43 }

slbNewCfgRealServerProxyIpNWclassPersistency OBJECT-TYPE   
    SYNTAX INTEGER {
        disable(0),
        client(1),
        unsupported(2147483647)
        }
    MAX-ACCESS  read-create
    STATUS  current
    DESCRIPTION
        "This object ID allows configuration of real server Network Class PIP persistency mode.
		This object ID can be set only if slbNewCfgRealServerProxyIpMode is nwclss else return failure.		
		Persistency is relevant only if a PIP class is configured. If PIP is not configured the
		persistency configuration is disable.
              Returns 0 when slbNewCfgRealServerProxyIpMode is not set to nwclss(3)." 
    ::= { slbNewCfgRealServerEntry 44 }   


 slbNewCfgRealServerHealthID OBJECT-TYPE
    SYNTAX DisplayString (SIZE(0..32))
    MAX-ACCESS read-write
    STATUS current
    DESCRIPTION
        "The Advanced HC ID."
    ::= { slbNewCfgRealServerEntry 45 }

-- Real server Proxy IP end 

-- Real Server Multiple Port Table

slbRealServPortTableMaxSize OBJECT-TYPE
    SYNTAX  Integer32 
    MAX-ACCESS  read-only 
    STATUS  current 
    DESCRIPTION 
        "The maximum number of entries in SLB RealServPortTable.
         Note:This mib is not supported on VX instance of Virtualization." 
    ::= { realServerCfg 4 }

slbCurCfgRealServPortTable OBJECT-TYPE
    SYNTAX  SEQUENCE OF SlbCurCfgRealServPortEntry
    MAX-ACCESS  not-accessible
    STATUS  current
    DESCRIPTION
        "The table of real server service ports.
         Note:This mib is not supported on VX instance of Virtualization."
    ::= { realServerCfg 5 }

slbCurCfgRealServPortEntry OBJECT-TYPE
    SYNTAX  SlbCurCfgRealServPortEntry
    MAX-ACCESS  not-accessible
    STATUS  current
    DESCRIPTION
        "A row in the real server service ports table."
    INDEX   { slbCurCfgRealServIndex, slbCurCfgRealServPortIndex }
    ::= { slbCurCfgRealServPortTable 1 }

SlbCurCfgRealServPortEntry ::= SEQUENCE {
    slbCurCfgRealServIndex         Integer32,
    slbCurCfgRealServPortIndex     Integer32,
    slbCurCfgRealServRealPort      INTEGER
    }

slbCurCfgRealServIndex OBJECT-TYPE
    SYNTAX  Integer32
    MAX-ACCESS  read-only
    STATUS  current
    DESCRIPTION
        "The number of the real server." 
    ::= { slbCurCfgRealServPortEntry 1 }

slbCurCfgRealServPortIndex OBJECT-TYPE 
    SYNTAX  Integer32 
    MAX-ACCESS  read-only 
    STATUS  current 
    DESCRIPTION 
        "The port index. This has no external meaning" 
    ::= { slbCurCfgRealServPortEntry 2 }

slbCurCfgRealServRealPort OBJECT-TYPE  
    SYNTAX  INTEGER (2..65534)
    MAX-ACCESS  read-only  
    STATUS  current  
    DESCRIPTION 
        "The layer4 real service port number."  
    ::= { slbCurCfgRealServPortEntry 3 } 

slbNewCfgRealServPortTable OBJECT-TYPE
    SYNTAX  SEQUENCE OF SlbNewCfgRealServPortEntry
    MAX-ACCESS  not-accessible
    STATUS  current
    DESCRIPTION
        "The table of real server service ports.
         Note:This mib is not supported on VX instance of Virtualization."
    ::= { realServerCfg 6 }

slbNewCfgRealServPortEntry OBJECT-TYPE
    SYNTAX  SlbNewCfgRealServPortEntry
    MAX-ACCESS  not-accessible
    STATUS  current
    DESCRIPTION
        "A row in the real server service ports table."
    INDEX   { slbNewCfgRealServIndex, slbNewCfgRealServPortIndex }
    ::= { slbNewCfgRealServPortTable 1 }

SlbNewCfgRealServPortEntry ::= SEQUENCE {
    slbNewCfgRealServIndex           Integer32,
    slbNewCfgRealServPortIndex       Integer32,
    slbNewCfgRealServRealPort        INTEGER,
    slbNewCfgRealServPortDelete      INTEGER,
    slbNewCfgRealServRealPortFreeIdx INTEGER
    }

slbNewCfgRealServIndex OBJECT-TYPE
    SYNTAX  Integer32
    MAX-ACCESS  read-only
    STATUS  current
    DESCRIPTION
        "The number of the real server." 
    ::= { slbNewCfgRealServPortEntry 1 }

slbNewCfgRealServPortIndex OBJECT-TYPE 
    SYNTAX  Integer32 
    MAX-ACCESS  read-only 
    STATUS  current 
    DESCRIPTION 
        "The port index. This has no external meaning" 
    ::= { slbNewCfgRealServPortEntry 2 }

slbNewCfgRealServRealPort OBJECT-TYPE  
    SYNTAX  INTEGER (2..65534)
    MAX-ACCESS  read-create  
    STATUS  current  
    DESCRIPTION 
        "The layer4 real service port number."  
    ::= { slbNewCfgRealServPortEntry 3 } 

slbNewCfgRealServPortDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { slbNewCfgRealServPortEntry 4 }

slbNewCfgRealServRealPortFreeIdx OBJECT-TYPE
    SYNTAX  INTEGER(0..64)
    MAX-ACCESS  read-create
    STATUS  current
    DESCRIPTION
        "The first free port index number of the real server.
         Value 0 will be returned when all 64 ports are 
         configured for a real server."
    ::= { slbNewCfgRealServPortEntry 5 }

slbBuddyTableMaxSize OBJECT-TYPE
    SYNTAX  Integer32
    MAX-ACCESS  read-only
    STATUS  current
    DESCRIPTION
        "The maximum number of entries in SLB real buddy server table.
         Note:This mib is not supported on VX instance of Virtualization."
    ::= { realServerCfg 7 }

slbCurCfgBuddyTable OBJECT-TYPE
    SYNTAX  SEQUENCE OF SlbCurCfgBuddyEntry
    MAX-ACCESS  not-accessible
    STATUS  current
    DESCRIPTION
        "The table of buddy information.
         Note:This mib is not supported on VX instance of Virtualization."
    ::= { realServerCfg 8 }

slbCurCfgBuddyEntry OBJECT-TYPE
    SYNTAX  SlbCurCfgBuddyEntry
    MAX-ACCESS  not-accessible
    STATUS  current
    DESCRIPTION
        "A row in the buddy server table."
    INDEX   { slbCurCfgRealSerIndex,  slbCurCfgBuddyIndex }
    ::= { slbCurCfgBuddyTable 1 }

SlbCurCfgBuddyEntry ::= SEQUENCE {
    slbCurCfgRealSerIndex       Integer32,
    slbCurCfgBuddyIndex         Integer32,
    slbCurCfgBuddyRealIndex     Integer32, 
    slbCurCfgBuddyGroupIndex    Integer32,
    slbCurCfgBuddyService       INTEGER 
    }

slbCurCfgRealSerIndex OBJECT-TYPE
    SYNTAX  Integer32
    MAX-ACCESS  read-only
    STATUS  current
    DESCRIPTION
        "The number of the real server."
    ::= { slbCurCfgBuddyEntry 1 }

slbCurCfgBuddyIndex OBJECT-TYPE
    SYNTAX  Integer32
    MAX-ACCESS  read-only
    STATUS  current
    DESCRIPTION
    "The buddy index. This has no external meaning"
    ::= { slbCurCfgBuddyEntry 2 }

slbCurCfgBuddyRealIndex OBJECT-TYPE
    SYNTAX  Integer32
    MAX-ACCESS  read-only
    STATUS  current
    DESCRIPTION
        "The buddy server's real server number."
    ::= { slbCurCfgBuddyEntry 3 }

slbCurCfgBuddyGroupIndex OBJECT-TYPE
    SYNTAX  Integer32
    MAX-ACCESS  read-only
    STATUS  current
    DESCRIPTION
        "The buddy server's real group number."
    ::= { slbCurCfgBuddyEntry 4 }

slbCurCfgBuddyService OBJECT-TYPE
    SYNTAX   INTEGER (9..65534)
    MAX-ACCESS  read-only
    STATUS  current
    DESCRIPTION
        "The buddy server's service."
    ::= { slbCurCfgBuddyEntry 5 }

slbNewCfgBuddyTable OBJECT-TYPE
    SYNTAX  SEQUENCE OF SlbNewCfgBuddyEntry
    MAX-ACCESS  not-accessible
    STATUS  current
    DESCRIPTION
        "The table of buddy servers.
         Note:This mib is not supported on VX instance of Virtualization."
    ::= { realServerCfg 9 }

slbNewCfgBuddyEntry OBJECT-TYPE
    SYNTAX  SlbNewCfgBuddyEntry
    MAX-ACCESS  not-accessible
    STATUS  current
    DESCRIPTION
        "A row in the real server buddy table."
    INDEX   { slbNewCfgRealSerIndex, slbNewCfgBuddyIndex  }
    ::= { slbNewCfgBuddyTable 1 }

SlbNewCfgBuddyEntry      ::= SEQUENCE {
    slbNewCfgRealSerIndex         Integer32,
    slbNewCfgBuddyIndex           Integer32,
    slbNewCfgBuddyRealIndex       Integer32,
    slbNewCfgBuddyGroupIndex      Integer32,
    slbNewCfgBuddyService         INTEGER,
    slbNewCfgBuddyDelete          INTEGER
    }

slbNewCfgRealSerIndex OBJECT-TYPE
    SYNTAX  Integer32
    MAX-ACCESS  read-only
    STATUS  current
    DESCRIPTION
        "The number of the real server."
    ::= { slbNewCfgBuddyEntry 1 }

slbNewCfgBuddyIndex OBJECT-TYPE
    SYNTAX  Integer32
    MAX-ACCESS  read-only
    STATUS  current
    DESCRIPTION
        "The buddy index. This has no external meaning"
    ::= { slbNewCfgBuddyEntry 2 }

slbNewCfgBuddyRealIndex OBJECT-TYPE
    SYNTAX  Integer32 
    MAX-ACCESS  read-create
    STATUS  current
    DESCRIPTION
        "The buddy server's real server number."
    ::= { slbNewCfgBuddyEntry 3 }

slbNewCfgBuddyGroupIndex OBJECT-TYPE
    SYNTAX  Integer32
    MAX-ACCESS  read-create
    STATUS  current
    DESCRIPTION
        "The buddy server's real group number."
    ::= { slbNewCfgBuddyEntry 4 }

slbNewCfgBuddyService OBJECT-TYPE
    SYNTAX  INTEGER (9..65534) 
    MAX-ACCESS  read-create
    STATUS  current
    DESCRIPTION
        "The buddy server's service."
    ::= { slbNewCfgBuddyEntry 5 }

slbNewCfgBuddyDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgBuddyEntry 6 }

 -- Real Server Enhanced Table - Current Configuration

slbCurCfgEnhRealServerTable OBJECT-TYPE
    SYNTAX SEQUENCE OF SlbCurCfgEnhRealServerEntry
    MAX-ACCESS not-accessible
    STATUS current
    DESCRIPTION
        "The table of Real Server configuration in the current_config.
         Note:This mib is not supported on VX instance of Virtualization."
    ::= { realServerCfg 10 }

slbCurCfgEnhRealServerEntry OBJECT-TYPE
    SYNTAX SlbCurCfgEnhRealServerEntry
    MAX-ACCESS not-accessible
    STATUS current
    DESCRIPTION
        "Information about a particular Real Server configuration."
    INDEX { slbCurCfgEnhRealServerIndex }
    ::= { slbCurCfgEnhRealServerTable 1 }

SlbCurCfgEnhRealServerEntry ::= SEQUENCE {
    slbCurCfgEnhRealServerIndex           DisplayString,
    slbCurCfgEnhRealServerIpAddr          IpAddress,
    slbCurCfgEnhRealServerWeight          INTEGER,
    slbCurCfgEnhRealServerMaxConns        INTEGER,
    slbCurCfgEnhRealServerTimeOut         INTEGER,
    slbCurCfgEnhRealServerPingInterval    INTEGER,
    slbCurCfgEnhRealServerFailRetry       INTEGER,
    slbCurCfgEnhRealServerSuccRetry       INTEGER,
    slbCurCfgEnhRealServerState           INTEGER,
    slbCurCfgEnhRealServerType            INTEGER,
    slbCurCfgEnhRealServerName            DisplayString,
    slbCurCfgEnhRealServerCookie          INTEGER,
    slbCurCfgEnhRealServerExcludeStr      INTEGER,
    slbCurCfgEnhRealServerSubmac          INTEGER,
    slbCurCfgEnhRealServerIdsport         Integer32,
    slbCurCfgEnhRealServerIpVer           INTEGER,
    slbCurCfgEnhRealServerIpv6Addr        DisplayString,
    slbCurCfgEnhRealServerLLBType         INTEGER,
    slbCurCfgEnhRealServerPortsIngress	  DisplayString,
    slbCurCfgEnhRealServerPortsEgress 	  DisplayString,
    slbCurCfgEnhRealServerVlanIngress	  Integer32,
    slbCurCfgEnhRealServerVlanEgress	  Integer32,
    slbCurCfgEnhRealServerEgressIf	 	  Integer32,
    slbCurCfgEnhRealServerSecType 		  INTEGER,
    slbCurCfgEnhRealServerIngressIf	 	  Integer32,
    slbCurCfgEnhRealServerIpVerDuplicate  INTEGER,
    slbCurCfgEnhRealServerSecDeviceFlag 		  INTEGER,
    slbCurCfgEnhRealServerIngport         Integer32

}

slbCurCfgEnhRealServerIndex OBJECT-TYPE
    SYNTAX DisplayString (SIZE(1..255))
    MAX-ACCESS  read-only
    STATUS  current
    DESCRIPTION
        "The real server number"
    ::= { slbCurCfgEnhRealServerEntry 1 }

slbCurCfgEnhRealServerIpAddr OBJECT-TYPE
    SYNTAX  IpAddress
    MAX-ACCESS  read-only
    STATUS  current
    DESCRIPTION
        "IP address of the real server identified by the instance of the
         slbRealServerIndex."
    ::= { slbCurCfgEnhRealServerEntry 2 }

slbCurCfgEnhRealServerWeight OBJECT-TYPE
    SYNTAX  INTEGER (1..48)
    MAX-ACCESS  read-only
    STATUS  current
    DESCRIPTION
        "The server weight."
    ::= { slbCurCfgEnhRealServerEntry 3 }

slbCurCfgEnhRealServerMaxConns OBJECT-TYPE
    SYNTAX  INTEGER (0..1000000)
    MAX-ACCESS  read-only
    STATUS  current
    DESCRIPTION
        "The maximum number of connections that are allowed."
    ::= { slbCurCfgEnhRealServerEntry 4 }

slbCurCfgEnhRealServerTimeOut OBJECT-TYPE
    SYNTAX  INTEGER (2..32768)
    MAX-ACCESS  read-only
    STATUS  current
    DESCRIPTION
        "The maximum number of minutes an inactive connection remains open."
    ::= { slbCurCfgEnhRealServerEntry 5 }

slbCurCfgEnhRealServerPingInterval OBJECT-TYPE
    SYNTAX  INTEGER (0..60)
    MAX-ACCESS  read-only
    STATUS  current
    DESCRIPTION
        "The interval between keep-alive (ping) attempts in number of seconds.
         Zero means disabling ping attempt."
    ::= { slbCurCfgEnhRealServerEntry 6 }

slbCurCfgEnhRealServerFailRetry OBJECT-TYPE
    SYNTAX  INTEGER  (1..63)
    MAX-ACCESS  read-only
    STATUS  current
    DESCRIPTION
        "The number of failed attempts to declare this server DOWN."
    ::= { slbCurCfgEnhRealServerEntry 7 }

slbCurCfgEnhRealServerSuccRetry OBJECT-TYPE
    SYNTAX  INTEGER (1..63)
    MAX-ACCESS  read-only
    STATUS  current
    DESCRIPTION
        "The number of successful attempts to declare a server UP."
    ::= { slbCurCfgEnhRealServerEntry 8 }

slbCurCfgEnhRealServerState OBJECT-TYPE
    SYNTAX  INTEGER {
        enabled(2),
        disabled(3),
        disabled-with-fastage(4),
	shutdown-connection(5),
	shutdown-persistent-sessions(6),
        unsupported(2147483647)
    }
    MAX-ACCESS  read-only
    STATUS  current
    DESCRIPTION
        "Enable or disable the server and remove the existing sessions using disabled-with-fastage option."
    ::= { slbCurCfgEnhRealServerEntry 9 }

slbCurCfgEnhRealServerType OBJECT-TYPE
    SYNTAX  INTEGER {
        local-server(1),
        remote-server(2),
        unsupported(2147483647)
    }
    MAX-ACCESS  read-only
    STATUS  current
    DESCRIPTION
        "The server type.  It participates in global server
         load balancing when it is configured as remote-server."
    ::= { slbCurCfgEnhRealServerEntry 10 }

slbCurCfgEnhRealServerName OBJECT-TYPE
    SYNTAX  DisplayString (SIZE(0..255))
    MAX-ACCESS  read-only
    STATUS  current
    DESCRIPTION
        "The name of the real server."
    ::= { slbCurCfgEnhRealServerEntry 11 }

slbCurCfgEnhRealServerCookie OBJECT-TYPE
    SYNTAX  INTEGER {
        enabled(1),
        disabled(2),
        unsupported(2147483647)
    }
    MAX-ACCESS  read-only
    STATUS  current
    DESCRIPTION
        "The real server that will handle client requests that doesn't
         contain an URL cookie if Cookie loadbalance is enabled."
    ::= { slbCurCfgEnhRealServerEntry 12 }

slbCurCfgEnhRealServerExcludeStr OBJECT-TYPE
    SYNTAX  INTEGER {
        enabled(1),
        disabled(2),
        unsupported(2147483647)
    }
    MAX-ACCESS  read-only
    STATUS  current
    DESCRIPTION
        "The real server will handle requests that don't match the
         loadbalance string if it is enabled."
    ::= { slbCurCfgEnhRealServerEntry 13 }

slbCurCfgEnhRealServerSubmac OBJECT-TYPE
    SYNTAX  INTEGER {
        enabled(1),
        disabled(2),
        unsupported(2147483647)
    }
    MAX-ACCESS  read-only
    STATUS  current
    DESCRIPTION
        "The real server config to enable/disable MAC SA substitution for
         L4 traffic. If disabled (the default) we will NOT substitute the
         MAC SA of client-to-server frames.  If enabled, we will substitute
         the MAC SA."
    ::= { slbCurCfgEnhRealServerEntry 14 }

slbCurCfgEnhRealServerIdsport OBJECT-TYPE
    SYNTAX  Integer32
    MAX-ACCESS  read-only
    STATUS  current
    DESCRIPTION
        "The port to be connected to the IDS server."
    ::= { slbCurCfgEnhRealServerEntry 15 }

slbCurCfgEnhRealServerIpVer OBJECT-TYPE
    SYNTAX  INTEGER{
        ipv4(1),
        ipv6(2),
        unsupported(2147483647)
    }
    MAX-ACCESS  read-only
    STATUS  current
    DESCRIPTION
        "The type of IP address."
    ::= { slbCurCfgEnhRealServerEntry 16 }


slbCurCfgEnhRealServerIpv6Addr OBJECT-TYPE
    SYNTAX DisplayString (SIZE(0..40))
    MAX-ACCESS  read-only
    STATUS  current
    DESCRIPTION
        "IPV6 address of the real server identified by the instance of the slbRealServerIndex.
         Address should be 4-byte hexadecimal colon notation. Valid IPv6 address should be in
         any of the following forms xxxx:xxxx:xxxx:xxxx:xxxx:xxxx:xxxx:xxxx or xxxx::xxxx:xxxx:xxxx:xxxx or ::xxxx "
    ::= { slbCurCfgEnhRealServerEntry 17 }


slbCurCfgEnhRealServerLLBType OBJECT-TYPE
    SYNTAX  INTEGER {
	local(0),
	remote(1),
	wanlink(2),
        unsupported(2147483647)
	}
    MAX-ACCESS  read-only
    STATUS  current
    DESCRIPTION
        "The server type." 
    ::= { slbCurCfgEnhRealServerEntry 18 }

slbCurCfgEnhRealServerPortsIngress OBJECT-TYPE
    SYNTAX DisplayString (SIZE(0..40))
    MAX-ACCESS  read-only
    STATUS  current
    DESCRIPTION
        " List of ingress ports attached to the real server (security device), used for SSL inspection WebUI wizard.
	Using the following format: xx, xx, xx"
    ::= { slbCurCfgEnhRealServerEntry 19 }

slbCurCfgEnhRealServerPortsEgress OBJECT-TYPE
    SYNTAX DisplayString (SIZE(0..40))
    MAX-ACCESS  read-only
    STATUS  current
    DESCRIPTION
        " List of egress ports attached to the real server (security device), used for SSL inspection WebUI wizard.
	Using the following format: xx, xx, xx"
    ::= { slbCurCfgEnhRealServerEntry 20 }

slbCurCfgEnhRealServerVlanIngress OBJECT-TYPE
    SYNTAX Integer32
    MAX-ACCESS  read-only
    STATUS  current
    DESCRIPTION
        " The egress Vlan specified on security device.
	 Used for SSL wizard"
    ::= { slbCurCfgEnhRealServerEntry 21 }

slbCurCfgEnhRealServerVlanEgress OBJECT-TYPE
    SYNTAX Integer32
    MAX-ACCESS  read-only
    STATUS  current
    DESCRIPTION
        " The egress Vlan specified on security device.
	 Used for SSL wizard"
    ::= { slbCurCfgEnhRealServerEntry 22 }

slbCurCfgEnhRealServerEgressIf OBJECT-TYPE
    SYNTAX Integer32
    MAX-ACCESS  read-only
    STATUS  current
    DESCRIPTION
        " The egress interface specified on security device.
	 Used for SSL wizard"
    ::= { slbCurCfgEnhRealServerEntry 23 }

slbCurCfgEnhRealServerSecType OBJECT-TYPE
    SYNTAX  INTEGER {
		none(1),
		virtual(2),
		layer(3),
		passive(4),
		l3sw(5),
                unsupported(2147483647)
	}
    MAX-ACCESS  read-only
    STATUS  current
    DESCRIPTION
        "The security device  type." 
    ::= { slbCurCfgEnhRealServerEntry 24 }

slbCurCfgEnhRealServerIngressIf OBJECT-TYPE
    SYNTAX Integer32
    MAX-ACCESS  read-only
    STATUS  current
    DESCRIPTION
        " The ingress interface specified on security device.
	 Used for SSL wizard"
    ::= { slbCurCfgEnhRealServerEntry 25 }

slbCurCfgEnhRealServerIpVerDuplicate OBJECT-TYPE
    SYNTAX  INTEGER{
        ipv4(1),
        ipv6(2),
        unsupported(2147483647)
    }
    MAX-ACCESS  read-only
    STATUS  current
    DESCRIPTION
        "The type of IP address."
    ::= { slbCurCfgEnhRealServerEntry 26 }

slbCurCfgEnhRealServerSecDeviceFlag OBJECT-TYPE
	SYNTAX  INTEGER {
        none(1),
		security(2),
        unsupported(2147483647)
	} 
	MAX-ACCESS  read-only
    STATUS  current
    DESCRIPTION
        "The Real security device flag"
    ::= { slbCurCfgEnhRealServerEntry 27 }

slbCurCfgEnhRealServerIngport OBJECT-TYPE
    SYNTAX  Integer32
    MAX-ACCESS  read-only
    STATUS  current
    DESCRIPTION
        "The port to be connected to the IDS server."
    ::= { slbCurCfgEnhRealServerEntry 28 }

slbCurCfgEnhRealServerSecondPartTable OBJECT-TYPE
    SYNTAX SEQUENCE OF SlbCurCfgEnhRealServerSecondPartEntry
    MAX-ACCESS not-accessible
    STATUS current
    DESCRIPTION
        "The second table of Real Server configuration in the current_config.
         Note:This mib is not supported on VX instance of Virtualization."
    ::= { realServerCfg 16 }

slbCurCfgEnhRealServerSecondPartEntry OBJECT-TYPE
    SYNTAX SlbCurCfgEnhRealServerSecondPartEntry
    MAX-ACCESS not-accessible
    STATUS current
    DESCRIPTION
        "Information about a particular Real Server configuration."
    INDEX { slbCurCfgEnhRealServerSecondPartIndex }
    ::= { slbCurCfgEnhRealServerSecondPartTable 1 }

SlbCurCfgEnhRealServerSecondPartEntry ::= SEQUENCE {
    slbCurCfgEnhRealServerSecondPartIndex DisplayString,
    slbCurCfgEnhRealServerUrlBmap         OCTET STRING,
    slbCurCfgEnhRealServerProxy           INTEGER,
    slbCurCfgEnhRealServerLdapwr          INTEGER,
    slbCurCfgEnhRealServerIdsvlan         INTEGER,
    slbCurCfgEnhRealServerAvail           INTEGER,
    slbCurCfgEnhRealServerFastHealthCheck INTEGER,
    slbCurCfgEnhRealServerSubdmac         INTEGER,
    slbCurCfgEnhRealServerOverflow        INTEGER,
    slbCurCfgEnhRealServerBkpPreempt      INTEGER,
    slbCurCfgEnhRealServerMode            INTEGER,
    slbCurCfgEnhRealServerProxyIpMode     INTEGER,
    slbCurCfgEnhRealServerProxyIpAddr     IpAddress,
    slbCurCfgEnhRealServerProxyIpMask     IpAddress,
    slbCurCfgEnhRealServerProxyIpv6Addr   DisplayString,
    slbCurCfgEnhRealServerProxyIpv6Prefix INTEGER,
    slbCurCfgEnhRealServerProxyIpPersistency   INTEGER,
    slbCurCfgEnhRealServerProxyIpNWclass  DisplayString,
    slbCurCfgEnhRealServerProxyIpNWclassPersistency   INTEGER,
    slbCurCfgEnhRealServerIngvlan         INTEGER

}

slbCurCfgEnhRealServerSecondPartIndex OBJECT-TYPE
    SYNTAX DisplayString (SIZE(1..255))
    MAX-ACCESS  read-only
    STATUS  current
    DESCRIPTION
        "The real server number"
    ::= { slbCurCfgEnhRealServerSecondPartEntry 1 }

slbCurCfgEnhRealServerUrlBmap OBJECT-TYPE
    SYNTAX  OCTET STRING
    MAX-ACCESS  read-only
    STATUS  current
    DESCRIPTION
        "The URL Paths selected for URL load balancing for by the real
         server.  The selected URL Paths are presented in a bitmap format.
         in receiving order:

    OCTET 1  OCTET 2  .....
    xxxxxxxx xxxxxxxx .....
    ||    || |_ URL Path 9
    ||    ||
    ||    ||___ URL Path 8
    ||    |____ URL Path 7
    ||      .    .   .
    ||_________ URL Path 2
    |__________ URL Path 1

    where x : 1 - The represented URL Path is selected
    0 - The represented URL Path is not selected"
    ::= { slbCurCfgEnhRealServerSecondPartEntry 2 }

slbCurCfgEnhRealServerProxy OBJECT-TYPE
    SYNTAX  INTEGER {
        enabled(1),
        disabled(2),
        unsupported(2147483647)
    }
    MAX-ACCESS  read-only
    STATUS  current
    DESCRIPTION
        "The real server config to enable/disable client proxy operation."
    ::= { slbCurCfgEnhRealServerSecondPartEntry 3 }

slbCurCfgEnhRealServerLdapwr OBJECT-TYPE
    SYNTAX  INTEGER {
        enabled(1),
        disabled(2),
        unsupported(2147483647)
    }
    MAX-ACCESS  read-only
    STATUS  current
    DESCRIPTION
        "The real server config to enable/disable LDAP write server."
    ::= { slbCurCfgEnhRealServerSecondPartEntry 4 }

slbCurCfgEnhRealServerIdsvlan OBJECT-TYPE
    SYNTAX  INTEGER (0..4090)
    MAX-ACCESS  read-only
    STATUS  current
    DESCRIPTION
        "The VLAN to be associated with the IDS server."
    ::= { slbCurCfgEnhRealServerSecondPartEntry 5 }

slbCurCfgEnhRealServerAvail OBJECT-TYPE
    SYNTAX  INTEGER (1..48)
    MAX-ACCESS  read-only
    STATUS  current
    DESCRIPTION
        "The remote real server Global SLB availability."
    ::= { slbCurCfgEnhRealServerSecondPartEntry 6 }

slbCurCfgEnhRealServerFastHealthCheck OBJECT-TYPE
    SYNTAX  INTEGER {
        enabled(1),
        disabled(2),
        unsupported(2147483647)
    }
    MAX-ACCESS  read-only
    STATUS  current
    DESCRIPTION
        "The real server config to enable/disable Fast Health Check Operation."
    ::= { slbCurCfgEnhRealServerSecondPartEntry 7 }

slbCurCfgEnhRealServerSubdmac OBJECT-TYPE
    SYNTAX  INTEGER {
        enabled(1),
        disabled(2),
        unsupported(2147483647)
    }
    MAX-ACCESS  read-only
    STATUS  current
    DESCRIPTION
        "The real server config to enable/disable MAC DA substitution for
         L4 traffic. If disabled, we will NOT substitute the MAC DA of
         client-to-server frames.  If enabled(default), we will substitute
         the MAC DA."
    ::= { slbCurCfgEnhRealServerSecondPartEntry 8 }

slbCurCfgEnhRealServerOverflow OBJECT-TYPE
    SYNTAX  INTEGER {
        enabled(1),
        disabled(2),
        unsupported(2147483647)
    }
    MAX-ACCESS  read-only
    STATUS  current
    DESCRIPTION
        "The real server config to enable/disable Overflow. If enabled(default)
         allows Backup server to kick in if real server reaches maximum
         connections."
    ::= { slbCurCfgEnhRealServerSecondPartEntry 9 }

slbCurCfgEnhRealServerBkpPreempt OBJECT-TYPE
    SYNTAX  INTEGER {
        enabled(1),
        disabled(2),
        unsupported(2147483647)
    }
    MAX-ACCESS  read-only
    STATUS  current
    DESCRIPTION
        "The real server config to enable/disable backup preemption. If enabled
         (default)allows to preempt the backup server when the primary server
         comes up. If disabled the backup server will continue to serve the
         traffic even when primary server comes up."
    ::= { slbCurCfgEnhRealServerSecondPartEntry 10 }

slbCurCfgEnhRealServerMode OBJECT-TYPE
    SYNTAX  INTEGER {
        physical(1),
        logical(2),
        unsupported(2147483647)
    }
    MAX-ACCESS  read-only
    STATUS  current
    DESCRIPTION
        "The mode of the real server. By default it is set to physical."
::= { slbCurCfgEnhRealServerSecondPartEntry 11 }

-- Cur Real server Proxy IP start
slbCurCfgEnhRealServerProxyIpMode OBJECT-TYPE
    SYNTAX INTEGER {
        enable(0),
        address(2),
        nwclss(3),
        disable(4),
        unsupported(2147483647)
    }
    MAX-ACCESS  read-only
    STATUS  current
    DESCRIPTION
        " the real server Proxy IP mode "
    ::= { slbCurCfgEnhRealServerSecondPartEntry 12 }

slbCurCfgEnhRealServerProxyIpAddr OBJECT-TYPE
    SYNTAX  IpAddress
    MAX-ACCESS  read-only
    STATUS  current
    DESCRIPTION
        "This object ID shows current configuration of real server proxy IP address .
         Returns 0 when slbCurCfgEnhRealServerProxyIpMode is not set to address.
         Returns 0 if IP version is IPv6."
    ::= { slbCurCfgEnhRealServerSecondPartEntry 13 }

slbCurCfgEnhRealServerProxyIpMask OBJECT-TYPE
    SYNTAX  IpAddress
    MAX-ACCESS  read-only
    STATUS  current
    DESCRIPTION
        "This object ID shows current configuration of real server proxy IP subnet mask.
         Returns 0 when slbCurCfgEnhRealServerProxyIpMode is not set to address.
         Returns 0 if IP version is IPv6."
    ::= { slbCurCfgEnhRealServerSecondPartEntry 14 }

slbCurCfgEnhRealServerProxyIpv6Addr OBJECT-TYPE
    SYNTAX  DisplayString (SIZE(0..40))
    MAX-ACCESS  read-only
    STATUS  current
    DESCRIPTION
        "This object ID shows current configuration of real server proxy IPv6 address .
         The IP version for addr must be the same as the real server IP version.
         Returns 0 when slbCurCfgEnhRealServerProxyIpMode is not set to address.
         Returns 0 if IP version is IPv4.
         When a subnet is configured, user has the ability to select PIP persistency mode.
         Persistency is relevant only if the PIP is configured as subnet. If PIP is not configured or
         not subnet, the persistency configuration value is disable."
    ::= { slbCurCfgEnhRealServerSecondPartEntry 15 }

slbCurCfgEnhRealServerProxyIpv6Prefix OBJECT-TYPE
    SYNTAX  INTEGER (1..128)
    MAX-ACCESS  read-only
    STATUS  current
    DESCRIPTION
        "This object ID allows configuration of real server proxy IPv6 Mask.
         The IP version for addr must be the same as the real server IP version.
         Returns 0 when slbCurCfgEnhRealServerProxyIpMode is not set to address.
         Returns 0 if IP version is IPv6.
         When a subnet is configured user has the ability to select PIP persistency mode.
         Persistency is relevant only if the PIP is configured as subnet. If PIP is not configured or
         not subnet, the persistency configuration value is disable."
    ::= { slbCurCfgEnhRealServerSecondPartEntry 16 }

slbCurCfgEnhRealServerProxyIpPersistency OBJECT-TYPE
    SYNTAX INTEGER {
        disable(0),
        client(1),
        host(2),
        unsupported(2147483647)
    }
    MAX-ACCESS  read-only
    STATUS  current
    DESCRIPTION
        "This object ID shows current configuration of real server proxy IP persistency mode.
         Persistency is relevant only if a PIP class is configured. If PIP is not configured the
         persistency configuration is disable."
    ::= { slbCurCfgEnhRealServerSecondPartEntry 17 }

slbCurCfgEnhRealServerProxyIpNWclass OBJECT-TYPE
    SYNTAX  DisplayString  (SIZE(0..32))
    MAX-ACCESS  read-only
    STATUS  current
    DESCRIPTION
        "This  object ID allows configuration of real server proxy IP IPv4 or IPv6 Network Class as PIP.
        Network Class PIP Persistency is relevant only if a PIP class is configured. If PIP is not configured the
        persistency configuration is disable.
        Returns 0 when slbCurCfgEnhRealServerProxyIpMode is not set to nwclss(3)."
        ::= { slbCurCfgEnhRealServerSecondPartEntry 18 }

slbCurCfgEnhRealServerProxyIpNWclassPersistency OBJECT-TYPE
    SYNTAX INTEGER {
        disable(0),
        client(1),
        unsupported(2147483647)
    }
    MAX-ACCESS  read-only
    STATUS  current
    DESCRIPTION
        "This object ID allows configuration of real server Network Class PIP persistency mode.
         Persistency is relevant only if a PIP class is configured. If PIP is not configured the
         persistency configuration is disable.
         Returns 0 when slbCurCfgEnhRealServerProxyIpMode is not set to nwclss(3)."
    ::= { slbCurCfgEnhRealServerSecondPartEntry 19 }

slbCurCfgEnhRealServerIngvlan OBJECT-TYPE
    SYNTAX  INTEGER (0..4090)
    MAX-ACCESS  read-only
    STATUS  current
    DESCRIPTION
        "The ingress VLAN to be associated with the IDS server."
    ::= { slbCurCfgEnhRealServerSecondPartEntry 20 }


slbCurCfgEnhRealServerThirdPartTable OBJECT-TYPE
    SYNTAX SEQUENCE OF SlbCurCfgEnhRealServerThirdPartEntry
    MAX-ACCESS not-accessible
    STATUS current
    DESCRIPTION
        "The second table of Real Server configuration in the current_config.
         Note:This mib is not supported on VX instance of Virtualization."
    ::= { realServerCfg 17 }

slbCurCfgEnhRealServerThirdPartEntry OBJECT-TYPE
    SYNTAX SlbCurCfgEnhRealServerThirdPartEntry
    MAX-ACCESS not-accessible
    STATUS current
    DESCRIPTION
        "Information about a particular Real Server configuration."
    INDEX { slbCurCfgEnhRealServerThirdPartIndex }
    ::= { slbCurCfgEnhRealServerThirdPartTable 1 }

SlbCurCfgEnhRealServerThirdPartEntry ::= SEQUENCE {
    slbCurCfgEnhRealServerThirdPartIndex  DisplayString,
    slbCurCfgEnhRealServerOid             DisplayString,
    slbCurCfgEnhRealServerCommString      DisplayString,
    slbCurCfgEnhRealServerBackUp          DisplayString,
    slbCurCfgEnhRealServerHealthID        DisplayString,
    slbCurCfgEnhRealCriticalConnThrsh     INTEGER,
    slbCurCfgEnhRealHighConnThrsh         INTEGER,
    slbCurCfgEnhRealUploadBandWidth       INTEGER,
    slbCurCfgEnhRealDownloadBandWidth     INTEGER
}

slbCurCfgEnhRealServerThirdPartIndex OBJECT-TYPE
    SYNTAX DisplayString (SIZE(1..255))
    MAX-ACCESS  read-only
    STATUS  current
    DESCRIPTION
        "The real server number"
    ::= { slbCurCfgEnhRealServerThirdPartEntry 1 }

slbCurCfgEnhRealServerOid OBJECT-TYPE
    SYNTAX DisplayString (SIZE(0..128))
    MAX-ACCESS read-only
    STATUS current
    DESCRIPTION
        "The OID to be sent in the SNMP get request packet."
    ::= { slbCurCfgEnhRealServerThirdPartEntry 2 }

slbCurCfgEnhRealServerCommString OBJECT-TYPE
    SYNTAX DisplayString (SIZE(0..32))
    MAX-ACCESS read-only
    STATUS current
    DESCRIPTION
        "The community string to be used in the SNMP get request packet."
    ::= { slbCurCfgEnhRealServerThirdPartEntry 3 }

slbCurCfgEnhRealServerBackUp OBJECT-TYPE
    SYNTAX DisplayString (SIZE(1..255))
    MAX-ACCESS  read-only
    STATUS  current
    DESCRIPTION
        "The backup server number for this server."
    ::= { slbCurCfgEnhRealServerThirdPartEntry 4 }

slbCurCfgEnhRealServerHealthID OBJECT-TYPE
    SYNTAX DisplayString (SIZE(0..32))
    MAX-ACCESS read-only
    STATUS current
    DESCRIPTION
        "The Advanced HC ID."
    ::= { slbCurCfgEnhRealServerThirdPartEntry 5 }

slbCurCfgEnhRealCriticalConnThrsh OBJECT-TYPE
    SYNTAX  INTEGER (0..2000000)
    MAX-ACCESS  read-only
    STATUS  current
    DESCRIPTION
        "Critical connection threshold."
    ::= { slbCurCfgEnhRealServerThirdPartEntry 6 }

slbCurCfgEnhRealHighConnThrsh OBJECT-TYPE
    SYNTAX  INTEGER (0..2000000)
    MAX-ACCESS  read-only
    STATUS  current
    DESCRIPTION
        "High connection threshold."
    ::= { slbCurCfgEnhRealServerThirdPartEntry 7 }

slbCurCfgEnhRealUploadBandWidth OBJECT-TYPE
    SYNTAX  INTEGER (0..100000)
    MAX-ACCESS  read-only
    STATUS  current
    DESCRIPTION
        "Upload bandwidth limit for WAN Link real server in Mbps."
    ::= { slbCurCfgEnhRealServerThirdPartEntry 8 }

slbCurCfgEnhRealDownloadBandWidth OBJECT-TYPE
    SYNTAX  INTEGER (0..100000)
    MAX-ACCESS  read-only
    STATUS  current
    DESCRIPTION
        "Download bandwidth limit for WAN Link real server in Mbps."
    ::= { slbCurCfgEnhRealServerThirdPartEntry 9 }


    -- Cur Real server Proxy IP end

    -- Real Server Table - New Configuration

slbNewCfgEnhRealServerTable OBJECT-TYPE
    SYNTAX  SEQUENCE OF SlbNewCfgEnhRealServerEntry
    MAX-ACCESS  not-accessible
    STATUS  current
    DESCRIPTION
        "The table of Real Server configuration in the new_config.
         Note:This mib is not supported on VX instance of Virtualization."
    ::= { realServerCfg 11 }

slbNewCfgEnhRealServerEntry OBJECT-TYPE
    SYNTAX  SlbNewCfgEnhRealServerEntry
    MAX-ACCESS  not-accessible
    STATUS  current
    DESCRIPTION
        "Information about a particular Real Server configuration."
    INDEX   { slbNewCfgEnhRealServerIndex }
    ::= { slbNewCfgEnhRealServerTable 1 }

SlbNewCfgEnhRealServerEntry ::= SEQUENCE {
    slbNewCfgEnhRealServerIndex           DisplayString,
    slbNewCfgEnhRealServerIpAddr          IpAddress,
    slbNewCfgEnhRealServerWeight          INTEGER,
    slbNewCfgEnhRealServerMaxConns        INTEGER,
    slbNewCfgEnhRealServerTimeOut         INTEGER,
    slbNewCfgEnhRealServerPingInterval    INTEGER,
    slbNewCfgEnhRealServerFailRetry       INTEGER,
    slbNewCfgEnhRealServerSuccRetry       INTEGER,
    slbNewCfgEnhRealServerState           INTEGER,
    slbNewCfgEnhRealServerDelete          INTEGER,
    slbNewCfgEnhRealServerType            INTEGER,
    slbNewCfgEnhRealServerName            DisplayString,
    slbNewCfgEnhRealServerAddUrl          Integer32,
    slbNewCfgEnhRealServerRemUrl          Integer32,
    slbNewCfgEnhRealServerCookie          INTEGER,
    slbNewCfgEnhRealServerExcludeStr      INTEGER,
    slbNewCfgEnhRealServerSubmac          INTEGER,
    slbNewCfgEnhRealServerIdsport         Integer32,
    slbNewCfgEnhRealServerIpVer           INTEGER,
    slbNewCfgEnhRealServerIpv6Addr        DisplayString,
    slbNewCfgEnhRealServerNxtRportIdx     INTEGER,
    slbNewCfgEnhRealServerNxtBuddyIdx     INTEGER,
    slbNewCfgEnhRealServerLLBType         INTEGER,
    slbNewCfgEnhRealServerCopy            DisplayString,
    slbNewCfgEnhRealServerPortsIngress	  DisplayString,
    slbNewCfgEnhRealServerPortsEgress 	  DisplayString,
    slbNewCfgEnhRealServerAddPortsIngress INTEGER,
    slbNewCfgEnhRealServerRemPortsIngress INTEGER,
    slbNewCfgEnhRealServerAddPortsEgress  INTEGER,
    slbNewCfgEnhRealServerRemPortsEgress  INTEGER,
    slbNewCfgEnhRealServerVlanIngress	  Integer32,
    slbNewCfgEnhRealServerVlanEgress	  Integer32,
    slbNewCfgEnhRealServerEgressIf	 	  Integer32,
	slbNewCfgEnhRealServerSecType    	  INTEGER,
    slbNewCfgEnhRealServerIngressIf	 	  Integer32,
	slbNewCfgEnhRealServerSecDeviceFlag   INTEGER,
    slbNewCfgEnhRealServerIngport         Integer32
}

slbNewCfgEnhRealServerIndex OBJECT-TYPE
    SYNTAX DisplayString (SIZE(1..255))
    MAX-ACCESS  read-only
    STATUS  current
    DESCRIPTION
        "The real server number"
    ::= { slbNewCfgEnhRealServerEntry 1 }

slbNewCfgEnhRealServerIpAddr OBJECT-TYPE
    SYNTAX  IpAddress
    MAX-ACCESS  read-create
    STATUS  current
    DESCRIPTION
        "IP address of the real server identified by the instance of
         slbRealServerIndex."
    ::= { slbNewCfgEnhRealServerEntry 2 }

slbNewCfgEnhRealServerWeight OBJECT-TYPE
    SYNTAX  INTEGER (1..48)
    MAX-ACCESS  read-create
    STATUS  current
    DESCRIPTION
        "The server weight."
    ::= { slbNewCfgEnhRealServerEntry 3 }

slbNewCfgEnhRealServerMaxConns OBJECT-TYPE
    SYNTAX  INTEGER (0..1000000)
    MAX-ACCESS  read-create
    STATUS  current
    DESCRIPTION
        "The maximum number of connections that are allowed."
    ::= { slbNewCfgEnhRealServerEntry 4 }

slbNewCfgEnhRealServerTimeOut OBJECT-TYPE
    SYNTAX  INTEGER (2..32768)
    MAX-ACCESS  read-create
    STATUS  current
    DESCRIPTION
        "The maximum number of minutes an inactive connection remains open."
    ::= { slbNewCfgEnhRealServerEntry 5 }

slbNewCfgEnhRealServerPingInterval OBJECT-TYPE
    SYNTAX  INTEGER (0..600)
    MAX-ACCESS  read-create
    STATUS  current
    DESCRIPTION
        "The interval between keep-alive (ping) attempts in number of
         seconds. Zero means disabling ping attempt."
    ::= { slbNewCfgEnhRealServerEntry 6 }

slbNewCfgEnhRealServerFailRetry OBJECT-TYPE
    SYNTAX  INTEGER  (0..63)
    MAX-ACCESS  read-create
    STATUS  current
    DESCRIPTION
        "The number of failed attempts to declare this server DOWN."
    ::= { slbNewCfgEnhRealServerEntry 7 }

slbNewCfgEnhRealServerSuccRetry OBJECT-TYPE
    SYNTAX  INTEGER (0..63)
    MAX-ACCESS  read-create
    STATUS  current
    DESCRIPTION
        "The number of successful attempts to declare a server UP."
    ::= { slbNewCfgEnhRealServerEntry 8 }

slbNewCfgEnhRealServerState OBJECT-TYPE
    SYNTAX  INTEGER {
        enabled(2),
        disabled(3),
        disabled-with-fastage(4),
	shutdown-connection(5),
	shutdown-persistent-sessions(6),
        unsupported(2147483647)
    }
    MAX-ACCESS  read-create
    STATUS  current
    DESCRIPTION
        "Enable or disable the server and remove the existing sessions using disabled-with-fastage option."
    ::= { slbNewCfgEnhRealServerEntry 9 }

slbNewCfgEnhRealServerDelete OBJECT-TYPE
    SYNTAX  INTEGER {
        other(1),
        delete(2),
        unsupported(2147483647)
    }
    MAX-ACCESS  read-create
    STATUS  current
    DESCRIPTION
        "By setting the value to delete(2), the entire row is deleted."
    ::= { slbNewCfgEnhRealServerEntry 10 }

slbNewCfgEnhRealServerType OBJECT-TYPE
    SYNTAX  INTEGER {
        local-server(1),
        remote-server(2),
        unsupported(2147483647)
    }
    MAX-ACCESS  read-create
    STATUS  current
    DESCRIPTION
        "The server type.  It participates in global server load balancing
         when it is configured as remote-server."
    ::= { slbNewCfgEnhRealServerEntry 11 }

slbNewCfgEnhRealServerName OBJECT-TYPE
    SYNTAX  DisplayString (SIZE(0..255))
    MAX-ACCESS  read-create
    STATUS  current
    DESCRIPTION
        "The name of the real server."
    ::= { slbNewCfgEnhRealServerEntry 12 }


slbNewCfgEnhRealServerAddUrl OBJECT-TYPE
    SYNTAX  Integer32
    MAX-ACCESS  read-create
    STATUS  current
    DESCRIPTION
        "The URL Path (slbCurCfgUrlLbPathIndex) to be added to the
         real server. A zero is returned when read."
    ::= { slbNewCfgEnhRealServerEntry 13 }

slbNewCfgEnhRealServerRemUrl OBJECT-TYPE
    SYNTAX  Integer32
    MAX-ACCESS  read-create
    STATUS  current
    DESCRIPTION
        "The URL Path (slbCurCfgUrlLbPathIndex) to be removed from
        the real server. A zero is returned when read."
    ::= { slbNewCfgEnhRealServerEntry 14 }

slbNewCfgEnhRealServerCookie OBJECT-TYPE
    SYNTAX  INTEGER {
        enabled(1),
        disabled(2),
        unsupported(2147483647)
    }
    MAX-ACCESS  read-create
    STATUS  current
    DESCRIPTION
        "Enable or disable real server to handle client requests
         that don't contain a cookie if cookie loadbalance is enabled."
    ::= { slbNewCfgEnhRealServerEntry 15 }

slbNewCfgEnhRealServerExcludeStr OBJECT-TYPE
    SYNTAX  INTEGER {
        enabled(1),
        disabled(2),
        unsupported(2147483647)
    }
    MAX-ACCESS  read-create
    STATUS  current
    DESCRIPTION
        "Enable or disable exclusionary matching string on real server."
    ::= { slbNewCfgEnhRealServerEntry 16 }

slbNewCfgEnhRealServerSubmac OBJECT-TYPE
    SYNTAX  INTEGER {
        enabled(1),
        disabled(2),
        unsupported(2147483647)
    }
    MAX-ACCESS  read-create
    STATUS  current
    DESCRIPTION
        "The real server config to enable/disable MAC SA substitution for
         L4 traffic. If disabled (the default) we will NOT substitute the
         MAC SA of client-to-server frames.  If enabled, we will substitute
         the MAC SA."
    ::= { slbNewCfgEnhRealServerEntry 17 }

slbNewCfgEnhRealServerIdsport OBJECT-TYPE
    SYNTAX  Integer32
    MAX-ACCESS  read-create
    STATUS  current
    DESCRIPTION
        "The port to be connected to IDS server."
    ::= { slbNewCfgEnhRealServerEntry 18 }

slbNewCfgEnhRealServerIpVer OBJECT-TYPE
    SYNTAX  INTEGER{
        ipv4(1),
        ipv6(2),
        unsupported(2147483647)
    }
    MAX-ACCESS  read-create
    STATUS  current
    DESCRIPTION
        "The type of IP address."
    ::= { slbNewCfgEnhRealServerEntry 19 }

slbNewCfgEnhRealServerIpv6Addr OBJECT-TYPE
    SYNTAX DisplayString (SIZE(0..40))
    MAX-ACCESS  read-create
    STATUS  current
    DESCRIPTION
        "  IPV6 address of the real server identified by the instance of the slbRealServerIndex.
        Address should be 4-byte hexadecimal colon notation. Valid IPv6 address should be in
        any of the following forms xxxx:xxxx:xxxx:xxxx:xxxx:xxxx:xxxx:xxxx or xxxx::xxxx:xxxx:xxxx:xxxx or ::xxxx "
    ::= { slbNewCfgEnhRealServerEntry 20 }

slbNewCfgEnhRealServerNxtRportIdx OBJECT-TYPE
    SYNTAX  INTEGER (0..64)
    MAX-ACCESS  read-only
    STATUS  current
    DESCRIPTION
        "The next available free slot index number, to add the real port
         to the server. Value 0 will be returned if no free slot available."
    ::= { slbNewCfgEnhRealServerEntry 21 }

slbNewCfgEnhRealServerNxtBuddyIdx OBJECT-TYPE
    SYNTAX  INTEGER (0..4)
    MAX-ACCESS  read-only
    STATUS  current
    DESCRIPTION
        "The next available free slot Buddy index number, to add the Buddy Server
         to the Real server. Value 0 will be returned if no free slot available."
    ::= { slbNewCfgEnhRealServerEntry 22 }

slbNewCfgEnhRealServerLLBType OBJECT-TYPE
    SYNTAX  INTEGER {
        local(0),
	remote(1),
	wanlink(2),
        unsupported(2147483647)
	}
    MAX-ACCESS  read-write
    STATUS  current
    DESCRIPTION
        "The server type." 
    ::= { slbNewCfgEnhRealServerEntry 23 }

slbNewCfgEnhRealServerCopy OBJECT-TYPE
    SYNTAX DisplayString (SIZE(1..255))
    MAX-ACCESS  read-create
    STATUS  current
    DESCRIPTION
        "The alphanumeric index of the new copy to be created."
    ::= { slbNewCfgEnhRealServerEntry 24 }

slbNewCfgEnhRealServerPortsIngress OBJECT-TYPE
    SYNTAX DisplayString (SIZE(0..40))
    MAX-ACCESS  read-create
    STATUS  current
    DESCRIPTION
        " List of ingress ports attached to the real server (security device), used for SSL inspection WebUI wizard.
	Using the following format: xx, xx, xx"
    ::= { slbNewCfgEnhRealServerEntry 25 }

slbNewCfgEnhRealServerPortsEgress OBJECT-TYPE
    SYNTAX DisplayString (SIZE(0..40))
    MAX-ACCESS  read-create
    STATUS  current
    DESCRIPTION
        " List of egress ports attached to the real server (security device), used for SSL inspection WebUI wizard.
	Using the following format: xx, xx, xx"
    ::= { slbNewCfgEnhRealServerEntry 26 }

slbNewCfgEnhRealServerAddPortsIngress OBJECT-TYPE
    SYNTAX  INTEGER
    MAX-ACCESS  read-create
    STATUS  current
    DESCRIPTION
        "The ingress port to be added to the specified security device.
	  A '0' value is returned when read."
    ::= { slbNewCfgEnhRealServerEntry 27 }

slbNewCfgEnhRealServerRemPortsIngress OBJECT-TYPE
    SYNTAX  INTEGER
    MAX-ACCESS  read-create
    STATUS  current
    DESCRIPTION
        "The ingress port to be removed to the specified security device.
	 A zero is returned when read."
    ::= { slbNewCfgEnhRealServerEntry 28 }

slbNewCfgEnhRealServerAddPortsEgress OBJECT-TYPE
    SYNTAX  INTEGER
    MAX-ACCESS  read-create
    STATUS  current
    DESCRIPTION
        "The egress port to be added to the specified security device.
	 A zero is returned when read."
    ::= { slbNewCfgEnhRealServerEntry 29 }

slbNewCfgEnhRealServerRemPortsEgress OBJECT-TYPE
    SYNTAX  INTEGER
    MAX-ACCESS  read-create
    STATUS  current
    DESCRIPTION
        "The egress port to be removed to the specified security device.
	 A zero is returned when read."
    ::= { slbNewCfgEnhRealServerEntry 30 }

slbNewCfgEnhRealServerVlanIngress OBJECT-TYPE
    SYNTAX  Integer32
    MAX-ACCESS  read-create
    STATUS  current
    DESCRIPTION
        "The ingress Vlan specified on security device.
	 Used for SSL wizard"
    ::= { slbNewCfgEnhRealServerEntry 31 }

slbNewCfgEnhRealServerVlanEgress OBJECT-TYPE
    SYNTAX  Integer32
    MAX-ACCESS  read-create
    STATUS  current
    DESCRIPTION
        "The egress Vlan specified on security device.
	 Used for SSL wizard"
    ::= { slbNewCfgEnhRealServerEntry 32 }

slbNewCfgEnhRealServerEgressIf OBJECT-TYPE
    SYNTAX  Integer32
    MAX-ACCESS  read-create
    STATUS  current
    DESCRIPTION
        "The egress interface specified on security device.
	 Used for SSL wizard"
    ::= { slbNewCfgEnhRealServerEntry 33 }

slbNewCfgEnhRealServerSecType OBJECT-TYPE
    SYNTAX  INTEGER {
        none(1),
		virtual(2),
		layer(3),
		passive(4),
		l3sw(5),
                unsupported(2147483647)
	}
    MAX-ACCESS  read-write
    STATUS  current
    DESCRIPTION
        "The security device  type." 
    ::= { slbNewCfgEnhRealServerEntry 34 }

slbNewCfgEnhRealServerIngressIf OBJECT-TYPE
    SYNTAX  Integer32
    MAX-ACCESS  read-create
    STATUS  current
    DESCRIPTION
        "The ingress interface specified on security device.
	 Used for SSL wizard"
    ::= { slbNewCfgEnhRealServerEntry 35 }

slbNewCfgEnhRealServerSecDeviceFlag OBJECT-TYPE
	SYNTAX  INTEGER {
        none(1),
		security(2),
        unsupported(2147483647)
	} 
	MAX-ACCESS  read-only
    STATUS  current
    DESCRIPTION
        "The Real security device flag."
    ::= { slbNewCfgEnhRealServerEntry 36 }

slbNewCfgEnhRealServerIngport OBJECT-TYPE
    SYNTAX  Integer32
    MAX-ACCESS  read-create
    STATUS  current
    DESCRIPTION
        "The ingress port to be connected to IDS server."
    ::= { slbNewCfgEnhRealServerEntry 37 }


slbNewCfgEnhRealServerSecondPartTable OBJECT-TYPE
    SYNTAX SEQUENCE OF SlbNewCfgEnhRealServerSecondPartEntry
    MAX-ACCESS not-accessible
    STATUS current
    DESCRIPTION
        "The second table of Real Server configuration in the current_config.
         Note:This mib is not supported on VX instance of Virtualization."
    ::= { realServerCfg 18 }

slbNewCfgEnhRealServerSecondPartEntry OBJECT-TYPE
    SYNTAX SlbNewCfgEnhRealServerSecondPartEntry
    MAX-ACCESS not-accessible
    STATUS current
    DESCRIPTION
        "Information about a particular Real Server configuration.
         Note:This mib is not supported for VX instance of Virtualization."
    INDEX { slbNewCfgEnhRealServerSecondPartIndex }
    ::= { slbNewCfgEnhRealServerSecondPartTable 1 }

SlbNewCfgEnhRealServerSecondPartEntry ::= SEQUENCE {
    slbNewCfgEnhRealServerSecondPartIndex DisplayString,
    slbNewCfgEnhRealServerUrlBmap         OCTET STRING,
    slbNewCfgEnhRealServerProxy           INTEGER,
    slbNewCfgEnhRealServerLdapwr          INTEGER,
    slbNewCfgEnhRealServerIdsvlan         INTEGER,
    slbNewCfgEnhRealServerAvail           INTEGER,
    slbNewCfgEnhRealServerFastHealthCheck INTEGER,
    slbNewCfgEnhRealServerSubdmac         INTEGER,
    slbNewCfgEnhRealServerOverflow        INTEGER,
    slbNewCfgEnhRealServerBkpPreempt      INTEGER,
    slbNewCfgEnhRealServerMode            INTEGER,
    slbNewCfgEnhUpdateAllRealServers      INTEGER,
    slbNewCfgEnhRealServerProxyIpMode     INTEGER,
    slbNewCfgEnhRealServerProxyIpAddr     IpAddress,
    slbNewCfgEnhRealServerProxyIpMask     IpAddress,
    slbNewCfgEnhRealServerProxyIpv6Addr   DisplayString,
    slbNewCfgEnhRealServerProxyIpv6Prefix INTEGER,
    slbNewCfgEnhRealServerProxyIpPersistency   INTEGER,
    slbNewCfgEnhRealServerProxyIpNWclass  DisplayString,
    slbNewCfgEnhRealServerProxyIpNWclassPersistency   INTEGER,
    slbNewCfgEnhRealServerIngvlan         INTEGER
}

slbNewCfgEnhRealServerSecondPartIndex OBJECT-TYPE
    SYNTAX DisplayString (SIZE(1..255))
    MAX-ACCESS  read-only
    STATUS  current
    DESCRIPTION
        "The real server number"
    ::= { slbNewCfgEnhRealServerSecondPartEntry 1 }

slbNewCfgEnhRealServerUrlBmap OBJECT-TYPE
    SYNTAX  OCTET STRING
    MAX-ACCESS  read-only
    STATUS  current
    DESCRIPTION
        "The URL Paths selected for URL load balancing for by the
         real server.  The selected URL Paths are presented in
         a bitmap format.

         in receiving order:

         OCTET 1  OCTET 2  .....
         xxxxxxxx xxxxxxxx .....
         ||    || |_ URL Path 9
         ||    ||
         ||    ||___ URL Path 8
         ||    |____ URL Path 7
         ||      .    .   .
         ||_________ URL Path 2
         |__________ URL Path 1

         where x : 1 - The represented URL Path is selected
         0 - The represented URL Path is not selected"
    ::= { slbNewCfgEnhRealServerSecondPartEntry 2 }

slbNewCfgEnhRealServerProxy OBJECT-TYPE
    SYNTAX  INTEGER {
        enabled(1),
        disabled(2),
        unsupported(2147483647)
    }
    MAX-ACCESS  read-create
    STATUS  current
    DESCRIPTION
        "The real server config to enable/disable client proxy operation."
    ::= { slbNewCfgEnhRealServerSecondPartEntry 3 }

slbNewCfgEnhRealServerLdapwr OBJECT-TYPE
    SYNTAX  INTEGER {
        enabled(1),
        disabled(2),
        unsupported(2147483647)
    }
    MAX-ACCESS  read-create
    STATUS  current
    DESCRIPTION
        "The real server config to enable/disable LDAP write server."
::= { slbNewCfgEnhRealServerSecondPartEntry 4 }

slbNewCfgEnhRealServerIdsvlan OBJECT-TYPE
    SYNTAX  INTEGER (0..4090)
    MAX-ACCESS  read-create
    STATUS  current
    DESCRIPTION
        "The VLAN to be associated with IDS server."
    ::= { slbNewCfgEnhRealServerSecondPartEntry 5 }


slbNewCfgEnhRealServerAvail OBJECT-TYPE
    SYNTAX  INTEGER (1..48)
    MAX-ACCESS  read-create
    STATUS  current
    DESCRIPTION
        "The remote real server Global SLB availability."
    ::= { slbNewCfgEnhRealServerSecondPartEntry 6 }

slbNewCfgEnhRealServerFastHealthCheck OBJECT-TYPE
    SYNTAX  INTEGER {
        enabled(1),
        disabled(2),
        unsupported(2147483647)
    }
    MAX-ACCESS  read-create
    STATUS  current
    DESCRIPTION
        "The real server config to enable/disable Fast Health Check Operation."
    ::= { slbNewCfgEnhRealServerSecondPartEntry 7 }

slbNewCfgEnhRealServerSubdmac OBJECT-TYPE
    SYNTAX  INTEGER {
        enabled(1),
        disabled(2),
        unsupported(2147483647)
    }
    MAX-ACCESS  read-create
    STATUS  current
    DESCRIPTION
        "The real server config to enable/disable MAC DA substitution for
        L4 traffic. If disabled, we will NOT substitute the MAC DA of
        client-to-server frames.  If enabled(default), we will substitute
        the MAC DA."
    ::= { slbNewCfgEnhRealServerSecondPartEntry 8 }

slbNewCfgEnhRealServerOverflow OBJECT-TYPE
    SYNTAX  INTEGER {
        enabled(1),
        disabled(2),
        unsupported(2147483647)
    }
    MAX-ACCESS  read-create
    STATUS  current
    DESCRIPTION
        "The real server config to enable/disable Overflow. If enabled(default)
         allows Backup server to kick in if real server reaches maximum
         connections."
    ::= { slbNewCfgEnhRealServerSecondPartEntry 9 }

slbNewCfgEnhRealServerBkpPreempt OBJECT-TYPE
    SYNTAX  INTEGER {
        enabled(1),
        disabled(2),
        unsupported(2147483647)
    }
    MAX-ACCESS  read-create
    STATUS  current
    DESCRIPTION
        "The real server config to enable/disable backup preemption. If enabled
        (default)allows to preempt the backup server when the primary server
        comes up. If disabled the backup server will continue to serve the
        traffic even when primary server comes up."
    ::= { slbNewCfgEnhRealServerSecondPartEntry 10 }

slbNewCfgEnhRealServerMode OBJECT-TYPE
    SYNTAX  INTEGER {
        physical(1),
        logical(2),
        unsupported(2147483647)
    }
    MAX-ACCESS  read-create
    STATUS  current
    DESCRIPTION
        "Set the mode of the real server. By default the mode is set to physical."
    ::= { slbNewCfgEnhRealServerSecondPartEntry 11 }

slbNewCfgEnhUpdateAllRealServers OBJECT-TYPE
    SYNTAX  INTEGER {
        none(0),
        mode(1),
        maxcon(2),
        weight(3),
        all(4),
        unsupported(2147483647)
    }
    MAX-ACCESS  read-create
    STATUS  current
    DESCRIPTION
        "Set all the real servers having the same RIP address as this real server
        with the mode and/or maximum connection value (if mode is physical) that is
        set in this real server. When read, none(0) is returned.
        mode   - set only the mode to all real servers with same RIP address.
        maxcon - set only the max connections to all real servers with same RIP address.
        weight - set only the weight to all real servers with same RIP address.
        all    - set mode, max connections and weight to all real servers with same RIP address."
    ::= { slbNewCfgEnhRealServerSecondPartEntry 12 }

-- Real server Proxy IP start
slbNewCfgEnhRealServerProxyIpMode OBJECT-TYPE
    SYNTAX INTEGER {
        enable(0),
        address(2),
        nwclss(3),
        disable(4),
        unsupported(2147483647) 
    }
    MAX-ACCESS  read-create
    STATUS  current
    DESCRIPTION
        "Set the real server Proxy IP mode.
         Changing from address(2) to any other mode will clear the configured IPv4/IPv6 address,prefix and persistancy.
         Changing from  nwclass(3) to any other mode will clear the configured NWclass and NWpersistancy."
    ::= { slbNewCfgEnhRealServerSecondPartEntry 13 }

slbNewCfgEnhRealServerProxyIpAddr OBJECT-TYPE
    SYNTAX  IpAddress
    MAX-ACCESS  read-create
    STATUS  current
    DESCRIPTION
        "This object ID allows configuration of real server proxy IP v4 address .
        The IP version for addr must be the same as the real server IP version.
        This object ID can be set only if slbNewCfgEnhRealServerIpVer is set to ipv4 &
        slbNewCfgEnhRealServerProxyIpMode is address else return failure.
        Returns 0 if IP version is IPv6 or slbNewCfgEnhRealServerProxyIpMode is not set to address.
        When a subnet is configured, user has the ability to select PIP persistency mode.
        Persistency is relevant only if the PIP is configured as subnet. If PIP is not configured or
        not subnet, the persistency configuration value is disable."
    ::= { slbNewCfgEnhRealServerSecondPartEntry 14 }

slbNewCfgEnhRealServerProxyIpMask OBJECT-TYPE
    SYNTAX  IpAddress
    MAX-ACCESS  read-create
    STATUS  current
    DESCRIPTION
        "This object ID allows configuration of real server proxy IP Mask.
        The IP version for addr must be the same as the real server IP version.
        This object ID can be set only if slbNewCfgEnhRealServerIpVer is set to ipv4
        & slbNewCfgEnhRealServerProxyIpMode is address else return failure.
        Returns 0 if IP version is IPv6 or slbNewCfgEnhRealServerProxyIpMode is not set to address.
        When a subnet is configured user has the ability to select PIP persistency mode.
        Persistency is relevant only if the PIP is configured as subnet. If PIP is not configured or
        not subnet, the persistency configuration value is disable."
    ::= { slbNewCfgEnhRealServerSecondPartEntry 15 }

slbNewCfgEnhRealServerProxyIpv6Addr OBJECT-TYPE
    SYNTAX  DisplayString (SIZE(0..40))
    MAX-ACCESS  read-create
    STATUS  current
    DESCRIPTION
        "This object ID allows configuration of real server proxy IPv6 address .
         The IP version for addr must be the same as the real server IP version.
         Returns emply if IP version is IPv4 or slbNewCfgEnhRealServerProxyIpMode is not set to address.
         This object ID can be set only if slbNewCfgEnhRealServerIpVer is set to ipv6
         & slbNewCfgEnhRealServerProxyIpMode is address else return failure.
         When a subnet is configured, user has the ability to select PIP persistency mode.
         Persistency is relevant only if the PIP is configured as subnet. If PIP is not configured or
         not subnet, the persistency configuration value is disable.
         Address should be 4-byte hexadecimal colon notation.
         Valid IPv6 address should be in any of the following forms
         xxxx:xxxx:xxxx:xxxx:xxxx:xxxx:xxxx:xxxx or
         xxxx::xxxx:xxxx:xxxx:xxxx or ::xxxx."
    ::= { slbNewCfgEnhRealServerSecondPartEntry 16 }

slbNewCfgEnhRealServerProxyIpv6Prefix OBJECT-TYPE
    SYNTAX  INTEGER (1..128)
    MAX-ACCESS  read-create
    STATUS  current
    DESCRIPTION
        "This object ID allows configuration of real server proxy IPv6 Mask.
         The IP version for addr must be the same as the real server IP version.
         This object ID can be set only if slbNewCfgEnhRealServerIpVer is set to ipv6
         & slbNewCfgEnhRealServerProxyIpMode is address else return failure.
         Returns 0 if IP version is IPv4 or slbNewCfgEnhRealServerProxyIpMode is set other than address.
         When a subnet is configured user has the ability to select PIP persistency mode.
         Persistency is relevant only if the PIP is configured as subnet. If PIP is not configured or
         not subnet, the persistency configuration value is disable."
    ::= { slbNewCfgEnhRealServerSecondPartEntry 17 }

slbNewCfgEnhRealServerProxyIpPersistency OBJECT-TYPE
    SYNTAX INTEGER {
        disable(0),
        client(1),
        host(2),
        unsupported(2147483647)
    }
    MAX-ACCESS  read-create
    STATUS  current
    DESCRIPTION
        "When a subnet is configured user has the ability to select PIP persistency mode.
         This object ID can be set only if slbNewCfgEnhRealServerProxyIpMode is address else return failure.
         Persistency is relevant only if a PIP class is configured. If PIP is not configured the
         persistency configuration is disable."
    ::= { slbNewCfgEnhRealServerSecondPartEntry 18 }

slbNewCfgEnhRealServerProxyIpNWclass OBJECT-TYPE
    SYNTAX  DisplayString  (SIZE(0..32))
    MAX-ACCESS  read-create
    STATUS  current
    DESCRIPTION
        "This  object ID allows configuration of real server proxy IP IPv4 or IPv6 Network Class as PIP.
        This object ID can be set only if slbNewCfgEnhRealServerProxyIpMode is nwclss else return failure.
        Persistency is relevant only if a PIP class is configured. If PIP is not configured the
        persistency configuration is disable.
        Returns empty string when slbNewCfgEnhRealServerProxyIpMode is not set to nwclss(3)."
    ::= { slbNewCfgEnhRealServerSecondPartEntry 19 }

slbNewCfgEnhRealServerProxyIpNWclassPersistency OBJECT-TYPE
    SYNTAX INTEGER {
        disable(0),
            client(1),
        unsupported(2147483647)
    }
    MAX-ACCESS  read-create
    STATUS  current
    DESCRIPTION
        "This object ID allows configuration of real server Network Class PIP persistency mode.
        This object ID can be set only if slbNewCfgEnhRealServerProxyIpMode is nwclss else return failure.
        Persistency is relevant only if a PIP class is configured. If PIP is not configured the
        persistency configuration is disable.
        Returns 0 when slbNewCfgEnhRealServerProxyIpMode is not set to nwclss(3)."
    ::= { slbNewCfgEnhRealServerSecondPartEntry 20 }

slbNewCfgEnhRealServerIngvlan OBJECT-TYPE
    SYNTAX  INTEGER (0..4090)
    MAX-ACCESS  read-create
    STATUS  current
    DESCRIPTION
        "The ingress VLAN to be associated with IDS server."
    ::= { slbNewCfgEnhRealServerSecondPartEntry 21 }


slbNewCfgEnhRealServerThirdPartTable OBJECT-TYPE
    SYNTAX SEQUENCE OF SlbNewCfgEnhRealServerThirdPartEntry
    MAX-ACCESS not-accessible
    STATUS current
    DESCRIPTION
        "The Third table of Real Server configuration in the new_config.
         Note:This mib is not supported for VX instance of Virtualization."
    ::= { realServerCfg 19 }

slbNewCfgEnhRealServerThirdPartEntry OBJECT-TYPE
    SYNTAX SlbNewCfgEnhRealServerThirdPartEntry
    MAX-ACCESS not-accessible
    STATUS current
    DESCRIPTION
        "Information about a particular Real Server configuration.
         Note:This mib is not supported for VX instance of Virtualization."
    INDEX { slbNewCfgEnhRealServerThirdPartIndex }
    ::= { slbNewCfgEnhRealServerThirdPartTable 1 }

SlbNewCfgEnhRealServerThirdPartEntry ::= SEQUENCE {
    slbNewCfgEnhRealServerThirdPartIndex DisplayString,
    slbNewCfgEnhRealServerOid             DisplayString,
    slbNewCfgEnhRealServerCommString      DisplayString,
    slbNewCfgEnhRealServerBackUp          DisplayString,
    slbNewCfgEnhRealServerHealthID        DisplayString,
    slbNewCfgEnhRealCriticalConnThrsh     INTEGER,
    slbNewCfgEnhRealHighConnThrsh         INTEGER,
    slbNewCfgEnhRealUploadBandWidth       INTEGER,
    slbNewCfgEnhRealDownloadBandWidth     INTEGER
}

slbNewCfgEnhRealServerThirdPartIndex OBJECT-TYPE
    SYNTAX DisplayString (SIZE(1..255))
    MAX-ACCESS  read-only
    STATUS  current
    DESCRIPTION
        "The real server number"
    ::= { slbNewCfgEnhRealServerThirdPartEntry 1 }

slbNewCfgEnhRealServerOid OBJECT-TYPE
    SYNTAX DisplayString (SIZE(0..128))
    MAX-ACCESS read-create
    STATUS current
    DESCRIPTION
        "The OID to be sent in the SNMP get request packet."
    ::= { slbNewCfgEnhRealServerThirdPartEntry 2 }

slbNewCfgEnhRealServerCommString OBJECT-TYPE
    SYNTAX DisplayString (SIZE(0..32))
    MAX-ACCESS read-create
    STATUS current
    DESCRIPTION
        "The community string to be used in the SNMP get request packet."
    ::= { slbNewCfgEnhRealServerThirdPartEntry 3 }

slbNewCfgEnhRealServerBackUp OBJECT-TYPE
    SYNTAX DisplayString (SIZE(0..255))
    MAX-ACCESS  read-create
    STATUS  current
    DESCRIPTION
        "The backup server number for this server."
    ::= { slbNewCfgEnhRealServerThirdPartEntry 4 }

slbNewCfgEnhRealServerHealthID OBJECT-TYPE
    SYNTAX DisplayString (SIZE(0..128))
    MAX-ACCESS read-write
    STATUS current
    DESCRIPTION
        "The Advanced HC ID."
    ::= { slbNewCfgEnhRealServerThirdPartEntry 5 }

slbNewCfgEnhRealCriticalConnThrsh OBJECT-TYPE
    SYNTAX  INTEGER (0..2000000)
    MAX-ACCESS  read-create
    STATUS  current
    DESCRIPTION
        "Critical connection threshold."
    ::= { slbNewCfgEnhRealServerThirdPartEntry 6 }

slbNewCfgEnhRealHighConnThrsh OBJECT-TYPE
    SYNTAX  INTEGER (0..2000000)
    MAX-ACCESS  read-create
    STATUS  current
    DESCRIPTION
        "High connection threshold."
    ::= { slbNewCfgEnhRealServerThirdPartEntry 7 }

slbNewCfgEnhRealUploadBandWidth OBJECT-TYPE
    SYNTAX  INTEGER (0..100000)
    MAX-ACCESS  read-create
    STATUS  current
    DESCRIPTION
        "Upload bandwidth limit for WAN Link real server in Mbps."
    ::= { slbNewCfgEnhRealServerThirdPartEntry 8 }

slbNewCfgEnhRealDownloadBandWidth OBJECT-TYPE
    SYNTAX  INTEGER (0..100000)
    MAX-ACCESS  read-create
    STATUS  current
    DESCRIPTION
        "Download bandwidth limit for WAN Link real server in Mbps."
    ::= { slbNewCfgEnhRealServerThirdPartEntry 9 }

-- Real Server Multiple Port Table

slbCurCfgEnhRealServPortTable OBJECT-TYPE
    SYNTAX  SEQUENCE OF SlbCurCfgEnhRealServPortEntry
    MAX-ACCESS  not-accessible
    STATUS  current
    DESCRIPTION
        "The table of real server service ports.
         Note:This mib is not supported on VX instance of Virtualization."
    ::= { realServerCfg 12 }

slbCurCfgEnhRealServPortEntry OBJECT-TYPE
    SYNTAX  SlbCurCfgEnhRealServPortEntry
    MAX-ACCESS  not-accessible
    STATUS  current
    DESCRIPTION
        "A row in the real server service ports table."
    INDEX   { slbCurCfgEnhRealServIndex, slbCurCfgEnhRealServPortIndex }
    ::= { slbCurCfgEnhRealServPortTable 1 }

SlbCurCfgEnhRealServPortEntry ::= SEQUENCE {
    slbCurCfgEnhRealServIndex         DisplayString,
    slbCurCfgEnhRealServPortIndex     Integer32,
    slbCurCfgEnhRealServRealPort      INTEGER
}

slbCurCfgEnhRealServIndex OBJECT-TYPE
    SYNTAX  DisplayString (SIZE(1..255))
    MAX-ACCESS  read-only
    STATUS  current
    DESCRIPTION
        "The number of the real server." 
::= { slbCurCfgEnhRealServPortEntry 1 }

slbCurCfgEnhRealServPortIndex OBJECT-TYPE 
    SYNTAX  Integer32 
    MAX-ACCESS  read-only 
    STATUS  current 
    DESCRIPTION 
        "The port index. This has no external meaning" 
    ::= { slbCurCfgEnhRealServPortEntry 2 }

slbCurCfgEnhRealServRealPort OBJECT-TYPE  
    SYNTAX  INTEGER (5..65534)
    MAX-ACCESS  read-only  
    STATUS  current  
    DESCRIPTION 
        "The layer4 real service port number."  
    ::= { slbCurCfgEnhRealServPortEntry 3 } 

slbNewCfgEnhRealServPortTable OBJECT-TYPE
    SYNTAX  SEQUENCE OF SlbNewCfgEnhRealServPortEntry
    MAX-ACCESS  not-accessible
    STATUS  current
    DESCRIPTION
        "The table of real server service ports.
         Note:This mib is not supported on VX instance of Virtualization."
    ::= { realServerCfg 13 }

slbNewCfgEnhRealServPortEntry OBJECT-TYPE
    SYNTAX  SlbNewCfgEnhRealServPortEntry
    MAX-ACCESS  not-accessible
    STATUS  current
    DESCRIPTION
        "A row in the real server service ports table."
    INDEX   { slbNewCfgEnhRealServIndex, slbNewCfgEnhRealServPortIndex }
    ::= { slbNewCfgEnhRealServPortTable 1 }

    SlbNewCfgEnhRealServPortEntry ::= SEQUENCE {
        slbNewCfgEnhRealServIndex           DisplayString,
        slbNewCfgEnhRealServPortIndex       Integer32,
        slbNewCfgEnhRealServRealPort        INTEGER,
        slbNewCfgEnhRealServPortDelete      INTEGER,
        slbNewCfgEnhRealServRealPortFreeIdx INTEGER
    }

slbNewCfgEnhRealServIndex OBJECT-TYPE
    SYNTAX  DisplayString (SIZE(1..255))
    MAX-ACCESS  read-only
    STATUS  current
    DESCRIPTION
        "The number of the real server." 
    ::= { slbNewCfgEnhRealServPortEntry 1 }

slbNewCfgEnhRealServPortIndex OBJECT-TYPE 
    SYNTAX  Integer32 
    MAX-ACCESS  read-only 
    STATUS  current 
    DESCRIPTION 
        "The port index. This has no external meaning" 
::= { slbNewCfgEnhRealServPortEntry 2 }

slbNewCfgEnhRealServRealPort OBJECT-TYPE  
    SYNTAX  INTEGER (5..65534)
    MAX-ACCESS  read-create  
    STATUS  current  
    DESCRIPTION 
        "The layer4 real service port number."  
    ::= { slbNewCfgEnhRealServPortEntry 3 } 

slbNewCfgEnhRealServPortDelete OBJECT-TYPE
    SYNTAX  INTEGER {
        other(1),
        delete(2)
    }
    MAX-ACCESS  read-create
    STATUS  current
    DESCRIPTION
        "When set to the value of 2 (delete), the entire row is deleted. 
        When read, other(1) is returned. Setting the value to anything 
        other than 2(delete) has no effect on the state of the row."
    ::= { slbNewCfgEnhRealServPortEntry 4 }

slbNewCfgEnhRealServRealPortFreeIdx OBJECT-TYPE
    SYNTAX  INTEGER(0..64)
    MAX-ACCESS  read-only
    STATUS  current
    DESCRIPTION
        "The first free port index number of the real server.
        Value 0 will be returned when all 64 ports are 
        configured for a real server."
    ::= { slbNewCfgEnhRealServPortEntry 5 }

slbCurCfgEnhBuddyTable OBJECT-TYPE
    SYNTAX  SEQUENCE OF SlbCurCfgEnhBuddyEntry
    MAX-ACCESS  not-accessible
    STATUS  current
    DESCRIPTION
        "The table of buddy information.
         Note:This mib is not supported on VX instance of Virtualization."
    ::= { realServerCfg 14 }

slbCurCfgEnhBuddyEntry OBJECT-TYPE
    SYNTAX  SlbCurCfgEnhBuddyEntry
    MAX-ACCESS  not-accessible
    STATUS  current
    DESCRIPTION
        "A row in the buddy server table."
    INDEX   { slbCurCfgEnhRealSerIndex,  slbCurCfgEnhBuddyIndex }
    ::= { slbCurCfgEnhBuddyTable 1 }

SlbCurCfgEnhBuddyEntry ::= SEQUENCE {
    slbCurCfgEnhRealSerIndex        DisplayString,
    slbCurCfgEnhBuddyIndex         Integer32,
    slbCurCfgEnhBuddyRealIndex     DisplayString, 
    slbCurCfgEnhBuddyGroupIndex    DisplayString,
    slbCurCfgEnhBuddyService       INTEGER 
}

slbCurCfgEnhRealSerIndex OBJECT-TYPE
    SYNTAX DisplayString (SIZE(1..255)) 
    MAX-ACCESS  read-only
    STATUS  current
    DESCRIPTION
        "The number of the real server."
    ::= { slbCurCfgEnhBuddyEntry 1 }

slbCurCfgEnhBuddyIndex OBJECT-TYPE
    SYNTAX  Integer32
    MAX-ACCESS  read-only
    STATUS  current
    DESCRIPTION
        "The buddy index. This has no external meaning"
    ::= { slbCurCfgEnhBuddyEntry 2 }

slbCurCfgEnhBuddyRealIndex OBJECT-TYPE
    SYNTAX  DisplayString (SIZE(0..255))
    MAX-ACCESS  read-only
    STATUS  current
    DESCRIPTION
        "The buddy server's real server number."
    ::= { slbCurCfgEnhBuddyEntry 3 }

slbCurCfgEnhBuddyGroupIndex OBJECT-TYPE
    SYNTAX  DisplayString (SIZE(0..255))
    MAX-ACCESS  read-only
    STATUS  current
    DESCRIPTION
        "The buddy server's real group number."
    ::= { slbCurCfgEnhBuddyEntry 4 }

slbCurCfgEnhBuddyService OBJECT-TYPE
    SYNTAX   INTEGER (9..65534)
    MAX-ACCESS  read-only
    STATUS  current
    DESCRIPTION
        "The buddy server's service."
    ::= { slbCurCfgEnhBuddyEntry 5 }

slbNewCfgEnhBuddyTable OBJECT-TYPE
    SYNTAX  SEQUENCE OF SlbNewCfgEnhBuddyEntry
    MAX-ACCESS  not-accessible
    STATUS  current
    DESCRIPTION
        "The table of buddy servers.
         Note:This mib is not supported on VX instance of Virtualization."
    ::= { realServerCfg 15 }

slbNewCfgEnhBuddyEntry OBJECT-TYPE
    SYNTAX  SlbNewCfgEnhBuddyEntry
    MAX-ACCESS  not-accessible
    STATUS  current
    DESCRIPTION
        "A row in the real server buddy table."
    INDEX   { slbNewCfgEnhRealSerIndex, slbNewCfgEnhBuddyIndex  }
    ::= { slbNewCfgEnhBuddyTable 1 }

SlbNewCfgEnhBuddyEntry      ::= SEQUENCE {
    slbNewCfgEnhRealSerIndex         DisplayString,
    slbNewCfgEnhBuddyIndex           Integer32,
    slbNewCfgEnhBuddyRealIndex       DisplayString,
    slbNewCfgEnhBuddyGroupIndex      DisplayString,
    slbNewCfgEnhBuddyService         INTEGER,
    slbNewCfgEnhBuddyDelete          INTEGER
    }

slbNewCfgEnhRealSerIndex OBJECT-TYPE
    SYNTAX  DisplayString (SIZE(1..255))
    MAX-ACCESS  read-only
    STATUS  current
    DESCRIPTION
        "The number of the real server."
    ::= { slbNewCfgEnhBuddyEntry 1 }

slbNewCfgEnhBuddyIndex OBJECT-TYPE
    SYNTAX  Integer32
    MAX-ACCESS  read-only
    STATUS  current
    DESCRIPTION
        "The buddy index. This has no external meaning"
    ::= { slbNewCfgEnhBuddyEntry 2 }

slbNewCfgEnhBuddyRealIndex OBJECT-TYPE
    SYNTAX  DisplayString (SIZE(0..255))
    MAX-ACCESS  read-create
    STATUS  current
    DESCRIPTION
        "The buddy server's real server number."
    ::= { slbNewCfgEnhBuddyEntry 3 }

slbNewCfgEnhBuddyGroupIndex OBJECT-TYPE
    SYNTAX  DisplayString (SIZE(0..255))
    MAX-ACCESS  read-create
    STATUS  current
    DESCRIPTION
        "The buddy server's real group number."
    ::= { slbNewCfgEnhBuddyEntry 4 }

slbNewCfgEnhBuddyService OBJECT-TYPE
    SYNTAX  INTEGER (9..65534) 
    MAX-ACCESS  read-create
    STATUS  current
    DESCRIPTION
        "The buddy server's service."
    ::= { slbNewCfgEnhBuddyEntry 5 }

slbNewCfgEnhBuddyDelete OBJECT-TYPE
    SYNTAX  INTEGER {
        other(1),
        delete(2),
        unsupported(2147483647)
    }
    MAX-ACCESS  read-create
    STATUS  current
    DESCRIPTION
        "When set to the value of 2 (delete), the entire row is deleted.
         When read, other(1) is returned. Setting the value to anything
         other than 2(delete) has no effect on the state of the row."
    ::= { slbNewCfgEnhBuddyEntry 6 }

-- Server load balancing - Group Table
slbGroupTableMaxSize OBJECT-TYPE
    SYNTAX  Integer32
    MAX-ACCESS  read-only
    STATUS  current
    DESCRIPTION
        "The maximum number of entries in SLB group tables.
         Note:This mib is not supported on VX instance of Virtualization."
    ::= { realServerGroupCfg 1 }

slbGroupMaxIdsSize OBJECT-TYPE
    SYNTAX  Integer32
    MAX-ACCESS  read-only
    STATUS  current
    DESCRIPTION
        "The maximum number of groups IDS can be enabled on.
         Note:This mib is not supported on VX instance of Virtualization."
    ::= { realServerGroupCfg 2 }

slbCurCfgGroupTable OBJECT-TYPE
    SYNTAX  SEQUENCE OF SlbCurCfgGroupEntry
    MAX-ACCESS  not-accessible
    STATUS  current
    DESCRIPTION
        "The table of groups,
         Note:This mib is not supported on VX instance of Virtualization."
    ::= { realServerGroupCfg 3 }

slbCurCfgGroupEntry OBJECT-TYPE
    SYNTAX  SlbCurCfgGroupEntry
    MAX-ACCESS  not-accessible
    STATUS  current
    DESCRIPTION
        "A row in the slbCurCfgGroupTable "
    INDEX   { slbCurCfgGroupIndex }
    ::= { slbCurCfgGroupTable 1 }

SlbCurCfgGroupEntry ::= SEQUENCE {
    slbCurCfgGroupIndex              Integer32,
    slbCurCfgGroupRealServers        OCTET STRING,
    slbCurCfgGroupMetric             INTEGER,
    slbCurCfgGroupBackupServer       Integer32,
    slbCurCfgGroupBackupGroup        Integer32,
    slbCurCfgGroupHealthCheckUrl     DisplayString,
    slbCurCfgGroupHealthCheckLayer   INTEGER,
    slbCurCfgGroupRealThreshold      INTEGER,
    slbCurCfgGroupVipHealthCheck     INTEGER,
    slbCurCfgGroupIdsState           INTEGER,
    slbCurCfgGroupIdsPort            INTEGER,
    slbCurCfgGroupIdsFlood           INTEGER,
    slbCurCfgGroupMinmissHash        INTEGER,
    slbCurCfgGroupPhashMask          IpAddress,
    slbCurCfgGroupRmetric            INTEGER,
    slbCurCfgGroupHealthCheckFormula DisplayString,
    slbCurCfgGroupWlm                Integer32,
    slbCurCfgGroupRadiusAuthenString DisplayString,
    slbCurCfgGroupOperatorAccess     INTEGER,
    slbCurCfgGroupSecBackupGroup     Integer32,
    slbCurCfgGroupSlowstart          Integer32,
    slbCurCfgGroupMinThreshold       Integer32,
    slbCurCfgGroupMaxThreshold       Integer32,

    slbCurCfgGroupName               DisplayString,
    slbCurCfgGroupIpVer              INTEGER,
    slbCurCfgGroupBackup             DisplayString,
    slbCurCfgGroupHealthID           DisplayString,
    slbCurCfgGroupPhashPrefixLength  INTEGER,
    slbCurCfgGroupIdsChain           INTEGER,
    slbCurCfgGroupMaxConEx           INTEGER
    }

slbCurCfgGroupIndex OBJECT-TYPE
    SYNTAX  Integer32
    MAX-ACCESS  read-only
    STATUS  current
    DESCRIPTION
        "The group number for which the information pertains."
    ::= { slbCurCfgGroupEntry 1 }

slbCurCfgGroupRealServers    OBJECT-TYPE
    SYNTAX  OCTET STRING
    MAX-ACCESS  read-only
    STATUS  current
    DESCRIPTION
        "The Real servers in the group. The servers are presented in 
         bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbCurCfgGroupEntry 2 }

slbCurCfgGroupMetric OBJECT-TYPE
    SYNTAX  INTEGER {
	roundRobin(1),
	leastConnections(2),
	minMisses(3),
	hash(4),
	response(5),
	bandwidth(6),
        phash(7),
        svcLeast(8),
        unsupported(2147483647)
	}
    MAX-ACCESS  read-only
    STATUS  current
    DESCRIPTION
        "The metric used to select next server in group."
    ::= { slbCurCfgGroupEntry 3 }

slbCurCfgGroupBackupServer OBJECT-TYPE
    SYNTAX Integer32
    MAX-ACCESS  read-only
    STATUS  current
    DESCRIPTION
        "The backup real server for this group."
    ::= { slbCurCfgGroupEntry 4 }

slbCurCfgGroupBackupGroup OBJECT-TYPE
    SYNTAX  Integer32
    MAX-ACCESS  read-only
    STATUS  current
    DESCRIPTION
        "The backup real server group for this group."
    ::= { slbCurCfgGroupEntry 5 }

slbCurCfgGroupHealthCheckUrl OBJECT-TYPE
    SYNTAX  DisplayString (SIZE(0..127))
    MAX-ACCESS  read-only
    STATUS  current
    DESCRIPTION
        "The specific content which is examined during health checks.
         The content depends on the type of health check."
    ::= { slbCurCfgGroupEntry 6 }

slbCurCfgGroupHealthCheckLayer OBJECT-TYPE
    SYNTAX  INTEGER {
		icmp(1),
		tcp(2),
		http(3),
		httphead(44),
		dns(4),
		smtp(5),
		pop3(6),
		nntp(7),
		ftp(8),
		imap(9),
		radius(10),
		sslh(11),
		script1(12),
		script2(13),
		script3(14),
		script4(15),
		script5(16),
		script6(17),
		script7(18),
		script8(19),
		script9(20),
		script10(21),
		script11(22),
		script12(23),
		script13(24),
		script14(25),
		script15(26),
		script16(27),
		link(28),
		wsp(29),
		wtls(30),
		ldap(31),
		udpdns(32),
		arp(33),
		snmp1(34),
		snmp2(35),
		snmp3(36),
		snmp4(37),
		snmp5(38),
		radiusacs(39),
		tftp(40),
		wtp(41),
		rtsp(42),
		sipping(43),
		sipoptions(45),
		wts(46),
		dhcp(47),
		radiusaa(48),
		sslv3(49),
		script17(116),
		script18(117),
		script19(118),
		script20(119),
		script21(120),
		script22(121),
		script23(122),
		script24(123),
		script25(124),
		script26(125),
		script27(126),
		script28(127),
		script29(128),
		script30(129),
		script31(130),
		script32(131),
		script33(132),
		script34(133),
		script35(134),
		script36(135),
		script37(136),
		script38(137),
		script39(138),
		script40(139),
		script41(140),
		script42(141),
		script43(142),
		script44(143),
		script45(144),
		script46(145),
		script47(146),
		script48(147),
		script49(148),
		script50(149),
		script51(150),
		script52(151),
		script53(152),
		script54(153),
		script55(154),
		script56(155),
		script57(156),
		script58(157),
		script59(158),
		script60(159),
		script61(160),
		script62(161),
		script63(162),
		script64(163),
		none(164),
		unknown(165),
                unsupported(2147483647)
	}
    MAX-ACCESS  read-only
    STATUS  current
    DESCRIPTION
        "The OSI layer at which servers are health checked.
		 From version 29.0.0.0 the following values are not supported:
		 snmp2-snmp5, script1-script64."
    ::= { slbCurCfgGroupEntry 7 }

slbCurCfgGroupName OBJECT-TYPE 
    SYNTAX  DisplayString (SIZE(0..255))
    MAX-ACCESS  read-only 
    STATUS  current 
    DESCRIPTION 
        "The name of the real server group."  
    ::= { slbCurCfgGroupEntry 8 }

slbCurCfgGroupRealThreshold OBJECT-TYPE 
    SYNTAX  INTEGER (0..15)
    MAX-ACCESS  read-only 
    STATUS  current 
    DESCRIPTION 
        "The minimum number of real servers available. If at any time, the 
         number reaches this minimum limit, a SYSLOG ALERT message is send to 
         to the configured syslog servers stating that the real server 
         threshold has been reached for the concerned group."  
    ::= { slbCurCfgGroupEntry 9 }

slbCurCfgGroupVipHealthCheck OBJECT-TYPE
    SYNTAX  INTEGER {
	enabled(1),
	disabled(2),
        unsupported(2147483647)
	}
    MAX-ACCESS  read-only
    STATUS  current
    DESCRIPTION
        "Enable or disable VIP health checking in DSR mode." 
    ::= { slbCurCfgGroupEntry 10 }

slbCurCfgGroupIdsState OBJECT-TYPE
    SYNTAX  INTEGER {
	enabled(1),
	disabled(2),
        unsupported(2147483647)
	}
    MAX-ACCESS  read-only
    STATUS  current
    DESCRIPTION
        "Enable or disable intrusion detection."
    ::= { slbCurCfgGroupEntry 11 }

slbCurCfgGroupIdsPort OBJECT-TYPE
    SYNTAX  INTEGER (0..65534)
    MAX-ACCESS  read-only
    STATUS  current
    DESCRIPTION
        "The intrusion detection port. A value of 1 is invalid."
    ::= { slbCurCfgGroupEntry 12 }

slbCurCfgGroupIdsFlood OBJECT-TYPE
    SYNTAX  INTEGER {
	enabled(1),
	disabled(2),
        unsupported(2147483647)
	}
    MAX-ACCESS  read-only
    STATUS  current
    DESCRIPTION
        "Enable or disable intrusion detection group flood."
    ::= { slbCurCfgGroupEntry 13 }

slbCurCfgGroupMinmissHash OBJECT-TYPE
    SYNTAX  INTEGER {
        minmiss-24(1),
        minmiss-32(2),
        unsupported(2147483647) 
        }
    MAX-ACCESS  read-only
    STATUS  current
    DESCRIPTION
        "24|32 number of ip bits used for minmisses hash in the
         current_configuration block."
    ::= { slbCurCfgGroupEntry 14 }

slbCurCfgGroupPhashMask OBJECT-TYPE
    SYNTAX  IpAddress
    MAX-ACCESS  read-only
    STATUS  current
    DESCRIPTION
        "IP address mask used by the persistent hash metric."
    ::= { slbCurCfgGroupEntry 15 }

slbCurCfgGroupRmetric OBJECT-TYPE
    SYNTAX  INTEGER {
	roundRobin(1),
	hash(2),
        leastConnections(3),
        unsupported(2147483647)
	}
    MAX-ACCESS  read-only
    STATUS  current
    DESCRIPTION
        "The metric used to select next rport in server."
    ::= { slbCurCfgGroupEntry 16 }

slbCurCfgGroupHealthCheckFormula OBJECT-TYPE
    SYNTAX  DisplayString (SIZE(0..31))
    MAX-ACCESS  read-only
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formula to mark the server group failed for the virtual server 
         if 1 and 2 FAILED or 3 and 4 FAILED is (1|2)&(3|4)
         This formula will mark the virtual server UP, if 1 or 2 and 3 or 4
         are health checked sucessfully."
    ::= { slbCurCfgGroupEntry 17 }

slbCurCfgGroupOperatorAccess OBJECT-TYPE
    SYNTAX  INTEGER {
	enabled(1),
	disabled(2),
        unsupported(2147483647)
	}
    MAX-ACCESS  read-only
    STATUS  current
    DESCRIPTION
        "Enable or disable access to this group for operator."
    ::= { slbCurCfgGroupEntry 18 }

slbCurCfgGroupWlm OBJECT-TYPE
    SYNTAX  Integer32
    MAX-ACCESS  read-only
    STATUS  current
    DESCRIPTION
        "The Workload Manager for this Group."
    ::= { slbCurCfgGroupEntry 19 }

slbCurCfgGroupRadiusAuthenString OBJECT-TYPE
    SYNTAX  DisplayString (SIZE(0..32))
    MAX-ACCESS  read-only
    STATUS  current
    DESCRIPTION
        "The group RADIUS authentication string. The string is used for
         generating encrypted authentication string while doing RADIUS
         health check for this group radius servers."
    ::= { slbCurCfgGroupEntry 20 }

slbCurCfgGroupSecBackupGroup OBJECT-TYPE
    SYNTAX  Integer32
    MAX-ACCESS  read-only
    STATUS  current
    DESCRIPTION
        "The Secondary backup real server group for this group."
    ::= { slbCurCfgGroupEntry 21 }

slbCurCfgGroupSlowstart OBJECT-TYPE
    SYNTAX  Integer32
    MAX-ACCESS  read-only
    STATUS  current
    DESCRIPTION
        "The slow-start time for this group."
    ::= { slbCurCfgGroupEntry 22 }

slbCurCfgGroupMinThreshold OBJECT-TYPE
    SYNTAX  Integer32
    MAX-ACCESS  read-only
    STATUS  current
    DESCRIPTION
        "The minimum threshold value for this group."
    ::= { slbCurCfgGroupEntry 23 }

slbCurCfgGroupMaxThreshold OBJECT-TYPE
    SYNTAX  Integer32
    MAX-ACCESS  read-only
    STATUS  current
    DESCRIPTION
        "The maximum threshold value for this group."
    ::= { slbCurCfgGroupEntry 24 }


slbCurCfgGroupIpVer OBJECT-TYPE
    SYNTAX  INTEGER{
        ipv4(1),
        ipv6(2),
        mixed(3),
        unsupported(2147483647)
        }
    MAX-ACCESS  read-only
    STATUS  current
    DESCRIPTION
        "The type of real server group IP address."
    ::= { slbCurCfgGroupEntry 25 }

slbCurCfgGroupBackup OBJECT-TYPE
    SYNTAX  DisplayString (SIZE(0..255))
    MAX-ACCESS  read-only
    STATUS  current
    DESCRIPTION
        "The backup real group or real server for this group."
    ::= { slbCurCfgGroupEntry 26 }

slbCurCfgGroupHealthID OBJECT-TYPE
    SYNTAX  DisplayString (SIZE(0..32))
    MAX-ACCESS  read-only
    STATUS  current
    DESCRIPTION
        "The Advanced HC ID."
    ::= { slbCurCfgGroupEntry 27 }

slbCurCfgGroupPhashPrefixLength OBJECT-TYPE
    SYNTAX  INTEGER (1..128)
    MAX-ACCESS  read-only
    STATUS  current
    DESCRIPTION
        "Prefix length used by the persistent hash metric."
    ::= { slbCurCfgGroupEntry 28 }

slbCurCfgGroupIdsChain OBJECT-TYPE
    SYNTAX  INTEGER {
	enabled(1),
	disabled(2),
        unsupported(2147483647)
	}
    MAX-ACCESS  read-only
    STATUS  current
    DESCRIPTION
        "Enable or disable IDS group participation in inspection chain."
    ::= { slbCurCfgGroupEntry 29 }

slbCurCfgGroupMaxConEx OBJECT-TYPE
    SYNTAX  INTEGER {
        enabled(1),
        disabled(2),
        unsupported(2147483647)
        }
    MAX-ACCESS read-only
    STATUS  current
    DESCRIPTION
        "Enable or Disable override maximum connections limit."
    ::= { slbCurCfgGroupEntry 30 }

-- Server load balancing - Group Table - New Configuration
slbNewCfgGroupTable OBJECT-TYPE
    SYNTAX  SEQUENCE OF SlbNewCfgGroupEntry
    MAX-ACCESS  not-accessible
    STATUS  current
    DESCRIPTION
        "The table of groups,
         Note:This mib is not supported on VX instance of Virtualization."
    ::= { realServerGroupCfg 4 }

slbNewCfgGroupEntry OBJECT-TYPE
    SYNTAX  SlbNewCfgGroupEntry
    MAX-ACCESS  not-accessible
    STATUS  current
    DESCRIPTION
        "A row in the slbNewCfgGroupTable "
    INDEX   { slbNewCfgGroupIndex }
    ::= { slbNewCfgGroupTable 1 }

SlbNewCfgGroupEntry ::= SEQUENCE {
    slbNewCfgGroupIndex              Integer32,
    slbNewCfgGroupRealServers        OCTET STRING,
    slbNewCfgGroupAddServer          Integer32,
    slbNewCfgGroupRemoveServer       Integer32,
    slbNewCfgGroupMetric             INTEGER,
    slbNewCfgGroupBackupServer       Integer32,
    slbNewCfgGroupBackupGroup	     Integer32,
    slbNewCfgGroupHealthCheckUrl     DisplayString,
    slbNewCfgGroupHealthCheckLayer   INTEGER,
    slbNewCfgGroupRealThreshold	     INTEGER,
    slbNewCfgGroupVipHealthCheck     INTEGER,
    slbNewCfgGroupIdsState           INTEGER,
    slbNewCfgGroupIdsPort            INTEGER,
    slbNewCfgGroupDelete             INTEGER,
    slbNewCfgGroupIdsFlood           INTEGER,
    slbNewCfgGroupMinmissHash        INTEGER,
    slbNewCfgGroupPhashMask          IpAddress,
    slbNewCfgGroupRmetric            INTEGER,
    slbNewCfgGroupHealthCheckFormula DisplayString,
    slbNewCfgGroupWlm                Integer32,
    slbNewCfgGroupRadiusAuthenString DisplayString,
    slbNewCfgGroupOperatorAccess     INTEGER,
    slbNewCfgGroupSecBackupGroup     Integer32,
    slbNewCfgGroupSlowstart          Integer32,
    slbNewCfgGroupName               DisplayString,
    slbNewCfgGroupIpVer              INTEGER,
    slbNewCfgGroupBackup             DisplayString,
    slbNewCfgGroupMinThreshold       Integer32,
    slbNewCfgGroupMaxThreshold       Integer32,
    slbNewCfgGroupBackupType         INTEGER,
    slbNewCfgGroupHealthID           DisplayString,
    slbNewCfgGroupPhashPrefixLength  INTEGER,
    slbNewCfgGroupIdsChain           INTEGER,
    slbNewCfgGroupMaxConEx           INTEGER

    }

slbNewCfgGroupIndex OBJECT-TYPE
    SYNTAX  Integer32
    MAX-ACCESS  read-only
    STATUS  current
    DESCRIPTION
        "The group number for which the information pertains."
    ::= { slbNewCfgGroupEntry 1 }

slbNewCfgGroupRealServers    OBJECT-TYPE
    SYNTAX  OCTET STRING
    MAX-ACCESS  read-only
    STATUS  current
    DESCRIPTION
        "The Real servers in the group.  The servers are presented
         in bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbNewCfgGroupEntry 2 }

slbNewCfgGroupAddServer OBJECT-TYPE
    SYNTAX  Integer32
    MAX-ACCESS  read-create
    STATUS  current
    DESCRIPTION
        "The real server to be added to the group. When read, 0 is returned."
    ::= { slbNewCfgGroupEntry 3 }

slbNewCfgGroupRemoveServer OBJECT-TYPE 
    SYNTAX  Integer32 
    MAX-ACCESS  read-create 
    STATUS  current
    DESCRIPTION
        "The real server to be removed from the group. When read, 0 is returned."
    ::= { slbNewCfgGroupEntry 4 }
  
slbNewCfgGroupMetric OBJECT-TYPE
    SYNTAX  INTEGER {  
	roundRobin(1),
	leastConnections(2),
	minMisses(3),
	hash(4),
	response(5),
	bandwidth(6),
        phash(7),
        svcLeast(8),
        unsupported(2147483647)
        }
    MAX-ACCESS  read-create
    STATUS  current
    DESCRIPTION
        "The metric used to select next server in group."
    ::= { slbNewCfgGroupEntry 5 }

slbNewCfgGroupBackupServer OBJECT-TYPE
    SYNTAX  Integer32
    MAX-ACCESS  read-create
    STATUS  current
    DESCRIPTION
        "The backup real server for this group."
    ::= { slbNewCfgGroupEntry 6 }

slbNewCfgGroupBackupGroup OBJECT-TYPE
    SYNTAX  Integer32
    MAX-ACCESS  read-create
    STATUS  current
    DESCRIPTION
        "The backup real server group for this group."
    ::= { slbNewCfgGroupEntry 7 }

slbNewCfgGroupHealthCheckUrl OBJECT-TYPE
    SYNTAX  DisplayString (SIZE(0..127))
    MAX-ACCESS  read-create
    STATUS  current
    DESCRIPTION
        "The specific content which is examined during health checks.
         The content depends on the type of health check."
    ::= { slbNewCfgGroupEntry 8 }

slbNewCfgGroupHealthCheckLayer OBJECT-TYPE
    SYNTAX  INTEGER {
		icmp(1),
		tcp(2),
		http(3),
		httphead(44),
		dns(4),
		smtp(5),
		pop3(6),
		nntp(7),
		ftp(8),
		imap(9),
		radius(10),
		sslh(11),
		script1(12),
		script2(13),
		script3(14),
		script4(15),
		script5(16),
		script6(17),
		script7(18),
		script8(19),
		script9(20),
		script10(21),
		script11(22),
		script12(23),
		script13(24),
		script14(25),
		script15(26),
		script16(27),
		link(28),
		wsp(29),
		wtls(30),
		ldap(31),
		udpdns(32),
		arp(33),
		snmp1(34),
		snmp2(35),
		snmp3(36),
		snmp4(37),
		snmp5(38),
		radiusacs(39),
		tftp(40),
		wtp(41),
		rtsp(42),
		sipping(43),
		sipoptions(45),
		wts(46),
		dhcp(47),
		radiusaa(48),
		sslv3(49),
		script17(116),
		script18(117),
		script19(118),
		script20(119),
		script21(120),
		script22(121),
		script23(122),
		script24(123),
		script25(124),
		script26(125),
		script27(126),
		script28(127),
		script29(128),
		script30(129),
		script31(130),
		script32(131),
		script33(132),
		script34(133),
		script35(134),
		script36(135),
		script37(136),
		script38(137),
		script39(138),
		script40(139),
		script41(140),
		script42(141),
		script43(142),
		script44(143),
		script45(144),
		script46(145),
		script47(146),
		script48(147),
		script49(148),
		script50(149),
		script51(150),
		script52(151),
		script53(152),
		script54(153),
		script55(154),
		script56(155),
		script57(156),
		script58(157),
		script59(158),
		script60(159),
		script61(160),
		script62(161),
		script63(162),
		script64(163),
		none(164),
		unknown(165),
                unsupported(2147483647)
	}
    MAX-ACCESS  read-write
    STATUS  current
    DESCRIPTION
        "The OSI layer at which servers are health checked.
		 From version 29.0.0.0 the following values are not supported:
		 snmp2-snmp5, script1-script64."
    ::= { slbNewCfgGroupEntry 9 }

slbNewCfgGroupName OBJECT-TYPE 
    SYNTAX  DisplayString (SIZE(0..255))
    MAX-ACCESS  read-create 
    STATUS  current 
    DESCRIPTION 
        "The name of the real server group."  
    ::= { slbNewCfgGroupEntry 10 }

slbNewCfgGroupRealThreshold OBJECT-TYPE 
    SYNTAX  INTEGER (0..15)
    MAX-ACCESS  read-create 
    STATUS  current 
    DESCRIPTION 
        "The minimum number of real servers available. If at any time, the 
         number reaches this minimum limit, a SYSLOG ALERT message is send to 
         to the configured syslog servers stating that the real server 
         threshold has been reached for the concerned group."  
    ::= { slbNewCfgGroupEntry 11 }

slbNewCfgGroupVipHealthCheck OBJECT-TYPE
    SYNTAX  INTEGER {
	enabled(1),
	disabled(2),
        unsupported(2147483647)
	}
    MAX-ACCESS  read-create
    STATUS  current
    DESCRIPTION
        "Enable or disable VIP health checking in DSR mode." 
    ::= { slbNewCfgGroupEntry 12 }

slbNewCfgGroupIdsState OBJECT-TYPE
    SYNTAX  INTEGER {
	enabled(1),
	disabled(2),
        unsupported(2147483647)
	}
    MAX-ACCESS  read-create
    STATUS  current
    DESCRIPTION
        "Enable or disable intrusion detection."
    ::= { slbNewCfgGroupEntry 13 }

slbNewCfgGroupIdsPort OBJECT-TYPE
    SYNTAX  INTEGER (0..65534)
    MAX-ACCESS  read-create
    STATUS  current
    DESCRIPTION
        "The intrusion detection port. A value of 1 is invalid."
    ::= { slbNewCfgGroupEntry 14 }

slbNewCfgGroupDelete OBJECT-TYPE
    SYNTAX  INTEGER {
	other(1),
	delete(2),
        unsupported(2147483647) 
	}
    MAX-ACCESS  read-create
    STATUS  current
    DESCRIPTION
        "By setting the value to delete(2), the entire group is deleted."
    ::= { slbNewCfgGroupEntry 15 }

slbNewCfgGroupIdsFlood OBJECT-TYPE
    SYNTAX  INTEGER {
	enabled(1),
	disabled(2),
        unsupported(2147483647)
	}
    MAX-ACCESS  read-create
    STATUS  current
    DESCRIPTION
        "Enable or disable intrusion detection group flood."
    ::= { slbNewCfgGroupEntry 16 }

slbNewCfgGroupMinmissHash OBJECT-TYPE
    SYNTAX  INTEGER {
        minmiss-24(1),
        minmiss-32(2),
        unsupported(2147483647)
        }
    MAX-ACCESS  read-create
    STATUS  current
    DESCRIPTION
        "24|32 number of sip bits used for minmisses hash in the
         new_configuration block."
    ::= { slbNewCfgGroupEntry 17 }

slbNewCfgGroupPhashMask OBJECT-TYPE
    SYNTAX  IpAddress
    MAX-ACCESS  read-create
    STATUS  current
    DESCRIPTION
        "IP address mask used by the persistent hash metric."
    ::= { slbNewCfgGroupEntry 18 }

slbNewCfgGroupRmetric OBJECT-TYPE
    SYNTAX  INTEGER {  
	roundRobin(1),
	hash(2),
        leastConnections(3),
        unsupported(2147483647)
        }
    MAX-ACCESS  read-create
    STATUS  current
    DESCRIPTION
        "The metric used to select next rport in server."
    ::= { slbNewCfgGroupEntry 19 }

slbNewCfgGroupHealthCheckFormula OBJECT-TYPE
    SYNTAX  DisplayString (SIZE(0..31))
    MAX-ACCESS  read-create 
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formula to mark the server group failed for the virtual server 
         if 1 and 2 FAILED or 3 and 4 FAILED is (1|2)&(3|4)
         This formula will mark the virtual server UP, if 1 or 2 and 3 or 4
         are health checked sucessfully."
    ::= { slbNewCfgGroupEntry 20 }

slbNewCfgGroupOperatorAccess OBJECT-TYPE
    SYNTAX  INTEGER {
	enabled(1),
	disabled(2),
        unsupported(2147483647)
	}
    MAX-ACCESS  read-create
    STATUS  current
    DESCRIPTION
        "Enable or disable access to this group for operator."
    ::= { slbNewCfgGroupEntry 21 }

slbNewCfgGroupWlm OBJECT-TYPE
    SYNTAX  Integer32
    MAX-ACCESS  read-create
    STATUS  current
    DESCRIPTION
        "The Workload Manager for this Group."
    ::= { slbNewCfgGroupEntry 22 }

slbNewCfgGroupRadiusAuthenString OBJECT-TYPE
    SYNTAX  DisplayString (SIZE(0..32))
    MAX-ACCESS  read-write
    STATUS  current
    DESCRIPTION
        "The group RADIUS authentication string. The string is used for
         generating encrypted authentication string while doing RADIUS
         health check for this group radius servers."
    ::= { slbNewCfgGroupEntry 23 }

slbNewCfgGroupSecBackupGroup OBJECT-TYPE
    SYNTAX  Integer32
    MAX-ACCESS  read-create
    STATUS  current
    DESCRIPTION
        "The Secondary backup real server group for this group."
    ::= { slbNewCfgGroupEntry 24 }

slbNewCfgGroupSlowstart OBJECT-TYPE
    SYNTAX  Integer32
    MAX-ACCESS  read-create
    STATUS  current
    DESCRIPTION
        "The slow-start time for this group."
    ::= { slbNewCfgGroupEntry 25 }

slbNewCfgGroupMinThreshold OBJECT-TYPE
    SYNTAX  Integer32
    MAX-ACCESS  read-create
    STATUS  current
    DESCRIPTION
        "The minimum threshold value for this group."
    ::= { slbNewCfgGroupEntry 26 }

slbNewCfgGroupMaxThreshold OBJECT-TYPE
    SYNTAX  Integer32
    MAX-ACCESS  read-create
    STATUS  current
    DESCRIPTION
        "The maximum threshold value for this group."
    ::= { slbNewCfgGroupEntry 27 }


slbNewCfgGroupIpVer OBJECT-TYPE
    SYNTAX  INTEGER{
        ipv4(1),
        ipv6(2),
        mixed(3),
        unsupported(2147483647)
        }
    MAX-ACCESS  read-create
    STATUS  current
    DESCRIPTION
        "The type of real server group IP address."
    ::= { slbNewCfgGroupEntry 28 }

slbNewCfgGroupBackup OBJECT-TYPE
    SYNTAX  DisplayString (SIZE(0..255))
    MAX-ACCESS  read-only
    STATUS  current
    DESCRIPTION
        "The backup real group or real server for this group."
    ::= { slbNewCfgGroupEntry 29 }

slbNewCfgGroupBackupType OBJECT-TYPE
    SYNTAX  INTEGER {
        none(1),
        server(2),
        group(3),
        unsupported(2147483647)
        }
    MAX-ACCESS  read-create
    STATUS  current
    DESCRIPTION
        "Backup type of the real server group."
    ::= { slbNewCfgGroupEntry 30 }

slbNewCfgGroupHealthID OBJECT-TYPE
    SYNTAX  DisplayString (SIZE(0..32))
    MAX-ACCESS  read-write
    STATUS  current
    DESCRIPTION
        "The Advanced HC ID."
    ::= { slbNewCfgGroupEntry 31 }

slbNewCfgGroupPhashPrefixLength OBJECT-TYPE
    SYNTAX  INTEGER (1..128)
    MAX-ACCESS  read-write
    STATUS  current
    DESCRIPTION
        "Prefix length used by the persistent hash metric."
    ::= { slbNewCfgGroupEntry 32 }

slbNewCfgGroupIdsChain OBJECT-TYPE
    SYNTAX  INTEGER {
	enabled(1),
	disabled(2),
        unsupported(2147483647)
	}
    MAX-ACCESS  read-create
    STATUS  current
    DESCRIPTION
        "Enable or disable IDS group participation in inspection chain."
    ::= { slbNewCfgGroupEntry 33 }

slbNewCfgGroupMaxConEx OBJECT-TYPE
    SYNTAX  INTEGER {
        enabled(1),
        disabled(2),
        unsupported(2147483647)
        }
    MAX-ACCESS read-create
    STATUS  current
    DESCRIPTION
        "Enable or Disable override maximum connections limit."
    ::= { slbNewCfgGroupEntry 34 }


-- SLB - Group Real Server Table
slbCurCfgGroupRealServerTable OBJECT-TYPE
    SYNTAX  SEQUENCE OF SlbCurCfgGroupRealServerEntry
    MAX-ACCESS  not-accessible
    STATUS  current
    DESCRIPTION
        "The table of real servers per group.
         Note:This mib is not supported on VX instance of Virtualization."
    ::= { realServerGroupCfg 5 }

slbCurCfgGroupRealServerEntry OBJECT-TYPE
    SYNTAX  SlbCurCfgGroupRealServerEntry
    MAX-ACCESS  not-accessible
    STATUS  current
    DESCRIPTION
        "A row in the Real server group table."
    INDEX   { slbCurCfgRealServGroupIndex, slbCurCfgGroupRealServIndex }
    ::= { slbCurCfgGroupRealServerTable 1 }

SlbCurCfgGroupRealServerEntry ::= SEQUENCE {
    slbCurCfgRealServGroupIndex       Integer32,
    slbCurCfgGroupRealServIndex       Integer32,
    slbCurCfgGroupRealServerState     INTEGER
    }

slbCurCfgRealServGroupIndex OBJECT-TYPE
    SYNTAX  Integer32
    MAX-ACCESS  read-only
    STATUS  current
    DESCRIPTION
        "The real server group index." 
    ::= { slbCurCfgGroupRealServerEntry 1 }

slbCurCfgGroupRealServIndex OBJECT-TYPE
    SYNTAX  Integer32
    MAX-ACCESS  read-only
    STATUS  current
    DESCRIPTION
        "The real server index." 
    ::= { slbCurCfgGroupRealServerEntry 2 }

slbCurCfgGroupRealServerState OBJECT-TYPE
    SYNTAX  INTEGER {
	enabled(1),
	disabled(2),
        unsupported(2147483647)
	}
    MAX-ACCESS  read-only
    STATUS  current
    DESCRIPTION
        "Enable/disable a real server gracefully on a per group basis." 
    ::= { slbCurCfgGroupRealServerEntry 3 }

slbNewCfgGroupRealServerTable OBJECT-TYPE
    SYNTAX  SEQUENCE OF SlbNewCfgGroupRealServerEntry
    MAX-ACCESS  not-accessible
    STATUS  current
    DESCRIPTION
        "The table of real server per group.
         Note:This mib is not supported on VX instance of Virtualization."
    ::= { realServerGroupCfg 6 }

slbNewCfgGroupRealServerEntry OBJECT-TYPE
    SYNTAX  SlbNewCfgGroupRealServerEntry
    MAX-ACCESS  not-accessible
    STATUS  current
    DESCRIPTION
        "A row in the Real server group table."
    INDEX   { slbNewCfgRealServGroupIndex, slbNewCfgGroupRealServIndex}
    ::= { slbNewCfgGroupRealServerTable 1 }

SlbNewCfgGroupRealServerEntry ::= SEQUENCE {
    slbNewCfgRealServGroupIndex        Integer32,
    slbNewCfgGroupRealServIndex        Integer32,
    slbNewCfgGroupRealServerState      INTEGER
    }

slbNewCfgRealServGroupIndex OBJECT-TYPE
    SYNTAX  Integer32
    MAX-ACCESS  read-only
    STATUS  current
    DESCRIPTION
        "The real server group index." 
    ::= { slbNewCfgGroupRealServerEntry 1 }

slbNewCfgGroupRealServIndex OBJECT-TYPE
    SYNTAX  Integer32
    MAX-ACCESS  read-only
    STATUS  current
    DESCRIPTION
        "The real server index." 
    ::= { slbNewCfgGroupRealServerEntry 2 }

slbNewCfgGroupRealServerState OBJECT-TYPE
    SYNTAX  INTEGER {
	enabled(1),
	disabled(2),
        unsupported(2147483647)
	}
    MAX-ACCESS  read-create
    STATUS  current
    DESCRIPTION
        "Enable/disable a real server gracefully on a per group basis." 
    ::= { slbNewCfgGroupRealServerEntry 3 }

-- Server load balancing - Group Table (alphanumeric key indexed) - Current Configuration

slbCurCfgEnhGroupTable OBJECT-TYPE
    SYNTAX  SEQUENCE OF SlbCurCfgEnhGroupEntry
    MAX-ACCESS  not-accessible
    STATUS  current
    DESCRIPTION
        "The table of groups,
         Note:This mib is not supported on VX instance of Virtualization."
    ::= { realServerGroupCfg 7 }

slbCurCfgEnhGroupEntry OBJECT-TYPE
    SYNTAX  SlbCurCfgEnhGroupEntry
    MAX-ACCESS  not-accessible
    STATUS  current
    DESCRIPTION
        "A row in the slbCurCfgEnhGroupTable "
    INDEX   { slbCurCfgEnhGroupIndex }
    ::= { slbCurCfgEnhGroupTable 1 }


SlbCurCfgEnhGroupEntry ::= SEQUENCE {
    slbCurCfgEnhGroupIndex              DisplayString,
    slbCurCfgEnhGroupMetric             INTEGER,
    slbCurCfgEnhGroupBackupServer       DisplayString,
    slbCurCfgEnhGroupBackupGroup        DisplayString,
    slbCurCfgEnhGroupHealthCheckUrl     DisplayString,
    slbCurCfgEnhGroupHealthCheckLayer   INTEGER,
    slbCurCfgEnhGroupRealThreshold      INTEGER,
    slbCurCfgEnhGroupVipHealthCheck     INTEGER,
    slbCurCfgEnhGroupIdsState           INTEGER,
    slbCurCfgEnhGroupIdsPort            INTEGER,
    slbCurCfgEnhGroupIdsFlood           INTEGER,
    slbCurCfgEnhGroupMinmissHash        INTEGER,
    slbCurCfgEnhGroupPhashMask          IpAddress,
    slbCurCfgEnhGroupRmetric            INTEGER,
    slbCurCfgEnhGroupHealthCheckFormula DisplayString,
    slbCurCfgEnhGroupWlm                Integer32,
    slbCurCfgEnhGroupRadiusAuthenString DisplayString,
    slbCurCfgEnhGroupOperatorAccess     INTEGER,
    slbCurCfgEnhGroupSecBackupGroup     DisplayString,
    slbCurCfgEnhGroupSlowstart          Integer32,
    slbCurCfgEnhGroupMinThreshold       Integer32,
    slbCurCfgEnhGroupMaxThreshold       Integer32,
    slbCurCfgEnhGroupName               DisplayString,
    slbCurCfgEnhGroupIpVer              INTEGER,
    slbCurCfgEnhGroupBackup             DisplayString,
    slbCurCfgEnhGroupHealthID           DisplayString,
    slbCurCfgEnhGroupPhashPrefixLength  INTEGER,
    slbCurCfgEnhGroupType               INTEGER,
    slbCurCfgEnhGroupIdsChain           INTEGER,
	slbCurCfgEnhGroupSecType			INTEGER,
	slbCurCfgEnhGroupSecDeviceFlag		INTEGER,
    slbCurCfgEnhGroupMaxConEx           INTEGER
    }

slbCurCfgEnhGroupIndex OBJECT-TYPE
    SYNTAX DisplayString (SIZE(1..255)) 
    MAX-ACCESS  read-only
    STATUS  current
    DESCRIPTION
        "The group alphanumeric index for which the information pertains."
    ::= { slbCurCfgEnhGroupEntry 1 }

slbCurCfgEnhGroupMetric OBJECT-TYPE
    SYNTAX  INTEGER {
        roundRobin(1),
        leastConnections(2),
        minMisses(3),
        hash(4),
        response(5),
        bandwidth(6),
        phash(7),
        svcLeast(8),
	hrw(9),
        unsupported(2147483647)
        }
    MAX-ACCESS  read-only
    STATUS  current
    DESCRIPTION
        "The metric used to select next server in group."
    ::= { slbCurCfgEnhGroupEntry 2 }

slbCurCfgEnhGroupBackupServer OBJECT-TYPE
    SYNTAX DisplayString (SIZE(1..255)) 
    MAX-ACCESS  read-only
    STATUS  current
    DESCRIPTION
        "The backup real server for this group."
    ::= { slbCurCfgEnhGroupEntry 3 }

slbCurCfgEnhGroupBackupGroup OBJECT-TYPE
    SYNTAX DisplayString (SIZE(1..255)) 
    MAX-ACCESS  read-only
    STATUS  current
    DESCRIPTION
        "The backup real server group for this group."
    ::= { slbCurCfgEnhGroupEntry 4 }

slbCurCfgEnhGroupHealthCheckUrl OBJECT-TYPE
    SYNTAX  DisplayString (SIZE(0..127))
    MAX-ACCESS  read-only
    STATUS  current
    DESCRIPTION
        "The specific content which is examined during health checks.
         The content depends on the type of health check."
    ::= { slbCurCfgEnhGroupEntry 5 }

slbCurCfgEnhGroupHealthCheckLayer OBJECT-TYPE
    SYNTAX  INTEGER {
                icmp(1),
                tcp(2),
                http(3),
                httphead(44),
                dns(4),
                smtp(5),
                pop3(6),
                nntp(7),
                ftp(8),
                imap(9),
                radius(10),
                sslh(11),
                script1(12),
                script2(13),
                script3(14),
                script4(15),
                script5(16),
                script6(17),
                script7(18),
                script8(19),
                script9(20),
                script10(21),
                script11(22),
                script12(23),
                script13(24),
                script14(25),
                script15(26),
                script16(27),
                link(28),
                wsp(29),
                wtls(30),
                ldap(31),
                udpdns(32),
                arp(33),
                snmp1(34),
                snmp2(35),
                snmp3(36),
                snmp4(37),
                snmp5(38),
                radiusacs(39),
                tftp(40),
                wtp(41),
                rtsp(42),
                sipping(43),
                sipoptions(45),
                wts(46),
                dhcp(47),
                radiusaa(48),
                sslv3(49),
                script17(116),
                script18(117),
                script19(118),
                script20(119),
                script21(120),
                script22(121),
                script23(122),
                script24(123),
                script25(124),
                script26(125),
                script27(126),
                script28(127),
                script29(128),
                script30(129),
                script31(130),
                script32(131),
                script33(132),
                script34(133),
                script35(134),
                script36(135),
                script37(136),
                script38(137),
                script39(138),
                script40(139),
                script41(140),
                script42(141),
                script43(142),
                script44(143),
                script45(144),
                script46(145),
                script47(146),
                script48(147),
                script49(148),
                script50(149),
                script51(150),
                script52(151),
                script53(152),
                script54(153),
                script55(154),
                script56(155),
                script57(156),
                script58(157),
                script59(158),
                script60(159),
                script61(160),
                script62(161),
                script63(162),
                script64(163),
                none(164),
                unknown(165),
                unsupported(2147483647)
        }
    MAX-ACCESS  read-only
    STATUS  current
    DESCRIPTION
        "The OSI layer at which servers are health checked.
                 From version 29.0.0.0 the following values are not supported:
                 snmp2-snmp5, script1-script64."
    ::= { slbCurCfgEnhGroupEntry 6 }

slbCurCfgEnhGroupName OBJECT-TYPE
    SYNTAX  DisplayString (SIZE(0..255))
    MAX-ACCESS  read-only
    STATUS  current
    DESCRIPTION
        "The name of the real server group."
    ::= { slbCurCfgEnhGroupEntry 7 }

slbCurCfgEnhGroupRealThreshold OBJECT-TYPE
    SYNTAX  INTEGER (0..15)
    MAX-ACCESS  read-only
    STATUS  current
    DESCRIPTION
        "The minimum number of real servers available. If at any time, the
         number reaches this minimum limit, a SYSLOG ALERT message is send to
         to the configured syslog servers stating that the real server
         threshold has been reached for the concerned group."
    ::= { slbCurCfgEnhGroupEntry 8 }

slbCurCfgEnhGroupVipHealthCheck OBJECT-TYPE
    SYNTAX  INTEGER {
        enabled(1),
        disabled(2),
        unsupported(2147483647)
        }
    MAX-ACCESS  read-only
    STATUS  current
    DESCRIPTION
        "Enable or disable VIP health checking in DSR mode."
    ::= { slbCurCfgEnhGroupEntry 9 }

slbCurCfgEnhGroupIdsState OBJECT-TYPE
    SYNTAX  INTEGER {
        enabled(1),
        disabled(2),
        unsupported(2147483647)
        }
    MAX-ACCESS  read-only
    STATUS  current
    DESCRIPTION
        "Enable or disable intrusion detection."
    ::= { slbCurCfgEnhGroupEntry 10 }

slbCurCfgEnhGroupIdsPort OBJECT-TYPE
    SYNTAX  INTEGER (0..65534)
    MAX-ACCESS  read-only
    STATUS  current
    DESCRIPTION
        "The intrusion detection port. A value of 1 is invalid."
    ::= { slbCurCfgEnhGroupEntry 11 }

slbCurCfgEnhGroupIdsFlood OBJECT-TYPE
    SYNTAX  INTEGER {
        enabled(1),
        disabled(2),
        unsupported(2147483647)
        }
    MAX-ACCESS  read-only
    STATUS  current
    DESCRIPTION
        "Enable or disable intrusion detection group flood."
    ::= { slbCurCfgEnhGroupEntry 12 }

slbCurCfgEnhGroupMinmissHash OBJECT-TYPE
    SYNTAX  INTEGER {
        minmiss-24(1),
        minmiss-32(2),
        unsupported(2147483647)
        }
    MAX-ACCESS  read-only
    STATUS  current
    DESCRIPTION
        "24|32 number of ip bits used for minmisses hash in the
         current_configuration block."
    ::= { slbCurCfgEnhGroupEntry 13 }

slbCurCfgEnhGroupPhashMask OBJECT-TYPE
    SYNTAX  IpAddress
    MAX-ACCESS  read-only
    STATUS  current
    DESCRIPTION
        "IP address mask used by the persistent hash metric."
    ::= { slbCurCfgEnhGroupEntry 14 }

slbCurCfgEnhGroupRmetric OBJECT-TYPE
    SYNTAX  INTEGER {
        roundRobin(1),
        hash(2),
        leastConnections(3),
        unsupported(2147483647)
        }
    MAX-ACCESS  read-only
    STATUS  current
    DESCRIPTION
        "The metric used to select next rport in server."
    ::= { slbCurCfgEnhGroupEntry 15 }

slbCurCfgEnhGroupHealthCheckFormula OBJECT-TYPE
    SYNTAX  DisplayString (SIZE(0..31))
    MAX-ACCESS  read-only
    STATUS  current
    DESCRIPTION
        "The formula used to state the actual health of a virtual service.
         It allows user to use the symbols of '(', ')', '|', '&' to
         construct a formula to state the health of the server group.
         This string can take the following formats :
             '(1&2|3..)', '128' or 'none'
         Example: Consider a group with 4 reals 1, 2, 3, 4.  An example of
         a formula to mark the server group failed for the virtual server
         if 1 and 2 FAILED or 3 and 4 FAILED is (1|2)&(3|4)
         This formula will mark the virtual server UP, if 1 or 2 and 3 or 4
         are health checked sucessfully."
    ::= { slbCurCfgEnhGroupEntry 16 }

slbCurCfgEnhGroupOperatorAccess OBJECT-TYPE
    SYNTAX  INTEGER {
        enabled(1),
        disabled(2),
        unsupported(2147483647)
        }
    MAX-ACCESS  read-only
    STATUS  current
    DESCRIPTION
        "Enable or disable access to this group for operator."
    ::= { slbCurCfgEnhGroupEntry 17 }

slbCurCfgEnhGroupWlm OBJECT-TYPE
    SYNTAX  Integer32
    MAX-ACCESS  read-only
    STATUS  current
    DESCRIPTION
        "The Workload Manager for this Group."
    ::= { slbCurCfgEnhGroupEntry 18 }

slbCurCfgEnhGroupRadiusAuthenString OBJECT-TYPE
    SYNTAX  DisplayString (SIZE(0..32))
    MAX-ACCESS  read-only
    STATUS  current
    DESCRIPTION
        "The group RADIUS authentication string. The string is used for
         generating encrypted authentication string while doing RADIUS
         health check for this group radius servers."
    ::= { slbCurCfgEnhGroupEntry 19 }

slbCurCfgEnhGroupSecBackupGroup OBJECT-TYPE
    SYNTAX DisplayString (SIZE(0..255))
    MAX-ACCESS  read-only
    STATUS  current
    DESCRIPTION
        "The Secondary backup real server group for this group."
    ::= { slbCurCfgEnhGroupEntry 20 }

slbCurCfgEnhGroupSlowstart OBJECT-TYPE
    SYNTAX  Integer32
    MAX-ACCESS  read-only
    STATUS  current
    DESCRIPTION
        "The slow-start time for this group."
    ::= { slbCurCfgEnhGroupEntry 21 }

slbCurCfgEnhGroupMinThreshold OBJECT-TYPE
    SYNTAX  Integer32
    MAX-ACCESS  read-only
    STATUS  current
    DESCRIPTION
        "The minimum threshold value for this group."
    ::= { slbCurCfgEnhGroupEntry 22 }

slbCurCfgEnhGroupMaxThreshold OBJECT-TYPE
    SYNTAX  Integer32
    MAX-ACCESS  read-only
    STATUS  current
    DESCRIPTION
        "The maximum threshold value for this group."
    ::= { slbCurCfgEnhGroupEntry 23 }

slbCurCfgEnhGroupIpVer OBJECT-TYPE
    SYNTAX  INTEGER{
        ipv4(1),
        ipv6(2),
        mixed(3),
        unsupported(2147483647)
        }
    MAX-ACCESS  read-only
    STATUS  current
    DESCRIPTION
        "The type of real server group IP address."
    ::= { slbCurCfgEnhGroupEntry 24 }

slbCurCfgEnhGroupBackup OBJECT-TYPE
    SYNTAX  DisplayString (SIZE(0..255))
    MAX-ACCESS  read-only
    STATUS  current
    DESCRIPTION
        "The backup real group or real server for this group."
    ::= { slbCurCfgEnhGroupEntry 25 }

slbCurCfgEnhGroupHealthID OBJECT-TYPE
    SYNTAX  DisplayString (SIZE(0..32))
    MAX-ACCESS  read-only
    STATUS  current
    DESCRIPTION
        "The Advanced HC ID."
    ::= { slbCurCfgEnhGroupEntry 26 }

slbCurCfgEnhGroupPhashPrefixLength OBJECT-TYPE
    SYNTAX  INTEGER (1..128)
    MAX-ACCESS  read-only
    STATUS  current
    DESCRIPTION
        "Prefix length used by the persistent hash metric."
    ::= { slbCurCfgEnhGroupEntry 27 }

slbCurCfgEnhGroupType OBJECT-TYPE
    SYNTAX  INTEGER {
	local(0),
	wanlink(2),
        unsupported(2147483647)
	}
    MAX-ACCESS  read-only
    STATUS  current
    DESCRIPTION
        "Group type."
    ::= { slbCurCfgEnhGroupEntry 28 }

slbCurCfgEnhGroupIdsChain OBJECT-TYPE
    SYNTAX  INTEGER {
        enabled(1),
        disabled(2),
        unsupported(2147483647)
        }
    MAX-ACCESS  read-only
    STATUS  current
    DESCRIPTION
        "Enable or disable IDS group participation in inspection chain."
    ::= { slbCurCfgEnhGroupEntry 29 }

slbCurCfgEnhGroupSecType OBJECT-TYPE
    SYNTAX  INTEGER {
		none(1),
		virtual(2),
		layer(3),
		passive(4),
		l3sw(5),
                unsupported(2147483647)
	}
    MAX-ACCESS  read-only
    STATUS  current
    DESCRIPTION
        "The group security device type." 
    ::= { slbCurCfgEnhGroupEntry 30 }

slbCurCfgEnhGroupSecDeviceFlag OBJECT-TYPE
	SYNTAX  INTEGER {
        none(1),
		security(2),
        unsupported(2147483647)
	} 
	MAX-ACCESS  read-only
    STATUS  current
    DESCRIPTION
        "The Group security device flag."
    ::= { slbCurCfgEnhGroupEntry 31 }

slbCurCfgEnhGroupMaxConEx OBJECT-TYPE
    SYNTAX  INTEGER {
        enabled(1),
        disabled(2),
        unsupported(2147483647)
        }
    MAX-ACCESS read-only
    STATUS  current
    DESCRIPTION
        "Enable or Disable override maximum connections limit."
    ::= { slbCurCfgEnhGroupEntry 32 }


-- Server load balancing - Group Table (alphanumeric key indexed) - New Configuration
slbNewCfgEnhGroupTable OBJECT-TYPE
    SYNTAX  SEQUENCE OF SlbNewCfgEnhGroupEntry
    MAX-ACCESS  not-accessible
    STATUS  current
    DESCRIPTION
        "The table of groups,
         Note:This mib is not supported for VX instance of Virtualization."
    ::= { realServerGroupCfg 8 }

slbNewCfgEnhGroupEntry OBJECT-TYPE
    SYNTAX  SlbNewCfgEnhGroupEntry
    MAX-ACCESS  not-accessible
    STATUS  current
    DESCRIPTION
        "A row in the slbNewCfgEnhGroupTable "
    INDEX   { slbNewCfgEnhGroupIndex }
    ::= { slbNewCfgEnhGroupTable 1 }

SlbNewCfgEnhGroupEntry ::= SEQUENCE {
    slbNewCfgEnhGroupIndex              DisplayString,
    slbNewCfgEnhGroupAddServer          DisplayString,
    slbNewCfgEnhGroupRemoveServer       DisplayString,
    slbNewCfgEnhGroupMetric             INTEGER,
    slbNewCfgEnhGroupBackupServer       DisplayString,
    slbNewCfgEnhGroupBackupGroup        DisplayString,
    slbNewCfgEnhGroupHealthCheckUrl     DisplayString,
    slbNewCfgEnhGroupHealthCheckLayer   INTEGER,
    slbNewCfgEnhGroupRealThreshold      INTEGER,
    slbNewCfgEnhGroupVipHealthCheck     INTEGER,
    slbNewCfgEnhGroupIdsState           INTEGER,
    slbNewCfgEnhGroupIdsPort            INTEGER,
    slbNewCfgEnhGroupDelete             INTEGER,
    slbNewCfgEnhGroupIdsFlood           INTEGER,
    slbNewCfgEnhGroupMinmissHash        INTEGER,
    slbNewCfgEnhGroupPhashMask          IpAddress,
    slbNewCfgEnhGroupRmetric            INTEGER,
    slbNewCfgEnhGroupHealthCheckFormula DisplayString,
    slbNewCfgEnhGroupWlm                Integer32,
    slbNewCfgEnhGroupRadiusAuthenString DisplayString,
    slbNewCfgEnhGroupOperatorAccess     INTEGER,
    slbNewCfgEnhGroupSecBackupGroup     DisplayString,
    slbNewCfgEnhGroupSlowstart          Integer32,
    slbNewCfgEnhGroupName               DisplayString,
    slbNewCfgEnhGroupIpVer              INTEGER,
    slbNewCfgEnhGroupBackup             DisplayString,
    slbNewCfgEnhGroupMinThreshold       Integer32,
    slbNewCfgEnhGroupMaxThreshold       Integer32,
    slbNewCfgEnhGroupBackupType         INTEGER,
    slbNewCfgEnhGroupHealthID           DisplayString,
    slbNewCfgEnhGroupPhashPrefixLength  INTEGER,
    slbNewCfgEnhGroupType               INTEGER,
    slbNewCfgEnhGroupCopy               DisplayString,
    slbNewCfgEnhGroupIdsChain           INTEGER,
	slbNewCfgEnhGroupSecType			INTEGER,
	slbNewCfgEnhGroupSecDeviceFlag		INTEGER,
    slbNewCfgEnhGroupMaxConEx           INTEGER

    }

slbNewCfgEnhGroupIndex OBJECT-TYPE
    SYNTAX DisplayString (SIZE(1..255)) 
    MAX-ACCESS  read-only
    STATUS  current
    DESCRIPTION
        "The group alphanumeric index for which the information pertains."
    ::= { slbNewCfgEnhGroupEntry 1 }

slbNewCfgEnhGroupAddServer OBJECT-TYPE
    SYNTAX DisplayString (SIZE(1..255)) 
    MAX-ACCESS  read-create
    STATUS  current
    DESCRIPTION
        "The real server to be added to the group. When read, 0 is returned."
    ::= { slbNewCfgEnhGroupEntry 2 }

slbNewCfgEnhGroupRemoveServer OBJECT-TYPE
    SYNTAX DisplayString (SIZE(1..255)) 
    MAX-ACCESS  read-create
    STATUS  current
    DESCRIPTION
        "The real server to be removed from the group. When read, 0 is returned."
    ::= { slbNewCfgEnhGroupEntry 3 }

slbNewCfgEnhGroupMetric OBJECT-TYPE
    SYNTAX  INTEGER {
        roundRobin(1),
        leastConnections(2),
        minMisses(3),
        hash(4),
        response(5),
        bandwidth(6),
        phash(7),
        svcLeast(8),
	hrw(9),
        unsupported(2147483647)
        }
    MAX-ACCESS  read-create
    STATUS  current
    DESCRIPTION
        "The metric used to select next server in group."
    ::= { slbNewCfgEnhGroupEntry 4 }

slbNewCfgEnhGroupBackupServer OBJECT-TYPE
    SYNTAX DisplayString (SIZE(1..255)) 
    MAX-ACCESS  read-create
    STATUS  current
    DESCRIPTION
        "The backup real server for this group."
    ::= { slbNewCfgEnhGroupEntry 5 }

slbNewCfgEnhGroupBackupGroup OBJECT-TYPE
    SYNTAX DisplayString (SIZE(1..255)) 
    MAX-ACCESS  read-create
    STATUS  current
    DESCRIPTION
        "The backup real server group for this group."
    ::= { slbNewCfgEnhGroupEntry 6 }

slbNewCfgEnhGroupHealthCheckUrl OBJECT-TYPE
    SYNTAX  DisplayString (SIZE(0..127))
    MAX-ACCESS  read-create
    STATUS  current
    DESCRIPTION
        "The specific content which is examined during health checks.
         The content depends on the type of health check."
    ::= { slbNewCfgEnhGroupEntry 7 }

slbNewCfgEnhGroupHealthCheckLayer OBJECT-TYPE
    SYNTAX  INTEGER {
                icmp(1),
                tcp(2),
                http(3),
                httphead(44),
                dns(4),
                smtp(5),
                pop3(6),
                nntp(7),
                ftp(8),
                imap(9),
                radius(10),
                sslh(11),
                script1(12),
                script2(13),
                script3(14),
                script4(15),
                script5(16),
                script6(17),
                script7(18),
                script8(19),
                script9(20),
                script10(21),
                script11(22),
                script12(23),
                script13(24),
                script14(25),
                script15(26),
                script16(27),
                link(28),
                wsp(29),
                wtls(30),
                ldap(31),
                udpdns(32),
                arp(33),
                snmp1(34),
                snmp2(35),
                snmp3(36),
                snmp4(37),
                snmp5(38),
                radiusacs(39),
                tftp(40),
                wtp(41),
                rtsp(42),
                sipping(43),
                sipoptions(45),
                wts(46),
                dhcp(47),
                radiusaa(48),
                sslv3(49),
                script17(116),
                script18(117),
                script19(118),
                script20(119),
                script21(120),
                script22(121),
                script23(122),
                script24(123),
                script25(124),
                script26(125),
                script27(126),
                script28(127),
                script29(128),
                script30(129),
                script31(130),
                script32(131),
                script33(132),
                script34(133),
                script35(134),
                script36(135),
                script37(136),
                script38(137),
                script39(138),
                script40(139),
                script41(140),
                script42(141),
                script43(142),
                script44(143),
                script45(144),
                script46(145),
                script47(146),
                script48(147),
                script49(148),
                script50(149),
                script51(150),
                script52(151),
                script53(152),
                script54(153),
                script55(154),
                script56(155),
                script57(156),
                script58(157),
                script59(158),
                script60(159),
                script61(160),
                script62(161),
                script63(162),
                script64(163),
                none(164),
                unknown(165),
                unsupported(2147483647)
        }
    MAX-ACCESS  read-write
    STATUS  current
    DESCRIPTION
        "The OSI layer at which servers are health checked.
                 From version 29.0.0.0 the following values are not supported:
                 snmp2-snmp5, script1-script64."
    ::= { slbNewCfgEnhGroupEntry 8 }

slbNewCfgEnhGroupName OBJECT-TYPE
    SYNTAX  DisplayString (SIZE(0..255))
    MAX-ACCESS  read-create
    STATUS  current
    DESCRIPTION
        "The name of the real server group."
    ::= { slbNewCfgEnhGroupEntry 9 }

slbNewCfgEnhGroupRealThreshold OBJECT-TYPE
    SYNTAX  INTEGER (0..15)
    MAX-ACCESS  read-create
    STATUS  current
    DESCRIPTION
        "The minimum number of real servers available. If at any time, the
         number reaches this minimum limit, a SYSLOG ALERT message is send to
         to the configured syslog servers stating that the real server
         threshold has been reached for the concerned group."
    ::= { slbNewCfgEnhGroupEntry 10 }

slbNewCfgEnhGroupVipHealthCheck OBJECT-TYPE
    SYNTAX  INTEGER {
        enabled(1),
        disabled(2),
        unsupported(2147483647)
        }
    MAX-ACCESS  read-create
    STATUS  current
    DESCRIPTION
        "Enable or disable VIP health checking in DSR mode."
    ::= { slbNewCfgEnhGroupEntry 11 }

slbNewCfgEnhGroupIdsState OBJECT-TYPE
    SYNTAX  INTEGER {
        enabled(1),
        disabled(2),
        unsupported(2147483647)
        }
    MAX-ACCESS  read-create
    STATUS  current
    DESCRIPTION
        "Enable or disable intrusion detection."
    ::= { slbNewCfgEnhGroupEntry 12 }

slbNewCfgEnhGroupIdsPort OBJECT-TYPE
    SYNTAX  INTEGER (0..65534)
    MAX-ACCESS  read-create
    STATUS  current
    DESCRIPTION
        "The intrusion detection port. A value of 1 is invalid."
    ::= { slbNewCfgEnhGroupEntry 13 }

slbNewCfgEnhGroupDelete OBJECT-TYPE
    SYNTAX  INTEGER {
        other(1),
        delete(2),
        unsupported(2147483647)
        }
    MAX-ACCESS  read-create
    STATUS  current
    DESCRIPTION
        "By setting the value to delete(2), the entire group is deleted."
    ::= { slbNewCfgEnhGroupEntry 14 }

slbNewCfgEnhGroupIdsFlood OBJECT-TYPE
    SYNTAX  INTEGER {
        enabled(1),
        disabled(2),
        unsupported(2147483647)
        }
    MAX-ACCESS  read-create
    STATUS  current
    DESCRIPTION
        "Enable or disable intrusion detection group flood."
    ::= { slbNewCfgEnhGroupEntry 15 }

slbNewCfgEnhGroupMinmissHash OBJECT-TYPE
    SYNTAX  INTEGER {
        minmiss-24(1),
        minmiss-32(2),
        unsupported(2147483647)
        }
    MAX-ACCESS  read-create
    STATUS  current
    DESCRIPTION
        "24|32 number of sip bits used for minmisses hash in the
         new_configuration block."
    ::= { slbNewCfgEnhGroupEntry 16 }

slbNewCfgEnhGroupPhashMask OBJECT-TYPE
    SYNTAX  IpAddress
    MAX-ACCESS  read-create
    STATUS  current
    DESCRIPTION
        "IP address mask used by the persistent hash metric."
    ::= { slbNewCfgEnhGroupEntry 17 }

slbNewCfgEnhGroupRmetric OBJECT-TYPE
    SYNTAX  INTEGER {
        roundRobin(1),
        hash(2),
        leastConnections(3),
        unsupported(2147483647)
        }
    MAX-ACCESS  read-create
    STATUS  current
    DESCRIPTION
        "The metric used to select next rport in server."
    ::= { slbNewCfgEnhGroupEntry 18 }

slbNewCfgEnhGroupHealthCheckFormula OBJECT-TYPE
    SYNTAX  DisplayString (SIZE(0..31))
    MAX-ACCESS  read-create
    STATUS  current
    DESCRIPTION
        "The formula used to state the actual health of a virtual service.
         It allows user to use the symbols of '(', ')', '|', '&' to
         construct a formula to state the health of the server group.
         This string can take the following formats :
             '(1&2|3..)', '128' or 'none'
         Example: Consider a group with 4 reals 1, 2, 3, 4.  An example of
         a formula to mark the server group failed for the virtual server
         if 1 and 2 FAILED or 3 and 4 FAILED is (1|2)&(3|4)
         This formula will mark the virtual server UP, if 1 or 2 and 3 or 4
         are health checked sucessfully."
    ::= { slbNewCfgEnhGroupEntry 19 }

slbNewCfgEnhGroupOperatorAccess OBJECT-TYPE
    SYNTAX  INTEGER {
        enabled(1),
        disabled(2),
        unsupported(2147483647)
        }
    MAX-ACCESS  read-create
    STATUS  current
    DESCRIPTION
        "Enable or disable access to this group for operator."
    ::= { slbNewCfgEnhGroupEntry 20 }

slbNewCfgEnhGroupWlm OBJECT-TYPE
    SYNTAX  Integer32
    MAX-ACCESS  read-create
    STATUS  current
    DESCRIPTION
        "The Workload Manager for this Group."
    ::= { slbNewCfgEnhGroupEntry 21 }

slbNewCfgEnhGroupRadiusAuthenString OBJECT-TYPE
    SYNTAX  DisplayString (SIZE(0..32))
    MAX-ACCESS  read-write
    STATUS  current
    DESCRIPTION
        "The group RADIUS authentication string. The string is used for
         generating encrypted authentication string while doing RADIUS
         health check for this group radius servers."
    ::= { slbNewCfgEnhGroupEntry 22 }

slbNewCfgEnhGroupSecBackupGroup OBJECT-TYPE
    SYNTAX DisplayString (SIZE(1..255)) 
    MAX-ACCESS  read-create
    STATUS  current
    DESCRIPTION
        "The Secondary backup real server group for this group."
    ::= { slbNewCfgEnhGroupEntry 23 }

slbNewCfgEnhGroupSlowstart OBJECT-TYPE
    SYNTAX  Integer32
    MAX-ACCESS  read-create
    STATUS  current
    DESCRIPTION
        "The slow-start time for this group."
    ::= { slbNewCfgEnhGroupEntry 24 }

slbNewCfgEnhGroupMinThreshold OBJECT-TYPE
    SYNTAX  Integer32
    MAX-ACCESS  read-create
    STATUS  current
    DESCRIPTION
        "The minimum threshold value for this group."
    ::= { slbNewCfgEnhGroupEntry 25 }

slbNewCfgEnhGroupMaxThreshold OBJECT-TYPE
    SYNTAX  Integer32
    MAX-ACCESS  read-create
    STATUS  current
    DESCRIPTION
        "The maximum threshold value for this group."
    ::= { slbNewCfgEnhGroupEntry 26 }

slbNewCfgEnhGroupIpVer OBJECT-TYPE
    SYNTAX  INTEGER{
        ipv4(1),
        ipv6(2),
        mixed(3),
        unsupported(2147483647)
        }
    MAX-ACCESS  read-create
    STATUS  current
    DESCRIPTION
        "The type of real server group IP address."
    ::= { slbNewCfgEnhGroupEntry 27 }

slbNewCfgEnhGroupBackup OBJECT-TYPE
    SYNTAX  DisplayString (SIZE(0..255))
    MAX-ACCESS  read-only
    STATUS  current
    DESCRIPTION
        "The backup real group or real server for this group."
    ::= { slbNewCfgEnhGroupEntry 28 }

slbNewCfgEnhGroupBackupType OBJECT-TYPE
    SYNTAX  INTEGER {
        none(1),
        server(2),
        group(3),
        unsupported(2147483647)
        }
    MAX-ACCESS  read-create
    STATUS  current
    DESCRIPTION
        "Backup type of the real server group."
    ::= { slbNewCfgEnhGroupEntry 29 }

slbNewCfgEnhGroupHealthID OBJECT-TYPE
    SYNTAX  DisplayString (SIZE(0..128))
    MAX-ACCESS  read-write
    STATUS  current
    DESCRIPTION
        "The Advanced HC ID."
    ::= { slbNewCfgEnhGroupEntry 30 }

slbNewCfgEnhGroupPhashPrefixLength OBJECT-TYPE
    SYNTAX  INTEGER (1..128)
    MAX-ACCESS  read-create
    STATUS  current
    DESCRIPTION
        "Prefix length used by the persistent hash metric."
    ::= { slbNewCfgEnhGroupEntry 31 }

slbNewCfgEnhGroupType OBJECT-TYPE
    SYNTAX  INTEGER {
	local(0),
	wanlink(2),
        unsupported(2147483647)
	}
    MAX-ACCESS  read-write
    STATUS  current
    DESCRIPTION
        "Group type."
    ::= { slbNewCfgEnhGroupEntry 32 }

slbNewCfgEnhGroupCopy OBJECT-TYPE
    SYNTAX  DisplayString (SIZE(1..255))
    MAX-ACCESS  read-create
    STATUS  current
    DESCRIPTION
        "The alphanumeric index of the new copy to be created."
    ::= { slbNewCfgEnhGroupEntry 33 }

slbNewCfgEnhGroupIdsChain OBJECT-TYPE
    SYNTAX  INTEGER {
        enabled(1),
        disabled(2),
        unsupported(2147483647)
        }
    MAX-ACCESS  read-create
    STATUS  current
    DESCRIPTION
        "Enable or disable IDS group participation in inspection chain."
    ::= { slbNewCfgEnhGroupEntry 34 }

slbNewCfgEnhGroupSecType OBJECT-TYPE
    SYNTAX  INTEGER {
        none(1),
		virtual(2),
		layer(3),
		passive(4),
		l3sw(5),
        unsupported(2147483647)
	}
    MAX-ACCESS  read-write
    STATUS  current
    DESCRIPTION
        "The Group security device type." 
    ::= { slbNewCfgEnhGroupEntry 35 }


slbNewCfgEnhGroupSecDeviceFlag OBJECT-TYPE
	SYNTAX  INTEGER {
        none(1),
		security(2),
        unsupported(2147483647)
	} 
	MAX-ACCESS  read-only
    STATUS  current
    DESCRIPTION
        "The Group security device flag"
    ::= { slbNewCfgEnhGroupEntry 36 }

slbNewCfgEnhGroupMaxConEx OBJECT-TYPE
    SYNTAX  INTEGER {
        enabled(1),
        disabled(2),
        unsupported(2147483647)
        }
    MAX-ACCESS read-create
    STATUS  current
    DESCRIPTION
        "Enable or Disable override maximum connections limit."
    ::= { slbNewCfgEnhGroupEntry 37 }



-- SLB - Group Real Server Table (alphanumeric key indexed) - Current configuration
slbCurCfgEnhGroupRealServerTable OBJECT-TYPE
    SYNTAX  SEQUENCE OF SlbCurCfgEnhGroupRealServerEntry
    MAX-ACCESS  not-accessible
    STATUS  current
    DESCRIPTION
        "The table of real servers per group.
         Note:This mib is not supported for VX instance of Virtualization."
    ::= { realServerGroupCfg 9 }

slbCurCfgEnhGroupRealServerEntry OBJECT-TYPE
    SYNTAX  SlbCurCfgEnhGroupRealServerEntry
    MAX-ACCESS  not-accessible
    STATUS  current
    DESCRIPTION
        "A row in the Real server group table."
    INDEX   { slbCurCfgEnhRealServGroupIndex, slbCurCfgEnhGroupRealServIndex }
    ::= { slbCurCfgEnhGroupRealServerTable 1 }

SlbCurCfgEnhGroupRealServerEntry ::= SEQUENCE {
    slbCurCfgEnhRealServGroupIndex       DisplayString,
    slbCurCfgEnhGroupRealServIndex       DisplayString,
    slbCurCfgEnhGroupRealServerState     INTEGER
    }

slbCurCfgEnhRealServGroupIndex OBJECT-TYPE
    SYNTAX DisplayString (SIZE(1..255)) 
    MAX-ACCESS  read-only
    STATUS  current
    DESCRIPTION
        "The real server group index."
    ::= { slbCurCfgEnhGroupRealServerEntry 1 }

slbCurCfgEnhGroupRealServIndex OBJECT-TYPE
    SYNTAX DisplayString (SIZE(1..255)) 
    MAX-ACCESS  read-only
    STATUS  current
    DESCRIPTION
        "The real server index."
    ::= { slbCurCfgEnhGroupRealServerEntry 2 }

slbCurCfgEnhGroupRealServerState OBJECT-TYPE
    SYNTAX  INTEGER {
        enabled(1),
        disabled(2),
	shutdown-connection(3),
	shutdown-persistent-sessions(4),
        unsupported(2147483647)
        }
    MAX-ACCESS  read-only
    STATUS  current
    DESCRIPTION
        "Enable/disable a real server gracefully on a per group basis."
    ::= { slbCurCfgEnhGroupRealServerEntry 3 }

-- SLB - Group Real Server Table (alphanumeric key indexed) - New Configuration

slbNewCfgEnhGroupRealServerTable OBJECT-TYPE
    SYNTAX  SEQUENCE OF SlbNewCfgEnhGroupRealServerEntry
    MAX-ACCESS  not-accessible
    STATUS  current
    DESCRIPTION
        "The table of real server per group.
         Note:This mib is not supported for VX instance of Virtualization."
    ::= { realServerGroupCfg 10 }

slbNewCfgEnhGroupRealServerEntry OBJECT-TYPE
    SYNTAX  SlbNewCfgEnhGroupRealServerEntry
    MAX-ACCESS  not-accessible
    STATUS  current
    DESCRIPTION
        "A row in the Real server group table."
    INDEX   { slbNewCfgEnhRealServGroupIndex, slbNewCfgEnhGroupRealServIndex}
    ::= { slbNewCfgEnhGroupRealServerTable 1 }

SlbNewCfgEnhGroupRealServerEntry ::= SEQUENCE {
    slbNewCfgEnhRealServGroupIndex        DisplayString,
    slbNewCfgEnhGroupRealServIndex        DisplayString,
    slbNewCfgEnhGroupRealServerState      INTEGER
    }

slbNewCfgEnhRealServGroupIndex OBJECT-TYPE
    SYNTAX DisplayString (SIZE(1..255)) 
    MAX-ACCESS  read-only
    STATUS  current
    DESCRIPTION
        "The real server group index."
    ::= { slbNewCfgEnhGroupRealServerEntry 1 }

slbNewCfgEnhGroupRealServIndex OBJECT-TYPE
    SYNTAX DisplayString (SIZE(1..255)) 
    MAX-ACCESS  read-only
    STATUS  current
    DESCRIPTION
        "The real server index."
    ::= { slbNewCfgEnhGroupRealServerEntry 2 }

slbNewCfgEnhGroupRealServerState OBJECT-TYPE
    SYNTAX  INTEGER {
        enabled(1),
        disabled(2),
	shutdown-connection(3),
	shutdown-persistent-sessions(4),
        unsupported(2147483647)
        }
    MAX-ACCESS  read-create
    STATUS  current
    DESCRIPTION
        "Enable/disable a real server gracefully on a per group basis."
    ::= { slbNewCfgEnhGroupRealServerEntry 3 }

-- SLB - Group Real Servers association Table (alphanumeric key indexed)

slbEnhGroupRealServersTable OBJECT-TYPE
    SYNTAX  SEQUENCE OF SlbEnhGroupRealServersEntry
    MAX-ACCESS  not-accessible
    STATUS  current
    DESCRIPTION
        "The table of real server per group.
         Note:This mib is not supported for VX instance of Virtualization."
    ::= { realServerGroupCfg 11 }

slbEnhGroupRealServersEntry OBJECT-TYPE
    SYNTAX  SlbEnhGroupRealServersEntry
    MAX-ACCESS  not-accessible
    STATUS  current
    DESCRIPTION
        "A row in the Real server group table."
    INDEX   { slbEnhRealServerGroupIndex, slbEnhGroupRealServerIndex}
    ::= { slbEnhGroupRealServersTable 1 }

SlbEnhGroupRealServersEntry ::= SEQUENCE {
    slbEnhRealServerGroupIndex        DisplayString,
    slbEnhGroupRealServerIndex        DisplayString
    }

slbEnhRealServerGroupIndex OBJECT-TYPE
    SYNTAX DisplayString (SIZE(1..255))
    MAX-ACCESS  read-only
    STATUS  current
    DESCRIPTION
        "The real server group index."
    ::= { slbEnhGroupRealServersEntry 1 }

slbEnhGroupRealServerIndex OBJECT-TYPE
    SYNTAX DisplayString (SIZE(1..255))
    MAX-ACCESS  read-only
    STATUS  current
    DESCRIPTION
        "The real server index."
    ::= { slbEnhGroupRealServersEntry 2 }

-- Server load balancing - Virtual Server Table
slbVirtServerTableMaxSize OBJECT-TYPE
    SYNTAX  Integer32
    MAX-ACCESS  read-only
    STATUS  current
    DESCRIPTION
        "The maximum number of entries in SLB VirtServerTable.
         Note:This mib is not supported for VX instance of Virtualization."
    ::= { virtualServerCfg 1 }

slbCurCfgVirtServerTable OBJECT-TYPE
    SYNTAX  SEQUENCE OF SlbCurCfgVirtualServerEntry
    MAX-ACCESS  not-accessible
    STATUS  current
    DESCRIPTION
        "The table of virtual Servers.
         Note:This mib is not supported for VX instance of Virtualization."
    ::= { virtualServerCfg 2 }
 
slbCurCfgVirtualServerEntry OBJECT-TYPE
    SYNTAX  SlbCurCfgVirtualServerEntry
    MAX-ACCESS  not-accessible
    STATUS  current
    DESCRIPTION
        "A row in the virtual server table."
    INDEX   { slbCurCfgVirtServerIndex }
    ::= { slbCurCfgVirtServerTable 1 }
 
SlbCurCfgVirtualServerEntry ::= SEQUENCE {
    slbCurCfgVirtServerIndex     	Integer32,
    slbCurCfgVirtServerIpAddress 	IpAddress,
    slbCurCfgVirtServerLayer3Only    	INTEGER,
    slbCurCfgVirtServerState     	INTEGER,
    slbCurCfgVirtServerDname     	DisplayString,
    slbCurCfgVirtServerBwmContract	Integer32,
    slbCurCfgVirtServerWeight           INTEGER,
    slbCurCfgVirtServerAvail            INTEGER,
    slbCurCfgVirtServerRule             OCTET STRING,
    slbCurCfgVirtServerIpVer            INTEGER,
    slbCurCfgVirtServerIpv6Addr         DisplayString,
    slbCurCfgVirtServerVname     	DisplayString,
    slbCurCfgVirtServerCReset           INTEGER,
    slbCurCfgVirtServerSrcNetwork       DisplayString,
    slbCurCfgVirtServerNat              IpAddress,
    slbCurCfgVirtServerNat6             DisplayString,
    slbCurCfgVirtServerIsDnsSecVip      INTEGER
    }

slbCurCfgVirtServerIndex OBJECT-TYPE
    SYNTAX  Integer32
    MAX-ACCESS  read-only
    STATUS  current
    DESCRIPTION
        "Virtual Server Number" 
    ::= { slbCurCfgVirtualServerEntry 1 }

slbCurCfgVirtServerIpAddress OBJECT-TYPE
    SYNTAX  IpAddress
    MAX-ACCESS  read-only
    STATUS  current
    DESCRIPTION
        "IP address of the virtual server." 
    ::= { slbCurCfgVirtualServerEntry 2 }

slbCurCfgVirtServerLayer3Only OBJECT-TYPE 
    SYNTAX  INTEGER {
	layer3Only(1),
	disabled(2),
        unsupported(2147483647)
	}
    MAX-ACCESS  read-only 
    STATUS  current 
    DESCRIPTION 
        "Enable or disable layer3 only balancing."  
    ::= { slbCurCfgVirtualServerEntry 3 }

slbCurCfgVirtServerState OBJECT-TYPE 
    SYNTAX  INTEGER {
	enabled(2),
	disabled(3),
        unsupported(2147483647)
	}
    MAX-ACCESS  read-only 
    STATUS  current 
    DESCRIPTION 
        "Enable or disable the virtual server."  
    ::= { slbCurCfgVirtualServerEntry 4 }

slbCurCfgVirtServerDname OBJECT-TYPE 
    SYNTAX  DisplayString (SIZE(0..64))
    MAX-ACCESS  read-only 
    STATUS  current 
    DESCRIPTION 
        "The domain name of the virtual server."  
    ::= { slbCurCfgVirtualServerEntry 5 }

slbCurCfgVirtServerBwmContract OBJECT-TYPE
    SYNTAX  Integer32
    MAX-ACCESS  read-only
    STATUS  current
    DESCRIPTION
        "The default BW contract of virtual server."
    ::= { slbCurCfgVirtualServerEntry 6 }

slbCurCfgVirtServerWeight OBJECT-TYPE
    SYNTAX  INTEGER (1..48)
    MAX-ACCESS  read-only
    STATUS  current
    DESCRIPTION
        "The virtual server Global SLB weight."
    ::= { slbCurCfgVirtualServerEntry 7 }

slbCurCfgVirtServerAvail OBJECT-TYPE
    SYNTAX  INTEGER (1..48)
    MAX-ACCESS  read-only
    STATUS  current
    DESCRIPTION
        "The virtual server Global SLB availability."
    ::= { slbCurCfgVirtualServerEntry 8 }

slbCurCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbCurCfgVirtualServerEntry 9 }

slbCurCfgVirtServerVname OBJECT-TYPE 
    SYNTAX  DisplayString (SIZE(0..32))
    MAX-ACCESS  read-only 
    STATUS  current 
    DESCRIPTION 
        "The name of the virtual server."  
    ::= { slbCurCfgVirtualServerEntry 10 }


slbCurCfgVirtServerIpVer OBJECT-TYPE
    SYNTAX  INTEGER{
        ipv4(1),
        ipv6(2),
        unsupported(2147483647)
        }
    MAX-ACCESS  read-only
    STATUS  current
    DESCRIPTION
        "The type of IP address."
    ::= { slbCurCfgVirtualServerEntry 11 }

slbCurCfgVirtServerIpv6Addr OBJECT-TYPE
    SYNTAX   DisplayString (SIZE(0..40))
    MAX-ACCESS  read-only
    STATUS  current
    DESCRIPTION
        "The IPv6 address of the virtual server. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbCurCfgVirtualServerEntry 12 }


slbCurCfgVirtServerCReset OBJECT-TYPE
    SYNTAX  INTEGER{
        enabled(1),
        disabled(2),
        unsupported(2147483647)
        }
    MAX-ACCESS  read-only
    STATUS  current
    DESCRIPTION
        "Enable/disable client connection reset for invalid VPORT."
    ::= { slbCurCfgVirtualServerEntry 13 }

slbCurCfgVirtServerSrcNetwork OBJECT-TYPE
    SYNTAX  DisplayString  (SIZE(0..32))
    MAX-ACCESS  read-only
    STATUS  current
    DESCRIPTION
        "Source Network Classifier of the virtual server."
    ::= { slbCurCfgVirtualServerEntry 14 }

slbCurCfgVirtServerNat OBJECT-TYPE
    SYNTAX  IpAddress
    MAX-ACCESS  read-only
    STATUS  current
    DESCRIPTION
        "IP address of the NAT." 
    ::= { slbCurCfgVirtualServerEntry 15 }

slbCurCfgVirtServerNat6 OBJECT-TYPE
    SYNTAX   DisplayString (SIZE(0..40))
    MAX-ACCESS  read-only
    STATUS  current
    DESCRIPTION
        "The IPv6 address of the NAT. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbCurCfgVirtualServerEntry 16 }

slbCurCfgVirtServerIsDnsSecVip OBJECT-TYPE
    SYNTAX  INTEGER {
        no(0),
        yes(1),
        unsupported(2147483647)
    }
    MAX-ACCESS  read-only
    STATUS  current
    DESCRIPTION
        "It returns Yes(1) if virtual server is a DNS Responder VIP, else returns no(0).
         This mib is added for Vision purpose."
    ::= { slbCurCfgVirtualServerEntry 17 }

-- Server load balancing - Virtual Server Table

slbNewCfgVirtServerTable OBJECT-TYPE
    SYNTAX  SEQUENCE OF SlbNewCfgVirtualServerEntry
    MAX-ACCESS  not-accessible
    STATUS  current
    DESCRIPTION
        "The table of virtual Servers.
         Note:This mib is not supported for VX instance of Virtualization."
    ::= { virtualServerCfg 3 }

slbNewCfgVirtualServerEntry OBJECT-TYPE
    SYNTAX  SlbNewCfgVirtualServerEntry
    MAX-ACCESS  not-accessible
    STATUS  current
    DESCRIPTION
        "A row in the virtual server table."
    INDEX   { slbNewCfgVirtServerIndex }
    ::= { slbNewCfgVirtServerTable 1 }
 
SlbNewCfgVirtualServerEntry ::= SEQUENCE {
    slbNewCfgVirtServerIndex   		Integer32,
    slbNewCfgVirtServerIpAddress 	IpAddress,
    slbNewCfgVirtServerLayer3Only   	INTEGER,
    slbNewCfgVirtServerState     	INTEGER,
    slbNewCfgVirtServerDname     	DisplayString,
    slbNewCfgVirtServerBwmContract	Integer32,
    slbNewCfgVirtServerDelete    	INTEGER,
    slbNewCfgVirtServerWeight           INTEGER,
    slbNewCfgVirtServerAvail            INTEGER,
    slbNewCfgVirtServerRule             OCTET STRING,
    slbNewCfgVirtServerAddRule          Integer32,
    slbNewCfgVirtServerRemoveRule       Integer32,
    slbNewCfgVirtServerIpVer            INTEGER,
    slbNewCfgVirtServerIpv6Addr         DisplayString,
    slbNewCfgVirtServerVname     	DisplayString,
    slbNewCfgVirtServerFreeServiceIdx   INTEGER,
    slbNewCfgVirtServerCReset           INTEGER,
    slbNewCfgVirtServerSrcNetwork       DisplayString,
    slbNewCfgVirtServerNat              IpAddress,
    slbNewCfgVirtServerNat6             DisplayString,
    slbNewCfgVirtServerIsDnsSecVip      INTEGER
    }

slbNewCfgVirtServerIndex OBJECT-TYPE
    SYNTAX  Integer32
    MAX-ACCESS  read-only
    STATUS  current
    DESCRIPTION
        "The Virtual Server Number" 
    ::= { slbNewCfgVirtualServerEntry 1 }

slbNewCfgVirtServerIpAddress OBJECT-TYPE
    SYNTAX  IpAddress
    MAX-ACCESS  read-create
    STATUS  current
    DESCRIPTION
        "IP address of the virtual server." 
    ::= { slbNewCfgVirtualServerEntry 2 }

slbNewCfgVirtServerLayer3Only OBJECT-TYPE 
    SYNTAX  INTEGER {
        layer3Only(1),
	disabled(2),
        unsupported(2147483647)
	}
    MAX-ACCESS  read-create 
    STATUS  current 
    DESCRIPTION 
        "Enable or disable layer3 only balancing."  
    ::= { slbNewCfgVirtualServerEntry 3 }

slbNewCfgVirtServerState OBJECT-TYPE 
    SYNTAX  INTEGER {
	enabled(2),
	disabled(3),
        unsupported(2147483647)
	}
    MAX-ACCESS  read-create 
    STATUS  current 
    DESCRIPTION 
        "Enable or disable the virtual server."  
    ::= { slbNewCfgVirtualServerEntry 4 }

slbNewCfgVirtServerDname OBJECT-TYPE 
    SYNTAX  DisplayString (SIZE(0..64))
    MAX-ACCESS  read-create 
    STATUS  current 
    DESCRIPTION 
        "The domain name of the virtual server."  
    ::= { slbNewCfgVirtualServerEntry 6 }

slbNewCfgVirtServerBwmContract OBJECT-TYPE 
    SYNTAX  Integer32
    MAX-ACCESS  read-create 
    STATUS  current 
    DESCRIPTION 
        "The default BW contract number of the virtual server."
    ::= { slbNewCfgVirtualServerEntry 7 }

slbNewCfgVirtServerDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgVirtualServerEntry 8 }

slbNewCfgVirtServerWeight OBJECT-TYPE
    SYNTAX  INTEGER (1..48)
    MAX-ACCESS  read-create
    STATUS  current
    DESCRIPTION
        "The virtual server Global SLB weight."
    ::= { slbNewCfgVirtualServerEntry 9 }

slbNewCfgVirtServerAvail OBJECT-TYPE
    SYNTAX  INTEGER (1..48)
    MAX-ACCESS  read-create
    STATUS  current
    DESCRIPTION
        "The virtual server Global SLB availability."
    ::= { slbNewCfgVirtualServerEntry 10 }

slbNewCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbNewCfgVirtualServerEntry 11 }

slbNewCfgVirtServerAddRule OBJECT-TYPE
    SYNTAX  Integer32
    MAX-ACCESS  read-create
    STATUS  current
    DESCRIPTION
        "The rule to be added to the domain. When read, 0 is returned."
    ::= { slbNewCfgVirtualServerEntry 12 }

slbNewCfgVirtServerRemoveRule OBJECT-TYPE
    SYNTAX  Integer32
    MAX-ACCESS  read-create
    STATUS  current
    DESCRIPTION
        "The rule to be removed from the domain. When read, 0 is returned."
    ::= { slbNewCfgVirtualServerEntry 13 }

slbNewCfgVirtServerVname OBJECT-TYPE 
    SYNTAX  DisplayString (SIZE(0..32))
    MAX-ACCESS  read-create 
    STATUS  current 
    DESCRIPTION 
        "The name of the virtual server."  
    ::= { slbNewCfgVirtualServerEntry 14 }


slbNewCfgVirtServerIpVer OBJECT-TYPE
    SYNTAX  INTEGER{
        ipv4(1),
        ipv6(2),
        unsupported(2147483647)
        }
    MAX-ACCESS read-create
    STATUS  current
    DESCRIPTION
        "The type of IP address."
    ::= { slbNewCfgVirtualServerEntry 15 }

slbNewCfgVirtServerIpv6Addr OBJECT-TYPE
    SYNTAX  DisplayString  (SIZE(0..40))
    MAX-ACCESS read-create
    STATUS  current
    DESCRIPTION
        "The IPv6 address of the virtual server. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbNewCfgVirtualServerEntry 16 }


slbNewCfgVirtServerFreeServiceIdx OBJECT-TYPE
    SYNTAX  INTEGER(0..8)
    MAX-ACCESS  read-only
    STATUS  current
    DESCRIPTION
        "The first free service index number of the virtual server.
         Value 0 will be returned when all 8 virtual services are 
         configured for a virtual server."
    ::= { slbNewCfgVirtualServerEntry 17 }

slbNewCfgVirtServerCReset OBJECT-TYPE
    SYNTAX  INTEGER{
        enabled(1),
        disabled(2),
        unsupported(2147483647)
        }
    MAX-ACCESS  read-create
    STATUS  current
    DESCRIPTION
        "Enable/disable client connection reset for invalid VPORT."
    ::= { slbNewCfgVirtualServerEntry 18 }

slbNewCfgVirtServerSrcNetwork OBJECT-TYPE
    SYNTAX  DisplayString  (SIZE(0..32))
    MAX-ACCESS  read-create
    STATUS  current
    DESCRIPTION
        "Source Network Classifier of the virtual server."
    ::= { slbNewCfgVirtualServerEntry 19 }

slbNewCfgVirtServerNat OBJECT-TYPE
    SYNTAX  IpAddress
    MAX-ACCESS  read-write
    STATUS  current
    DESCRIPTION
        "IP address of the NAT." 
    ::= { slbNewCfgVirtualServerEntry 20 }

slbNewCfgVirtServerNat6 OBJECT-TYPE
    SYNTAX   DisplayString (SIZE(0..40))
    MAX-ACCESS  read-write
    STATUS  current
    DESCRIPTION
        "The IPv6 address of the NAT. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbNewCfgVirtualServerEntry 21 }


slbNewCfgVirtServerIsDnsSecVip OBJECT-TYPE
    SYNTAX  INTEGER {
        no(0),
        yes(1),
        unsupported(2147483647)
    }
    MAX-ACCESS  read-only
    STATUS  current
    DESCRIPTION
        "This mib returns Yes(1) if virtual server is a DNS Responder VIP, else returns no(0)"
    ::= { slbNewCfgVirtualServerEntry 22 }


-- Server load balancing - Virtual Services Table 
slbVirtServicesTableMaxSize OBJECT-TYPE
    SYNTAX  Integer32 
    MAX-ACCESS  read-only 
    STATUS  current 
    DESCRIPTION 
        "The maximum number of entries in SLB Virtual Services Table.
         Note:This mib is not supported for VX instance of Virtualization." 
    ::= { virtualServerCfg 4 }

slbCurCfgVirtServicesTable OBJECT-TYPE
    SYNTAX  SEQUENCE OF SlbCurCfgVirtServicesEntry
    MAX-ACCESS  not-accessible
    STATUS  current
    DESCRIPTION
        "The table of virtual services.
         Note:This mib is not supported for VX instance of Virtualization."
    ::= { virtualServerCfg 5 }

slbCurCfgVirtServicesEntry OBJECT-TYPE
    SYNTAX  SlbCurCfgVirtServicesEntry
    MAX-ACCESS  not-accessible
    STATUS  current
    DESCRIPTION
        "A row in the virtual services table."
    INDEX   { slbCurCfgVirtServIndex, slbCurCfgVirtServiceIndex }
    ::= { slbCurCfgVirtServicesTable 1 }

SlbCurCfgVirtServicesEntry ::= SEQUENCE {
    slbCurCfgVirtServIndex            Integer32,
    slbCurCfgVirtServiceIndex         Integer32,
    slbCurCfgVirtServiceVirtPort      INTEGER,
    slbCurCfgVirtServiceRealGroup     Integer32,
    slbCurCfgVirtServiceRealPort      INTEGER,
    slbCurCfgVirtServiceUDPBalance    INTEGER,
    slbCurCfgVirtServiceHname         DisplayString,
    slbCurCfgVirtServiceBwmContract   Integer32,
    slbCurCfgVirtServiceDirServerRtn  INTEGER,
    slbCurCfgVirtServiceRtspUrlParse  INTEGER,
    slbCurCfgVirtServiceFtpParsing    INTEGER,
    slbCurCfgVirtServiceRemapUDPFrags INTEGER,
    slbCurCfgVirtServiceDnsSlb        INTEGER,
    slbCurCfgVirtServiceResponseCount INTEGER,
    slbCurCfgVirtServicePBind         INTEGER,
    slbCurCfgVirtServiceCname         DisplayString,
    slbCurCfgVirtServiceCoffset       INTEGER,
    slbCurCfgVirtServiceClength       INTEGER,
    slbCurCfgVirtServiceUriCookie     INTEGER,
    slbCurCfgVirtServiceCExpire       DisplayString,
    slbCurCfgVirtServiceCookieMode    INTEGER,
    slbCurCfgVirtServiceDBind         INTEGER,
    slbCurCfgVirtServiceHttpSlb       INTEGER,
    slbCurCfgVirtServiceHttpSlbOption INTEGER,
    slbCurCfgVirtServiceHttpSlb2      INTEGER,
    slbCurCfgVirtServiceHttpHdrName   DisplayString,
    slbCurCfgVirtServiceUrlHashLen    INTEGER,
    slbCurCfgVirtServiceCookieDname   INTEGER,
    slbCurCfgVirtServiceClsRST        INTEGER,
    slbCurCfgVirtServiceDirect        INTEGER,
    slbCurCfgVirtServiceThash         INTEGER,
    slbCurCfgVirtServiceLdapreset     INTEGER,
    slbCurCfgVirtServiceLdapslb       INTEGER,
    slbCurCfgVirtServiceSip           INTEGER,
    slbCurCfgVirtServiceXForwardedFor INTEGER,
    slbCurCfgVirtServiceHttpRedir     INTEGER,
    slbCurCfgVirtServicePbindRport    INTEGER,
    slbCurCfgVirtServiceEgressPip     INTEGER,
    slbCurCfgVirtServiceWts           INTEGER,
    slbCurCfgVirtServiceTimeOut       INTEGER,
    slbCurCfgVirtServiceSoftGrid      INTEGER,
    slbCurCfgVirtServiceSessionMirror INTEGER,
    slbCurCfgVirtServiceSdpNat        INTEGER,
    slbCurCfgVirtServiceConnPooling   INTEGER,
    slbCurCfgVirtPersistentTimeOut    INTEGER,
    slbCurCfgVirtServiceUhash         INTEGER,
    slbCurCfgVirtServiceProxyIpMode   INTEGER,
    slbCurCfgVirtServiceProxyIpAddr   IpAddress,
    slbCurCfgVirtServiceProxyIpMask   IpAddress,
    slbCurCfgVirtServiceProxyIpv6Addr   DisplayString,
    slbCurCfgVirtServiceProxyIpv6Prefix   INTEGER,
    slbCurCfgVirtServiceProxyIpPersistency   INTEGER,
    slbCurCfgVirtServiceProxyIpNWclass   DisplayString,
    slbCurCfgVirtServiceProxyIpv6NWclass   DisplayString,
    slbCurCfgVirtServiceProxyIpNWclassPersistency   INTEGER, 
    slbCurCfgVirtServiceHashLen       INTEGER,
    slbCurCfgVirtServiceApm           INTEGER,
    slbCurCfgVirtServiceNonHTTP       INTEGER
}

slbCurCfgVirtServIndex OBJECT-TYPE
    SYNTAX  Integer32
    MAX-ACCESS  read-only
    STATUS  current
    DESCRIPTION
        "The number of the virtual server." 
    ::= { slbCurCfgVirtServicesEntry 1 }

slbCurCfgVirtServiceIndex OBJECT-TYPE 
    SYNTAX  Integer32 
    MAX-ACCESS  read-only 
    STATUS  current 
    DESCRIPTION 
        "The service index. This has no external meaning" 
    ::= { slbCurCfgVirtServicesEntry 2 }

slbCurCfgVirtServiceVirtPort OBJECT-TYPE  
    SYNTAX  INTEGER (1..65534)
    MAX-ACCESS  read-only  
    STATUS  current  
    DESCRIPTION 
        "The layer4 virtual port number of the service."  
    ::= { slbCurCfgVirtServicesEntry 3 } 

slbCurCfgVirtServiceRealGroup OBJECT-TYPE   
    SYNTAX  Integer32   
    MAX-ACCESS  read-only   
    STATUS  current   
    DESCRIPTION 
        "The real server group number for this service."   
    ::= { slbCurCfgVirtServicesEntry 4 }

slbCurCfgVirtServiceRealPort OBJECT-TYPE   
    SYNTAX  INTEGER (0..65534)
    MAX-ACCESS  read-only   
    STATUS  current   
    DESCRIPTION 
        "The layer4 real port number of the service."   
    ::= { slbCurCfgVirtServicesEntry 5 }

slbCurCfgVirtServiceUDPBalance OBJECT-TYPE   
    SYNTAX  INTEGER    {
	udp(2),
	tcp(3),
	stateless(4),
        tcpAndUdp(5),
        sctp(6),
        unsupported(2147483647)
	}
    MAX-ACCESS  read-only   
    STATUS  current   
    DESCRIPTION 
        "Set protocol for the virtual service to
         UDP or TCP or SCTP or tcpAndUdp or stateless.
         tcpAndUdp is applicable only to ip service."
    ::= { slbCurCfgVirtServicesEntry 6 }

slbCurCfgVirtServiceHname OBJECT-TYPE 
    SYNTAX  DisplayString (SIZE(0..34))
    MAX-ACCESS  read-only 
    STATUS  current 
    DESCRIPTION 
        "The host name of the virtual service."  
    ::= { slbCurCfgVirtServicesEntry 7 }

slbCurCfgVirtServiceBwmContract OBJECT-TYPE   
    SYNTAX  Integer32   
    MAX-ACCESS  read-only   
    STATUS  current   
    DESCRIPTION 
        "The BWM contract number for this service."   
    ::= { slbCurCfgVirtServicesEntry 8 }

slbCurCfgVirtServiceDirServerRtn OBJECT-TYPE   
    SYNTAX  INTEGER {
	enabled(1),
	disabled(2),
        unsupported(2147483647)
	}
    MAX-ACCESS  read-only   
    STATUS  current   
    DESCRIPTION 
        "Enable or disable direct server return feature. To translate only 
         MAC addresses in performing server load balancing when enabled.
         This allow servers to return directly to client since IP addresses 
         have not been changed."
    ::= { slbCurCfgVirtServicesEntry 9 }

slbCurCfgVirtServiceRtspUrlParse OBJECT-TYPE   
    SYNTAX  INTEGER {
        none(1),
        l4hash(2),
        hash(3),
        patternMatch(4),
        unsupported(2147483647)
	}
    MAX-ACCESS  read-only
    STATUS  current   
    DESCRIPTION 
        "Select RTSP URL load balancing type."
    ::= { slbCurCfgVirtServicesEntry 10 }


slbCurCfgVirtServiceDBind OBJECT-TYPE   
    SYNTAX  INTEGER {
	enabled(1),
	disabled(2),
	forceproxy(3),
        unsupported(2147483647)
	}
    MAX-ACCESS  read-only
    STATUS  current   
    DESCRIPTION 
        "Enable/disable/forceproxy delayed binding."
    ::= { slbCurCfgVirtServicesEntry 11 }


slbCurCfgVirtServiceFtpParsing OBJECT-TYPE
    SYNTAX  INTEGER {
	enabled(1),
	disabled(2),
        unsupported(2147483647)
	}
    MAX-ACCESS  read-only
    STATUS  current
    DESCRIPTION
        "Enable or Disable the ftp parsing for the virtual service."
    ::= { slbCurCfgVirtServicesEntry 12 }

slbCurCfgVirtServiceRemapUDPFrags OBJECT-TYPE   
    SYNTAX INTEGER {
        enabled(1),
        disabled(2),
        unsupported(2147483647)
        }
    MAX-ACCESS read-only   
    STATUS current   
    DESCRIPTION 
        "Enable or disable remapping UDP server fragments"   
    ::= { slbCurCfgVirtServicesEntry 13 }

slbCurCfgVirtServiceDnsSlb OBJECT-TYPE   
    SYNTAX  INTEGER {
        enabled(1),
	disabled(2),
        unsupported(2147483647)
	}
    MAX-ACCESS  read-only   
    STATUS  current   
    DESCRIPTION 
        "Enable or disable DNS query load balancing."
    ::= { slbCurCfgVirtServicesEntry 14 }

slbCurCfgVirtServiceResponseCount OBJECT-TYPE 
    SYNTAX  INTEGER (1..16)
    MAX-ACCESS  read-only 
    STATUS  current 
    DESCRIPTION 
        "The number of cookie search response count."
    ::= { slbCurCfgVirtServicesEntry 15 }

slbCurCfgVirtServicePBind OBJECT-TYPE   
    SYNTAX  INTEGER {
	clientip(2),
	disabled(3),
	sslid(4),
        cookie(5),
        unsupported(2147483647)
	}
    MAX-ACCESS  read-only   
    STATUS  current   
    DESCRIPTION 
        "Enable or disable persistent bindings for the virtual port."
    ::= { slbCurCfgVirtServicesEntry 16 }

slbCurCfgVirtServiceCname OBJECT-TYPE 
    SYNTAX  DisplayString (SIZE(0..20))
    MAX-ACCESS  read-only 
    STATUS  current 
    DESCRIPTION 
        "The cookie name of the virtual server used for cookie load balance."  
    ::= { slbCurCfgVirtServicesEntry 17 }

slbCurCfgVirtServiceCoffset OBJECT-TYPE
    SYNTAX  INTEGER (1..64)
    MAX-ACCESS  read-only 
    STATUS  current
    DESCRIPTION
        "The starting byte offset of the cookie value." 
    ::= { slbCurCfgVirtServicesEntry 18 }

slbCurCfgVirtServiceClength OBJECT-TYPE
    SYNTAX  INTEGER (1..64)
    MAX-ACCESS  read-only
    STATUS  current
    DESCRIPTION
        "The number of bytes to extract from the cookie value." 
    ::= { slbCurCfgVirtServicesEntry 19 }

slbCurCfgVirtServiceUriCookie OBJECT-TYPE 
    SYNTAX  INTEGER {
	enabled(1),
	disabled(2),
        unsupported(2147483647)
	}
    MAX-ACCESS  read-only 
    STATUS  current 
    DESCRIPTION 
        "Enable or disable cookie search in URI"  
    ::= { slbCurCfgVirtServicesEntry 20}

slbCurCfgVirtServiceCExpire OBJECT-TYPE 
    SYNTAX  DisplayString (SIZE(0..20))
    MAX-ACCESS  read-only 
    STATUS  current 
    DESCRIPTION 
        "The cookie expire of the virtual server used for insert cookie load
         balance depending on the mode it has the following format 
         <MM/dd/yy[@hh:mm]> absolute mode or <days[:hours[:minutes]]>
         for relative mode."  
    ::= { slbCurCfgVirtServicesEntry 21 }

slbCurCfgVirtServiceCookieMode OBJECT-TYPE   
    SYNTAX INTEGER {
        rewrite(1),
        passive(2),
	insert(3),
	disabled(4),
        unsupported(2147483647)
        }
    MAX-ACCESS read-only 
    STATUS current   
    DESCRIPTION 
        "Select cookie persistence mode."
    ::= { slbCurCfgVirtServicesEntry 22 }

slbCurCfgVirtServiceHttpSlb OBJECT-TYPE   
    SYNTAX  INTEGER {
	disabled(1),
        urlslb(2),
        urlhash(3),
        cookie(4),
        host(5),
        browser(6),
        others(7),
        headerhash(8),
	version(9),
        unsupported(2147483647)
	}
    MAX-ACCESS  read-only   
    STATUS  current   
    DESCRIPTION 
        "Select HTTP server loadbalancing for the virtual port."   
    ::= { slbCurCfgVirtServicesEntry 23 }

slbCurCfgVirtServiceHttpSlbOption OBJECT-TYPE   
    SYNTAX  INTEGER {
	and(1),
        or(2),
        none(3),
        unsupported(2147483647)
	}
    MAX-ACCESS  read-only   
    STATUS  current   
    DESCRIPTION 
        "Select HTTP server loadbalancing for the virtual port."   
    ::= { slbCurCfgVirtServicesEntry 24 }

slbCurCfgVirtServiceHttpSlb2 OBJECT-TYPE   
    SYNTAX  INTEGER {
	disabled(1),
        urlslb(2),
        urlhash(3),
        cookie(4),
        host(5),
        browser(6),
        others(7),
        headerhash(8),
	version(9),
        unsupported(2147483647)
	}
    MAX-ACCESS  read-only   
    STATUS  current   
    DESCRIPTION 
        "Select HTTP server loadbalancing for the virtual port."   
    ::= { slbCurCfgVirtServicesEntry 25 }

slbCurCfgVirtServiceHttpHdrName OBJECT-TYPE 
    SYNTAX  DisplayString  (SIZE(0..32))
    MAX-ACCESS  read-only 
    STATUS  current 
    DESCRIPTION 
        "The HTTP header name of the virtual server."
    ::= { slbCurCfgVirtServicesEntry 26 }

slbCurCfgVirtServiceUrlHashLen OBJECT-TYPE 
    SYNTAX  INTEGER (0..255)
    MAX-ACCESS  read-only 
    STATUS  current 
    DESCRIPTION 
        "The number of bytes used to hash onto server, A zero means
         URL hashing disabled."
    ::= { slbCurCfgVirtServicesEntry 27}

slbCurCfgVirtServiceDirect OBJECT-TYPE   
    SYNTAX  INTEGER {
        enabled(1),
	disabled(2),
        unsupported(2147483647)
	}
    MAX-ACCESS  read-only   
    STATUS  current   
    DESCRIPTION 
        "Enable or disable DAM for this service." 
    ::= { slbCurCfgVirtServicesEntry 28 }

slbCurCfgVirtServiceThash OBJECT-TYPE   
    SYNTAX  INTEGER {
        sip(1),
        sip-sport(2),
        unsupported(2147483647)
        }
    MAX-ACCESS  read-only
    STATUS  current   
    DESCRIPTION 
        "Set hash parameter."
    ::= { slbCurCfgVirtServicesEntry 29 }

slbCurCfgVirtServiceLdapreset OBJECT-TYPE 
    SYNTAX  INTEGER {
        enabled(1),
        disabled(2),
        unsupported(2147483647)
        }
    MAX-ACCESS  read-only 
    STATUS  current 
    DESCRIPTION 
        "Enable or disable LDAP Server Reset"  
    ::= { slbCurCfgVirtServicesEntry 30 }

slbCurCfgVirtServiceLdapslb OBJECT-TYPE 
    SYNTAX  INTEGER {
        enabled(1),
        disabled(2),
        unsupported(2147483647)
        }
    MAX-ACCESS  read-only 
    STATUS  current 
    DESCRIPTION 
        "Enable or disable LDAP Server load balancing"  
    ::= { slbCurCfgVirtServicesEntry 31 }

slbCurCfgVirtServiceSip OBJECT-TYPE   
    SYNTAX  INTEGER {
        enabled(1),
	disabled(2),
        unsupported(2147483647)
	}
    MAX-ACCESS  read-only   
    STATUS  current   
    DESCRIPTION 
        "Enable/disable SIP load balancing."
    ::= { slbCurCfgVirtServicesEntry 32 }

slbCurCfgVirtServiceXForwardedFor OBJECT-TYPE   
    SYNTAX  INTEGER {
        enabled(1),
	disabled(2),
        unsupported(2147483647)
	}
    MAX-ACCESS  read-only
    STATUS  current   
    DESCRIPTION 
        "Enable/disable X-Forwarded-For for proxy mode."
    ::= { slbCurCfgVirtServicesEntry 33 }

slbCurCfgVirtServiceHttpRedir OBJECT-TYPE
    SYNTAX  INTEGER {
        enabled(1),
        disabled(2),
        unsupported(2147483647)
        }
    MAX-ACCESS  read-only
    STATUS  current
    DESCRIPTION
        "Enable/disable HTTP/HTTPS redirect for GSLB."
    ::= { slbCurCfgVirtServicesEntry 34 }

slbCurCfgVirtServicePbindRport OBJECT-TYPE   
    SYNTAX  INTEGER {
        enabled(1),
	disabled(2),
        unsupported(2147483647)
	}
    MAX-ACCESS  read-only
    STATUS  current   
    DESCRIPTION 
        "Enable or disable use of rport in the session lookup for a persistent
         session."
    ::= { slbCurCfgVirtServicesEntry 35 }
    
slbCurCfgVirtServiceEgressPip OBJECT-TYPE   
    SYNTAX  INTEGER {
        enabled(1),
	disabled(2),
        unsupported(2147483647)
	}
    MAX-ACCESS  read-only
    STATUS  current   
    DESCRIPTION 
        "Enable/disable pip selection based on egress port/vlan."
    ::= { slbCurCfgVirtServicesEntry 36 }

slbCurCfgVirtServiceCookieDname OBJECT-TYPE
    SYNTAX INTEGER {
        enabled(1),
        disabled(2),
        unsupported(2147483647)
        }
    MAX-ACCESS read-only
    STATUS current
    DESCRIPTION
        "Select dname for insert cookie persistence mode."
    ::= { slbCurCfgVirtServicesEntry 37 }
    
slbCurCfgVirtServiceWts OBJECT-TYPE
    SYNTAX INTEGER {
        enabled(1),
        disabled(2),
        unsupported(2147483647)
        }
    MAX-ACCESS read-only
    STATUS current
    DESCRIPTION
        "Enable or disable WTS loadbalancing and persistence."
    ::= { slbCurCfgVirtServicesEntry 38 }

slbCurCfgVirtServiceUhash OBJECT-TYPE
    SYNTAX INTEGER {
        enabled(1),
        disabled(2),
        unsupported(2147483647)
        }
    MAX-ACCESS read-only
    STATUS current
    DESCRIPTION
        "Enable when there is no Session Directory server."
    ::= { slbCurCfgVirtServicesEntry 39 }


slbCurCfgVirtServiceTimeOut OBJECT-TYPE
    SYNTAX  INTEGER (0..32768)
    MAX-ACCESS  read-only
    STATUS  current
    DESCRIPTION
        "The maximum number of minutes an inactive connection remains open."
    ::= { slbCurCfgVirtServicesEntry 40 }

slbCurCfgVirtServiceSessionMirror OBJECT-TYPE
    SYNTAX  INTEGER {
        enabled(1),
        disabled(2),
        unsupported(2147483647)
        }
    MAX-ACCESS  read-only
    STATUS  current
    DESCRIPTION
        "Enable/disable session mirroring."
    ::= { slbCurCfgVirtServicesEntry 42 }

slbCurCfgVirtServiceSoftGrid OBJECT-TYPE
    SYNTAX  INTEGER {
        enabled(1),
        disabled(2),
        unsupported(2147483647)
        }
    MAX-ACCESS  read-only
    STATUS  current
    DESCRIPTION
        "Enable/disable softgrid load balancing."
    ::= { slbCurCfgVirtServicesEntry 43 }

slbCurCfgVirtServiceSdpNat OBJECT-TYPE
    SYNTAX  INTEGER {
        enabled(1),
        disabled(2),
        unsupported(2147483647)
        }
    MAX-ACCESS  read-only
    STATUS  current
    DESCRIPTION
        "Enable/disable SIP Media portal NAT."
    ::= { slbCurCfgVirtServicesEntry 41 }

slbCurCfgVirtServiceConnPooling OBJECT-TYPE
    SYNTAX  INTEGER {
        enabled(1),
            disabled(2),
        unsupported(2147483647)
    }
    MAX-ACCESS  read-only
    STATUS  current
    DESCRIPTION
        "Enable/disable connection pooling for HTTP traffic."
    ::= { slbCurCfgVirtServicesEntry 44 }

slbCurCfgVirtPersistentTimeOut OBJECT-TYPE
    SYNTAX  INTEGER (0..32768)
    MAX-ACCESS  read-only
    STATUS  current
    DESCRIPTION
        "The maximum number of minutes a persistent session should exist."
    ::= { slbCurCfgVirtServicesEntry 45 }

--Proxy IP Cur config start
slbCurCfgVirtServiceProxyIpMode OBJECT-TYPE   
    SYNTAX INTEGER {
        ingress(0),
	 egress(1),
	 address(2),
	 nwclss(3),
        disable(4),
        unsupported(2147483647)
        }
    MAX-ACCESS  read-only
    STATUS  current
    DESCRIPTION
        " the configured Proxy IP mode, default is ingress "
    ::= { slbCurCfgVirtServicesEntry 46 }

    slbCurCfgVirtServiceProxyIpAddr OBJECT-TYPE
    SYNTAX  IpAddress
    MAX-ACCESS  read-only
    STATUS  current
    DESCRIPTION
        "This object ID shows current configured IPv4 PIP address. 
		Returns 0 when slbCurCfgVirtServiceProxyIpMode is not set to address.
		If neither of the addresses (v4 & v6) are configured or are subnets, the persistency
		value is disable." 
    ::= { slbCurCfgVirtServicesEntry 47 }

   slbCurCfgVirtServiceProxyIpMask OBJECT-TYPE
    SYNTAX  IpAddress
    MAX-ACCESS  read-only
    STATUS  current
    DESCRIPTION
        "This object ID  shows current configured  IPv4 PIP Mask.
		Returns 0 when slbCurCfgVirtServiceProxyIpMode is not set to address.
		If neither of the addresses (v4 & v6) are configured or are subnets, the persistency
		value is disable." 
    ::= { slbCurCfgVirtServicesEntry 48 }

    slbCurCfgVirtServiceProxyIpv6Addr OBJECT-TYPE
    SYNTAX  DisplayString (SIZE(0..40))
    MAX-ACCESS  read-only
    STATUS  current
    DESCRIPTION
        "This object ID shows current configured IPv6 PIP address. 
		Address should be 4-byte hexadecimal colon notation.
		Valid IPv6 address should be in any of the following forms
		       xxxx:xxxx:xxxx:xxxx:xxxx:xxxx:xxxx:xxxx or
		       xxxx::xxxx:xxxx:xxxx:xxxx or ::xxxx.        
		Returns empty string when slbCurCfgVirtServiceProxyIpMode is not set to address.
		If neither of the addresses (v4 & v6) are configured or are subnets, the persistency
		value is disable." 
    ::= { slbCurCfgVirtServicesEntry 49 }

   slbCurCfgVirtServiceProxyIpv6Prefix OBJECT-TYPE
    SYNTAX  INTEGER (1..128)
    MAX-ACCESS  read-only
    STATUS  current
    DESCRIPTION
        "This object ID shows current configured IPv6 PIP Mask. 
		Returns 0 when slbCurCfgVirtServiceProxyIpMode is not set to address.
		If neither of the addresses (v4 & v6) are configured or are subnets, the persistency
		value is disable." 
    ::= { slbCurCfgVirtServicesEntry 50 }

slbCurCfgVirtServiceProxyIpPersistency OBJECT-TYPE   
    SYNTAX INTEGER {
        disable(0),
        client(1),
	 host(2),
        unsupported(2147483647)
        }
    MAX-ACCESS  read-only
    STATUS  current
    DESCRIPTION
        "This object ID shows current configured virtual service proxy IP persistency.
		Returns 0 when slbCurCfgVirtServiceProxyIpMode is not set to address.
		If neither of the addresses (v4 & v6) are configured or are subnets, the persistency
		value is disable. "
    ::= { slbCurCfgVirtServicesEntry 51 }

   slbCurCfgVirtServiceProxyIpNWclass OBJECT-TYPE
    SYNTAX  DisplayString  (SIZE(0..32)) 
    MAX-ACCESS  read-only
    STATUS  current
    DESCRIPTION
        "This object ID ows current configured IPv4 Network Class as PIP .
		Returns empty string when slbCurCfgVirtServiceProxyIpMode is not set to nwclass.
		Persistency is relevant only if either IPv4 or IPv6 class (or both) are configured.
		If neither of the classes (v4 & v6) are configured, the persistency configuration value is disable." 
    ::= { slbCurCfgVirtServicesEntry 52 }

   slbCurCfgVirtServiceProxyIpv6NWclass OBJECT-TYPE
    SYNTAX  DisplayString  (SIZE(0..32)) 
    MAX-ACCESS  read-only
    STATUS  current
    DESCRIPTION
        "This object ID shows current configured IPv6 Network Class as PIP .
		Returns empty string when slbCurCfgVirtServiceProxyIpMode is not set to nwclass.        
		Persistency is relevant only if either IPv4 or IPv6 class (or both) are configured.
		If neither of the classes (v4 & v6) are configured, the persistency configuration value is disable." 
    ::= { slbCurCfgVirtServicesEntry 53 }

slbCurCfgVirtServiceProxyIpNWclassPersistency OBJECT-TYPE   
    SYNTAX INTEGER {
        disable(0),
        client(1),
        unsupported(2147483647)
        }
    MAX-ACCESS  read-only
    STATUS  current
    DESCRIPTION
        "This object ID shows current configured Network Class PIP persistency mode.
		Returns 0 when slbCurCfgVirtServiceProxyIpMode is not set to nwclass.        
		Persistency is relevant only if either IPv4 PIP or IPv6 PIP (or both) are configured as
		subnet.
		If neither of the classes (v4 & v6) are configured, the persistency configuration value is disable." 
    ::= { slbCurCfgVirtServicesEntry 54 }    
--Proxy IP Cur config end

slbCurCfgVirtServiceHashLen OBJECT-TYPE
    SYNTAX INTEGER (4..256)
    MAX-ACCESS  read-only
    STATUS  current
    DESCRIPTION
        "Set length for slb service sip hashing (4- 256 bytes)"
    ::= { slbCurCfgVirtServicesEntry 55 }

slbCurCfgVirtServiceApm OBJECT-TYPE
    SYNTAX  INTEGER {
        enabled(1),
        disabled(2),
        unsupported(2147483647)
        }
    MAX-ACCESS  read-only
    STATUS  obsolete
    DESCRIPTION
        "Enable/disable apm."
    ::= { slbCurCfgVirtServicesEntry 56 }

slbCurCfgVirtServiceClsRST OBJECT-TYPE   
    SYNTAX  INTEGER {
	enabled(1),
	disabled(2),
        unsupported(2147483647)
	}
    MAX-ACCESS  read-only
    STATUS  current   
    DESCRIPTION 
        "Enable or disable Send RST on connection close."
    ::= { slbCurCfgVirtServicesEntry 58 }

slbCurCfgVirtServiceNonHTTP OBJECT-TYPE   
    SYNTAX  INTEGER {
	enabled(1),
	disabled(2),
        unsupported(2147483647)
	}
    MAX-ACCESS  read-only
    STATUS  current   
    DESCRIPTION 
        "Enable or disable Send non-HTTP traffic."
    ::= { slbCurCfgVirtServicesEntry 59 }

    
slbCurCfgVirtServicesSecondPartTable OBJECT-TYPE
    SYNTAX  SEQUENCE OF SlbCurCfgVirtServicesSecondPartEntry
    MAX-ACCESS  not-accessible
    STATUS  current
    DESCRIPTION
        "The table of virtual Services.
         Note:This mib is not supported for VX instance of Virtualization."
    ::= { virtualServerCfg 12 }

slbCurCfgVirtServicesSecondPartEntry OBJECT-TYPE
    SYNTAX  SlbCurCfgVirtServicesSecondPartEntry
    MAX-ACCESS  not-accessible
    STATUS  current
    DESCRIPTION
        "A row in the virtual services table."
    INDEX   { slbCurCfgVirtServSecondPartIndex, slbCurCfgVirtServiceSecondPartIndex }
    ::= { slbCurCfgVirtServicesSecondPartTable 1 }

SlbCurCfgVirtServicesSecondPartEntry ::= SEQUENCE {
    slbCurCfgVirtServSecondPartIndex            Integer32,
    slbCurCfgVirtServiceSecondPartIndex         Integer32,

    slbCurCfgVirtServiceConnmgtStatus  INTEGER,
    slbCurCfgVirtServiceConnmgtTimeout INTEGER,
    slbCurCfgVirtServiceCachepol      DisplayString,
    slbCurCfgVirtServiceComppol       DisplayString,
    slbCurCfgVirtServiceSSLpol        DisplayString,
    slbCurCfgVirtServiceServCert      DisplayString,
    slbCurCfgVirtServiceHttpmodList   DisplayString,
    slbCurCfgVirtServiceCloaksrv      INTEGER,

    slbCurCfgVirtServErrcodeStatus    INTEGER,
    slbCurCfgVirtServErrcodeMatch     DisplayString,
    slbCurCfgVirtServErrcodeHttpRedir INTEGER,
    slbCurCfgVirtServErrcodeUrl       DisplayString,
    slbCurCfgVirtServErrcode          DisplayString,
    slbCurCfgVirtServErrcodeNew       DisplayString,
    slbCurCfgVirtServErrcodeReason    DisplayString,
    slbCurCfgVirtServUrlchangStatus     INTEGER,
    slbCurCfgVirtServUrlchangHostType   INTEGER
}

slbCurCfgVirtServSecondPartIndex OBJECT-TYPE
    SYNTAX  Integer32
    MAX-ACCESS  read-only
    STATUS  current
    DESCRIPTION
        "The number of the virtual server." 
    ::= { slbCurCfgVirtServicesSecondPartEntry 1 }

slbCurCfgVirtServiceSecondPartIndex OBJECT-TYPE 
    SYNTAX  Integer32 
    MAX-ACCESS  read-only 
    STATUS  current 
    DESCRIPTION 
        "The service index. This has no external meaning" 
    ::= { slbCurCfgVirtServicesSecondPartEntry 2 }


slbCurCfgVirtServiceConnmgtStatus OBJECT-TYPE
    SYNTAX  INTEGER {
        disabled(0),
        pooling(1),
        muxenabled(2),
        unsupported(2147483647)
        }
    MAX-ACCESS  read-only
    STATUS  current
    DESCRIPTION
        "Connection management configuration for HTTP traffic(Enable/disable/pooling) [Default: Disable]."
    ::= { slbCurCfgVirtServicesSecondPartEntry 3 }

slbCurCfgVirtServiceConnmgtTimeout OBJECT-TYPE
    SYNTAX  INTEGER (0..32768)
    MAX-ACCESS  read-only
    STATUS  current
    DESCRIPTION
        "Connection management server side connection idle timeout in minutes [0-32768] [Default: 10]."
    ::= { slbCurCfgVirtServicesSecondPartEntry 4 }

slbCurCfgVirtServiceCachepol OBJECT-TYPE
    SYNTAX  DisplayString  (SIZE(0..32))
    MAX-ACCESS  read-only
    STATUS  current
    DESCRIPTION
        "Cache policy name associated with this virtual service."
    ::= { slbCurCfgVirtServicesSecondPartEntry 5 }

slbCurCfgVirtServiceComppol OBJECT-TYPE
    SYNTAX  DisplayString  (SIZE(0..32))
    MAX-ACCESS  read-only
    STATUS  current
    DESCRIPTION
        "Compression policy name associated with this virtual service."
    ::= { slbCurCfgVirtServicesSecondPartEntry 6 }

slbCurCfgVirtServiceSSLpol OBJECT-TYPE
    SYNTAX  DisplayString  (SIZE(0..32))
    MAX-ACCESS  read-only
    STATUS  current
    DESCRIPTION
        "SSL policy name associated with this virtual service."
    ::= { slbCurCfgVirtServicesSecondPartEntry 7 }

slbCurCfgVirtServiceServCert OBJECT-TYPE
    SYNTAX  DisplayString  (SIZE(0..128))
    MAX-ACCESS  read-only
    STATUS  current
    DESCRIPTION
        "Server Certificate name associated with this virtual service."
    ::= { slbCurCfgVirtServicesSecondPartEntry 8 }

slbCurCfgVirtServiceHttpmodList OBJECT-TYPE
    SYNTAX  DisplayString  (SIZE(0..32))
    MAX-ACCESS  read-only
    STATUS  current
    DESCRIPTION
        "HTTP Content Modifications Rule-list associated with this virtual service."
    ::= { slbCurCfgVirtServicesSecondPartEntry 9 }

slbCurCfgVirtServiceCloaksrv OBJECT-TYPE
    SYNTAX  INTEGER {
        enabled(1),
        disabled(2),
        unsupported(2147483647)
        }
    MAX-ACCESS  read-only
    STATUS  current
    DESCRIPTION
        "Enable/disable server cloaking."
    ::= { slbCurCfgVirtServicesSecondPartEntry 10 }

slbCurCfgVirtServErrcodeStatus OBJECT-TYPE
    SYNTAX  INTEGER {
        enabled(1),
        disabled(2),
        clear(3),
        unsupported(2147483647)
        }
    MAX-ACCESS  read-only
    STATUS  current
    DESCRIPTION
        "Enable/disable/clear error-code configuration."
    ::= { slbCurCfgVirtServicesSecondPartEntry 11 }

slbCurCfgVirtServErrcodeMatch OBJECT-TYPE
    SYNTAX  DisplayString (SIZE (0..64))
    MAX-ACCESS  read-only
    STATUS  current
    DESCRIPTION
        "Match error-code(s), e.g 203,204 ."
    ::= { slbCurCfgVirtServicesSecondPartEntry 12 }

slbCurCfgVirtServErrcodeHttpRedir OBJECT-TYPE
    SYNTAX  INTEGER {
        yes(1),
        no(2),
        unsupported(2147483647)
    }
    MAX-ACCESS  read-only
    STATUS  current
    DESCRIPTION
        "Use http redirection [yes/no] [Default: yes]."
    ::= { slbCurCfgVirtServicesSecondPartEntry 13 }

slbCurCfgVirtServErrcodeUrl OBJECT-TYPE
    SYNTAX  DisplayString (SIZE(0..240))
    MAX-ACCESS  read-only
    STATUS  current
    DESCRIPTION
        "URL for redirection."
    ::= { slbCurCfgVirtServicesSecondPartEntry 14 }


slbCurCfgVirtServErrcode OBJECT-TYPE
    SYNTAX  DisplayString (SIZE(0..3))
    MAX-ACCESS  read-only
    STATUS  current
    DESCRIPTION
        "Set error code [Default: 302]."
    ::= { slbCurCfgVirtServicesSecondPartEntry 15 }

slbCurCfgVirtServErrcodeNew OBJECT-TYPE
    SYNTAX  DisplayString (SIZE(0..3))
    MAX-ACCESS  read-only
    STATUS  current
    DESCRIPTION
        "Enter Cur error code [Default: 302]."
    ::= { slbCurCfgVirtServicesSecondPartEntry 16 }

slbCurCfgVirtServErrcodeReason OBJECT-TYPE
    SYNTAX  DisplayString (SIZE(0..128))
    MAX-ACCESS  read-only
    STATUS  current
    DESCRIPTION
        "Enter error reason."
    ::= { slbCurCfgVirtServicesSecondPartEntry 17 }

slbCurCfgVirtServUrlchangStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgVirtServicesSecondPartEntry 18 }

slbCurCfgVirtServUrlchangHostType OBJECT-TYPE
    SYNTAX  INTEGER {
        sufx(1),
        prefx(2),
        eq(3),
        incl(4),
        any(5),
        unsupported(2147483647)
    }
    MAX-ACCESS  read-only
    STATUS  current
    DESCRIPTION
        "Enter hostname match type [sufx|prefx|eq|incl|any] [Default: any]"
    ::= { slbCurCfgVirtServicesSecondPartEntry 19 }


slbCurCfgVirtServicesThirdPartTable OBJECT-TYPE
    SYNTAX  SEQUENCE OF SlbCurCfgVirtServicesThirdPartEntry
    MAX-ACCESS  not-accessible
    STATUS  current
    DESCRIPTION
        "The table of virtual Services.
         Note:This mib is not supported for VX instance of Virtualization."
    ::= { virtualServerCfg 13 }

slbCurCfgVirtServicesThirdPartEntry OBJECT-TYPE
    SYNTAX  SlbCurCfgVirtServicesThirdPartEntry
    MAX-ACCESS  not-accessible
    STATUS  current
    DESCRIPTION
        "A row in the virtual services table."
    INDEX   { slbCurCfgVirtServThirdPartIndex, slbCurCfgVirtServiceThirdPartIndex }
    ::= { slbCurCfgVirtServicesThirdPartTable 1 }

SlbCurCfgVirtServicesThirdPartEntry ::= SEQUENCE {
    slbCurCfgVirtServThirdPartIndex            Integer32,
    slbCurCfgVirtServiceThirdPartIndex         Integer32,

    slbCurCfgVirtServUrlchangHostName   DisplayString,
    slbCurCfgVirtServUrlchangPathType   INTEGER,
    slbCurCfgVirtServUrlchangPathMatch  DisplayString,
    slbCurCfgVirtServUrlchangPageName   DisplayString,
    slbCurCfgVirtServUrlchangPageType   DisplayString,
    slbCurCfgVirtServUrlchangActnType   INTEGER,
    slbCurCfgVirtServUrlchangPathInsrt  DisplayString,
    slbCurCfgVirtServUrlchangInsrtPostn INTEGER
}


slbCurCfgVirtServThirdPartIndex OBJECT-TYPE
    SYNTAX  Integer32
    MAX-ACCESS  read-only
    STATUS  current
    DESCRIPTION
        "The number of the virtual server." 
    ::= { slbCurCfgVirtServicesThirdPartEntry 1 }

slbCurCfgVirtServiceThirdPartIndex OBJECT-TYPE 
    SYNTAX  Integer32 
    MAX-ACCESS  read-only 
    STATUS  current 
    DESCRIPTION 
        "The service index. This has no external meaning" 
    ::= { slbCurCfgVirtServicesThirdPartEntry 2 }

slbCurCfgVirtServUrlchangHostName OBJECT-TYPE
    SYNTAX  DisplayString (SIZE(0..250))
    MAX-ACCESS  read-only
    STATUS  current
    DESCRIPTION
        "Enter hostname to match."
    ::= { slbCurCfgVirtServicesThirdPartEntry 3 }

slbCurCfgVirtServUrlchangPathType OBJECT-TYPE
    SYNTAX  INTEGER {
        sufx(1),
        prefx(2),
        eq(3),
        incl(4),
        any(5),
        none(6),
        unsupported(2147483647)
    }
    MAX-ACCESS  read-only
    STATUS  current
    DESCRIPTION
        "Enter path match type [sufx|prefx|eq|incl|any]."
    ::= { slbCurCfgVirtServicesThirdPartEntry 4 }

slbCurCfgVirtServUrlchangPathMatch OBJECT-TYPE
    SYNTAX  DisplayString (SIZE(0..250))
    MAX-ACCESS  read-only
    STATUS  current
    DESCRIPTION
        "Enter path to match."
    ::= { slbCurCfgVirtServicesThirdPartEntry 5 }

slbCurCfgVirtServUrlchangPageName OBJECT-TYPE
    SYNTAX  DisplayString (SIZE(0..64))
    MAX-ACCESS  read-only
    STATUS  current
    DESCRIPTION
        "Enter page name to match or none."
    ::= { slbCurCfgVirtServicesThirdPartEntry 6 }

slbCurCfgVirtServUrlchangPageType OBJECT-TYPE
    SYNTAX  DisplayString (SIZE(0..64))
    MAX-ACCESS  read-only
    STATUS  current
    DESCRIPTION
        "Enter page type to match or none."
    ::= { slbCurCfgVirtServicesThirdPartEntry 7 }

slbCurCfgVirtServUrlchangActnType OBJECT-TYPE
    SYNTAX  INTEGER {
        insert(1),
        replace(2),
        remove(3),
        none(4),
        unsupported(2147483647)
    }
    MAX-ACCESS  read-only
    STATUS  current
    DESCRIPTION
        "Enter path action type."
    ::= { slbCurCfgVirtServicesThirdPartEntry 8 }

slbCurCfgVirtServUrlchangPathInsrt OBJECT-TYPE
    SYNTAX  DisplayString (SIZE(0..250))
    MAX-ACCESS  read-only
    STATUS  current
    DESCRIPTION
        "Enter path to insert."
    ::= { slbCurCfgVirtServicesThirdPartEntry 9 }


slbCurCfgVirtServUrlchangInsrtPostn OBJECT-TYPE
    SYNTAX  INTEGER {
        before(1),
        after(2),
        unsupported(2147483647)
    }
    MAX-ACCESS  read-only
    STATUS  current
    DESCRIPTION
        "Insert the specified path before or after the matched section"
    ::= { slbCurCfgVirtServicesThirdPartEntry 10 }



slbCurCfgVirtServicesFourthPartTable OBJECT-TYPE
    SYNTAX  SEQUENCE OF SlbCurCfgVirtServicesFourthPartEntry
    MAX-ACCESS  not-accessible
    STATUS  current
    DESCRIPTION
        "The table of virtual Services.
         Note:This mib is not supported for VX instance of Virtualization."
    ::= { virtualServerCfg 14 }

slbCurCfgVirtServicesFourthPartEntry OBJECT-TYPE
    SYNTAX  SlbCurCfgVirtServicesFourthPartEntry
    MAX-ACCESS  not-accessible
    STATUS  current
    DESCRIPTION
        "A row in the virtual services table."
    INDEX   { slbCurCfgVirtServFourthPartIndex, slbCurCfgVirtServiceFourthPartIndex }
    ::= { slbCurCfgVirtServicesFourthPartTable 1 }

SlbCurCfgVirtServicesFourthPartEntry ::= SEQUENCE {
    slbCurCfgVirtServFourthPartIndex            Integer32,
    slbCurCfgVirtServiceFourthPartIndex         Integer32,

    slbCurCfgVirtServUrlchangNewPgName  DisplayString,
    slbCurCfgVirtServUrlchangNewPgType  DisplayString,

    slbCurCfgVirtServPathHideStatus     INTEGER,
    slbCurCfgVirtServPathHideHostType   INTEGER,
    slbCurCfgVirtServPathHideHostName   DisplayString,
    slbCurCfgVirtServPathHidePathType   INTEGER,
    slbCurCfgVirtServPathHidePathName   DisplayString,

    slbCurCfgVirtServTextrepStatus      INTEGER,
    slbCurCfgVirtServTextrepAction      INTEGER
}

slbCurCfgVirtServFourthPartIndex OBJECT-TYPE
    SYNTAX  Integer32
    MAX-ACCESS  read-only
    STATUS  current
    DESCRIPTION
        "The number of the virtual server." 
    ::= { slbCurCfgVirtServicesFourthPartEntry 1 }

slbCurCfgVirtServiceFourthPartIndex OBJECT-TYPE 
    SYNTAX  Integer32 
    MAX-ACCESS  read-only 
    STATUS  current 
    DESCRIPTION 
        "The service index. This has no external meaning" 
    ::= { slbCurCfgVirtServicesFourthPartEntry 2 }

slbCurCfgVirtServUrlchangNewPgName OBJECT-TYPE
    SYNTAX  DisplayString (SIZE(0..64))
    MAX-ACCESS  read-only
    STATUS  current
    DESCRIPTION
        "Enter Cur page name or none."
    ::= { slbCurCfgVirtServicesFourthPartEntry 3 }

slbCurCfgVirtServUrlchangNewPgType OBJECT-TYPE
    SYNTAX  DisplayString (SIZE(0..64))
    MAX-ACCESS  read-only
    STATUS  current
    DESCRIPTION
        "Enter Cur page type or none."
    ::= { slbCurCfgVirtServicesFourthPartEntry 4 }

slbCurCfgVirtServPathHideStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgVirtServicesFourthPartEntry 5 }

slbCurCfgVirtServPathHideHostType OBJECT-TYPE
    SYNTAX  INTEGER {
        sufx(1),
        prefx(2),
        eq(3),
        incl(4),
        any(5),
        unsupported(2147483647)
    }
    MAX-ACCESS  read-only
    STATUS  current
    DESCRIPTION
        "Enter hostname type [sufx|prefx|eq|incl|any] [Default: any]."
    ::= { slbCurCfgVirtServicesFourthPartEntry 6 }

slbCurCfgVirtServPathHideHostName OBJECT-TYPE
    SYNTAX  DisplayString (SIZE(0..250))
    MAX-ACCESS  read-only
    STATUS  current
    DESCRIPTION
        "Enter hostname to match."
    ::= { slbCurCfgVirtServicesFourthPartEntry 7 }

slbCurCfgVirtServPathHidePathType OBJECT-TYPE
    SYNTAX  INTEGER {
        sufx(1),
        prefx(2),
        eq(3),
        none(4),
        unsupported(2147483647)
    }
    MAX-ACCESS  read-only
    STATUS  current
    DESCRIPTION
        "Enter path match type [sufx|prefx|eq|none]."
    ::= { slbCurCfgVirtServicesFourthPartEntry 8 }

slbCurCfgVirtServPathHidePathName OBJECT-TYPE
    SYNTAX  DisplayString (SIZE(0..250))
    MAX-ACCESS  read-only
    STATUS  current
    DESCRIPTION
        "Enter path to remove."
    ::= { slbCurCfgVirtServicesFourthPartEntry 9 }

slbCurCfgVirtServTextrepStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgVirtServicesFourthPartEntry 10 }

slbCurCfgVirtServTextrepAction OBJECT-TYPE
    SYNTAX  INTEGER {
        none(0),
        replace(1),
        remove(2),
        unsupported(2147483647)
    }
    MAX-ACCESS  read-only
    STATUS  current
    DESCRIPTION
        "Enter action [replace|remove|none]."
    ::= { slbCurCfgVirtServicesFourthPartEntry 11 }




slbCurCfgVirtServicesFifthPartTable OBJECT-TYPE
    SYNTAX  SEQUENCE OF SlbCurCfgVirtServicesFifthPartEntry
    MAX-ACCESS  not-accessible
    STATUS  current
    DESCRIPTION
        "The table of virtual Services.
         Note:This mib is not supported for VX instance of Virtualization."
    ::= { virtualServerCfg 15 }

slbCurCfgVirtServicesFifthPartEntry OBJECT-TYPE
    SYNTAX  SlbCurCfgVirtServicesFifthPartEntry
    MAX-ACCESS  not-accessible
    STATUS  current
    DESCRIPTION
        "A row in the virtual services table."
    INDEX   { slbCurCfgVirtServFifthPartIndex, slbCurCfgVirtServiceFifthPartIndex }
    ::= { slbCurCfgVirtServicesFifthPartTable 1 }

SlbCurCfgVirtServicesFifthPartEntry ::= SEQUENCE {

    slbCurCfgVirtServFifthPartIndex            Integer32,
    slbCurCfgVirtServiceFifthPartIndex         Integer32,

    slbCurCfgVirtServTextrepMatchText   DisplayString,
    slbCurCfgVirtServTextrepReplacTxt   DisplayString,

    slbCurCfgVirtServApplicationType    INTEGER,
    slbCurCfgVirtServiceName          DisplayString,
    slbCurCfgVirtServiceAction        INTEGER,
    slbCurCfgVirtServiceRedirect      DisplayString,

    slbCurCfgVirtServiceServCertGrpMark INTEGER,
    slbCurCfgVirtServiceDnsType         INTEGER,
    slbCurCfgVirtServiceClntproxType    INTEGER,
    slbCurCfgVirtServiceZerowinSize     INTEGER,
    slbCurCfgVirtServiceCookiePath    	DisplayString,
    slbCurCfgVirtServiceCookieSecure    INTEGER,
    slbCurCfgVirtServiceNoRtsp          INTEGER,
    slbCurCfgVirtServiceCkRebind        INTEGER,
    slbCurCfgVirtServiceParseLimit      INTEGER,
    slbCurCfgVirtServiceParseLength     INTEGER,
    slbCurCfgVirtServiceUriNorm         INTEGER,
    slbCurCfgVirtServiceGranularity     INTEGER,
    slbCurCfgVirtServiceSessLog         INTEGER,
    slbCurCfgVirtServiceAppwallWebappId		DisplayString
}

slbCurCfgVirtServFifthPartIndex OBJECT-TYPE
    SYNTAX  Integer32
    MAX-ACCESS  read-only
    STATUS  current
    DESCRIPTION
        "The number of the virtual server." 
    ::= { slbCurCfgVirtServicesFifthPartEntry 1 }

slbCurCfgVirtServiceFifthPartIndex OBJECT-TYPE 
    SYNTAX  Integer32 
    MAX-ACCESS  read-only 
    STATUS  current 
    DESCRIPTION 
        "The service index. This has no external meaning" 
    ::= { slbCurCfgVirtServicesFifthPartEntry 2 }

slbCurCfgVirtServTextrepMatchText OBJECT-TYPE
    SYNTAX  DisplayString (SIZE(0..128))
    MAX-ACCESS  read-only
    STATUS  current
    DESCRIPTION
        "Enter text to be replaced."
    ::= { slbCurCfgVirtServicesFifthPartEntry 3 }

slbCurCfgVirtServTextrepReplacTxt OBJECT-TYPE
    SYNTAX  DisplayString (SIZE(0..128))
    MAX-ACCESS  read-only
    STATUS  current
    DESCRIPTION
        "Enter Cur text."
    ::= { slbCurCfgVirtServicesFifthPartEntry 4 }

slbCurCfgVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12),
      smtp(13),
      pop3(14),
      ip(15),
      mh-sctp(16),
      unsupported(2147483647)
    }
    MAX-ACCESS  read-only
    STATUS  current
    DESCRIPTION
        "Application Type for virtual service."
    ::= { slbCurCfgVirtServicesFifthPartEntry 5 }

slbCurCfgVirtServiceName OBJECT-TYPE
    SYNTAX  DisplayString (SIZE(0..32))
    MAX-ACCESS  read-only
    STATUS  current
    DESCRIPTION
        "The name of the virtual service."
    ::= { slbCurCfgVirtServicesFifthPartEntry 6 }

slbCurCfgVirtServiceAction OBJECT-TYPE
    SYNTAX  INTEGER    {
    group(1),
    redirect(2),
    discard(3),
    unsupported(2147483647)
    }
    MAX-ACCESS  read-only
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbCurCfgVirtServicesFifthPartEntry 7 }

slbCurCfgVirtServiceRedirect OBJECT-TYPE
    SYNTAX  DisplayString  (SIZE(0..255))
    MAX-ACCESS  read-only
    STATUS  current
    DESCRIPTION
        "application redirection location.We need to provide this
         value When action type is set to redirect(2)."
    ::= { slbCurCfgVirtServicesFifthPartEntry 8 }

slbCurCfgVirtServiceServCertGrpMark OBJECT-TYPE
    SYNTAX  INTEGER    {
    cert(1),
    group(2),
    unsupported(2147483647)
    }
    MAX-ACCESS  read-only
    STATUS  current
    DESCRIPTION
        "Group Mark for Server Certificate. If we set value as cert(0)
         It will denote that the server certificate (name) associated with 
         this virtual service, represents a certificate. Otherwise, a value of group(1), denotes that the server    
         certificate (name) represents a group."
    ::= { slbCurCfgVirtServicesFifthPartEntry 9}

slbCurCfgVirtServiceDnsType OBJECT-TYPE
    SYNTAX  INTEGER {
        dns(1),
        dnssec(2),
        both(3),
        unsupported(2147483647)
        }
    MAX-ACCESS  read-only
    STATUS  current
    DESCRIPTION
        "Set DNS type for this service (DNS, DNSSEC)."
    ::= { slbCurCfgVirtServicesFifthPartEntry 10 }

slbCurCfgVirtServiceClntproxType OBJECT-TYPE
    SYNTAX  INTEGER {
        none(1),
        http(2),
        https(3),
        unsupported(2147483647)
        }
    MAX-ACCESS  read-only
    STATUS  current
    DESCRIPTION
        "Set client proximity type for this service."
    ::= { slbCurCfgVirtServicesFifthPartEntry 11 }

slbCurCfgVirtServiceZerowinSize OBJECT-TYPE
    SYNTAX  INTEGER {
        enabled(1),
        disabled(2),
        unsupported(2147483647)
        }
    MAX-ACCESS  read-only
    STATUS  current
    DESCRIPTION
        "Enable or disable zero window size in SYN+ACK for this service."
    ::= { slbCurCfgVirtServicesFifthPartEntry 12 }

slbCurCfgVirtServiceCookiePath OBJECT-TYPE
    SYNTAX  DisplayString (SIZE(0..32))
    MAX-ACCESS  read-only
    STATUS  current
    DESCRIPTION
        "The cookie path name of the virtual server used for cookie load balance."
    ::= { slbCurCfgVirtServicesFifthPartEntry 13 }

slbCurCfgVirtServiceCookieSecure OBJECT-TYPE
    SYNTAX  INTEGER {
	    no(1),
        yes(2),
        unsupported(2147483647)
        }
    MAX-ACCESS  read-only
    STATUS  current
    DESCRIPTION
        "Is cookie secure [yes/no] [Default: no]."
    ::= { slbCurCfgVirtServicesFifthPartEntry 14 }

slbCurCfgVirtServiceNoRtsp OBJECT-TYPE
    SYNTAX  INTEGER {
	enabled(1),
        disabled(2),
        unsupported(2147483647)
        }
    MAX-ACCESS  read-only
    STATUS  current
    DESCRIPTION
        "Enable or disable only rtsp SLB for this service."
    ::= { slbCurCfgVirtServicesFifthPartEntry 15 }

slbCurCfgVirtServiceCkRebind OBJECT-TYPE
    SYNTAX  INTEGER {
        enabled(1),
        disabled(2),
        unsupported(2147483647)
        }
    MAX-ACCESS  read-only
    STATUS  current
    DESCRIPTION
        "Server rebalancing when cookie is absent.
         When enabled, server load balancing will happen 
         for subsequent request comes without cookie."
    ::= { slbCurCfgVirtServicesFifthPartEntry 16 }

slbCurCfgVirtServiceParseLimit OBJECT-TYPE
    SYNTAX  INTEGER {
        enabled(1),
        disabled(2),
        unsupported(2147483647)
        }
    MAX-ACCESS  read-only
    STATUS  current
    DESCRIPTION
        "Enable or disable buffer limit for content based selection."
    ::= { slbCurCfgVirtServicesFifthPartEntry 17 }

slbCurCfgVirtServiceParseLength OBJECT-TYPE
    SYNTAX  INTEGER (0..18200)
    MAX-ACCESS  read-only
    STATUS  current
    DESCRIPTION
        "The buffer length for content based selection."
    ::= { slbCurCfgVirtServicesFifthPartEntry 18 }

slbCurCfgVirtServiceUriNorm OBJECT-TYPE
    SYNTAX  INTEGER {
        enabled(1),
        disabled(2),
        unsupported(2147483647)
        }
    MAX-ACCESS  read-only
    STATUS  current
    DESCRIPTION
        "Enable or disable URI normalization for HTTP content matching."
    ::= { slbCurCfgVirtServicesFifthPartEntry 19 }

slbCurCfgVirtServiceGranularity OBJECT-TYPE
    SYNTAX  INTEGER {
	service(0),
        real(2),
        unsupported(2147483647)
        }
    MAX-ACCESS  read-only
    STATUS  current
    DESCRIPTION
        "Get the current Granularity of this service, for statistics report-protocol information.
	 Group(1) - for group level, or GroupAndServers(2) - for server level."
    ::= { slbCurCfgVirtServicesFifthPartEntry 20 }

slbCurCfgVirtServiceSessLog OBJECT-TYPE
    SYNTAX  INTEGER {
        enabled(1),
        disabled(2),
        unsupported(2147483647)
        }
    MAX-ACCESS  read-only
    STATUS  current
    DESCRIPTION
        "Enable or disable Session Logging."
    ::= { slbCurCfgVirtServicesFifthPartEntry 21 }

slbCurCfgVirtServiceAppwallWebappId OBJECT-TYPE
    SYNTAX  DisplayString  (SIZE(0..32)) 
    MAX-ACCESS  read-only
    STATUS  current
    DESCRIPTION
        "This object ID shows current configured web security ID." 
    ::= { slbCurCfgVirtServicesFifthPartEntry 22 }

-- Server load balancing - Virtual Services Table 

slbNewCfgVirtServicesTable OBJECT-TYPE
    SYNTAX  SEQUENCE OF SlbNewCfgVirtServicesEntry
    MAX-ACCESS  not-accessible
    STATUS  current
    DESCRIPTION
        "The table of virtual Services.
         Note:This mib is not supported for VX instance of Virtualization."
    ::= { virtualServerCfg 6 }

slbNewCfgVirtServicesEntry OBJECT-TYPE
    SYNTAX  SlbNewCfgVirtServicesEntry
    MAX-ACCESS  not-accessible
    STATUS  current
    DESCRIPTION
        "A row in the virtual services table."
    INDEX   { slbNewCfgVirtServIndex, slbNewCfgVirtServiceIndex }
    ::= { slbNewCfgVirtServicesTable 1 }

SlbNewCfgVirtServicesEntry ::= SEQUENCE {
    slbNewCfgVirtServIndex            Integer32,
    slbNewCfgVirtServiceIndex         Integer32,

    slbNewCfgVirtServiceVirtPort      INTEGER,
    slbNewCfgVirtServiceRealGroup     Integer32,
    slbNewCfgVirtServiceRealPort      INTEGER,
    slbNewCfgVirtServiceUDPBalance    INTEGER,
    slbNewCfgVirtServiceHname         DisplayString,
    slbNewCfgVirtServiceBwmContract   Integer32,
    slbNewCfgVirtServiceDirServerRtn  INTEGER,
    slbNewCfgVirtServiceRtspUrlParse  INTEGER,
    slbNewCfgVirtServiceFtpParsing    INTEGER,
    slbNewCfgVirtServiceRemapUDPFrags INTEGER,
    slbNewCfgVirtServiceDnsSlb        INTEGER,
    slbNewCfgVirtServiceResponseCount INTEGER,
    slbNewCfgVirtServicePBind         INTEGER,
    slbNewCfgVirtServiceCname         DisplayString,
    slbNewCfgVirtServiceCoffset       INTEGER,
    slbNewCfgVirtServiceClength       INTEGER, 
    slbNewCfgVirtServiceUriCookie     INTEGER,
    slbNewCfgVirtServiceCExpire       DisplayString,
    slbNewCfgVirtServiceCookieMode    INTEGER,
    slbNewCfgVirtServiceDBind         INTEGER,
    slbNewCfgVirtServiceHttpSlb       INTEGER,
    slbNewCfgVirtServiceHttpSlbOption INTEGER,
    slbNewCfgVirtServiceHttpSlb2      INTEGER,
    slbNewCfgVirtServiceHttpHdrName   DisplayString,
    slbNewCfgVirtServiceUrlHashLen    INTEGER,
    slbNewCfgVirtServiceCookieDname   INTEGER,
    slbNewCfgVirtServiceClsRST        INTEGER,
    slbNewCfgVirtServiceDelete        INTEGER, 
    slbNewCfgVirtServiceDirect        INTEGER,
    slbNewCfgVirtServiceThash         INTEGER,
    slbNewCfgVirtServiceLdapreset     INTEGER,
    slbNewCfgVirtServiceLdapslb       INTEGER,
    slbNewCfgVirtServiceSip           INTEGER,
    slbNewCfgVirtServiceXForwardedFor INTEGER,
    slbNewCfgVirtServiceHttpRedir     INTEGER,
    slbNewCfgVirtServicePbindRport    INTEGER,
    slbNewCfgVirtServiceEgressPip     INTEGER,
    slbNewCfgVirtServiceWts           INTEGER,
    slbNewCfgVirtServiceTimeOut       INTEGER,
    slbNewCfgVirtServiceSoftGrid      INTEGER,
    slbNewCfgVirtServiceSessionMirror INTEGER,
    slbNewCfgVirtServiceSdpNat        INTEGER,
    slbNewCfgVirtServiceConnPooling   INTEGER,
    slbNewCfgVirtPersistentTimeOut    INTEGER,
    slbNewCfgVirtServiceUhash         INTEGER,
    slbNewCfgVirtServiceProxyIpMode   INTEGER,
    slbNewCfgVirtServiceProxyIpAddr   IpAddress,
    slbNewCfgVirtServiceProxyIpMask   IpAddress,
    slbNewCfgVirtServiceProxyIpv6Addr   DisplayString,
    slbNewCfgVirtServiceProxyIpv6Prefix   INTEGER,
    slbNewCfgVirtServiceProxyIpPersistency   INTEGER,
    slbNewCfgVirtServiceProxyIpNWclass   DisplayString,
    slbNewCfgVirtServiceProxyIpv6NWclass   DisplayString,
    slbNewCfgVirtServiceProxyIpNWclassPersistency   INTEGER,    
    slbNewCfgVirtServiceHashLen       INTEGER,
    slbNewCfgVirtServiceApm           INTEGER,
    slbNewCfgVirtServiceNonHTTP       INTEGER
}

slbNewCfgVirtServIndex OBJECT-TYPE
    SYNTAX  Integer32
    MAX-ACCESS  read-only
    STATUS  current
    DESCRIPTION
        "The number of the virtual server." 
    ::= { slbNewCfgVirtServicesEntry 1 }

slbNewCfgVirtServiceIndex OBJECT-TYPE 
    SYNTAX  Integer32 (1..8)
    MAX-ACCESS  read-only 
    STATUS  current 
    DESCRIPTION 
        "The service index. This has no external meaning" 
    ::= { slbNewCfgVirtServicesEntry 2 }

slbNewCfgVirtServiceVirtPort OBJECT-TYPE  
    SYNTAX  INTEGER (1..65534)
    MAX-ACCESS  read-create  
    STATUS  current  
    DESCRIPTION 
        "The layer4 virtual port number of the service."  
    ::= { slbNewCfgVirtServicesEntry 3 } 

slbNewCfgVirtServiceRealGroup OBJECT-TYPE   
    SYNTAX  Integer32   
    MAX-ACCESS  read-create   
    STATUS  current   
    DESCRIPTION 
        "The real server group number for this service."   
    ::= { slbNewCfgVirtServicesEntry 4 }

slbNewCfgVirtServiceRealPort OBJECT-TYPE   
    SYNTAX  INTEGER (0..65534)
    MAX-ACCESS  read-create   
    STATUS  current   
    DESCRIPTION 
        "The layer4 real port number of the service."   
    ::= { slbNewCfgVirtServicesEntry 5 }

slbNewCfgVirtServiceUDPBalance OBJECT-TYPE   
    SYNTAX  INTEGER {
	udp(2),
	tcp(3),
	stateless(4),
        tcpAndUdp(5),
        sctp(6),
        unsupported(2147483647)
	}
    MAX-ACCESS  read-create   
    STATUS  current   
    DESCRIPTION 
        "Set protocol for the virtual service to
         UDP or TCP or SCTP or tcpAndUdp or stateless.
         tcpAndUdp is applicable only to ip service."
    ::= { slbNewCfgVirtServicesEntry 6 }

slbNewCfgVirtServiceHname OBJECT-TYPE 
    SYNTAX  DisplayString (SIZE(0..34))
    MAX-ACCESS  read-create 
    STATUS  current 
    DESCRIPTION 
        "The host name of the virtual service."  
    ::= { slbNewCfgVirtServicesEntry 7 }

slbNewCfgVirtServiceBwmContract OBJECT-TYPE   
    SYNTAX  Integer32   
    MAX-ACCESS  read-create
    STATUS  current   
    DESCRIPTION 
        "The BWM contract number for this service."   
    ::= { slbNewCfgVirtServicesEntry 8 }

slbNewCfgVirtServiceDirServerRtn OBJECT-TYPE
    SYNTAX  INTEGER {
        enabled(1),
        disabled(2),
        unsupported(2147483647)
        }
    MAX-ACCESS  read-create
    STATUS  current   
    DESCRIPTION 
        "Enable or disable direct server return feature. To translate only 
         MAC addresses in performing server load balancing when enabled.  
         This allow servers to return directly to client since IP addresses 
         have not been changed."
    ::= { slbNewCfgVirtServicesEntry 9 }

slbNewCfgVirtServiceRtspUrlParse OBJECT-TYPE   
    SYNTAX  INTEGER {
        none(1),
        l4hash(2),
        hash(3),
        patternMatch(4),
        unsupported(2147483647)
	}
    MAX-ACCESS  read-create
    STATUS  current   
    DESCRIPTION 
        "Select RTSP URL load balancing type."
    ::= { slbNewCfgVirtServicesEntry 10 }

slbNewCfgVirtServiceDBind OBJECT-TYPE   
    SYNTAX  INTEGER {
	enabled(1),
	disabled(2),
	forceproxy(3),
        unsupported(2147483647)
	}
    MAX-ACCESS  read-create
    STATUS  current   
    DESCRIPTION 
        "Enable/disable/forceproxy delayed binding."
    ::= { slbNewCfgVirtServicesEntry 11 }


slbNewCfgVirtServiceFtpParsing OBJECT-TYPE
    SYNTAX  INTEGER {
	enabled(1),
	disabled(2),
        unsupported(2147483647)
	}
    MAX-ACCESS  read-create
    STATUS  current
    DESCRIPTION
        "Enable or Disable the ftp parsing for the virtual service."
    ::= { slbNewCfgVirtServicesEntry 12 }

slbNewCfgVirtServiceRemapUDPFrags OBJECT-TYPE   
    SYNTAX INTEGER {
        enabled(1),
        disabled(2),
        unsupported(2147483647)
        }
    MAX-ACCESS read-create   
    STATUS current   
    DESCRIPTION 
        "Enable or disable remapping UDP server fragments"   
    ::= { slbNewCfgVirtServicesEntry 13 }
slbNewCfgVirtServiceDnsSlb OBJECT-TYPE   
    SYNTAX  INTEGER {
        enabled(1),
	disabled(2),
        unsupported(2147483647)
	}
    MAX-ACCESS  read-create   
    STATUS  current   
    DESCRIPTION 
        "Enable or disable DNS query load balancing."
    ::= { slbNewCfgVirtServicesEntry 14 }

slbNewCfgVirtServiceResponseCount OBJECT-TYPE 
    SYNTAX  INTEGER (1..16)
    MAX-ACCESS  read-create 
    STATUS  current 
    DESCRIPTION 
        "The number of cookie search response count."
    ::= { slbNewCfgVirtServicesEntry 15 }

slbNewCfgVirtServicePBind OBJECT-TYPE   
    SYNTAX  INTEGER {
	clientip(2),
	disabled(3),
	sslid(4),
        cookie(5),
        unsupported(2147483647)
	}
    MAX-ACCESS  read-create   
    STATUS  current   
    DESCRIPTION 
        "Enable or disable persistent bindings for the virtual port."
    ::= { slbNewCfgVirtServicesEntry 16 }

slbNewCfgVirtServiceCname OBJECT-TYPE 
    SYNTAX  DisplayString (SIZE(0..20))
    MAX-ACCESS  read-create 
    STATUS  current 
    DESCRIPTION 
        "The cookie name of the virtual server used for cookie load balance."  
    ::= { slbNewCfgVirtServicesEntry 17 }

slbNewCfgVirtServiceCoffset OBJECT-TYPE
    SYNTAX  INTEGER (1..64)
    MAX-ACCESS  read-create 
    STATUS  current
    DESCRIPTION
        "The starting byte offset of the cookie value." 
    ::= { slbNewCfgVirtServicesEntry 18 }

slbNewCfgVirtServiceClength OBJECT-TYPE
    SYNTAX  INTEGER (1..64)
    MAX-ACCESS  read-create
    STATUS  current
    DESCRIPTION
        "The number of bytes to extract from the cookie value." 
    ::= { slbNewCfgVirtServicesEntry 19 }

slbNewCfgVirtServiceUriCookie OBJECT-TYPE 
    SYNTAX  INTEGER {
	enabled(1),
	disabled(2),
        unsupported(2147483647)
	}
    MAX-ACCESS  read-create 
    STATUS  current 
    DESCRIPTION 
        "Enable or disable cookie search in URI"  
    ::= { slbNewCfgVirtServicesEntry 20}

slbNewCfgVirtServiceCExpire OBJECT-TYPE 
    SYNTAX  DisplayString (SIZE(0..20))
    MAX-ACCESS  read-create 
    STATUS  current 
    DESCRIPTION 
        "The cookie expire of the virtual server used for insert cookie load
         balance depending on the mode it has the following format 
         <MM/dd/yy[@hh:mm]> absolute mode or <days[:hours[:minutes]]>
         for relative mode."  
    ::= { slbNewCfgVirtServicesEntry 21 }

slbNewCfgVirtServiceCookieMode OBJECT-TYPE   
    SYNTAX INTEGER {
        rewrite(1),
        passive(2),
	insert(3),
        unsupported(2147483647)
        }
    MAX-ACCESS read-create 
    STATUS current   
    DESCRIPTION 
        "Select cookie persistence mode. Mode disabled(4) not supported on Alteon"
    ::= { slbNewCfgVirtServicesEntry 22 }

slbNewCfgVirtServiceHttpSlb OBJECT-TYPE   
    SYNTAX  INTEGER {
	disabled(1),
        urlslb(2),
        urlhash(3),
        cookie(4),
        host(5),
        browser(6),
        others(7),
        headerhash(8),
	version(9),
        unsupported(2147483647)
	}
    MAX-ACCESS  read-create   
    STATUS  current   
    DESCRIPTION 
        "Select HTTP server loadbalancing for the virtual port."   
    ::= { slbNewCfgVirtServicesEntry 23 }

slbNewCfgVirtServiceHttpSlbOption OBJECT-TYPE   
    SYNTAX  INTEGER {
	and(1),
        or(2),
        none(3),
        unsupported(2147483647)
	}
    MAX-ACCESS  read-create   
    STATUS  current   
    DESCRIPTION 
        "Select HTTP server loadbalancing for the virtual port."   
    ::= { slbNewCfgVirtServicesEntry 24 }

slbNewCfgVirtServiceHttpSlb2 OBJECT-TYPE   
    SYNTAX  INTEGER {
	disabled(1),
        urlslb(2),
        urlhash(3),
        cookie(4),
        host(5),
        browser(6),
        others(7),
        headerhash(8),
	version(9),
        unsupported(2147483647)
	}
    MAX-ACCESS  read-create   
    STATUS  current   
    DESCRIPTION 
        "Select HTTP server loadbalancing for the virtual port."   
    ::= { slbNewCfgVirtServicesEntry 25 }

slbNewCfgVirtServiceHttpHdrName OBJECT-TYPE 
    SYNTAX  DisplayString  (SIZE(0..32))
    MAX-ACCESS  read-create 
    STATUS  current 
    DESCRIPTION 
        "The HTTP header name of the virtual server."
    ::= { slbNewCfgVirtServicesEntry 26 }

slbNewCfgVirtServiceUrlHashLen OBJECT-TYPE 
    SYNTAX  INTEGER (0..255)
    MAX-ACCESS  read-create 
    STATUS  current 
    DESCRIPTION 
        "The number of bytes used to hash onto server, A zero means
         URL hashing disabled."
    ::= { slbNewCfgVirtServicesEntry 27}

slbNewCfgVirtServiceDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { slbNewCfgVirtServicesEntry 28 }

slbNewCfgVirtServiceDirect OBJECT-TYPE   
    SYNTAX  INTEGER {
        enabled(1),
	disabled(2),
        unsupported(2147483647)
	}
    MAX-ACCESS  read-create   
    STATUS  current   
    DESCRIPTION 
        "Enable or disable DAM for this service." 
    ::= { slbNewCfgVirtServicesEntry 29 }

slbNewCfgVirtServiceThash OBJECT-TYPE   
    SYNTAX  INTEGER {
        sip(1),
        sip-sport(2),
        unsupported(2147483647)
        }
    MAX-ACCESS  read-create
    STATUS  current   
    DESCRIPTION 
        "Set hash parameter."
    ::= { slbNewCfgVirtServicesEntry 30 }

slbNewCfgVirtServiceLdapreset OBJECT-TYPE 
    SYNTAX  INTEGER {
        enabled(1),
        disabled(2),
        unsupported(2147483647)
        }
    MAX-ACCESS  read-create 
    STATUS  current 
    DESCRIPTION 
        "Enable or disable LDAP Server Reset"  
    ::= { slbNewCfgVirtServicesEntry 31 }

slbNewCfgVirtServiceLdapslb OBJECT-TYPE 
    SYNTAX  INTEGER {
        enabled(1),
        disabled(2),
        unsupported(2147483647)
        }
    MAX-ACCESS  read-create 
    STATUS  current 
    DESCRIPTION 
        "Enable or disable LDAP Server load balancing"  
    ::= { slbNewCfgVirtServicesEntry 32 }

slbNewCfgVirtServiceSip OBJECT-TYPE   
    SYNTAX  INTEGER {
        enabled(1),
	disabled(2),
        unsupported(2147483647)
	}
    MAX-ACCESS  read-create   
    STATUS  current   
    DESCRIPTION 
        "Enable/disable SIP load balancing."
    ::= { slbNewCfgVirtServicesEntry 33 }

slbNewCfgVirtServiceXForwardedFor OBJECT-TYPE   
    SYNTAX  INTEGER {
        enabled(1),
	disabled(2),
        unsupported(2147483647)
	}
    MAX-ACCESS  read-create
    STATUS  current   
    DESCRIPTION 
        "Enable/disable X-Forwarded-For for proxy mode."
    ::= { slbNewCfgVirtServicesEntry 34 }

slbNewCfgVirtServiceHttpRedir OBJECT-TYPE
    SYNTAX  INTEGER {
        enabled(1),
        disabled(2),
        unsupported(2147483647)
        }
    MAX-ACCESS  read-create
    STATUS  current
    DESCRIPTION
        "Enable/disable HTTP/HTTPS redirect for GSLB."
    ::= { slbNewCfgVirtServicesEntry 35 }

slbNewCfgVirtServicePbindRport OBJECT-TYPE   
    SYNTAX  INTEGER {
        enabled(1),
	disabled(2),
        unsupported(2147483647)
	}
    MAX-ACCESS  read-create
    STATUS  current   
    DESCRIPTION 
        "Enable or disable use of rport in the session lookup for a persistent
         session."
    ::= { slbNewCfgVirtServicesEntry 36 }
    
slbNewCfgVirtServiceEgressPip OBJECT-TYPE   
    SYNTAX  INTEGER {
        enabled(1),
	disabled(2),
        unsupported(2147483647)
	}
    MAX-ACCESS  read-create
    STATUS  current   
    DESCRIPTION 
        "Enable/disable pip selection based on egress port/vlan."
    ::= { slbNewCfgVirtServicesEntry 37 }

slbNewCfgVirtServiceCookieDname OBJECT-TYPE
    SYNTAX INTEGER {
        enabled(1),
        disabled(2),
        unsupported(2147483647)
        }
    MAX-ACCESS read-create
    STATUS current
    DESCRIPTION
        "Select dname for insert cookie persistence mode."
    ::= { slbNewCfgVirtServicesEntry 38 }
    
slbNewCfgVirtServiceWts OBJECT-TYPE
    SYNTAX INTEGER {
        enabled(1),
        disabled(2),
        unsupported(2147483647)
        }
    MAX-ACCESS read-create
    STATUS current
    DESCRIPTION
        "Enable or disable WTS loadbalancing and persistence."
    ::= { slbNewCfgVirtServicesEntry 39 }

slbNewCfgVirtServiceUhash OBJECT-TYPE
    SYNTAX INTEGER {
        enabled(1),
        disabled(2),
        unsupported(2147483647)
        }
    MAX-ACCESS read-create
    STATUS current
    DESCRIPTION
        "Enable when there is no Session Directory server."
    ::= { slbNewCfgVirtServicesEntry 40 }


slbNewCfgVirtServiceTimeOut OBJECT-TYPE
    SYNTAX  INTEGER (0..32768)
    MAX-ACCESS  read-create
    STATUS  current
    DESCRIPTION
        "The maximum number of minutes an inactive connection remains open."
    ::= { slbNewCfgVirtServicesEntry 41 }

slbNewCfgVirtServiceSessionMirror OBJECT-TYPE
    SYNTAX  INTEGER {
        enabled(1),
        disabled(2),
        unsupported(2147483647)
        }
    MAX-ACCESS  read-create
    STATUS  current
    DESCRIPTION
        "Enable/disable session mirroring."
    ::= { slbNewCfgVirtServicesEntry 43 }

slbNewCfgVirtServiceSoftGrid OBJECT-TYPE
    SYNTAX  INTEGER {
        enabled(1),
        disabled(2),
        unsupported(2147483647)
        }
    MAX-ACCESS  read-create
    STATUS  current
    DESCRIPTION
        "Enable/disable softgrid load balancing."
    ::= { slbNewCfgVirtServicesEntry 44 }

slbNewCfgVirtServiceSdpNat OBJECT-TYPE
    SYNTAX  INTEGER {
        enabled(1),
        disabled(2),
        unsupported(2147483647)
        }
    MAX-ACCESS  read-create
    STATUS  current
    DESCRIPTION
        "Enable/disable SIP Media portal NAT."
    ::= { slbNewCfgVirtServicesEntry 42 }

slbNewCfgVirtServiceConnPooling OBJECT-TYPE
    SYNTAX  INTEGER {
        enabled(1),
            disabled(2),
        unsupported(2147483647)
    }
    MAX-ACCESS  read-create
    STATUS  current
    DESCRIPTION
        "Enable/disable connection pooling for HTTP traffic."
    ::= { slbNewCfgVirtServicesEntry 45 }

slbNewCfgVirtPersistentTimeOut OBJECT-TYPE
    SYNTAX  INTEGER (0..32768)
    MAX-ACCESS  read-create
    STATUS  current
    DESCRIPTION
        "The maximum number of minutes a persistent session should exist."
    ::= { slbNewCfgVirtServicesEntry 46 }

--Proxy IP New config start
slbNewCfgVirtServiceProxyIpMode OBJECT-TYPE   
    SYNTAX INTEGER {
        ingress(0),
	 egress(1),
	 address(2),
	 nwclss(3),
        disable(4),
        unsupported(2147483647)
        }
    MAX-ACCESS  read-create
    STATUS  current
    DESCRIPTION
        "Set the Proxy IP mode, default is ingress(0).
		Changing from address(2) to any other mode will clear the configured IPv4/IPv6 address,prefix and persistancy.
		Changing from  nwclass(3) to any other mode will clear the configured NWclass and NWpersistancy."
    ::= { slbNewCfgVirtServicesEntry 47 }

    slbNewCfgVirtServiceProxyIpAddr OBJECT-TYPE
    SYNTAX  IpAddress
    MAX-ACCESS  read-create
    STATUS  current
    DESCRIPTION
        "This object ID allows configuring IPv4 PIP address. 
		This object ID can be set only if slbNewCfgVirtServiceProxyIpMode is address else return failure.
		Returns 0 when slbNewCfgVirtServiceProxyIpMode is not set to address.  
		When a subnet is configured user has the ability to select PIP persistency mode.
		Persistency is relevant only if either IPv4 PIP or IPv6 PIP (or both) are configured as
		subnet.
		If neither of the addresses (v4 & v6) are configured or are subnets, the persistency
		value is disable." 
    ::= { slbNewCfgVirtServicesEntry 48 }

   slbNewCfgVirtServiceProxyIpMask OBJECT-TYPE
    SYNTAX  IpAddress
    MAX-ACCESS  read-create
    STATUS  current
    DESCRIPTION
        "This object ID allows configuring IPv4 PIP Mask. 
		Returns 0 when slbNewCfgVirtServiceProxyIpMode is not set to address.  
		When a subnet is configured user has the ability to select PIP persistency mode.
		Persistency is relevant only if either IPv4 PIP or IPv6 PIP (or both) are configured as
		subnet.
		If neither of the addresses (v4 & v6) are configured or are subnets, the persistency
		value is disable." 
    ::= { slbNewCfgVirtServicesEntry 49 }

    slbNewCfgVirtServiceProxyIpv6Addr OBJECT-TYPE
    SYNTAX  DisplayString  (SIZE(0..40)) 
    MAX-ACCESS  read-create
    STATUS  current
    DESCRIPTION
        "This object ID allows configuring IPv6 PIP address. 
		Returns 0 when slbNewCfgVirtServiceProxyIpMode is not set to address.  
		When a subnet is configured user has the ability to select PIP persistency mode.
		Persistency is relevant only if either IPv4 PIP or IPv6 PIP (or both) are configured as
		subnet.
		Address should be 4-byte hexadecimal colon notation.
		Valid IPv6 address should be in any of the following forms
		       xxxx:xxxx:xxxx:xxxx:xxxx:xxxx:xxxx:xxxx or
		       xxxx::xxxx:xxxx:xxxx:xxxx or ::xxxx.
		If neither of the addresses (v4 & v6) are configured or are subnets, the persistency
		value is disable." 
    ::= { slbNewCfgVirtServicesEntry 50 }

   slbNewCfgVirtServiceProxyIpv6Prefix OBJECT-TYPE
    SYNTAX  INTEGER (1..128)
    MAX-ACCESS  read-create
    STATUS  current
    DESCRIPTION
        "This object ID allows configuring IPv6 PIP Mask. 
		Returns 0 when slbNewCfgVirtServiceProxyIpMode is not set to address.  
		When a subnet is configured user has the ability to select PIP persistency mode.
		Persistency is relevant only if either IPv4 PIP or IPv6 PIP (or both) are configured as
		subnet.
		If neither of the addresses (v4 & v6) are configured or are subnets, the persistency
		value is disable." 
    ::= { slbNewCfgVirtServicesEntry 51 }

slbNewCfgVirtServiceProxyIpPersistency OBJECT-TYPE   
    SYNTAX INTEGER {
        disable(0),
        client(1),
	 host(2),
        unsupported(2147483647)
        }
    MAX-ACCESS  read-create
    STATUS  current
    DESCRIPTION
        "When a subnet is configured user has the ability to select PIP persistency mode.
		Returns 0 when slbNewCfgVirtServiceProxyIpMode is not set to address.          
		Persistency is relevant only if either IPv4 PIP or IPv6 PIP (or both) are configured as
		subnet.
		If neither of the addresses (v4 & v6) are configured or are subnets, the persistency
		value is disable. "
    ::= { slbNewCfgVirtServicesEntry 52 }

   slbNewCfgVirtServiceProxyIpNWclass OBJECT-TYPE
    SYNTAX  DisplayString  (SIZE(0..32)) 
    MAX-ACCESS  read-create
    STATUS  current
    DESCRIPTION
        "This object ID allows configuring IPv4 Network Class as PIP and PIP persistency mode.
		Returns empty string when slbNewCfgVirtServiceProxyIpMode is not set to nwclass.          
		Persistency is relevant only if either IPv4 or IPv6 class (or both) are configured.
		If neither of the classes (v4 & v6) are configured, the persistency configuration value is disable." 
    ::= { slbNewCfgVirtServicesEntry 53 }

   slbNewCfgVirtServiceProxyIpv6NWclass OBJECT-TYPE
    SYNTAX  DisplayString  (SIZE(0..32)) 
    MAX-ACCESS  read-create
    STATUS  current
    DESCRIPTION
        "This object ID allows configuring IPv6 Network Class as PIP and PIP persistency mode.
		Returns empty string when slbNewCfgVirtServiceProxyIpMode is not set to nwclass.          
		Persistency is relevant only if either IPv4 or IPv6 class (or both) are configured.
		If neither of the classes (v4 & v6) are configured, the persistency configuration value is disable." 
    ::= { slbNewCfgVirtServicesEntry 54 }

slbNewCfgVirtServiceProxyIpNWclassPersistency OBJECT-TYPE   
    SYNTAX INTEGER {
        disable(0),
        client(1),
        unsupported(2147483647)
        }
    MAX-ACCESS  read-create
    STATUS  current
    DESCRIPTION
        "This object ID allows configuring Network Class PIP persistency mode.
		Returns 0 when slbNewCfgVirtServiceProxyIpMode is not set to nwclass.          
		Persistency is relevant only if either IPv4 PIP or IPv6 PIP (or both) are configured as
		subnet.
		If neither of the addresses (v4 & v6) are configured or are subnets, the persistency
		value is disable. "
    ::= { slbNewCfgVirtServicesEntry 55 }    
--Proxy IP New config end

slbNewCfgVirtServiceHashLen OBJECT-TYPE
    SYNTAX INTEGER (4..256)
    MAX-ACCESS  read-create
    STATUS  current
    DESCRIPTION
        "Set length for slb service sip hashing (4- 256 bytes)"
    ::= { slbNewCfgVirtServicesEntry 56 }

slbNewCfgVirtServiceApm OBJECT-TYPE
    SYNTAX  INTEGER {
        enabled(1),
        disabled(2),
        unsupported(2147483647)
        }
    MAX-ACCESS  read-create
    STATUS  obsolete
    DESCRIPTION
        "Enable/disable apm."
    ::= { slbNewCfgVirtServicesEntry 57 }

slbNewCfgVirtServiceClsRST OBJECT-TYPE   
    SYNTAX  INTEGER {
	enabled(1),
	disabled(2),
        unsupported(2147483647)
	}
    MAX-ACCESS  read-create
    STATUS  current   
    DESCRIPTION 
        "Enable or disable Send RST on connection close."
    ::= { slbNewCfgVirtServicesEntry 58 }
    
slbNewCfgVirtServiceNonHTTP OBJECT-TYPE   
    SYNTAX  INTEGER {
	enabled(1),
	disabled(2),
        unsupported(2147483647)
	}
    MAX-ACCESS  read-create
    STATUS  current   
    DESCRIPTION 
        "Enable or disable Send non-HTTP traffic."
    ::= { slbNewCfgVirtServicesEntry 59 }

slbNewCfgVirtServicesSecondPartTable OBJECT-TYPE
    SYNTAX  SEQUENCE OF SlbNewCfgVirtServicesSecondPartEntry
    MAX-ACCESS  not-accessible
    STATUS  current
    DESCRIPTION
        "The table of virtual Services.
         Note:This mib is not supported for VX instance of Virtualization."
    ::= { virtualServerCfg 16 }

slbNewCfgVirtServicesSecondPartEntry OBJECT-TYPE
    SYNTAX  SlbNewCfgVirtServicesSecondPartEntry
    MAX-ACCESS  not-accessible
    STATUS  current
    DESCRIPTION
        "A row in the virtual services table."
    INDEX   { slbNewCfgVirtServSecondPartIndex, slbNewCfgVirtServiceSecondPartIndex }
    ::= { slbNewCfgVirtServicesSecondPartTable 1 }

SlbNewCfgVirtServicesSecondPartEntry ::= SEQUENCE {
    slbNewCfgVirtServSecondPartIndex            Integer32,
    slbNewCfgVirtServiceSecondPartIndex         Integer32,

    slbNewCfgVirtServiceConnmgtStatus  INTEGER,
    slbNewCfgVirtServiceConnmgtTimeout INTEGER,
    slbNewCfgVirtServiceCachepol      DisplayString,
    slbNewCfgVirtServiceComppol       DisplayString,
    slbNewCfgVirtServiceSSLpol        DisplayString,
    slbNewCfgVirtServiceServCert      DisplayString,
    slbNewCfgVirtServiceHttpmodList   DisplayString,
    slbNewCfgVirtServiceCloaksrv      INTEGER,

    slbNewCfgVirtServErrcodeStatus    INTEGER,
    slbNewCfgVirtServErrcodeMatch     DisplayString,
    slbNewCfgVirtServErrcodeHttpRedir INTEGER,
    slbNewCfgVirtServErrcodeUrl       DisplayString,
    slbNewCfgVirtServErrcode          DisplayString,
    slbNewCfgVirtServErrcodeNew       DisplayString,
    slbNewCfgVirtServErrcodeReason    DisplayString,
    slbNewCfgVirtServUrlchangStatus     INTEGER,
    slbNewCfgVirtServUrlchangHostType   INTEGER
}

slbNewCfgVirtServSecondPartIndex OBJECT-TYPE
    SYNTAX  Integer32
    MAX-ACCESS  read-only
    STATUS  current
    DESCRIPTION
        "The number of the virtual server." 
    ::= { slbNewCfgVirtServicesSecondPartEntry 1 }

slbNewCfgVirtServiceSecondPartIndex OBJECT-TYPE 
    SYNTAX  Integer32 
    MAX-ACCESS  read-only 
    STATUS  current 
    DESCRIPTION 
        "The service index. This has no external meaning" 
    ::= { slbNewCfgVirtServicesSecondPartEntry 2 }


slbNewCfgVirtServiceConnmgtStatus OBJECT-TYPE
    SYNTAX  INTEGER {
        disabled(0),
        pooling(1),
        muxenabled(2),
        unsupported(2147483647)
        }
    MAX-ACCESS  read-create
    STATUS  current
    DESCRIPTION
        "Connection management configuration for HTTP traffic(Enable/disable/pooling) [Default: Disable]."
    ::= { slbNewCfgVirtServicesSecondPartEntry 3 }

slbNewCfgVirtServiceConnmgtTimeout OBJECT-TYPE
    SYNTAX  INTEGER (0..32768)
    MAX-ACCESS  read-create
    STATUS  current
    DESCRIPTION
        "Connection management server side connection idle timeout in minutes [0-32768] [Default: 10]."
    ::= { slbNewCfgVirtServicesSecondPartEntry 4 }

slbNewCfgVirtServiceCachepol OBJECT-TYPE
    SYNTAX  DisplayString  (SIZE(0..32))
    MAX-ACCESS  read-create
    STATUS  current
    DESCRIPTION
        "Cache policy name associated with this virtual service.Set none to delete entry"
    ::= { slbNewCfgVirtServicesSecondPartEntry 5 }

slbNewCfgVirtServiceComppol OBJECT-TYPE
    SYNTAX  DisplayString  (SIZE(0..32))
    MAX-ACCESS  read-create
    STATUS  current
    DESCRIPTION
        "Compression policy name associated with this virtual service.Set none to delete entry"
    ::= { slbNewCfgVirtServicesSecondPartEntry 6 }

slbNewCfgVirtServiceSSLpol OBJECT-TYPE
    SYNTAX  DisplayString  (SIZE(0..32))
    MAX-ACCESS  read-create
    STATUS  current
    DESCRIPTION
        "SSL policy name associated with this virtual service.Set none to delete entry"
    ::= { slbNewCfgVirtServicesSecondPartEntry 7 }

slbNewCfgVirtServiceServCert OBJECT-TYPE
    SYNTAX  DisplayString  (SIZE(0..128))
    MAX-ACCESS  read-create
    STATUS  current
    DESCRIPTION
        "Server Certificate name associated with this virtual service."
    ::= { slbNewCfgVirtServicesSecondPartEntry 8 }

slbNewCfgVirtServiceHttpmodList OBJECT-TYPE
    SYNTAX  DisplayString  (SIZE(0..32))
    MAX-ACCESS  read-create
    STATUS  current
    DESCRIPTION
        "HTTP Content Modifications Rule-list associated with this virtual service.Set none to delete entry"
    ::= { slbNewCfgVirtServicesSecondPartEntry 9 }

slbNewCfgVirtServiceCloaksrv OBJECT-TYPE
    SYNTAX  INTEGER {
        enabled(1),
        disabled(2),
        unsupported(2147483647)
        }
    MAX-ACCESS  read-create
    STATUS  current
    DESCRIPTION
        "Enable/disable server cloaking."
    ::= { slbNewCfgVirtServicesSecondPartEntry 10 }

slbNewCfgVirtServErrcodeStatus OBJECT-TYPE
    SYNTAX  INTEGER {
        enabled(1),
        disabled(2),
        clear(3),
        unsupported(2147483647)
        }
    MAX-ACCESS  read-create
    STATUS  current
    DESCRIPTION
        "Enable/disable/clear error-code configuration."
    ::= { slbNewCfgVirtServicesSecondPartEntry 11 }

slbNewCfgVirtServErrcodeMatch OBJECT-TYPE
    SYNTAX  DisplayString (SIZE (0..64))
    MAX-ACCESS  read-create
    STATUS  current
    DESCRIPTION
        "Match error-code(s), e.g 203,204 ."
    ::= { slbNewCfgVirtServicesSecondPartEntry 12 }

slbNewCfgVirtServErrcodeHttpRedir OBJECT-TYPE
    SYNTAX  INTEGER {
        yes(1),
        no(2),
        unsupported(2147483647)
    }
    MAX-ACCESS  read-create
    STATUS  current
    DESCRIPTION
        "Use http redirection [yes/no] [Default: yes]."
    ::= { slbNewCfgVirtServicesSecondPartEntry 13 }

slbNewCfgVirtServErrcodeUrl OBJECT-TYPE
    SYNTAX  DisplayString (SIZE(0..240))
    MAX-ACCESS  read-create
    STATUS  current
    DESCRIPTION
        "URL for redirection."
    ::= { slbNewCfgVirtServicesSecondPartEntry 14 }


slbNewCfgVirtServErrcode OBJECT-TYPE
    SYNTAX  DisplayString (SIZE(0..3))
    MAX-ACCESS  read-create
    STATUS  current
    DESCRIPTION
        "set error code [Default: 302]."
    ::= { slbNewCfgVirtServicesSecondPartEntry 15 }

slbNewCfgVirtServErrcodeNew OBJECT-TYPE
    SYNTAX DisplayString (SIZE(0..3)) 
    MAX-ACCESS  read-create
    STATUS  current
    DESCRIPTION
        "Enter new error code [Default: 302]."
    ::= { slbNewCfgVirtServicesSecondPartEntry 16 }

slbNewCfgVirtServErrcodeReason OBJECT-TYPE
    SYNTAX  DisplayString (SIZE(0..128))
    MAX-ACCESS  read-create
    STATUS  current
    DESCRIPTION
        "Enter error reason."
    ::= { slbNewCfgVirtServicesSecondPartEntry 17 }

slbNewCfgVirtServUrlchangStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgVirtServicesSecondPartEntry 18 }

slbNewCfgVirtServUrlchangHostType OBJECT-TYPE
    SYNTAX  INTEGER {
        sufx(1),
        prefx(2),
        eq(3),
        incl(4),
        any(5),
        unsupported(2147483647)
    }
    MAX-ACCESS  read-create
    STATUS  current
    DESCRIPTION
        "Enter hostname match type [sufx|prefx|eq|incl|any] [Default: any]"
    ::= { slbNewCfgVirtServicesSecondPartEntry 19 }



slbNewCfgVirtServicesThirdPartTable OBJECT-TYPE
    SYNTAX  SEQUENCE OF SlbNewCfgVirtServicesThirdPartEntry
    MAX-ACCESS  not-accessible
    STATUS  current
    DESCRIPTION
        "The table of virtual Services.
         Note:This mib is not supported for VX instance of Virtualization."
    ::= { virtualServerCfg 17 }

slbNewCfgVirtServicesThirdPartEntry OBJECT-TYPE
    SYNTAX  SlbNewCfgVirtServicesThirdPartEntry
    MAX-ACCESS  not-accessible
    STATUS  current
    DESCRIPTION
        "A row in the virtual services table."
    INDEX   { slbNewCfgVirtServThirdPartIndex, slbNewCfgVirtServiceThirdPartIndex }
    ::= { slbNewCfgVirtServicesThirdPartTable 1 }

SlbNewCfgVirtServicesThirdPartEntry ::= SEQUENCE {
    slbNewCfgVirtServThirdPartIndex            Integer32,
    slbNewCfgVirtServiceThirdPartIndex         Integer32,

    slbNewCfgVirtServUrlchangHostName   DisplayString,
    slbNewCfgVirtServUrlchangPathType   INTEGER,
    slbNewCfgVirtServUrlchangPathMatch  DisplayString,
    slbNewCfgVirtServUrlchangPageName   DisplayString,
    slbNewCfgVirtServUrlchangPageType   DisplayString,
    slbNewCfgVirtServUrlchangActnType   INTEGER,
    slbNewCfgVirtServUrlchangPathInsrt  DisplayString,
    slbNewCfgVirtServUrlchangInsrtPostn INTEGER
}


slbNewCfgVirtServThirdPartIndex OBJECT-TYPE
    SYNTAX  Integer32
    MAX-ACCESS  read-only
    STATUS  current
    DESCRIPTION
        "The number of the virtual server." 
    ::= { slbNewCfgVirtServicesThirdPartEntry 1 }

slbNewCfgVirtServiceThirdPartIndex OBJECT-TYPE 
    SYNTAX  Integer32 
    MAX-ACCESS  read-only 
    STATUS  current 
    DESCRIPTION 
        "The service index. This has no external meaning" 
    ::= { slbNewCfgVirtServicesThirdPartEntry 2 }

slbNewCfgVirtServUrlchangHostName OBJECT-TYPE
    SYNTAX  DisplayString (SIZE(0..250))
    MAX-ACCESS  read-create
    STATUS  current
    DESCRIPTION
        "Enter hostname to match."
    ::= { slbNewCfgVirtServicesThirdPartEntry 3 }

slbNewCfgVirtServUrlchangPathType OBJECT-TYPE
    SYNTAX  INTEGER {
        sufx(1),
        prefx(2),
        eq(3),
        incl(4),
        any(5),
        none(6),
        unsupported(2147483647)
    }
    MAX-ACCESS  read-create
    STATUS  current
    DESCRIPTION
        "Enter path match type [sufx|prefx|eq|incl|any|none]."
    ::= { slbNewCfgVirtServicesThirdPartEntry 4 }

slbNewCfgVirtServUrlchangPathMatch OBJECT-TYPE
    SYNTAX  DisplayString (SIZE(0..250))
    MAX-ACCESS  read-create
    STATUS  current
    DESCRIPTION
        "Enter path to match."
    ::= { slbNewCfgVirtServicesThirdPartEntry 5 }

slbNewCfgVirtServUrlchangPageName OBJECT-TYPE
    SYNTAX  DisplayString (SIZE(0..64))
    MAX-ACCESS  read-create
    STATUS  current
    DESCRIPTION
        "Enter page name to match or none."
    ::= { slbNewCfgVirtServicesThirdPartEntry 6 }

slbNewCfgVirtServUrlchangPageType OBJECT-TYPE
    SYNTAX  DisplayString (SIZE(0..64))
    MAX-ACCESS  read-create
    STATUS  current
    DESCRIPTION
        "Enter page type to match or none."
    ::= { slbNewCfgVirtServicesThirdPartEntry 7 }

slbNewCfgVirtServUrlchangActnType OBJECT-TYPE
    SYNTAX  INTEGER {
        insert(1),
        replace(2),
        remove(3),
        none(4),
        unsupported(2147483647)
    }
    MAX-ACCESS  read-create
    STATUS  current
    DESCRIPTION
        "Enter path action type."
    ::= { slbNewCfgVirtServicesThirdPartEntry 8 }

slbNewCfgVirtServUrlchangPathInsrt OBJECT-TYPE
    SYNTAX  DisplayString (SIZE(0..250))
    MAX-ACCESS  read-create
    STATUS  current
    DESCRIPTION
        "Enter path to insert."
    ::= { slbNewCfgVirtServicesThirdPartEntry 9 }


slbNewCfgVirtServUrlchangInsrtPostn OBJECT-TYPE
    SYNTAX  INTEGER {
        before(1),
        after(2),
        unsupported(2147483647)
    }
    MAX-ACCESS  read-create
    STATUS  current
    DESCRIPTION
        "Insert the specified path before or after the matched section"
    ::= { slbNewCfgVirtServicesThirdPartEntry 10 }



slbNewCfgVirtServicesFourthPartTable OBJECT-TYPE
    SYNTAX  SEQUENCE OF SlbNewCfgVirtServicesFourthPartEntry
    MAX-ACCESS  not-accessible
    STATUS  current
    DESCRIPTION
        "The table of virtual Services.
         Note:This mib is not supported for VX instance of Virtualization."
    ::= { virtualServerCfg 18 }

slbNewCfgVirtServicesFourthPartEntry OBJECT-TYPE
    SYNTAX  SlbNewCfgVirtServicesFourthPartEntry
    MAX-ACCESS  not-accessible
    STATUS  current
    DESCRIPTION
        "A row in the virtual services table."
    INDEX   { slbNewCfgVirtServFourthPartIndex, slbNewCfgVirtServiceFourthPartIndex }
    ::= { slbNewCfgVirtServicesFourthPartTable 1 }

SlbNewCfgVirtServicesFourthPartEntry ::= SEQUENCE {
    slbNewCfgVirtServFourthPartIndex            Integer32,
    slbNewCfgVirtServiceFourthPartIndex         Integer32,

    slbNewCfgVirtServUrlchangNewPgName  DisplayString,
    slbNewCfgVirtServUrlchangNewPgType  DisplayString,

    slbNewCfgVirtServPathHideStatus     INTEGER,
    slbNewCfgVirtServPathHideHostType   INTEGER,
    slbNewCfgVirtServPathHideHostName   DisplayString,
    slbNewCfgVirtServPathHidePathType   INTEGER,
    slbNewCfgVirtServPathHidePathName   DisplayString,

    slbNewCfgVirtServTextrepStatus      INTEGER,
    slbNewCfgVirtServTextrepAction      INTEGER
}

slbNewCfgVirtServFourthPartIndex OBJECT-TYPE
    SYNTAX  Integer32
    MAX-ACCESS  read-only
    STATUS  current
    DESCRIPTION
        "The number of the virtual server." 
    ::= { slbNewCfgVirtServicesFourthPartEntry 1 }

slbNewCfgVirtServiceFourthPartIndex OBJECT-TYPE 
    SYNTAX  Integer32 
    MAX-ACCESS  read-only 
    STATUS  current 
    DESCRIPTION 
        "The service index. This has no external meaning" 
    ::= { slbNewCfgVirtServicesFourthPartEntry 2 }

slbNewCfgVirtServUrlchangNewPgName OBJECT-TYPE
    SYNTAX  DisplayString (SIZE(0..64))
    MAX-ACCESS  read-create
    STATUS  current
    DESCRIPTION
        "Enter new page name or none."
    ::= { slbNewCfgVirtServicesFourthPartEntry 3 }

slbNewCfgVirtServUrlchangNewPgType OBJECT-TYPE
    SYNTAX  DisplayString (SIZE(0..64))
    MAX-ACCESS  read-create
    STATUS  current
    DESCRIPTION
        "Enter new page type or none."
    ::= { slbNewCfgVirtServicesFourthPartEntry 4 }

slbNewCfgVirtServPathHideStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgVirtServicesFourthPartEntry 5 }

slbNewCfgVirtServPathHideHostType OBJECT-TYPE
    SYNTAX  INTEGER {
        sufx(1),
        prefx(2),
        eq(3),
        incl(4),
        any(5),
        unsupported(2147483647)
    }
    MAX-ACCESS  read-create
    STATUS  current
    DESCRIPTION
        "Enter hostname type [sufx|prefx|eq|incl|any] [Default: any]."
    ::= { slbNewCfgVirtServicesFourthPartEntry 6 }

slbNewCfgVirtServPathHideHostName OBJECT-TYPE
    SYNTAX  DisplayString (SIZE(0..250))
    MAX-ACCESS  read-create
    STATUS  current
    DESCRIPTION
        "Enter hostname to match."
    ::= { slbNewCfgVirtServicesFourthPartEntry 7 }

slbNewCfgVirtServPathHidePathType OBJECT-TYPE
    SYNTAX  INTEGER {
        sufx(1),
        prefx(2),
        eq(3),
        none(4),
        unsupported(2147483647)
    }
    MAX-ACCESS  read-create
    STATUS  current
    DESCRIPTION
        "Enter path match type [sufx|prefx|eq|none]."
    ::= { slbNewCfgVirtServicesFourthPartEntry 8 }

slbNewCfgVirtServPathHidePathName OBJECT-TYPE
    SYNTAX  DisplayString (SIZE(0..250))
    MAX-ACCESS  read-create
    STATUS  current
    DESCRIPTION
        "Enter path to remove."
    ::= { slbNewCfgVirtServicesFourthPartEntry 9 }

slbNewCfgVirtServTextrepStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgVirtServicesFourthPartEntry 10 }

slbNewCfgVirtServTextrepAction OBJECT-TYPE
    SYNTAX  INTEGER {
        none(0),
        replace(1),
        remove(2),
        unsupported(2147483647)
    }
    MAX-ACCESS  read-create
    STATUS  current
    DESCRIPTION
        "Enter action [replace|remove|none]."
    ::= { slbNewCfgVirtServicesFourthPartEntry 11 }

slbNewCfgVirtServicesFifthPartTable OBJECT-TYPE
    SYNTAX  SEQUENCE OF SlbNewCfgVirtServicesFifthPartEntry
    MAX-ACCESS  not-accessible
    STATUS  current
    DESCRIPTION
        "The table of virtual Services.
         Note:This mib is not supported for VX instance of Virtualization."
    ::= { virtualServerCfg 19 }

slbNewCfgVirtServicesFifthPartEntry OBJECT-TYPE
    SYNTAX  SlbNewCfgVirtServicesFifthPartEntry
    MAX-ACCESS  not-accessible
    STATUS  current
    DESCRIPTION
        "A row in the virtual services table."
    INDEX   { slbNewCfgVirtServFifthPartIndex, slbNewCfgVirtServiceFifthPartIndex }
    ::= { slbNewCfgVirtServicesFifthPartTable 1 }

SlbNewCfgVirtServicesFifthPartEntry ::= SEQUENCE {

    slbNewCfgVirtServFifthPartIndex            Integer32,
    slbNewCfgVirtServiceFifthPartIndex         Integer32,

    slbNewCfgVirtServTextrepMatchText   DisplayString,
    slbNewCfgVirtServTextrepReplacTxt   DisplayString,

    slbNewCfgVirtServApplicationType    INTEGER,
    slbNewCfgVirtServiceName          DisplayString,
    slbNewCfgVirtServiceAction        INTEGER,
    slbNewCfgVirtServiceRedirect      DisplayString,

    slbNewCfgVirtServiceServCertGrpMark INTEGER,
    slbNewCfgVirtServiceDnsType         INTEGER,
    slbNewCfgVirtServiceClntproxType    INTEGER,
    slbNewCfgVirtServiceZerowinSize     INTEGER,
    slbNewCfgVirtServiceCookiePath    DisplayString,
    slbNewCfgVirtServiceCookieSecure    INTEGER,
    slbNewCfgVirtServiceNoRtsp          INTEGER,
    slbNewCfgVirtServiceCkRebind        INTEGER,
    slbNewCfgVirtServiceParseLimit      INTEGER,
    slbNewCfgVirtServiceParseLength     INTEGER,
    slbNewCfgVirtServiceUriNorm         INTEGER,
    slbNewCfgVirtServiceGranularity     INTEGER,
    slbNewCfgVirtServiceSessLog         INTEGER,
    slbNewCfgVirtServiceAppwallWebappId  DisplayString
}

slbNewCfgVirtServFifthPartIndex OBJECT-TYPE
    SYNTAX  Integer32
    MAX-ACCESS  read-only
    STATUS  current
    DESCRIPTION
        "The number of the virtual server." 
    ::= { slbNewCfgVirtServicesFifthPartEntry 1 }

slbNewCfgVirtServiceFifthPartIndex OBJECT-TYPE 
    SYNTAX  Integer32 
    MAX-ACCESS  read-only 
    STATUS  current 
    DESCRIPTION 
        "The service index. This has no external meaning" 
    ::= { slbNewCfgVirtServicesFifthPartEntry 2 }

slbNewCfgVirtServTextrepMatchText OBJECT-TYPE
    SYNTAX  DisplayString (SIZE(0..128))
    MAX-ACCESS  read-create
    STATUS  current
    DESCRIPTION
        "Enter text to be replaced."
    ::= { slbNewCfgVirtServicesFifthPartEntry 3 }

slbNewCfgVirtServTextrepReplacTxt OBJECT-TYPE
    SYNTAX  DisplayString (SIZE(0..128))
    MAX-ACCESS  read-create
    STATUS  current
    DESCRIPTION
        "Enter new text."
    ::= { slbNewCfgVirtServicesFifthPartEntry 4 }

slbNewCfgVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12),
      smtp(13),
      pop3(14),
      ip(15),
      mh-sctp(16)
    }
    MAX-ACCESS  read-create
    STATUS  current
    DESCRIPTION
        "Application Type for virtual service."
    ::= { slbNewCfgVirtServicesFifthPartEntry 5 }

slbNewCfgVirtServiceName OBJECT-TYPE
    SYNTAX  DisplayString (SIZE(0..32))
    MAX-ACCESS  read-create
    STATUS  current
    DESCRIPTION
        "The name of the virtual service."
    ::= { slbNewCfgVirtServicesFifthPartEntry 6 }

slbNewCfgVirtServiceAction OBJECT-TYPE
    SYNTAX  INTEGER    {
    group(1),
    redirect(2),
    discard(3),
    unsupported(2147483647)
    }
    MAX-ACCESS  read-create
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbNewCfgVirtServicesFifthPartEntry 7 }

slbNewCfgVirtServiceRedirect OBJECT-TYPE
    SYNTAX  DisplayString  (SIZE(0..255))
    MAX-ACCESS  read-create
    STATUS  current
    DESCRIPTION
        "application redirection location.We need to provide this
         value When action type is set to redirect(2)."
    ::= { slbNewCfgVirtServicesFifthPartEntry 8 }

slbNewCfgVirtServiceServCertGrpMark OBJECT-TYPE
    SYNTAX  INTEGER    {
    cert(1),
    group(2),
    unsupported(2147483647)
    }
    MAX-ACCESS  read-create
    STATUS  current
    DESCRIPTION
        "Group Mark for Server Certificate. If we set value as cert(0)
         It will denote that the server certificate (name) associated with 
         this virtual service, represents a certificate. Otherwise, a value of group(1), denotes that the server    
         certificate (name) represents a group."
    ::= { slbNewCfgVirtServicesFifthPartEntry 9}

slbNewCfgVirtServiceDnsType OBJECT-TYPE
    SYNTAX  INTEGER {
        dns(1),
        dnssec(2),
        both(3),
        unsupported(2147483647)
        }
    MAX-ACCESS  read-create
    STATUS  current
    DESCRIPTION
        "Set DNS type for this service (DNS, DNSSEC)."
    ::= { slbNewCfgVirtServicesFifthPartEntry 10 }

slbNewCfgVirtServiceClntproxType OBJECT-TYPE
    SYNTAX  INTEGER {
        none(1),
        http(2),
        https(3),
        unsupported(2147483647)
        }
    MAX-ACCESS  read-create
    STATUS  current
    DESCRIPTION
        "Set client proximity type for this service."
    ::= { slbNewCfgVirtServicesFifthPartEntry 11 }

slbNewCfgVirtServiceZerowinSize OBJECT-TYPE
    SYNTAX  INTEGER {
        enabled(1),
        disabled(2),
        unsupported(2147483647)
        }
    MAX-ACCESS  read-create
    STATUS  current
    DESCRIPTION
        "Enable or disable zero window size in SYN+ACK for this service."
    ::= { slbNewCfgVirtServicesFifthPartEntry 12 }

slbNewCfgVirtServiceCookiePath OBJECT-TYPE
    SYNTAX  DisplayString (SIZE(0..32))
    MAX-ACCESS  read-create
    STATUS  current
    DESCRIPTION
        "The cookie path name of the virtual server used for cookie load balance."
    ::= { slbNewCfgVirtServicesFifthPartEntry 13 }

slbNewCfgVirtServiceCookieSecure OBJECT-TYPE
    SYNTAX  INTEGER {
	    no(1),
        yes(2),
        unsupported(2147483647)
        }
    MAX-ACCESS  read-create
    STATUS  current
    DESCRIPTION
        "Is cookie secure [yes/no] [Default: no]."
    ::= { slbNewCfgVirtServicesFifthPartEntry 14 }

slbNewCfgVirtServiceNoRtsp OBJECT-TYPE
    SYNTAX  INTEGER {
	enabled(1),
        disabled(2),
        unsupported(2147483647)
        }
    MAX-ACCESS  read-create
    STATUS  current
    DESCRIPTION
        "Enable or disable only rtsp SLB for this service."
    ::= { slbNewCfgVirtServicesFifthPartEntry 15 }

slbNewCfgVirtServiceCkRebind OBJECT-TYPE
    SYNTAX  INTEGER {
        enabled(1),
        disabled(2),
        unsupported(2147483647)
        }
    MAX-ACCESS  read-create
    STATUS  current
    DESCRIPTION
        "Enable or disable server rebalancing when cookie is absent.
        When enabled, server load balancing will happen
        for subsequent request comes without cookie."
    ::= { slbNewCfgVirtServicesFifthPartEntry 16 }

slbNewCfgVirtServiceParseLimit OBJECT-TYPE
    SYNTAX  INTEGER {
        enabled(1),
        disabled(2),
        unsupported(2147483647)
        }
    MAX-ACCESS  read-create
    STATUS  current
    DESCRIPTION
        "Enable or disable buffer limit for content based selection."
    ::= { slbNewCfgVirtServicesFifthPartEntry 17 }

slbNewCfgVirtServiceParseLength OBJECT-TYPE
    SYNTAX  INTEGER (0..18200)
    MAX-ACCESS  read-create
    STATUS  current
    DESCRIPTION
        "The buffer length for content based selection."
    ::= { slbNewCfgVirtServicesFifthPartEntry 18 }

slbNewCfgVirtServiceUriNorm OBJECT-TYPE
    SYNTAX  INTEGER {
        enabled(1),
        disabled(2),
        unsupported(2147483647)
        }
    MAX-ACCESS  read-create
    STATUS  current
    DESCRIPTION
        "Enable or disable URI normalization for HTTP content matching."
    ::= { slbNewCfgVirtServicesFifthPartEntry 19 }

slbNewCfgVirtServiceGranularity OBJECT-TYPE
    SYNTAX  INTEGER {
	service(0),
        real(2),
        unsupported(2147483647)
        }
    MAX-ACCESS  read-create
    STATUS  current
    DESCRIPTION
        "Sets the Granularity for this service, for statistics report-protocol information.
	Group(1) - for group level, or GroupAndServers(2) - for server level."
    ::= { slbNewCfgVirtServicesFifthPartEntry 20 }

slbNewCfgVirtServiceSessLog OBJECT-TYPE
    SYNTAX  INTEGER {
        enabled(1),
        disabled(2),
        unsupported(2147483647)
        }
    MAX-ACCESS  read-create
    STATUS  current
    DESCRIPTION
        "Enable or disable Session Logging."
    ::= { slbNewCfgVirtServicesFifthPartEntry 21 }

slbNewCfgVirtServiceAppwallWebappId OBJECT-TYPE
    SYNTAX  DisplayString  (SIZE(0..32)) 
    MAX-ACCESS  read-create
    STATUS  current
    DESCRIPTION
        "This object ID allows configuring the web security ID" 
    ::= { slbNewCfgVirtServicesFifthPartEntry 22 }

-- URL based BWM table for Virtual Services

slbUrlBwmTableMaxSize OBJECT-TYPE
    SYNTAX  Integer32 
    MAX-ACCESS  read-only 
    STATUS  current 
    DESCRIPTION 
        "The maximum number of entries in SLB URL BWM Table.
         Note:This mib is not supported for VX instance of Virtualization." 
    ::= { virtualServerCfg 7}

slbCurCfgUrlBwmTable OBJECT-TYPE
    SYNTAX  SEQUENCE OF SlbCurCfgUrlBwmEntry
    MAX-ACCESS  not-accessible
    STATUS  current
    DESCRIPTION
        "The table of URL based BWM for Virtual Services.
         Note:This mib is not supported for VX instance of Virtualization."
    ::= { virtualServerCfg 8 }

slbCurCfgUrlBwmEntry OBJECT-TYPE
    SYNTAX  SlbCurCfgUrlBwmEntry
    MAX-ACCESS  not-accessible
    STATUS  current
    DESCRIPTION
        "A row in the URL based BWM virtual services table."
    INDEX   { slbCurCfgUrlBwmVirtServIndex, 
              slbCurCfgUrlBwmVirtServiceIndex, 
              slbCurCfgUrlBwmUrlId }
    ::= { slbCurCfgUrlBwmTable 1 }

SlbCurCfgUrlBwmEntry ::= SEQUENCE {
    slbCurCfgUrlBwmVirtServIndex     Integer32,
    slbCurCfgUrlBwmVirtServiceIndex  Integer32,
    slbCurCfgUrlBwmUrlId             Integer32,
    slbCurCfgUrlBwmContract          Integer32
    }

slbCurCfgUrlBwmVirtServIndex OBJECT-TYPE
    SYNTAX  Integer32
    MAX-ACCESS  read-only
    STATUS  current
    DESCRIPTION
        "The number of the virtual server." 
    ::= { slbCurCfgUrlBwmEntry 1 }

slbCurCfgUrlBwmVirtServiceIndex OBJECT-TYPE 
    SYNTAX  Integer32 
    MAX-ACCESS  read-only 
    STATUS  current 
    DESCRIPTION 
        "The service index. This has no external meaning" 
    ::= { slbCurCfgUrlBwmEntry 2 }

slbCurCfgUrlBwmUrlId OBJECT-TYPE  
    SYNTAX  Integer32  
    MAX-ACCESS  read-only  
    STATUS  current  
    DESCRIPTION 
        "The URL Path Identifier."  
    ::= { slbCurCfgUrlBwmEntry 3 } 

slbCurCfgUrlBwmContract OBJECT-TYPE  
    SYNTAX  Integer32  
    MAX-ACCESS  read-only  
    STATUS  current  
    DESCRIPTION 
        "The BW contract number."  
    ::= { slbCurCfgUrlBwmEntry 4 } 

slbNewCfgUrlBwmTable OBJECT-TYPE
    SYNTAX  SEQUENCE OF SlbNewCfgUrlBwmEntry
    MAX-ACCESS  not-accessible
    STATUS  current
    DESCRIPTION
        "The table of URL based BWM for Virtual Services.
         Note:This mib is not supported for VX instance of Virtualization."
    ::= { virtualServerCfg 9 }

slbNewCfgUrlBwmEntry OBJECT-TYPE
    SYNTAX  SlbNewCfgUrlBwmEntry
    MAX-ACCESS  not-accessible
    STATUS  current
    DESCRIPTION
        "A row in the URL based BWM virtual services table."
    INDEX   { slbNewCfgUrlBwmVirtServIndex, 
              slbNewCfgUrlBwmVirtServiceIndex, 
              slbNewCfgUrlBwmUrlId }
    ::= { slbNewCfgUrlBwmTable 1 }

SlbNewCfgUrlBwmEntry ::= SEQUENCE {
    slbNewCfgUrlBwmVirtServIndex     Integer32,
    slbNewCfgUrlBwmVirtServiceIndex  Integer32,
    slbNewCfgUrlBwmUrlId             Integer32,
    slbNewCfgUrlBwmContract          Integer32,
    slbNewCfgUrlBwmDelete            INTEGER
    }

slbNewCfgUrlBwmVirtServIndex OBJECT-TYPE
    SYNTAX  Integer32
    MAX-ACCESS  read-only
    STATUS  current
    DESCRIPTION
        "The number of the virtual server." 
    ::= { slbNewCfgUrlBwmEntry 1 }

slbNewCfgUrlBwmVirtServiceIndex OBJECT-TYPE 
    SYNTAX  Integer32 
    MAX-ACCESS  read-only 
    STATUS  current 
    DESCRIPTION 
        "The service index. This has no external meaning" 
    ::= { slbNewCfgUrlBwmEntry 2 }

slbNewCfgUrlBwmUrlId OBJECT-TYPE  
    SYNTAX  Integer32  
    MAX-ACCESS  read-only  
    STATUS  current  
    DESCRIPTION 
        "The URL Path Identifier."  
    ::= { slbNewCfgUrlBwmEntry 3 } 

slbNewCfgUrlBwmContract OBJECT-TYPE  
    SYNTAX  Integer32  
    MAX-ACCESS  read-create  
    STATUS  current  
    DESCRIPTION 
        "The BW contract number."
    ::= { slbNewCfgUrlBwmEntry 4 } 

slbNewCfgUrlBwmDelete OBJECT-TYPE
    SYNTAX  INTEGER {
        other(1),
        delete(2),
        unsupported(2147483647)
       }
    MAX-ACCESS  read-create
    STATUS  current
    DESCRIPTION
        "When set to the value of 2 (delete), the entire row is deleted. 
         When read, other(1) is returned. Setting the value to anything 
         other than 2(delete) has no effect on the state of the row."
    ::= { slbNewCfgUrlBwmEntry 5 }

--L7 Content based services rule
slbCurCfgContRuleTable OBJECT-TYPE
    SYNTAX  SEQUENCE OF SlbCurCfgContRuleEntry
    MAX-ACCESS  not-accessible
    STATUS  current
    DESCRIPTION
        "The table of Content based Services Rules.
         Note:This mib is not supported for VX instance of Virtualization."
    ::= { virtualServerCfg 10 }

slbCurCfgContRuleEntry OBJECT-TYPE
    SYNTAX  SlbCurCfgContRuleEntry
    MAX-ACCESS  not-accessible
    STATUS  current
    DESCRIPTION
        "A row in the Content Based Services Rules table."
    INDEX  { slbCurCfgContVirtServIndex, slbCurCfgContVirtServiceIndex,
             slbCurCfgContRuleIndex } 
    ::= { slbCurCfgContRuleTable 1 }

SlbCurCfgContRuleEntry ::= SEQUENCE {
    slbCurCfgContVirtServIndex       Integer32,
    slbCurCfgContVirtServiceIndex  Integer32,
    slbCurCfgContRuleIndex   Integer32,
    slbCurCfgContRuleName     DisplayString,
    slbCurCfgContRuleContClass  DisplayString, 
    slbCurCfgContRuleAction    INTEGER,
    slbCurCfgContRuleRealGrpNum       INTEGER,
    slbCurCfgContRuleGotoRuleNum      INTEGER,
    slbCurCfgContRuleRedirection  DisplayString,
    slbCurCfgContRuleState   INTEGER
    }

slbCurCfgContVirtServIndex OBJECT-TYPE
    SYNTAX  Integer32
    MAX-ACCESS  read-only
    STATUS  current
    DESCRIPTION
        "The number of the virtual server." 
    ::= { slbCurCfgContRuleEntry  1 }

slbCurCfgContVirtServiceIndex OBJECT-TYPE 
    SYNTAX  Integer32 
    MAX-ACCESS  read-only 
    STATUS  current 
    DESCRIPTION 
        "The service index. This has no external meaning" 
    ::= { slbCurCfgContRuleEntry  2 }

slbCurCfgContRuleIndex OBJECT-TYPE
    SYNTAX  Integer32
    MAX-ACCESS  read-only
    STATUS  current
    DESCRIPTION
        "The content based service rule index."
    ::= { slbCurCfgContRuleEntry  3 }

slbCurCfgContRuleName OBJECT-TYPE 
    SYNTAX  DisplayString (SIZE(0..32))
    MAX-ACCESS  read-only
    STATUS  current 
    DESCRIPTION 
        "The Content Rule Name."  
    ::= { slbCurCfgContRuleEntry  4 }

slbCurCfgContRuleContClass OBJECT-TYPE 
    SYNTAX  DisplayString (SIZE(0..32))
    MAX-ACCESS  read-only
    STATUS  current 
    DESCRIPTION 
        "The Content Class for the rule."  
    ::= { slbCurCfgContRuleEntry  5 }

slbCurCfgContRuleAction OBJECT-TYPE 
    SYNTAX  INTEGER {
    group(1),
    appredir(2),
    discard(3),
    goto(4),
    unsupported(2147483647)
    }
    MAX-ACCESS  read-only
    STATUS  current 
    DESCRIPTION 
        "Action type of the rule."  
    ::= { slbCurCfgContRuleEntry  6 }

slbCurCfgContRuleRealGrpNum OBJECT-TYPE 
    SYNTAX  INTEGER (1..1024)
    MAX-ACCESS  read-only
    STATUS  current 
    DESCRIPTION 
        "The group number of real server."
    ::= { slbCurCfgContRuleEntry 7 }

slbCurCfgContRuleGotoRuleNum OBJECT-TYPE
    SYNTAX  INTEGER (1..12800)
    MAX-ACCESS  read-only
    STATUS  current
    DESCRIPTION
        "The group number of real server."
    ::= { slbCurCfgContRuleEntry 8 } 

slbCurCfgContRuleRedirection OBJECT-TYPE 
    SYNTAX  DisplayString (SIZE(0..255))
    MAX-ACCESS  read-only
    STATUS  current 
    DESCRIPTION 
        "Application redirection for the rule."  
    ::= { slbCurCfgContRuleEntry  9 }

slbCurCfgContRuleState OBJECT-TYPE   
    SYNTAX INTEGER {
        enabled(1),
    disabled(2),
        unsupported(2147483647)
    }
    MAX-ACCESS  read-only   
    STATUS  current   
    DESCRIPTION 
        "Enable or disable Content Based Services Rule ."
    ::= { slbCurCfgContRuleEntry 10 }

slbNewCfgContRuleTable OBJECT-TYPE
    SYNTAX  SEQUENCE OF SlbNewCfgContRuleEntry
    MAX-ACCESS  not-accessible
    STATUS  current
    DESCRIPTION
        "The table of Content based Services Rules.
         Note:This mib is not supported for VX instance of Virtualization."
    ::= { virtualServerCfg 11 }

slbNewCfgContRuleEntry OBJECT-TYPE
    SYNTAX  SlbNewCfgContRuleEntry
    MAX-ACCESS  not-accessible
    STATUS  current
    DESCRIPTION
        "A row in the Content Based Services Rules table."
    INDEX  { slbNewCfgContVirtServIndex, slbNewCfgContVirtServiceIndex,
             slbNewCfgContRuleIndex } 
    ::= { slbNewCfgContRuleTable 1 }

SlbNewCfgContRuleEntry ::= SEQUENCE {
    slbNewCfgContVirtServIndex       Integer32,
    slbNewCfgContVirtServiceIndex  Integer32,
    slbNewCfgContRuleIndex         Integer32,
    slbNewCfgContRuleName     DisplayString,
    slbNewCfgContRuleContClass  DisplayString, 
    slbNewCfgContRuleAction    INTEGER,
    slbNewCfgContRuleRealGrpNum       INTEGER,
    slbNewCfgContRuleGotoRuleNum INTEGER,
    slbNewCfgContRuleRedirection  DisplayString,
    slbNewCfgContRuleCopy   INTEGER,
    slbNewCfgContRuleState   INTEGER,
    slbNewCfgContRuleDelete   INTEGER   
    }

slbNewCfgContVirtServIndex OBJECT-TYPE
    SYNTAX  Integer32
    MAX-ACCESS  read-only
    STATUS  current
    DESCRIPTION
        "The number of the virtual server." 
    ::= { slbNewCfgContRuleEntry  1 }

slbNewCfgContVirtServiceIndex OBJECT-TYPE 
    SYNTAX  Integer32 
    MAX-ACCESS  read-only 
    STATUS  current 
    DESCRIPTION 
        "The service index. This has no external meaning" 
    ::= { slbNewCfgContRuleEntry  2 }

slbNewCfgContRuleIndex OBJECT-TYPE
    SYNTAX  Integer32
    MAX-ACCESS  read-only
    STATUS  current
    DESCRIPTION
        "The content based service index."
    ::= { slbNewCfgContRuleEntry  3 }

slbNewCfgContRuleName OBJECT-TYPE 
    SYNTAX  DisplayString (SIZE(0..32))
    MAX-ACCESS  read-create
    STATUS  current 
    DESCRIPTION 
        "The Content Rule Name."  
    ::= { slbNewCfgContRuleEntry  4 }

slbNewCfgContRuleContClass OBJECT-TYPE 
    SYNTAX  DisplayString (SIZE(0..32))
    MAX-ACCESS  read-create
    STATUS  current 
    DESCRIPTION 
        "The Content Class for the rule."  
    ::= { slbNewCfgContRuleEntry  5 }

slbNewCfgContRuleAction OBJECT-TYPE 
    SYNTAX  INTEGER {
    group(1),
    appredir(2),
              discard(3),
              goto(4),
     unsupported(2147483647)
    }
    MAX-ACCESS  read-create
    STATUS  current 
    DESCRIPTION 
        "Action type of the rule."  
    ::= { slbNewCfgContRuleEntry  6 }

slbNewCfgContRuleRealGrpNum OBJECT-TYPE 
    SYNTAX  INTEGER (1..1024)
    MAX-ACCESS  read-create
    STATUS  current 
    DESCRIPTION 
        "The group number of real server."
    ::= { slbNewCfgContRuleEntry 7 }

slbNewCfgContRuleGotoRuleNum OBJECT-TYPE
    SYNTAX  INTEGER (1..12800)
    MAX-ACCESS  read-create
    STATUS  current
    DESCRIPTION
        "The group number of real server."
    ::= { slbNewCfgContRuleEntry 8 }


slbNewCfgContRuleRedirection OBJECT-TYPE 
    SYNTAX  DisplayString (SIZE(0..255))
    MAX-ACCESS  read-create
    STATUS  current 
    DESCRIPTION 
        "Application redirection for the rule."  
    ::= { slbNewCfgContRuleEntry  9 }

slbNewCfgContRuleCopy OBJECT-TYPE 
    SYNTAX  INTEGER (1..12800)
    MAX-ACCESS  read-create
    STATUS  current 
    DESCRIPTION 
        "The Number to which current rule is to be copied."
    ::= { slbNewCfgContRuleEntry 10 }


slbNewCfgContRuleState OBJECT-TYPE   
    SYNTAX  INTEGER {
        enabled(1),
        disabled(2),
        unsupported(2147483647)
    }
    MAX-ACCESS  read-create   
    STATUS  current   
    DESCRIPTION 
        "Enable or disable Content Based Services Rule ."
    ::= { slbNewCfgContRuleEntry 11 }


slbNewCfgContRuleDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgContRuleEntry 12 }


--AppShapes for virtual service

slbCurCfgSerAppShapeTable OBJECT-TYPE
    SYNTAX  SEQUENCE OF SlbCurCfgSerAppShapeEntry
    MAX-ACCESS  not-accessible
    STATUS  current
    DESCRIPTION
        "The table of App Rules added to virtual services.
         Note:This mib is not supported for VX instance of Virtualization."
    ::= { virtualServerCfg 20 }

slbCurCfgSerAppShapeEntry OBJECT-TYPE
    SYNTAX  SlbCurCfgSerAppShapeEntry
    MAX-ACCESS  not-accessible
    STATUS  current
    DESCRIPTION
        "A row in the  AppShape Based Services Rules table."
    INDEX  { slbCurCfgSerAppShapeVirtServIndex, slbCurCfgSerAppShapeVirtServiceIndex,
             slbCurCfgSerAppShapePriority }
    ::= { slbCurCfgSerAppShapeTable 1 }

SlbCurCfgSerAppShapeEntry ::= SEQUENCE {
    slbCurCfgSerAppShapeVirtServIndex     Integer32,
    slbCurCfgSerAppShapeVirtServiceIndex  Integer32,
    slbCurCfgSerAppShapePriority          Integer32,
    slbCurCfgSerAppShapeIndex             DisplayString
    }
slbCurCfgSerAppShapeVirtServIndex OBJECT-TYPE
    SYNTAX  Integer32
    MAX-ACCESS  read-only
    STATUS  current
    DESCRIPTION
        "The number of the virtual server."
    ::= { slbCurCfgSerAppShapeEntry  1 }

slbCurCfgSerAppShapeVirtServiceIndex OBJECT-TYPE
    SYNTAX  Integer32
    MAX-ACCESS  read-only
    STATUS  current
    DESCRIPTION
        "The service index. This has no external meaning"
    ::= { slbCurCfgSerAppShapeEntry  2 }

slbCurCfgSerAppShapePriority OBJECT-TYPE
    SYNTAX  Integer32
    MAX-ACCESS  read-only
    STATUS  current
    DESCRIPTION
        "The number of the virtual server."
    ::= { slbCurCfgSerAppShapeEntry  3 }

slbCurCfgSerAppShapeIndex OBJECT-TYPE
    SYNTAX  DisplayString (SIZE(0..128))
    MAX-ACCESS  read-only
    STATUS  current
    DESCRIPTION
        "The AppShape ID added to the virtual service"
    ::= { slbCurCfgSerAppShapeEntry  4 }

slbNewCfgSerAppShapeTable OBJECT-TYPE
    SYNTAX  SEQUENCE OF SlbNewCfgSerAppShapeEntry
    MAX-ACCESS  not-accessible
    STATUS  current
    DESCRIPTION
        "The table of Content based Services Rules.
         Note:This mib is not supported for VX instance of Virtualization."
    ::= { virtualServerCfg 21 }

slbNewCfgSerAppShapeEntry OBJECT-TYPE
    SYNTAX  SlbNewCfgSerAppShapeEntry
    MAX-ACCESS  not-accessible
    STATUS  current
    DESCRIPTION
        "A row in the Content Based Services Rules table."
    INDEX  { slbNewCfgSerAppShapeVirtServIndex, slbNewCfgSerAppShapeVirtServiceIndex,
             slbNewCfgSerAppShapePriority }
    ::= { slbNewCfgSerAppShapeTable 1 }
SlbNewCfgSerAppShapeEntry ::= SEQUENCE {
    slbNewCfgSerAppShapeVirtServIndex     Integer32,
    slbNewCfgSerAppShapeVirtServiceIndex  Integer32,
    slbNewCfgSerAppShapePriority          Integer32,
    slbNewCfgSerAppShapeIndex             DisplayString,
    slbNewCfgSerAppShapeDelete            INTEGER
    }
slbNewCfgSerAppShapeVirtServIndex OBJECT-TYPE
    SYNTAX  Integer32
    MAX-ACCESS  read-only
    STATUS  current
    DESCRIPTION
        "The number of the virtual server."
    ::= { slbNewCfgSerAppShapeEntry  1 }

slbNewCfgSerAppShapeVirtServiceIndex OBJECT-TYPE
    SYNTAX  Integer32
    MAX-ACCESS  read-only
    STATUS  current
    DESCRIPTION
        "The service index. This has no external meaning"
    ::= { slbNewCfgSerAppShapeEntry  2 }

slbNewCfgSerAppShapePriority OBJECT-TYPE
    SYNTAX  Integer32
    MAX-ACCESS  read-create
    STATUS  current
    DESCRIPTION
        "The number of the virtual server."
    ::= { slbNewCfgSerAppShapeEntry  3 }

slbNewCfgSerAppShapeIndex OBJECT-TYPE
    SYNTAX  DisplayString (SIZE(0..128))
    MAX-ACCESS  read-create
    STATUS  current
    DESCRIPTION
        "The AppShape ID added to the virtual service"
    ::= { slbNewCfgSerAppShapeEntry  4 }

slbNewCfgSerAppShapeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgSerAppShapeEntry 5 }

-- Sunil Start
-- Enhance Virtual server configuration starts
-- Server load balancing - Enhance Virtual Server Table
slbCurCfgEnhVirtServerTable OBJECT-TYPE
    SYNTAX  SEQUENCE OF SlbCurCfgEnhVirtualServerEntry
    MAX-ACCESS  not-accessible
    STATUS  current
    DESCRIPTION
        "The table of virtual Servers.
         Note:This mib is not supported for VX instance of Virtualization."
    ::= { virtualServerCfg 22 }

slbCurCfgEnhVirtualServerEntry OBJECT-TYPE
    SYNTAX  SlbCurCfgEnhVirtualServerEntry
    MAX-ACCESS  not-accessible
    STATUS  current
    DESCRIPTION
        "A row in the virtual server table."
    INDEX   { slbCurCfgEnhVirtServerIndex }
    ::= { slbCurCfgEnhVirtServerTable 1 }

SlbCurCfgEnhVirtualServerEntry ::= SEQUENCE {
    slbCurCfgEnhVirtServerIndex            DisplayString,
    slbCurCfgEnhVirtServerIpAddress        IpAddress,
    slbCurCfgEnhVirtServerLayer3Only       INTEGER,
    slbCurCfgEnhVirtServerState            INTEGER,
    slbCurCfgEnhVirtServerDname            DisplayString,
    slbCurCfgEnhVirtServerBwmContract      Integer32,
    slbCurCfgEnhVirtServerWeight           INTEGER,
    slbCurCfgEnhVirtServerAvail            INTEGER,
    slbCurCfgEnhVirtServerRule             OCTET STRING,
    slbCurCfgEnhVirtServerIpVer            INTEGER,
    slbCurCfgEnhVirtServerIpv6Addr         DisplayString,
    slbCurCfgEnhVirtServerVname            DisplayString,
    slbCurCfgEnhVirtServerCReset           INTEGER,
    slbCurCfgEnhVirtServerSrcNetwork       DisplayString,
    slbCurCfgEnhVirtServerNat              IpAddress,
    slbCurCfgEnhVirtServerNat6             DisplayString,
    slbCurCfgEnhVirtServerIsDnsSecVip      INTEGER,
    slbCurCfgEnhVirtServerAvailPersist     INTEGER,
    slbCurCfgEnhVirtServerWanlink          DisplayString,
    slbCurCfgEnhVirtServerRtSrcMac	   INTEGER,
    slbCurCfgEnhVirtServerCreationType	   INTEGER,
    slbCurCfgEnhVirtServerDnsDirect        Counter32,
    slbCurCfgEnhVirtServerThresholdExceeded    Counter32
    }

slbCurCfgEnhVirtServerIndex OBJECT-TYPE
    SYNTAX  DisplayString (SIZE(1..255))
    MAX-ACCESS  read-only
    STATUS  current
    DESCRIPTION
        "Virtual Server Number in Alphanumeric"
    ::= { slbCurCfgEnhVirtualServerEntry 1 }

slbCurCfgEnhVirtServerIpAddress OBJECT-TYPE
    SYNTAX  IpAddress
    MAX-ACCESS  read-only
    STATUS  current
    DESCRIPTION
        "IP address of the virtual server."
    ::= { slbCurCfgEnhVirtualServerEntry 2 }

slbCurCfgEnhVirtServerLayer3Only OBJECT-TYPE
    SYNTAX  INTEGER {
        layer3Only(1),
        disabled(2),
        unsupported(2147483647)
        }
    MAX-ACCESS  read-only
    STATUS  current
    DESCRIPTION
        "Enable or disable layer3 only balancing."
    ::= { slbCurCfgEnhVirtualServerEntry 3 }

slbCurCfgEnhVirtServerState OBJECT-TYPE
    SYNTAX  INTEGER {
        enabled(2),
        disabled(3),
        unsupported(2147483647)
        }
    MAX-ACCESS  read-only
    STATUS  current
    DESCRIPTION
        "Enable or disable the virtual server."
    ::= { slbCurCfgEnhVirtualServerEntry 4 }

slbCurCfgEnhVirtServerDname OBJECT-TYPE
    SYNTAX  DisplayString (SIZE(0..64))
    MAX-ACCESS  read-only
    STATUS  current
    DESCRIPTION
        "The domain name of the virtual server."
    ::= { slbCurCfgEnhVirtualServerEntry 5 }

slbCurCfgEnhVirtServerBwmContract OBJECT-TYPE
    SYNTAX  Integer32
    MAX-ACCESS  read-only
    STATUS  current
    DESCRIPTION
        "The default BW contract of virtual server."
    ::= { slbCurCfgEnhVirtualServerEntry 6 }

slbCurCfgEnhVirtServerWeight OBJECT-TYPE
    SYNTAX  INTEGER (1..48)
    MAX-ACCESS  read-only
    STATUS  current
    DESCRIPTION
        "The virtual server Global SLB weight."
    ::= { slbCurCfgEnhVirtualServerEntry 7 }

slbCurCfgEnhVirtServerAvail OBJECT-TYPE
    SYNTAX  INTEGER (1..48)
    MAX-ACCESS  read-only
    STATUS  current
    DESCRIPTION
        "The virtual server Global SLB availability."
    ::= { slbCurCfgEnhVirtualServerEntry 8 }

slbCurCfgEnhVirtServerRule OBJECT-TYPE
    SYNTAX OCTET STRING
    MAX-ACCESS read-only
    STATUS current
    DESCRIPTION
        "The Global SLB rules for the domain.
         The rules are presented in bitmap format.
          in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbCurCfgEnhVirtualServerEntry 9 }

slbCurCfgEnhVirtServerVname OBJECT-TYPE
    SYNTAX  DisplayString (SIZE(0..128))
    MAX-ACCESS  read-only
    STATUS  current
    DESCRIPTION
        "The name of the virtual server."
    ::= { slbCurCfgEnhVirtualServerEntry 10 }


slbCurCfgEnhVirtServerIpVer OBJECT-TYPE
    SYNTAX  INTEGER{
        ipv4(1),
        ipv6(2),
        unsupported(2147483647)
        }
    MAX-ACCESS  read-only
    STATUS  current
    DESCRIPTION
        "The type of IP address."
    ::= { slbCurCfgEnhVirtualServerEntry 11 }

slbCurCfgEnhVirtServerIpv6Addr OBJECT-TYPE
    SYNTAX   DisplayString (SIZE(0..40))
    MAX-ACCESS  read-only
    STATUS  current
    DESCRIPTION
        "The IPv6 address of the virtual server. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbCurCfgEnhVirtualServerEntry 12 }


slbCurCfgEnhVirtServerCReset OBJECT-TYPE
    SYNTAX  INTEGER{
        enabled(1),
        disabled(2),
        unsupported(2147483647)
        }
    MAX-ACCESS  read-only
    STATUS  current
    DESCRIPTION
        "Enable/disable client connection reset for invalid VPORT."
    ::= { slbCurCfgEnhVirtualServerEntry 13 }

slbCurCfgEnhVirtServerSrcNetwork OBJECT-TYPE
    SYNTAX  DisplayString  (SIZE(0..32))
    MAX-ACCESS  read-only
    STATUS  current
    DESCRIPTION
        "Source Network Classifier of the virtual server."
    ::= { slbCurCfgEnhVirtualServerEntry 14 }

slbCurCfgEnhVirtServerNat OBJECT-TYPE
    SYNTAX  IpAddress
    MAX-ACCESS  read-only
    STATUS  current
    DESCRIPTION
        "IP address of the NAT."
    ::= { slbCurCfgEnhVirtualServerEntry 15 }

slbCurCfgEnhVirtServerNat6 OBJECT-TYPE
    SYNTAX   DisplayString (SIZE(0..40))
    MAX-ACCESS  read-only
    STATUS  current
    DESCRIPTION
        "The IPv6 address of the NAT. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbCurCfgEnhVirtualServerEntry 16 }

slbCurCfgEnhVirtServerIsDnsSecVip OBJECT-TYPE
    SYNTAX  INTEGER {
        no(0),
        yes(1),
        unsupported(2147483647)
    }
    MAX-ACCESS  read-only
    STATUS  current
    DESCRIPTION
        "It returns Yes(1) if virtual server is a DNS Responder VIP, else returns no(0).
         This mib is added for Vision purpose."
    ::= { slbCurCfgEnhVirtualServerEntry 17 }

slbCurCfgEnhVirtServerAvailPersist OBJECT-TYPE
    SYNTAX  INTEGER {
        enabled(1),
        disabled(2),
        unsupported(2147483647)
        }
    MAX-ACCESS  read-only
    STATUS  current
    DESCRIPTION
        "Enable/disable GSLB availability persistence."
    ::= { slbCurCfgEnhVirtualServerEntry 18 }

slbCurCfgEnhVirtServerWanlink OBJECT-TYPE
    SYNTAX  DisplayString (SIZE(0..255))
    MAX-ACCESS  read-only
    STATUS  current
    DESCRIPTION
        "Associate a real wanlink server to virtual server."
    ::= { slbCurCfgEnhVirtualServerEntry 19 }

slbCurCfgEnhVirtServerRtSrcMac OBJECT-TYPE
    SYNTAX  INTEGER {
        enabled(1),
        disabled(2),
        unsupported(2147483647)
    }
    MAX-ACCESS  read-only
    STATUS  current
    DESCRIPTION
        "Enable/disable return to source mac address"
    ::= { slbCurCfgEnhVirtualServerEntry 24 }

slbCurCfgEnhVirtServerCreationType OBJECT-TYPE
    SYNTAX INTEGER {
        general(0),
        wizard(1),
        unsupported(2147483647)
        }
    MAX-ACCESS read-only
    STATUS current
    DESCRIPTION
        "Virtual Server Creation Type"
    ::= { slbCurCfgEnhVirtualServerEntry 25 }

slbCurCfgEnhVirtServerDnsDirect OBJECT-TYPE
    SYNTAX Counter32
    MAX-ACCESS read-only
    STATUS current
    DESCRIPTION
        "The total number of DNS directs sent to the virtual server or remote real server."
    ::= { slbCurCfgEnhVirtualServerEntry 26 }

slbCurCfgEnhVirtServerThresholdExceeded OBJECT-TYPE
    SYNTAX Counter32
    MAX-ACCESS read-only
    STATUS current
    DESCRIPTION
        "The total number of hits exceeded threshold for virtual server or remote real server."
    ::= { slbCurCfgEnhVirtualServerEntry 27 }

slbNewCfgEnhVirtServerTable OBJECT-TYPE
    SYNTAX  SEQUENCE OF SlbNewCfgEnhVirtualServerEntry
    MAX-ACCESS  not-accessible
    STATUS  current
    DESCRIPTION
        "The table of virtual Servers.
         Note:This mib is not supported for VX instance of Virtualization."
    ::= { virtualServerCfg 23 }

slbNewCfgEnhVirtualServerEntry OBJECT-TYPE
    SYNTAX  SlbNewCfgEnhVirtualServerEntry
    MAX-ACCESS  not-accessible
    STATUS  current
    DESCRIPTION
        "A row in the virtual server table."
    INDEX   { slbNewCfgEnhVirtServerIndex }
    ::= { slbNewCfgEnhVirtServerTable 1 }

SlbNewCfgEnhVirtualServerEntry ::= SEQUENCE {
    slbNewCfgEnhVirtServerIndex            DisplayString,
    slbNewCfgEnhVirtServerIpAddress        IpAddress,
    slbNewCfgEnhVirtServerLayer3Only       INTEGER,
    slbNewCfgEnhVirtServerState            INTEGER,
    slbNewCfgEnhVirtServerDname            DisplayString,
    slbNewCfgEnhVirtServerBwmContract      Integer32,
    slbNewCfgEnhVirtServerDelete           INTEGER,
    slbNewCfgEnhVirtServerWeight           INTEGER,
    slbNewCfgEnhVirtServerAvail            INTEGER,
    slbNewCfgEnhVirtServerRule             OCTET STRING,
    slbNewCfgEnhVirtServerAddRule          Integer32,
    slbNewCfgEnhVirtServerRemoveRule       Integer32,
    slbNewCfgEnhVirtServerIpVer            INTEGER,
    slbNewCfgEnhVirtServerIpv6Addr         DisplayString,
    slbNewCfgEnhVirtServerVname            DisplayString,
    slbNewCfgEnhVirtServerFreeServiceIdx   INTEGER,
    slbNewCfgEnhVirtServerCReset           INTEGER,
    slbNewCfgEnhVirtServerSrcNetwork       DisplayString,
    slbNewCfgEnhVirtServerNat              IpAddress,
    slbNewCfgEnhVirtServerNat6             DisplayString,
    slbNewCfgEnhVirtServerIsDnsSecVip      INTEGER,
    slbNewCfgEnhVirtServerAvailPersist     INTEGER,
    slbNewCfgEnhVirtServerWanlink          DisplayString,
    slbNewCfgEnhVirtServerRtSrcMac	   INTEGER,
    slbNewCfgEnhVirtServerCreationType     INTEGER	
    }

slbNewCfgEnhVirtServerIndex OBJECT-TYPE
    SYNTAX  DisplayString (SIZE(1..255))
    MAX-ACCESS  read-only
    STATUS  current
    DESCRIPTION
        "The Virtual Server Number"
    ::= { slbNewCfgEnhVirtualServerEntry 1 }

slbNewCfgEnhVirtServerIpAddress OBJECT-TYPE
    SYNTAX  IpAddress
    MAX-ACCESS  read-create
    STATUS  current
    DESCRIPTION
        "IP address of the virtual server."
    ::= { slbNewCfgEnhVirtualServerEntry 2 }

slbNewCfgEnhVirtServerLayer3Only OBJECT-TYPE
    SYNTAX  INTEGER {
        layer3Only(1),
        disabled(2),
        unsupported(2147483647)
        }
    MAX-ACCESS  read-create
    STATUS  current
    DESCRIPTION
        "Enable or disable layer3 only balancing."
    ::= { slbNewCfgEnhVirtualServerEntry 3 }

slbNewCfgEnhVirtServerState OBJECT-TYPE
    SYNTAX  INTEGER {
        enabled(2),
        disabled(3),
        unsupported(2147483647)
        }
    MAX-ACCESS  read-create
    STATUS  current
    DESCRIPTION
        "Enable or disable the virtual server."
    ::= { slbNewCfgEnhVirtualServerEntry 4 }

slbNewCfgEnhVirtServerDname OBJECT-TYPE
    SYNTAX  DisplayString (SIZE(0..64))
    MAX-ACCESS  read-create
    STATUS  current
    DESCRIPTION
        "The domain name of the virtual server."
    ::= { slbNewCfgEnhVirtualServerEntry 6 }

slbNewCfgEnhVirtServerBwmContract OBJECT-TYPE
    SYNTAX  Integer32
    MAX-ACCESS  read-create
    STATUS  current
    DESCRIPTION
        "The default BW contract number of the virtual server."
    ::= { slbNewCfgEnhVirtualServerEntry 7 }

slbNewCfgEnhVirtServerDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgEnhVirtualServerEntry 8 }

slbNewCfgEnhVirtServerWeight OBJECT-TYPE
    SYNTAX  INTEGER (1..48)
    MAX-ACCESS  read-create
    STATUS  current
    DESCRIPTION
        "The virtual server Global SLB weight."
    ::= { slbNewCfgEnhVirtualServerEntry 9 }

slbNewCfgEnhVirtServerAvail OBJECT-TYPE
    SYNTAX  INTEGER (1..48)
    MAX-ACCESS  read-create
    STATUS  current
    DESCRIPTION
        "The virtual server Global SLB availability."
    ::= { slbNewCfgEnhVirtualServerEntry 10 }

slbNewCfgEnhVirtServerRule OBJECT-TYPE
    SYNTAX OCTET STRING
    MAX-ACCESS read-only
    STATUS current
    DESCRIPTION
        "The Global SLB rules for the domain.
         The rules are presented in bitmap format.

           in receiving order:

             OCTET 1  OCTET 2  .....
             xxxxxxxx xxxxxxxx .....
             |     || |_ server 9
             |     ||
             |     ||___ server 8
             |     |____ server 7
             |       .    .   .
             |__________ server 1

       where x : 1 - The represented rule belongs to the domain
                   0 - The represented rule does not belong to the domain"
    ::= { slbNewCfgEnhVirtualServerEntry 11 }

slbNewCfgEnhVirtServerAddRule OBJECT-TYPE
    SYNTAX  Integer32
    MAX-ACCESS  read-create
    STATUS  current
    DESCRIPTION
        "The rule to be added to the domain. When read, 0 is returned."
    ::= { slbNewCfgEnhVirtualServerEntry 12 }

slbNewCfgEnhVirtServerRemoveRule OBJECT-TYPE
    SYNTAX  Integer32
    MAX-ACCESS  read-create
    STATUS  current
    DESCRIPTION
        "The rule to be removed from the domain. When read, 0 is returned."
    ::= { slbNewCfgEnhVirtualServerEntry 13 }

slbNewCfgEnhVirtServerVname OBJECT-TYPE
    SYNTAX  DisplayString (SIZE(0..128))
    MAX-ACCESS  read-create
    STATUS  current
    DESCRIPTION
        "The name of the virtual server."
    ::= { slbNewCfgEnhVirtualServerEntry 14 }


slbNewCfgEnhVirtServerIpVer OBJECT-TYPE
    SYNTAX  INTEGER{
        ipv4(1),
        ipv6(2),
        unsupported(2147483647)
        }
    MAX-ACCESS read-create
    STATUS  current
    DESCRIPTION
        "The type of IP address."
    ::= { slbNewCfgEnhVirtualServerEntry 15 }

slbNewCfgEnhVirtServerIpv6Addr OBJECT-TYPE
    SYNTAX  DisplayString  (SIZE(0..40))
    MAX-ACCESS read-create
    STATUS  current
    DESCRIPTION
        "The IPv6 address of the virtual server. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbNewCfgEnhVirtualServerEntry 16 }


slbNewCfgEnhVirtServerFreeServiceIdx OBJECT-TYPE
    SYNTAX  INTEGER(0..8)
    MAX-ACCESS  read-only
    STATUS  current
    DESCRIPTION
        "The first free service index number of the virtual server.
         Value 0 will be returned when all 8 virtual services are
         configured for a virtual server."
    ::= { slbNewCfgEnhVirtualServerEntry 17 }

slbNewCfgEnhVirtServerCReset OBJECT-TYPE
    SYNTAX  INTEGER{
        enabled(1),
        disabled(2),
        unsupported(2147483647)
        }
    MAX-ACCESS  read-create
    STATUS  current
    DESCRIPTION
        "Enable/disable client connection reset for invalid VPORT."
    ::= { slbNewCfgEnhVirtualServerEntry 18 }

slbNewCfgEnhVirtServerSrcNetwork OBJECT-TYPE
    SYNTAX  DisplayString  (SIZE(0..32))
    MAX-ACCESS  read-create
    STATUS  current
    DESCRIPTION
        "Source Network Classifier of the virtual server."
    ::= { slbNewCfgEnhVirtualServerEntry 19 }

slbNewCfgEnhVirtServerNat OBJECT-TYPE
    SYNTAX  IpAddress
    MAX-ACCESS  read-write
    STATUS  current
    DESCRIPTION
        "IP address of the NAT."
    ::= { slbNewCfgEnhVirtualServerEntry 20 }

slbNewCfgEnhVirtServerNat6 OBJECT-TYPE
    SYNTAX   DisplayString (SIZE(0..40))
    MAX-ACCESS  read-write
    STATUS  current
    DESCRIPTION
        "The IPv6 address of the NAT. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { slbNewCfgEnhVirtualServerEntry 21 }

slbNewCfgEnhVirtServerIsDnsSecVip OBJECT-TYPE
    SYNTAX  INTEGER {
        no(0),
        yes(1),
        unsupported(2147483647)
    }
    MAX-ACCESS  read-only
    STATUS  current
    DESCRIPTION
        "This mib returns Yes(1) if virtual server is a DNS Responder VIP, else returns no(0)"
    ::= { slbNewCfgEnhVirtualServerEntry 22 }

slbNewCfgEnhVirtServerAvailPersist OBJECT-TYPE
    SYNTAX  INTEGER {
        enabled(1),
        disabled(2),
        unsupported(2147483647)
        }
    MAX-ACCESS  read-create
    STATUS  current
    DESCRIPTION
        "Enable/disable GSLB availability persistence."
    ::= { slbNewCfgEnhVirtualServerEntry 23 }

slbNewCfgEnhVirtServerWanlink OBJECT-TYPE
    SYNTAX  DisplayString (SIZE(0..255))
    MAX-ACCESS  read-create
    STATUS  current
    DESCRIPTION
        "Associate a real wanlink server to virtual server."
    ::= { slbNewCfgEnhVirtualServerEntry 24 }

slbNewCfgEnhVirtServerRtSrcMac OBJECT-TYPE
    SYNTAX  INTEGER {
        enabled(1),
        disabled(2),
        unsupported(2147483647)
    }
    MAX-ACCESS  read-write
    STATUS  current
    DESCRIPTION
        "Enable/disable return to source mac address"
    ::= { slbNewCfgEnhVirtualServerEntry 25 }

slbNewCfgEnhVirtServerCreationType OBJECT-TYPE
    SYNTAX INTEGER {
        general(0),
        wizard(1),
        unsupported(2147483647)
        }
    MAX-ACCESS read-write
    STATUS current
    DESCRIPTION
        "Virtual Server Creation Type"
    ::= { slbNewCfgEnhVirtualServerEntry 26 }

-- Sunil End

-- SLB total CPS Statistics For All virts

slbStatCPSAll OBJECT IDENTIFIER ::= { layer4Stats 46 }

slbStatCPSSwitch OBJECT-TYPE
    SYNTAX  Counter64
    MAX-ACCESS  read-only
    STATUS  current
    DESCRIPTION
        "Number of Sessions handled by the switch per second.
         Note:This mib is not supported for VX instance of Virtualization."
    ::= {slbStatCPSAll 1 }

slbStatThroughputSwitch OBJECT-TYPE
    SYNTAX DisplayString(SIZE(0..31))
    MAX-ACCESS  read-only
    STATUS  current
    DESCRIPTION
        "Current Throughput Usage per second (Mbps).
         Note:This mib is not supported for VX instance of Virtualization."
    ::= {slbStatCPSAll 2 }

slbStatSSLCPSSwitch OBJECT-TYPE
    SYNTAX DisplayString(SIZE(0..31))
    MAX-ACCESS  read-only
    STATUS  current
    DESCRIPTION
        "Current SSL Capacity per second (CPS) Usage.
         Note:This mib is not supported for VX instance of Virtualization."
    ::= {slbStatCPSAll 3 }

-- CPS Statistics End

slbCurCfgEnhVirtServicesTable OBJECT-TYPE
    SYNTAX  SEQUENCE OF SlbCurCfgEnhVirtServicesEntry
    MAX-ACCESS  not-accessible
    STATUS  current
    DESCRIPTION
        "The table of virtual services.
         Note:This mib is not supported for VX instance of Virtualization."
    ::= { virtualServerCfg 24 }

slbCurCfgEnhVirtServicesEntry OBJECT-TYPE
    SYNTAX  SlbCurCfgEnhVirtServicesEntry
    MAX-ACCESS  not-accessible
    STATUS  current
    DESCRIPTION
        "A row in the virtual services table."
    INDEX   { slbCurCfgEnhVirtServIndex, slbCurCfgEnhVirtServiceIndex }
    ::= { slbCurCfgEnhVirtServicesTable 1 }

SlbCurCfgEnhVirtServicesEntry ::= SEQUENCE {
    slbCurCfgEnhVirtServIndex            DisplayString,
    slbCurCfgEnhVirtServiceIndex         Integer32,
    slbCurCfgEnhVirtServiceVirtPort      INTEGER,
    slbCurCfgEnhVirtServiceRealPort      INTEGER,
    slbCurCfgEnhVirtServiceUDPBalance    INTEGER,
    slbCurCfgEnhVirtServiceBwmContract   Integer32,
    slbCurCfgEnhVirtServiceDirServerRtn  INTEGER,
    slbCurCfgEnhVirtServiceRtspUrlParse  INTEGER,
    slbCurCfgEnhVirtServiceFtpParsing    INTEGER,
    slbCurCfgEnhVirtServiceRemapUDPFrags INTEGER,
    slbCurCfgEnhVirtServiceDnsSlb        INTEGER,
    slbCurCfgEnhVirtServiceResponseCount INTEGER,
    slbCurCfgEnhVirtServicePBind         INTEGER,
    slbCurCfgEnhVirtServiceCoffset       INTEGER,
    slbCurCfgEnhVirtServiceClength       INTEGER,
    slbCurCfgEnhVirtServiceUriCookie     INTEGER,
    slbCurCfgEnhVirtServiceCookieMode    INTEGER,
    slbCurCfgEnhVirtServiceDBind         INTEGER,
    slbCurCfgEnhVirtServiceHttpSlb       INTEGER,
    slbCurCfgEnhVirtServiceHttpSlbOption INTEGER,
    slbCurCfgEnhVirtServiceHttpSlb2      INTEGER,
    slbCurCfgEnhVirtServiceApm           INTEGER,
    slbCurCfgEnhVirtServiceNonHTTP       INTEGER,
    slbCurCfgEnhVirtServiceDname         DisplayString,
    slbCurCfgEnhVirtServiceIpRep         INTEGER,
    slbCurCfgEnhVirtServiceCdnProxy      INTEGER,
    slbCurCfgEnhVirtServiceCurrSessions      Gauge32,
    slbCurCfgEnhVirtServiceTotalSessions     Counter32,
    slbCurCfgEnhVirtServiceHighestSessions   Counter32,
    slbCurCfgEnhVirtServiceHCOctetsLow32     Counter32,
    slbCurCfgEnhVirtServiceHCOctetsHigh32    Counter32,
    slbCurCfgEnhVirtServiceHCOctets          Counter64,
    slbCurCfgEnhVirtServiceSessPerSec        Counter32,
    slbCurCfgEnhVirtServiceOctetsPerSec      DisplayString,
    slbCurCfgEnhVirtServiceClientRtt        DisplayString,
    slbCurCfgEnhVirtServiceServerRtt        DisplayString,
    slbCurCfgEnhVirtServiceAppResponse      DisplayString,
    slbCurCfgEnhVirtServiceRespTransfer     DisplayString,
    slbCurCfgEnhVirtServiceEndToEndTotal    DisplayString,
    slbCurCfgEnhVirtServiceStatus    	 INTEGER,
    slbCurCfgEnhVirtServiceRtSrcTnl      INTEGER
}

slbCurCfgEnhVirtServIndex OBJECT-TYPE
    SYNTAX  DisplayString (SIZE(1..255))
    MAX-ACCESS  read-only
    STATUS  current
    DESCRIPTION
        "The number of the virtual server."
    ::= { slbCurCfgEnhVirtServicesEntry 1 }

slbCurCfgEnhVirtServiceIndex OBJECT-TYPE
    SYNTAX  Integer32
    MAX-ACCESS  read-only
    STATUS  current
    DESCRIPTION
        "The service index. This has no external meaning"
    ::= { slbCurCfgEnhVirtServicesEntry 2 }

slbCurCfgEnhVirtServiceVirtPort OBJECT-TYPE
    SYNTAX  INTEGER (1..65534)
    MAX-ACCESS  read-only
    STATUS  current
    DESCRIPTION
        "The layer4 virtual port number of the service. it can be either 1 for ip or between 9 to 65534, virt port no. 2 to 9 are invalid"
    ::= { slbCurCfgEnhVirtServicesEntry 3 }

slbCurCfgEnhVirtServiceRealPort OBJECT-TYPE
    SYNTAX  INTEGER (0..65534)
    MAX-ACCESS  read-only
    STATUS  current
    DESCRIPTION
        "The layer4 real port number of the service, it can be either 0 for multiple real ports or 1 for ip service or between 5 to 65534. (2 to 5 are invalid)"
    ::= { slbCurCfgEnhVirtServicesEntry 4 }

slbCurCfgEnhVirtServiceUDPBalance OBJECT-TYPE
    SYNTAX  INTEGER    {
        udp(2),
        tcp(3),
        stateless(4),
        tcpAndUdp(5),
        sctp(6),
        unsupported(2147483647)
        }
    MAX-ACCESS  read-only
    STATUS  current
    DESCRIPTION
        "Set protocol for the virtual service to
         UDP or TCP or SCTP or tcpAndUdp or stateless.
         tcpAndUdp is applicable only to ip service."
    ::= { slbCurCfgEnhVirtServicesEntry 5 }

slbCurCfgEnhVirtServiceBwmContract OBJECT-TYPE
    SYNTAX  Integer32
    MAX-ACCESS  read-only
    STATUS  current
    DESCRIPTION
        "The BWM contract number for this service."
    ::= { slbCurCfgEnhVirtServicesEntry 6 }

slbCurCfgEnhVirtServiceDirServerRtn OBJECT-TYPE
    SYNTAX  INTEGER {
        enabled(1),
        disabled(2),
        unsupported(2147483647)
        }
    MAX-ACCESS  read-only
    STATUS  current
    DESCRIPTION
        "Enable or disable direct server return feature. To translate only
         MAC addresses in performing server load balancing when enabled.
         This allow servers to return directly to client since IP addresses
         have not been changed."
    ::= { slbCurCfgEnhVirtServicesEntry 7 }

slbCurCfgEnhVirtServiceRtspUrlParse OBJECT-TYPE
    SYNTAX  INTEGER {
        none(1),
        l4hash(2),
        hash(3),
        patternMatch(4),
        unsupported(2147483647)
        }
    MAX-ACCESS  read-only
    STATUS  current
    DESCRIPTION
        "Select RTSP URL load balancing type."
    ::= { slbCurCfgEnhVirtServicesEntry 8 }

slbCurCfgEnhVirtServiceFtpParsing OBJECT-TYPE
    SYNTAX  INTEGER {
        enabled(1),
        disabled(2),
        unsupported(2147483647)
        }
    MAX-ACCESS  read-only
    STATUS  current
    DESCRIPTION
        "Enable or Disable the ftp parsing for the virtual service."
    ::= { slbCurCfgEnhVirtServicesEntry 9 }

slbCurCfgEnhVirtServiceRemapUDPFrags OBJECT-TYPE
    SYNTAX INTEGER {
        enabled(1),
        disabled(2),
        unsupported(2147483647)
        }
    MAX-ACCESS read-only
    STATUS current
    DESCRIPTION
        "Enable or disable remapping UDP server fragments"
    ::= { slbCurCfgEnhVirtServicesEntry 10 }

slbCurCfgEnhVirtServiceDnsSlb OBJECT-TYPE
    SYNTAX  INTEGER {
        enabled(1),
        disabled(2),
        unsupported(2147483647)
        }
    MAX-ACCESS  read-only
    STATUS  current
    DESCRIPTION
        "Enable or disable DNS query load balancing."
    ::= { slbCurCfgEnhVirtServicesEntry 11 }

slbCurCfgEnhVirtServiceResponseCount OBJECT-TYPE
    SYNTAX  INTEGER (1..16)
    MAX-ACCESS  read-only
    STATUS  current
    DESCRIPTION
        "The number of cookie search response count."
    ::= { slbCurCfgEnhVirtServicesEntry 12 }

slbCurCfgEnhVirtServicePBind OBJECT-TYPE
    SYNTAX  INTEGER {
        clientip(2),
        disabled(3),
        sslid(4),
        cookie(5),
        unsupported(2147483647)
        }
    MAX-ACCESS  read-only
    STATUS  current
    DESCRIPTION
        "Enable or disable persistent bindings for the virtual port."
    ::= { slbCurCfgEnhVirtServicesEntry 13 }

slbCurCfgEnhVirtServiceCoffset OBJECT-TYPE
    SYNTAX  INTEGER (1..64)
    MAX-ACCESS  read-only
    STATUS  current
    DESCRIPTION
        "The starting byte offset of the cookie value."
    ::= { slbCurCfgEnhVirtServicesEntry 14 }

slbCurCfgEnhVirtServiceClength OBJECT-TYPE
    SYNTAX  INTEGER (1..64)
    MAX-ACCESS  read-only
    STATUS  current
    DESCRIPTION
        "The number of bytes to extract from the cookie value."
    ::= { slbCurCfgEnhVirtServicesEntry 15 }

slbCurCfgEnhVirtServiceUriCookie OBJECT-TYPE
    SYNTAX  INTEGER {
        enabled(1),
        disabled(2),
        unsupported(2147483647)
        }
    MAX-ACCESS  read-only
    STATUS  current
    DESCRIPTION
        "Enable or disable cookie search in URI"
    ::= { slbCurCfgEnhVirtServicesEntry 16 }

slbCurCfgEnhVirtServiceCookieMode OBJECT-TYPE
    SYNTAX INTEGER {
        rewrite(1),
        passive(2),
        insert(3),
        disabled(4),
        unsupported(2147483647)
        }
    MAX-ACCESS read-only
    STATUS current
    DESCRIPTION
        "Select cookie persistence mode."
    ::= { slbCurCfgEnhVirtServicesEntry 17 }


slbCurCfgEnhVirtServiceDBind OBJECT-TYPE
    SYNTAX  INTEGER {
        enabled(1),
        disabled(2),
        forceproxy(3),
        unsupported(2147483647)
        }
    MAX-ACCESS  read-only
    STATUS  current
    DESCRIPTION
        "Enable/disable/forceproxy delayed binding."
    ::= { slbCurCfgEnhVirtServicesEntry 18 }


slbCurCfgEnhVirtServiceHttpSlb OBJECT-TYPE
    SYNTAX  INTEGER {
        disabled(1),
        urlslb(2),
        urlhash(3),
        cookie(4),
        host(5),
        browser(6),
        others(7),
        headerhash(8),
        version(9),
        unsupported(2147483647)
        }
    MAX-ACCESS  read-only
    STATUS  current
    DESCRIPTION
        "Select HTTP server loadbalancing for the virtual port."
    ::= { slbCurCfgEnhVirtServicesEntry 19 }
slbCurCfgEnhVirtServiceHttpSlbOption OBJECT-TYPE
    SYNTAX  INTEGER {
        and(1),
        or(2),
        none(3),
        unsupported(2147483647)
        }
    MAX-ACCESS  read-only
    STATUS  current
    DESCRIPTION
        "Select HTTP server loadbalancing for the virtual port."
    ::= { slbCurCfgEnhVirtServicesEntry 20 }

slbCurCfgEnhVirtServiceHttpSlb2 OBJECT-TYPE
    SYNTAX  INTEGER {
        disabled(1),
        urlslb(2),
        urlhash(3),
        cookie(4),
        host(5),
        browser(6),
        others(7),
        headerhash(8),
        version(9),
        unsupported(2147483647)
        }
    MAX-ACCESS  read-only
    STATUS  current
    DESCRIPTION
        "Select HTTP server loadbalancing for the virtual port."
    ::= { slbCurCfgEnhVirtServicesEntry 21 }
slbCurCfgEnhVirtServiceApm OBJECT-TYPE
    SYNTAX  INTEGER {
        enabled(1),
        disabled(2),
        unsupported(2147483647)
        }
    MAX-ACCESS  read-only
    STATUS  obsolete
    DESCRIPTION
        "Enable/disable apm."
    ::= { slbCurCfgEnhVirtServicesEntry 22 }
slbCurCfgEnhVirtServiceNonHTTP OBJECT-TYPE   
    SYNTAX  INTEGER {
	enabled(1),
	disabled(2),
        unsupported(2147483647)
	}
    MAX-ACCESS  read-only
    STATUS  current   
    DESCRIPTION 
        "Enable or disable Send non-HTTP traffic."
    ::= { slbCurCfgEnhVirtServicesEntry 23 }

slbCurCfgEnhVirtServiceDname OBJECT-TYPE
    SYNTAX DisplayString (SIZE(0..64))
    MAX-ACCESS read-only
    STATUS current
    DESCRIPTION
        "The domain name of the virtual server and remote real server."
    ::= { slbCurCfgEnhVirtServicesEntry 24 }

slbCurCfgEnhVirtServiceIpRep OBJECT-TYPE   
    SYNTAX  INTEGER { 
	enabled(1),
    disabled(2),
        unsupported(2147483647)
	}
    MAX-ACCESS  read-only
    STATUS  current   
    DESCRIPTION 
        "Enable or disable IP reputation."
    ::= { slbCurCfgEnhVirtServicesEntry 25 }

slbCurCfgEnhVirtServiceCdnProxy OBJECT-TYPE   
    SYNTAX  INTEGER {
	enabled(1),
    disabled(2),
        unsupported(2147483647)
	}
    MAX-ACCESS  read-only
    STATUS  current   
    DESCRIPTION 
        "Enable or disable CDN proxy."
    ::= { slbCurCfgEnhVirtServicesEntry 26 }

slbCurCfgEnhVirtServiceCurrSessions OBJECT-TYPE
    SYNTAX  Gauge32
    MAX-ACCESS  read-only
    STATUS  current
    DESCRIPTION
        "Total number of sessions that are currently handled by the virtual service."
    ::= { slbCurCfgEnhVirtServicesEntry 27 }

slbCurCfgEnhVirtServiceTotalSessions OBJECT-TYPE
    SYNTAX  Counter32
    MAX-ACCESS  read-only
    STATUS  current
    DESCRIPTION
        "Total number of sessions that are handled by the virtual service."
    ::= { slbCurCfgEnhVirtServicesEntry 28}

slbCurCfgEnhVirtServiceHighestSessions OBJECT-TYPE
    SYNTAX  Counter32
    MAX-ACCESS  read-only
    STATUS  current
    DESCRIPTION
        "Highest number of sessions that have been handled by the virtual service."
    ::= { slbCurCfgEnhVirtServicesEntry 29}

slbCurCfgEnhVirtServiceHCOctetsLow32 OBJECT-TYPE
    SYNTAX  Counter32
    MAX-ACCESS  read-only
    STATUS  current
    DESCRIPTION
        "The lower 32 bit value of total octets received and transmitted out of the virtual service."
    ::= { slbCurCfgEnhVirtServicesEntry 30}

slbCurCfgEnhVirtServiceHCOctetsHigh32 OBJECT-TYPE
    SYNTAX  Counter32
    MAX-ACCESS  read-only
    STATUS  current
    DESCRIPTION
        "The higher 32 bit value of total octets received and transmitted out of the virtual service."
    ::= { slbCurCfgEnhVirtServicesEntry 31}

slbCurCfgEnhVirtServiceHCOctets OBJECT-TYPE
    SYNTAX  Counter64
    MAX-ACCESS  read-only
    STATUS  current
    DESCRIPTION
        "Total octets received and transmitted by the virtual service."
    ::= { slbCurCfgEnhVirtServicesEntry 32}

slbCurCfgEnhVirtServiceSessPerSec OBJECT-TYPE
    SYNTAX  Counter32
    MAX-ACCESS  read-only
    STATUS  current
    DESCRIPTION
        "Number of sessions that are currently handled per second by the virtual service ."
    ::= { slbCurCfgEnhVirtServicesEntry 33}

slbCurCfgEnhVirtServiceOctetsPerSec OBJECT-TYPE
    SYNTAX  DisplayString (SIZE(1..24))
    MAX-ACCESS  read-only
    STATUS  current
    DESCRIPTION
         "Number of octets received and transmitted per second by the virtual service."
    ::= { slbCurCfgEnhVirtServicesEntry 34}

slbCurCfgEnhVirtServiceClientRtt OBJECT-TYPE
    SYNTAX  DisplayString (SIZE(1..255))
    MAX-ACCESS  read-only
    STATUS  current
    DESCRIPTION
    "The average ClientRTT in ms during the past collection interval."
    ::= { slbCurCfgEnhVirtServicesEntry 35 }

slbCurCfgEnhVirtServiceServerRtt OBJECT-TYPE
    SYNTAX  DisplayString (SIZE(1..255))
    MAX-ACCESS  read-only
    STATUS  current
    DESCRIPTION
    "The average ServerRTT in ms during the past collection interval."
    ::= { slbCurCfgEnhVirtServicesEntry 36 }

slbCurCfgEnhVirtServiceAppResponse OBJECT-TYPE
    SYNTAX  DisplayString (SIZE(1..255))
    MAX-ACCESS  read-only
    STATUS  current
    DESCRIPTION
    "The average application response from AX in ms during the past collection interval."
    ::= { slbCurCfgEnhVirtServicesEntry 37 }

slbCurCfgEnhVirtServiceRespTransfer OBJECT-TYPE
    SYNTAX  DisplayString (SIZE(1..255))
    MAX-ACCESS  read-only
    STATUS  current
    DESCRIPTION
    "The average response transfer from AX in ms during the past collection interval."
    ::= { slbCurCfgEnhVirtServicesEntry 38 }

slbCurCfgEnhVirtServiceEndToEndTotal OBJECT-TYPE
    SYNTAX  DisplayString (SIZE(1..255))
    MAX-ACCESS  read-only
    STATUS  current
    DESCRIPTION
    "The sum of clientRtt, serverRtt, application response, response transfer."
    ::= { slbCurCfgEnhVirtServicesEntry 39 }

slbCurCfgEnhVirtServiceStatus    OBJECT-TYPE
    SYNTAX  INTEGER {
        up(1),
        down(2),
        adminDown(3),
        warning(4),
        shutdown(5),
        error(6),
        unsupported(2147483647)
        }
    MAX-ACCESS  read-only
    STATUS  current
    DESCRIPTION
    "The service status: up, down, admin down, warning, shutdown, error."
    ::= { slbCurCfgEnhVirtServicesEntry 40 }

slbCurCfgEnhVirtServiceRtSrcTnl  OBJECT-TYPE
    SYNTAX  INTEGER {
        enabled(1),
        disabled(2),
        unsupported(2147483647)
        }
    MAX-ACCESS  read-only
    STATUS  current
    DESCRIPTION
        "Enable or disable Return to Source Tunnel."
    ::= { slbCurCfgEnhVirtServicesEntry 41 }


slbCurCfgEnhVirtServicesSecondPartTable OBJECT-TYPE
    SYNTAX  SEQUENCE OF SlbCurCfgEnhVirtServicesSecondPartEntry
    MAX-ACCESS  not-accessible
    STATUS  current
    DESCRIPTION
        "The table of virtual Services.
         Note:This mib is not supported for VX instance of Virtualization."
    ::= { virtualServerCfg 25 }

slbCurCfgEnhVirtServicesSecondPartEntry OBJECT-TYPE
    SYNTAX  SlbCurCfgEnhVirtServicesSecondPartEntry
    MAX-ACCESS  not-accessible
    STATUS  current
    DESCRIPTION
        "A row in the virtual services table."
    INDEX   { slbCurCfgEnhVirtServSecondPartIndex, slbCurCfgEnhVirtServiceSecondPartIndex }
    ::= { slbCurCfgEnhVirtServicesSecondPartTable 1 }

SlbCurCfgEnhVirtServicesSecondPartEntry ::= SEQUENCE {
    slbCurCfgEnhVirtServSecondPartIndex            DisplayString,
    slbCurCfgEnhVirtServiceSecondPartIndex         Integer32,

    slbCurCfgEnhVirtServiceConnmgtStatus  INTEGER,
    slbCurCfgEnhVirtServiceConnmgtTimeout INTEGER,
    slbCurCfgEnhVirtServiceCachepol      DisplayString,
    slbCurCfgEnhVirtServiceComppol       DisplayString,
    slbCurCfgEnhVirtServiceSSLpol        DisplayString,
    slbCurCfgEnhVirtServiceServCert      DisplayString,
    slbCurCfgEnhVirtServiceHttpmodList   DisplayString,
    slbCurCfgEnhVirtServiceCloaksrv      INTEGER,

    slbCurCfgEnhVirtServErrcodeStatus    INTEGER,
    slbCurCfgEnhVirtServErrcodeMatch     DisplayString,
    slbCurCfgEnhVirtServErrcodeHttpRedir INTEGER,
    slbCurCfgEnhVirtServErrcodeUrl       DisplayString,
    slbCurCfgEnhVirtServErrcode          DisplayString,
    slbCurCfgEnhVirtServErrcodeNew       DisplayString,
    slbCurCfgEnhVirtServErrcodeReason    DisplayString,
    slbCurCfgEnhVirtServUrlchangStatus     INTEGER,
    slbCurCfgEnhVirtServUrlchangHostType   INTEGER,
    slbCurCfgEnhVirtServiceFeTcpPolId       DisplayString,
    slbCurCfgEnhVirtServiceBeTcpPolId       DisplayString
}

slbCurCfgEnhVirtServSecondPartIndex OBJECT-TYPE
    SYNTAX  DisplayString (SIZE(1..255))
    MAX-ACCESS  read-only
    STATUS  current
    DESCRIPTION
        "The number of the virtual server."
    ::= { slbCurCfgEnhVirtServicesSecondPartEntry 1 }

slbCurCfgEnhVirtServiceSecondPartIndex OBJECT-TYPE
    SYNTAX  Integer32
    MAX-ACCESS  read-only
    STATUS  current
    DESCRIPTION
        "The service index. This has no external meaning"
    ::= { slbCurCfgEnhVirtServicesSecondPartEntry 2 }


slbCurCfgEnhVirtServiceConnmgtStatus OBJECT-TYPE
    SYNTAX  INTEGER {
        disabled(0),
        pooling(1),
        muxenabled(2),
        h2(3),
        unsupported(2147483647)
        }
    MAX-ACCESS  read-only
    STATUS  current
    DESCRIPTION
        "Connection management configuration for HTTP traffic(Enable/disable/pooling) [Default: Disable]."
    ::= { slbCurCfgEnhVirtServicesSecondPartEntry 3 }

slbCurCfgEnhVirtServiceConnmgtTimeout OBJECT-TYPE
    SYNTAX  INTEGER (0..32768)
    MAX-ACCESS  read-only
    STATUS  current
    DESCRIPTION
        "Connection management server side connection idle timeout in minutes [0-32768] [Default: 10]."
    ::= { slbCurCfgEnhVirtServicesSecondPartEntry 4 }

slbCurCfgEnhVirtServiceCachepol OBJECT-TYPE
    SYNTAX  DisplayString  (SIZE(0..32))
    MAX-ACCESS  read-only
    STATUS  current
    DESCRIPTION
        "Cache policy name associated with this virtual service."
    ::= { slbCurCfgEnhVirtServicesSecondPartEntry 5 }

slbCurCfgEnhVirtServiceComppol OBJECT-TYPE
    SYNTAX  DisplayString  (SIZE(0..32))
    MAX-ACCESS  read-only
    STATUS  current
    DESCRIPTION
        "Compression policy name associated with this virtual service."
    ::= { slbCurCfgEnhVirtServicesSecondPartEntry 6 }

slbCurCfgEnhVirtServiceSSLpol OBJECT-TYPE
    SYNTAX  DisplayString  (SIZE(0..32))
    MAX-ACCESS  read-only
    STATUS  current
    DESCRIPTION
        "SSL policy name associated with this virtual service."
    ::= { slbCurCfgEnhVirtServicesSecondPartEntry 7 }

slbCurCfgEnhVirtServiceServCert OBJECT-TYPE
    SYNTAX  DisplayString  (SIZE(0..128))
    MAX-ACCESS  read-only
    STATUS  current
    DESCRIPTION
        "Server Certificate name associated with this virtual service."
    ::= { slbCurCfgEnhVirtServicesSecondPartEntry 8 }
slbCurCfgEnhVirtServiceHttpmodList OBJECT-TYPE
    SYNTAX  DisplayString  (SIZE(0..32))
    MAX-ACCESS  read-only
    STATUS  current
    DESCRIPTION
        "HTTP Content Modifications Rule-list associated with this virtual service."
    ::= { slbCurCfgEnhVirtServicesSecondPartEntry 9 }

slbCurCfgEnhVirtServiceCloaksrv OBJECT-TYPE
    SYNTAX  INTEGER {
        enabled(1),
        disabled(2),
        unsupported(2147483647)
        }
    MAX-ACCESS  read-only
    STATUS  current
    DESCRIPTION
        "Enable/disable server cloaking."
    ::= { slbCurCfgEnhVirtServicesSecondPartEntry 10 }

slbCurCfgEnhVirtServErrcodeStatus OBJECT-TYPE
    SYNTAX  INTEGER {
        enabled(1),
        disabled(2),
        clear(3),
        unsupported(2147483647)
        }
    MAX-ACCESS  read-only
    STATUS  current
    DESCRIPTION
        "Enable/disable/clear error-code configuration."
    ::= { slbCurCfgEnhVirtServicesSecondPartEntry 11 }

slbCurCfgEnhVirtServErrcodeMatch OBJECT-TYPE
    SYNTAX  DisplayString (SIZE (0..64))
    MAX-ACCESS  read-only
    STATUS  current
    DESCRIPTION
        "Match error-code(s), e.g 203,204 ."
    ::= { slbCurCfgEnhVirtServicesSecondPartEntry 12 }

slbCurCfgEnhVirtServErrcodeHttpRedir OBJECT-TYPE
    SYNTAX  INTEGER {
        yes(1),
        no(2),
        unsupported(2147483647)
    }
    MAX-ACCESS  read-only
    STATUS  current
    DESCRIPTION
        "Use http redirection [yes/no] [Default: yes]."
    ::= { slbCurCfgEnhVirtServicesSecondPartEntry 13 }

slbCurCfgEnhVirtServErrcodeUrl OBJECT-TYPE
    SYNTAX  DisplayString (SIZE(0..240))
    MAX-ACCESS  read-only
    STATUS  current
    DESCRIPTION
        "URL for redirection."
    ::= { slbCurCfgEnhVirtServicesSecondPartEntry 14 }


slbCurCfgEnhVirtServErrcode OBJECT-TYPE
    SYNTAX  DisplayString (SIZE(0..3))
    MAX-ACCESS  read-only
    STATUS  current
    DESCRIPTION
        "Set error code [Default: 302]."
    ::= { slbCurCfgEnhVirtServicesSecondPartEntry 15 }

slbCurCfgEnhVirtServErrcodeNew OBJECT-TYPE
    SYNTAX  DisplayString (SIZE(0..3))
    MAX-ACCESS  read-only
    STATUS  current
    DESCRIPTION
        "Enter Cur error code [Default: 302]."
    ::= { slbCurCfgEnhVirtServicesSecondPartEntry 16 }

slbCurCfgEnhVirtServErrcodeReason OBJECT-TYPE
    SYNTAX  DisplayString (SIZE(0..128))
    MAX-ACCESS  read-only
    STATUS  current
    DESCRIPTION
        "Enter error reason."
    ::= { slbCurCfgEnhVirtServicesSecondPartEntry 17 }

slbCurCfgEnhVirtServUrlchangStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgEnhVirtServicesSecondPartEntry 18 }

slbCurCfgEnhVirtServUrlchangHostType OBJECT-TYPE
    SYNTAX  INTEGER {
        sufx(1),
        prefx(2),
        eq(3),
        incl(4),
        any(5),
        unsupported(2147483647)
    }
    MAX-ACCESS  read-only
    STATUS  current
    DESCRIPTION
        "Enter hostname match type [sufx|prefx|eq|incl|any] [Default: any]"
    ::= { slbCurCfgEnhVirtServicesSecondPartEntry 19 }

slbCurCfgEnhVirtServiceFeTcpPolId  OBJECT-TYPE   
    SYNTAX  DisplayString  (SIZE(0..32))
    MAX-ACCESS  read-only
    STATUS  current   
    DESCRIPTION 
        "Frontend TCP optimization policy."
    ::= { slbCurCfgEnhVirtServicesSecondPartEntry 20 }

slbCurCfgEnhVirtServiceBeTcpPolId OBJECT-TYPE   
    SYNTAX  DisplayString  (SIZE(0..32))
    MAX-ACCESS  read-only
    STATUS  current   
    DESCRIPTION 
        "Backend TCP optimization policy."
    ::= { slbCurCfgEnhVirtServicesSecondPartEntry 21 }

slbCurCfgEnhVirtServicesThirdPartTable OBJECT-TYPE
    SYNTAX  SEQUENCE OF SlbCurCfgEnhVirtServicesThirdPartEntry
    MAX-ACCESS  not-accessible
    STATUS  current
    DESCRIPTION
        "The table of virtual Services.
         Note:This mib is not supported for VX instance of Virtualization."
    ::= { virtualServerCfg 26 }

slbCurCfgEnhVirtServicesThirdPartEntry OBJECT-TYPE
    SYNTAX  SlbCurCfgEnhVirtServicesThirdPartEntry
    MAX-ACCESS  not-accessible
    STATUS  current
    DESCRIPTION
        "A row in the virtual services table."
    INDEX   { slbCurCfgEnhVirtServThirdPartIndex, slbCurCfgEnhVirtServiceThirdPartIndex }
    ::= { slbCurCfgEnhVirtServicesThirdPartTable 1 }

SlbCurCfgEnhVirtServicesThirdPartEntry ::= SEQUENCE {
    slbCurCfgEnhVirtServThirdPartIndex            DisplayString,
    slbCurCfgEnhVirtServiceThirdPartIndex         Integer32,

    slbCurCfgEnhVirtServUrlchangHostName   DisplayString,
    slbCurCfgEnhVirtServUrlchangPathType   INTEGER,
    slbCurCfgEnhVirtServUrlchangPathMatch  DisplayString,
    slbCurCfgEnhVirtServUrlchangPageName   DisplayString,
    slbCurCfgEnhVirtServUrlchangPageType   DisplayString,
    slbCurCfgEnhVirtServUrlchangActnType   INTEGER,
    slbCurCfgEnhVirtServUrlchangPathInsrt  DisplayString,
    slbCurCfgEnhVirtServUrlchangInsrtPostn INTEGER
}


slbCurCfgEnhVirtServThirdPartIndex OBJECT-TYPE
    SYNTAX  DisplayString (SIZE(1..255))
    MAX-ACCESS  read-only
    STATUS  current
    DESCRIPTION
        "The number of the virtual server."
    ::= { slbCurCfgEnhVirtServicesThirdPartEntry 1 }

slbCurCfgEnhVirtServiceThirdPartIndex OBJECT-TYPE
    SYNTAX  Integer32
    MAX-ACCESS  read-only
    STATUS  current
    DESCRIPTION
        "The service index. This has no external meaning"
    ::= { slbCurCfgEnhVirtServicesThirdPartEntry 2 }

slbCurCfgEnhVirtServUrlchangHostName OBJECT-TYPE
    SYNTAX  DisplayString (SIZE(0..250))
    MAX-ACCESS  read-only
    STATUS  current
    DESCRIPTION
        "Enter hostname to match."
    ::= { slbCurCfgEnhVirtServicesThirdPartEntry 3 }

slbCurCfgEnhVirtServUrlchangPathType OBJECT-TYPE
    SYNTAX  INTEGER {
        sufx(1),
        prefx(2),
        eq(3),
        incl(4),
        any(5),
        none(6),
        unsupported(2147483647)
    }
    MAX-ACCESS  read-only
    STATUS  current
    DESCRIPTION
        "Enter path match type [sufx|prefx|eq|incl|any]."
    ::= { slbCurCfgEnhVirtServicesThirdPartEntry 4 }

slbCurCfgEnhVirtServUrlchangPathMatch OBJECT-TYPE
    SYNTAX  DisplayString (SIZE(0..250))
    MAX-ACCESS  read-only
    STATUS  current
    DESCRIPTION
        "Enter path to match."
    ::= { slbCurCfgEnhVirtServicesThirdPartEntry 5 }

slbCurCfgEnhVirtServUrlchangPageName OBJECT-TYPE
    SYNTAX  DisplayString (SIZE(0..64))
    MAX-ACCESS  read-only
    STATUS  current
    DESCRIPTION
        "Enter page name to match or none."
    ::= { slbCurCfgEnhVirtServicesThirdPartEntry 6 }

slbCurCfgEnhVirtServUrlchangPageType OBJECT-TYPE
    SYNTAX  DisplayString (SIZE(0..64))
    MAX-ACCESS  read-only
    STATUS  current
    DESCRIPTION
        "Enter page type to match or none."
    ::= { slbCurCfgEnhVirtServicesThirdPartEntry 7 }

slbCurCfgEnhVirtServUrlchangActnType OBJECT-TYPE
    SYNTAX  INTEGER {
        insert(1),
        replace(2),
        remove(3),
        none(4),
        unsupported(2147483647)
    }
    MAX-ACCESS  read-only
    STATUS  current
    DESCRIPTION
        "Enter path action type."
    ::= { slbCurCfgEnhVirtServicesThirdPartEntry 8 }

slbCurCfgEnhVirtServUrlchangPathInsrt OBJECT-TYPE
    SYNTAX  DisplayString (SIZE(0..250))
    MAX-ACCESS  read-only
    STATUS  current
    DESCRIPTION
        "Enter path to insert."
    ::= { slbCurCfgEnhVirtServicesThirdPartEntry 9 }


slbCurCfgEnhVirtServUrlchangInsrtPostn OBJECT-TYPE
    SYNTAX  INTEGER {
        before(1),
        after(2),
        unsupported(2147483647)
    }
    MAX-ACCESS  read-only
    STATUS  current
    DESCRIPTION
        "Insert the specified path before or after the matched section"
    ::= { slbCurCfgEnhVirtServicesThirdPartEntry 10 }



slbCurCfgEnhVirtServicesFourthPartTable OBJECT-TYPE
    SYNTAX  SEQUENCE OF SlbCurCfgEnhVirtServicesFourthPartEntry
    MAX-ACCESS  not-accessible
    STATUS  current
    DESCRIPTION
        "The table of virtual Services.
         Note:This mib is not supported for VX instance of Virtualization."
    ::= { virtualServerCfg 27 }

slbCurCfgEnhVirtServicesFourthPartEntry OBJECT-TYPE
    SYNTAX  SlbCurCfgEnhVirtServicesFourthPartEntry
    MAX-ACCESS  not-accessible
    STATUS  current
    DESCRIPTION
        "A row in the virtual services table."
    INDEX   { slbCurCfgEnhVirtServFourthPartIndex, slbCurCfgEnhVirtServiceFourthPartIndex }
    ::= { slbCurCfgEnhVirtServicesFourthPartTable 1 }

SlbCurCfgEnhVirtServicesFourthPartEntry ::= SEQUENCE {
    slbCurCfgEnhVirtServFourthPartIndex            DisplayString,
    slbCurCfgEnhVirtServiceFourthPartIndex         Integer32,

    slbCurCfgEnhVirtServUrlchangNewPgName  DisplayString,
    slbCurCfgEnhVirtServUrlchangNewPgType  DisplayString,

    slbCurCfgEnhVirtServPathHideStatus     INTEGER,
    slbCurCfgEnhVirtServPathHideHostType   INTEGER,
    slbCurCfgEnhVirtServPathHideHostName   DisplayString,
    slbCurCfgEnhVirtServPathHidePathType   INTEGER,
    slbCurCfgEnhVirtServPathHidePathName   DisplayString,

    slbCurCfgEnhVirtServTextrepStatus      INTEGER,
    slbCurCfgEnhVirtServTextrepAction      INTEGER
}

slbCurCfgEnhVirtServFourthPartIndex OBJECT-TYPE
    SYNTAX  DisplayString  (SIZE(1..255))
    MAX-ACCESS  read-only
    STATUS  current
    DESCRIPTION
        "The number of the virtual server."
    ::= { slbCurCfgEnhVirtServicesFourthPartEntry 1 }

slbCurCfgEnhVirtServiceFourthPartIndex OBJECT-TYPE
    SYNTAX  Integer32
    MAX-ACCESS  read-only
    STATUS  current
    DESCRIPTION
        "The service index. This has no external meaning"
    ::= { slbCurCfgEnhVirtServicesFourthPartEntry 2 }
slbCurCfgEnhVirtServUrlchangNewPgName OBJECT-TYPE
    SYNTAX  DisplayString (SIZE(0..64))
    MAX-ACCESS  read-only
    STATUS  current
    DESCRIPTION
        "Enter Cur page name or none."
    ::= { slbCurCfgEnhVirtServicesFourthPartEntry 3 }

slbCurCfgEnhVirtServUrlchangNewPgType OBJECT-TYPE
    SYNTAX  DisplayString (SIZE(0..64))
    MAX-ACCESS  read-only
    STATUS  current
    DESCRIPTION
        "Enter Cur page type or none."
    ::= { slbCurCfgEnhVirtServicesFourthPartEntry 4 }

slbCurCfgEnhVirtServPathHideStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgEnhVirtServicesFourthPartEntry 5 }

slbCurCfgEnhVirtServPathHideHostType OBJECT-TYPE
    SYNTAX  INTEGER {
        sufx(1),
        prefx(2),
        eq(3),
        incl(4),
        any(5),
        unsupported(2147483647)
    }
    MAX-ACCESS  read-only
    STATUS  current
    DESCRIPTION
        "Enter hostname type [sufx|prefx|eq|incl|any] [Default: any]."
    ::= { slbCurCfgEnhVirtServicesFourthPartEntry 6 }

slbCurCfgEnhVirtServPathHideHostName OBJECT-TYPE
    SYNTAX  DisplayString (SIZE(0..250))
    MAX-ACCESS  read-only
    STATUS  current
    DESCRIPTION
        "Enter hostname to match."
    ::= { slbCurCfgEnhVirtServicesFourthPartEntry 7 }

slbCurCfgEnhVirtServPathHidePathType OBJECT-TYPE
    SYNTAX  INTEGER {
        sufx(1),
        prefx(2),
        eq(3),
        none(4),
        unsupported(2147483647)
    }
    MAX-ACCESS  read-only
    STATUS  current
    DESCRIPTION
        "Enter path match type [sufx|prefx|eq|none]."
    ::= { slbCurCfgEnhVirtServicesFourthPartEntry 8 }

slbCurCfgEnhVirtServPathHidePathName OBJECT-TYPE
    SYNTAX  DisplayString (SIZE(0..250))
    MAX-ACCESS  read-only
    STATUS  current
    DESCRIPTION
        "Enter path to remove."
    ::= { slbCurCfgEnhVirtServicesFourthPartEntry 9 }


slbCurCfgEnhVirtServTextrepStatus OBJECT-TYPE
    SYNTAX  INTEGER {
        enable(1),
        disable(2),
        clear(3),
        unsupported(2147483647)
    }
    MAX-ACCESS  read-only
    STATUS  current
    DESCRIPTION
        "Enter enabled/disabled/clear [Default: clear]."
    ::= { slbCurCfgEnhVirtServicesFourthPartEntry 10 }

slbCurCfgEnhVirtServTextrepAction OBJECT-TYPE
    SYNTAX  INTEGER {
        none(0),
        replace(1),
        remove(2),
        unsupported(2147483647)
    }
    MAX-ACCESS  read-only
    STATUS  current
    DESCRIPTION
        "Enter action [replace|remove|none]."
    ::= { slbCurCfgEnhVirtServicesFourthPartEntry 11 }




slbCurCfgEnhVirtServicesFifthPartTable OBJECT-TYPE
    SYNTAX  SEQUENCE OF SlbCurCfgEnhVirtServicesFifthPartEntry
    MAX-ACCESS  not-accessible
    STATUS  current
    DESCRIPTION
        "The table of virtual Services.
         Note:This mib is not supported for VX instance of Virtualization."
    ::= { virtualServerCfg 28 }

slbCurCfgEnhVirtServicesFifthPartEntry OBJECT-TYPE
    SYNTAX  SlbCurCfgEnhVirtServicesFifthPartEntry
    MAX-ACCESS  not-accessible
    STATUS  current
    DESCRIPTION
        "A row in the virtual services table."
    INDEX   { slbCurCfgEnhVirtServFifthPartIndex, slbCurCfgEnhVirtServiceFifthPartIndex }
    ::= { slbCurCfgEnhVirtServicesFifthPartTable 1 }


SlbCurCfgEnhVirtServicesFifthPartEntry ::= SEQUENCE {

    slbCurCfgEnhVirtServFifthPartIndex            DisplayString,
    slbCurCfgEnhVirtServiceFifthPartIndex         Integer32,

    slbCurCfgEnhVirtServTextrepMatchText   DisplayString,
    slbCurCfgEnhVirtServTextrepReplacTxt   DisplayString,

    slbCurCfgEnhVirtServApplicationType    INTEGER,
    slbCurCfgEnhVirtServiceName          DisplayString,
    slbCurCfgEnhVirtServiceAction        INTEGER,
    slbCurCfgEnhVirtServiceRedirect      DisplayString,

        slbCurCfgEnhVirtServiceServCertGrpMark INTEGER,
        slbCurCfgEnhVirtServiceDnsType         INTEGER,
        slbCurCfgEnhVirtServiceClntproxType    INTEGER,
        slbCurCfgEnhVirtServiceZerowinSize     INTEGER,
        slbCurCfgEnhVirtServiceCookiePath    DisplayString,
        slbCurCfgEnhVirtServiceCookieSecure    INTEGER,
        slbCurCfgEnhVirtServiceNoRtsp          INTEGER,
        slbCurCfgEnhVirtServiceCkRebind        INTEGER,
        slbCurCfgEnhVirtServiceParseLimit      INTEGER,
        slbCurCfgEnhVirtServiceParseLength     INTEGER,
        slbCurCfgEnhVirtServiceUriNorm         INTEGER,
        slbCurCfgEnhVirtServiceGranularity     INTEGER,
        slbCurCfgEnhVirtServiceSessLog         INTEGER,
        slbCurCfgEnhVirtServiceUdpAge          INTEGER,
        slbCurCfgEnhVirtServiceSessEntryMode   INTEGER,
	slbCurCfgEnhVirtServiceSecPol        DisplayString,
        slbCurCfgEnhVirtServiceAlwaysOn        INTEGER,
	slbCurCfgEnhVirtServiceSendRST         INTEGER,
	slbCurCfgEnhVirtServiceClsOnSlowage    INTEGER
    }

    slbCurCfgEnhVirtServFifthPartIndex OBJECT-TYPE
        SYNTAX  DisplayString  (SIZE(1..255))
        MAX-ACCESS  read-only
        STATUS  current
        DESCRIPTION
            "The number of the virtual server."
        ::= { slbCurCfgEnhVirtServicesFifthPartEntry 1 }

    slbCurCfgEnhVirtServiceFifthPartIndex OBJECT-TYPE
        SYNTAX  Integer32
        MAX-ACCESS  read-only
    STATUS  current
    DESCRIPTION
        "The service index. This has no external meaning"
    ::= { slbCurCfgEnhVirtServicesFifthPartEntry 2 }

slbCurCfgEnhVirtServTextrepMatchText OBJECT-TYPE
    SYNTAX  DisplayString (SIZE(0..128))
    MAX-ACCESS  read-only
    STATUS  current
    DESCRIPTION
        "Enter text to be replaced."
    ::= { slbCurCfgEnhVirtServicesFifthPartEntry 3 }

slbCurCfgEnhVirtServTextrepReplacTxt OBJECT-TYPE
    SYNTAX  DisplayString (SIZE(0..128))
    MAX-ACCESS  read-only
    STATUS  current
    DESCRIPTION
        "Enter Cur text."
    ::= { slbCurCfgEnhVirtServicesFifthPartEntry 4 }

slbCurCfgEnhVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12),
      smtp(13),
      pop3(14),
      ip(15),
      mh-sctp(16),
      unsupported(2147483647)
    }
    MAX-ACCESS  read-only
    STATUS  current
    DESCRIPTION
        "Application Type for virtual service."
    ::= { slbCurCfgEnhVirtServicesFifthPartEntry 5 }

slbCurCfgEnhVirtServiceName OBJECT-TYPE
    SYNTAX  DisplayString (SIZE(0..32))
    MAX-ACCESS  read-only
    STATUS  current
    DESCRIPTION
        "The name of the virtual service."
    ::= { slbCurCfgEnhVirtServicesFifthPartEntry 6 }

slbCurCfgEnhVirtServiceAction OBJECT-TYPE
    SYNTAX  INTEGER    {
    group(1),
    redirect(2),
    discard(3),
    unsupported(2147483647)
    }
    MAX-ACCESS  read-only
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbCurCfgEnhVirtServicesFifthPartEntry 7 }

slbCurCfgEnhVirtServiceRedirect OBJECT-TYPE
    SYNTAX  DisplayString  (SIZE(0..255))
    MAX-ACCESS  read-only
    STATUS  current
    DESCRIPTION
        "application redirection location.We need to provide this
         value When action type is set to redirect(2)."
    ::= { slbCurCfgEnhVirtServicesFifthPartEntry 8 }

slbCurCfgEnhVirtServiceServCertGrpMark OBJECT-TYPE
    SYNTAX  INTEGER    {
    cert(1),
    group(2),
    unsupported(2147483647)
    }
    MAX-ACCESS  read-only
    STATUS  current
    DESCRIPTION
        "Group Mark for Server Certificate. If we set value as cert(0)
         It will denote that the server certificate (name) associated with
         this virtual service, represents a certificate. Otherwise, a value of group(1), denotes that the server
         certificate (name) represents a group."
    ::= { slbCurCfgEnhVirtServicesFifthPartEntry 9}

slbCurCfgEnhVirtServiceDnsType OBJECT-TYPE
    SYNTAX  INTEGER {
        dns(1),
        dnssec(2),
        both(3),
        unsupported(2147483647)
        }
    MAX-ACCESS  read-only
    STATUS  current
    DESCRIPTION
        "Set DNS type for this service (DNS, DNSSEC)."
    ::= { slbCurCfgEnhVirtServicesFifthPartEntry 10 }

slbCurCfgEnhVirtServiceClntproxType OBJECT-TYPE
    SYNTAX  INTEGER {
        none(1),
        http(2),
        https(3),
        unsupported(2147483647)
        }
    MAX-ACCESS  read-only
    STATUS  current
    DESCRIPTION
        "Set client proximity type for this service."
    ::= { slbCurCfgEnhVirtServicesFifthPartEntry 11 }

slbCurCfgEnhVirtServiceZerowinSize OBJECT-TYPE
    SYNTAX  INTEGER {
        enabled(1),
        disabled(2),
        unsupported(2147483647)
        }
    MAX-ACCESS  read-only
    STATUS  current
    DESCRIPTION
        "Enable or disable zero window size in SYN+ACK for this service."
    ::= { slbCurCfgEnhVirtServicesFifthPartEntry 12 }

slbCurCfgEnhVirtServiceCookiePath OBJECT-TYPE
    SYNTAX  DisplayString (SIZE(0..32))
    MAX-ACCESS  read-only
    STATUS  current
    DESCRIPTION
        "The cookie path name of the virtual server used for cookie load balance."
    ::= { slbCurCfgEnhVirtServicesFifthPartEntry 13 }

slbCurCfgEnhVirtServiceCookieSecure OBJECT-TYPE
    SYNTAX  INTEGER {
            no(1),
        yes(2),
        unsupported(2147483647)
        }
    MAX-ACCESS  read-only
    STATUS  current
    DESCRIPTION
        "Is cookie secure [yes/no] [Default: no]."
    ::= { slbCurCfgEnhVirtServicesFifthPartEntry 14 }

slbCurCfgEnhVirtServiceNoRtsp OBJECT-TYPE
    SYNTAX  INTEGER {
        enabled(1),
        disabled(2),
        unsupported(2147483647)
        }
    MAX-ACCESS  read-only
    STATUS  current
    DESCRIPTION
        "Enable or disable only rtsp SLB for this service."
    ::= { slbCurCfgEnhVirtServicesFifthPartEntry 15 }

slbCurCfgEnhVirtServiceCkRebind OBJECT-TYPE
    SYNTAX  INTEGER {
        enabled(1),
        disabled(2),
        unsupported(2147483647)
        }
    MAX-ACCESS  read-only
    STATUS  current
    DESCRIPTION
        "Server rebalancing when cookie is absent.
         When enabled, server load balancing will happen
         for subsequent request comes without cookie."
    ::= { slbCurCfgEnhVirtServicesFifthPartEntry 16 }

slbCurCfgEnhVirtServiceParseLimit OBJECT-TYPE
    SYNTAX  INTEGER {
        enabled(1),
        disabled(2),
        unsupported(2147483647)
        }
    MAX-ACCESS  read-only
    STATUS  current
    DESCRIPTION
        "Enable or disable buffer limit for content based selection."
    ::= { slbCurCfgEnhVirtServicesFifthPartEntry 17 }

slbCurCfgEnhVirtServiceParseLength OBJECT-TYPE
    SYNTAX  INTEGER (0..18200)
    MAX-ACCESS  read-only
    STATUS  current
    DESCRIPTION
        "The buffer length for content based selection."
    ::= { slbCurCfgEnhVirtServicesFifthPartEntry 18 }

slbCurCfgEnhVirtServiceUriNorm OBJECT-TYPE
    SYNTAX  INTEGER {
        enabled(1),
        disabled(2),
        unsupported(2147483647)
        }
    MAX-ACCESS  read-only
    STATUS  current
    DESCRIPTION
        "Enable or disable URI normalization for HTTP content matching."
    ::= { slbCurCfgEnhVirtServicesFifthPartEntry 19 }

slbCurCfgEnhVirtServiceGranularity OBJECT-TYPE
    SYNTAX  INTEGER {
        service(0),
        real(2),
        unsupported(2147483647)
        }
    MAX-ACCESS  read-only
    STATUS  current
    DESCRIPTION
        "Get the current Granularity of this service, for statistics report-protocol information.
         Group(1) - for group level, or GroupAndServers(2) - for server level."
    ::= { slbCurCfgEnhVirtServicesFifthPartEntry 20 }

slbCurCfgEnhVirtServiceSessLog OBJECT-TYPE
    SYNTAX  INTEGER {
        enabled(1),
        disabled(2),
        unsupported(2147483647)
        }
    MAX-ACCESS  read-only
    STATUS  current
    DESCRIPTION
        "Enable or disable Session Logging."
    ::= { slbCurCfgEnhVirtServicesFifthPartEntry 21 }

slbCurCfgEnhVirtServiceUdpAge OBJECT-TYPE
    SYNTAX  INTEGER {
        enabled(1),
        disabled(2),
        unsupported(2147483647)
        }
    MAX-ACCESS  read-only
    STATUS  current
    DESCRIPTION
        "Fast aging of UDP sessions."
    ::= { slbCurCfgEnhVirtServicesFifthPartEntry 22 }

slbCurCfgEnhVirtServiceSessEntryMode 
OBJECT-TYPE
    SYNTAX  INTEGER {
        single(1),
        multiple(2),
        unsupported(2147483647)
        }
    MAX-ACCESS  read-only
    STATUS  current
    DESCRIPTION
        "Session entry mode."
    ::= { slbCurCfgEnhVirtServicesFifthPartEntry 23 }

slbCurCfgEnhVirtServiceSecPol  OBJECT-TYPE
    SYNTAX  DisplayString  (SIZE(0..32))
    MAX-ACCESS  read-only
    STATUS  current
    DESCRIPTION
        "Security policy name associated with this virtual service."
    ::= { slbCurCfgEnhVirtServicesFifthPartEntry 24 }

slbCurCfgEnhVirtServiceAlwaysOn OBJECT-TYPE
    SYNTAX  INTEGER {
        enabled(1),
        disabled(2),
        unsupported(2147483647)
        }
    MAX-ACCESS  read-only
    STATUS  current
    DESCRIPTION
        "service always on when AS++ script attached."
    ::= { slbCurCfgEnhVirtServicesFifthPartEntry 25 }

slbCurCfgEnhVirtServiceSendRST OBJECT-TYPE
    SYNTAX  INTEGER {
        reset(1),
        drop(2),
        unsupported(2147483647)
        }
    MAX-ACCESS  read-only
    STATUS  current
    DESCRIPTION
        "Enable/Disable sending reset when the service is down."
    ::= { slbCurCfgEnhVirtServicesFifthPartEntry 26 }

slbCurCfgEnhVirtServiceClsOnSlowage OBJECT-TYPE
    SYNTAX  INTEGER {
        none(1),
        client(2),
        server(3),
        both(4),
        unsupported(2147483647)
        }
    MAX-ACCESS  read-only
    STATUS  current
    DESCRIPTION
        "Set close connection on aging treatment."
    ::= { slbCurCfgEnhVirtServicesFifthPartEntry 27 }

slbCurCfgEnhVirtServicesSixthPartTable OBJECT-TYPE
    SYNTAX  SEQUENCE OF SlbCurCfgEnhVirtServicesSixthPartEntry
    MAX-ACCESS  not-accessible
    STATUS  current
    DESCRIPTION
        "The table of virtual Services.
         Note:This mib is not supported for VX instance of Virtualization."
    ::= { virtualServerCfg 40 }

slbCurCfgEnhVirtServicesSixthPartEntry OBJECT-TYPE
    SYNTAX  SlbCurCfgEnhVirtServicesSixthPartEntry
    MAX-ACCESS  not-accessible
    STATUS  current
    DESCRIPTION
        "A row in the virtual services table."
    INDEX   { slbCurCfgEnhVirtServSixthPartIndex, slbCurCfgEnhVirtServiceSixthPartIndex }
    ::= { slbCurCfgEnhVirtServicesSixthPartTable 1 }

SlbCurCfgEnhVirtServicesSixthPartEntry ::= SEQUENCE {

    slbCurCfgEnhVirtServSixthPartIndex            DisplayString,
    slbCurCfgEnhVirtServiceSixthPartIndex         Integer32,
    slbCurCfgEnhVirtServiceHname         DisplayString,
    slbCurCfgEnhVirtServiceCname         DisplayString,
    slbCurCfgEnhVirtServiceCExpire       DisplayString,
    slbCurCfgEnhVirtServiceUrlHashLen    INTEGER,
    slbCurCfgEnhVirtServiceDirect        INTEGER,
    slbCurCfgEnhVirtServiceThash         INTEGER,
    slbCurCfgEnhVirtServiceLdapreset     INTEGER,
    slbCurCfgEnhVirtServiceLdapslb       INTEGER,
    slbCurCfgEnhVirtServiceSip           INTEGER,
    slbCurCfgEnhVirtServiceXForwardedFor INTEGER,
    slbCurCfgEnhVirtServiceHttpRedir     INTEGER,
    slbCurCfgEnhVirtServicePbindRport    INTEGER,
    slbCurCfgEnhVirtServiceEgressPip     INTEGER,
    slbCurCfgEnhVirtServiceCookieDname   INTEGER,
    slbCurCfgEnhVirtServiceWts           INTEGER,
    slbCurCfgEnhVirtServiceUhash         INTEGER,
    slbCurCfgEnhVirtServiceTimeOut       INTEGER,
    slbCurCfgEnhVirtServiceSdpNat        INTEGER

}

slbCurCfgEnhVirtServSixthPartIndex OBJECT-TYPE
    SYNTAX  DisplayString (SIZE(1..255))
    MAX-ACCESS  read-only
    STATUS  current
    DESCRIPTION
        "The number of the virtual server."
    ::= { slbCurCfgEnhVirtServicesSixthPartEntry 1 }

slbCurCfgEnhVirtServiceSixthPartIndex OBJECT-TYPE
    SYNTAX  Integer32
    MAX-ACCESS  read-only
    STATUS  current
    DESCRIPTION
        "The service index. This has no external meaning"
    ::= { slbCurCfgEnhVirtServicesSixthPartEntry 2 }

slbCurCfgEnhVirtServiceHname OBJECT-TYPE
    SYNTAX  DisplayString (SIZE(0..34))
    MAX-ACCESS  read-only
    STATUS  current
    DESCRIPTION
        "The host name of the virtual service."
    ::= { slbCurCfgEnhVirtServicesSixthPartEntry 3 }

slbCurCfgEnhVirtServiceCname OBJECT-TYPE
    SYNTAX  DisplayString (SIZE(0..20))
    MAX-ACCESS  read-only
    STATUS  current
    DESCRIPTION
        "The cookie name of the virtual server used for cookie load balance."
    ::= { slbCurCfgEnhVirtServicesSixthPartEntry 4 }

slbCurCfgEnhVirtServiceCExpire OBJECT-TYPE
    SYNTAX  DisplayString (SIZE(0..20))
    MAX-ACCESS  read-only
    STATUS  current
    DESCRIPTION
        "The cookie expire of the virtual server used for insert cookie load
         balance depending on the mode it has the following format
         <MM/dd/yy[@hh:mm]> absolute mode or <days[:hours[:minutes]]>
         for relative mode."
    ::= { slbCurCfgEnhVirtServicesSixthPartEntry 5 }

slbCurCfgEnhVirtServiceUrlHashLen OBJECT-TYPE
    SYNTAX  INTEGER (0..255)
    MAX-ACCESS  read-only
    STATUS  current
    DESCRIPTION
        "The number of bytes used to hash onto server, A zero means
         URL hashing disabled."
    ::= { slbCurCfgEnhVirtServicesSixthPartEntry 6 }


slbCurCfgEnhVirtServiceDirect OBJECT-TYPE
    SYNTAX  INTEGER {
        enabled(1),
        disabled(2),
        unsupported(2147483647)
        }
    MAX-ACCESS  read-only
    STATUS  current
    DESCRIPTION
        "Enable or disable DAM for this service."
    ::= { slbCurCfgEnhVirtServicesSixthPartEntry 7 }

slbCurCfgEnhVirtServiceThash OBJECT-TYPE
    SYNTAX  INTEGER {
        sip(1),
        sip-sport(2),
        unsupported(2147483647)
        }
    MAX-ACCESS  read-only
    STATUS  current
    DESCRIPTION
        "Set hash parameter."
    ::= { slbCurCfgEnhVirtServicesSixthPartEntry 8 }

slbCurCfgEnhVirtServiceLdapreset OBJECT-TYPE
    SYNTAX  INTEGER {
        enabled(1),
        disabled(2),
        unsupported(2147483647)
        }
    MAX-ACCESS  read-only
    STATUS  current
    DESCRIPTION
        "Enable or disable LDAP Server Reset"
    ::= { slbCurCfgEnhVirtServicesSixthPartEntry 9 }

slbCurCfgEnhVirtServiceLdapslb OBJECT-TYPE
    SYNTAX  INTEGER {
        enabled(1),
        disabled(2),
        unsupported(2147483647)
        }
    MAX-ACCESS  read-only
    STATUS  current
    DESCRIPTION
        "Enable or disable LDAP Server load balancing"
    ::= { slbCurCfgEnhVirtServicesSixthPartEntry 10 }

slbCurCfgEnhVirtServiceSip OBJECT-TYPE
    SYNTAX  INTEGER {
        enabled(1),
        disabled(2),
        unsupported(2147483647)
        }
    MAX-ACCESS  read-only
    STATUS  current
    DESCRIPTION
        "Enable/disable SIP load balancing."
    ::= { slbCurCfgEnhVirtServicesSixthPartEntry 11 }

slbCurCfgEnhVirtServiceXForwardedFor OBJECT-TYPE
    SYNTAX  INTEGER {
        enabled(1),
        disabled(2),
        unsupported(2147483647)
        }
    MAX-ACCESS  read-only
    STATUS  current
    DESCRIPTION
        "Enable/disable X-Forwarded-For for proxy mode."
    ::= { slbCurCfgEnhVirtServicesSixthPartEntry 12 }

slbCurCfgEnhVirtServiceHttpRedir OBJECT-TYPE
    SYNTAX  INTEGER {
        enabled(1),
        disabled(2),
        unsupported(2147483647)
        }
    MAX-ACCESS  read-only
    STATUS  current
    DESCRIPTION
        "Enable/disable HTTP/HTTPS redirect for GSLB."
    ::= { slbCurCfgEnhVirtServicesSixthPartEntry 13 }

slbCurCfgEnhVirtServicePbindRport OBJECT-TYPE
    SYNTAX  INTEGER {
        enabled(1),
        disabled(2),
        unsupported(2147483647)
        }
    MAX-ACCESS  read-only
    STATUS  current
    DESCRIPTION
        "Enable or disable use of rport in the session lookup for a persistent
         session."
    ::= { slbCurCfgEnhVirtServicesSixthPartEntry 14 }

slbCurCfgEnhVirtServiceEgressPip OBJECT-TYPE
    SYNTAX  INTEGER {
        enabled(1),
        disabled(2),
        unsupported(2147483647)
        }
    MAX-ACCESS  read-only
    STATUS  current
    DESCRIPTION
        "Enable/disable pip selection based on egress port/vlan."
    ::= { slbCurCfgEnhVirtServicesSixthPartEntry 15 }

slbCurCfgEnhVirtServiceCookieDname OBJECT-TYPE
    SYNTAX INTEGER {
        enabled(1),
        disabled(2),
        unsupported(2147483647)
        }
    MAX-ACCESS read-only
    STATUS current
    DESCRIPTION
        "Select dname for insert cookie persistence mode."
    ::= { slbCurCfgEnhVirtServicesSixthPartEntry 16 }

slbCurCfgEnhVirtServiceWts OBJECT-TYPE
    SYNTAX INTEGER {
        enabled(1),
        disabled(2),
        unsupported(2147483647)
        }
    MAX-ACCESS read-only
    STATUS current
    DESCRIPTION
        "Enable or disable WTS loadbalancing and persistence."
    ::= { slbCurCfgEnhVirtServicesSixthPartEntry 17 }

slbCurCfgEnhVirtServiceUhash OBJECT-TYPE
    SYNTAX INTEGER {
        enabled(1),
        disabled(2),
        unsupported(2147483647)
        }
    MAX-ACCESS read-only
    STATUS current
    DESCRIPTION
        "Enable when there is no Session Directory server."
    ::= { slbCurCfgEnhVirtServicesSixthPartEntry 18 }

slbCurCfgEnhVirtServiceTimeOut OBJECT-TYPE
    SYNTAX  INTEGER (0..32768)
    MAX-ACCESS  read-only
    STATUS  current
    DESCRIPTION
        "The maximum number of minutes an inactive connection remains open."
    ::= { slbCurCfgEnhVirtServicesSixthPartEntry 19 }

slbCurCfgEnhVirtServiceSdpNat OBJECT-TYPE
    SYNTAX  INTEGER {
        enabled(1),
        disabled(2),
        unsupported(2147483647)
        }
    MAX-ACCESS  read-only
    STATUS  current
    DESCRIPTION
        "Enable/disable SIP Media portal NAT."
    ::= { slbCurCfgEnhVirtServicesSixthPartEntry 20 }

slbCurCfgEnhVirtServicesSeventhPartTable OBJECT-TYPE
    SYNTAX  SEQUENCE OF SlbCurCfgEnhVirtServicesSeventhPartEntry
    MAX-ACCESS  not-accessible
    STATUS  current
    DESCRIPTION
        "The table of virtual Services.
         Note:This mib is not supported for VX instance of Virtualization."
    ::= { virtualServerCfg 41 }

slbCurCfgEnhVirtServicesSeventhPartEntry OBJECT-TYPE
    SYNTAX  SlbCurCfgEnhVirtServicesSeventhPartEntry
    MAX-ACCESS  not-accessible
    STATUS  current
    DESCRIPTION
        "A row in the virtual services table."
    INDEX   { slbCurCfgEnhVirtServSeventhPartIndex, slbCurCfgEnhVirtServiceSeventhPartIndex }
    ::= { slbCurCfgEnhVirtServicesSeventhPartTable 1 }

SlbCurCfgEnhVirtServicesSeventhPartEntry ::= SEQUENCE {

    slbCurCfgEnhVirtServSeventhPartIndex            DisplayString,
    slbCurCfgEnhVirtServiceSeventhPartIndex         Integer32,
    slbCurCfgEnhVirtServiceRealGroup     DisplayString,
    slbCurCfgEnhVirtServiceSessionMirror INTEGER,
    slbCurCfgEnhVirtServiceSoftGrid      INTEGER,
    slbCurCfgEnhVirtServiceConnPooling   INTEGER,
    slbCurCfgEnhVirtPersistentTimeOut    INTEGER,
    slbCurCfgEnhVirtServiceProxyIpMode   INTEGER,
    slbCurCfgEnhVirtServiceProxyIpAddr   IpAddress,
    slbCurCfgEnhVirtServiceProxyIpMask   IpAddress,
    slbCurCfgEnhVirtServiceProxyIpv6Addr   DisplayString,
    slbCurCfgEnhVirtServiceProxyIpv6Prefix   INTEGER,
    slbCurCfgEnhVirtServiceProxyIpPersistency   INTEGER,
    slbCurCfgEnhVirtServiceProxyIpNWclass   DisplayString,
    slbCurCfgEnhVirtServiceProxyIpv6NWclass   DisplayString,
    slbCurCfgEnhVirtServiceProxyIpNWclassPersistency   INTEGER,
    slbCurCfgEnhVirtServiceHashLen          INTEGER,
    slbCurCfgEnhVirtServiceClsRST           INTEGER,
    slbCurCfgEnhVirtServiceHttpHdrName      DisplayString,
    slbCurCfgEnhVirtServFastWa              DisplayString,
    slbCurCfgEnhVirtServiceAppwallWebappId  DisplayString,
    slbCurCfgEnhVirtServiceHttp2            DisplayString,
    slbCurCfgEnhVirtServiceCluster          INTEGER,
    slbCurCfgEnhVirtServiceDataPort         INTEGER,
    slbCurCfgEnhVirtServiceApplicName       RadwareLongDisplayString,
    slbCurCfgEnhVirtServiceReport           INTEGER,
    slbCurCfgEnhVirtServiceTrevpol          DisplayString,
    slbCurCfgEnhVirtServiceSatisrt          INTEGER,
    slbCurCfgEnhVirtServiceNamesrvr         DisplayString,
    slbCurCfgEnhVirtServiceIsDnsSecVip      INTEGER
}

slbCurCfgEnhVirtServSeventhPartIndex OBJECT-TYPE
    SYNTAX  DisplayString (SIZE(1..255))
    MAX-ACCESS  read-only
    STATUS  current
    DESCRIPTION
        "The number of the virtual server."
    ::= { slbCurCfgEnhVirtServicesSeventhPartEntry 1 }

slbCurCfgEnhVirtServiceSeventhPartIndex OBJECT-TYPE
    SYNTAX  Integer32
    MAX-ACCESS  read-only
    STATUS  current
    DESCRIPTION
        "The service index. This has no external meaning"
    ::= { slbCurCfgEnhVirtServicesSeventhPartEntry 2 }

slbCurCfgEnhVirtServiceRealGroup OBJECT-TYPE
    SYNTAX  DisplayString (SIZE(1..255))
    MAX-ACCESS  read-only
    STATUS  current
    DESCRIPTION
        "The real server group number for this service."
    ::= { slbCurCfgEnhVirtServicesSeventhPartEntry 3 }


slbCurCfgEnhVirtServiceSessionMirror OBJECT-TYPE
    SYNTAX  INTEGER {
        enabled(1),
        disabled(2),
        unsupported(2147483647)
        }
    MAX-ACCESS  read-only
    STATUS  current
    DESCRIPTION
        "Enable/disable session mirroring."
    ::= { slbCurCfgEnhVirtServicesSeventhPartEntry 4 }

slbCurCfgEnhVirtServiceSoftGrid OBJECT-TYPE
    SYNTAX  INTEGER {
        enabled(1),
        disabled(2),
        unsupported(2147483647)
        }
    MAX-ACCESS  read-only
    STATUS  current
    DESCRIPTION
        "Enable/disable softgrid load balancing."
    ::= { slbCurCfgEnhVirtServicesSeventhPartEntry 5 }

slbCurCfgEnhVirtServiceConnPooling OBJECT-TYPE
    SYNTAX  INTEGER {
        enabled(1),
            disabled(2),
        unsupported(2147483647)
    }
    MAX-ACCESS  read-only
    STATUS  current
    DESCRIPTION
        "Enable/disable connection pooling for HTTP traffic."
    ::= { slbCurCfgEnhVirtServicesSeventhPartEntry 6 }

slbCurCfgEnhVirtPersistentTimeOut OBJECT-TYPE
    SYNTAX  INTEGER (0..32768)
    MAX-ACCESS  read-only
    STATUS  current
    DESCRIPTION
        "The maximum number of minutes a persistent session should exist."
    ::= { slbCurCfgEnhVirtServicesSeventhPartEntry 7 }

--Proxy IP Cur config start
slbCurCfgEnhVirtServiceProxyIpMode OBJECT-TYPE
    SYNTAX INTEGER {
        ingress(0),
         egress(1),
         address(2),
         nwclss(3),
        disable(4),
        unsupported(2147483647)
        }
    MAX-ACCESS  read-only
    STATUS  current
    DESCRIPTION
        "Set the Proxy IP mode, default is ingress(0).
                Changing from address(2) to any other mode will clear the configured IPv4/IPv6 address,prefix and persistancy.
                Changing from  nwclass(3) to any other mode will clear the configured NWclass and NWpersistancy."
    ::= { slbCurCfgEnhVirtServicesSeventhPartEntry 8 }

    slbCurCfgEnhVirtServiceProxyIpAddr OBJECT-TYPE
    SYNTAX  IpAddress
    MAX-ACCESS  read-only
    STATUS  current
    DESCRIPTION
        "This object ID allows configuring IPv4 PIP address.
                This object ID can be set only if slbCurCfgVirtServiceProxyIpMode is address else return failure.
                Returns 0 when slbCurCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbCurCfgEnhVirtServicesSeventhPartEntry 9 }

   slbCurCfgEnhVirtServiceProxyIpMask OBJECT-TYPE
    SYNTAX  IpAddress
    MAX-ACCESS  read-only
    STATUS  current
    DESCRIPTION
        "This object ID allows configuring IPv4 PIP Mask.
                Returns 0 when slbCurCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbCurCfgEnhVirtServicesSeventhPartEntry 10 }

    slbCurCfgEnhVirtServiceProxyIpv6Addr OBJECT-TYPE
    SYNTAX  DisplayString  (SIZE(0..40))
    MAX-ACCESS  read-only
    STATUS  current
    DESCRIPTION
        "This object ID allows configuring IPv6 PIP address.
                Returns 0 when slbCurCfgVirtServiceProxyIpMode is not set to address.
                When a subnet is configured user has the ability to select PIP persistency mode.
                Persistency is relevant only if either IPv4 PIP or IPv6 PIP (or both) are configured as
                subnet.
                Address should be 4-byte hexadecimal colon notation.
                Valid IPv6 address should be in any of the following forms
                       xxxx:xxxx:xxxx:xxxx:xxxx:xxxx:xxxx:xxxx or
                       xxxx::xxxx:xxxx:xxxx:xxxx or ::xxxx.
                If neither of the addresses (v4 & v6) are configured or are subnets, the persistency
                value is disable."
    ::= { slbCurCfgEnhVirtServicesSeventhPartEntry 11 }

   slbCurCfgEnhVirtServiceProxyIpv6Prefix OBJECT-TYPE
    SYNTAX  INTEGER (1..128)
    MAX-ACCESS  read-only
    STATUS  current
    DESCRIPTION
        "This object ID allows configuring IPv6 PIP Mask.
                Returns 0 when slbCurCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbCurCfgEnhVirtServicesSeventhPartEntry 12 }

slbCurCfgEnhVirtServiceProxyIpPersistency OBJECT-TYPE
    SYNTAX INTEGER {
        disable(0),
        client(1),
         host(2),
         unsupported(2147483647)
        }
    MAX-ACCESS  read-only
    STATUS  current
    DESCRIPTION
        "When a subnet is configured user has the ability to select PIP persistency mode.
                Returns 0 when slbCurCfgVirtServiceProxyIpMode is not set to address.
                Persistency is relevant only if either IPv4 PIP or IPv6 PIP (or both) are configured as
                subnet.
                If neither of the addresses (v4 & v6) are configured or are subnets, the persistency
                value is disable. "
    ::= { slbCurCfgEnhVirtServicesSeventhPartEntry 13 }

   slbCurCfgEnhVirtServiceProxyIpNWclass OBJECT-TYPE
    SYNTAX  DisplayString  (SIZE(0..32))
    MAX-ACCESS  read-only
    STATUS  current
    DESCRIPTION
        "This object ID allows configuring IPv4 Network Class as PIP and PIP persistency mode.
                Returns empty string when slbCurCfgVirtServiceProxyIpMode is not set to nwclass.
                Persistency is relevant only if either IPv4 or IPv6 class (or both) are configured.
                If neither of the classes (v4 & v6) are configured, the persistency configuration value is disable."
    ::= { slbCurCfgEnhVirtServicesSeventhPartEntry 14 }

   slbCurCfgEnhVirtServiceProxyIpv6NWclass OBJECT-TYPE
    SYNTAX  DisplayString  (SIZE(0..32))
    MAX-ACCESS  read-only
    STATUS  current
    DESCRIPTION
        "This object ID allows configuring IPv6 Network Class as PIP and PIP persistency mode.
                Returns empty string when slbCurCfgVirtServiceProxyIpMode is not set to nwclass.
                Persistency is relevant only if either IPv4 or IPv6 class (or both) are configured.
                If neither of the classes (v4 & v6) are configured, the persistency configuration value is disable."
    ::= { slbCurCfgEnhVirtServicesSeventhPartEntry 15 }

slbCurCfgEnhVirtServiceProxyIpNWclassPersistency OBJECT-TYPE
    SYNTAX INTEGER {
        disable(0),
        client(1),
        unsupported(2147483647)
        }
    MAX-ACCESS  read-only
    STATUS  current
    DESCRIPTION
        "This object ID allows configuring Network Class PIP persistency mode.
                Returns 0 when slbCurCfgVirtServiceProxyIpMode is not set to nwclass.
                Persistency is relevant only if either IPv4 PIP or IPv6 PIP (or both) are configured as
                subnet.
                If neither of the addresses (v4 & v6) are configured or are subnets, the persistency
                value is disable. "
    ::= { slbCurCfgEnhVirtServicesSeventhPartEntry 16 }
--Proxy IP Cur config end

slbCurCfgEnhVirtServiceHashLen OBJECT-TYPE
    SYNTAX INTEGER (4..256)
    MAX-ACCESS  read-only
    STATUS  current
    DESCRIPTION
        "Set length for slb service sip hashing (4- 256 bytes)"
    ::= { slbCurCfgEnhVirtServicesSeventhPartEntry 17 }

slbCurCfgEnhVirtServiceClsRST OBJECT-TYPE
    SYNTAX  INTEGER {
        enabled(1),
        disabled(2),
        unsupported(2147483647)
        }
    MAX-ACCESS  read-only
    STATUS  current
    DESCRIPTION
        "Enable or disable Send RST on connection close."
    ::= { slbCurCfgEnhVirtServicesSeventhPartEntry 18 }

slbCurCfgEnhVirtServiceHttpHdrName OBJECT-TYPE
    SYNTAX  DisplayString  (SIZE(0..32))
    MAX-ACCESS  read-only
    STATUS  current
    DESCRIPTION
        "The HTTP header name of the virtual server."
    ::= { slbCurCfgEnhVirtServicesSeventhPartEntry 19 }

slbCurCfgEnhVirtServFastWa OBJECT-TYPE
    SYNTAX  DisplayString  (SIZE(0..32))
    MAX-ACCESS  read-only
    STATUS  current
    DESCRIPTION
        "Fastview web application name associated with this virtual service."
    ::= { slbCurCfgEnhVirtServicesSeventhPartEntry 20 }
    
slbCurCfgEnhVirtServiceAppwallWebappId OBJECT-TYPE
    SYNTAX  DisplayString  (SIZE(0..32)) 
    MAX-ACCESS  read-only
    STATUS  current
    DESCRIPTION
        "This object ID shows current configured web security ID." 
    ::= { slbCurCfgEnhVirtServicesSeventhPartEntry 21 }    

slbCurCfgEnhVirtServiceHttp2 OBJECT-TYPE
    SYNTAX  DisplayString  (SIZE(0..32)) 
    MAX-ACCESS  read-only
    STATUS  current
    DESCRIPTION
        "Http2 policy name associated with this virtual service." 
    ::= { slbCurCfgEnhVirtServicesSeventhPartEntry 22 }    

slbCurCfgEnhVirtServiceCluster OBJECT-TYPE
    SYNTAX  INTEGER {
        enabled(1),
        disabled(2),
        unsupported(2147483647)
        }
    MAX-ACCESS  read-only
    STATUS  current
    DESCRIPTION
        "State of Cluster upadates for the service (Ena or Dis)."
    ::= { slbCurCfgEnhVirtServicesSeventhPartEntry 23 }

slbCurCfgEnhVirtServiceDataPort OBJECT-TYPE
    SYNTAX  INTEGER (1..65534)
    MAX-ACCESS  read-only
    STATUS  current
    DESCRIPTION
        "The ftp control service data port"
    ::= { slbCurCfgEnhVirtServicesSeventhPartEntry 24 }

slbCurCfgEnhVirtServiceApplicName OBJECT-TYPE
    SYNTAX  RadwareLongDisplayString (SIZE(1..261))
    MAX-ACCESS  read-only
    STATUS  current
    DESCRIPTION
    "Correlate several services into one application at the visualization."
    ::= { slbCurCfgEnhVirtServicesSeventhPartEntry 25 }

slbCurCfgEnhVirtServiceReport OBJECT-TYPE
    SYNTAX  INTEGER {
        enabled(1),
        disabled(2),
        unsupported(2147483647)
        }
    MAX-ACCESS  read-only
    STATUS  current
    DESCRIPTION
    "Enable/disable counter based reporting for service."
    ::= { slbCurCfgEnhVirtServicesSeventhPartEntry 26 }

slbCurCfgEnhVirtServiceTrevpol OBJECT-TYPE
    SYNTAX DisplayString  (SIZE(0..128))
    MAX-ACCESS  read-only
    STATUS  current
    DESCRIPTION
    "Current Traffic Event Log Policy."
    ::= { slbCurCfgEnhVirtServicesSeventhPartEntry 27 }

slbCurCfgEnhVirtServiceSatisrt OBJECT-TYPE
    SYNTAX  INTEGER (0..999999)
    MAX-ACCESS  read-only
    STATUS  current
    DESCRIPTION
        "Application satisfied response time threshold, inherits the value from the global satisfied value or set with different value 1-999999 ms."
    ::= { slbCurCfgEnhVirtServicesSeventhPartEntry 28 }

slbCurCfgEnhVirtServiceNamesrvr OBJECT-TYPE
    SYNTAX DisplayString  (SIZE(0..128))
    MAX-ACCESS  read-only
    STATUS  current
    DESCRIPTION
        "Current DNS Nameserver group."
    ::= { slbCurCfgEnhVirtServicesSeventhPartEntry 30 }


slbCurCfgEnhVirtServiceIsDnsSecVip OBJECT-TYPE
    SYNTAX  INTEGER {
        no(0),
        yes(1),
        unsupported(2147483647)
    }
    MAX-ACCESS  read-only
    STATUS  current
    DESCRIPTION
        "It returns Yes(1) if virtual service is configure auto with a DNS Responder VIP, else returns no(0)."
    ::= { slbCurCfgEnhVirtServicesSeventhPartEntry 31 }

-- Server load balancing - Virtual Services Table

slbNewCfgEnhVirtServicesTable OBJECT-TYPE
    SYNTAX  SEQUENCE OF SlbNewCfgEnhVirtServicesEntry
    MAX-ACCESS  not-accessible
    STATUS  current
    DESCRIPTION
        "The table of virtual Services.
         Note:This mib is not supported for VX instance of Virtualization."
    ::= { virtualServerCfg 29 }

slbNewCfgEnhVirtServicesEntry OBJECT-TYPE
    SYNTAX  SlbNewCfgEnhVirtServicesEntry
    MAX-ACCESS  not-accessible
    STATUS  current
    DESCRIPTION
        "A row in the virtual services table."
    INDEX   { slbNewCfgEnhVirtServIndex, slbNewCfgEnhVirtServiceIndex }
    ::= { slbNewCfgEnhVirtServicesTable 1 }


SlbNewCfgEnhVirtServicesEntry ::= SEQUENCE {
    slbNewCfgEnhVirtServIndex            DisplayString,
    slbNewCfgEnhVirtServiceIndex         Integer32,
    slbNewCfgEnhVirtServiceVirtPort      INTEGER,
    slbNewCfgEnhVirtServiceRealPort      INTEGER,
    slbNewCfgEnhVirtServiceUDPBalance    INTEGER,
    slbNewCfgEnhVirtServiceBwmContract   Integer32,
    slbNewCfgEnhVirtServiceDirServerRtn  INTEGER,
    slbNewCfgEnhVirtServiceRtspUrlParse  INTEGER,
    slbNewCfgEnhVirtServiceFtpParsing    INTEGER,
    slbNewCfgEnhVirtServiceRemapUDPFrags INTEGER,
    slbNewCfgEnhVirtServiceDnsSlb        INTEGER,
    slbNewCfgEnhVirtServiceResponseCount INTEGER,
    slbNewCfgEnhVirtServicePBind         INTEGER,
    slbNewCfgEnhVirtServiceCoffset       INTEGER,
    slbNewCfgEnhVirtServiceClength       INTEGER,
    slbNewCfgEnhVirtServiceUriCookie     INTEGER,
    slbNewCfgEnhVirtServiceCookieMode    INTEGER,
    slbNewCfgEnhVirtServiceDBind         INTEGER,
    slbNewCfgEnhVirtServiceHttpSlb       INTEGER,
    slbNewCfgEnhVirtServiceHttpSlbOption INTEGER,
    slbNewCfgEnhVirtServiceHttpSlb2      INTEGER,
    slbNewCfgEnhVirtServiceDelete        INTEGER,
    slbNewCfgEnhVirtServiceApm           INTEGER,
    slbNewCfgEnhVirtServiceNonHTTP       INTEGER,
    slbNewCfgEnhVirtServiceIpRep         INTEGER,
    slbNewCfgEnhVirtServiceCdnProxy      INTEGER,
    slbNewCfgEnhVirtServiceStatus      	 INTEGER,
    slbNewCfgEnhVirtServiceRtSrcTnl      INTEGER
}

slbNewCfgEnhVirtServIndex OBJECT-TYPE
    SYNTAX  DisplayString (SIZE(1..255))
    MAX-ACCESS  read-only
    STATUS  current
    DESCRIPTION
        "The number of the virtual server."
    ::= { slbNewCfgEnhVirtServicesEntry 1 }

slbNewCfgEnhVirtServiceIndex OBJECT-TYPE
    SYNTAX  Integer32 (1..8)
    MAX-ACCESS  read-only
    STATUS  current
    DESCRIPTION
        "The service index. This has no external meaning"
    ::= { slbNewCfgEnhVirtServicesEntry 2 }

slbNewCfgEnhVirtServiceVirtPort OBJECT-TYPE
    SYNTAX  INTEGER (1..65534)
    MAX-ACCESS  read-create
    STATUS  current
    DESCRIPTION
        "The layer4 virtual port number of the service. it can be either 1 for ip or between 9 to 65534, virt port no. 2 to 9 are invalid"
    ::= { slbNewCfgEnhVirtServicesEntry 3 }

slbNewCfgEnhVirtServiceRealPort OBJECT-TYPE
    SYNTAX  INTEGER (0..65534)
    MAX-ACCESS  read-create
    STATUS  current
    DESCRIPTION
        "The layer4 real port number of the service, it can be either 0 for multiple real ports or 1 for ip service or between 5 to 65534. (2 to 5 are invalid)"
    ::= { slbNewCfgEnhVirtServicesEntry 4 }

slbNewCfgEnhVirtServiceUDPBalance OBJECT-TYPE
    SYNTAX  INTEGER {
        udp(2),
        tcp(3),
        stateless(4),
        tcpAndUdp(5),
        sctp(6),
        unsupported(2147483647)
        }
    MAX-ACCESS  read-create
    STATUS  current
    DESCRIPTION
        "Set protocol for the virtual service to
         UDP or TCP or SCTP or tcpAndUdp or stateless.
         tcpAndUdp is applicable only to ip service."
    ::= { slbNewCfgEnhVirtServicesEntry 5 }

slbNewCfgEnhVirtServiceBwmContract OBJECT-TYPE
    SYNTAX  Integer32
    MAX-ACCESS  read-create
    STATUS  current
    DESCRIPTION
        "The BWM contract number for this service."
    ::= { slbNewCfgEnhVirtServicesEntry 6 }

slbNewCfgEnhVirtServiceDirServerRtn OBJECT-TYPE
    SYNTAX  INTEGER {
        enabled(1),
        disabled(2),
        unsupported(2147483647)
        }
    MAX-ACCESS  read-create
    STATUS  current
    DESCRIPTION
        "Enable or disable direct server return feature. To translate only
         MAC addresses in performing server load balancing when enabled.
         This allow servers to return directly to client since IP addresses
         have not been changed."
    ::= { slbNewCfgEnhVirtServicesEntry 7 }

slbNewCfgEnhVirtServiceRtspUrlParse OBJECT-TYPE
    SYNTAX  INTEGER {
        none(1),
        l4hash(2),
        hash(3),
        patternMatch(4),
        unsupported(2147483647)
        }
    MAX-ACCESS  read-create
    STATUS  current
    DESCRIPTION
        "Select RTSP URL load balancing type."
    ::= { slbNewCfgEnhVirtServicesEntry 8 }

slbNewCfgEnhVirtServiceDBind OBJECT-TYPE
    SYNTAX  INTEGER {
        enabled(1),
        disabled(2),
        forceproxy(3),
        unsupported(2147483647)
        }
    MAX-ACCESS  read-create
    STATUS  current
    DESCRIPTION
        "Enable/disable/forceproxy delayed binding."
    ::= { slbNewCfgEnhVirtServicesEntry 9 }


slbNewCfgEnhVirtServiceFtpParsing OBJECT-TYPE
    SYNTAX  INTEGER {
        enabled(1),
        disabled(2),
        unsupported(2147483647)
        }
    MAX-ACCESS  read-create
    STATUS  current
    DESCRIPTION
        "Enable or Disable the ftp parsing for the virtual service."
    ::= { slbNewCfgEnhVirtServicesEntry 10 }

slbNewCfgEnhVirtServiceRemapUDPFrags OBJECT-TYPE
    SYNTAX INTEGER {
        enabled(1),
        disabled(2),
        unsupported(2147483647)
        }
    MAX-ACCESS read-create
    STATUS current
    DESCRIPTION
        "Enable or disable remapping UDP server fragments"
    ::= { slbNewCfgEnhVirtServicesEntry 11 }
slbNewCfgEnhVirtServiceDnsSlb OBJECT-TYPE
    SYNTAX  INTEGER {
        enabled(1),
        disabled(2),
        unsupported(2147483647)
        }
    MAX-ACCESS  read-create
    STATUS  current
    DESCRIPTION
        "Enable or disable DNS query load balancing."
    ::= { slbNewCfgEnhVirtServicesEntry 12 }

slbNewCfgEnhVirtServiceResponseCount OBJECT-TYPE
    SYNTAX  INTEGER (1..16)
    MAX-ACCESS  read-create
    STATUS  current
    DESCRIPTION
        "The number of cookie search response count."
    ::= { slbNewCfgEnhVirtServicesEntry 13 }

slbNewCfgEnhVirtServicePBind OBJECT-TYPE
    SYNTAX  INTEGER {
        clientip(2),
        disabled(3),
        sslid(4),
        cookie(5),
        unsupported(2147483647)
        }
    MAX-ACCESS  read-create
    STATUS  current
    DESCRIPTION
        "Enable or disable persistent bindings for the virtual port."
    ::= { slbNewCfgEnhVirtServicesEntry 14 }

slbNewCfgEnhVirtServiceCoffset OBJECT-TYPE
    SYNTAX  INTEGER (1..64)
    MAX-ACCESS  read-create
    STATUS  current
    DESCRIPTION
        "The starting byte offset of the cookie value."
    ::= { slbNewCfgEnhVirtServicesEntry 15 }

slbNewCfgEnhVirtServiceClength OBJECT-TYPE
    SYNTAX  INTEGER (1..64)
    MAX-ACCESS  read-create
    STATUS  current
    DESCRIPTION
        "The number of bytes to extract from the cookie value."
    ::= { slbNewCfgEnhVirtServicesEntry 16 }

slbNewCfgEnhVirtServiceUriCookie OBJECT-TYPE
    SYNTAX  INTEGER {
        enabled(1),
        disabled(2),
        unsupported(2147483647)
        }
    MAX-ACCESS  read-create
    STATUS  current
    DESCRIPTION
        "Enable or disable cookie search in URI"
    ::= { slbNewCfgEnhVirtServicesEntry 17 }

slbNewCfgEnhVirtServiceCookieMode OBJECT-TYPE
    SYNTAX INTEGER {
        rewrite(1),
        passive(2),
        insert(3),
        unsupported(2147483647)
        }
    MAX-ACCESS read-create
    STATUS current
    DESCRIPTION
        "Select cookie persistence mode. Mode disabled(4) not supported on Alteon"
    ::= { slbNewCfgEnhVirtServicesEntry 18 }

slbNewCfgEnhVirtServiceHttpSlb OBJECT-TYPE
    SYNTAX  INTEGER {
        disabled(1),
        urlslb(2),
        urlhash(3),
        cookie(4),
        host(5),
        browser(6),
        others(7),
        headerhash(8),
        version(9),
        unsupported(2147483647)
        }
    MAX-ACCESS  read-create
    STATUS  current
    DESCRIPTION
        "Select HTTP server loadbalancing for the virtual port."
    ::= { slbNewCfgEnhVirtServicesEntry 19 }

slbNewCfgEnhVirtServiceHttpSlbOption OBJECT-TYPE
    SYNTAX  INTEGER {
        and(1),
        or(2),
        none(3),
        unsupported(2147483647)
        }
    MAX-ACCESS  read-create
    STATUS  current
    DESCRIPTION
        "Select HTTP server loadbalancing for the virtual port."
    ::= { slbNewCfgEnhVirtServicesEntry 20 }

slbNewCfgEnhVirtServiceHttpSlb2 OBJECT-TYPE
    SYNTAX  INTEGER {
        disabled(1),
        urlslb(2),
        urlhash(3),
        cookie(4),
        host(5),
        browser(6),
        others(7),
        headerhash(8),
        version(9),
        unsupported(2147483647)
        }
    MAX-ACCESS  read-create
    STATUS  current
    DESCRIPTION
        "Select HTTP server loadbalancing for the virtual port."
    ::= { slbNewCfgEnhVirtServicesEntry 21 }


slbNewCfgEnhVirtServiceDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."

    ::= { slbNewCfgEnhVirtServicesEntry 22 }

slbNewCfgEnhVirtServiceApm OBJECT-TYPE
    SYNTAX  INTEGER {
        enabled(1),
        disabled(2),
        unsupported(2147483647)
        }
    MAX-ACCESS  read-create
    STATUS  obsolete
    DESCRIPTION
        "Enable/disable apm."
    ::= { slbNewCfgEnhVirtServicesEntry 23 }
slbNewCfgEnhVirtServiceNonHTTP OBJECT-TYPE
    SYNTAX  INTEGER {
        enabled(1),
        disabled(2),
        unsupported(2147483647)
        }
    MAX-ACCESS  read-create
    STATUS  current
    DESCRIPTION
        "Enable/Disable to send non-HTTP traffic."
    ::= { slbNewCfgEnhVirtServicesEntry 24 }

slbNewCfgEnhVirtServiceIpRep OBJECT-TYPE
    SYNTAX  INTEGER {
        enabled(1),
        disabled(2),
        unsupported(2147483647)
        }
    MAX-ACCESS  read-create
    STATUS  current
    DESCRIPTION
        "Enable/Disable IP reputation."
    ::= { slbNewCfgEnhVirtServicesEntry 25 }

slbNewCfgEnhVirtServiceCdnProxy OBJECT-TYPE
    SYNTAX  INTEGER {
        enabled(1),
        disabled(2),
        unsupported(2147483647)
        }
    MAX-ACCESS  read-create
    STATUS  current
    DESCRIPTION
        "Enable/Disable CDN proxy."
    ::= { slbNewCfgEnhVirtServicesEntry 26 }

slbNewCfgEnhVirtServiceStatus    OBJECT-TYPE
    SYNTAX  INTEGER {
        up(1),
        down(2),
        adminDown(3),
        warning(4),
        shutdown(5),
        error(6),
        unsupported(2147483647)
        }
    MAX-ACCESS  read-create
    STATUS  current
    DESCRIPTION
    "The service status: up, down, admin down, warning, shutdown, error."
    ::= { slbNewCfgEnhVirtServicesEntry 27 }

slbNewCfgEnhVirtServiceRtSrcTnl  OBJECT-TYPE
    SYNTAX  INTEGER {
        enabled(1),
        disabled(2),
        unsupported(2147483647)
        }
    MAX-ACCESS  read-create
    STATUS  current
    DESCRIPTION
        "Enable/Disable Return to Source Tunnel."
    ::= { slbNewCfgEnhVirtServicesEntry 28 }

slbNewCfgEnhVirtServicesSecondPartTable OBJECT-TYPE
    SYNTAX  SEQUENCE OF SlbNewCfgEnhVirtServicesSecondPartEntry
    MAX-ACCESS  not-accessible
    STATUS  current
    DESCRIPTION
        "The table of virtual Services.
         Note:This mib is not supported for VX instance of Virtualization."
    ::= { virtualServerCfg 30 }

slbNewCfgEnhVirtServicesSecondPartEntry OBJECT-TYPE
    SYNTAX  SlbNewCfgEnhVirtServicesSecondPartEntry
    MAX-ACCESS  not-accessible
    STATUS  current
    DESCRIPTION
        "A row in the virtual services table."
    INDEX   { slbNewCfgEnhVirtServSecondPartIndex, slbNewCfgEnhVirtServiceSecondPartIndex }
    ::= { slbNewCfgEnhVirtServicesSecondPartTable 1 }

SlbNewCfgEnhVirtServicesSecondPartEntry ::= SEQUENCE {
    slbNewCfgEnhVirtServSecondPartIndex            DisplayString,
    slbNewCfgEnhVirtServiceSecondPartIndex         Integer32,

    slbNewCfgEnhVirtServiceConnmgtStatus  INTEGER,
    slbNewCfgEnhVirtServiceConnmgtTimeout INTEGER,
    slbNewCfgEnhVirtServiceCachepol      DisplayString,
    slbNewCfgEnhVirtServiceComppol       DisplayString,
    slbNewCfgEnhVirtServiceSSLpol        DisplayString,
    slbNewCfgEnhVirtServiceServCert      DisplayString,
    slbNewCfgEnhVirtServiceHttpmodList   DisplayString,
    slbNewCfgEnhVirtServiceCloaksrv      INTEGER,

    slbNewCfgEnhVirtServErrcodeStatus    INTEGER,
    slbNewCfgEnhVirtServErrcodeMatch     DisplayString,
    slbNewCfgEnhVirtServErrcodeHttpRedir INTEGER,
    slbNewCfgEnhVirtServErrcodeUrl       DisplayString,
    slbNewCfgEnhVirtServErrcode          DisplayString,
    slbNewCfgEnhVirtServErrcodeNew       DisplayString,
    slbNewCfgEnhVirtServErrcodeReason    DisplayString,
    slbNewCfgEnhVirtServUrlchangStatus     INTEGER,
    slbNewCfgEnhVirtServUrlchangHostType   INTEGER,
    slbNewCfgEnhVirtServiceFeTcpPolId    DisplayString,
    slbNewCfgEnhVirtServiceBeTcpPolId    DisplayString,
    slbNewCfgEnhVirtServiceBasicConnmgtStatus  INTEGER
}

slbNewCfgEnhVirtServSecondPartIndex OBJECT-TYPE
    SYNTAX  DisplayString (SIZE(1..255))
    MAX-ACCESS  read-only
    STATUS  current
    DESCRIPTION
        "The number of the virtual server."
    ::= { slbNewCfgEnhVirtServicesSecondPartEntry 1 }

slbNewCfgEnhVirtServiceSecondPartIndex OBJECT-TYPE
    SYNTAX  Integer32
    MAX-ACCESS  read-only
    STATUS  current
    DESCRIPTION
        "The service index. This has no external meaning"
    ::= { slbNewCfgEnhVirtServicesSecondPartEntry 2 }


slbNewCfgEnhVirtServiceConnmgtStatus OBJECT-TYPE
    SYNTAX  INTEGER {
        disabled(0),
        pooling(1),
        muxenabled(2),
        h2(3),
        unsupported(2147483647)
        }
    MAX-ACCESS  read-create
    STATUS  current
    DESCRIPTION
        "Connection management configuration for HTTP traffic(Enable/disable/pooling) [Default: Disable]."
    ::= { slbNewCfgEnhVirtServicesSecondPartEntry 3 }

slbNewCfgEnhVirtServiceConnmgtTimeout OBJECT-TYPE
    SYNTAX  INTEGER (0..32768)
    MAX-ACCESS  read-create
    STATUS  current
    DESCRIPTION
        "Connection management server side connection idle timeout in minutes [0-32768] [Default: 10]."
    ::= { slbNewCfgEnhVirtServicesSecondPartEntry 4 }

slbNewCfgEnhVirtServiceCachepol OBJECT-TYPE
    SYNTAX  DisplayString  (SIZE(0..32))
    MAX-ACCESS  read-create
    STATUS  current
    DESCRIPTION
        "Cache policy name associated with this virtual service.Set none to delete entry"
    ::= { slbNewCfgEnhVirtServicesSecondPartEntry 5 }

slbNewCfgEnhVirtServiceComppol OBJECT-TYPE
    SYNTAX  DisplayString  (SIZE(0..32))
    MAX-ACCESS  read-create
    STATUS  current
    DESCRIPTION
        "Compression policy name associated with this virtual service.Set none to delete entry"
    ::= { slbNewCfgEnhVirtServicesSecondPartEntry 6 }

slbNewCfgEnhVirtServiceSSLpol OBJECT-TYPE
    SYNTAX  DisplayString  (SIZE(0..32))
    MAX-ACCESS  read-create
    STATUS  current
    DESCRIPTION
        "SSL policy name associated with this virtual service.Set none to delete entry"
    ::= { slbNewCfgEnhVirtServicesSecondPartEntry 7 }

slbNewCfgEnhVirtServiceServCert OBJECT-TYPE
    SYNTAX  DisplayString  (SIZE(0..128))
    MAX-ACCESS  read-create
    STATUS  current
    DESCRIPTION
        "Server Certificate name associated with this virtual service."
    ::= { slbNewCfgEnhVirtServicesSecondPartEntry 8 }

slbNewCfgEnhVirtServiceHttpmodList OBJECT-TYPE
    SYNTAX  DisplayString  (SIZE(0..32))
    MAX-ACCESS  read-create
    STATUS  current
    DESCRIPTION
        "HTTP Content Modifications Rule-list associated with this virtual service.Set none to delete entry"
    ::= { slbNewCfgEnhVirtServicesSecondPartEntry 9 }

slbNewCfgEnhVirtServiceCloaksrv OBJECT-TYPE
    SYNTAX  INTEGER {
        enabled(1),
        disabled(2),
        unsupported(2147483647)
        }
    MAX-ACCESS  read-create
    STATUS  current
    DESCRIPTION
        "Enable/disable server cloaking."
    ::= { slbNewCfgEnhVirtServicesSecondPartEntry 10 }

slbNewCfgEnhVirtServErrcodeStatus OBJECT-TYPE
    SYNTAX  INTEGER {
        enabled(1),
        disabled(2),
        clear(3),
        unsupported(2147483647)
        }
    MAX-ACCESS  read-create
    STATUS  current
    DESCRIPTION
        "Enable/disable/clear error-code configuration."
    ::= { slbNewCfgEnhVirtServicesSecondPartEntry 11 }

slbNewCfgEnhVirtServErrcodeMatch OBJECT-TYPE
    SYNTAX  DisplayString (SIZE (0..64))
    MAX-ACCESS  read-create
    STATUS  current
    DESCRIPTION
        "Match error-code(s), e.g 203,204 ."
    ::= { slbNewCfgEnhVirtServicesSecondPartEntry 12 }
slbNewCfgEnhVirtServErrcodeHttpRedir OBJECT-TYPE
    SYNTAX  INTEGER {
        yes(1),
        no(2),
        unsupported(2147483647)
    }
    MAX-ACCESS  read-create
    STATUS  current
    DESCRIPTION
        "Use http redirection [yes/no] [Default: yes]."
    ::= { slbNewCfgEnhVirtServicesSecondPartEntry 13 }

slbNewCfgEnhVirtServErrcodeUrl OBJECT-TYPE
    SYNTAX  DisplayString (SIZE(0..240))
    MAX-ACCESS  read-create
    STATUS  current
    DESCRIPTION
        "URL for redirection."
    ::= { slbNewCfgEnhVirtServicesSecondPartEntry 14 }


slbNewCfgEnhVirtServErrcode OBJECT-TYPE
    SYNTAX  DisplayString (SIZE(0..3))
    MAX-ACCESS  read-create
    STATUS  current
    DESCRIPTION
        "set error code [Default: 302]."
    ::= { slbNewCfgEnhVirtServicesSecondPartEntry 15 }

slbNewCfgEnhVirtServErrcodeNew OBJECT-TYPE
    SYNTAX  DisplayString (SIZE(0..3)) 
    MAX-ACCESS  read-create
    STATUS  current
    DESCRIPTION
        "Enter new error code [Default: 302]."
    ::= { slbNewCfgEnhVirtServicesSecondPartEntry 16 }

slbNewCfgEnhVirtServErrcodeReason OBJECT-TYPE
    SYNTAX  DisplayString (SIZE(0..128))
    MAX-ACCESS  read-create
    STATUS  current
    DESCRIPTION
        "Enter error reason."
    ::= { slbNewCfgEnhVirtServicesSecondPartEntry 17 }

slbNewCfgEnhVirtServUrlchangStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgEnhVirtServicesSecondPartEntry 18 }

slbNewCfgEnhVirtServUrlchangHostType OBJECT-TYPE
    SYNTAX  INTEGER {
        sufx(1),
        prefx(2),
        eq(3),
        incl(4),
        any(5),
        unsupported(2147483647)
    }
    MAX-ACCESS  read-create
    STATUS  current
    DESCRIPTION
        "Enter hostname match type [sufx|prefx|eq|incl|any] [Default: any]"
    ::= { slbNewCfgEnhVirtServicesSecondPartEntry 19 }

slbNewCfgEnhVirtServiceFeTcpPolId  OBJECT-TYPE   
    SYNTAX  DisplayString  (SIZE(0..32))
    MAX-ACCESS  read-create
    STATUS  current   
    DESCRIPTION 
        "Frontend TCP optimization policy."
    ::= { slbNewCfgEnhVirtServicesSecondPartEntry 20 }

slbNewCfgEnhVirtServiceBeTcpPolId OBJECT-TYPE   
    SYNTAX  DisplayString  (SIZE(0..32))
    MAX-ACCESS  read-create
    STATUS  current   
    DESCRIPTION 
        "Backend TCP optimization policy."
    ::= { slbNewCfgEnhVirtServicesSecondPartEntry 21 }

slbNewCfgEnhVirtServiceBasicConnmgtStatus OBJECT-TYPE
    SYNTAX  INTEGER {
        disabled(0),
        muxenabled(2),
        unsupported(2147483647)
        }
    MAX-ACCESS  read-create
    STATUS  current
    DESCRIPTION
        "Connection management configuration for Tcp traffic(Enable/disable) [Default: Disable]."
    ::= { slbNewCfgEnhVirtServicesSecondPartEntry 22 }


slbNewCfgEnhVirtServicesThirdPartTable OBJECT-TYPE
    SYNTAX  SEQUENCE OF SlbNewCfgEnhVirtServicesThirdPartEntry
    MAX-ACCESS  not-accessible
    STATUS  current
    DESCRIPTION
        "The table of virtual Services.
         Note:This mib is not supported for VX instance of Virtualization."
    ::= { virtualServerCfg 31 }

slbNewCfgEnhVirtServicesThirdPartEntry OBJECT-TYPE
    SYNTAX  SlbNewCfgEnhVirtServicesThirdPartEntry
    MAX-ACCESS  not-accessible
    STATUS  current
    DESCRIPTION
        "A row in the virtual services table."
    INDEX   { slbNewCfgEnhVirtServThirdPartIndex, slbNewCfgEnhVirtServiceThirdPartIndex }
    ::= { slbNewCfgEnhVirtServicesThirdPartTable 1 }

SlbNewCfgEnhVirtServicesThirdPartEntry ::= SEQUENCE {
    slbNewCfgEnhVirtServThirdPartIndex            DisplayString,
    slbNewCfgEnhVirtServiceThirdPartIndex         Integer32,

    slbNewCfgEnhVirtServUrlchangHostName   DisplayString,
    slbNewCfgEnhVirtServUrlchangPathType   INTEGER,
    slbNewCfgEnhVirtServUrlchangPathMatch  DisplayString,
    slbNewCfgEnhVirtServUrlchangPageName   DisplayString,
    slbNewCfgEnhVirtServUrlchangPageType   DisplayString,
    slbNewCfgEnhVirtServUrlchangActnType   INTEGER,
    slbNewCfgEnhVirtServUrlchangPathInsrt  DisplayString,
    slbNewCfgEnhVirtServUrlchangInsrtPostn INTEGER
}


slbNewCfgEnhVirtServThirdPartIndex OBJECT-TYPE
    SYNTAX  DisplayString (SIZE(1..255))
    MAX-ACCESS  read-only
    STATUS  current
    DESCRIPTION
        "The number of the virtual server."
    ::= { slbNewCfgEnhVirtServicesThirdPartEntry 1 }

slbNewCfgEnhVirtServiceThirdPartIndex OBJECT-TYPE
    SYNTAX  Integer32
    MAX-ACCESS  read-only
    STATUS  current
    DESCRIPTION
        "The service index. This has no external meaning"
    ::= { slbNewCfgEnhVirtServicesThirdPartEntry 2 }

slbNewCfgEnhVirtServUrlchangHostName OBJECT-TYPE
    SYNTAX  DisplayString (SIZE(0..250))
    MAX-ACCESS  read-create
    STATUS  current
    DESCRIPTION
        "Enter hostname to match."
    ::= { slbNewCfgEnhVirtServicesThirdPartEntry 3 }

slbNewCfgEnhVirtServUrlchangPathType OBJECT-TYPE
    SYNTAX  INTEGER {
        sufx(1),
        prefx(2),
        eq(3),
        incl(4),
        any(5),
        none(6),
        unsupported(2147483647)
    }
    MAX-ACCESS  read-create
    STATUS  current
    DESCRIPTION
        "Enter path match type [sufx|prefx|eq|incl|any|none]."
    ::= { slbNewCfgEnhVirtServicesThirdPartEntry 4 }

slbNewCfgEnhVirtServUrlchangPathMatch OBJECT-TYPE
    SYNTAX  DisplayString (SIZE(0..250))
    MAX-ACCESS  read-create
    STATUS  current
    DESCRIPTION
        "Enter path to match."
    ::= { slbNewCfgEnhVirtServicesThirdPartEntry 5 }

slbNewCfgEnhVirtServUrlchangPageName OBJECT-TYPE
    SYNTAX  DisplayString (SIZE(0..64))
    MAX-ACCESS  read-create
    STATUS  current
    DESCRIPTION
        "Enter page name to match or none."
    ::= { slbNewCfgEnhVirtServicesThirdPartEntry 6 }

slbNewCfgEnhVirtServUrlchangPageType OBJECT-TYPE
    SYNTAX  DisplayString (SIZE(0..64))
    MAX-ACCESS  read-create
    STATUS  current
    DESCRIPTION
        "Enter page type to match or none."
    ::= { slbNewCfgEnhVirtServicesThirdPartEntry 7 }

slbNewCfgEnhVirtServUrlchangActnType OBJECT-TYPE
    SYNTAX  INTEGER {
        insert(1),
        replace(2),
        remove(3),
        none(4),
        unsupported(2147483647)
    }
    MAX-ACCESS  read-create
    STATUS  current
    DESCRIPTION
        "Enter path action type."
    ::= { slbNewCfgEnhVirtServicesThirdPartEntry 8 }

slbNewCfgEnhVirtServUrlchangPathInsrt OBJECT-TYPE
    SYNTAX  DisplayString (SIZE(0..250))
    MAX-ACCESS  read-create
    STATUS  current
    DESCRIPTION
        "Enter path to insert."
    ::= { slbNewCfgEnhVirtServicesThirdPartEntry 9 }


slbNewCfgEnhVirtServUrlchangInsrtPostn OBJECT-TYPE
    SYNTAX  INTEGER {
        before(1),
        after(2),
        unsupported(2147483647)
    }
    MAX-ACCESS  read-create
    STATUS  current
    DESCRIPTION
        "Insert the specified path before or after the matched section"
    ::= { slbNewCfgEnhVirtServicesThirdPartEntry 10 }



slbNewCfgEnhVirtServicesFourthPartTable OBJECT-TYPE
    SYNTAX  SEQUENCE OF SlbNewCfgEnhVirtServicesFourthPartEntry
    MAX-ACCESS  not-accessible
    STATUS  current
    DESCRIPTION
        "The table of virtual Services.
         Note:This mib is not supported for VX instance of Virtualization."
    ::= { virtualServerCfg 32 }

slbNewCfgEnhVirtServicesFourthPartEntry OBJECT-TYPE
    SYNTAX  SlbNewCfgEnhVirtServicesFourthPartEntry
    MAX-ACCESS  not-accessible
    STATUS  current
    DESCRIPTION
        "A row in the virtual services table."
    INDEX   { slbNewCfgEnhVirtServFourthPartIndex, slbNewCfgEnhVirtServiceFourthPartIndex }
    ::= { slbNewCfgEnhVirtServicesFourthPartTable 1 }

SlbNewCfgEnhVirtServicesFourthPartEntry ::= SEQUENCE {
    slbNewCfgEnhVirtServFourthPartIndex            DisplayString,
    slbNewCfgEnhVirtServiceFourthPartIndex         Integer32,

    slbNewCfgEnhVirtServUrlchangNewPgName  DisplayString,
    slbNewCfgEnhVirtServUrlchangNewPgType  DisplayString,

    slbNewCfgEnhVirtServPathHideStatus     INTEGER,
    slbNewCfgEnhVirtServPathHideHostType   INTEGER,
    slbNewCfgEnhVirtServPathHideHostName   DisplayString,
    slbNewCfgEnhVirtServPathHidePathType   INTEGER,
    slbNewCfgEnhVirtServPathHidePathName   DisplayString,

    slbNewCfgEnhVirtServTextrepStatus      INTEGER,
    slbNewCfgEnhVirtServTextrepAction      INTEGER
}

slbNewCfgEnhVirtServFourthPartIndex OBJECT-TYPE
    SYNTAX  DisplayString (SIZE(1..255))
    MAX-ACCESS  read-only
    STATUS  current
    DESCRIPTION
        "The number of the virtual server."
    ::= { slbNewCfgEnhVirtServicesFourthPartEntry 1 }

slbNewCfgEnhVirtServiceFourthPartIndex OBJECT-TYPE
    SYNTAX  Integer32
    MAX-ACCESS  read-only
    STATUS  current
    DESCRIPTION
        "The service index. This has no external meaning"
    ::= { slbNewCfgEnhVirtServicesFourthPartEntry 2 }

slbNewCfgEnhVirtServUrlchangNewPgName OBJECT-TYPE
    SYNTAX  DisplayString (SIZE(0..64))
    MAX-ACCESS  read-create
    STATUS  current
    DESCRIPTION
        "Enter new page name or none."
    ::= { slbNewCfgEnhVirtServicesFourthPartEntry 3 }

slbNewCfgEnhVirtServUrlchangNewPgType OBJECT-TYPE
    SYNTAX  DisplayString (SIZE(0..64))
    MAX-ACCESS  read-create
    STATUS  current
    DESCRIPTION
        "Enter new page type or none."
    ::= { slbNewCfgEnhVirtServicesFourthPartEntry 4 }

slbNewCfgEnhVirtServPathHideStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgEnhVirtServicesFourthPartEntry 5 }

slbNewCfgEnhVirtServPathHideHostType OBJECT-TYPE
    SYNTAX  INTEGER {
        sufx(1),
        prefx(2),
        eq(3),
        incl(4),
        any(5),
        unsupported(2147483647)
    }
    MAX-ACCESS  read-create
    STATUS  current
    DESCRIPTION
        "Enter hostname type [sufx|prefx|eq|incl|any] [Default: any]."
    ::= { slbNewCfgEnhVirtServicesFourthPartEntry 6 }

slbNewCfgEnhVirtServPathHideHostName OBJECT-TYPE
    SYNTAX  DisplayString (SIZE(0..250))
    MAX-ACCESS  read-create
    STATUS  current
    DESCRIPTION
        "Enter hostname to match."
    ::= { slbNewCfgEnhVirtServicesFourthPartEntry 7 }

slbNewCfgEnhVirtServPathHidePathType OBJECT-TYPE
    SYNTAX  INTEGER {
        sufx(1),
        prefx(2),
        eq(3),
        none(4),
        unsupported(2147483647)
    }
    MAX-ACCESS  read-create
    STATUS  current
    DESCRIPTION
        "Enter path match type [sufx|prefx|eq|none]."
    ::= { slbNewCfgEnhVirtServicesFourthPartEntry 8 }

slbNewCfgEnhVirtServPathHidePathName OBJECT-TYPE
    SYNTAX  DisplayString (SIZE(0..250))
    MAX-ACCESS  read-create
    STATUS  current
    DESCRIPTION
        "Enter path to remove."
    ::= { slbNewCfgEnhVirtServicesFourthPartEntry 9 }

slbNewCfgEnhVirtServTextrepStatus OBJECT-TYPE
    SYNTAX  INTEGER {
        enable(1),
        disable(2),
        clear(3),
        unsupported(2147483647)
    }
    MAX-ACCESS  read-create
    STATUS  current
    DESCRIPTION
        "Enter enabled/disabled/clear [Default: clear]."
    ::= { slbNewCfgEnhVirtServicesFourthPartEntry 10 }

slbNewCfgEnhVirtServTextrepAction OBJECT-TYPE
    SYNTAX  INTEGER {
        none(0),
        replace(1),
        remove(2),
        unsupported(2147483647)
    }
    MAX-ACCESS  read-create
    STATUS  current
    DESCRIPTION
        "Enter action [replace|remove|none]."
    ::= { slbNewCfgEnhVirtServicesFourthPartEntry 11 }

slbNewCfgEnhVirtServicesFifthPartTable OBJECT-TYPE
    SYNTAX  SEQUENCE OF SlbNewCfgEnhVirtServicesFifthPartEntry
    MAX-ACCESS  not-accessible
    STATUS  current
    DESCRIPTION
        "The table of virtual Services.
         Note:This mib is not supported for VX instance of Virtualization."
    ::= { virtualServerCfg 33 }

slbNewCfgEnhVirtServicesFifthPartEntry OBJECT-TYPE
    SYNTAX  SlbNewCfgEnhVirtServicesFifthPartEntry
    MAX-ACCESS  not-accessible
    STATUS  current
    DESCRIPTION
        "A row in the virtual services table."
    INDEX   { slbNewCfgEnhVirtServFifthPartIndex, slbNewCfgEnhVirtServiceFifthPartIndex }
    ::= { slbNewCfgEnhVirtServicesFifthPartTable 1 }

SlbNewCfgEnhVirtServicesFifthPartEntry ::= SEQUENCE {

    slbNewCfgEnhVirtServFifthPartIndex            DisplayString,
    slbNewCfgEnhVirtServiceFifthPartIndex         Integer32,

    slbNewCfgEnhVirtServTextrepMatchText   DisplayString,
    slbNewCfgEnhVirtServTextrepReplacTxt   DisplayString,

    slbNewCfgEnhVirtServApplicationType    INTEGER,
    slbNewCfgEnhVirtServiceName          DisplayString,
    slbNewCfgEnhVirtServiceAction        INTEGER,
    slbNewCfgEnhVirtServiceRedirect      DisplayString,

    slbNewCfgEnhVirtServiceServCertGrpMark INTEGER,
    slbNewCfgEnhVirtServiceDnsType         INTEGER,
    slbNewCfgEnhVirtServiceClntproxType    INTEGER,
    slbNewCfgEnhVirtServiceZerowinSize     INTEGER,
    slbNewCfgEnhVirtServiceCookiePath      DisplayString,
    slbNewCfgEnhVirtServiceCookieSecure    INTEGER,
    slbNewCfgEnhVirtServiceNoRtsp          INTEGER,
    slbNewCfgEnhVirtServiceCkRebind        INTEGER,
    slbNewCfgEnhVirtServiceParseLimit      INTEGER,
    slbNewCfgEnhVirtServiceParseLength     INTEGER,
    slbNewCfgEnhVirtServiceUriNorm         INTEGER,
    slbNewCfgEnhVirtServiceGranularity     INTEGER,
    slbNewCfgEnhVirtServiceSessLog         INTEGER,
    slbNewCfgEnhVirtServiceUdpAge          INTEGER,
    slbNewCfgEnhVirtServiceSessEntryMode   INTEGER,
    slbNewCfgEnhVirtServiceSecPol          DisplayString,
    slbNewCfgEnhVirtServiceAlwaysOn        INTEGER,
    slbNewCfgEnhVirtServiceSendRST         INTEGER,
    slbNewCfgEnhVirtServiceClsOnSlowage    INTEGER
}

slbNewCfgEnhVirtServFifthPartIndex OBJECT-TYPE
    SYNTAX  DisplayString (SIZE(1..255))
    MAX-ACCESS  read-only
    STATUS  current
    DESCRIPTION
        "The number of the virtual server."
    ::= { slbNewCfgEnhVirtServicesFifthPartEntry 1 }

slbNewCfgEnhVirtServiceFifthPartIndex OBJECT-TYPE
    SYNTAX  Integer32
    MAX-ACCESS  read-only
    STATUS  current
    DESCRIPTION
        "The service index. This has no external meaning"
    ::= { slbNewCfgEnhVirtServicesFifthPartEntry 2 }

slbNewCfgEnhVirtServTextrepMatchText OBJECT-TYPE
    SYNTAX  DisplayString (SIZE(0..128))
    MAX-ACCESS  read-create
    STATUS  current
    DESCRIPTION
        "Enter text to be replaced."
    ::= { slbNewCfgEnhVirtServicesFifthPartEntry 3 }

slbNewCfgEnhVirtServTextrepReplacTxt OBJECT-TYPE
    SYNTAX  DisplayString (SIZE(0..128))
    MAX-ACCESS  read-create
    STATUS  current
    DESCRIPTION
        "Enter new text."
    ::= { slbNewCfgEnhVirtServicesFifthPartEntry 4 }

slbNewCfgEnhVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12),
      smtp(13),
      pop3(14),
      ip(15),
      mh-sctp(16),
      unsupported(2147483647)
    }
    MAX-ACCESS  read-create
    STATUS  current
    DESCRIPTION
        "Application Type for virtual service."
    ::= { slbNewCfgEnhVirtServicesFifthPartEntry 5 }

slbNewCfgEnhVirtServiceName OBJECT-TYPE
    SYNTAX  DisplayString (SIZE(0..32))
    MAX-ACCESS  read-create
    STATUS  current
    DESCRIPTION
        "The name of the virtual service."
    ::= { slbNewCfgEnhVirtServicesFifthPartEntry 6 }

slbNewCfgEnhVirtServiceAction OBJECT-TYPE
    SYNTAX  INTEGER    {
    group(1),
    redirect(2),
    discard(3),
    unsupported(2147483647)
    }
    MAX-ACCESS  read-create
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbNewCfgEnhVirtServicesFifthPartEntry 7 }

slbNewCfgEnhVirtServiceRedirect OBJECT-TYPE
    SYNTAX  DisplayString  (SIZE(0..255))
    MAX-ACCESS  read-create
    STATUS  current
    DESCRIPTION
        "application redirection location.We need to provide this
         value When action type is set to redirect(2)."
    ::= { slbNewCfgEnhVirtServicesFifthPartEntry 8 }

slbNewCfgEnhVirtServiceServCertGrpMark OBJECT-TYPE
    SYNTAX  INTEGER    {
    cert(1),
    group(2),
    unsupported(2147483647)
    }
    MAX-ACCESS  read-create
    STATUS  current
    DESCRIPTION
        "Group Mark for Server Certificate. If we set value as cert(0)
         It will denote that the server certificate (name) associated with
         this virtual service, represents a certificate. Otherwise, a value of group(1), denotes that the server
         certificate (name) represents a group."
    ::= { slbNewCfgEnhVirtServicesFifthPartEntry 9}

slbNewCfgEnhVirtServiceDnsType OBJECT-TYPE
    SYNTAX  INTEGER {
        dns(1),
        dnssec(2),
        both(3),
        unsupported(2147483647)
        }
    MAX-ACCESS  read-create
    STATUS  current
    DESCRIPTION
        "Set DNS type for this service (DNS, DNSSEC)."
    ::= { slbNewCfgEnhVirtServicesFifthPartEntry 10 }

slbNewCfgEnhVirtServiceClntproxType OBJECT-TYPE
    SYNTAX  INTEGER {
        none(1),
        http(2),
        https(3),
        unsupported(2147483647)
        }
    MAX-ACCESS  read-create
    STATUS  current
    DESCRIPTION
        "Set client proximity type for this service."
    ::= { slbNewCfgEnhVirtServicesFifthPartEntry 11 }

slbNewCfgEnhVirtServiceZerowinSize OBJECT-TYPE
    SYNTAX  INTEGER {
        enabled(1),
        disabled(2),
        unsupported(2147483647)
        }
    MAX-ACCESS  read-create
    STATUS  current
    DESCRIPTION
        "Enable or disable zero window size in SYN+ACK for this service."
    ::= { slbNewCfgEnhVirtServicesFifthPartEntry 12 }

slbNewCfgEnhVirtServiceCookiePath OBJECT-TYPE
    SYNTAX  DisplayString (SIZE(0..32))
    MAX-ACCESS  read-create
    STATUS  current
    DESCRIPTION
        "The cookie path name of the virtual server used for cookie load balance."
    ::= { slbNewCfgEnhVirtServicesFifthPartEntry 13 }

slbNewCfgEnhVirtServiceCookieSecure OBJECT-TYPE
    SYNTAX  INTEGER {
            no(1),
        yes(2),
        unsupported(2147483647)
        }
    MAX-ACCESS  read-create
    STATUS  current
    DESCRIPTION
        "Is cookie secure [yes/no] [Default: no]."
    ::= { slbNewCfgEnhVirtServicesFifthPartEntry 14 }

slbNewCfgEnhVirtServiceNoRtsp OBJECT-TYPE
    SYNTAX  INTEGER {
        enabled(1),
        disabled(2),
        unsupported(2147483647)
        }
    MAX-ACCESS  read-create
    STATUS  current
    DESCRIPTION
        "Enable or disable only rtsp SLB for this service."
    ::= { slbNewCfgEnhVirtServicesFifthPartEntry 15 }

slbNewCfgEnhVirtServiceCkRebind OBJECT-TYPE
    SYNTAX  INTEGER {
        enabled(1),
        disabled(2),
        unsupported(2147483647)
        }
    MAX-ACCESS  read-create
    STATUS  current
    DESCRIPTION
        "Enable or disable server rebalancing when cookie is absent.
        When enabled, server load balancing will happen
        for subsequent request comes without cookie."
    ::= { slbNewCfgEnhVirtServicesFifthPartEntry 16 }

slbNewCfgEnhVirtServiceParseLimit OBJECT-TYPE
    SYNTAX  INTEGER {
        enabled(1),
        disabled(2),
        unsupported(2147483647)
        }
    MAX-ACCESS  read-create
    STATUS  current
    DESCRIPTION
        "Enable or disable buffer limit for content based selection."
    ::= { slbNewCfgEnhVirtServicesFifthPartEntry 17 }

slbNewCfgEnhVirtServiceParseLength OBJECT-TYPE
    SYNTAX  INTEGER (0..18200)
    MAX-ACCESS  read-create
    STATUS  current
    DESCRIPTION
        "The buffer length for content based selection."
    ::= { slbNewCfgEnhVirtServicesFifthPartEntry 18 }

slbNewCfgEnhVirtServiceUriNorm OBJECT-TYPE
    SYNTAX  INTEGER {
        enabled(1),
        disabled(2),
        unsupported(2147483647)
        }
    MAX-ACCESS  read-create
    STATUS  current
    DESCRIPTION
        "Enable or disable URI normalization for HTTP content matching."
    ::= { slbNewCfgEnhVirtServicesFifthPartEntry 19 }

slbNewCfgEnhVirtServiceGranularity OBJECT-TYPE
    SYNTAX  INTEGER {
        service(0),
        real(2),
        unsupported(2147483647)
        }
    MAX-ACCESS  read-create
    STATUS  current
    DESCRIPTION
        "Sets the Granularity for this service, for statistics report-protocol information.
        Group(1) - for group level, or GroupAndServers(2) - for server level."
    ::= { slbNewCfgEnhVirtServicesFifthPartEntry 20 }

slbNewCfgEnhVirtServiceSessLog OBJECT-TYPE
    SYNTAX  INTEGER {
        enabled(1),
        disabled(2),
        unsupported(2147483647)
        }
    MAX-ACCESS  read-create
    STATUS  current
    DESCRIPTION
        "Enable or disable Session Logging."
    ::= { slbNewCfgEnhVirtServicesFifthPartEntry 21 }

slbNewCfgEnhVirtServiceUdpAge OBJECT-TYPE
    SYNTAX  INTEGER {
        enabled(1),
        disabled(2),
        unsupported(2147483647)
        }
    MAX-ACCESS  read-create
    STATUS  current
    DESCRIPTION
        "Fast aging of UDP sessions."
    ::= { slbNewCfgEnhVirtServicesFifthPartEntry 22 }

slbNewCfgEnhVirtServiceSessEntryMode OBJECT-TYPE
    SYNTAX  INTEGER {
        single(1),
        multiple(2),
        unsupported(2147483647)
        }
    MAX-ACCESS  read-create
    STATUS  current
    DESCRIPTION
        "Session entry mode."
    ::= { slbNewCfgEnhVirtServicesFifthPartEntry 23 }

slbNewCfgEnhVirtServiceSecPol OBJECT-TYPE
    SYNTAX  DisplayString  (SIZE(0..32))
    MAX-ACCESS  read-create
    STATUS  current
    DESCRIPTION
        "Security policy name associated with this virtual service. Set none to delete entry"
    ::= { slbNewCfgEnhVirtServicesFifthPartEntry 24 }

slbNewCfgEnhVirtServiceAlwaysOn OBJECT-TYPE
    SYNTAX  INTEGER {
        enabled(1),
        disabled(2),
        unsupported(2147483647)
        }
    MAX-ACCESS  read-create
    STATUS  current
    DESCRIPTION
        "service always on when AS++ script attached."
    ::= { slbNewCfgEnhVirtServicesFifthPartEntry 25 }

slbNewCfgEnhVirtServiceSendRST OBJECT-TYPE
    SYNTAX  INTEGER {
        reset(1),
        drop(2),
        unsupported(2147483647)
        }
    MAX-ACCESS  read-create
    STATUS  current
    DESCRIPTION
        "Enable/Disable sending reset when the service is down."
    ::= { slbNewCfgEnhVirtServicesFifthPartEntry 26 }

slbNewCfgEnhVirtServiceClsOnSlowage OBJECT-TYPE
    SYNTAX  INTEGER {
        none(1),
        client(2),
        server(3),
        both(4),
        unsupported(2147483647)
        }
    MAX-ACCESS  read-create
    STATUS  current
    DESCRIPTION
        "Set close connection on aging treatment."
    ::= { slbNewCfgEnhVirtServicesFifthPartEntry 27 }

slbNewCfgEnhVirtServicesSixthPartTable OBJECT-TYPE
    SYNTAX  SEQUENCE OF SlbNewCfgEnhVirtServicesSixthPartEntry
    MAX-ACCESS  not-accessible
    STATUS  current
    DESCRIPTION
        "The table of virtual Services.
         Note:This mib is not supported for VX instance of Virtualization."
    ::= { virtualServerCfg 42 }

slbNewCfgEnhVirtServicesSixthPartEntry OBJECT-TYPE
    SYNTAX  SlbNewCfgEnhVirtServicesSixthPartEntry
    MAX-ACCESS  not-accessible
    STATUS  current
    DESCRIPTION
        "A row in the virtual services table."
    INDEX   { slbNewCfgEnhVirtServSixthPartIndex, slbNewCfgEnhVirtServiceSixthPartIndex }
    ::= { slbNewCfgEnhVirtServicesSixthPartTable 1 }

SlbNewCfgEnhVirtServicesSixthPartEntry ::= SEQUENCE {

    slbNewCfgEnhVirtServSixthPartIndex            DisplayString,
    slbNewCfgEnhVirtServiceSixthPartIndex         Integer32,
    slbNewCfgEnhVirtServiceHname         DisplayString,
    slbNewCfgEnhVirtServiceCname         DisplayString,
    slbNewCfgEnhVirtServiceCExpire       DisplayString,
    slbNewCfgEnhVirtServiceUrlHashLen    INTEGER,
    slbNewCfgEnhVirtServiceDummyDelete        INTEGER,
    slbNewCfgEnhVirtServiceDirect        INTEGER,
    slbNewCfgEnhVirtServiceThash         INTEGER,
    slbNewCfgEnhVirtServiceLdapreset     INTEGER,
    slbNewCfgEnhVirtServiceLdapslb       INTEGER,
    slbNewCfgEnhVirtServiceSip           INTEGER,
    slbNewCfgEnhVirtServiceXForwardedFor INTEGER,
    slbNewCfgEnhVirtServiceHttpRedir     INTEGER,
    slbNewCfgEnhVirtServicePbindRport    INTEGER,
    slbNewCfgEnhVirtServiceEgressPip     INTEGER,
    slbNewCfgEnhVirtServiceCookieDname   INTEGER,
    slbNewCfgEnhVirtServiceWts           INTEGER,
    slbNewCfgEnhVirtServiceUhash         INTEGER,
    slbNewCfgEnhVirtServiceTimeOut       INTEGER,
    slbNewCfgEnhVirtServiceSdpNat        INTEGER

}
slbNewCfgEnhVirtServSixthPartIndex OBJECT-TYPE
    SYNTAX  DisplayString (SIZE(1..255))
    MAX-ACCESS  read-only
    STATUS  current
    DESCRIPTION
        "The number of the virtual server."
    ::= { slbNewCfgEnhVirtServicesSixthPartEntry 1 }

slbNewCfgEnhVirtServiceSixthPartIndex OBJECT-TYPE
    SYNTAX  Integer32
    MAX-ACCESS  read-only
    STATUS  current
    DESCRIPTION
        "The service index. This has no external meaning"
    ::= { slbNewCfgEnhVirtServicesSixthPartEntry 2 }

slbNewCfgEnhVirtServiceHname OBJECT-TYPE
    SYNTAX  DisplayString (SIZE(0..34))
    MAX-ACCESS  read-create
    STATUS  current
    DESCRIPTION
        "The host name of the virtual service."
    ::= { slbNewCfgEnhVirtServicesSixthPartEntry 3 }

slbNewCfgEnhVirtServiceCname OBJECT-TYPE
    SYNTAX  DisplayString (SIZE(0..20))
    MAX-ACCESS  read-create
    STATUS  current
    DESCRIPTION
        "The cookie name of the virtual server used for cookie load balance."
    ::= { slbNewCfgEnhVirtServicesSixthPartEntry 4 }

slbNewCfgEnhVirtServiceCExpire OBJECT-TYPE
    SYNTAX  DisplayString (SIZE(0..20))
    MAX-ACCESS  read-create
    STATUS  current
    DESCRIPTION
        "The cookie expire of the virtual server used for insert cookie load
         balance depending on the mode it has the following format
         <MM/dd/yy[@hh:mm]> absolute mode or <days[:hours[:minutes]]>
         for relative mode."
    ::= { slbNewCfgEnhVirtServicesSixthPartEntry 5 }

slbNewCfgEnhVirtServiceUrlHashLen OBJECT-TYPE
    SYNTAX  INTEGER (0..255)
    MAX-ACCESS  read-create
    STATUS  current
    DESCRIPTION
        "The number of bytes used to hash onto server, A zero means
         URL hashing disabled."
    ::= { slbNewCfgEnhVirtServicesSixthPartEntry 6}

slbNewCfgEnhVirtServiceDummyDelete OBJECT-TYPE
    SYNTAX  INTEGER {
        other(1),
        delete(2),
        unsupported(2147483647)
        }
    MAX-ACCESS  read-only
    STATUS  current
    DESCRIPTION
        "This mib is dummy,the main Delete mib is in slbNewCfgEnhVirtServicesTable
         When read, other(1) is returned." 
    ::= { slbNewCfgEnhVirtServicesSixthPartEntry 7 }

slbNewCfgEnhVirtServiceDirect OBJECT-TYPE
    SYNTAX  INTEGER {
        enabled(1),
        disabled(2),
        unsupported(2147483647)
        }
    MAX-ACCESS  read-create
    STATUS  current
    DESCRIPTION
        "Enable or disable DAM for this service."
    ::= { slbNewCfgEnhVirtServicesSixthPartEntry 8 }

slbNewCfgEnhVirtServiceThash OBJECT-TYPE
    SYNTAX  INTEGER {
        sip(1),
        sip-sport(2),
        unsupported(2147483647)
        }
    MAX-ACCESS  read-create
    STATUS  current
    DESCRIPTION
        "Set hash parameter."
    ::= { slbNewCfgEnhVirtServicesSixthPartEntry 9 }

slbNewCfgEnhVirtServiceLdapreset OBJECT-TYPE
    SYNTAX  INTEGER {
        enabled(1),
        disabled(2),
        unsupported(2147483647)
        }
    MAX-ACCESS  read-create
    STATUS  current
    DESCRIPTION
        "Enable or disable LDAP Server Reset"
    ::= { slbNewCfgEnhVirtServicesSixthPartEntry 10 }

slbNewCfgEnhVirtServiceLdapslb OBJECT-TYPE
    SYNTAX  INTEGER {
        enabled(1),
        disabled(2),
        unsupported(2147483647)
        }
    MAX-ACCESS  read-create
    STATUS  current
    DESCRIPTION
        "Enable or disable LDAP Server load balancing"
    ::= { slbNewCfgEnhVirtServicesSixthPartEntry 11 }

slbNewCfgEnhVirtServiceSip OBJECT-TYPE
    SYNTAX  INTEGER {
        enabled(1),
        disabled(2),
        unsupported(2147483647)
        }
    MAX-ACCESS  read-create
    STATUS  current
    DESCRIPTION
        "Enable/disable SIP load balancing."
    ::= { slbNewCfgEnhVirtServicesSixthPartEntry 12 }

slbNewCfgEnhVirtServiceXForwardedFor OBJECT-TYPE
    SYNTAX  INTEGER {
        enabled(1),
        disabled(2),
        unsupported(2147483647)
        }
    MAX-ACCESS  read-create
    STATUS  current
    DESCRIPTION
        "Enable/disable X-Forwarded-For for proxy mode."
    ::= { slbNewCfgEnhVirtServicesSixthPartEntry 13 }

slbNewCfgEnhVirtServiceHttpRedir OBJECT-TYPE
    SYNTAX  INTEGER {
        enabled(1),
        disabled(2),
        unsupported(2147483647)
        }
    MAX-ACCESS  read-create
    STATUS  current
    DESCRIPTION
        "Enable/disable HTTP/HTTPS redirect for GSLB."
    ::= { slbNewCfgEnhVirtServicesSixthPartEntry 14 }

slbNewCfgEnhVirtServicePbindRport OBJECT-TYPE
    SYNTAX  INTEGER {
        enabled(1),
        disabled(2),
        unsupported(2147483647)
        }
    MAX-ACCESS  read-create
    STATUS  current
    DESCRIPTION
        "Enable or disable use of rport in the session lookup for a persistent
         session."
    ::= { slbNewCfgEnhVirtServicesSixthPartEntry 15 }

slbNewCfgEnhVirtServiceEgressPip OBJECT-TYPE
    SYNTAX  INTEGER {
        enabled(1),
        disabled(2),
        unsupported(2147483647)
        }
    MAX-ACCESS  read-create
    STATUS  current
    DESCRIPTION
        "Enable/disable pip selection based on egress port/vlan."
    ::= { slbNewCfgEnhVirtServicesSixthPartEntry 16 }

slbNewCfgEnhVirtServiceCookieDname OBJECT-TYPE
    SYNTAX INTEGER {
        enabled(1),
        disabled(2),
        unsupported(2147483647)
        }
    MAX-ACCESS read-create
    STATUS current
    DESCRIPTION
        "Select dname for insert cookie persistence mode."
    ::= { slbNewCfgEnhVirtServicesSixthPartEntry 17 }

slbNewCfgEnhVirtServiceWts OBJECT-TYPE
    SYNTAX INTEGER {
        enabled(1),
        disabled(2),
        unsupported(2147483647)
        }
    MAX-ACCESS read-create
    STATUS current
    DESCRIPTION
        "Enable or disable WTS loadbalancing and persistence."
    ::= { slbNewCfgEnhVirtServicesSixthPartEntry 18 }

slbNewCfgEnhVirtServiceUhash OBJECT-TYPE
    SYNTAX INTEGER {
        enabled(1),
        disabled(2),
        unsupported(2147483647)
        }
    MAX-ACCESS read-create
    STATUS current
    DESCRIPTION
        "Enable when there is no Session Directory server."
    ::= { slbNewCfgEnhVirtServicesSixthPartEntry 19 }

slbNewCfgEnhVirtServiceTimeOut OBJECT-TYPE
    SYNTAX  INTEGER (0..32768)
    MAX-ACCESS  read-create
    STATUS  current
    DESCRIPTION
        "The maximum number of minutes an inactive connection remains open."
    ::= { slbNewCfgEnhVirtServicesSixthPartEntry 20 }

slbNewCfgEnhVirtServiceSdpNat OBJECT-TYPE
    SYNTAX  INTEGER {
        enabled(1),
        disabled(2),
        unsupported(2147483647)
        }
    MAX-ACCESS  read-create
    STATUS  current
    DESCRIPTION
        "Enable/disable SIP Media portal NAT."
    ::= { slbNewCfgEnhVirtServicesSixthPartEntry 21 }

slbNewCfgEnhVirtServicesSeventhPartTable OBJECT-TYPE
    SYNTAX  SEQUENCE OF SlbNewCfgEnhVirtServicesSeventhPartEntry
    MAX-ACCESS  not-accessible
    STATUS  current
    DESCRIPTION
        "The table of virtual Services.
         Note:This mib is not supported for VX instance of Virtualization."
    ::= { virtualServerCfg 43 }

slbNewCfgEnhVirtServicesSeventhPartEntry OBJECT-TYPE
    SYNTAX  SlbNewCfgEnhVirtServicesSeventhPartEntry
    MAX-ACCESS  not-accessible
    STATUS  current
    DESCRIPTION
        "A row in the virtual services table."
    INDEX   { slbNewCfgEnhVirtServSeventhPartIndex, slbNewCfgEnhVirtServiceSeventhPartIndex }
    ::= { slbNewCfgEnhVirtServicesSeventhPartTable 1 }

SlbNewCfgEnhVirtServicesSeventhPartEntry ::= SEQUENCE {

    slbNewCfgEnhVirtServSeventhPartIndex            DisplayString,
    slbNewCfgEnhVirtServiceSeventhPartIndex         Integer32,
    slbNewCfgEnhVirtServiceRealGroup     DisplayString,
    slbNewCfgEnhVirtServiceSessionMirror INTEGER,
    slbNewCfgEnhVirtServiceSoftGrid      INTEGER,
    slbNewCfgEnhVirtServiceConnPooling   INTEGER,
    slbNewCfgEnhVirtPersistentTimeOut    INTEGER,
    slbNewCfgEnhVirtServiceProxyIpMode   INTEGER,
    slbNewCfgEnhVirtServiceProxyIpAddr   IpAddress,
    slbNewCfgEnhVirtServiceProxyIpMask   IpAddress,
    slbNewCfgEnhVirtServiceProxyIpv6Addr   DisplayString,
    slbNewCfgEnhVirtServiceProxyIpv6Prefix   INTEGER,
    slbNewCfgEnhVirtServiceProxyIpPersistency   INTEGER,
    slbNewCfgEnhVirtServiceProxyIpNWclass   DisplayString,
    slbNewCfgEnhVirtServiceProxyIpv6NWclass   DisplayString,
    slbNewCfgEnhVirtServiceProxyIpNWclassPersistency   INTEGER,
    slbNewCfgEnhVirtServiceHashLen          INTEGER,
    slbNewCfgEnhVirtServiceClsRST           INTEGER,
    slbNewCfgEnhVirtServiceHttpHdrName      DisplayString,
    slbNewCfgEnhVirtServFastWa              DisplayString,
    slbNewCfgEnhVirtServiceAppwallWebappId  DisplayString,
    slbNewCfgEnhVirtServiceHttp2            DisplayString,
    slbNewCfgEnhVirtServiceCluster          INTEGER,
    slbNewCfgEnhVirtServiceDataPort         INTEGER,
    slbNewCfgEnhVirtServiceApplicName       RadwareLongDisplayString,
    slbNewCfgEnhVirtServiceReport           INTEGER,
    slbNewCfgEnhVirtServiceTrevpol          DisplayString,
    slbNewCfgEnhVirtServiceSatisrt          INTEGER,
    slbNewCfgEnhVirtServiceNamesrvr         DisplayString,
    slbNewCfgEnhVirtServiceIsDnsSecVip      INTEGER
}

slbNewCfgEnhVirtServSeventhPartIndex OBJECT-TYPE
    SYNTAX  DisplayString (SIZE(1..255))
    MAX-ACCESS  read-only
    STATUS  current
    DESCRIPTION
        "The number of the virtual server."
    ::= { slbNewCfgEnhVirtServicesSeventhPartEntry 1 }

slbNewCfgEnhVirtServiceSeventhPartIndex OBJECT-TYPE
    SYNTAX  Integer32
    MAX-ACCESS  read-only
    STATUS  current
    DESCRIPTION
        "The service index. This has no external meaning"
    ::= { slbNewCfgEnhVirtServicesSeventhPartEntry 2 }

slbNewCfgEnhVirtServiceRealGroup OBJECT-TYPE
    SYNTAX DisplayString (SIZE(1..255))
    MAX-ACCESS  read-create
    STATUS  current
    DESCRIPTION
        "The real server group number for this service."
    ::= { slbNewCfgEnhVirtServicesSeventhPartEntry 3 }


slbNewCfgEnhVirtServiceSessionMirror OBJECT-TYPE
    SYNTAX  INTEGER {
        enabled(1),
        disabled(2),
        unsupported(2147483647)
        }
    MAX-ACCESS  read-create
    STATUS  current
    DESCRIPTION
        "Enable/disable session mirroring."
    ::= { slbNewCfgEnhVirtServicesSeventhPartEntry 4 }

slbNewCfgEnhVirtServiceSoftGrid OBJECT-TYPE
    SYNTAX  INTEGER {
        enabled(1),
        disabled(2),
        unsupported(2147483647)
        }
    MAX-ACCESS  read-create
    STATUS  current
    DESCRIPTION
        "Enable/disable softgrid load balancing."
    ::= { slbNewCfgEnhVirtServicesSeventhPartEntry 5 }

slbNewCfgEnhVirtServiceConnPooling OBJECT-TYPE
    SYNTAX  INTEGER {
        enabled(1),
            disabled(2),
        unsupported(2147483647)
    }
    MAX-ACCESS  read-create
    STATUS  current
    DESCRIPTION
        "Enable/disable connection pooling for HTTP traffic."
    ::= { slbNewCfgEnhVirtServicesSeventhPartEntry 6 }

slbNewCfgEnhVirtPersistentTimeOut OBJECT-TYPE
    SYNTAX  INTEGER (0..32768)
    MAX-ACCESS  read-create
    STATUS  current
    DESCRIPTION
        "The maximum number of minutes a persistent session should exist."
    ::= { slbNewCfgEnhVirtServicesSeventhPartEntry 7 }
--Proxy IP New config start
slbNewCfgEnhVirtServiceProxyIpMode OBJECT-TYPE
    SYNTAX INTEGER {
        ingress(0),
         egress(1),
         address(2),
         nwclss(3),
        disable(4),
        unsupported(2147483647)
        }
    MAX-ACCESS  read-create
    STATUS  current
    DESCRIPTION
        "Set the Proxy IP mode, default is ingress(0).
                Changing from address(2) to any other mode will clear the configured IPv4/IPv6 address,prefix and persistancy.
                Changing from  nwclass(3) to any other mode will clear the configured NWclass and NWpersistancy."
    ::= { slbNewCfgEnhVirtServicesSeventhPartEntry 8 }

    slbNewCfgEnhVirtServiceProxyIpAddr OBJECT-TYPE
    SYNTAX  IpAddress
    MAX-ACCESS  read-create
    STATUS  current
    DESCRIPTION
        "This object ID allows configuring IPv4 PIP address.
                This object ID can be set only if slbNewCfgVirtServiceProxyIpMode is address else return failure.
                Returns 0 when slbNewCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbNewCfgEnhVirtServicesSeventhPartEntry 9 }

   slbNewCfgEnhVirtServiceProxyIpMask OBJECT-TYPE
    SYNTAX  IpAddress
    MAX-ACCESS  read-create
    STATUS  current
    DESCRIPTION
        "This object ID allows configuring IPv4 PIP Mask.
                Returns 0 when slbNewCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbNewCfgEnhVirtServicesSeventhPartEntry 10 }

    slbNewCfgEnhVirtServiceProxyIpv6Addr OBJECT-TYPE
    SYNTAX  DisplayString  (SIZE(0..40))
    MAX-ACCESS  read-create
    STATUS  current
    DESCRIPTION
        "This object ID allows configuring IPv6 PIP address.
                Returns 0 when slbNewCfgVirtServiceProxyIpMode is not set to address.
                When a subnet is configured user has the ability to select PIP persistency mode.
                Persistency is relevant only if either IPv4 PIP or IPv6 PIP (or both) are configured as
                subnet.
                Address should be 4-byte hexadecimal colon notation.
                Valid IPv6 address should be in any of the following forms
                       xxxx:xxxx:xxxx:xxxx:xxxx:xxxx:xxxx:xxxx or
                       xxxx::xxxx:xxxx:xxxx:xxxx or ::xxxx.
                If neither of the addresses (v4 & v6) are configured or are subnets, the persistency
                value is disable."
    ::= { slbNewCfgEnhVirtServicesSeventhPartEntry 11 }

   slbNewCfgEnhVirtServiceProxyIpv6Prefix OBJECT-TYPE
    SYNTAX  INTEGER (1..128)
    MAX-ACCESS  read-create
    STATUS  current
    DESCRIPTION
        "This object ID allows configuring IPv6 PIP Mask.
                Returns 0 when slbNewCfgVirtServiceProxyIpMode is not set to address.
                When a subnet is configured user has the ability to select PIP persistency mode.
                Persistency is relevant only if either IPv4 PIP or IPv6 PIP (or both) are configured as
                subnet.
                If neither of the addresses (v4 & v6) are configured or are subnets, the persistency
                value is disable."
    ::= { slbNewCfgEnhVirtServicesSeventhPartEntry 12 }

slbNewCfgEnhVirtServiceProxyIpPersistency OBJECT-TYPE
    SYNTAX INTEGER {
        disable(0),
        client(1),
         host(2),
         unsupported(2147483647)
        }
    MAX-ACCESS  read-create
    STATUS  current
    DESCRIPTION
        "When a subnet is configured user has the ability to select PIP persistency mode.
                Returns 0 when slbNewCfgVirtServiceProxyIpMode is not set to address.
                Persistency is relevant only if either IPv4 PIP or IPv6 PIP (or both) are configured as
                subnet.
                If neither of the addresses (v4 & v6) are configured or are subnets, the persistency
                value is disable. "
    ::= { slbNewCfgEnhVirtServicesSeventhPartEntry 13 }

   slbNewCfgEnhVirtServiceProxyIpNWclass OBJECT-TYPE
    SYNTAX  DisplayString  (SIZE(0..32))
    MAX-ACCESS  read-create
    STATUS  current
    DESCRIPTION
        "This object ID allows configuring IPv4 Network Class as PIP and PIP persistency mode.
                Returns empty string when slbNewCfgVirtServiceProxyIpMode is not set to nwclass.
                Persistency is relevant only if either IPv4 or IPv6 class (or both) are configured.
                If neither of the classes (v4 & v6) are configured, the persistency configuration value is disable."
    ::= { slbNewCfgEnhVirtServicesSeventhPartEntry 14 }

   slbNewCfgEnhVirtServiceProxyIpv6NWclass OBJECT-TYPE
    SYNTAX  DisplayString  (SIZE(0..32))
    MAX-ACCESS  read-create
    STATUS  current
    DESCRIPTION
        "This object ID allows configuring IPv6 Network Class as PIP and PIP persistency mode.
                Returns empty string when slbNewCfgVirtServiceProxyIpMode is not set to nwclass.
                Persistency is relevant only if either IPv4 or IPv6 class (or both) are configured.
                If neither of the classes (v4 & v6) are configured, the persistency configuration value is disable."
    ::= { slbNewCfgEnhVirtServicesSeventhPartEntry 15 }

slbNewCfgEnhVirtServiceProxyIpNWclassPersistency OBJECT-TYPE
    SYNTAX INTEGER {
        disable(0),
        client(1),
        unsupported(2147483647)
        }
    MAX-ACCESS  read-create
    STATUS  current
    DESCRIPTION
        "This object ID allows configuring Network Class PIP persistency mode.
                Returns 0 when slbNewCfgVirtServiceProxyIpMode is not set to nwclass.
                Persistency is relevant only if either IPv4 PIP or IPv6 PIP (or both) are configured as
                subnet.
                If neither of the addresses (v4 & v6) are configured or are subnets, the persistency
                value is disable. "
    ::= { slbNewCfgEnhVirtServicesSeventhPartEntry 16 }
--Proxy IP New config end

slbNewCfgEnhVirtServiceHashLen OBJECT-TYPE
    SYNTAX INTEGER (4..256)
    MAX-ACCESS  read-create
    STATUS  current
    DESCRIPTION
        "Set length for slb service sip hashing (4- 256 bytes)"
    ::= { slbNewCfgEnhVirtServicesSeventhPartEntry 17 }

slbNewCfgEnhVirtServiceClsRST OBJECT-TYPE
    SYNTAX  INTEGER {
        enabled(1),
        disabled(2),
        unsupported(2147483647)
        }
    MAX-ACCESS  read-create
    STATUS  current
    DESCRIPTION
        "Enable or disable Send RST on connection close."
    ::= { slbNewCfgEnhVirtServicesSeventhPartEntry 18 }

slbNewCfgEnhVirtServiceHttpHdrName OBJECT-TYPE
    SYNTAX  DisplayString  (SIZE(0..32))
    MAX-ACCESS  read-create
    STATUS  current
    DESCRIPTION
        "The HTTP header name of the virtual server."
    ::= { slbNewCfgEnhVirtServicesSeventhPartEntry 19 }

slbNewCfgEnhVirtServFastWa OBJECT-TYPE
    SYNTAX  DisplayString  (SIZE(0..32))
    MAX-ACCESS  read-create
    STATUS  current
    DESCRIPTION
        "Fastview web application name associated with this virtual service.Set none to delete entry"
    ::= { slbNewCfgEnhVirtServicesSeventhPartEntry 20 }

slbNewCfgEnhVirtServiceAppwallWebappId OBJECT-TYPE
    SYNTAX  DisplayString  (SIZE(0..32)) 
    MAX-ACCESS  read-create
    STATUS  current
    DESCRIPTION
        "This object ID allows configuring the web security ID" 
    ::= { slbNewCfgEnhVirtServicesSeventhPartEntry 21 } 

slbNewCfgEnhVirtServiceHttp2 OBJECT-TYPE
    SYNTAX  DisplayString  (SIZE(0..32)) 
    MAX-ACCESS  read-create
    STATUS  current
    DESCRIPTION
        "Http2 policy name associated with this virtual service." 
    ::= { slbNewCfgEnhVirtServicesSeventhPartEntry 22 } 

slbNewCfgEnhVirtServiceCluster OBJECT-TYPE
    SYNTAX  INTEGER {
        enabled(1),
        disabled(2),
        unsupported(2147483647)
        }
    MAX-ACCESS  read-create
    STATUS  current
    DESCRIPTION
        "Enable or disable Cluster Updates for the service."
    ::= { slbNewCfgEnhVirtServicesSeventhPartEntry 23 }

slbNewCfgEnhVirtServiceDataPort OBJECT-TYPE
    SYNTAX  INTEGER (1..65534)
    MAX-ACCESS  read-create
    STATUS  current
    DESCRIPTION
        "The ftp control service data port"
    ::= { slbNewCfgEnhVirtServicesSeventhPartEntry 24 }

slbNewCfgEnhVirtServiceApplicName OBJECT-TYPE
    SYNTAX  RadwareLongDisplayString (SIZE(1..261))
    MAX-ACCESS  read-create
    STATUS  current
    DESCRIPTION
        "Correlate several services into one application at the visualization."
    ::= { slbNewCfgEnhVirtServicesSeventhPartEntry 25 }

slbNewCfgEnhVirtServiceReport OBJECT-TYPE
    SYNTAX  INTEGER {
    enabled(1),
    disabled(2),
    unsupported(2147483647)
    }
    MAX-ACCESS  read-create
    STATUS  current
    DESCRIPTION
        "Enable/disable counter based reporting for service."
    ::= { slbNewCfgEnhVirtServicesSeventhPartEntry 26 }

slbNewCfgEnhVirtServiceTrevpol OBJECT-TYPE
    SYNTAX DisplayString  (SIZE(0..128))
    MAX-ACCESS  read-create
    STATUS  current
    DESCRIPTION
        "Set Traffic Event Log Policy."
    ::= { slbNewCfgEnhVirtServicesSeventhPartEntry 27 } 

slbNewCfgEnhVirtServiceSatisrt OBJECT-TYPE
    SYNTAX  INTEGER (0..999999)
    MAX-ACCESS  read-create
    STATUS  current
    DESCRIPTION
        "Application satisfied response time threshold, inherits the value from the global satisfied value or set with different value 1-999999 ms."
    ::= { slbNewCfgEnhVirtServicesSeventhPartEntry  28 }

slbNewCfgEnhVirtServiceNamesrvr OBJECT-TYPE
    SYNTAX DisplayString  (SIZE(0..128))
    MAX-ACCESS  read-create
    STATUS  current
    DESCRIPTION
        "Set DNS Nameserver group."
    ::= { slbNewCfgEnhVirtServicesSeventhPartEntry 30 }

slbNewCfgEnhVirtServiceIsDnsSecVip OBJECT-TYPE
    SYNTAX  INTEGER {
        no(0),
        yes(1),
        unsupported(2147483647)
    }
    MAX-ACCESS  read-only
    STATUS  current
    DESCRIPTION
        "It returns Yes(1) if virtual service is configure auto with a DNS Responder VIP, else returns no(0)."
    ::= { slbNewCfgEnhVirtServicesSeventhPartEntry 31 }

slbEnhVirtServicesWithApmTable OBJECT-TYPE
    SYNTAX  SEQUENCE OF SlbEnhVirtServicesWithApmEntry
    MAX-ACCESS  not-accessible
    STATUS  obsolete
    DESCRIPTION
        "Table of virtual services with APM enable on the service.
         Note:This mib is not supported for VX instance of Virtualization."
    ::= { virtualServerCfg 44 }
    
slbEnhVirtServicesWithApmEntry OBJECT-TYPE
    SYNTAX  SlbEnhVirtServicesWithApmEntry
    MAX-ACCESS  not-accessible
    STATUS  obsolete
    DESCRIPTION
        "A row in the virtual services with APM enabled table."
    INDEX   { slbEnhVirtServerWithApmIndex, slbEnhVirtServiceWithApmIndex }
    ::= { slbEnhVirtServicesWithApmTable 1 }

SlbEnhVirtServicesWithApmEntry ::= SEQUENCE {
    slbEnhVirtServerWithApmIndex      DisplayString,
    slbEnhVirtServiceWithApmIndex     Integer32
}

slbEnhVirtServerWithApmIndex OBJECT-TYPE
    SYNTAX DisplayString (SIZE(1..255))
    MAX-ACCESS  read-only
    STATUS  obsolete
    DESCRIPTION
        "The virtual server id."
    ::= { slbEnhVirtServicesWithApmEntry 1 }

slbEnhVirtServiceWithApmIndex OBJECT-TYPE
    SYNTAX Integer32 
    MAX-ACCESS  read-only
    STATUS  obsolete
    DESCRIPTION
        "The virtual service index."
    ::= { slbEnhVirtServicesWithApmEntry 2 }



-- URL based BWM table for Virtual Services

    slbCurCfgEnhUrlBwmTable OBJECT-TYPE
        SYNTAX  SEQUENCE OF SlbCurCfgEnhUrlBwmEntry
        MAX-ACCESS  not-accessible
        STATUS  current
        DESCRIPTION
            "The table of URL based BWM for Virtual Services.
             Note:This mib is not supported for VX instance of Virtualization."
        ::= { virtualServerCfg 34 }

    slbCurCfgEnhUrlBwmEntry OBJECT-TYPE
        SYNTAX  SlbCurCfgEnhUrlBwmEntry
        MAX-ACCESS  not-accessible
        STATUS  current
        DESCRIPTION
            "A row in the URL based BWM virtual services table."
        INDEX   { slbCurCfgEnhUrlBwmVirtServIndex,
                  slbCurCfgEnhUrlBwmVirtServiceIndex,
                  slbCurCfgEnhUrlBwmUrlId }
        ::= { slbCurCfgEnhUrlBwmTable 1 }

    SlbCurCfgEnhUrlBwmEntry ::= SEQUENCE {
        slbCurCfgEnhUrlBwmVirtServIndex     DisplayString,
        slbCurCfgEnhUrlBwmVirtServiceIndex  Integer32,
        slbCurCfgEnhUrlBwmUrlId             Integer32,
        slbCurCfgEnhUrlBwmContract          Integer32
        }

    slbCurCfgEnhUrlBwmVirtServIndex OBJECT-TYPE
        SYNTAX  DisplayString (SIZE(1..255))
        MAX-ACCESS  read-only
        STATUS  current
        DESCRIPTION
            "The number of the virtual server."
        ::= { slbCurCfgEnhUrlBwmEntry 1 }

    slbCurCfgEnhUrlBwmVirtServiceIndex OBJECT-TYPE
        SYNTAX  Integer32
        MAX-ACCESS  read-only
        STATUS  current
        DESCRIPTION
            "The service index. This has no external meaning"
        ::= { slbCurCfgEnhUrlBwmEntry 2 }

    slbCurCfgEnhUrlBwmUrlId OBJECT-TYPE
        SYNTAX  Integer32
        MAX-ACCESS  read-only
        STATUS  current
    DESCRIPTION
        "The URL Path Identifier."
    ::= { slbCurCfgEnhUrlBwmEntry 3 }

slbCurCfgEnhUrlBwmContract OBJECT-TYPE
    SYNTAX  Integer32
    MAX-ACCESS  read-only
    STATUS  current
    DESCRIPTION
        "The BW contract number."
    ::= { slbCurCfgEnhUrlBwmEntry 4 }
slbNewCfgEnhUrlBwmTable OBJECT-TYPE
    SYNTAX  SEQUENCE OF SlbNewCfgEnhUrlBwmEntry
    MAX-ACCESS  not-accessible
    STATUS  current
    DESCRIPTION
        "The table of URL based BWM for Virtual Services.
         Note:This mib is not supported for VX instance of Virtualization."
    ::= { virtualServerCfg 35 }

slbNewCfgEnhUrlBwmEntry OBJECT-TYPE
    SYNTAX  SlbNewCfgEnhUrlBwmEntry
    MAX-ACCESS  not-accessible
    STATUS  current
    DESCRIPTION
        "A row in the URL based BWM virtual services table."
    INDEX   { slbNewCfgEnhUrlBwmVirtServIndex,
              slbNewCfgEnhUrlBwmVirtServiceIndex,
              slbNewCfgEnhUrlBwmUrlId }
    ::= { slbNewCfgEnhUrlBwmTable 1 }

SlbNewCfgEnhUrlBwmEntry ::= SEQUENCE {
    slbNewCfgEnhUrlBwmVirtServIndex     DisplayString,
    slbNewCfgEnhUrlBwmVirtServiceIndex  Integer32,
    slbNewCfgEnhUrlBwmUrlId             Integer32,
    slbNewCfgEnhUrlBwmContract          Integer32,
    slbNewCfgEnhUrlBwmDelete            INTEGER
    }

slbNewCfgEnhUrlBwmVirtServIndex OBJECT-TYPE
    SYNTAX  DisplayString (SIZE(1..255))
    MAX-ACCESS  read-only
    STATUS  current
    DESCRIPTION
        "The number of the virtual server."
    ::= { slbNewCfgEnhUrlBwmEntry 1 }

slbNewCfgEnhUrlBwmVirtServiceIndex OBJECT-TYPE
    SYNTAX  Integer32
    MAX-ACCESS  read-only
    STATUS  current
    DESCRIPTION
        "The service index. This has no external meaning"
    ::= { slbNewCfgEnhUrlBwmEntry 2 }

slbNewCfgEnhUrlBwmUrlId OBJECT-TYPE
    SYNTAX  Integer32
    MAX-ACCESS  read-only
    STATUS  current
    DESCRIPTION
        "The URL Path Identifier."
    ::= { slbNewCfgEnhUrlBwmEntry 3 }

slbNewCfgEnhUrlBwmContract OBJECT-TYPE
    SYNTAX  Integer32
    MAX-ACCESS  read-create
    STATUS  current
    DESCRIPTION
        "The BW contract number."
    ::= { slbNewCfgEnhUrlBwmEntry 4 }

slbNewCfgEnhUrlBwmDelete OBJECT-TYPE
    SYNTAX  INTEGER {
        other(1),
        delete(2),
        unsupported(2147483647)
       }
    MAX-ACCESS  read-create
    STATUS  current
    DESCRIPTION
        "When set to the value of 2 (delete), the entire row is deleted.
         When read, other(1) is returned. Setting the value to anything
         other than 2(delete) has no effect on the state of the row."
    ::= { slbNewCfgEnhUrlBwmEntry 5 }


--L7 Content based services rule

slbCurCfgEnhContRuleTable OBJECT-TYPE
    SYNTAX  SEQUENCE OF SlbCurCfgEnhContRuleEntry
    MAX-ACCESS  not-accessible
    STATUS  current
    DESCRIPTION
        "The table of Content based Services Rules.
         Note:This mib is not supported for VX instance of Virtualization."
    ::= { virtualServerCfg 36 }

slbCurCfgEnhContRuleEntry OBJECT-TYPE
    SYNTAX  SlbCurCfgEnhContRuleEntry
    MAX-ACCESS  not-accessible
    STATUS  current
    DESCRIPTION
        "A row in the Content Based Services Rules table."
    INDEX  { slbCurCfgEnhContVirtServIndex, slbCurCfgEnhContVirtServiceIndex,
             slbCurCfgEnhContRuleIndex }
    ::= { slbCurCfgEnhContRuleTable 1 }

SlbCurCfgEnhContRuleEntry ::= SEQUENCE {
    slbCurCfgEnhContVirtServIndex       DisplayString,
    slbCurCfgEnhContVirtServiceIndex  Integer32,
    slbCurCfgEnhContRuleIndex   Integer32,
    slbCurCfgEnhContRuleName     DisplayString,
    slbCurCfgEnhContRuleContClass  DisplayString,
    slbCurCfgEnhContRuleAction    INTEGER,
    slbCurCfgEnhContRuleRealGrpNum       DisplayString,
    slbCurCfgEnhContRuleGotoRuleNum      INTEGER,
    slbCurCfgEnhContRuleRedirection  DisplayString,
    slbCurCfgEnhContRuleState   INTEGER,
    slbCurCfgEnhContRuleFastWa       DisplayString    
    }

slbCurCfgEnhContVirtServIndex OBJECT-TYPE
    SYNTAX  DisplayString (SIZE(1..255))
    MAX-ACCESS  read-only
    STATUS  current
    DESCRIPTION
        "The number of the virtual server."
    ::= { slbCurCfgEnhContRuleEntry  1 }


slbCurCfgEnhContVirtServiceIndex OBJECT-TYPE
    SYNTAX  Integer32
    MAX-ACCESS  read-only
    STATUS  current
    DESCRIPTION
        "The service index. This has no external meaning"
    ::= { slbCurCfgEnhContRuleEntry  2 }
slbCurCfgEnhContRuleIndex OBJECT-TYPE
    SYNTAX  Integer32
    MAX-ACCESS  read-only
    STATUS  current
    DESCRIPTION
        "The content based service rule index."
    ::= { slbCurCfgEnhContRuleEntry  3 }

slbCurCfgEnhContRuleName OBJECT-TYPE
    SYNTAX  DisplayString (SIZE(0..32))
    MAX-ACCESS  read-only
    STATUS  current
    DESCRIPTION
        "The Content Rule Name."
    ::= { slbCurCfgEnhContRuleEntry  4 }

slbCurCfgEnhContRuleContClass OBJECT-TYPE
    SYNTAX  DisplayString (SIZE(0..32))
    MAX-ACCESS  read-only
    STATUS  current
    DESCRIPTION
        "The Content Class for the rule."
    ::= { slbCurCfgEnhContRuleEntry  5 }

slbCurCfgEnhContRuleAction OBJECT-TYPE
    SYNTAX  INTEGER {
    group(1),
    appredir(2),
    discard(3),
    goto(4),
    unsupported(2147483647)
    }
    MAX-ACCESS  read-only
    STATUS  current
    DESCRIPTION
        "Action type of the rule."
    ::= { slbCurCfgEnhContRuleEntry  6 }

slbCurCfgEnhContRuleRealGrpNum OBJECT-TYPE
    SYNTAX  DisplayString (SIZE(1..255))
    MAX-ACCESS  read-only
    STATUS  current
    DESCRIPTION
        "The group number of real server."
    ::= { slbCurCfgEnhContRuleEntry 7 }

slbCurCfgEnhContRuleGotoRuleNum OBJECT-TYPE
    SYNTAX  INTEGER (1..12800)
    MAX-ACCESS  read-only
    STATUS  current
    DESCRIPTION
        "The group number of real server."
    ::= { slbCurCfgEnhContRuleEntry 8 }

slbCurCfgEnhContRuleRedirection OBJECT-TYPE
    SYNTAX  DisplayString (SIZE(0..255))
    MAX-ACCESS  read-only
    STATUS  current
    DESCRIPTION
        "Application redirection for the rule."
    ::= { slbCurCfgEnhContRuleEntry  9 }

slbCurCfgEnhContRuleState OBJECT-TYPE
    SYNTAX INTEGER {
        enabled(1),
    disabled(2),
        unsupported(2147483647)
    }
    MAX-ACCESS  read-only
    STATUS  current
    DESCRIPTION
        "Enable or disable Content Based Services Rule ."
    ::= { slbCurCfgEnhContRuleEntry 10 }

slbCurCfgEnhContRuleFastWa OBJECT-TYPE
    SYNTAX  DisplayString  (SIZE(0..32))
    MAX-ACCESS  read-only
    STATUS  current
    DESCRIPTION
        "Fastview web application name associated with this rule."
    ::= { slbCurCfgEnhContRuleEntry 11 }

slbNewCfgEnhContRuleTable OBJECT-TYPE
    SYNTAX  SEQUENCE OF SlbNewCfgEnhContRuleEntry
    MAX-ACCESS  not-accessible
    STATUS  current
    DESCRIPTION
        "The table of Content based Services Rules.
         Note:This mib is not supported for VX instance of Virtualization."
    ::= { virtualServerCfg 37 }

slbNewCfgEnhContRuleEntry OBJECT-TYPE
    SYNTAX  SlbNewCfgEnhContRuleEntry
    MAX-ACCESS  not-accessible
    STATUS  current
    DESCRIPTION
        "A row in the Content Based Services Rules table."
    INDEX  { slbNewCfgEnhContVirtServIndex, slbNewCfgEnhContVirtServiceIndex,
             slbNewCfgEnhContRuleIndex }
    ::= { slbNewCfgEnhContRuleTable 1 }

SlbNewCfgEnhContRuleEntry ::= SEQUENCE {
    slbNewCfgEnhContVirtServIndex       DisplayString,
    slbNewCfgEnhContVirtServiceIndex  Integer32,
    slbNewCfgEnhContRuleIndex         Integer32,
    slbNewCfgEnhContRuleName     DisplayString,
    slbNewCfgEnhContRuleContClass  DisplayString,
    slbNewCfgEnhContRuleAction    INTEGER,
    slbNewCfgEnhContRuleRealGrpNum      DisplayString,
    slbNewCfgEnhContRuleGotoRuleNum INTEGER,
    slbNewCfgEnhContRuleRedirection  RadwareLongDisplayString,
    slbNewCfgEnhContRuleCopy   INTEGER,
    slbNewCfgEnhContRuleState   INTEGER,
    slbNewCfgEnhContRuleDelete   INTEGER,
    slbNewCfgEnhContRuleFastWa       DisplayString    
    }
slbNewCfgEnhContVirtServIndex OBJECT-TYPE
    SYNTAX  DisplayString (SIZE(1..255))
    MAX-ACCESS  read-only
    STATUS  current
    DESCRIPTION
        "The number of the virtual server."
    ::= { slbNewCfgEnhContRuleEntry  1 }

slbNewCfgEnhContVirtServiceIndex OBJECT-TYPE
    SYNTAX  Integer32
    MAX-ACCESS  read-only
    STATUS  current
    DESCRIPTION
        "The service index. This has no external meaning"
    ::= { slbNewCfgEnhContRuleEntry  2 }

slbNewCfgEnhContRuleIndex OBJECT-TYPE
    SYNTAX  Integer32
    MAX-ACCESS  read-only
    STATUS  current
    DESCRIPTION
        "The content based service index."
    ::= { slbNewCfgEnhContRuleEntry  3 }

slbNewCfgEnhContRuleName OBJECT-TYPE
    SYNTAX  DisplayString (SIZE(0..32))
    MAX-ACCESS  read-create
    STATUS  current
    DESCRIPTION
        "The Content Rule Name."
    ::= { slbNewCfgEnhContRuleEntry  4 }

slbNewCfgEnhContRuleContClass OBJECT-TYPE
    SYNTAX  DisplayString (SIZE(0..32))
    MAX-ACCESS  read-create
    STATUS  current
    DESCRIPTION
        "The Content Class for the rule."
    ::= { slbNewCfgEnhContRuleEntry  5 }

slbNewCfgEnhContRuleAction OBJECT-TYPE
    SYNTAX  INTEGER {
    group(1),
    appredir(2),
              discard(3),
              goto(4),
    unsupported(2147483647)
    }
    MAX-ACCESS  read-create
    STATUS  current
    DESCRIPTION
        "Action type of the rule."
    ::= { slbNewCfgEnhContRuleEntry  6 }

slbNewCfgEnhContRuleRealGrpNum OBJECT-TYPE
    SYNTAX  DisplayString (SIZE(1..255))
    MAX-ACCESS  read-create
    STATUS  current
    DESCRIPTION
        "The group number of real server."
    ::= { slbNewCfgEnhContRuleEntry 7 }

slbNewCfgEnhContRuleGotoRuleNum OBJECT-TYPE
    SYNTAX  INTEGER (1..12800)
    MAX-ACCESS  read-create
    STATUS  current
    DESCRIPTION
        "The group number of real server."
    ::= { slbNewCfgEnhContRuleEntry 8 }


slbNewCfgEnhContRuleRedirection OBJECT-TYPE
    SYNTAX  RadwareLongDisplayString (SIZE(0..256))
    MAX-ACCESS  read-create
    STATUS  current
    DESCRIPTION
        "Application redirection for the rule."
    ::= { slbNewCfgEnhContRuleEntry  9 }

slbNewCfgEnhContRuleCopy OBJECT-TYPE
    SYNTAX  INTEGER (1..12800)
    MAX-ACCESS  read-create
    STATUS  current
    DESCRIPTION
        "The Number to which current rule is to be copied."
    ::= { slbNewCfgEnhContRuleEntry 10 }


slbNewCfgEnhContRuleState OBJECT-TYPE
    SYNTAX  INTEGER {
        enabled(1),
        disabled(2),
        unsupported(2147483647)
    }
    MAX-ACCESS  read-create
    STATUS  current
    DESCRIPTION
        "Enable or disable Content Based Services Rule ."
    ::= { slbNewCfgEnhContRuleEntry 11 }


slbNewCfgEnhContRuleDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgEnhContRuleEntry 12 }

slbNewCfgEnhContRuleFastWa OBJECT-TYPE
    SYNTAX  DisplayString  (SIZE(0..32))
    MAX-ACCESS  read-create
    STATUS  current
    DESCRIPTION
        "Fastview web application name associated with this rule."
    ::= { slbNewCfgEnhContRuleEntry 13 }


--AppShapes for virtual service

slbCurCfgEnhSerAppShapeTable OBJECT-TYPE
    SYNTAX  SEQUENCE OF SlbCurCfgEnhSerAppShapeEntry
    MAX-ACCESS  not-accessible
    STATUS  current
    DESCRIPTION
        "The table of App Rules added to virtual services.
         Note:This mib is not supported for VX instance of Virtualization."
    ::= { virtualServerCfg 38 }

slbCurCfgEnhSerAppShapeEntry OBJECT-TYPE
    SYNTAX  SlbCurCfgEnhSerAppShapeEntry
    MAX-ACCESS  not-accessible
    STATUS  current
    DESCRIPTION
        "A row in the  AppShape Based Services Rules table."
    INDEX  { slbCurCfgEnhSerAppShapeVirtServIndex, slbCurCfgEnhSerAppShapeVirtServiceIndex,
             slbCurCfgEnhSerAppShapePriority }
    ::= { slbCurCfgEnhSerAppShapeTable 1 }

SlbCurCfgEnhSerAppShapeEntry ::= SEQUENCE {
    slbCurCfgEnhSerAppShapeVirtServIndex     DisplayString,
    slbCurCfgEnhSerAppShapeVirtServiceIndex  Integer32,
    slbCurCfgEnhSerAppShapePriority          Integer32,
    slbCurCfgEnhSerAppShapeIndex             DisplayString
    }
slbCurCfgEnhSerAppShapeVirtServIndex OBJECT-TYPE
    SYNTAX  DisplayString (SIZE(1..255))
    MAX-ACCESS  read-only
    STATUS  current
    DESCRIPTION
        "The number of the virtual server."
    ::= { slbCurCfgEnhSerAppShapeEntry  1 }

slbCurCfgEnhSerAppShapeVirtServiceIndex OBJECT-TYPE
    SYNTAX  Integer32
    MAX-ACCESS  read-only
    STATUS  current
    DESCRIPTION
        "The service index. This has no external meaning"
    ::= { slbCurCfgEnhSerAppShapeEntry  2 }

slbCurCfgEnhSerAppShapePriority OBJECT-TYPE
    SYNTAX  Integer32
    MAX-ACCESS  read-only
    STATUS  current
    DESCRIPTION
        "The number of the virtual server."
    ::= { slbCurCfgEnhSerAppShapeEntry  3 }

slbCurCfgEnhSerAppShapeIndex OBJECT-TYPE
    SYNTAX  DisplayString (SIZE(0..128))
    MAX-ACCESS  read-only
    STATUS  current
    DESCRIPTION
        "The AppShape ID added to the virtual service"
    ::= { slbCurCfgEnhSerAppShapeEntry  4 }

slbNewCfgEnhSerAppShapeTable OBJECT-TYPE
    SYNTAX  SEQUENCE OF SlbNewCfgEnhSerAppShapeEntry
    MAX-ACCESS  not-accessible
    STATUS  current
    DESCRIPTION
        "The table of Content based Services Rules.
         Note:This mib is not supported for VX instance of Virtualization."
    ::= { virtualServerCfg 39 }

slbNewCfgEnhSerAppShapeEntry OBJECT-TYPE
    SYNTAX  SlbNewCfgEnhSerAppShapeEntry
    MAX-ACCESS  not-accessible
    STATUS  current
    DESCRIPTION
        "A row in the Content Based Services Rules table."
    INDEX  { slbNewCfgEnhSerAppShapeVirtServIndex, slbNewCfgEnhSerAppShapeVirtServiceIndex,
             slbNewCfgEnhSerAppShapePriority }
    ::= { slbNewCfgEnhSerAppShapeTable 1 }
SlbNewCfgEnhSerAppShapeEntry ::= SEQUENCE {
    slbNewCfgEnhSerAppShapeVirtServIndex     DisplayString,
    slbNewCfgEnhSerAppShapeVirtServiceIndex  Integer32,
    slbNewCfgEnhSerAppShapePriority          Integer32,
    slbNewCfgEnhSerAppShapeIndex             DisplayString,
    slbNewCfgEnhSerAppShapeDelete            INTEGER
    }
slbNewCfgEnhSerAppShapeVirtServIndex OBJECT-TYPE
    SYNTAX  DisplayString (SIZE(1..255))
    MAX-ACCESS  read-only
    STATUS  current
    DESCRIPTION
        "The number of the virtual server."
    ::= { slbNewCfgEnhSerAppShapeEntry  1 }

slbNewCfgEnhSerAppShapeVirtServiceIndex OBJECT-TYPE
    SYNTAX  Integer32
    MAX-ACCESS  read-only
    STATUS  current
    DESCRIPTION
        "The service index. This has no external meaning"
    ::= { slbNewCfgEnhSerAppShapeEntry  2 }

slbNewCfgEnhSerAppShapePriority OBJECT-TYPE
    SYNTAX  Integer32
    MAX-ACCESS  read-create
    STATUS  current
    DESCRIPTION
        "The number of the virtual server."
    ::= { slbNewCfgEnhSerAppShapeEntry  3 }

slbNewCfgEnhSerAppShapeIndex OBJECT-TYPE
    SYNTAX  DisplayString (SIZE(0..128))
    MAX-ACCESS  read-create
    STATUS  current
    DESCRIPTION
        "The AppShape ID added to the virtual service"
    ::= { slbNewCfgEnhSerAppShapeEntry  4 }

slbNewCfgEnhSerAppShapeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgEnhSerAppShapeEntry 5 }
	
--  SLB Filter Set table

slbFiltsetTableMaxSize OBJECT-TYPE
    SYNTAX  Integer32 
    MAX-ACCESS  read-only 
    STATUS  current 
    DESCRIPTION 
        "The maximum number of entries in SLB Filter set Table.
         Note:This mib is not supported for VX instance of Virtualization." 
    ::= { filtsetCfg 1 }

slbCurCfgFiltsetTable OBJECT-TYPE
    SYNTAX  SEQUENCE OF SlbCurCfgFiltsetEntry
    MAX-ACCESS  not-accessible
    STATUS  current
    DESCRIPTION
       "The table of filter sets and their SLB states,
        Note:This mib is not supported for VX instance of Virtualization."
    ::= { filtsetCfg 2 }

slbCurCfgFiltsetEntry OBJECT-TYPE
    SYNTAX  SlbCurCfgFiltsetEntry
    MAX-ACCESS  not-accessible
    STATUS  current
    DESCRIPTION
        "A row in the slbFiltersetTable,
         Note:This mib is not supported for VX instance of Virtualization."
    INDEX   { slbCurCfgFiltsetIndex }
    ::= { slbCurCfgFiltsetTable 1 }

SlbCurCfgFiltsetEntry ::= SEQUENCE {
    slbCurCfgFiltsetIndex         Integer32,
    slbCurCfgFiltsetSlbFilterBmap      OCTET STRING
    }

slbCurCfgFiltsetIndex OBJECT-TYPE
    SYNTAX  Integer32
    MAX-ACCESS  read-only
    STATUS  current
    DESCRIPTION
        "The filter set number for which the SLB information pertains." 
    ::= { slbCurCfgFiltsetEntry 1 }

slbCurCfgFiltsetSlbFilterBmap OBJECT-TYPE
    SYNTAX  OCTET STRING (SIZE(0..256))
    MAX-ACCESS  read-only
    STATUS  current
    DESCRIPTION
	"The filtering rules applied to the filter set.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the filter set
		   0 - The represented filter rule not applied to the filter set "
    ::= { slbCurCfgFiltsetEntry 2 }

--  SLB Port table

slbPortTableMaxSize OBJECT-TYPE
    SYNTAX  Integer32 
    MAX-ACCESS  read-only 
    STATUS  current 
    DESCRIPTION 
        "The maximum number of entries in SLB Port Table.
         Note:This mib is not supported for VX instance of Virtualization." 
    ::= { portCfg 1 }

slbCurCfgPortTable OBJECT-TYPE
    SYNTAX  SEQUENCE OF SlbCurCfgPortEntry
    MAX-ACCESS  not-accessible
    STATUS  current
    DESCRIPTION
       "The table of ports and their SLB states,
        Note:This mib is not supported for VX instance of Virtualization."
    ::= { portCfg 2 }

slbCurCfgPortEntry OBJECT-TYPE
    SYNTAX  SlbCurCfgPortEntry
    MAX-ACCESS  not-accessible
    STATUS  current
    DESCRIPTION
        "A row in the slbPortTable "
    INDEX   { slbCurCfgPortIndex }
    ::= { slbCurCfgPortTable 1 }

SlbCurCfgPortEntry ::= SEQUENCE {
    slbCurCfgPortIndex              Integer32,
    slbCurCfgPortSlbHotStandby      INTEGER,
    slbCurCfgPortSlbInterSwitch     INTEGER,
    slbCurCfgPortSlbPipState        INTEGER,
    slbCurCfgPortSlbRtsState        INTEGER,
    slbCurCfgPortSlbIdslbState      INTEGER,
    slbCurCfgPortSlbState           INTEGER,
    slbCurCfgPortSlbFilter          INTEGER,
    slbCurCfgPortSlbServState       INTEGER,
    slbCurCfgPortSlbClntState       INTEGER,
    slbCurCfgPortSlbL3Filter        INTEGER,
    slbCurCfgPortSlbFilterBmap      OCTET STRING,
    slbCurCfgPortInterSwitchVlan    INTEGER,
    slbCurCfgPortVlanBmap           OCTET STRING
    }

slbCurCfgPortIndex OBJECT-TYPE
    SYNTAX  Integer32
    MAX-ACCESS  read-only
    STATUS  current
    DESCRIPTION
        "The port number for which the SLB information pertains." 
    ::= { slbCurCfgPortEntry 1 }

slbCurCfgPortSlbState OBJECT-TYPE
    SYNTAX  INTEGER {
	none(1),
	client(2),
	server(3),
	client-server(4),
        unsupported(2147483647)
	}
    MAX-ACCESS  read-only
    STATUS  current
    DESCRIPTION
        "The SLB state of the port.
	 none(1)            - not SLB port
	 client(2)          - SLB client port
	 server(3)          - SLB server port
	 client-server(4)   - SLB client and server port"
    ::= { slbCurCfgPortEntry 2 }

slbCurCfgPortSlbFilter OBJECT-TYPE
    SYNTAX  INTEGER {
        enabled(1),
        disabled(2),
        unsupported(2147483647)
        }
    MAX-ACCESS  read-only
    STATUS  current
    DESCRIPTION
        "Enable or disable Filtering."
    ::= { slbCurCfgPortEntry 9 }

slbCurCfgPortSlbHotStandby OBJECT-TYPE
    SYNTAX  INTEGER {
        enabled(1),
        disabled(2),
        unsupported(2147483647)
        }
    MAX-ACCESS  read-only
    STATUS  current
    DESCRIPTION
        "Enable or disable hot standby processing on the switch port."
    ::= { slbCurCfgPortEntry 3 }

slbCurCfgPortSlbInterSwitch OBJECT-TYPE
    SYNTAX  INTEGER {
        enabled(1),
        disabled(2),
        unsupported(2147483647)
        }
    MAX-ACCESS  read-only
    STATUS  current
    DESCRIPTION
        "Enable or disable inter-switch processing on the switch port."
    ::= { slbCurCfgPortEntry 4 }

slbCurCfgPortSlbPipState OBJECT-TYPE
    SYNTAX  INTEGER {
        enabled(1),
        disabled(2),
        unsupported(2147483647)
        }
    MAX-ACCESS  read-only
    STATUS  current
    DESCRIPTION
        "Enable or disable use of proxy IP address on the switch port."
    ::= { slbCurCfgPortEntry 5 }

slbCurCfgPortSlbRtsState OBJECT-TYPE
    SYNTAX  INTEGER   {
        enabled(1),
        disabled(2),
        unsupported(2147483647)
        }
    MAX-ACCESS  read-only
    STATUS  current
    DESCRIPTION
        "Enable or disable RTS processing on the switch port."
    ::= { slbCurCfgPortEntry 6 }

slbCurCfgPortSlbIdslbState OBJECT-TYPE
    SYNTAX  INTEGER {
        enabled(1),
        disabled(2),
        unsupported(2147483647)
        }
    MAX-ACCESS  read-only
    STATUS  current
    DESCRIPTION
        "Enable or disable Intrusion Detection server load balancing."
    ::= { slbCurCfgPortEntry 7 }


slbCurCfgPortSlbServState OBJECT-TYPE
    SYNTAX  INTEGER {
        enabled(1),
            disabled(2),
        unsupported(2147483647)
    }
    MAX-ACCESS  read-only
    STATUS  current
    DESCRIPTION
        "Enable or disable server processing."
    ::= { slbCurCfgPortEntry 10 }

slbCurCfgPortSlbClntState OBJECT-TYPE
    SYNTAX  INTEGER {
        enabled(1),
        disabled(2),
        unsupported(2147483647)
    }
    MAX-ACCESS  read-only
    STATUS  current
    DESCRIPTION
        "Enable or disable client processing."
    ::= { slbCurCfgPortEntry 11 }

slbCurCfgPortSlbL3Filter OBJECT-TYPE
    SYNTAX  INTEGER {
        enabled(1),
        disabled(2),
        unsupported(2147483647)
        }
    MAX-ACCESS  read-only
    STATUS  current
    DESCRIPTION
        "Enable or disable Layer3 Filtering."
    ::= { slbCurCfgPortEntry 12 }

slbCurCfgPortSlbFilterBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { slbCurCfgPortEntry 13 }

slbCurCfgPortInterSwitchVlan OBJECT-TYPE
    SYNTAX  INTEGER (1..4090)
    MAX-ACCESS read-only
    STATUS  current
    DESCRIPTION
        "VLAN for inter-switch processing."
    ::= { slbCurCfgPortEntry 14 }

slbCurCfgPortVlanBmap  OBJECT-TYPE
    SYNTAX  OCTET STRING
    MAX-ACCESS  read-only
    STATUS  current
    DESCRIPTION
        "VLANs associated with this port.
         The VLANs are presented in a bitmap format.

         OCTET 1  OCTET 2  .....
         xxxxxxxx xxxxxxxx .....
         ||    || |_ VLAN 9
         ||    ||
         ||    ||___ VLAN 8
         ||    |____ VLAN 7
         ||      .    .   .
         ||_________ VLAN 2
         |__________ VLAN 1

         where x : 1 - VLAN is associated
                   0 - VLAN is not associated"
    ::= { slbCurCfgPortEntry 15 }

-- Server load balancing - slb port state table

slbNewCfgPortTable OBJECT-TYPE
    SYNTAX  SEQUENCE OF SlbNewCfgPortEntry
    MAX-ACCESS  not-accessible
    STATUS  current
    DESCRIPTION
        "The table of ports and their SLB states,
         Note:This mib is not supported for VX instance of Virtualization."
    ::= { portCfg 3 }

slbNewCfgPortEntry OBJECT-TYPE
    SYNTAX  SlbNewCfgPortEntry
    MAX-ACCESS  not-accessible
    STATUS  current
    DESCRIPTION
        "A row in the slbPortTable "
    INDEX   { slbNewCfgPortIndex }
    ::= { slbNewCfgPortTable 1 }

SlbNewCfgPortEntry ::= SEQUENCE {
    slbNewCfgPortIndex              Integer32,
    slbNewCfgPortSlbHotStandby      INTEGER,
    slbNewCfgPortSlbInterSwitch     INTEGER,
    slbNewCfgPortSlbPipState        INTEGER,
    slbNewCfgPortSlbRtsState        INTEGER,
    slbNewCfgPortDelete             INTEGER,
    slbNewCfgPortSlbIdslbState      INTEGER,
    slbNewCfgPortSlbState           INTEGER,
    slbNewCfgPortSlbFilter          INTEGER,
    slbNewCfgPortSlbAddFilter       INTEGER,
    slbNewCfgPortSlbRemFilter       INTEGER,
    slbNewCfgPortSlbServState       INTEGER,
    slbNewCfgPortSlbClntState       INTEGER,
    slbNewCfgPortSlbL3Filter        INTEGER,
    slbNewCfgPortSlbFilterBmap      OCTET STRING,
    slbNewCfgPortInterSwitchVlan    INTEGER,
    slbNewCfgPortVlanBmap           OCTET STRING
    }

slbNewCfgPortIndex OBJECT-TYPE
    SYNTAX  Integer32
    MAX-ACCESS  read-only
    STATUS  current
    DESCRIPTION
        "The port number for which the SLB information pertains." 
    ::= { slbNewCfgPortEntry 1 }

slbNewCfgPortSlbState OBJECT-TYPE
    SYNTAX  INTEGER {
	none(1),
	client(2),
	server(3),
	client-server(4),
        unsupported(2147483647)
	}
    MAX-ACCESS  read-write
    STATUS  current
    DESCRIPTION
        "The SLB state of the port.
	 none(1)            - not SLB port
	 client(2)          - SLB client port
	 server(3)          - SLB server port
	 client-server(4)   - SLB client and server port"
    ::= { slbNewCfgPortEntry 2 }

slbNewCfgPortSlbHotStandby OBJECT-TYPE
    SYNTAX  INTEGER   {
        enabled(1),
        disabled(2),
        unsupported(2147483647)
        }
    MAX-ACCESS  read-write
    STATUS  current
    DESCRIPTION
        "Enable or disable hot standby processing on the switch port."
    ::= { slbNewCfgPortEntry 3 }

slbNewCfgPortSlbInterSwitch OBJECT-TYPE
    SYNTAX  INTEGER   {
        enabled(1),
        disabled(2),
        unsupported(2147483647)
        }
    MAX-ACCESS  read-write
    STATUS  current
    DESCRIPTION
        "Enable or disable inter-switch processing on the switch port."
    ::= { slbNewCfgPortEntry 4 }

slbNewCfgPortSlbPipState OBJECT-TYPE
    SYNTAX  INTEGER   {
        enabled(1),
        disabled(2),
        unsupported(2147483647)
        }
    MAX-ACCESS  read-write
    STATUS  current
    DESCRIPTION
        "Enable or disable use of proxy IP address on the switch port."
    ::= { slbNewCfgPortEntry 5 }

slbNewCfgPortSlbRtsState OBJECT-TYPE
    SYNTAX  INTEGER   {
        enabled(1),
        disabled(2),
        unsupported(2147483647)
        }
    MAX-ACCESS  read-write
    STATUS  current
    DESCRIPTION
        "Enable or disable RTS processing on the switch port."
    ::= { slbNewCfgPortEntry 6 }

slbNewCfgPortDelete OBJECT-TYPE
    SYNTAX INTEGER {
        other(1),
        delete(2),
        unsupported(2147483647)
        }
    MAX-ACCESS read-write
    STATUS current
    DESCRIPTION
        "When set to the value of 2 (delete), the entire row is deleted. 
         When read, other(1) is returned. Setting the value to anything 
         other than 2(delete) has no effect on the state of the row."
    ::= { slbNewCfgPortEntry 7 }

slbNewCfgPortSlbIdslbState OBJECT-TYPE
    SYNTAX  INTEGER {
        enabled(1),
        disabled(2),
        unsupported(2147483647)
        }
    MAX-ACCESS  read-write
    STATUS  current
    DESCRIPTION
        "Enable or disable Intrusion Detection server load balancing."
    ::= { slbNewCfgPortEntry 8 }


slbNewCfgPortSlbFilter OBJECT-TYPE
    SYNTAX  INTEGER {
        enabled(1),
        disabled(2),
        unsupported(2147483647)
        }
    MAX-ACCESS  read-write
    STATUS  current
    DESCRIPTION
        "Enable or disable Filtering."
    ::= { slbNewCfgPortEntry 10 }

slbNewCfgPortSlbAddFilter OBJECT-TYPE
    SYNTAX  INTEGER (1..2048)
    MAX-ACCESS  read-write
    STATUS  current
    DESCRIPTION
         "Specify the Filter Number to be added to this Port table." 
    ::= { slbNewCfgPortEntry 11 }

slbNewCfgPortSlbRemFilter OBJECT-TYPE
    SYNTAX  INTEGER (1..2048)
    MAX-ACCESS  read-write
    STATUS  current
    DESCRIPTION
         "Specify the Filter Number to be deleted from this Port table."
    ::= { slbNewCfgPortEntry 12 }

slbNewCfgPortSlbServState OBJECT-TYPE
    SYNTAX  INTEGER {
        enabled(1),
            disabled(2),
        unsupported(2147483647)
    }
    MAX-ACCESS  read-write
    STATUS  current
    DESCRIPTION
        "Enable or disable Server Processing."
    ::= { slbNewCfgPortEntry 13 }

slbNewCfgPortSlbClntState OBJECT-TYPE
    SYNTAX  INTEGER {
        enabled(1),
            disabled(2),
        unsupported(2147483647)
    }
    MAX-ACCESS  read-write
    STATUS  current
    DESCRIPTION
        "Enable or disable Client Processing."
    ::= { slbNewCfgPortEntry 14 }

slbNewCfgPortSlbL3Filter OBJECT-TYPE
    SYNTAX  INTEGER {
        enabled(1),
        disabled(2),
        unsupported(2147483647)
        }
    MAX-ACCESS  read-write
    STATUS  current
    DESCRIPTION
        "Enable or disable Layer3 Filtering."
    ::= { slbNewCfgPortEntry 15 }

slbNewCfgPortSlbFilterBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { slbNewCfgPortEntry 16 }

slbNewCfgPortInterSwitchVlan OBJECT-TYPE
    SYNTAX  INTEGER (1..4090)
    MAX-ACCESS read-write 
    STATUS  current
    DESCRIPTION
        "VLAN for inter-switch processing."
    ::= { slbNewCfgPortEntry 17 }

slbNewCfgPortVlanBmap OBJECT-TYPE
    SYNTAX  OCTET STRING
    MAX-ACCESS  read-only
    STATUS  current
    DESCRIPTION
        "VLANs associated with this port.
         The VLANs are presented in a bitmap format.

         OCTET 1  OCTET 2  .....
         xxxxxxxx xxxxxxxx .....
         ||    || |_ VLAN 9
         ||    ||
         ||    ||___ VLAN 8
         ||    |____ VLAN 7
         ||      .    .   .
         ||_________ VLAN 2
         |__________ VLAN 1

         where x : 1 - VLAN is associated
                   0 - VLAN is not associated"
    ::= { slbNewCfgPortEntry 18 }

-- SLB General Configuration 

slbCurCfgGlobalControl OBJECT-TYPE
    SYNTAX  INTEGER { 
	enabled(2),
	disabled(3),
        unsupported(2147483647)
	}
    MAX-ACCESS  read-only
    STATUS  current
    DESCRIPTION
        "The global state of Server Load Balancing.
         Note:This mib is not supported for VX instance of Virtualization."
    ::= { slbGeneralCfg 1 }

slbNewCfgGlobalControl OBJECT-TYPE
    SYNTAX  INTEGER { 
        enabled(2),
        disabled(3),
        unsupported(2147483647)
        }
    MAX-ACCESS  read-write
    STATUS  current
    DESCRIPTION
        "The global state of Server Load Balancing.
         Note:This mib is not supported for VX instance of Virtualization."
    ::= { slbGeneralCfg 2 }

slbCurCfgImask OBJECT-TYPE
    SYNTAX  IpAddress
    MAX-ACCESS  read-only
    STATUS  current
    DESCRIPTION
        "The virtual and real IP address mask - corresponding to the
	 imask command of the slb configuration menu.
         Note:This mib is not supported for VX instance of Virtualization."
    ::= { slbGeneralCfg 3 }

slbNewCfgImask OBJECT-TYPE
    SYNTAX  IpAddress
    MAX-ACCESS  read-write
    STATUS  current
    DESCRIPTION
        "The virtual and real IP address mask - corresponding to the
         imask command of the slb configuration menu.
         Note:This mib is not supported for VX instance of Virtualization."
    ::= { slbGeneralCfg 4 }

slbCurCfgMnet OBJECT-TYPE
    SYNTAX  IpAddress
    MAX-ACCESS  read-only
    STATUS  current
    DESCRIPTION
        "The management network - corresponding to the mnet command of 
         the slb configuration menu.
         Note:This mib is not supported for VX instance of Virtualization."
    ::= { slbGeneralCfg 5 }

slbNewCfgMnet OBJECT-TYPE
    SYNTAX  IpAddress
    MAX-ACCESS  read-write
    STATUS  current
    DESCRIPTION
        "The management network - corresponding to the mnet command of 
         the slb configuration menu.
         Note:This mib is not supported for VX instance of Virtualization."
    ::= { slbGeneralCfg 6 }

slbCurCfgMmask OBJECT-TYPE
    SYNTAX  IpAddress
    MAX-ACCESS  read-only
    STATUS  current
    DESCRIPTION
        "The management subnet mask - corresponding to the mmask command 
         of the slb configuration menu.
         Note:This mib is not supported for VX instance of Virtualization."
    ::= { slbGeneralCfg 7 }

slbNewCfgMmask OBJECT-TYPE
    SYNTAX  IpAddress
    MAX-ACCESS  read-write
    STATUS  current
    DESCRIPTION
        "The management subnet mask - corresponding to the mmask command 
         of the slb configuration menu.
         Note:This mib is not supported for VX instance of Virtualization."
    ::= { slbGeneralCfg 8 }

slbCurCfgRadiusAuthenString OBJECT-TYPE
    SYNTAX  DisplayString (SIZE(0..32))
    MAX-ACCESS  read-only
    STATUS  current
    DESCRIPTION
        "The RADIUS authentication string.  The string is used for 
	 generating encrypted authentication string for RADIUS health check.
         Note:This mib is not supported for VX instance of Virtualization."
    ::= { slbGeneralCfg 9 }

slbNewCfgRadiusAuthenString OBJECT-TYPE
    SYNTAX  DisplayString (SIZE(0..32))
    MAX-ACCESS  read-write
    STATUS  current
    DESCRIPTION
        "The RADIUS authentication string.  The string is used for 
	 generating encrypted authentication string for RADIUS health check.
         Note:This mib is not supported for VX instance of Virtualization."
    ::= { slbGeneralCfg 10 }

slbCurCfgDirectMode OBJECT-TYPE
    SYNTAX  INTEGER {
        enabled(1),
        disabled(2),
        unsupported(2147483647)
        }
    MAX-ACCESS  read-only
    STATUS  current
    DESCRIPTION
        "Enable or disable direct access mode. It allows direct access to 
         real servers and any combination of virtual and real servers 
         when set to enabled(1).
         Note:This mib is not supported for VX instance of Virtualization."
    ::= { slbGeneralCfg 11 }

slbNewCfgDirectMode OBJECT-TYPE
    SYNTAX  INTEGER {
        enabled(1),
        disabled(2),
        unsupported(2147483647)
        }
    MAX-ACCESS  read-write
    STATUS  current
    DESCRIPTION
        "Enable or disable direct access mode. It allows direct access to 
         real servers and any combination of virtual and real servers 
         when set to enabled(1).
         Note:This mib is not supported for VX instance of Virtualization."
    ::= { slbGeneralCfg 12 }

slbCurCfgPmask OBJECT-TYPE
    SYNTAX  IpAddress
    MAX-ACCESS  read-only
    STATUS  current
    DESCRIPTION
        "The persistent mask - corresponding to the pmask command of the 
         slb configuration menu.
         Note:This mib is not supported for VX instance of Virtualization."
    ::= { slbGeneralCfg 13 }

slbNewCfgPmask OBJECT-TYPE
    SYNTAX  IpAddress
    MAX-ACCESS  read-write
    STATUS  current
    DESCRIPTION
        "The persistent mask - corresponding to the pmask command of the 
         slb configuration menu.
         Note:This mib is not supported for VX instance of Virtualization."
    ::= { slbGeneralCfg 14 }

slbCurCfgGrace OBJECT-TYPE
    SYNTAX  INTEGER {
        enabled(1),
        disabled(2),
        unsupported(2147483647)
        }
    MAX-ACCESS  read-only
    STATUS  current
    DESCRIPTION
        "Enable or disable graceful server failure. It allows to keep the 
         connection to the failure real servers when set to enabled(1).
         Note:This mib is not supported for VX instance of Virtualization."
    ::= { slbGeneralCfg 15 }

slbNewCfgGrace OBJECT-TYPE
    SYNTAX  INTEGER {
        enabled(1),
        disabled(2),
        unsupported(2147483647)
                }
    MAX-ACCESS  read-write
    STATUS  current
    DESCRIPTION
        "Enable or disable graceful server failure. It allows to keep the 
         connection to the failure real servers when set to enabled(1).
         Note:This mib is not supported for VX instance of Virtualization."
    ::= { slbGeneralCfg 16 }

slbCurCfgVirtMatrixArch OBJECT-TYPE
    SYNTAX  INTEGER {
        enabled(1),
        disabled(2),
        unsupported(2147483647)
        }
    MAX-ACCESS  read-only
    STATUS  current
    DESCRIPTION
        "Enable or disable Virtual Matrix Architecture.
         Note:This mib is not supported for VX instance of Virtualization."
    ::= { slbGeneralCfg 17 }

slbNewCfgVirtMatrixArch OBJECT-TYPE
    SYNTAX  INTEGER {
        enabled(1),
        disabled(2),
        unsupported(2147483647)
        }
    MAX-ACCESS  read-write
    STATUS  current
    DESCRIPTION
        "Enable or disable Virtual Matrix Architecture.
         Note:This mib is not supported for VX instance of Virtualization."
    ::= { slbGeneralCfg 18 }

slbCurCfgFastage OBJECT-TYPE
    SYNTAX  INTEGER (0..7) 
    MAX-ACCESS  read-only
    STATUS  current 
    DESCRIPTION
        "Session table fast-age (1 sec) period bit shift. 2^(0-7) means (1,2,4,8,16,32,64,128).
         Note:This mib is not supported for VX instance of Virtualization."
    ::= { slbGeneralCfg 19 }

slbNewCfgFastage OBJECT-TYPE
    SYNTAX  INTEGER (0..7) 
    MAX-ACCESS  read-write
    STATUS  current 
    DESCRIPTION
        "Session table fast-age (1 sec) period bit shift. 2^(0-7) means (1,2,4,8,16,32,64,128).
         Note:This mib is not supported for VX instance of Virtualization."
    ::= { slbGeneralCfg 20 }

slbCurCfgSlowage OBJECT-TYPE
    SYNTAX  INTEGER (0..15) 
    MAX-ACCESS  read-only
    STATUS  obsolete
    DESCRIPTION
        "Session table slow-age (2 min) period bit shift. 2^(0-13) means (1,2,4,8,16,32 ...).
         Note:This mib is not supported for VX instance of Virtualization."
    ::= { slbGeneralCfg 21 }

slbNewCfgSlowage OBJECT-TYPE
    SYNTAX  INTEGER (0..15) 
    MAX-ACCESS  read-write
    STATUS  obsolete
    DESCRIPTION
        "Session table slow-age (2 min) period bit shift. 2^(0-13) means (1,2,4,8,16,32 ...).
         Note:This mib is not supported for VX instance of Virtualization."
    ::= { slbGeneralCfg 22 }

slbCurCfgTpcp OBJECT-TYPE
    SYNTAX  INTEGER {
        enabled(1),
        disabled(2),
        unsupported(2147483647)
        }
    MAX-ACCESS  read-only
    STATUS  current
    DESCRIPTION
        "Enable or disable Transparent Proxy Cache Protocol.
         Note:This mib is not supported for VX instance of Virtualization."
    ::= { slbGeneralCfg 23 }

slbNewCfgTpcp OBJECT-TYPE
    SYNTAX  INTEGER {
        enabled(1),
        disabled(2),
        unsupported(2147483647)
        }
    MAX-ACCESS  read-write
    STATUS  current
    DESCRIPTION
        "Enable or disable Transparent Proxy Cache Protocol.
         Note:This mib is not supported for VX instance of Virtualization."
    ::= { slbGeneralCfg 24 }

slbCurCfgMetricInterval OBJECT-TYPE
    SYNTAX  INTEGER (1..256) 
    MAX-ACCESS  read-only
    STATUS  current
    DESCRIPTION
        "The interval of response and bandwidth metric updates.
         Note:This mib is not supported for VX instance of Virtualization."
    ::= { slbGeneralCfg 25 }

slbNewCfgMetricInterval OBJECT-TYPE
    SYNTAX  INTEGER (1..256) 
    MAX-ACCESS  read-write
    STATUS  current
    DESCRIPTION
        "The interval of response and bandwidth metric updates.
         Note:This mib is not supported for VX instance of Virtualization."
    ::= { slbGeneralCfg 26 }

slbCurCfgLdapVersion OBJECT-TYPE
    SYNTAX  INTEGER {
	version2(1),
	version3(2),
        unsupported(2147483647)
    } 
    MAX-ACCESS  read-only
    STATUS  current
    DESCRIPTION
        "The version number for LDAP.
         Note:This mib is not supported for VX instance of Virtualization."
    ::= { slbGeneralCfg 27 }

slbNewCfgLdapVersion OBJECT-TYPE
    SYNTAX  INTEGER {
	version2(1),
	version3(2),
        unsupported(2147483647)
    } 
    MAX-ACCESS  read-write
    STATUS  current
    DESCRIPTION
        "The Version number of LDAP.
         Note:This mib is not supported for VX instance of Virtualization."
    ::= { slbGeneralCfg 28 }

slbCurCfgAllowHttpHc OBJECT-TYPE
    SYNTAX  INTEGER {
	enabled(1),
	disabled(2),
        unsupported(2147483647)
    } 
    MAX-ACCESS  read-only
    STATUS  current
    DESCRIPTION
        "Enable or disable allow HTTP health check on any port.
         If disabled the non-HTTP virtual services will use TCP Health Checks,
         if enabled the HTTP Content Health Check will be sent to any port 
         except HTTPS (443) if properly configured.
         Note:This mib is not supported for VX instance of Virtualization."
    ::= { slbGeneralCfg 29 }

slbNewCfgAllowHttpHc OBJECT-TYPE
    SYNTAX  INTEGER {
	enabled(1),
	disabled(2),
        unsupported(2147483647)
    } 
    MAX-ACCESS  read-write
    STATUS  current
    DESCRIPTION
        "Enable or disable allow HTTP health check on any port.
         If disabled the non-HTTP virtual services will use TCP Health Checks,
         if enabled the HTTP Content Health Check will be sent to any port 
         except HTTPS (443) if properly configured.
         Note:This mib is not supported for VX instance of Virtualization."
    ::= { slbGeneralCfg 30 }

slbCurCfgSubmac OBJECT-TYPE
    SYNTAX  INTEGER {
        enabled(1),
        disabled(2),
        unsupported(2147483647) 
        }
    MAX-ACCESS  read-only
    STATUS  current
    DESCRIPTION
        "Enable or disable Source MAC Address substitution.
         Enabling this feature supercedes individual real server
         setting for Source MAC Address substitution.
         Note:This mib is not supported for VX instance of Virtualization."
    ::= { slbGeneralCfg 31 }

slbNewCfgSubmac OBJECT-TYPE
    SYNTAX  INTEGER {
        enabled(1),
        disabled(2),
        unsupported(2147483647)
        }
    MAX-ACCESS  read-write
    STATUS  current
    DESCRIPTION
        "Enable or disable Source MAC Address substitution.
         Enabling this feature supercedes individual real server
         setting for Source MAC Address substitution.
         Note:This mib is not supported for VX instance of Virtualization."
    ::= { slbGeneralCfg 32 }

slbCurCfgProxyGratArp OBJECT-TYPE
    SYNTAX  INTEGER {
        enabled(1),
        disabled(2),
        unsupported(2147483647)
        }
    MAX-ACCESS  read-only
    STATUS  obsolete
    DESCRIPTION
        "Enable or disable Proxy IP Gratuitous ARP.
         Note:This mib is not supported for VX instance of Virtualization."
    ::= { slbGeneralCfg 33 }

slbNewCfgProxyGratArp OBJECT-TYPE
    SYNTAX  INTEGER {
        enabled(1),
        disabled(2),
        unsupported(2147483647)
        }
    MAX-ACCESS  read-write
    STATUS  obsolete
    DESCRIPTION
        "Enable or disable Proxy IP Gratuitous ARP.
         Note:This mib is not supported for VX instance of Virtualization."
    ::= { slbGeneralCfg 34 }

slbCurCfgRtsVlan OBJECT-TYPE
    SYNTAX  INTEGER {
        enabled(1),
        disabled(2),
        unsupported(2147483647)
        }
    MAX-ACCESS  read-only
    STATUS  current
    DESCRIPTION
        "Enable or disable use VLAN info for real server lookup. In case of Enabled, lookup will be performed by
         MAC and VLAN, in case of Disabled, only by MAC.
         Note:This mib is not supported for VX instance of Virtualization."
    ::= { slbGeneralCfg 35 }

slbNewCfgRtsVlan OBJECT-TYPE
    SYNTAX  INTEGER {
        enabled(1),
        disabled(2),
        unsupported(2147483647)
        }
    MAX-ACCESS  read-write
    STATUS  current
    DESCRIPTION
        "Enable or disable use VLAN info for real server lookup. In case of Enabled, lookup will be performed by
         MAC and VLAN, in case of Disabled, only by MAC.
         Note:This mib is not supported for VX instance of Virtualization."
    ::= { slbGeneralCfg 36 }

slbCurCfgVirtualServiceStats OBJECT-TYPE
    SYNTAX  INTEGER {
        enabled(1),
        disabled(2),
        unsupported(2147483647)
        }
    MAX-ACCESS  read-only
    STATUS  current
    DESCRIPTION
        "Enable/disable Virtual Service Statistics.
         Note:This mib is not supported for VX instance of Virtualization."
    ::= { slbGeneralCfg 37 }

slbNewCfgVirtualServiceStats OBJECT-TYPE
    SYNTAX  INTEGER {
        enabled(1),
        disabled(2),
        unsupported(2147483647)
                }
    MAX-ACCESS  read-write
    STATUS  current
    DESCRIPTION
        "Enable/disable Virtual Service Statistics.
         Note:This mib is not supported for VX instance of Virtualization."
 ::= { slbGeneralCfg 38 }

slbCurCfgSlbSessAtkIntrval OBJECT-TYPE
    SYNTAX  INTEGER (0..3600)
    MAX-ACCESS  read-only
    STATUS  current
    DESCRIPTION
        "Set SLB session attack inspection interval.
         Note:This mib is not supported for VX instance of Virtualization."
    ::= { slbGeneralCfg 39 }

slbNewCfgSlbSessAtkIntrval OBJECT-TYPE
    SYNTAX  INTEGER (0..3600)
    MAX-ACCESS  read-write
    STATUS  current
    DESCRIPTION
        "Set SLB session attack inspection interval.
         Note:This mib is not supported for VX instance of Virtualization."
 ::= { slbGeneralCfg 40 }

slbCurCfgSlbSessAtkAllowlim OBJECT-TYPE
    SYNTAX  INTEGER
    MAX-ACCESS  read-only
    STATUS  current
    DESCRIPTION
        "Set SLB session attack alert allowable limit.
         Note:This mib is not supported for VX instance of Virtualization."
    ::= { slbGeneralCfg 41 }

slbNewCfgSlbSessAtkAllowlim OBJECT-TYPE
    SYNTAX  INTEGER
    MAX-ACCESS  read-write
    STATUS  current
    DESCRIPTION
        "Set SLB session attack alert allowable limit.
         Note:This mib is not supported for VX instance of Virtualization."
 ::= { slbGeneralCfg 42 }

slbCurCfgNewSlowage OBJECT-TYPE
    SYNTAX  INTEGER (0..14) 
    MAX-ACCESS  read-only
    STATUS  current
    DESCRIPTION
        "Session table slow-age (2 min) period bit shift.
         Note:This mib is not supported for VX instance of Virtualization."
    ::= { slbGeneralCfg 43 }

slbNewCfgNewSlowage OBJECT-TYPE
    SYNTAX  INTEGER (0..14) 
    MAX-ACCESS  read-write
    STATUS  current
    DESCRIPTION
        "Session table slow-age (2 min) period bit shift.
         Note:This mib is not supported for VX instance of Virtualization."
    ::= { slbGeneralCfg 44 }
    
slbCurCfgPortBind OBJECT-TYPE
    SYNTAX  INTEGER {
        enabled(1),
        disabled(2),
        unsupported(2147483647)
        }
    MAX-ACCESS  read-only
    STATUS  current
    DESCRIPTION
        "Enable/disable ingress port for session table Binding. SP uses
         ingress port for session lookup when set to enable.
         Note:This mib is not supported for VX instance of Virtualization."
    ::= { slbGeneralCfg 45 }

slbNewCfgPortBind OBJECT-TYPE
    SYNTAX  INTEGER {
        enabled(1),
        disabled(2),
        unsupported(2147483647)
                }
    MAX-ACCESS  read-write
    STATUS  current
    DESCRIPTION
        "Enable/disable ingress port for session table Binding. SP uses
         ingress port for session lookup when set to enable. (1)-Include, (2)-Exclude.
         Note:This mib is not supported for VX instance of Virtualization."
 ::= { slbGeneralCfg 46 }

slbCurCfgVmaSrcPort OBJECT-TYPE
    SYNTAX  INTEGER {
        enabled(1),
        disabled(2),
        unsupported(2147483647)
        }
    MAX-ACCESS  read-only
    STATUS  current
    DESCRIPTION
       "Enable/disable VMA source port.
        Note:This mib is not supported for VX instance of Virtualization."
 ::= { slbGeneralCfg 47 }

slbNewCfgVmaSrcPort OBJECT-TYPE
    SYNTAX  INTEGER {
        enabled(1),
        disabled(2)
        }
    MAX-ACCESS  read-write
    STATUS  current
    DESCRIPTION
        "Enable/disable VMA source port. (1)-Source IP + port, (2)-Source IP only.
         Note:This mib is not supported for VX instance of Virtualization."
 ::= { slbGeneralCfg 48 }
 
slbCurCfgIpTcpCksum OBJECT-TYPE
    SYNTAX  INTEGER {
        enabled(1),
        disabled(2),
        unsupported(2147483647)
        }
    MAX-ACCESS  read-only
    STATUS  current
    DESCRIPTION
        "Enable/disable Layer 7 IP/TCP Checksum Validation.
         Note:This mib is not supported for VX instance of Virtualization."
    ::= { slbGeneralCfg 49 }

slbNewCfgIpTcpCksum OBJECT-TYPE
    SYNTAX  INTEGER {
        enabled(1),
        disabled(2),
        unsupported(2147483647)
                }
    MAX-ACCESS  read-write
    STATUS  current
    DESCRIPTION
        "Enable/disable Layer 7 IP/TCP Checksum Validation.
         Note:This mib is not supported for VX instance of Virtualization."
 ::= { slbGeneralCfg 50 }

slbCurCfgAuxRipHash OBJECT-TYPE
    SYNTAX  INTEGER {
    	enabled(1),
	disabled(2),
        unsupported(2147483647)
	}
    MAX-ACCESS  read-only
    STATUS  current
    DESCRIPTION
    	"Enable/disable Include RIP in AUX table hashing.
         Note:This mib is not supported for VX instance of Virtualization."
    ::= { slbGeneralCfg 51 }

slbNewCfgAuxRipHash OBJECT-TYPE
    SYNTAX  INTEGER {
	enabled(1),
	disabled(2),
        unsupported(2147483647)
	}
    MAX-ACCESS  read-write
    STATUS  current
    DESCRIPTION
	"Enable/disable Include RIP in AUX table hashing.
         Note:This mib is not supported for VX instance of Virtualization."
    ::= { slbGeneralCfg 52 }

slbCurCfgClearBackup OBJECT-TYPE
    SYNTAX  INTEGER {
        enabled(1),
        disabled(2),
        unsupported(2147483647)
    }
    MAX-ACCESS  read-only
    STATUS  current
    DESCRIPTION
        "Enable/Disable clear backup in the current config.
         Note:This mib is not supported for VX instance of Virtualization."
    ::= { slbGeneralCfg 53 }

slbNewCfgClearBackup OBJECT-TYPE
    SYNTAX  INTEGER {
        enabled(1),
        disabled(2),
        unsupported(2147483647)
    }
    MAX-ACCESS  read-write
    STATUS  current
    DESCRIPTION
        "Enable/Disable clear backup in the new config.(1)-Clear on Master resume, (2)-Keep on Master resume.
         Note:This mib is not supported for VX instance of Virtualization."
    ::= { slbGeneralCfg 54 }

slbCurCfgmStat OBJECT-TYPE
    SYNTAX  INTEGER (1..3600)
    MAX-ACCESS  read-only
    STATUS  current
    DESCRIPTION
        "Measuring period for Acceleration, HTTP and 
         SSL offloading statistics in the current config.
         Note:This mib is not supported for VX instance of Virtualization."
    ::= { slbGeneralCfg 55 }

slbNewCfgmStat OBJECT-TYPE
    SYNTAX  INTEGER (1..3600)
    MAX-ACCESS  read-write
    STATUS  current
    DESCRIPTION
        "Measuring period for Acceleration, HTTP and
         SSL offloading statistics in the new config.
         Note:This mib is not supported for VX instance of Virtualization."
    ::= { slbGeneralCfg 56 }

slbCurCfgvStat OBJECT-TYPE
    SYNTAX  INTEGER {
        enabled(1),
        disabled(2),
        unsupported(2147483647)
    }
    MAX-ACCESS  read-only
    STATUS  current
    DESCRIPTION
        "Enable/Disable Virtual Service 
         Statistics in the current config.
         Note:This mib is not supported for VX instance of Virtualization."
    ::= { slbGeneralCfg 57 }

slbNewCfgvStat OBJECT-TYPE
    SYNTAX  INTEGER {
        enabled(1),
        disabled(2),
        unsupported(2147483647)
    }
    MAX-ACCESS  read-write
    STATUS  current
    DESCRIPTION
        "Enable/Disable Virtual Service 
         Statistics in the new config.
         Note:This mib is not supported for VX instance of Virtualization."
    ::= { slbGeneralCfg 58 }

slbCurCfgVmaDip OBJECT-TYPE
    SYNTAX  INTEGER {
        enabled(1),
        disabled(2),
        unsupported(2147483647)
    }
    MAX-ACCESS  read-only
    STATUS  current
    DESCRIPTION
        "Enable/Disable VMA with destination IP
         in the current config.
         Note:This mib is not supported for VX instance of Virtualization."
    ::= { slbGeneralCfg 59 }

slbNewCfgVmaDip OBJECT-TYPE
    SYNTAX  INTEGER {
        enabled(1),
        disabled(2),
        unsupported(2147483647)
    }
    MAX-ACCESS  read-write
    STATUS  current
    DESCRIPTION
        "Enable/Disable VMA with destination IP
         in the new config.
         Note:This mib is not supported for VX instance of Virtualization."
    ::= { slbGeneralCfg 60 }

slbCurCfgClsRst OBJECT-TYPE
    SYNTAX  INTEGER {
        enabled(1),
        disabled(2),
        unsupported(2147483647)
    }
    MAX-ACCESS  read-only
    STATUS  current
    DESCRIPTION
        "Enable/Disable Session clear on RST
         in the current config.
         Note:This mib is not supported for VX instance of Virtualization."
    ::= { slbGeneralCfg 61 }

slbNewCfgClsRst OBJECT-TYPE
    SYNTAX  INTEGER {
        enabled(1),
        disabled(2),
        unsupported(2147483647)
    }
    MAX-ACCESS  read-write
    STATUS  current
    DESCRIPTION
        "Enable/Disable Session clear on RST. in the new config. (1)-clear, (2)-fastage.
         Note:This mib is not supported for VX instance of Virtualization."
    ::= { slbGeneralCfg 62 }

slbCurCfgRtsIpLkp OBJECT-TYPE
    SYNTAX  INTEGER {
        enabled(1),
        disabled(2),
        unsupported(2147483647)
    }
    MAX-ACCESS  read-only
    STATUS  current
    DESCRIPTION
        "Enable/Disable RTS-IP lookup in the current config.
         Note:This mib is not supported for VX instance of Virtualization."
    ::= { slbGeneralCfg 63 }

slbNewCfgRtsIpLkp OBJECT-TYPE
    SYNTAX  INTEGER {
        enabled(1),
        disabled(2),
        unsupported(2147483647)
    }
    MAX-ACCESS  read-write
    STATUS  current
    DESCRIPTION
        "Enable/Disable RTS-IP lookup in the new config.
         Note:This mib is not supported for VX instance of Virtualization."
    ::= { slbGeneralCfg 64 }

slbCurCfgPprefix OBJECT-TYPE
    SYNTAX  INTEGER (1..128)
    MAX-ACCESS  read-only
    STATUS  current
    DESCRIPTION
        "The ipv6 persistent prefix length - corresponding to the pmask command of the 
         slb configuration menu.
         Note:This mib is not supported for VX instance of Virtualization."
    ::= { slbGeneralCfg 65 }

slbNewCfgPprefix OBJECT-TYPE
    SYNTAX  INTEGER (1..128)
    MAX-ACCESS  read-write
    STATUS  current
    DESCRIPTION
        "The ipv6 persistent prefix length - corresponding to the pmask command of the 
         slb configuration menu.
         Note:This mib is not supported for VX instance of Virtualization."
    ::= { slbGeneralCfg 66 }

slbCurCfgSubdmac OBJECT-TYPE
    SYNTAX  INTEGER {
        enabled(1),
        disabled(2),
        unsupported(2147483647)
    }
    MAX-ACCESS  read-only
    STATUS  current
    DESCRIPTION
        "Enable or disable DMAC substitution.
         Enabling this feature supercedes individual real server
         setting for DMAC substitution.
         Note:This mib is not supported for VX instance of Virtualization."
    ::= { slbGeneralCfg 67 }

slbNewCfgSubdmac OBJECT-TYPE
    SYNTAX  INTEGER {
        enabled(1),
        disabled(2),
        unsupported(2147483647)
    }
    MAX-ACCESS  read-write
    STATUS  current
    DESCRIPTION
        "Enable or disable DMAC substitution.
         Enabling this feature supercedes individual real server
         setting for DMAC substitution.
         Note:This mib is not supported for VX instance of Virtualization."
    ::= { slbGeneralCfg 68 }

slbCurCfgpVlanTag OBJECT-TYPE
    SYNTAX  INTEGER {
        enabled(1),
        disabled(2),
        unsupported(2147483647)
    }
    MAX-ACCESS  read-only
    STATUS  current
    DESCRIPTION
        "Enable or disable preserving vlan tag during packet forwarding.
         Note:This mib is not supported for VX instance of Virtualization."
    ::= { slbGeneralCfg 69 }

slbNewCfgpVlanTag OBJECT-TYPE
    SYNTAX  INTEGER {
        enabled(1),
        disabled(2),
        unsupported(2147483647)
    }
    MAX-ACCESS  read-write
    STATUS  current
    DESCRIPTION
        "Enable or disable preserving vlan tag during packet forwarding.
         Note:This mib is not supported for VX instance of Virtualization."
    ::= { slbGeneralCfg 70 }

slbCurCfgNmask OBJECT-TYPE
    SYNTAX  IpAddress
    MAX-ACCESS  read-only
    STATUS  current
    DESCRIPTION
        "The session mask in the current config block.
         Note:This mib is not supported for VX instance of Virtualization."
    ::= { slbGeneralCfg 71 }

slbNewCfgNmask OBJECT-TYPE
    SYNTAX  IpAddress
    MAX-ACCESS  read-write
    STATUS  current
    DESCRIPTION
        "The session mask in the new config block.
         Note:This mib is not supported for VX instance of Virtualization."
    ::= { slbGeneralCfg 72 }

slbCurCfgSessRevive OBJECT-TYPE
    SYNTAX  INTEGER {
        enabled(1),
        disabled(2),
        unsupported(2147483647)
        }
    MAX-ACCESS  read-only
    STATUS  current
    DESCRIPTION
        "Enable/disable session drop when fastage.
         Note:This mib is not supported for VX instance of Virtualization."
    ::= { slbGeneralCfg 73 }

slbNewCfgSessRevive OBJECT-TYPE
    SYNTAX  INTEGER {
        enabled(1),
        disabled(2),
        unsupported(2147483647)
        }
    MAX-ACCESS  read-write
    STATUS  current
    DESCRIPTION
        "Enable/disable session drop when fastage.
         Note:This mib is not supported for VX instance of Virtualization."
    ::= { slbGeneralCfg 74 }

slbCurCfgSipSpat OBJECT-TYPE
    SYNTAX  INTEGER {
        enabled(1),
        disabled(2),
        unsupported(2147483647)
        }
    MAX-ACCESS  read-only
    STATUS  current
    DESCRIPTION
        "Enable/disable SIP SPAT.
         Note:This mib is not supported for VX instance of Virtualization."
    ::= { slbGeneralCfg 75 }

slbNewCfgSipSpat OBJECT-TYPE
    SYNTAX  INTEGER {
        enabled(1),
        disabled(2),
        unsupported(2147483647)
        }
    MAX-ACCESS  read-write
    STATUS  current
    DESCRIPTION
        "Enable/disable SIP SPAT.
         Note:This mib is not supported for VX instance of Virtualization."
    ::= { slbGeneralCfg 76 }

slbCurCfgSlbFilterParseLen OBJECT-TYPE
    SYNTAX  INTEGER (0..18200)
    MAX-ACCESS  read-only
    STATUS  current
    DESCRIPTION
        "Set buffer length for filter content based classification.
         Note:This mib is not supported for VX instance of Virtualization."
 ::= { slbGeneralCfg 77 }

slbNewCfgSlbFilterParseLen OBJECT-TYPE
    SYNTAX  INTEGER (0..18200)
    MAX-ACCESS  read-write
    STATUS  current
    DESCRIPTION
        "Set buffer length for filter content based classification.
         Note:This mib is not supported for VX instance of Virtualization."
 ::= { slbGeneralCfg 78 }

slbCurCfgServDown OBJECT-TYPE
    SYNTAX  INTEGER {
        route(1),
        drop(2),
        unsupported(2147483647)
    }
    MAX-ACCESS  read-only
    STATUS  current
    DESCRIPTION
    "Route/drop Service down Behavior.
     Note:This mib is not supported for VX instance of Virtualization."
 ::= { slbGeneralCfg 79 }

slbNewCfgServDown OBJECT-TYPE
    SYNTAX  INTEGER {
        route(1),
        drop(2),
        unsupported(2147483647)
    }
    MAX-ACCESS  read-write
    STATUS  current
    DESCRIPTION
    "Route/drop Service down Behavior.
     Note:This mib is not supported for VX instance of Virtualization."
 ::= { slbGeneralCfg 80 }

slbCurCfgSlbFtpDataSessAge OBJECT-TYPE
    SYNTAX  INTEGER (0..5)
    MAX-ACCESS  read-only
    STATUS  current
    DESCRIPTION
        "Set FTP Data session age.
         Note:This mib is not supported for VX instance of Virtualization."
 ::= { slbGeneralCfg 81 }

slbNewCfgSlbFtpDataSessAge OBJECT-TYPE
    SYNTAX  INTEGER (0..5)
    MAX-ACCESS  read-write
    STATUS  current
    DESCRIPTION
        "Set FTP Data session age.
         Note:This mib is not supported for VX instance of Virtualization."
 ::= { slbGeneralCfg 82 }


slbCurCfgSlbTcpRstSecSeqNumChk OBJECT-TYPE
    SYNTAX  INTEGER {
        enabled(1),
        disabled(2),
        unsupported(2147483647)
        }
    MAX-ACCESS  read-only
    STATUS  current
    DESCRIPTION
        "Enable/disable TCP RST Secure Sequence Number Check.
         Note:This mib is not supported for VX instance of Virtualization."
    ::= { slbGeneralCfg 83 }

slbNewCfgSlbTcpRstSecSeqNumChk OBJECT-TYPE
    SYNTAX  INTEGER {
        enabled(1),
        disabled(2),
        unsupported(2147483647)
        }
    MAX-ACCESS  read-write
    STATUS  current
    DESCRIPTION
        "Enable/disable TCP RST Secure Sequence Number Check.
         Note:This mib is not supported for VX instance of Virtualization."
    ::= { slbGeneralCfg 84 }

slbCurCfgSlbSrvCkData OBJECT-TYPE
    SYNTAX  INTEGER {
        enabled(1),
        disabled(2),
        unsupported(2147483647)
        }
    MAX-ACCESS  read-only
    STATUS  current
    DESCRIPTION
        "Enable/disable server return data check.
         Note:This mib is not supported for VX instance of Virtualization."
    ::= { slbGeneralCfg 85 }

slbNewCfgSlbSrvCkData OBJECT-TYPE
    SYNTAX  INTEGER {
        enabled(1),
        disabled(2),
        unsupported(2147483647)
        }
    MAX-ACCESS  read-write
    STATUS  current
    DESCRIPTION
        "Enable/disable server return data check.
         Note:This mib is not supported for VX instance of Virtualization."
    ::= { slbGeneralCfg 86 }

slbCurCfgSlbSessVpt OBJECT-TYPE
    SYNTAX  INTEGER {
        enabled(1),
        disabled(2),
        unsupported(2147483647)
        }
    MAX-ACCESS  read-only
    STATUS  current
    DESCRIPTION
        "Enable/disable session VPT update.
         Note:This mib is not supported for VX instance of Virtualization."
    ::= { slbGeneralCfg 87 }

slbNewCfgSlbSessVpt OBJECT-TYPE
    SYNTAX  INTEGER {
        enabled(1),
        disabled(2),
        unsupported(2147483647)
        }
    MAX-ACCESS  read-write
    STATUS  current
    DESCRIPTION
        "Enable/disable session VPT update.
         Note:This mib is not supported for VX instance of Virtualization."
    ::= { slbGeneralCfg 88 }

slbCurCfgSlbMilliSecResolution OBJECT-TYPE
    SYNTAX  INTEGER {
        enabled(1),
        disabled(2),
        unsupported(2147483647)
        }
    MAX-ACCESS  read-only
    STATUS  current
    DESCRIPTION
        "Enable/disable millisecond resolution for timers.
         Note:This mib is not supported for VX instance of Virtualization."
    ::= { slbGeneralCfg 89 }

slbNewCfgSlbMilliSecResolution OBJECT-TYPE
    SYNTAX  INTEGER {
        enabled(1),
        disabled(2),
        unsupported(2147483647)
        }
    MAX-ACCESS  read-write
    STATUS  current
    DESCRIPTION
        "Enable/disable millisecond resolution for timers.
         Note:This mib is not supported for VX instance of Virtualization."
    ::= { slbGeneralCfg 90 }

slbCurCfgSlbVmacBkp OBJECT-TYPE
    SYNTAX  INTEGER {
        enabled(1),
        disabled(2),
        unsupported(2147483647)
        }
    MAX-ACCESS  read-only
    STATUS  current
    DESCRIPTION
        "Enable/Disable VMAC use on backup switch.
         Note:This mib is not supported for VX instance of Virtualization."
    ::= { slbGeneralCfg 91 }

slbNewCfgSlbVmacBkp OBJECT-TYPE
    SYNTAX  INTEGER {
        enabled(1),
        disabled(2),
        unsupported(2147483647)
        }
    MAX-ACCESS  read-write
    STATUS  current
    DESCRIPTION
        "Enable/Disable VMAC use on backup switch.
         Note:This mib is not supported for VX instance of Virtualization."
    ::= { slbGeneralCfg 92 }


slbCurCfgSlbFmrPort OBJECT-TYPE
    SYNTAX  INTEGER {
        enabled(1),
        disabled(2),
        unsupported(2147483647)
        }
    MAX-ACCESS  read-only
    STATUS  current
    DESCRIPTION
        "Enable/Disable fine tuning of multi RPORT LB.
         Note:This mib is not supported for VX instance of Virtualization."
    ::= { slbGeneralCfg 93 }

slbNewCfgSlbFmrPort OBJECT-TYPE
    SYNTAX  INTEGER {
        enabled(1),
        disabled(2),
        unsupported(2147483647)
        }
    MAX-ACCESS  read-write
    STATUS  current
    DESCRIPTION
        "Enable/Disable fine tuning of multi RPORT LB.
         Note:This mib is not supported for VX instance of Virtualization."
    ::= { slbGeneralCfg 94 }

slbCurCfgSlbEnhance OBJECT-TYPE
    SYNTAX  INTEGER {
        enabled(1),
        disabled(2),
        unsupported(2147483647)
        }
    MAX-ACCESS  read-only
    STATUS  current
    DESCRIPTION
        "Enable/Disable URL string rebind over cookie.
         Note:This mib is not supported for VX instance of Virtualization."
    ::= { slbGeneralCfg 95 }

slbNewCfgSlbEnhance OBJECT-TYPE
    SYNTAX  INTEGER {
        enabled(1),
        disabled(2),
        unsupported(2147483647)
        }
    MAX-ACCESS  read-write
    STATUS  current
    DESCRIPTION
        "Enable/Disable URL string rebind over cookie.
         Note:This mib is not supported for VX instance of Virtualization."
    ::= { slbGeneralCfg 96 }

slbCurCfgNonHTTP OBJECT-TYPE
    SYNTAX  INTEGER {
        enabled(1),
        disabled(2),
        unsupported(2147483647)
        }
    MAX-ACCESS  read-only
    STATUS  current
    DESCRIPTION
        "Enable or disable Send non-HTTP traffic for filters.
         Note:This mib is not supported for VX instance of Virtualization."
    ::= { slbGeneralCfg 97 }

slbNewCfgNonHTTP OBJECT-TYPE
    SYNTAX  INTEGER {
        enabled(1),
        disabled(2),
        unsupported(2147483647)
        }
    MAX-ACCESS  read-write
    STATUS  current
    DESCRIPTION
        "Enable or disable Send non-HTTP traffic for filters.
         Note:This mib is not supported for VX instance of Virtualization."
    ::= { slbGeneralCfg 98 }

slbCurCfgSlbSlntcls OBJECT-TYPE
    SYNTAX  INTEGER {
        enabled(1),
        disabled(2),
        unsupported(2147483647)
        }
    MAX-ACCESS  read-only
    STATUS  current
    DESCRIPTION
        "Enable/Disable silent TCP connection closure.
         Note:This mib is not supported for VX instance of Virtualization."
    ::= { slbGeneralCfg 99 }

slbNewCfgSlbSlntcls OBJECT-TYPE
    SYNTAX  INTEGER {
        enabled(1),
        disabled(2),
        unsupported(2147483647)
        }
    MAX-ACCESS  read-write
    STATUS  current
    DESCRIPTION
        "Enable/Disable silent TCP connection closure.
         Note:This mib is not supported for VX instance of Virtualization."
    ::= { slbGeneralCfg 100 }

slbCurCfgDrctRSS OBJECT-TYPE
    SYNTAX  INTEGER {
        enabled(1),
        disabled(2),
        unsupported(2147483647)
    }
    MAX-ACCESS  read-only
    STATUS  current
    DESCRIPTION
        "Enable/Disable Direct RSS
         in the current config.
         Note:This mib is supported only on VA Platform."
    ::= { slbGeneralCfg 101 }

slbNewCfgDrctRSS OBJECT-TYPE
    SYNTAX  INTEGER {
        enabled(1),
        disabled(2),
        unsupported(2147483647)
    }
    MAX-ACCESS  read-write
    STATUS  current
    DESCRIPTION
        "Enable/Disable Direct RSS
         in the new config.
         Note:This mib is supported only on VA Platform."
    ::= { slbGeneralCfg 102 }

    
slbCurCfgSlbSessTblCap OBJECT-TYPE
    SYNTAX  INTEGER (0..100)
    MAX-ACCESS  read-only
    STATUS  current
    DESCRIPTION
        "Get the session table size according to max (100%).
         Note:This mib is not supported for VX instance of Virtualization."
 ::= { slbGeneralCfg 103 }

slbNewCfgSlbSessTblCap OBJECT-TYPE
    SYNTAX  INTEGER (0..100)
    MAX-ACCESS  read-write
    STATUS  current
    DESCRIPTION
        "Set the session table size according to max (100%).
         Note:This mib is not supported for VX instance of Virtualization."
 ::= { slbGeneralCfg 104 }

slbCurCfgSlbDataTblCap OBJECT-TYPE
    SYNTAX  INTEGER (0..25)
    MAX-ACCESS  read-only
    STATUS  current
    DESCRIPTION
        "Percentage of AE memory currently allocated to data table.
         Note:This mib is not supported for VX instance of Virtualization."
 ::= { slbGeneralCfg 105 }

slbNewCfgSlbDataTblCap OBJECT-TYPE
    SYNTAX  INTEGER (0..25)
    MAX-ACCESS  read-write
    STATUS  current
    DESCRIPTION
        " Percentage of AE memory to be allocated to data table after reboot.
          Note:This mib is not supported for VX instance of Virtualization."
 ::= { slbGeneralCfg 106 }


-- FQDN Server configuration New

slbFQDNServer   OBJECT IDENTIFIER ::= { slbGeneralCfg 107 }   


slbNewCfgFQDNServerTable  OBJECT-TYPE
    SYNTAX  SEQUENCE OF SlbNewCfgFQDNServerEntry 
    MAX-ACCESS  not-accessible
    STATUS  current
    DESCRIPTION
        "The table of FQDN Real Server configuration in the new_config.
         Note:This mib is not supported for VX instance of Virtualization."
    ::= { slbFQDNServer 1 }
	
slbNewCfgFQDNServerEntry  OBJECT-TYPE
    SYNTAX  SlbNewCfgFQDNServerEntry 
    MAX-ACCESS  not-accessible
    STATUS  current
    DESCRIPTION
        "Information about a particular FQDN Server configuration.
         Note:This mib is not supported for VX instance of Virtualization."
    INDEX   { slbNewCfgFQDNServerIdIndex  }
    ::= { slbNewCfgFQDNServerTable 1 }

SlbNewCfgFQDNServerEntry ::= SEQUENCE {
    slbNewCfgFQDNServerIdIndex          DisplayString,
    slbNewCfgFQDNServerFQDN           DisplayString,
    slbNewCfgFQDNServerIpVers            	INTEGER,
    slbNewCfgFQDNServerTTL               	INTEGER,
    slbNewCfgFQDNServerGroup            DisplayString,
    slbNewCfgFQDNServerTempl            DisplayString,
    slbNewCfgFQDNServerState          	    INTEGER,
	slbNewCfgFQDNServerDelete          		INTEGER
    ,
    slbNewCfgFQDNServerMode          		INTEGER,
    slbNewCfgFQDNServerRGName          		DisplayString
}

slbNewCfgFQDNServerIdIndex OBJECT-TYPE
    SYNTAX DisplayString (SIZE(1..24))
    MAX-ACCESS  read-only
    STATUS  current
    DESCRIPTION
        "The Fqdn server index"
    ::= { slbNewCfgFQDNServerEntry 1 }

slbNewCfgFQDNServerFQDN OBJECT-TYPE
    SYNTAX DisplayString (SIZE(1..255))
    MAX-ACCESS  read-create
    STATUS  current
    DESCRIPTION
        "The Fqdn field of the server"
    ::= { slbNewCfgFQDNServerEntry 2 }

	slbNewCfgFQDNServerIpVers OBJECT-TYPE
    SYNTAX  INTEGER{
        ipv4(1),
        ipv6(2),
        unsupported(2147483647)
    }
    MAX-ACCESS  read-create
    STATUS  current
    DESCRIPTION
        "The type of IP address."
    ::= { slbNewCfgFQDNServerEntry 3 }

slbNewCfgFQDNServerTTL OBJECT-TYPE
    SYNTAX  INTEGER (1..35791394)
    MAX-ACCESS  read-create
    STATUS  current
    DESCRIPTION
        "minimum time to live."
    ::= { slbNewCfgFQDNServerEntry 4 }
	
slbNewCfgFQDNServerGroup OBJECT-TYPE
    SYNTAX  DisplayString (SIZE(0..255))
    MAX-ACCESS  read-create
    STATUS  current
    DESCRIPTION
        "FQDN Server Group Id."
    ::= { slbNewCfgFQDNServerEntry 5 }


	slbNewCfgFQDNServerTempl OBJECT-TYPE
    SYNTAX DisplayString (SIZE(1..255))
    MAX-ACCESS  read-create
    STATUS  current
    DESCRIPTION
        "Template Real Server Id."
    ::= { slbNewCfgFQDNServerEntry 6 }

	
	slbNewCfgFQDNServerState OBJECT-TYPE
    SYNTAX  INTEGER {
        enabled(2),
        disabled(3),
        unsupported(2147483647)
    }
    MAX-ACCESS  read-create
    STATUS  current
    DESCRIPTION
        "Enable or disable the server."
    ::= { slbNewCfgFQDNServerEntry 7 }


	slbNewCfgFQDNServerDelete OBJECT-TYPE
    SYNTAX  INTEGER {
        other(1),
        delete(2),
        unsupported(2147483647)
    }
    MAX-ACCESS  read-create
    STATUS  current
    DESCRIPTION
        "By setting the value to delete(2), the entire row is deleted."
    ::= { slbNewCfgFQDNServerEntry 8 }


slbNewCfgFQDNServerMode OBJECT-TYPE
    SYNTAX  INTEGER {
        fqdn(1),
        cscale(2),
        unsupported(2147483647)
    }
    MAX-ACCESS  read-create
    STATUS  current
    DESCRIPTION
        "Set the server mode to FQDN or Auto Scaling (Cloud platform)."
    ::= { slbNewCfgFQDNServerEntry 9 }


slbNewCfgFQDNServerRGName OBJECT-TYPE
    SYNTAX DisplayString (SIZE(1..255))
    MAX-ACCESS  read-create
    STATUS  current
    DESCRIPTION
        "Resource Group Name (Cloud platform)."
    ::= { slbNewCfgFQDNServerEntry 10 }

-- FQDN Server configuration Cur





slbCurCfgFQDNServerTable  OBJECT-TYPE
    SYNTAX  SEQUENCE OF SlbCurCfgFQDNServerEntry 
    MAX-ACCESS  not-accessible
    STATUS  current
    DESCRIPTION
        "The table of FQDN Real Server configuration in the Cur_config.
         Note:This mib is not supported for VX instance of Virtualization."
    ::= { slbFQDNServer 2 }
	
slbCurCfgFQDNServerEntry  OBJECT-TYPE
    SYNTAX  SlbCurCfgFQDNServerEntry 
    MAX-ACCESS  not-accessible
    STATUS  current
    DESCRIPTION
        "Information about a particular FQDN Server configuration.
         Note:This mib is not supported for VX instance of Virtualization."
    INDEX   { slbCurCfgFQDNServerIdIndex  }
    ::= { slbCurCfgFQDNServerTable 1 }

SlbCurCfgFQDNServerEntry ::= SEQUENCE {
    slbCurCfgFQDNServerIdIndex          DisplayString,
    slbCurCfgFQDNServerFQDN           DisplayString,
    slbCurCfgFQDNServerIpVers            	INTEGER,
    slbCurCfgFQDNServerTTL               	INTEGER,
    slbCurCfgFQDNServerGroup            DisplayString,
    slbCurCfgFQDNServerTempl            DisplayString,
    slbCurCfgFQDNServerState          	    INTEGER
    ,
    slbCurCfgFQDNServerMode                 INTEGER,
    slbCurCfgFQDNServerRGName               DisplayString
}

slbCurCfgFQDNServerIdIndex OBJECT-TYPE
    SYNTAX DisplayString (SIZE(1..24))
    MAX-ACCESS  read-only
    STATUS  current
    DESCRIPTION
        "The Fqdn server index"
    ::= { slbCurCfgFQDNServerEntry 1 }

slbCurCfgFQDNServerFQDN OBJECT-TYPE
    SYNTAX DisplayString (SIZE(1..255))
    MAX-ACCESS  read-only
    STATUS  current
    DESCRIPTION
        "The Fqdn field of the server"
    ::= { slbCurCfgFQDNServerEntry 2 }

	slbCurCfgFQDNServerIpVers OBJECT-TYPE
    SYNTAX  INTEGER{
        ipv4(1),
        ipv6(2),
        unsupported(2147483647)
    }
    MAX-ACCESS  read-only
    STATUS  current
    DESCRIPTION
        "The type of IP address."
    ::= { slbCurCfgFQDNServerEntry 3 }

slbCurCfgFQDNServerTTL OBJECT-TYPE
    SYNTAX  INTEGER (0..35791394)
    MAX-ACCESS  read-only
    STATUS  current
    DESCRIPTION
        "minimum time to live."
    ::= { slbCurCfgFQDNServerEntry 4 }
	
slbCurCfgFQDNServerGroup OBJECT-TYPE
    SYNTAX  DisplayString (SIZE(0..255))
    MAX-ACCESS  read-only
    STATUS  current
    DESCRIPTION
        "FQDN Server Group Id."
    ::= { slbCurCfgFQDNServerEntry 5 }


	slbCurCfgFQDNServerTempl OBJECT-TYPE
    SYNTAX DisplayString (SIZE(1..255))
    MAX-ACCESS  read-only
    STATUS  current
    DESCRIPTION
        "Template Real Server Id."
    ::= { slbCurCfgFQDNServerEntry 6 }

	
	slbCurCfgFQDNServerState OBJECT-TYPE
    SYNTAX  INTEGER {
        enabled(2),
        disabled(3),
        unsupported(2147483647)
    }
    MAX-ACCESS  read-only
    STATUS  current
    DESCRIPTION
        "Enable or disable the server."
    ::= { slbCurCfgFQDNServerEntry 7 }

slbCurCfgFQDNServerMode OBJECT-TYPE
    SYNTAX  INTEGER {
        fqdn(1),
        cscale(2),
        unsupported(2147483647)
    }
    MAX-ACCESS  read-only
    STATUS  current
    DESCRIPTION
        "Set the server mode to FQDN or Auto Scaling (Cloud platform)."
    ::= { slbCurCfgFQDNServerEntry 8 }


slbCurCfgFQDNServerRGName OBJECT-TYPE
    SYNTAX DisplayString (SIZE(1..255))
    MAX-ACCESS  read-only
    STATUS  current
    DESCRIPTION
        "Resource Group Name (Cloud platform)."
    ::= { slbCurCfgFQDNServerEntry 9 }

-- SLB TSO Configuration

slbCurCfgSlbTso OBJECT-TYPE
    SYNTAX  INTEGER {
        enabled(1),
        disabled(2),
        unsupported(2147483647)
        }
    MAX-ACCESS  read-only
    STATUS  current
    DESCRIPTION
        "Enable/Disable TCP Segmentation Offload.
         Note:This mib is supported only on VA and standalone Platforms."
    ::= { slbGeneralCfg 108 }

slbNewCfgSlbTso OBJECT-TYPE
    SYNTAX  INTEGER {
        enabled(1),
        disabled(2),
        unsupported(2147483647)
        }
    MAX-ACCESS  read-write
    STATUS  current
    DESCRIPTION
        "Enable/Disable TCP Segmentation Offload.
         Note:This mib is supported only on VA and standalone Platforms."
    ::= { slbGeneralCfg 109 }

slbCurCfgIpTos OBJECT-TYPE
    SYNTAX  INTEGER {
        enabled(1),
        disabled(2),
        unsupported(2147483647)
        }
    MAX-ACCESS  read-only
    STATUS  current
    DESCRIPTION
        "Enable/disable IP ToS preservation in Proxy mode for filters.
         Note:This mib is not supported for VX instance of Virtualization."
    ::= { slbGeneralCfg 110 }

slbNewCfgIpTos OBJECT-TYPE
    SYNTAX  INTEGER {
        enabled(1),
        disabled(2),
        unsupported(2147483647)
        }
    MAX-ACCESS  read-write
    STATUS  current
    DESCRIPTION
        "Enable/disable IP ToS preservation in Proxy mode for filters.
         Note:This mib is not supported for VX instance of Virtualization."
    ::= { slbGeneralCfg 111 }

slbCurCfgSlbDynAddr OBJECT-TYPE
    SYNTAX  INTEGER {
        enabled(1),
        disabled(2),
        unsupported(2147483647)
        }
    MAX-ACCESS  read-only
    STATUS  current
    DESCRIPTION
        "Enable or disable extracting client IP from tcp options.
         Note:This mib is not supported for VX instance of Virtualization."
    ::= { slbGeneralCfg 112 }

slbNewCfgSlbDynAddr OBJECT-TYPE
    SYNTAX  INTEGER {
        enabled(1),
        disabled(2),
        unsupported(2147483647)
        }
    MAX-ACCESS  read-write
    STATUS  current
    DESCRIPTION
        "Enable or disable extracting client IP from tcp options.
         Note:This mib is not supported for VX instance of Virtualization."
    ::= { slbGeneralCfg 113 }

slbCurCfgClientCert OBJECT-TYPE
    SYNTAX  DisplayString  (SIZE(0..128))
    MAX-ACCESS read-only
    STATUS  current
    DESCRIPTION
        "The client certificate name. The string is used to fetch
        certificate used for HTTPS/LDAPS health check.
        Note:This mib is not supported for VX instance of Virtualization."
    ::= { slbGeneralCfg 114 }

slbNewCfgClientCert OBJECT-TYPE
    SYNTAX  DisplayString  (SIZE(0..128))
    MAX-ACCESS  read-write
    STATUS  current
    DESCRIPTION
        "The client certificate name. The string is used to fetch
        certificate used for HTTPS/LDAPS health check.
        Note:This mib is not supported for VX instance of Virtualization."
    ::= { slbGeneralCfg 115 }
     
 slbCurCfgHwHash OBJECT-TYPE
    SYNTAX  INTEGER {
        l4(1),
        l3(2),
        unsupported(2147483647)
        }
    MAX-ACCESS  read-only
    STATUS  current
    DESCRIPTION
        "Set HW Hash to be l3 or l4.
         Note:This mib is not supported for VX instance of Virtualization."
    ::= { slbGeneralCfg 116 }

slbNewCfgHwHash OBJECT-TYPE
    SYNTAX  INTEGER {
        l4(1),
        l3(2),
        unsupported(2147483647)
        }
    MAX-ACCESS  read-write
    STATUS  current
    DESCRIPTION
        "Set HW Hash to be l3 or l4.
         Note:This mib is not supported for VX instance of Virtualization."
 ::= { slbGeneralCfg 117 }
    
slbCurCfgPreserve OBJECT-TYPE
    SYNTAX  INTEGER {
        enabled(1),
        disabled(2),
        unsupported(2147483647)
        }
    MAX-ACCESS  read-only
    STATUS  current
    DESCRIPTION
        "Enable or disable preserve server port. It allows to preserve
         source port for ipsec traffic when set to enabled(1).
         Note:This mib is not supported for VX instance of Virtualization."
    ::= { slbGeneralCfg 118 }

slbNewCfgPreserve OBJECT-TYPE
    SYNTAX  INTEGER {
        enabled(1),
        disabled(2),
        unsupported(2147483647)
        }
    MAX-ACCESS  read-write
    STATUS  current
    DESCRIPTION
        "Enable or disable preserve server port. It allows to preserve
         source port for ipsec traffic when set to enabled(1).
         Note:This mib is not supported for VX instance of Virtualization."
    ::= { slbGeneralCfg 119 }
      
slbCurCfgProxyage OBJECT-TYPE
    SYNTAX  INTEGER (1..86400) 
    MAX-ACCESS  read-only
    STATUS  current 
    DESCRIPTION
        "Inactive session aging for proxy processing (in sec).
         Note:This mib is not supported for VX instance of Virtualization."
    ::= { slbGeneralCfg 120 }

slbNewCfgProxyage OBJECT-TYPE
    SYNTAX  INTEGER (1..86400) 
    MAX-ACCESS  read-write
    STATUS  current 
    DESCRIPTION
        "Inactive session aging for proxy processing (in sec).
         Note:This mib is not supported for VX instance of Virtualization."
    ::= { slbGeneralCfg 121 }
      
slbNewCfgSlbRlookup OBJECT-TYPE
    SYNTAX  INTEGER {
        enabled(1),
        disabled(2),
        unsupported(2147483647)
        }
    MAX-ACCESS  read-write
    STATUS  current
    DESCRIPTION
        "Enable/Disable reverse lookup for session entry.
         Note:This mib is not supported for VX instance of Virtualization."
    ::= { slbGeneralCfg 122 }    

slbCurCfgSlbRlookup OBJECT-TYPE
    SYNTAX  INTEGER {
        enabled(1),
        disabled(2),
        unsupported(2147483647)
        }
    MAX-ACCESS  read-only
    STATUS  current
    DESCRIPTION
        "Enable/Disable reverse lookup for session entry.
         Note:This mib is not supported for VX instance of Virtualization."
    ::= { slbGeneralCfg 123 }

slbCurCfgAllowExternalHc OBJECT-TYPE
     SYNTAX  INTEGER {
        enabled(1),
        disabled(2),
        unsupported(2147483647)
        }
    MAX-ACCESS  read-only
    STATUS  current
    DESCRIPTION
        "Enable/Disable health checks handling by external module.
         Note:This mib is not supported for VX instance of Virtualization."
    ::= { slbGeneralCfg 124 } 

slbNewCfgAllowExternalHc OBJECT-TYPE
     SYNTAX  INTEGER {
        enabled(1),
        disabled(2),
        unsupported(2147483647)
        }
    MAX-ACCESS  read-write
    STATUS  current
    DESCRIPTION
        "Enable/Disable health checks handling by external module.
         Note:This mib is not supported for VX instance of Virtualization."
    ::= { slbGeneralCfg 125 } 

slbCurCfgMacToMe OBJECT-TYPE
    SYNTAX  INTEGER {
        enabled(1),
        disabled(2),
        unsupported(2147483647)
        }
    MAX-ACCESS  read-only
    STATUS  current
    DESCRIPTION
        "Enable/disable matching filter traffic to device mac addresses.
         Note:This mib is not supported for VX instance of Virtualization."
    ::= { slbGeneralCfg 126 }

slbNewCfgMacToMe OBJECT-TYPE
    SYNTAX  INTEGER {
        enabled(1),
        disabled(2),
        unsupported(2147483647)
        }
    MAX-ACCESS  read-write
    STATUS  current
    DESCRIPTION
        "Enable/disable matching filter traffic to device mac addresses.
         Note:This mib is not supported for VX instance of Virtualization."
    ::= { slbGeneralCfg 127 }

slbCurCfgQinQ OBJECT-TYPE
    SYNTAX  INTEGER {
        enabled(1),
        disabled(2),
        unsupported(2147483647)
        }
    MAX-ACCESS  read-only
    STATUS  current
    DESCRIPTION
        "Current status of IEEE 802.1ad (QinQ) support.
         Note:This mib is only supported for VA instance."
    ::= { slbGeneralCfg 128 }

slbNewCfgQinQ OBJECT-TYPE
    SYNTAX  INTEGER {
        enabled(1),
        disabled(2),
        unsupported(2147483647)
        }
    MAX-ACCESS  read-write
    STATUS  current
    DESCRIPTION
        "Enable or disable IEEE 802.1ad (QinQ) support.
         Note:This mib is only supported for VA instance."
    ::= { slbGeneralCfg 129 }

slbCurCfgVLANBind OBJECT-TYPE
    SYNTAX  INTEGER {
        disabled(1),
        enabled(2),
        unsupported(2147483647)
        }
    MAX-ACCESS  read-only
    STATUS  current
    DESCRIPTION
        "Enable/disable ingress VLAN for session table Binding. SP uses
         ingress VLAN for session lookup when set to enable.
         Note:This mib is not supported for VX instance of Virtualization."
    ::= { slbGeneralCfg 130 }

slbNewCfgVLANBind OBJECT-TYPE
    SYNTAX  INTEGER {
        disabled(1),
        enabled(2),
        unsupported(2147483647)
        }
    MAX-ACCESS  read-write
    STATUS  current
    DESCRIPTION
        "Enable/disable ingress VLAN for session table Binding. SP uses
         ingress VLAN for session lookup when set to enable.
         Note:This mib is not supported for VX instance of Virtualization."
 ::= { slbGeneralCfg 131 }

slbCurCfgSessRtSrcMacUpdate OBJECT-TYPE
    SYNTAX  INTEGER {
        disabled(1),
        enabled(2),
        unsupported(2147483647)
        }
    MAX-ACCESS  read-only
    STATUS  current
    DESCRIPTION
        "Enable/disable rtsrcmac update on session table.
         Note:This mib is not supported for VX instance of Virtualization."
    ::= { slbGeneralCfg 132 }

slbNewCfgSessRtSrcMacUpdate OBJECT-TYPE
    SYNTAX  INTEGER {
        disabled(1),
        enabled(2),
        unsupported(2147483647)
        }
    MAX-ACCESS  read-write
    STATUS  current
    DESCRIPTION
        "Enable/disable rtsrcmac update on session table.
         Note:This mib is not supported for VX instance of Virtualization."
    ::= { slbGeneralCfg 133 }

slbCurCfgSatisrt OBJECT-TYPE
    SYNTAX  INTEGER (1..999999) 
    MAX-ACCESS  read-only
    STATUS  current 
    DESCRIPTION
        "application satisfied response time threshold (global settings), 1-999999 ms"
    ::= { slbGeneralCfg 134 }

slbNewCfgSatisrt OBJECT-TYPE
    SYNTAX  INTEGER (1..999999) 
    MAX-ACCESS  read-write
    STATUS  current 
    DESCRIPTION
        "application satisfied response time threshold (global settings), 1-999999 ms"
    ::= { slbGeneralCfg 135 }

slbCurCfgPportSelection OBJECT-TYPE
    SYNTAX  INTEGER {
        sequential(1),
        random(2),
        unsupported(2147483647)
        }
    MAX-ACCESS  read-only
    STATUS  current
    DESCRIPTION
        "Sequential or random pport selection.
         Note:This mib is not supported for VX instance of Virtualization."
    ::= { slbGeneralCfg 136 }

slbNewCfgPportSelection OBJECT-TYPE
    SYNTAX  INTEGER {
        sequential(1),
        random(2),
        unsupported(2147483647)
        }
    MAX-ACCESS  read-write
    STATUS  current
    DESCRIPTION
        "Sequential or random pport selection.
         Note:This mib is not supported for VX instance of Virtualization."
    ::= { slbGeneralCfg 137 }

 slbCurCfgTDHash OBJECT-TYPE
     SYNTAX  INTEGER {
        rss(1),
        l3(2),
        l4(3),
        unsupported(2147483647)
        }
    MAX-ACCESS  read-only
    STATUS  current
    DESCRIPTION
        "Hash level for TD based core selection and value rss is by default.
         Note:This mib is supported only for VA devices."
    ::= { slbGeneralCfg 146 }

slbNewCfgTDHash OBJECT-TYPE
     SYNTAX  INTEGER {
        rss(1),
        l3(2),
        l4(3),
        unsupported(2147483647)
        }
    MAX-ACCESS  read-write
    STATUS  current
    DESCRIPTION
        "Hash level for TD based core selection.
         rss: TD core selection is based on hardware rss hash (default configuration).
         l3 : l3 level hash based on IP delivery header of the packet
         l4 : l4 level hash based on TCP/UDP header of the packet
         Set VA TD Hash to be rss or l3 or l4.
         Note:This mib is supported only for VA devices with TD configuration."
 ::= { slbGeneralCfg 147 }

 slbCurCfgTDTnlHash OBJECT-TYPE
     SYNTAX  INTEGER {
        l3(1),
        l4(2),
        none(3),
        unsupported(2147483647)
        }
    MAX-ACCESS  read-only
    STATUS  current
    DESCRIPTION
        "Hash level for GRE/IPIP tunnel packets TD core selection and value l3 by default.
         Note:This mib is supported only for VA devices."
    ::= { slbGeneralCfg 148 }

slbNewCfgTDTnlHash OBJECT-TYPE
     SYNTAX  INTEGER {
        l3(1),
        l4(2),
        none(3),
        unsupported(2147483647)
        }
    MAX-ACCESS  read-write
    STATUS  current
    DESCRIPTION
        "Hash level for GRE/IPIP tunnel packets TD core selection.
         l3  : l3 level hash based on IP header in GRE/IPIP's payload packet (default configuration)
         l4  : l4 level hash based on TCP/UDP header in GRE/IPIP's payload packet
         none: TD core selection is based on slbCurCfgTDHash configuration.
         Set VA tunnel TD Hash to be l3 or l4 or none.
         Note:This mib is supported only for VA devices with TD configuration."
 ::= { slbGeneralCfg 149 }

-- WAP Health Check configuration

slbCurCfgWaphcWSPPort OBJECT-TYPE   
    SYNTAX INTEGER (0..65534)
    MAX-ACCESS read-only   
    STATUS current   
    DESCRIPTION 
        "The WSP port number to health check.
         Note:This mib is not supported for VX instance of Virtualization."
    ::= { waphcCfg 1 }

slbNewCfgWaphcWSPPort OBJECT-TYPE   
    SYNTAX INTEGER (0..65534)
    MAX-ACCESS read-write
    STATUS current   
    DESCRIPTION 
        "The WSP port number to health check.
         Note:This mib is not supported for VX instance of Virtualization."
    ::= { waphcCfg 2 }

slbCurCfgWaphcOffset OBJECT-TYPE   
    SYNTAX INTEGER (0..256)
    MAX-ACCESS read-only   
    STATUS current   
    DESCRIPTION 
        "The offset in received WSP packet.
         Note:This mib is not supported for VX instance of Virtualization."
    ::= { waphcCfg 3 }

slbNewCfgWaphcOffset OBJECT-TYPE   
    SYNTAX INTEGER (0..256)
    MAX-ACCESS read-write
    STATUS current   
    DESCRIPTION 
        "The offset in received WSP packet.
         Note:This mib is not supported for VX instance of Virtualization."
    ::= { waphcCfg 4 }

slbCurCfgWaphcSndContent OBJECT-TYPE   
    SYNTAX OCTET STRING (SIZE(0..512))
    MAX-ACCESS read-only   
    STATUS current   
    DESCRIPTION 
        "The content to be sent to the WAP gateway.
         Note:This mib is not supported for VX instance of Virtualization."
    ::= { waphcCfg 5 }

slbNewCfgWaphcSndContent OBJECT-TYPE   
    SYNTAX OCTET STRING (SIZE(0..512))
    MAX-ACCESS read-write
    STATUS current   
    DESCRIPTION 
        "The content to be sent to the WAP gateway.
         Note:This mib is not supported for VX instance of Virtualization."
    ::= { waphcCfg 6 }

slbCurCfgWaphcRcvContent OBJECT-TYPE   
    SYNTAX OCTET STRING (SIZE(0..512))
    MAX-ACCESS read-only   
    STATUS current   
    DESCRIPTION 
        "The content to be received from the WAP gateway.
         Note:This mib is not supported for VX instance of Virtualization."
    ::= { waphcCfg 7 }

slbNewCfgWaphcRcvContent OBJECT-TYPE   
    SYNTAX OCTET STRING (SIZE(0..512))
    MAX-ACCESS read-write
    STATUS current   
    DESCRIPTION 
        "The content to be received from the WAP gateway.
         Note:This mib is not supported for VX instance of Virtualization."
    ::= { waphcCfg 8 }

slbCurCfgWaphcWTLSPort OBJECT-TYPE   
    SYNTAX INTEGER (0..65534)
    MAX-ACCESS read-only   
    STATUS current   
    DESCRIPTION 
        "The WTLS port number to health check.
         Note:This mib is not supported for VX instance of Virtualization."
    ::= { waphcCfg 9 }

slbNewCfgWaphcWTLSPort OBJECT-TYPE   
    SYNTAX INTEGER (0..65534)
    MAX-ACCESS read-write
    STATUS current   
    DESCRIPTION 
        "The WTLS port number to health check.
         Note:This mib is not supported for VX instance of Virtualization."
    ::= { waphcCfg 10 }

slbCurCfgWaphcWTPSndContent OBJECT-TYPE   
    SYNTAX OCTET STRING (SIZE(0..512))
    MAX-ACCESS read-only   
    STATUS current   
    DESCRIPTION 
        "The WTP+WSP content to be sent to the WAP gateway.
         Note:This mib is not supported for VX instance of Virtualization."
    ::= { waphcCfg 11 }

slbNewCfgWaphcWTPSndContent OBJECT-TYPE   
    SYNTAX OCTET STRING (SIZE(0..512))
    MAX-ACCESS read-write
    STATUS current   
    DESCRIPTION 
        "The WTP+WSP content to be sent to the WAP gateway.
         Note:This mib is not supported for VX instance of Virtualization."
    ::= { waphcCfg 12 }

slbCurCfgWaphcWTPRcvContent OBJECT-TYPE   
    SYNTAX OCTET STRING (SIZE(0..512))
    MAX-ACCESS read-only   
    STATUS current   
    DESCRIPTION 
        "The WTP+WSP content to be received from the WAP gateway.
         Note:This mib is not supported for VX instance of Virtualization."
    ::= { waphcCfg 13 }

slbNewCfgWaphcWTPRcvContent OBJECT-TYPE   
    SYNTAX OCTET STRING (SIZE(0..512))
    MAX-ACCESS read-write
    STATUS current   
    DESCRIPTION 
        "The WTP+WSP content to be received from the WAP gateway.
         Note:This mib is not supported for VX instance of Virtualization."
    ::= { waphcCfg 14 }

slbCurCfgWaphcWTPConnContent OBJECT-TYPE   
    SYNTAX OCTET STRING (SIZE(0..512))
    MAX-ACCESS read-only   
    STATUS current   
    DESCRIPTION 
        "The WTP+WSP CONNECT content to be sent to the WAP gateway.
         Note:This mib is not supported for VX instance of Virtualization."
    ::= { waphcCfg 15 }

slbNewCfgWaphcWTPConnContent OBJECT-TYPE   
    SYNTAX OCTET STRING (SIZE(0..512))
    MAX-ACCESS read-write
    STATUS current   
    DESCRIPTION 
        "The WTP+WSP CONNECT content to be sent to the WAP gateway.
         Note:This mib is not supported for VX instance of Virtualization."
    ::= { waphcCfg 16 }

slbCurCfgWaphcWTPPort OBJECT-TYPE   
    SYNTAX INTEGER (0..65534)
    MAX-ACCESS read-only   
    STATUS current   
    DESCRIPTION 
        "The WTP port number to health check.
         Note:This mib is not supported for VX instance of Virtualization."
    ::= { waphcCfg 17 }

slbNewCfgWaphcWTPPort OBJECT-TYPE   
    SYNTAX INTEGER (0..65534)
    MAX-ACCESS read-write
    STATUS current   
    DESCRIPTION 
        "The WTP port number to health check.
         Note:This mib is not supported for VX instance of Virtualization."
    ::= { waphcCfg 18 }

slbCurCfgWaphcWTLSWSPPort OBJECT-TYPE   
    SYNTAX INTEGER (0..65534)
    MAX-ACCESS read-only   
    STATUS current   
    DESCRIPTION 
        "The WTLS+WSP port number to health check.
         Note:This mib is not supported for VX instance of Virtualization."
    ::= { waphcCfg 19 }

slbNewCfgWaphcWTLSWSPPort OBJECT-TYPE   
    SYNTAX INTEGER (0..65534)
    MAX-ACCESS read-write
    STATUS current   
    DESCRIPTION 
        "The WTLS+WSP port number to health check.
         Note:This mib is not supported for VX instance of Virtualization."
    ::= { waphcCfg 20 }

slbCurCfgWaphcWTPOffset OBJECT-TYPE   
    SYNTAX INTEGER (0..256)
    MAX-ACCESS read-only   
    STATUS current   
    DESCRIPTION 
        "The offset in received WTP packet.
         Note:This mib is not supported for VX instance of Virtualization."
    ::= { waphcCfg 21 }

slbNewCfgWaphcWTPOffset OBJECT-TYPE   
    SYNTAX INTEGER (0..256)
    MAX-ACCESS read-write
    STATUS current   
    DESCRIPTION 
        "The offset in received WTP packet.
         Note:This mib is not supported for VX instance of Virtualization."
    ::= { waphcCfg 22 }

slbCurCfgWaphcCouple OBJECT-TYPE
    SYNTAX INTEGER {
        enabled(1),
        disabled(2),
        unsupported(2147483647)
        }
    MAX-ACCESS  read-only
    STATUS  current
    DESCRIPTION
        "Enable or disable coupling of WAP and RADIUS Accounting 
	 health checks.
         Note:This mib is not supported for VX instance of Virtualization."
    ::= { waphcCfg 23 }

slbNewCfgWaphcCouple OBJECT-TYPE
    SYNTAX INTEGER {
        enabled(1),
        disabled(2),
        unsupported(2147483647)
        }
    MAX-ACCESS  read-write
    STATUS  current
    DESCRIPTION
        "Enable or disable coupling of WAP and RADIUS Accounting 
	 health checks.
         Note:This mib is not supported for VX instance of Virtualization."
    ::= { waphcCfg 24 }

slbCurCfgWaphcConnPDU OBJECT-TYPE
    SYNTAX OCTET STRING (SIZE(0..512)) 
    MAX-ACCESS  read-only
    STATUS  current
    DESCRIPTION
        "The CONNECT PDU to be sent to the WAP gateway.
         Note:This mib is not supported for VX instance of Virtualization."
    ::= { waphcCfg 25 }

slbNewCfgWaphcConnPDU OBJECT-TYPE
    SYNTAX OCTET STRING (SIZE(0..512))
    MAX-ACCESS  read-write
    STATUS  current
    DESCRIPTION
        "The CONNECT PDU to be sent to the WAP gateway.
         Note:This mib is not supported for VX instance of Virtualization."
    ::= { waphcCfg 26 }

slbCurCfgWaphcSndPDU OBJECT-TYPE
    SYNTAX OCTET STRING (SIZE(0..512))
    MAX-ACCESS read-only
    STATUS current
    DESCRIPTION
        "The GET PDU to be sent to the WAP gateway.
         Note:This mib is not supported for VX instance of Virtualization."
    ::= { waphcCfg 27 }

slbNewCfgWaphcSndPDU OBJECT-TYPE
    SYNTAX OCTET STRING (SIZE(0..512))
    MAX-ACCESS read-write
    STATUS current
    DESCRIPTION
        "The GET PDU to be sent to the WAP gateway.
         Note:This mib is not supported for VX instance of Virtualization."
    ::= { waphcCfg 28 }

slbCurCfgWaphcRcvPDU OBJECT-TYPE
    SYNTAX OCTET STRING (SIZE(0..512))
    MAX-ACCESS read-only
    STATUS current
    DESCRIPTION
        "The REPLY PDU to be received from the WAP gateway.
         Note:This mib is not supported for VX instance of Virtualization."
    ::= { waphcCfg 29 }

slbNewCfgWaphcRcvPDU OBJECT-TYPE
    SYNTAX OCTET STRING (SIZE(0..512))
    MAX-ACCESS read-write
    STATUS current
    DESCRIPTION
        "The REPLY PDU to be received from the WAP gateway.
         Note:This mib is not supported for VX instance of Virtualization."
    ::= { waphcCfg 30 }

-- WAP Load Balancing Configuration 

slbCurCfgWapTpcp OBJECT-TYPE
    SYNTAX INTEGER {
        enabled(1),
        disabled(2),
        unsupported(2147483647)
        }
    MAX-ACCESS  read-only
    STATUS  current
    DESCRIPTION
        "Enable or disable WAP load balancing.
         Note:This mib is not supported for VX instance of Virtualization."
    ::= { wapCfg 1 }

slbNewCfgWapTpcp OBJECT-TYPE
    SYNTAX INTEGER {
        enabled(1),
        disabled(2),
        unsupported(2147483647)
        }
    MAX-ACCESS  read-write
    STATUS  current
    DESCRIPTION
        "Enable or disable WAP load balancing.
         Note:This mib is not supported for VX instance of Virtualization."
    ::= { wapCfg 2 }

slbCurCfgWapDebug OBJECT-TYPE
    SYNTAX  INTEGER  (0..10)
    MAX-ACCESS  read-only
    STATUS  current
    DESCRIPTION
        "WAP Debug level.
         Note:This mib is not supported for VX instance of Virtualization."
    ::= { wapCfg 3 }

slbNewCfgWapDebug OBJECT-TYPE
    SYNTAX  INTEGER  (0..10)
    MAX-ACCESS  read-write
    STATUS  current
    DESCRIPTION
        "WAP Debug level.
         Note:This mib is not supported for VX instance of Virtualization."
    ::= { wapCfg 4 }


-- Synch Peer Switch Configuration
slbPeerTableMaxSize OBJECT-TYPE
    SYNTAX  Integer32 
    MAX-ACCESS  read-only 
    STATUS  current 
    DESCRIPTION 
        "The maximum number of entries in SLB Peer Table.
         Note:This mib is not supported for VX instance of Virtualization." 
    ::= { syncCfg 2 }

slbCurCfgPeerTable OBJECT-TYPE
    SYNTAX SEQUENCE OF SlbCurCfgPeerEntry
    MAX-ACCESS not-accessible
    STATUS current
    DESCRIPTION
        "The table of Synch Peer Switch configuration in the current_config.
         Note:This mib is not supported for VX instance of Virtualization."
    ::= { syncCfg 3 }

slbCurCfgPeerEntry OBJECT-TYPE
    SYNTAX SlbCurCfgPeerEntry
    MAX-ACCESS not-accessible
    STATUS current
    DESCRIPTION
        "Information about Synch Peer Switch configuration.
         Note:This mib is not supported for VX instance of Virtualization."
    INDEX { slbCurCfgPeerIndex }
    ::= { slbCurCfgPeerTable 1 }
 
SlbCurCfgPeerEntry ::= SEQUENCE {
    slbCurCfgPeerIndex          Integer32,
    slbCurCfgPeerIpAddr         IpAddress,
    slbCurCfgPeerState          INTEGER,
    slbCurCfgPeerIpv6Addr      DisplayString,
    slbCurCfgPeerIpVersion     INTEGER
    }
 
slbCurCfgPeerIndex OBJECT-TYPE
    SYNTAX Integer32
    MAX-ACCESS read-only
    STATUS current
    DESCRIPTION
        "The index for synch peer switchs."
    ::= { slbCurCfgPeerEntry 1 }

slbCurCfgPeerIpAddr OBJECT-TYPE
    SYNTAX IpAddress
    MAX-ACCESS read-only
    STATUS current
    DESCRIPTION
        "The IP address of the peer switch."
    ::= { slbCurCfgPeerEntry 2 }
 
slbCurCfgPeerState OBJECT-TYPE
    SYNTAX INTEGER {
        enable(1),
        disable(2),
        unsupported(2147483647)
        }
    MAX-ACCESS  read-only
    STATUS  current
    DESCRIPTION
        "Enable or disable the peer switch."
    ::= { slbCurCfgPeerEntry 3 }

slbCurCfgPeerIpv6Addr OBJECT-TYPE
    SYNTAX DisplayString (SIZE(0..40))
    MAX-ACCESS read-only
    STATUS current
    DESCRIPTION
        "The IPv6 address of the Peer switch.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { slbCurCfgPeerEntry 4 }

slbCurCfgPeerIpVersion OBJECT-TYPE
    SYNTAX INTEGER {
        ipv4(4),
        ipv6(6),
        unsupported(2147483647)
    }
    MAX-ACCESS read-only
    STATUS current
    DESCRIPTION
        "Peer Ip Address Version."
    ::= { slbCurCfgPeerEntry 5 }

slbNewCfgPeerTable OBJECT-TYPE
    SYNTAX SEQUENCE OF SlbNewCfgPeerEntry
    MAX-ACCESS not-accessible
    STATUS current
    DESCRIPTION
        "The table of Synch Peer Switch configuration in the new_config.
         Note:This mib is not supported for VX instance of Virtualization."
    ::= { syncCfg 4 }
 
slbNewCfgPeerEntry OBJECT-TYPE
    SYNTAX SlbNewCfgPeerEntry
    MAX-ACCESS not-accessible
    STATUS current
    DESCRIPTION
        "Information about synch peer switch  configuration.
         Note:This mib is not supported for VX instance of Virtualization."
    INDEX { slbNewCfgPeerIndex }
    ::= { slbNewCfgPeerTable 1 }
 
SlbNewCfgPeerEntry ::= SEQUENCE {
    slbNewCfgPeerIndex          Integer32,
    slbNewCfgPeerIpAddr         IpAddress,
    slbNewCfgPeerState          INTEGER,
    slbNewCfgPeerDelete         INTEGER,
    slbNewCfgPeerIpv6Addr       DisplayString,
    slbNewCfgPeerIpVersion      INTEGER
    }
 
slbNewCfgPeerIndex OBJECT-TYPE
    SYNTAX Integer32
    MAX-ACCESS read-only
    STATUS current
    DESCRIPTION
        "The index number for synch peer switchs."
    ::= { slbNewCfgPeerEntry 1 }
 
slbNewCfgPeerIpAddr OBJECT-TYPE
    SYNTAX IpAddress
    MAX-ACCESS read-create
    STATUS current
    DESCRIPTION
        "The IP address of the peer switch."
    ::= { slbNewCfgPeerEntry 2 }
 
slbNewCfgPeerState OBJECT-TYPE
    SYNTAX INTEGER {
        enable(1),
        disable(2),
        unsupported(2147483647)
        }
    MAX-ACCESS  read-create
    STATUS  current
    DESCRIPTION
        "Enable or disable the peer switch."
    ::= { slbNewCfgPeerEntry 3 }
 
slbNewCfgPeerDelete OBJECT-TYPE
    SYNTAX INTEGER {
        other(1),
        delete(2),
        unsupported(2147483647)
        }
    MAX-ACCESS  read-create
    STATUS  current
    DESCRIPTION
        "By setting the value to delete(2), the entire row is
         deleted."
    ::= { slbNewCfgPeerEntry 4 }

slbNewCfgPeerIpv6Addr OBJECT-TYPE
    SYNTAX DisplayString (SIZE(0..40))
    MAX-ACCESS read-create
    STATUS current
    DESCRIPTION
        "The IPv6 address of the Peer switch.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { slbNewCfgPeerEntry 5 }

slbNewCfgPeerIpVersion OBJECT-TYPE
    SYNTAX INTEGER {
        ipv4(4),
        ipv6(6),
        unsupported(2147483647)
    }
    MAX-ACCESS read-create
    STATUS current
    DESCRIPTION
        "Peer Ip Address Version."
    ::= { slbNewCfgPeerEntry 6 }


slbCurCfgPeerPIPTable OBJECT-TYPE
    SYNTAX SEQUENCE OF SlbCurCfgPeerPIPEntry
    MAX-ACCESS not-accessible
    STATUS current
    DESCRIPTION
        "The table of Peer PIP configuration in the current_config.
         Note:This mib is not supported for VX instance of Virtualization."
    ::= { peerpipTblCfg 1 }

slbCurCfgPeerPIPEntry OBJECT-TYPE
    SYNTAX SlbCurCfgPeerPIPEntry
    MAX-ACCESS not-accessible
    STATUS current
    DESCRIPTION
        "Information about Peer PIP configuration.
         Note:This mib is not supported for VX instance of Virtualization."
    INDEX { slbCurCfgPeerPIPIndex }
    ::= { slbCurCfgPeerPIPTable 1 }

SlbCurCfgPeerPIPEntry ::= SEQUENCE {
    slbCurCfgPeerPIPIndex       Integer32,
    slbCurCfgPeerPIPAddr        IpAddress,
    slbCurCfgPeerPIPv6Addr      DisplayString,
    slbCurCfgPeerPIPVersion	INTEGER
    }

slbCurCfgPeerPIPIndex OBJECT-TYPE
    SYNTAX Integer32
    MAX-ACCESS read-only
    STATUS current
    DESCRIPTION
        "The index for peer PIP."
    ::= { slbCurCfgPeerPIPEntry 1 }

slbCurCfgPeerPIPAddr OBJECT-TYPE
    SYNTAX IpAddress
    MAX-ACCESS read-only
    STATUS current
    DESCRIPTION
        "The IP address of the peer PIP."
    ::= { slbCurCfgPeerPIPEntry 2 }

slbCurCfgPeerPIPv6Addr OBJECT-TYPE
    SYNTAX DisplayString (SIZE(0..40))
    MAX-ACCESS read-only
    STATUS current
    DESCRIPTION
        "The IPv6 address of the Peer PIP.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { slbCurCfgPeerPIPEntry 3 }

slbCurCfgPeerPIPVersion OBJECT-TYPE
    SYNTAX  INTEGER {
	unknown(0),
        ipv4(4),
        ipv6(6),
        unsupported(2147483647)
        }
    MAX-ACCESS read-only
    STATUS current
    DESCRIPTION
        "The IP version of the peer PIP."
    ::= { slbCurCfgPeerPIPEntry 4 }

slbNewCfgPeerPIPTable OBJECT-TYPE
    SYNTAX SEQUENCE OF SlbNewCfgPeerPIPEntry
    MAX-ACCESS not-accessible
    STATUS current
    DESCRIPTION
        "The table of Peer PIP configuration in the new_config. Either v4 or v6 IP can be configured
in a single row.
         Note:This mib is not supported for VX instance of Virtualization."
    ::= { peerpipTblCfg 2 }

slbNewCfgPeerPIPEntry OBJECT-TYPE
    SYNTAX SlbNewCfgPeerPIPEntry
    MAX-ACCESS not-accessible
    STATUS current
    DESCRIPTION
        "Information about Peer PIP configuration."
    INDEX { slbNewCfgPeerPIPIndex }
    ::= { slbNewCfgPeerPIPTable 1 }

SlbNewCfgPeerPIPEntry ::= SEQUENCE {
    slbNewCfgPeerPIPIndex       Integer32,
    slbNewCfgPeerPIPAddr        IpAddress,
    slbNewCfgPeerPIPv6Addr      DisplayString,
    slbNewCfgPeerPIPDelete      INTEGER,
    slbNewCfgPeerPIPVersion	INTEGER
    }

slbNewCfgPeerPIPIndex OBJECT-TYPE
    SYNTAX Integer32
    MAX-ACCESS read-only
    STATUS current
    DESCRIPTION
        "The index for peer PIP."
    ::= { slbNewCfgPeerPIPEntry 1 }

slbNewCfgPeerPIPAddr OBJECT-TYPE
    SYNTAX IpAddress
    MAX-ACCESS read-create 
    STATUS current
    DESCRIPTION
        "The IP address of the peer PIP. Only new entry can be created,cannot modify existing ip."
    ::= { slbNewCfgPeerPIPEntry 2 }

slbNewCfgPeerPIPv6Addr OBJECT-TYPE
    SYNTAX DisplayString (SIZE(0..40))
    MAX-ACCESS read-create 
    STATUS current
    DESCRIPTION
        "The IPv6 address of the Peer PIP.
         Address should be 16-byte hexadecimal colon notation.
         Valid IPv6 address should be in any of the following forms
         xxxx:xxxx:xxxx:xxxx:xxxx:xxxx:xxxx:xxxx or
         xxxx::xxxx:xxxx:xxxx:xxxx or ::xxxx
	 Only new entry can be created,cannot modify existing ip."
    ::= { slbNewCfgPeerPIPEntry 3 }

slbNewCfgPeerPIPDelete OBJECT-TYPE
    SYNTAX INTEGER {
        other(1),
        delete(2),
        unsupported(2147483647)
        }
    MAX-ACCESS  read-create
    STATUS  current
    DESCRIPTION
        "By setting the value to delete(2), the entire row is
         deleted."
    ::= { slbNewCfgPeerPIPEntry 4 }

slbNewCfgPeerPIPVersion OBJECT-TYPE
    SYNTAX  INTEGER {
	unknown(0),
        ipv4(4),
        ipv6(6),
        unsupported(2147483647)
        }
    MAX-ACCESS read-only
    STATUS current
    DESCRIPTION
        "The IP version of the peer PIP."
    ::= { slbNewCfgPeerPIPEntry 5 }

slbCurCfgSyncFilt OBJECT-TYPE
    SYNTAX  INTEGER {
        enabled(1),
        disabled(2),
        unsupported(2147483647)
        }
    MAX-ACCESS  read-only
    STATUS  current
    DESCRIPTION
        "Enable or disable synch filter configuration.
         Note:This mib is not supported for VX instance of Virtualization."
    ::= { syncGeneralCfg 1 }

slbNewCfgSyncFilt OBJECT-TYPE
    SYNTAX  INTEGER {
        enabled(1),
        disabled(2),
        unsupported(2147483647)
        }
    MAX-ACCESS  read-write
    STATUS  current
    DESCRIPTION
        "Enable or disable synch filter configuration.
         Note:This mib is not supported for VX instance of Virtualization."
    ::= { syncGeneralCfg 2 }

slbCurCfgSyncPort OBJECT-TYPE
    SYNTAX  INTEGER {
        enabled(1),
        disabled(2),
        unsupported(2147483647)
        }
    MAX-ACCESS  read-only
    STATUS  current
    DESCRIPTION
        "Enable or disable synch port configuration.
         Note:This mib is not supported for VX instance of Virtualization."
    ::= { syncGeneralCfg 3 }

slbNewCfgSyncPort OBJECT-TYPE
    SYNTAX  INTEGER {
        enabled(1),
        disabled(2)
        }
    MAX-ACCESS  read-write
    STATUS  current
    DESCRIPTION
        "Enable or disable synch port configuration.
         Note:This mib is not supported for VX instance of Virtualization."
    ::= { syncGeneralCfg 4 }

slbCurCfgSyncVrrp OBJECT-TYPE
    SYNTAX  INTEGER {
        enabled(1),
        disabled(2),
        unsupported(2147483647)
        }
    MAX-ACCESS  read-only
    STATUS  current
    DESCRIPTION
        "Enable or disable synch VRRP Priorities.
         Note:This mib is not supported for VX instance of Virtualization."
    ::= { syncGeneralCfg 5 }

slbNewCfgSyncVrrp OBJECT-TYPE
    SYNTAX  INTEGER {
        enabled(1),
        disabled(2),
        unsupported(2147483647)
        }
    MAX-ACCESS  read-write
    STATUS  current
    DESCRIPTION
        "Enable or disable synch VRRP Priorities.
         Note:This mib is not supported for VX instance of Virtualization."
    ::= { syncGeneralCfg 6 }

slbCurCfgSyncPip OBJECT-TYPE
    SYNTAX  INTEGER {
        enabled(1),
        disabled(2),
        unsupported(2147483647)
        }
    MAX-ACCESS  read-only
    STATUS  current
    DESCRIPTION
        "Enable or disable synch proxy IP addresses.
         Note:This mib is not supported for VX instance of Virtualization."
    ::= { syncGeneralCfg 7 }

slbNewCfgSyncPip OBJECT-TYPE
    SYNTAX  INTEGER {
        enabled(1),
        disabled(2),
        unsupported(2147483647)
        }
    MAX-ACCESS  read-write
    STATUS  current
    DESCRIPTION
        "Enable or disable synch proxy IP addresses.
         Note:This mib is not supported for VX instance of Virtualization."
    ::= { syncGeneralCfg 8 }

slbCurCfgSyncSfo OBJECT-TYPE
    SYNTAX  INTEGER {
        enabled(1),
        disabled(2),
        unsupported(2147483647)
        }
    MAX-ACCESS  read-only
    STATUS  current
    DESCRIPTION
        "Enable or disable synch stateful failover.
         Note:This mib is not supported for VX instance of Virtualization."
    ::= { syncGeneralCfg 9 }

slbNewCfgSyncSfo OBJECT-TYPE
    SYNTAX  INTEGER {
        enabled(1),
        disabled(2),
        unsupported(2147483647)
        }
    MAX-ACCESS  read-write
    STATUS  current
    DESCRIPTION
        "Enable or disable synch stateful failover.
         Note:This mib is not supported for VX instance of Virtualization."
    ::= { syncGeneralCfg 10 }

slbCurCfgSyncSfoUpdatePeriod OBJECT-TYPE
    SYNTAX  INTEGER (1..60)
    MAX-ACCESS  read-only
    STATUS  current
    DESCRIPTION
        "The stateful failover update period in seconds.
         Note:This mib is not supported for VX instance of Virtualization."
    ::= { syncGeneralCfg 11 }

slbNewCfgSyncSfoUpdatePeriod OBJECT-TYPE
    SYNTAX  INTEGER (1..60)
    MAX-ACCESS  read-write
    STATUS  current
    DESCRIPTION
        "The stateful failover update period in seconds.
         Note:This mib is not supported for VX instance of Virtualization."
    ::= { syncGeneralCfg 12 }

slbCurCfgSyncBwm OBJECT-TYPE
    SYNTAX  INTEGER {
        enabled(1),
        disabled(2),
        unsupported(2147483647)
        }
    MAX-ACCESS  read-only
    STATUS  current
    DESCRIPTION
        "Enable or disable syncing BWM configuration.
         Note:This mib is not supported for VX instance of Virtualization."
    ::= { syncGeneralCfg 13 }

slbNewCfgSyncBwm OBJECT-TYPE
    SYNTAX  INTEGER {
        enabled(1),
        disabled(2),
        unsupported(2147483647)
        }
    MAX-ACCESS  read-write
    STATUS  current
    DESCRIPTION
        "Enable or disable syncing BWM configuration.
         Note:This mib is not supported for VX instance of Virtualization."
    ::= { syncGeneralCfg 14 }
    
slbCurCfgSyncPeerPip OBJECT-TYPE
    SYNTAX  INTEGER {
        enabled(1),
        disabled(2),
        unsupported(2147483647)
        }
    MAX-ACCESS  read-only
    STATUS  current
    DESCRIPTION
        "Enable or disable synch peer proxy IP addresses.
         Note:This mib is not supported for VX instance of Virtualization."
    ::= { syncGeneralCfg 15 }

slbNewCfgSyncPeerPip OBJECT-TYPE
    SYNTAX  INTEGER {
        enabled(1),
        disabled(2),
        unsupported(2147483647)
        }
    MAX-ACCESS  read-write
    STATUS  current
    DESCRIPTION
        "Enable or disable synch peer proxy IP addresses.
         Note:This mib is not supported for VX instance of Virtualization."
    ::= { syncGeneralCfg 16}

slbCurCfgSyncCerts OBJECT-TYPE
    SYNTAX  INTEGER {
        enabled(1),
        disabled(2),
        unsupported(2147483647)
    }
    MAX-ACCESS  read-only
    STATUS  current
    DESCRIPTION
        "Enable or disable syncing certificate repository components.
         Note:This mib is not supported for VX instance of Virtualization."
    ::= { syncGeneralCfg 17 }

slbNewCfgSyncCerts OBJECT-TYPE
    SYNTAX  INTEGER {
        enabled(1),
        disabled(2),
        unsupported(2147483647)
    }
    MAX-ACCESS  read-write
    STATUS  current
    DESCRIPTION
        "Enable or disable syncing certificate repository components.
         If Enable option is selected then Passphrase to encrypt/decrypt 
         certificates and private keys during configuration sync must be 
         set in all peer switches.
         Note:This mib is not supported for VX instance of Virtualization."
    ::= { syncGeneralCfg 18 }

slbCurCfgSyncCertsPassPhrase OBJECT-TYPE
    SYNTAX  DisplayString (SIZE(4..40))
    MAX-ACCESS  read-only
    STATUS  current
    DESCRIPTION
        "Set passphrase to encrypt/decrypt synced certificates and
         dnssec private keys.
         Note:This mib is not supported for VX instance of Virtualization."
    ::= { syncGeneralCfg 19 }

slbNewCfgSyncCertsPassPhrase OBJECT-TYPE
    SYNTAX  DisplayString (SIZE(4..40))
    MAX-ACCESS  read-write
    STATUS  current
    DESCRIPTION
        "Set passphrase to encrypt/decrypt synced certificates and
         dnssec private keys.Same PassPhrase should be set at all
         peer switches.
         Note:This mib is not supported for VX instance of Virtualization."
    ::= { syncGeneralCfg 20 }

slbNewCfgSyncCertsConfPassPhrase OBJECT-TYPE
    SYNTAX  DisplayString (SIZE(4..40))
    MAX-ACCESS  read-write
    STATUS  current
    DESCRIPTION
        "This character string is used to confirm Passphrase 
         which is already entered in slbNewCfgSyncCertsPassPhrase.
         Note:This mib is not supported for VX instance of Virtualization."
    ::= { syncGeneralCfg 21 }

slbCurCfgSyncRoute OBJECT-TYPE
    SYNTAX  INTEGER {
        enabled(1),
        disabled(2),
        unsupported(2147483647)
    }
    MAX-ACCESS  read-only
    STATUS  current
    DESCRIPTION
        "Enable or disable synch static route configuration.
         Note:This mib is not supported for VX instance of Virtualization."
    ::= { syncGeneralCfg 22 }

slbNewCfgSyncRoute OBJECT-TYPE
    SYNTAX  INTEGER {
        enabled(1),
        disabled(2),
        unsupported(2147483647)
    }
    MAX-ACCESS  read-write
    STATUS  current
    DESCRIPTION
        "Enable or disable synch static route configuration.
         Note:This mib is not supported for VX instance of Virtualization."
    ::= { syncGeneralCfg 23 }

slbCurCfgSyncRouteTbl OBJECT-TYPE
    SYNTAX  INTEGER {
        enabled(1),
        disabled(2),
        unsupported(2147483647)
    }
    MAX-ACCESS  read-only
    STATUS  current
    DESCRIPTION
        "Enable or disable sync route table.
         Note:This mib is not supported for VX instance of Virtualization."
    ::= { syncGeneralCfg 24 }

slbNewCfgSyncRouteTbl OBJECT-TYPE
    SYNTAX  INTEGER {
        enabled(1),
        disabled(2),
        unsupported(2147483647)
    }
    MAX-ACCESS  read-write
    STATUS  current
    DESCRIPTION
        "Enable or disable sync route table.
         Note:This mib is not supported for VX instance of Virtualization."
    ::= { syncGeneralCfg 25 }

slbCurCfgSyncDynamicData OBJECT-TYPE
    SYNTAX  INTEGER {
        enabled(1),
        disabled(2),
        unsupported(2147483647)
    }
    MAX-ACCESS  read-only
    STATUS  current
    DESCRIPTION
        "Enable or disable sync dynamic data.
         Note:This mib is not supported for VX instance of Virtualization."
    ::= { syncGeneralCfg 26 }

slbNewCfgSyncDynamicData OBJECT-TYPE
    SYNTAX  INTEGER {
        enabled(1),
        disabled(2),
        unsupported(2147483647)
    }
    MAX-ACCESS  read-write
    STATUS  current
    DESCRIPTION
        "Enable or disable sync dynamic data.
         Note:This mib is not supported for VX instance of Virtualization."
    ::= { syncGeneralCfg 27 }


slbCurCfgSyncRUpdate OBJECT-TYPE
    SYNTAX  INTEGER (10..600)
    MAX-ACCESS  read-only
    STATUS  current
    DESCRIPTION
        "Get sync route update period.
         Note:This mib is not supported for VX instance of Virtualization."
    ::= { syncGeneralCfg 28 }

slbNewCfgSyncRUpdate OBJECT-TYPE
    SYNTAX  INTEGER (10..600)
    MAX-ACCESS  read-write
    STATUS  current
    DESCRIPTION
        "Set sync route update period.
         Note:This mib is not supported for VX instance of Virtualization."
    ::= { syncGeneralCfg 29 }

slbCurCfgSyncRHold OBJECT-TYPE
    SYNTAX  INTEGER (10..600)
    MAX-ACCESS  read-only
    STATUS  current
    DESCRIPTION
        "Get time to hold the sync routes after failover.
         Note:This mib is not supported for VX instance of Virtualization."
    ::= { syncGeneralCfg 30 }

slbNewCfgSyncRHold OBJECT-TYPE
    SYNTAX  INTEGER (10..600)
    MAX-ACCESS  read-write
    STATUS  current
    DESCRIPTION
        " Set time to hold the sync routes after failover.
          Note:This mib is not supported for VX instance of Virtualization."
    ::= { syncGeneralCfg 31 }

slbCurCfgSyncL3 OBJECT-TYPE
    SYNTAX  INTEGER {
        enabled(1),
        disabled(2),
        unsupported(2147483647)
        }
    MAX-ACCESS  read-only
    STATUS  current
    DESCRIPTION
        "Enable or disable synch l3 configuration.
         Note:This mib is not supported for VX instance of Virtualization."
    ::= { syncGeneralCfg 32 }

slbNewCfgSyncL3 OBJECT-TYPE
    SYNTAX  INTEGER {
        enabled(1),
        disabled(2),
        unsupported(2147483647)
        }
    MAX-ACCESS  read-write
    STATUS  current
    DESCRIPTION
        "Enable or disable synch l3 configuration.
         Note:This mib is not supported for VX instance of Virtualization."
    ::= { syncGeneralCfg 33 }

slbNewCfgSyncUcastSfo OBJECT-TYPE
    SYNTAX  INTEGER {
        enabled(1),
        disabled(2),
        unsupported(2147483647)
        }
    MAX-ACCESS  read-write
    STATUS  current
    DESCRIPTION
        "Enable or disable unicast mode for SFO.
         Note:This mib is not supported for VX instance of Virtualization."
    ::= { syncGeneralCfg 34 }

slbCurCfgSyncUcastSfo OBJECT-TYPE
    SYNTAX  INTEGER {
        enabled(1),
        disabled(2),
        unsupported(2147483647)
        }
    MAX-ACCESS  read-only
    STATUS  current
    DESCRIPTION
        "Enable or disable unicast mode for SFO.
         Note:This mib is not supported for VX instance of Virtualization."
    ::= { syncGeneralCfg 35 }
	
slbNewCfgSyncUcastSfoPrimif OBJECT-TYPE
    SYNTAX  INTEGER (0..256)
    MAX-ACCESS  read-write
    STATUS  current
    DESCRIPTION
        "Unicast SFO Primary Interafce in NewCfg.
         Note:This mib is not supported for VX instance of Virtualization."
    ::= { syncGeneralCfg 36 }

slbCurCfgSyncUcastSfoPrimif OBJECT-TYPE
    SYNTAX  INTEGER (0..256)
    MAX-ACCESS  read-only
    STATUS  current
    DESCRIPTION
        "Unicast SFO Primary Interafce in CurCfg.
         Note:This mib is not supported for VX instance of Virtualization."
    ::= { syncGeneralCfg 37 }
	
slbNewCfgSyncUcastSfoSecif OBJECT-TYPE
    SYNTAX  INTEGER (0..256)
    MAX-ACCESS  read-write
    STATUS  current
    DESCRIPTION
        "Unicast SFO Secondary Interafce in NewCfg.
         Note:This mib is not supported for VX instance of Virtualization."
    ::= { syncGeneralCfg 38 }

slbCurCfgSyncUcastSfoSecif OBJECT-TYPE
    SYNTAX  INTEGER (0..256)
    MAX-ACCESS  read-only
    STATUS  current
    DESCRIPTION
        "Unicast SFO Secondary Interafce in CurCfg.
         Note:This mib is not supported for VX instance of Virtualization."
    ::= { syncGeneralCfg 39 }

slbCurCfgSyncMaponly OBJECT-TYPE
    SYNTAX  INTEGER {
        enabled(1),
        disabled(2),
        unsupported(2147483647)
        }
    MAX-ACCESS  read-only
    STATUS  current
    DESCRIPTION
        "Enable or disable syncing index mapping table only.
         Note:This mib is not supported for VX instance of Virtualization."
    ::= { syncGeneralCfg 40 }

slbNewCfgSyncMaponly OBJECT-TYPE
    SYNTAX  INTEGER {
        enabled(1),
        disabled(2),
        unsupported(2147483647)
        }
    MAX-ACCESS  read-write
    STATUS  current
    DESCRIPTION
        "Enable or disable syncing index mapping table only.
         Note:This mib is not supported for VX instance of Virtualization."
    ::= { syncGeneralCfg 41 }

slbCurCfgSyncPasswordMode OBJECT-TYPE
    SYNTAX  INTEGER{
        admin(1),
        passphrase(2),
        unsupported(2147483647)
        }
    MAX-ACCESS  read-only
    STATUS  current
    DESCRIPTION
        "The password mode used for authentication in config sync.
         Only passphrase mode is currently supported.
         Note:This mib is not supported for VX instance of Virtualization."
    ::= { syncGeneralCfg 42 }

slbNewCfgSyncPasswordMode OBJECT-TYPE
    SYNTAX  INTEGER{
        admin(1),
        passphrase(2),
        unsupported(2147483647)
        }
    MAX-ACCESS  read-write
    STATUS  current
    DESCRIPTION
        "The password mode used for authentication in config sync.
         Only passphrase mode is currently supported.
         Note:This mib is not supported for VX instance of Virtualization."
    ::= { syncGeneralCfg 43 }

slbCfgSyncPassphrase OBJECT-TYPE
    SYNTAX  DisplayString (SIZE(4..128))
    MAX-ACCESS  read-write
    STATUS  current
    DESCRIPTION
        "Set passphrase to replace the admin password for authentication at the peer device.
         Note:This mib is not supported for VX instance of Virtualization."
    ::= { syncGeneralCfg 44 }

slbCurCfgSyncGw OBJECT-TYPE
    SYNTAX  INTEGER {
        enabled(1),
        disabled(2),
        unsupported(2147483647)
        }
    MAX-ACCESS  read-only
    STATUS  current
    DESCRIPTION
        "Enable or disable synch gw configuration.
         Note:This mib is not supported for VX instance of Virtualization."
    ::= { syncGeneralCfg 45 }

slbNewCfgSyncGw OBJECT-TYPE
    SYNTAX  INTEGER {
        enabled(1),
        disabled(2),
        unsupported(2147483647)
        }
    MAX-ACCESS  read-write
    STATUS  current
    DESCRIPTION
        "Enable or disable synch gw configuration.
         Note:This mib is not supported for VX instance of Virtualization."
    ::= { syncGeneralCfg 46 }

slbCurCfgSyncAutosync OBJECT-TYPE
    SYNTAX  INTEGER {
        enabled(1),
        disabled(2),
        unsupported(2147483647)
        }
    MAX-ACCESS  read-only
    STATUS  current
    DESCRIPTION
        "Enable or disable automatic syncing of configuration.
         Note:This mib is not supported for VX instance of Virtualization."
    ::= { syncGeneralCfg 47 }

slbNewCfgSyncAutosync OBJECT-TYPE
    SYNTAX  INTEGER {
        enabled(1),
        disabled(2),
        unsupported(2147483647)
        }
    MAX-ACCESS  read-write
    STATUS  current
    DESCRIPTION
        "Enable or disable automatic syncing of configuration.
         Note:This mib is not supported for VX instance of Virtualization."
    ::= { syncGeneralCfg 48 }

slbCurCfgSyncTicketKeySyncStatus OBJECT-TYPE
    SYNTAX  INTEGER {
        enabled(1),
        disabled(2),
        unsupported(2147483647)
    }
    MAX-ACCESS  read-only
    STATUS  current
    DESCRIPTION
        "Enable/Disable Ticket Key mirroring.
         Note:This mib is not supported for VX instance of Virtualization."
    ::= { syncGeneralCfg 49 }

slbNewCfgSyncTicketKeySyncStatus OBJECT-TYPE
    SYNTAX  INTEGER {
        enabled(1),
        disabled(2),
        unsupported(2147483647)
    }
    MAX-ACCESS  read-write
    STATUS  current
    DESCRIPTION
        "Enable/Disable Ticket Key mirroring.
         Note:This mib is not supported for VX instance of Virtualization."
    ::= { syncGeneralCfg 50 }

slbCurCfgSyncTicketKeySyncPassword OBJECT-TYPE
    SYNTAX   DisplayString (SIZE (8..20))
    MAX-ACCESS  read-only
    STATUS  current
    DESCRIPTION
        "Set Ticket Key mirroring password.
         Note:This mib is not supported for VX instance of Virtualization."
    ::= { syncGeneralCfg 51 }

slbNewCfgSyncTicketKeySyncPassword OBJECT-TYPE
    SYNTAX   DisplayString (SIZE (8..20))
    MAX-ACCESS  read-write
    STATUS  current
    DESCRIPTION
        "Set Ticket Key mirroring password.
         Note:This mib is not supported for VX instance of Virtualization."
    ::= { syncGeneralCfg 52 }

slbCurCfgSyncIpTunnel OBJECT-TYPE
    SYNTAX  INTEGER {
        enabled(1),
        disabled(2),
        unsupported(2147483647)
        }
    MAX-ACCESS  read-only
    STATUS  current
    DESCRIPTION
        "Enable or disable syncing IP tunnel configuration.
         Note:This mib is not supported for VX instance of Virtualization."
    ::= { syncGeneralCfg 53 }

slbNewCfgSyncIpTunnel OBJECT-TYPE
    SYNTAX  INTEGER {
        enabled(1),
        disabled(2),
        unsupported(2147483647)
        }
    MAX-ACCESS  read-write
    STATUS  current
    DESCRIPTION
        "Enable or disable syncing IP tunnel configuration.
         Note:This mib is not supported for VX instance of Virtualization."
    ::= { syncGeneralCfg 54 }


-- SYN Attack Detection 

synAttackCurCfgInterval OBJECT-TYPE
    SYNTAX  INTEGER (2..3600)
    MAX-ACCESS  read-only
    STATUS  current
    DESCRIPTION
        "The interval specified in seconds determines how frequently the 
         switch checks for SYN attacks.
         Note:This mib is not supported for VX instance of Virtualization."
    ::= { synAttackDetCfg 1 }

synAttackNewCfgInterval OBJECT-TYPE
    SYNTAX  INTEGER (2..3600)
    MAX-ACCESS  read-write
    STATUS  current
    DESCRIPTION
        "The interval specified in seconds determines how frequently the 
         switch checks for SYN attacks.
         Note:This mib is not supported for VX instance of Virtualization."
    ::= { synAttackDetCfg 2 }

synAttackCurCfgThreshhold OBJECT-TYPE
    SYNTAX  INTEGER (1..512000)
    MAX-ACCESS  read-only
    STATUS  current
    DESCRIPTION
        "The threshhold indicating the number of new half-open sessions
         per second.
         Note:This mib is not supported for VX instance of Virtualization."
    ::= { synAttackDetCfg 3 }

synAttackNewCfgThreshhold OBJECT-TYPE
    SYNTAX  INTEGER (1..512000)
    MAX-ACCESS  read-write
    STATUS  current
    DESCRIPTION
        "The threshhold indicating the number of new half-open sessions
         per second.
         Note:This mib is not supported for VX instance of Virtualization."
    ::= { synAttackDetCfg 4 }

synAttackCurCfgResponseInterval OBJECT-TYPE
    SYNTAX  INTEGER (10..1000)
    MAX-ACCESS  read-only
    STATUS  current
    DESCRIPTION
        "The interval specified in milliseconds determines how frequently the 
         switch generate new SYN cookie value.
         Note:This mib is not supported for VX instance of Virtualization."
    ::= { synAttackDetCfg 5 }

synAttackNewCfgResponseInterval OBJECT-TYPE
    SYNTAX  INTEGER (10..1000)
    MAX-ACCESS  read-write
    STATUS  current
    DESCRIPTION
        "The interval specified in milliseconds determines how frequently the 
         switch generate new SYN cookie value.
         Note:This mib is not supported for VX instance of Virtualization."
    ::= { synAttackDetCfg 6 }

synAttackCurCfgOnOff  OBJECT-TYPE
   SYNTAX  INTEGER { on(1), off(2)}
   MAX-ACCESS  read-only
   STATUS  current
   DESCRIPTION
       "Globally ON or OFF of SYN Protection.
        Note:This mib is not supported for VX instance of Virtualization."
   ::= { synAttackDetCfg 7 }

synAttackNewCfgOnOff  OBJECT-TYPE
   SYNTAX  INTEGER { on(1), off(2)}
   MAX-ACCESS  read-write
   STATUS  current
   DESCRIPTION
       "Globally ON or OFF of SYN Protection.
        Note:This mib is not supported for VX instance of Virtualization."
   ::= { synAttackDetCfg 8 }


-- Filtering Group
 
fltCfgTableMaxSize OBJECT-TYPE
    SYNTAX  Integer32
    MAX-ACCESS  read-only
    STATUS  current
    DESCRIPTION
        "The maximum number of filtering table entries.
         Note:This mib is not supported for VX instance of Virtualization."
    ::= { filterCfg 1 }

-- Current Config Filtering Table

fltCurCfgTable OBJECT-TYPE
    SYNTAX  SEQUENCE OF FltCurCfgTableEntry
    MAX-ACCESS  not-accessible
    STATUS  current
    DESCRIPTION
        "The filtering table in the current configuration block.
         Note:This mib is not supported for VX instance of Virtualization."
    ::= { filterCfg 2 }

fltCurCfgTableEntry OBJECT-TYPE
    SYNTAX  FltCurCfgTableEntry
    MAX-ACCESS  not-accessible
    STATUS  current
    DESCRIPTION
        "A row in the filtering table."
    INDEX   { fltCurCfgIndx }
    ::= { fltCurCfgTable 1 }

FltCurCfgTableEntry ::= SEQUENCE {
    fltCurCfgIndx             Integer32,
    fltCurCfgSrcIpMac         INTEGER,
    fltCurCfgSrcIp            IpAddress,
    fltCurCfgSrcIpMask        IpAddress,
    fltCurCfgDstIpMac         INTEGER,
    fltCurCfgDstIp            IpAddress,
    fltCurCfgDstIpMask        IpAddress,
    fltCurCfgProtocol         INTEGER,
    fltCurCfgRangeLowSrcPort  INTEGER,
    fltCurCfgRangeHighSrcPort INTEGER,
    fltCurCfgRangeLowDstPort  INTEGER,
    fltCurCfgRangeHighDstPort INTEGER,
    fltCurCfgAction           INTEGER,
    fltCurCfgRedirPort        INTEGER,
    fltCurCfgRedirGroup       Integer32,
    fltCurCfgLog              INTEGER,
    fltCurCfgState            INTEGER,
    fltCurCfgNat              INTEGER,
    fltCurCfgCache            INTEGER,
    fltCurCfgInvert           INTEGER,
    fltCurCfgClientProxy      INTEGER,
    fltCurCfgTcpAck           INTEGER,
    fltCurCfgSrcMac           PhysAddress,
    fltCurCfgDstMac           PhysAddress,
    fltCurCfgFtpNatActive     INTEGER,
    fltCurCfgAclTcpUrg        INTEGER, 
    fltCurCfgAclTcpAck        INTEGER, 
    fltCurCfgAclTcpPsh        INTEGER, 
    fltCurCfgAclTcpRst        INTEGER, 
    fltCurCfgAclTcpSyn        INTEGER, 
    fltCurCfgAclTcpFin        INTEGER,
    fltCurCfgAclIcmp	      INTEGER,
    fltCurCfgAclIpOption      INTEGER,
    fltCurCfgBwmContract      Integer32,
    fltCurCfgAclIpTos         INTEGER,
    fltCurCfgAclIpTosMask     INTEGER,
    fltCurCfgAclIpTosNew      INTEGER,
    fltCurCfgFwlb	      INTEGER,
    fltCurCfgNatTimeout       INTEGER,
    fltCurCfgLinklb           INTEGER,
    fltCurCfgWapRadiusSnoop   INTEGER,
    fltCurCfgIdslbHash        INTEGER,
    fltCurCfgVlan             INTEGER,
    fltCurCfgTcpRateLimit     INTEGER,
    fltCurCfgTcpRateMaxConn   INTEGER,
    fltCurCfgHash             INTEGER,
    fltCurCfgLayer7DenyState  INTEGER,
    fltCurCfgLayer7DenyUrlBmap OCTET STRING,
    fltCurCfgGotoFilter       Integer32,
    fltCurCfgRadiusWapPersist INTEGER,
    fltCurCfgPbind            INTEGER,
    fltCurCfgTimeWindow       INTEGER,
    fltCurCfgHoldDuration     INTEGER,
    fltCurCfgProxyIp          IpAddress,
    fltCurCfgPatternMatch     INTEGER,
    fltCurCfgLayer7DenyMatchAll INTEGER,
    fltCurCfgLayer7ParseAll   INTEGER,
    fltCurCfgSecurityParseAll INTEGER,
    fltCurCfgPatternMatchGroupBmap OCTET STRING,
    fltCurCfg8021pBitsValue   INTEGER,
    fltCurCfg8021pBitsMatch   INTEGER,
    fltCurCfgAclIpLength      INTEGER,
    fltCurCfgIdsGroup         Integer32,
    fltCurCfgEgressPip        INTEGER,
    fltCurCfgDbind            INTEGER,
    fltCurCfgReverse          INTEGER,
    fltCurCfgRevBwmContract   Integer32, 
    fltCurCfgParseChn         INTEGER,
    fltCurCfgRtpBwmContract   Integer32,
    fltCurCfgSipParsing       INTEGER,
    fltCurCfgSessionMirror    INTEGER,
    fltCurCfgIpVer            INTEGER,
    fltCurCfgIpv6Sip          DisplayString,
    fltCurCfgIpv6Sprefix      INTEGER,
    fltCurCfgIpv6Dip          DisplayString,
    fltCurCfgIpv6Dprefix      INTEGER,
    fltCurCfgHdrHash          INTEGER,
    fltCurCfgHdrName          DisplayString,
    fltCurCfgHdrHashLen       INTEGER,
    fltCurCfgName             DisplayString,
    fltCurCfgNatIp            IpAddress,
    fltCurCfgIpv6Nip          DisplayString,
    fltCurCfgIpv6Proxy        DisplayString,    
    fltCurCfgL7SipFilt        INTEGER,
    fltCurCfgL3Filter          INTEGER,
    fltCurCfgNatMcastVlan     INTEGER,
    fltCurCfgNbind            INTEGER,
    fltCurCfgLayer7InvertAction   INTEGER,
    fltCurCfgSrcClassId       DisplayString,
    fltCurCfgDstClassId       DisplayString,
    fltCurCfgRtsrcmac         INTEGER,
    fltCurCfgRtproxy          INTEGER,
    fltCurCfgSesslog          INTEGER,
    fltCurCfgCntclass         DisplayString,
    fltCurCfgApplicType       INTEGER,
    fltCurCfgEnhRedirGroup       DisplayString,
    fltCurCfgEnhIdsGroup         DisplayString,
    fltCurCfgRtsport          INTEGER,
    fltCurCfgSrcAddrType   INTEGER,
    fltCurCfgDstAddrType   INTEGER,
    fltCurCfgSourceIp      DisplayString,
    fltCurCfgDestIp        DisplayString,
    fltCurCfgSourceMask    DisplayString,
    fltCurCfgDestMask      DisplayString,
    fltCurCfgCosStr        DisplayString,
    fltCurCfgUdpAge        INTEGER,
    fltCurCfgFeTcpPolId    DisplayString,
    fltCurCfgBeTcpPolId    DisplayString,
    fltCurCfgComppol       DisplayString,
    fltCurCfgSslInspectionEna    INTEGER,
    fltCurCfgSrvCertGroup        INTEGER,
    fltCurCfgSrvCert       DisplayString,
    fltCurCfgSslPolicy     DisplayString,
    fltCurCfgMatchDev      INTEGER,
    fltCurCfgSslL7Action   INTEGER,
    fltCurCfgFallback      INTEGER,
    fltCurCfgFbgoto	       Integer32,
    fltCurCfgVpnFlood      INTEGER,
    fltCurCfgUrlFltPol     DisplayString,
    fltCurCfgPorts 	       OCTET STRING,
    fltCurCfgFbport        Integer32,
    fltCurCfgSetIndex      Integer32,
    fltCurCfgReportState       INTEGER,
    fltCurCfgReportLocation    INTEGER,
    fltCurCfgReportPurpose     INTEGER,
    fltCurCfgReportAppl        INTEGER,
    fltCurCfgReportDir         INTEGER,
    fltCurCfgIcapPol           DisplayString,
    fltCurCfgTrafficEventPol   DisplayString,
    fltCurCfgDpmReportState    INTEGER,
    fltCurCfgMacToMe       INTEGER,
    fltCurCfgSecwa             DisplayString,
    fltCurCfgFbvlan            INTEGER,
    fltCurCfgUrlfmode            INTEGER,
    fltCurCfgRtSrcTnl          INTEGER
}

fltCurCfgIndx OBJECT-TYPE
    SYNTAX  Integer32
    MAX-ACCESS  read-only
    STATUS  current
    DESCRIPTION
        "The filtering table index."
    ::= { fltCurCfgTableEntry 1 }

fltCurCfgSrcIp OBJECT-TYPE
    SYNTAX  IpAddress
    MAX-ACCESS  read-only
    STATUS  current
    DESCRIPTION
        "The source IP address to be filtered."
    ::= { fltCurCfgTableEntry 2 }

fltCurCfgSrcIpMask OBJECT-TYPE
    SYNTAX  IpAddress
    MAX-ACCESS  read-only
    STATUS  current
    DESCRIPTION
        "The source IP sub-net mask for filtering."
    ::= { fltCurCfgTableEntry 3 }

fltCurCfgDstIp OBJECT-TYPE
    SYNTAX  IpAddress
    MAX-ACCESS  read-only
    STATUS  current
    DESCRIPTION
        "The destination IP address to be filtered."
    ::= { fltCurCfgTableEntry 4 }

fltCurCfgDstIpMask OBJECT-TYPE
    SYNTAX  IpAddress
    MAX-ACCESS  read-only
    STATUS  current
    DESCRIPTION
        "The destination IP sub-net mask for filtering."
    ::= { fltCurCfgTableEntry 5 }

fltCurCfgProtocol OBJECT-TYPE
    SYNTAX  INTEGER (0..255)
    MAX-ACCESS  read-only
    STATUS  current
    DESCRIPTION
        "The protocol to be filtered."
    ::= { fltCurCfgTableEntry 6 }

fltCurCfgRangeHighSrcPort OBJECT-TYPE
    SYNTAX  INTEGER (0..65534)
    MAX-ACCESS  read-only
    STATUS  current
    DESCRIPTION
        "The higher source TCP/UDP port number to be filtered. It applies 
         only when protocol defined in fltCurCfgProtocol is UDP or TCP.
         '0' means no filtering."
    ::= { fltCurCfgTableEntry 7 }

fltCurCfgRangeLowSrcPort OBJECT-TYPE
    SYNTAX  INTEGER (0..65534)
    MAX-ACCESS  read-only
    STATUS  current
    DESCRIPTION
        "The lower source TCP/UDP port number to be filtered. It applies 
         only when protocol defined in fltCurCfgProtocol is UDP or TCP.  
         '0' means no filtering."
    ::= { fltCurCfgTableEntry 8 }

fltCurCfgRangeLowDstPort OBJECT-TYPE
    SYNTAX  INTEGER (0..65534)
    MAX-ACCESS  read-only
    STATUS  current
    DESCRIPTION
        "The lower destination TCP/UDP port number to be filtered. It applies 
         only when protocol defined in fltCurCfgProtocol is UDP or TCP.
         '0' means no filtering."
    ::= { fltCurCfgTableEntry 9 }

fltCurCfgRangeHighDstPort OBJECT-TYPE
    SYNTAX  INTEGER (0..65534)
    MAX-ACCESS  read-only
    STATUS  current
    DESCRIPTION
        "The higher destination TCP/UDP port number to be filtered. It applies
         only when protocol defined in fltCurCfgProtocol is UDP or TCP.
         '0' means no filtering."
    ::= { fltCurCfgTableEntry 10 }

fltCurCfgAction OBJECT-TYPE
    SYNTAX  INTEGER {
        allow(1),
        deny(2),
        redirect(3),
        nat(4),      -- network address translation
        goto(5),
	outbound-llb(6),
        unsupported(2147483647)
        }
    MAX-ACCESS  read-only
    STATUS  current
    DESCRIPTION
        "The action for the filtering rule."
    ::= { fltCurCfgTableEntry 11 }

fltCurCfgRedirPort OBJECT-TYPE
    SYNTAX  INTEGER (0..65534)
    MAX-ACCESS  read-only
    STATUS  current
    DESCRIPTION
        "The real server port number used for redirection."
    ::= { fltCurCfgTableEntry 12 }

fltCurCfgRedirGroup OBJECT-TYPE
    SYNTAX  Integer32
    MAX-ACCESS  read-only
    STATUS  current
    DESCRIPTION
        "The real server group to be redirected to."
    ::= { fltCurCfgTableEntry 13 }

fltCurCfgLog OBJECT-TYPE
    SYNTAX  INTEGER {
        enabled(1),
        disabled(2),
        unsupported(2147483647)
        }
    MAX-ACCESS  read-only
    STATUS  current
    DESCRIPTION
        "Enable or disable logging."
    ::= { fltCurCfgTableEntry 14 }

fltCurCfgState OBJECT-TYPE
    SYNTAX  INTEGER {
        enabled(1),
        disabled(2),
        unsupported(2147483647)
        }
    MAX-ACCESS  read-only
    STATUS  current
    DESCRIPTION
        "The state of this filtering rule."
    ::= { fltCurCfgTableEntry 15 }

fltCurCfgNat OBJECT-TYPE
    SYNTAX  INTEGER {
        destination-address(1),
        source-address(2),
	multicast-address(3),
        unsupported(2147483647)
        }
    MAX-ACCESS  read-only
    STATUS  current
    DESCRIPTION
        "The selection of destination or source or multicast for
         network address translation."
    ::= { fltCurCfgTableEntry 16 }

fltCurCfgCache OBJECT-TYPE
    SYNTAX  INTEGER {
        enabled(1),
        disabled(2),
        unsupported(2147483647)
        }
    MAX-ACCESS  read-only
    STATUS  current
    DESCRIPTION
        "Enable or disable caching sessions that match filter."
    ::= { fltCurCfgTableEntry 17 }

fltCurCfgInvert OBJECT-TYPE
    SYNTAX  INTEGER {
        enabled(1),
        disabled(2),
        unsupported(2147483647)
        }
    MAX-ACCESS  read-only
    STATUS  current
    DESCRIPTION
        "Turn the invert logic on or off for the filter entry."
    ::= { fltCurCfgTableEntry 18 }

fltCurCfgClientProxy OBJECT-TYPE
    SYNTAX  INTEGER {
        enabled(1),
        disabled(2),
        unsupported(2147483647)
        }
    MAX-ACCESS  read-only
    STATUS  current
    DESCRIPTION
        "Enable or disable client proxy."
    ::= { fltCurCfgTableEntry 19 }

fltCurCfgTcpAck OBJECT-TYPE
    SYNTAX  INTEGER {
        enabled(1),
        disabled(2),
        unsupported(2147483647)
        }
    MAX-ACCESS  read-only
    STATUS  current
    DESCRIPTION
        "Enable or disable filtering on matching TCP ACK and RST flag."
    ::= { fltCurCfgTableEntry 20 }

fltCurCfgSrcMac OBJECT-TYPE
    SYNTAX  PhysAddress 
    MAX-ACCESS  read-only
    STATUS  current
    DESCRIPTION
        "The source MAC address to be filtered."
    ::= { fltCurCfgTableEntry 22 }

fltCurCfgDstMac OBJECT-TYPE
    SYNTAX  PhysAddress 
    MAX-ACCESS  read-only
    STATUS  current
    DESCRIPTION
        "The Destination MAC address to be filtered."
    ::= { fltCurCfgTableEntry 23 }

fltCurCfgFtpNatActive OBJECT-TYPE
    SYNTAX  INTEGER{
	enabled(1),
	disabled(2),
        unsupported(2147483647)
	}
    MAX-ACCESS  read-only
    STATUS  current	
    DESCRIPTION
        "Enable or disable FTP NAT for active ftp only."
    ::= { fltCurCfgTableEntry 24 }

-- Current Config for TCP ACL filtering Table 

fltCurCfgAclTcpUrg OBJECT-TYPE
    SYNTAX  INTEGER {
	enable(1),
	disable(2),
        unsupported(2147483647)
	}
    MAX-ACCESS  read-only
    STATUS  current
    DESCRIPTION
        "Enable or disable TCP URG packet."
    ::= { fltCurCfgTableEntry 25 }	

fltCurCfgAclTcpAck OBJECT-TYPE
    SYNTAX  INTEGER {
	enable(1),
	disable(2),
        unsupported(2147483647)
	}
    MAX-ACCESS  read-only
    STATUS  current
    DESCRIPTION
        "Enable or disable TCP ACK packet."
    ::= { fltCurCfgTableEntry 26 }	

fltCurCfgAclTcpPsh OBJECT-TYPE
    SYNTAX  INTEGER {
	enable(1),
	disable(2),
        unsupported(2147483647)
	}
    MAX-ACCESS  read-only
    STATUS  current
    DESCRIPTION
        "Enable or disable TCP PSH packet."
    ::= { fltCurCfgTableEntry 27 }	

fltCurCfgAclTcpRst OBJECT-TYPE
    SYNTAX  INTEGER {
	enable(1),
	disable(2),
        unsupported(2147483647)
	}
    MAX-ACCESS  read-only
    STATUS  current 
    DESCRIPTION
        "Enable or disable TCP RST packet."
    ::= { fltCurCfgTableEntry 28 }	

fltCurCfgAclTcpSyn OBJECT-TYPE
    SYNTAX  INTEGER {
	enable(1),
	disable(2),
        unsupported(2147483647)
	}
    MAX-ACCESS  read-only
    STATUS  current
    DESCRIPTION
        "Enable or disable TCP SYN packet."
    ::= { fltCurCfgTableEntry 29 }	

fltCurCfgAclTcpFin OBJECT-TYPE
    SYNTAX  INTEGER {
	enable(1),
	disable(2),
        unsupported(2147483647)
	}
    MAX-ACCESS  read-only
    STATUS  current
    DESCRIPTION
	"Enable or disable TCP FIN packet."
    ::= { fltCurCfgTableEntry 30 }	

-- Current Config for ICMP Type ACL filtering Table 

fltCurCfgAclIcmp OBJECT-TYPE
    SYNTAX  INTEGER (0..255)
    MAX-ACCESS  read-only
    STATUS  current
    DESCRIPTION
        "ICMP type to be filtered. A ICMP type of 255 indicates 'any'"
    ::= { fltCurCfgTableEntry 31 }	

-- Current Config IP Option ACL Filtering Table

fltCurCfgAclIpOption OBJECT-TYPE
    SYNTAX  INTEGER {
        enable(1),
	disable(2),
        unsupported(2147483647)
        }
    MAX-ACCESS  read-only
    STATUS  current
    DESCRIPTION
        "Enable or disable IP option matching."
    ::= { fltCurCfgTableEntry 32 }

fltCurCfgBwmContract OBJECT-TYPE
    SYNTAX  Integer32
    MAX-ACCESS  read-only
    STATUS  current
    DESCRIPTION
	"Filt default BW contract number."
    ::= { fltCurCfgTableEntry 33 }	

fltCurCfgAclIpTos OBJECT-TYPE
    SYNTAX  INTEGER (0..255)
    MAX-ACCESS  read-only
    STATUS  current
    DESCRIPTION
        "The IP TOS value to be filtered."
    ::= { fltCurCfgTableEntry 34 }	

fltCurCfgAclIpTosMask OBJECT-TYPE
    SYNTAX  INTEGER (0..255)
    MAX-ACCESS  read-only
    STATUS  current
    DESCRIPTION
        "The IP TOS mask for filtering."
    ::= { fltCurCfgTableEntry 35 }	

fltCurCfgAclIpTosNew OBJECT-TYPE
    SYNTAX  INTEGER (0..255)
    MAX-ACCESS  read-only
    STATUS  current
    DESCRIPTION
        "The new IP TOS value to over-write when filtering fired."
    ::= { fltCurCfgTableEntry 36 }	

fltCurCfgFwlb OBJECT-TYPE
    SYNTAX  INTEGER {
        enabled(1),
        disabled(2),
        unsupported(2147483647)
        }
    MAX-ACCESS  read-only
    STATUS  current
    DESCRIPTION
        "Enable or disable filtering on firewall redirect hash method."
    ::= { fltCurCfgTableEntry 37 }

fltCurCfgNatTimeout OBJECT-TYPE
    SYNTAX  INTEGER (4..32768)
    MAX-ACCESS  read-only
    STATUS  current
    DESCRIPTION
        "The NAT session timeout. The timeout value should be an even number 
         between 4 and 32768."
    ::= { fltCurCfgTableEntry 38 }	

fltCurCfgLinklb OBJECT-TYPE
    SYNTAX  INTEGER {
        enabled(1),
        disabled(2),
        unsupported(2147483647)
        }
    MAX-ACCESS  read-only
    STATUS  current
    DESCRIPTION
        "Enable or disable WAN link load balancing."
    ::= { fltCurCfgTableEntry 39 }

fltCurCfgWapRadiusSnoop OBJECT-TYPE
    SYNTAX  INTEGER {
        enabled(1),
        disabled(2),
        unsupported(2147483647)
        }
    MAX-ACCESS  read-only
    STATUS  current
    DESCRIPTION
        "Enable or disable WAP RADIUS snooping."
    ::= { fltCurCfgTableEntry 40 }

fltCurCfgSrcIpMac OBJECT-TYPE
    SYNTAX  INTEGER {
        ip(1),
        mac(2),
        unsupported(2147483647)
        }
    MAX-ACCESS  read-only
    STATUS  current
    DESCRIPTION
        "Set a flag indicating whether filtering should be based on the 
         source IP address or the source MAC address field."
    ::= { fltCurCfgTableEntry 41 }

fltCurCfgDstIpMac OBJECT-TYPE
    SYNTAX  INTEGER {
        ip(1),
        mac(2),
        unsupported(2147483647)
        }
    MAX-ACCESS  read-only
    STATUS  current
    DESCRIPTION
        "Set a flag indicating whether filtering should be based on the 
         destination IP address or the destination MAC address field."
    ::= { fltCurCfgTableEntry 42 }

fltCurCfgIdslbHash OBJECT-TYPE
    SYNTAX  INTEGER {
        sip(1),
        dip(2),
        sipdip(3),
        sipsport(4),
        dipdport(5),
        all(6),
        unsupported(2147483647)
        }
    MAX-ACCESS  read-only
    STATUS  current
    DESCRIPTION
        "Set hash parameter for intrusion detection server load balancing."
    ::= { fltCurCfgTableEntry 43 }

fltCurCfgVlan OBJECT-TYPE
    SYNTAX  INTEGER (0..4090)
    MAX-ACCESS  read-only
    STATUS  current
    DESCRIPTION
        "Set the VLAN assoicated with the filter."
    ::= { fltCurCfgTableEntry 44 }

fltCurCfgName OBJECT-TYPE
    SYNTAX DisplayString (SIZE(0..31))
    MAX-ACCESS read-only
    STATUS current
    DESCRIPTION
        "The name of the filter."
    ::= { fltCurCfgTableEntry 45 }

fltCurCfgTcpRateLimit OBJECT-TYPE
    SYNTAX  INTEGER {
        enabled(1),
        disabled(2),
        unsupported(2147483647)
        }
    MAX-ACCESS  read-only
    STATUS  current
    DESCRIPTION
        "Enable or disable protocol rate limiting."
    ::= { fltCurCfgTableEntry 46 }

fltCurCfgTcpRateMaxConn OBJECT-TYPE
    SYNTAX  INTEGER (0..255)
    MAX-ACCESS  read-only
    STATUS  current
    DESCRIPTION
        "Set maximum connections (number of connections in units of 10)
         for TCP connection rate limiting.  In the case of ICMP and UDP,
	 this is the maximum packets (number of packets in units of 10)."
    ::= { fltCurCfgTableEntry 47 }

fltCurCfgHash OBJECT-TYPE
    SYNTAX  INTEGER {
	auto(1),
        sip(2),
        dip(3),
        both(4),
	sipsport(5),
	dip32(6),
        unsupported(2147483647)
        }
    MAX-ACCESS  read-only
    STATUS  current
    DESCRIPTION
        "Set hash parameter for the filter."
    ::= { fltCurCfgTableEntry 48 }


fltCurCfgLayer7DenyState OBJECT-TYPE
    SYNTAX  INTEGER {
        enabled(1),
        disabled(2),
        unsupported(2147483647)
        }
    MAX-ACCESS  read-only
    STATUS  current
    DESCRIPTION
        "Enable or disable layer 7 deny filtering."
    ::= { fltCurCfgTableEntry 50 }

fltCurCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltCurCfgTableEntry 51 }

fltCurCfgGotoFilter OBJECT-TYPE
    SYNTAX  Integer32
    MAX-ACCESS  read-only
    STATUS  current	
    DESCRIPTION
        "The filter ID for GOTO action in the current config."
    ::= { fltCurCfgTableEntry 52 }

fltCurCfgRadiusWapPersist OBJECT-TYPE
    SYNTAX  INTEGER {
        enabled(1),
        disabled(2),
        unsupported(2147483647)
        }
    MAX-ACCESS  read-only
    STATUS  current	
    DESCRIPTION
        "Enable or disable Radius/WAP persistence."
    ::= { fltCurCfgTableEntry 53 }

fltCurCfgPbind OBJECT-TYPE
    SYNTAX  INTEGER {
        enabled(1),
        disabled(2),
        unsupported(2147483647)
        }
    MAX-ACCESS  read-only
    STATUS  current	
    DESCRIPTION
        "Enable or disable filter persistent binding."
    ::= { fltCurCfgTableEntry 54 }
   
fltCurCfgTimeWindow OBJECT-TYPE
    SYNTAX  INTEGER (1..65535)
    MAX-ACCESS  read-only
    STATUS  current
    DESCRIPTION
        "The time window for protocol rate limiting (in seconds)."
    ::= { fltCurCfgTableEntry 55 }

fltCurCfgHoldDuration OBJECT-TYPE
    SYNTAX  INTEGER (2..65535)
    MAX-ACCESS  read-only
    STATUS  current
    DESCRIPTION
        "The hold down duration for protocol rate limiting (in minutes)."
    ::= { fltCurCfgTableEntry 56 }

fltCurCfgPatternMatch OBJECT-TYPE
    SYNTAX  INTEGER {
        enabled(1),
        disabled(2),
        unsupported(2147483647)
        }
    MAX-ACCESS  read-only
    STATUS  current	
    DESCRIPTION
        "Enable or disable binary pattern matching."
    ::= { fltCurCfgTableEntry 57 }

fltCurCfgLayer7DenyMatchAll OBJECT-TYPE
    SYNTAX  INTEGER {
        enabled(1),
        disabled(2),
        unsupported(2147483647)
        }
    MAX-ACCESS  read-only
    STATUS  current
    DESCRIPTION
        "Enable or disable match-all criteria for L7 deny string matching."
    ::= { fltCurCfgTableEntry 58 }
    
fltCurCfgProxyIp OBJECT-TYPE
    SYNTAX  IpAddress
    MAX-ACCESS  read-only
    STATUS  current
    DESCRIPTION
        "The client proxy IP address for NAT and REDIR filter."
        
    ::= { fltCurCfgTableEntry 59 }
    
fltCurCfgLayer7ParseAll OBJECT-TYPE
    SYNTAX  INTEGER {
        enabled(1),
        disabled(2),
        unsupported(2147483647)
        }
    MAX-ACCESS  read-only
    STATUS  current
    DESCRIPTION
        "Enable or disable layer 7 lookup (parsing) of all packets."
    ::= { fltCurCfgTableEntry 60 }

fltCurCfgSecurityParseAll OBJECT-TYPE
    SYNTAX  INTEGER {
        enabled(1),
        disabled(2),
        unsupported(2147483647)
        }
    MAX-ACCESS  read-only
    STATUS  current
    DESCRIPTION
        "Enable or disable pattern string lookup (parsing) of all packets."
    ::= { fltCurCfgTableEntry 61 }
    
fltCurCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltCurCfgTableEntry 62 }

fltCurCfg8021pBitsValue OBJECT-TYPE
    SYNTAX  INTEGER (0..7)
    MAX-ACCESS  read-only
    STATUS  current
    DESCRIPTION
        "The 802.1p bits value to match."
    ::= { fltCurCfgTableEntry 63 }

fltCurCfg8021pBitsMatch OBJECT-TYPE
    SYNTAX  INTEGER {
        enabled(1),
        disabled(2),
        unsupported(2147483647)
        }
    MAX-ACCESS  read-only
    STATUS  current
    DESCRIPTION
        "Enable or disable matching on 802.1p bits in the packets."
    ::= { fltCurCfgTableEntry 64 }
 
fltCurCfgAclIpLength OBJECT-TYPE
    SYNTAX  INTEGER (0..65535)
    MAX-ACCESS  read-only
    STATUS  current 
    DESCRIPTION
        "Set the IP maximum packet length in bytes. A value can be either 0 
         which indicates 'any' length or between 64 and 65535."
    ::= { fltCurCfgTableEntry 65 }	

fltCurCfgIdsGroup OBJECT-TYPE
    SYNTAX  Integer32
    MAX-ACCESS  read-only
    STATUS  current
    DESCRIPTION
        "The real server group for IDS load balancing. A value of 0 indicates
	 'none'." 
    ::= { fltCurCfgTableEntry 66 }
    
fltCurCfgEgressPip OBJECT-TYPE
    SYNTAX  INTEGER {
        enabled(1),
        disabled(2),
        unsupported(2147483647)
        }
    MAX-ACCESS  read-only
    STATUS  current
    DESCRIPTION
        "Enable or disable pip selection based on egress port/vlan."
    ::= { fltCurCfgTableEntry 67 }
    
fltCurCfgDbind OBJECT-TYPE
    SYNTAX  INTEGER {
        enabled(1),
        disabled(2),
	forceproxy(3),
        unsupported(2147483647)
        }
    MAX-ACCESS  read-only
    STATUS  current	
    DESCRIPTION
        "Enable or disable filter delayed binding."
    ::= { fltCurCfgTableEntry 68 }

fltCurCfgRevBwmContract OBJECT-TYPE
    SYNTAX  Integer32
    MAX-ACCESS  read-only
    STATUS  current
    DESCRIPTION
	"Filt reverse session BWM contract number."
    ::= { fltCurCfgTableEntry 69 }	

fltCurCfgReverse OBJECT-TYPE
    SYNTAX  INTEGER {
        enabled(1),
        disabled(2),
        unsupported(2147483647)
        }
    MAX-ACCESS  read-only
    STATUS  current	
    DESCRIPTION
        "Enable or disable creating session for reverse side traffic."
    ::= { fltCurCfgTableEntry 70 }

fltCurCfgParseChn OBJECT-TYPE
    SYNTAX INTEGER { 
	enabled(1),
	disabled(2),
        unsupported(2147483647)
	}
    MAX-ACCESS  read-only
    STATUS  current
    DESCRIPTION
	"Enable or disable chained pgroup match criteria for l7 filtering."
    ::= { fltCurCfgTableEntry 71 }


fltCurCfgRtpBwmContract OBJECT-TYPE
    SYNTAX  Integer32
    MAX-ACCESS  read-only
    STATUS  current
    DESCRIPTION
        "BWM contract for SIP RTP traffic."
    ::= { fltCurCfgTableEntry 72 }

fltCurCfgSipParsing OBJECT-TYPE
    SYNTAX  INTEGER {
        enabled(1),
        disabled(2),
        unsupported(2147483647)
        }
    MAX-ACCESS  read-only
    STATUS  current
    DESCRIPTION
        "Enable or disable SIP NAT."
    ::= { fltCurCfgTableEntry 73 }


fltCurCfgSessionMirror  OBJECT-TYPE
    SYNTAX  INTEGER {
        enabled(1),
        disabled(2),
        unsupported(2147483647)
        }
    MAX-ACCESS  read-only
    STATUS  current
    DESCRIPTION
        "Enable or disable session mirroring."
    ::= { fltCurCfgTableEntry 74 }


fltCurCfgIpVer OBJECT-TYPE
    SYNTAX  INTEGER{
        ipv4(1),
        ipv6(2),
        unsupported(2147483647)
        }
    MAX-ACCESS  read-only
    STATUS  current
    DESCRIPTION
        "The type of IP address."
    ::= { fltCurCfgTableEntry 75 }

fltCurCfgIpv6Sip   OBJECT-TYPE
    SYNTAX   DisplayString (SIZE(0..40))
    MAX-ACCESS  read-only
    STATUS  current
    DESCRIPTION
        "The source IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltCurCfgTableEntry 76 }

fltCurCfgIpv6Sprefix   OBJECT-TYPE
    SYNTAX  INTEGER(0..128) 
    MAX-ACCESS  read-only
    STATUS  current
    DESCRIPTION
        "The prefix length associated with source IP address ."
    ::= { fltCurCfgTableEntry 77 }

fltCurCfgIpv6Dip     OBJECT-TYPE
    SYNTAX   DisplayString (SIZE(0..40))
    MAX-ACCESS  read-only
    STATUS  current
    DESCRIPTION
        "The destination  IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltCurCfgTableEntry 78 }

fltCurCfgIpv6Dprefix OBJECT-TYPE
    SYNTAX   INTEGER(0..128) 
    MAX-ACCESS  read-only
    STATUS  current
    DESCRIPTION
        "The prefix length associated with destination IP address ."
    ::= { fltCurCfgTableEntry 79 }


fltCurCfgHdrHash OBJECT-TYPE
       SYNTAX  INTEGER {
        none(1),
        headerhash(2),
        unsupported(2147483647)
        }
    MAX-ACCESS read-only
    STATUS current
    DESCRIPTION
        "The header hash filter."
    ::= { fltCurCfgTableEntry 80 }

fltCurCfgHdrName OBJECT-TYPE
    SYNTAX DisplayString (SIZE(0..31))
    MAX-ACCESS read-only
    STATUS current
    DESCRIPTION
        "The header name of the filter."
    ::= { fltCurCfgTableEntry 81 }

fltCurCfgHdrHashLen OBJECT-TYPE
    SYNTAX  INTEGER (0..255)
    MAX-ACCESS  read-only
    STATUS  current
    DESCRIPTION
        "The header hash length of the filter."
    ::= { fltCurCfgTableEntry 82 }

fltCurCfgL3Filter OBJECT-TYPE
    SYNTAX  INTEGER {
        enabled(1),
        disabled(2),
        unsupported(2147483647)
    }
    MAX-ACCESS  read-only
    STATUS  current
    DESCRIPTION
        "The L3 filter processing state for this filter."
    ::= { fltCurCfgTableEntry 83 }


fltCurCfgNatIp OBJECT-TYPE
    SYNTAX  IpAddress
    MAX-ACCESS  read-only
    STATUS  current
    DESCRIPTION
        "The nat IP address to be filtered."
    ::= { fltCurCfgTableEntry 84 }

fltCurCfgIpv6Nip     OBJECT-TYPE
    SYNTAX   DisplayString (SIZE(0..40))
    MAX-ACCESS  read-only
    STATUS  current
    DESCRIPTION
        "The nat IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltCurCfgTableEntry 85 }

fltCurCfgIpv6Proxy  OBJECT-TYPE
    SYNTAX   DisplayString (SIZE(0..40))
    MAX-ACCESS  read-only
    STATUS  current
    DESCRIPTION
        "The proxy IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltCurCfgTableEntry 86 }
    
fltCurCfgL7SipFilt OBJECT-TYPE
    SYNTAX  INTEGER {
        enabled(1),
        disabled(2),
        unsupported(2147483647)
        }
    MAX-ACCESS  read-only
    STATUS  current
    DESCRIPTION
        "Enable/Disable L7 application SIP UDP filtering."
    ::= { fltCurCfgTableEntry 87 }

fltCurCfgNatMcastVlan OBJECT-TYPE
    SYNTAX  INTEGER (0..4090)
    MAX-ACCESS  read-only
    STATUS  current
    DESCRIPTION
        "Multicast VLAN."
    ::= { fltCurCfgTableEntry 88 }

fltCurCfgNbind OBJECT-TYPE
    SYNTAX  INTEGER {
        enabled(1),
        disabled(2),
        unsupported(2147483647)
    }
    MAX-ACCESS  read-only
    STATUS  current
    DESCRIPTION
        "Enable or disable subnet binding for redirection."
    ::= { fltCurCfgTableEntry 89 }
fltCurCfgLayer7InvertAction OBJECT-TYPE
    SYNTAX  INTEGER {
        enabled(1),
        disabled(2),
        unsupported(2147483647)
        }
    MAX-ACCESS  read-only
    STATUS  current
    DESCRIPTION
        "Enable or disable invert action for layer 7 string matching ."
    ::= { fltCurCfgTableEntry 90 }

fltCurCfgSrcClassId  OBJECT-TYPE
    SYNTAX   DisplayString (SIZE(0..32))
    MAX-ACCESS  read-only
    STATUS  current
    DESCRIPTION
        "The source network class ID to be filtered."
    ::= { fltCurCfgTableEntry 91 }

fltCurCfgDstClassId  OBJECT-TYPE
    SYNTAX   DisplayString (SIZE(0..32))
    MAX-ACCESS  read-only
    STATUS  current
    DESCRIPTION
        "The destination network class ID to be filtered."
    ::= { fltCurCfgTableEntry 92 }

fltCurCfgRtsrcmac OBJECT-TYPE
    SYNTAX  INTEGER {
        enabled(1),
        disabled(2),
        unsupported(2147483647)
        }
    MAX-ACCESS  read-only
    STATUS  current
    DESCRIPTION
        "Enable or disable return to source mac addr."
    ::= { fltCurCfgTableEntry 93 }

fltCurCfgRtproxy OBJECT-TYPE
    SYNTAX  INTEGER {
        enabled(1),
        disabled(2),
        unsupported(2147483647)
        }
    MAX-ACCESS  read-only
    STATUS  current
    DESCRIPTION
        "Enable or disable redirect to proxy server."
    ::= { fltCurCfgTableEntry 94 }

fltCurCfgSesslog OBJECT-TYPE
    SYNTAX  INTEGER {
        enabled(1),
        disabled(2),
        unsupported(2147483647)
        }
    MAX-ACCESS  read-only
    STATUS  current
    DESCRIPTION
        "Enable or disable session logging."
    ::= { fltCurCfgTableEntry 95 }

fltCurCfgCntclass OBJECT-TYPE
    SYNTAX   DisplayString (SIZE(0..32))
    MAX-ACCESS  read-only
    STATUS  current
    DESCRIPTION
        "The cntclass of the filter."
    ::= { fltCurCfgTableEntry 96 }

fltCurCfgApplicType OBJECT-TYPE
    SYNTAX  INTEGER {
        none(1),
        basic(2),
        http(3),
        sip(4),
        dns(5),
        smtp(6),
        pop3(7),
        imap(8),
        ftp(9),
        unsupported(2147483647)
    }
    MAX-ACCESS  read-only
    STATUS  current
    DESCRIPTION
        "Application type for this filter."
    ::= { fltCurCfgTableEntry 97 }
fltCurCfgEnhRedirGroup OBJECT-TYPE
    SYNTAX DisplayString (SIZE(1..255))
    MAX-ACCESS  read-only
    STATUS  current
    DESCRIPTION
        "The real server group to be redirected to."
    ::= { fltCurCfgTableEntry 98 }

fltCurCfgEnhIdsGroup OBJECT-TYPE
    SYNTAX DisplayString (SIZE(1..255))
    MAX-ACCESS  read-only
    STATUS  current
    DESCRIPTION
        "The real server group for IDS load balancing. A NULL string indicates
         'none'."
    ::= { fltCurCfgTableEntry 99 }

fltCurCfgRtsport OBJECT-TYPE
    SYNTAX  INTEGER {
        mod5060(1),
        preserve(2),
        disabled(3),
        unsupported(2147483647)
    }
    MAX-ACCESS  read-only
    STATUS  current
    DESCRIPTION
        "Source port modification for SIP.
         the mod5060 indicates modification of source port to 5060,
         preserve indicates to retain the source port."
    ::= { fltCurCfgTableEntry 100 }

fltCurCfgSrcAddrType OBJECT-TYPE
    SYNTAX  INTEGER {
        ipAddress(1),
        network(2),
        unsupported(2147483647)
    }
    MAX-ACCESS  read-only
    STATUS  current
    DESCRIPTION
        "Source address type from address and network for NAT filter."
    ::= { fltCurCfgTableEntry 101 }

fltCurCfgDstAddrType OBJECT-TYPE
    SYNTAX  INTEGER {
        ipAddress(1),
        network(2),
        unsupported(2147483647)
    }
    MAX-ACCESS  read-only
    STATUS  current
    DESCRIPTION
        "Destination address type from address and network for NAT filter."
    ::= { fltCurCfgTableEntry 102 }

fltCurCfgSourceIp OBJECT-TYPE
    SYNTAX DisplayString (SIZE(1..40))
    MAX-ACCESS  read-only
    STATUS  current
    DESCRIPTION
        "Filter source Ip. It can be IPv4/IPv6."
    ::= { fltCurCfgTableEntry 103 }

fltCurCfgDestIp OBJECT-TYPE
    SYNTAX DisplayString (SIZE(1..40))
    MAX-ACCESS  read-only
    STATUS  current
    DESCRIPTION
        "Filter Destination Ip. It can be IPv4/IPv6."
    ::= { fltCurCfgTableEntry 104 }

fltCurCfgSourceMask OBJECT-TYPE
    SYNTAX DisplayString (SIZE(1..32))
    MAX-ACCESS  read-only
    STATUS  current
    DESCRIPTION
         "Filter Mask or Prefix."
    ::= { fltCurCfgTableEntry 105 }

fltCurCfgDestMask OBJECT-TYPE
    SYNTAX DisplayString (SIZE(1..32))
    MAX-ACCESS  read-only
    STATUS  current
    DESCRIPTION
         "Filter Mask or Prefix."
    ::= { fltCurCfgTableEntry 106 }

fltCurCfgCosStr OBJECT-TYPE
    SYNTAX   DisplayString (SIZE(0..32))
    MAX-ACCESS  read-only
    STATUS  current
    DESCRIPTION
        "The class of service of the filter.
	Empty string - ignore cos
	'Any' string - ignore string use only the source IP
	Specific string - match only if the string matches"
    ::= { fltCurCfgTableEntry 107 }

fltCurCfgUdpAge OBJECT-TYPE
    SYNTAX  INTEGER {
        onlydns(1),
        disabled(2),
        enabled(3),
        unsupported(2147483647)
    }
    MAX-ACCESS  read-only
    STATUS  current
    DESCRIPTION
        "Fast aging of UDP sessions."
    ::= { fltCurCfgTableEntry 108 }


fltCurCfgFeTcpPolId OBJECT-TYPE
    SYNTAX   DisplayString (SIZE(0..32))
    MAX-ACCESS  read-only
    STATUS  current
    DESCRIPTION
        "frontend TCP optimization policy"
    ::= { fltCurCfgTableEntry 109 }

fltCurCfgBeTcpPolId OBJECT-TYPE
    SYNTAX   DisplayString (SIZE(0..32))
    MAX-ACCESS  read-only
    STATUS  current
    DESCRIPTION
        "backend TCP optimization policy"
    ::= { fltCurCfgTableEntry 110 }
    
fltCurCfgComppol OBJECT-TYPE
    SYNTAX   DisplayString (SIZE(0..32))
    MAX-ACCESS  read-only
    STATUS  current
    DESCRIPTION
        "Compression policy name associated with this filter."
    ::= { fltCurCfgTableEntry 111 }

fltCurCfgSslInspectionEna OBJECT-TYPE
    SYNTAX  INTEGER {
        enabled(1),
        disabled(2),
        unsupported(2147483647)
        }
    MAX-ACCESS  read-only
    STATUS  current
    DESCRIPTION
        "Enable or disable SSL inspection inspection."
    ::= { fltCurCfgTableEntry 112 }

fltCurCfgSrvCertGroup OBJECT-TYPE
    SYNTAX  INTEGER {
        group(1),
        cert(2),
	none(3),
        unsupported(2147483647)
        }
    MAX-ACCESS  read-only
    STATUS  current
    DESCRIPTION
        "Server Certificate or Group."
    ::= { fltCurCfgTableEntry 113 }


fltCurCfgSrvCert OBJECT-TYPE
    SYNTAX   DisplayString (SIZE(0..32))
    MAX-ACCESS  read-only
    STATUS  current
    DESCRIPTION
        "Server certificate / group name associated with this filter."
    ::= { fltCurCfgTableEntry 114 }
        

fltCurCfgSslPolicy OBJECT-TYPE
    SYNTAX   DisplayString (SIZE(0..32))
    MAX-ACCESS  read-only
    STATUS  current
    DESCRIPTION
        "SSL policy name associated with this filter."
    ::= { fltCurCfgTableEntry 115 }

fltCurCfgMatchDev OBJECT-TYPE
   SYNTAX  INTEGER {
       allexclif(1),
       all(2),
       none(3),
        unsupported(2147483647)
   }
   MAX-ACCESS  read-only
   STATUS  current
   DESCRIPTION
        "Match device IP addresses in this filter:
         allexclif : match all device IPs, but exclude interface IPs
         all       : match all device IPs
         none      : match no device IPs"
   ::= { fltCurCfgTableEntry 116 }

fltCurCfgSslL7Action OBJECT-TYPE
   SYNTAX  INTEGER {
       none(1),
       bypass(2),
       inspect(3),
        unsupported(2147483647)
   }
   MAX-ACCESS  read-only
   STATUS  current
   DESCRIPTION
       "Set SSL inspection action on L7 match."
   ::= { fltCurCfgTableEntry 117 }
   
fltCurCfgFallback OBJECT-TYPE
    SYNTAX  INTEGER {
        allow(1),
        deny(2),
        goto(5),
        contFlow(6),
        unsupported(2147483647)
        }
    MAX-ACCESS  read-only
    STATUS  current
    DESCRIPTION
        "Fallback action (group down)."
    ::= { fltCurCfgTableEntry 118 }

fltCurCfgFbgoto OBJECT-TYPE
    SYNTAX  Integer32
    MAX-ACCESS  read-only
    STATUS  current	
    DESCRIPTION
        "The filter ID for GOTO fallback action in the current config."
    ::= { fltCurCfgTableEntry 119 }
    
fltCurCfgVpnFlood OBJECT-TYPE
   SYNTAX  INTEGER {
       enabled(1),
       disabled(2),
        unsupported(2147483647)
   }
   MAX-ACCESS  read-only
   STATUS  current
   DESCRIPTION
       "Enable or disable Two Way VPN LB."
   ::= { fltCurCfgTableEntry 120 }   
   
fltCurCfgUrlFltPol OBJECT-TYPE
    SYNTAX   DisplayString (SIZE(0..32))
    MAX-ACCESS  read-only
    STATUS  current
    DESCRIPTION
        "The url filter policy of the filter."
    ::= { fltCurCfgTableEntry 121 }	 

fltCurCfgPorts	OBJECT-TYPE
    SYNTAX  OCTET STRING
    MAX-ACCESS  read-only
    STATUS  current
    DESCRIPTION
        "The port list in the filter. The ports are presented in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the filter
		   0 - The represented port does not belong to the filter"
    ::= { fltCurCfgTableEntry 122 }

fltCurCfgFbport OBJECT-TYPE
    SYNTAX  Integer32
    MAX-ACCESS  read-only
    STATUS  current	
    DESCRIPTION
        "The ingress port for fallback action continueFlow in the current config."
    ::= { fltCurCfgTableEntry 123 }

fltCurCfgSetIndex OBJECT-TYPE
    SYNTAX  Integer32
    MAX-ACCESS  read-only
    STATUS  current	
    DESCRIPTION
        "Group Index of filters on same tunnel."
    ::= { fltCurCfgTableEntry 124 }

fltCurCfgReportState OBJECT-TYPE
    SYNTAX  INTEGER {
        disabled(0),
        enabled(1),
        unsupported(2147483647)
        }
    MAX-ACCESS  read-only
    STATUS  current
    DESCRIPTION
        "Enable or disable filter inspect reporting."
    ::= { fltCurCfgTableEntry 125 }

fltCurCfgReportLocation OBJECT-TYPE
    SYNTAX  INTEGER {
        none(0),
        clientside(1),
        serverside(2),
        unsupported(2147483647)
        }
    MAX-ACCESS  read-only
    STATUS  current
    DESCRIPTION
        "get filter location none/client/server."
    ::= { fltCurCfgTableEntry 126 }

fltCurCfgReportPurpose OBJECT-TYPE
    SYNTAX  INTEGER {
        none(0),
        bypass(1),
        inspect(2),
        unsupported(2147483647)
        }
    MAX-ACCESS  read-only
    STATUS  current
    DESCRIPTION
        "get filter purpose none/bypass/inspect."
    ::= { fltCurCfgTableEntry 127 }

fltCurCfgReportAppl OBJECT-TYPE
    SYNTAX  INTEGER {
        none(0),
        https(1),
        http(2),
        unsupported(2147483647)
        }
    MAX-ACCESS  read-only
    STATUS  current
    DESCRIPTION
        "get filter application none/https/http."
    ::= { fltCurCfgTableEntry 128 }

fltCurCfgReportDir OBJECT-TYPE
    SYNTAX  INTEGER {
        outbound(0),
        inbound(1),
        none(2),
        unsupported(2147483647)
        }
    MAX-ACCESS  read-only
    STATUS  current
    DESCRIPTION
        "get filter direction inbound/outbound."
    ::= { fltCurCfgTableEntry 129 }

fltCurCfgIcapPol OBJECT-TYPE
    SYNTAX   DisplayString (SIZE(0..32))
    MAX-ACCESS  read-only
    STATUS  current
    DESCRIPTION
        "The icap policy of the filter."
    ::= { fltCurCfgTableEntry 130 }

fltCurCfgTrafficEventPol OBJECT-TYPE
    SYNTAX   DisplayString (SIZE(0..128))
    MAX-ACCESS  read-only
    STATUS  current
    DESCRIPTION
        "The traffic event policy of the filter."
    ::= { fltCurCfgTableEntry 131 }

fltCurCfgDpmReportState OBJECT-TYPE
    SYNTAX  INTEGER {
        disabled(0),
        enabled(1),
        unsupported(2147483647)
        }
    MAX-ACCESS  read-only
    STATUS  current
    DESCRIPTION
        "Enable or disable filter dpm reporting."
    ::= { fltCurCfgTableEntry 132 }
    
fltCurCfgMacToMe OBJECT-TYPE
   SYNTAX  INTEGER {
       enabled(1),
       disabled(2),
       unsupported(2147483647)
   }
   MAX-ACCESS  read-only
   STATUS  current
   DESCRIPTION
       "Enable/disable matching traffic to device mac addresses."
   ::= { fltCurCfgTableEntry 133 }

fltCurCfgSecwa OBJECT-TYPE
    SYNTAX   DisplayString (SIZE(0..32))
    MAX-ACCESS  read-only
    STATUS  current
    DESCRIPTION
        "Secured web application associated with this filter."
    ::= { fltCurCfgTableEntry 134 }

fltCurCfgFbvlan OBJECT-TYPE
    SYNTAX  INTEGER (0..4090)
    MAX-ACCESS  read-only
    STATUS  current
    DESCRIPTION
        "The ingress VLAN ID for fallback action continueFlow in the current config."
    ::= { fltCurCfgTableEntry 135 }

fltCurCfgUrlfmode OBJECT-TYPE
    SYNTAX  INTEGER (0..1)
    MAX-ACCESS  read-only
    STATUS  current
    DESCRIPTION
        "URL filter classification mode."
    ::= { fltCurCfgTableEntry 136 }

fltCurCfgRtSrcTnl OBJECT-TYPE
    SYNTAX  INTEGER {
        enabled(1),
        disabled(2),
        unsupported(2147483647)
        }
    MAX-ACCESS  read-only
    STATUS  current
    DESCRIPTION
        "Enable or disable Return to Source Tunnel."
    ::= { fltCurCfgTableEntry 137 }

-- New Config Filtering Table

fltNewCfgTable OBJECT-TYPE
    SYNTAX  SEQUENCE OF FltNewCfgTableEntry
    MAX-ACCESS  not-accessible
    STATUS  current
    DESCRIPTION
        "The filtering table in the new configuration block.
         Note:This mib is not supported for VX instance of Virtualization."
    ::= { filterCfg 3 }

fltNewCfgTableEntry OBJECT-TYPE
    SYNTAX  FltNewCfgTableEntry
    MAX-ACCESS  not-accessible
    STATUS  current
    DESCRIPTION
        "A row in the filtering table."
    INDEX   { fltNewCfgIndx }
    ::= { fltNewCfgTable 1 }

FltNewCfgTableEntry ::= SEQUENCE {
    fltNewCfgIndx             Integer32,
    fltNewCfgSrcIpMac         INTEGER,
    fltNewCfgSrcIp            IpAddress,
    fltNewCfgSrcIpMask        IpAddress,
    fltNewCfgDstIpMac         INTEGER,
    fltNewCfgDstIp            IpAddress,
    fltNewCfgDstIpMask        IpAddress,
    fltNewCfgProtocol         INTEGER,
    fltNewCfgRangeLowSrcPort  INTEGER,
    fltNewCfgRangeHighSrcPort INTEGER,
    fltNewCfgRangeLowDstPort  INTEGER,
    fltNewCfgRangeHighDstPort INTEGER,
    fltNewCfgAction           INTEGER,
    fltNewCfgRedirPort        INTEGER,
    fltNewCfgRedirGroup       Integer32,
    fltNewCfgLog              INTEGER,
    fltNewCfgState            INTEGER,
    fltNewCfgNat              INTEGER,
    fltNewCfgCache            INTEGER,
    fltNewCfgInvert           INTEGER,
    fltNewCfgClientProxy      INTEGER,
    fltNewCfgTcpAck           INTEGER,
    fltNewCfgSrcMac           PhysAddress,
    fltNewCfgDstMac           PhysAddress,
    fltNewCfgFtpNatActive     INTEGER,
    fltNewCfgAclTcpUrg        INTEGER,
    fltNewCfgAclTcpAck        INTEGER,
    fltNewCfgAclTcpPsh        INTEGER,
    fltNewCfgAclTcpRst        INTEGER,
    fltNewCfgAclTcpSyn        INTEGER,
    fltNewCfgAclTcpFin        INTEGER,
    fltNewCfgAclIcmp          INTEGER,
    fltNewCfgAclIpOption      INTEGER,
    fltNewCfgBwmContract      Integer32,
    fltNewCfgAclIpTos	      INTEGER,
    fltNewCfgAclIpTosMask     INTEGER,
    fltNewCfgAclIpTosNew      INTEGER,
    fltNewCfgFwlb             INTEGER,
    fltNewCfgNatTimeout	      INTEGER,
    fltNewCfgLinklb           INTEGER,
    fltNewCfgWapRadiusSnoop   INTEGER,
    fltNewCfgIdslbHash        INTEGER,
    fltNewCfgVlan             INTEGER,
    fltNewCfgName             DisplayString,
    fltNewCfgTcpRateLimit     INTEGER,
    fltNewCfgTcpRateMaxConn   INTEGER,
    fltNewCfgHash             INTEGER,
    fltNewCfgLayer7DenyState  INTEGER,
    fltNewCfgLayer7DenyUrlBmap OCTET STRING,
    fltNewCfgLayer7DenyAddUrl Integer32,
    fltNewCfgLayer7DenyRemUrl Integer32,
    fltNewCfgGotoFilter       Integer32,
    fltNewCfgRadiusWapPersist INTEGER,
    fltNewCfgPbind            INTEGER,
    fltNewCfgTimeWindow       INTEGER,
    fltNewCfgHoldDuration     INTEGER,
    fltNewCfgProxyIp          IpAddress,
    fltNewCfgPatternMatch     INTEGER,
    fltNewCfgLayer7DenyMatchAll INTEGER,
    fltNewCfgLayer7ParseAll   INTEGER,
    fltNewCfgSecurityParseAll INTEGER,
    fltNewCfgPatternMatchGroupBmap OCTET STRING,
    fltNewCfgAddPatternMatchGroup  Integer32,
    fltNewCfgRemPatternMatchGroup Integer32,
    fltNewCfg8021pBitsValue   INTEGER,
    fltNewCfg8021pBitsMatch   INTEGER,
    fltNewCfgAclIpLength      INTEGER,
    fltNewCfgIdsGroup         Integer32,
    fltNewCfgEgressPip        INTEGER,
    fltNewCfgDbind            INTEGER,
    fltNewCfgReverse          INTEGER,
    fltNewCfgRevBwmContract   Integer32,
    fltNewCfgParseChn         INTEGER,
    fltNewCfgRtpBwmContract   Integer32,
    fltNewCfgSipParsing       INTEGER,
    fltNewCfgSessionMirror    INTEGER,
    fltNewCfgIpVer            INTEGER,
    fltNewCfgIpv6Sip          DisplayString,
    fltNewCfgIpv6Sprefix      INTEGER,
    fltNewCfgIpv6Dip          DisplayString,
    fltNewCfgIpv6Dprefix      INTEGER,
    fltNewCfgHdrHash          INTEGER,
    fltNewCfgHdrName          DisplayString,
    fltNewCfgHdrHashLen       INTEGER,
    fltNewCfgL3Filter          INTEGER,
    fltNewCfgDelete           INTEGER,
    fltNewCfgNatIp            IpAddress,
    fltNewCfgIpv6Nip          DisplayString,
    fltNewCfgIpv6Proxy        DisplayString,    
    fltNewCfgL7SipFilt        INTEGER,
    fltNewCfgNatMcastVlan     INTEGER,
    fltNewCfgNbind            INTEGER,
    fltNewCfgLayer7InvertAction   INTEGER,
    fltNewCfgSrcClassId       DisplayString,
    fltNewCfgDstClassId       DisplayString,
    fltNewCfgRtsrcmac	      INTEGER,
    fltNewCfgRtproxy   	      INTEGER,
    fltNewCfgSesslog          INTEGER,
    fltNewCfgCntclass         DisplayString,
    fltNewCfgApplicType       INTEGER,
    fltNewCfgRtsport          INTEGER,
    fltNewCfgSrcAddrType   INTEGER,
    fltNewCfgDstAddrType      INTEGER,
    fltNewCfgCosStr           DisplayString,
    fltNewCfgUdpAge           INTEGER,
    fltNewCfgFeTcpPolId       DisplayString,
    fltNewCfgBeTcpPolId       DisplayString,
    fltNewCfgComppol          DisplayString,
    fltNewCfgSslInspectionEna       INTEGER,
    fltNewCfgSrvCertGroup           INTEGER,
    fltNewCfgSrvCert          DisplayString,
    fltNewCfgSslPolicy        DisplayString,
    fltNewCfgMatchDev         INTEGER,
    fltNewCfgSslL7Action      INTEGER,
    fltNewCfgFallback         INTEGER,
    fltNewCfgFbgoto           Integer32,
    fltNewCfgVpnFlood	      INTEGER,
    fltNewCfgUrlFltPol	      DisplayString,
    fltNewCfgPorts	      OCTET STRING,
    fltNewCfgAddPort	      Integer32,
    fltNewCfgRemovePort	      Integer32,
    fltNewCfgFbport           Integer32,
    fltNewCfgSetIndex         Integer32,
    fltNewCfgMacToMe          INTEGER,
    fltNewCfgFbvlan           INTEGER,
    fltNewCfgUrlfmode           INTEGER
}

fltNewCfgIndx OBJECT-TYPE
    SYNTAX  Integer32
    MAX-ACCESS  read-only
    STATUS  current
    DESCRIPTION
        "The filtering table index."
    ::= { fltNewCfgTableEntry 1 }

fltNewCfgSrcIp OBJECT-TYPE
    SYNTAX  IpAddress
    MAX-ACCESS  read-create
    STATUS  current
    DESCRIPTION
        "The source IP address to be filtered."
    ::= { fltNewCfgTableEntry 2 }

fltNewCfgSrcIpMask OBJECT-TYPE
    SYNTAX  IpAddress
    MAX-ACCESS  read-create
    STATUS  current
    DESCRIPTION
        "The source IP sub-net mask for filtering."
    ::= { fltNewCfgTableEntry 3 }

fltNewCfgDstIp OBJECT-TYPE
    SYNTAX  IpAddress
    MAX-ACCESS  read-create
    STATUS  current
    DESCRIPTION
        "The destination IP address to be filtered."
    ::= { fltNewCfgTableEntry 4 }

fltNewCfgDstIpMask OBJECT-TYPE
    SYNTAX  IpAddress
    MAX-ACCESS  read-create
    STATUS  current
    DESCRIPTION
        "The destination IP sub-net mask for filtering."
    ::= { fltNewCfgTableEntry 5 }

fltNewCfgProtocol OBJECT-TYPE
    SYNTAX  INTEGER (0..255)
    MAX-ACCESS  read-create
    STATUS  current
    DESCRIPTION
        "The protocol to be filtered."
    ::= { fltNewCfgTableEntry 6 }

fltNewCfgRangeHighSrcPort OBJECT-TYPE
    SYNTAX  INTEGER (0..65534)
    MAX-ACCESS  read-create
    STATUS  current
    DESCRIPTION
        "The higher source TCP/UDP port number to be filtered. It applies 
         only when protocol defined in fltNewCfgProtocol is UDP or TCP. 
         '0' means no filtering."
    ::= { fltNewCfgTableEntry 7 }

fltNewCfgRangeLowSrcPort OBJECT-TYPE
    SYNTAX  INTEGER (0..65534)
    MAX-ACCESS  read-create
    STATUS  current
    DESCRIPTION
        "The lower source TCP/UDP port number to be filtered. It applies 
         only when protocol defined in fltNewCfgProtocol is UDP or TCP. 
         '0' means no filtering."
    ::= { fltNewCfgTableEntry 8 }

fltNewCfgRangeLowDstPort OBJECT-TYPE
    SYNTAX  INTEGER (0..65534)
    MAX-ACCESS  read-create
    STATUS  current
    DESCRIPTION
        "The lower destination TCP/UDP port number to be filtered.
         It applies only when protocol defined in fltNewCfgProtocol
	 is UDP or TCP.  '0' means no filtering."
    ::= { fltNewCfgTableEntry 9 }

fltNewCfgRangeHighDstPort OBJECT-TYPE
    SYNTAX  INTEGER (0..65534)
    MAX-ACCESS  read-create
    STATUS  current
    DESCRIPTION
        "The higher destination TCP/UDP port number to be filtered.
         It applies only when protocol defined in fltNewCfgProtocol
         is UDP or TCP.  '0' means no filtering."
    ::= { fltNewCfgTableEntry 10 }

fltNewCfgAction OBJECT-TYPE
    SYNTAX  INTEGER {
        allow(1),
        deny(2),
        redirect(3),
        nat(4),      -- network address translation
        goto(5),
	outbound-llb(6),
        unsupported(2147483647)
        }
    MAX-ACCESS  read-create
    STATUS  current
    DESCRIPTION
        "The action for the filtering rule."
    ::= { fltNewCfgTableEntry 11 }

fltNewCfgRedirPort OBJECT-TYPE
    SYNTAX  INTEGER (0..65534)
    MAX-ACCESS  read-create
    STATUS  current
    DESCRIPTION
        "The real server port number used for redirection."
    ::= { fltNewCfgTableEntry 12 }

fltNewCfgRedirGroup OBJECT-TYPE
    SYNTAX  Integer32
    MAX-ACCESS  read-create
    STATUS  current
    DESCRIPTION
        "The real server group to be redirected to."
    ::= { fltNewCfgTableEntry 13 }

fltNewCfgLog OBJECT-TYPE
    SYNTAX  INTEGER {
        enabled(1),
        disabled(2),
        unsupported(2147483647)
        }
    MAX-ACCESS  read-create
    STATUS  current
    DESCRIPTION
        "Enable or disable logging."
    ::= { fltNewCfgTableEntry 14 }

fltNewCfgState OBJECT-TYPE
    SYNTAX  INTEGER {
        enabled(1),
        disabled(2),
        unsupported(2147483647)
        }
    MAX-ACCESS  read-create
    STATUS  current
    DESCRIPTION
        "The state of this filtering rule."
    ::= { fltNewCfgTableEntry 15 }

fltNewCfgDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { fltNewCfgTableEntry 16 }

fltNewCfgNat OBJECT-TYPE
    SYNTAX  INTEGER {
        destination-address(1),
        source-address(2),
	multicast-address(3),
        unsupported(2147483647)
        }
    MAX-ACCESS  read-create
    STATUS  current
    DESCRIPTION
        "The selection of destination or source or multicast for 
         network address translation."
    ::= { fltNewCfgTableEntry 17 }

fltNewCfgCache OBJECT-TYPE
    SYNTAX  INTEGER {
        enabled(1),
        disabled(2),
        unsupported(2147483647)
        }
    MAX-ACCESS  read-create
    STATUS  current
    DESCRIPTION
        "Enable or disable caching sessions that match filter."
    ::= { fltNewCfgTableEntry 18 }

fltNewCfgInvert OBJECT-TYPE
    SYNTAX  INTEGER {
        enabled(1),
        disabled(2),
        unsupported(2147483647)
        }
    MAX-ACCESS  read-create
    STATUS  current
    DESCRIPTION
        "Turn the invert logic on or off for the filter entry."
    ::= { fltNewCfgTableEntry 19 }

fltNewCfgClientProxy OBJECT-TYPE
    SYNTAX  INTEGER {
        enabled(1),
        disabled(2),
        unsupported(2147483647)
        }
    MAX-ACCESS  read-create
    STATUS  current
    DESCRIPTION
        "Enable or disable client proxy."
    ::= { fltNewCfgTableEntry 20 }

fltNewCfgTcpAck OBJECT-TYPE
    SYNTAX  INTEGER {
        enabled(1),
        disabled(2),
        unsupported(2147483647)
        }
    MAX-ACCESS  read-create
    STATUS  current
    DESCRIPTION
        "Enable or disable filtering on matching TCP ACK and RST flag."
    ::= { fltNewCfgTableEntry 21 }

fltNewCfgSrcMac OBJECT-TYPE
    SYNTAX  PhysAddress 
    MAX-ACCESS  read-create
    STATUS  current
    DESCRIPTION
        "The source MAC address to be filtered."
    ::= { fltNewCfgTableEntry 23 }

fltNewCfgDstMac OBJECT-TYPE
    SYNTAX  PhysAddress 
    MAX-ACCESS  read-create
    STATUS  current
    DESCRIPTION
        "The Destination MAC address to be filtered."
    ::= { fltNewCfgTableEntry 24 }

fltNewCfgFtpNatActive OBJECT-TYPE
    SYNTAX  INTEGER {
        enabled(1),	
	disabled(2),
        unsupported(2147483647)
	}	
    MAX-ACCESS  read-create
    STATUS  current
    DESCRIPTION
        "Enable or disable FTP NAT for active ftp."
    ::= { fltNewCfgTableEntry 25 }	

-- New Config TCP Flag ACL Filtering Table

fltNewCfgAclTcpUrg OBJECT-TYPE
    SYNTAX  INTEGER {
	enable(1),
	disable(2),
        unsupported(2147483647)
	}	
    MAX-ACCESS  read-create
    STATUS  current
    DESCRIPTION
	"Enable or disable TCP URG packet."
    ::= { fltNewCfgTableEntry 26 }	

fltNewCfgAclTcpAck OBJECT-TYPE
    SYNTAX  INTEGER {
	enable(1),
	disable(2),
        unsupported(2147483647)
	}	
    MAX-ACCESS  read-create
    STATUS  current
    DESCRIPTION
        "Enable or disable TCP ACK packet."
    ::= { fltNewCfgTableEntry 27 }	

fltNewCfgAclTcpPsh OBJECT-TYPE
    SYNTAX  INTEGER {
	enable(1),
	disable(2),
        unsupported(2147483647)
	}	
    MAX-ACCESS  read-create
    STATUS  current
    DESCRIPTION
        "Enable or disable TCP PSH packet."
    ::= { fltNewCfgTableEntry 28 }	

fltNewCfgAclTcpRst OBJECT-TYPE
    SYNTAX  INTEGER {
	enable(1),
	disable(2),
        unsupported(2147483647)
	}	
    MAX-ACCESS  read-create
    STATUS  current
    DESCRIPTION
        "Enable or disable TCP RST packet."
    ::= { fltNewCfgTableEntry 29 }	

fltNewCfgAclTcpSyn OBJECT-TYPE
    SYNTAX  INTEGER {
	enable(1),
	disable(2),
        unsupported(2147483647)
	}	
    MAX-ACCESS  read-create
    STATUS  current
    DESCRIPTION
        "Enable or disable TCP SYN packet."
    ::= { fltNewCfgTableEntry 30 }	

fltNewCfgAclTcpFin OBJECT-TYPE
    SYNTAX  INTEGER {
	enable(1),
	disable(2),
        unsupported(2147483647)
	}	
    MAX-ACCESS  read-create
    STATUS  current
    DESCRIPTION
        "Enable or disable TCP FIN packet."
    ::= { fltNewCfgTableEntry 31 }	

-- New Config ICMP Type ACL Filtering Table

fltNewCfgAclIcmp OBJECT-TYPE
    SYNTAX  INTEGER (0..255) 
    MAX-ACCESS  read-create
    STATUS  current
    DESCRIPTION
        "ICMP type to be filtered. A ICMP type of 255 indicates 'any'"
    ::= { fltNewCfgTableEntry 32 }	

-- New Config IP Option ACL Filtering Table

fltNewCfgAclIpOption OBJECT-TYPE
    SYNTAX  INTEGER {
        enable(1),
        disable(2),
        unsupported(2147483647)
        }
    MAX-ACCESS  read-create
    STATUS  current
    DESCRIPTION
        "Enable or disable IP option matching."
    ::= { fltNewCfgTableEntry 33 }

fltNewCfgBwmContract OBJECT-TYPE
    SYNTAX  Integer32 
    MAX-ACCESS  read-create
    STATUS  current
    DESCRIPTION
        "Filt default BW contract number."
    ::= { fltNewCfgTableEntry 34 }	

fltNewCfgAclIpTos OBJECT-TYPE
    SYNTAX  INTEGER (0..255)
    MAX-ACCESS  read-create
    STATUS  current
    DESCRIPTION
        "The IP TOS value to be filtered."
    ::= { fltNewCfgTableEntry 35 }	

fltNewCfgAclIpTosMask OBJECT-TYPE
    SYNTAX  INTEGER (0..255)
    MAX-ACCESS  read-create
    STATUS  current
    DESCRIPTION
        "The IP TOS mask for filtering."
    ::= { fltNewCfgTableEntry 36 }	

fltNewCfgAclIpTosNew OBJECT-TYPE
    SYNTAX  INTEGER (0..255)
    MAX-ACCESS  read-create
    STATUS  current
    DESCRIPTION
        "The new IP TOS value to over-write when filtering fired."
    ::= { fltNewCfgTableEntry 37 }	

fltNewCfgFwlb OBJECT-TYPE
    SYNTAX  INTEGER {
        enabled(1),
        disabled(2),
        unsupported(2147483647)
        }
    MAX-ACCESS  read-create
    STATUS  current
    DESCRIPTION
        "Enable or disable filtering on firewall redirect hash method."
    ::= { fltNewCfgTableEntry 38 }

fltNewCfgNatTimeout OBJECT-TYPE
    SYNTAX  INTEGER (4..32768)
    MAX-ACCESS  read-create
    STATUS  current
    DESCRIPTION
	"The NAT session timeout. The timeout value should be an even
         number between 4 and 32768."
    ::= { fltNewCfgTableEntry 39 }	

fltNewCfgLinklb OBJECT-TYPE
    SYNTAX  INTEGER {
        enabled(1),
        disabled(2),
        unsupported(2147483647)
        }
    MAX-ACCESS  read-create
    STATUS  current
    DESCRIPTION
        "Enable or disable WAN link load balancing."
    ::= { fltNewCfgTableEntry 40 }

fltNewCfgWapRadiusSnoop OBJECT-TYPE
    SYNTAX  INTEGER {
        enabled(1),
        disabled(2),
        unsupported(2147483647)
        }
    MAX-ACCESS  read-create
    STATUS  current
    DESCRIPTION
        "Enable or disable WAP RADIUS snooping."
    ::= { fltNewCfgTableEntry 41 }

fltNewCfgSrcIpMac OBJECT-TYPE
    SYNTAX  INTEGER {
        ip(1),
        mac(2),
        unsupported(2147483647)
        }
    MAX-ACCESS  read-create
    STATUS  current
    DESCRIPTION
        "Set a flag indicating whether filtering should be based on the 
         source IP address or the source MAC address field."
    ::= { fltNewCfgTableEntry 42 }

fltNewCfgDstIpMac OBJECT-TYPE
    SYNTAX  INTEGER {
        ip(1),
        mac(2),
        unsupported(2147483647)
        }
    MAX-ACCESS  read-create
    STATUS  current
    DESCRIPTION
        "Set a flag indicating whether filtering should be based on the 
         destination IP address or the destination MAC address field."
    ::= { fltNewCfgTableEntry 43 }

fltNewCfgIdslbHash OBJECT-TYPE
    SYNTAX  INTEGER {
        sip(1),
        dip(2),
        sipdip(3),
        sipsport(4),
        dipdport(5),
        all(6),
        unsupported(2147483647)
        }
    MAX-ACCESS  read-create
    STATUS  current
    DESCRIPTION
        "Set hash parameter for intrusion detection server load balancing."
    ::= { fltNewCfgTableEntry 44 }

fltNewCfgVlan OBJECT-TYPE
    SYNTAX  INTEGER (0..4090)
    MAX-ACCESS  read-create
    STATUS  current
    DESCRIPTION
        "Set the VLAN assoicated with the filter."
    ::= { fltNewCfgTableEntry 45 }

fltNewCfgName OBJECT-TYPE
    SYNTAX DisplayString (SIZE(0..31))
    MAX-ACCESS read-create
    STATUS current
    DESCRIPTION
        "The name of the filter."
    ::= { fltNewCfgTableEntry 46 }

fltNewCfgTcpRateLimit OBJECT-TYPE
    SYNTAX  INTEGER {
        enabled(1),
        disabled(2),
        unsupported(2147483647)
        }
    MAX-ACCESS  read-create
    STATUS  current
    DESCRIPTION
        "Enable or disable protocol rate limiting."
    ::= { fltNewCfgTableEntry 47 }

fltNewCfgTcpRateMaxConn OBJECT-TYPE
    SYNTAX  INTEGER (0..255)
    MAX-ACCESS  read-create
    STATUS  current
    DESCRIPTION
        "Set maximum connections (number of connections in units of 10)
         for TCP connection rate limiting. In the case of ICMP and UDP,
	 this is the maximum packets (number of packets in units of 10)."
    ::= { fltNewCfgTableEntry 48 }

fltNewCfgHash OBJECT-TYPE
    SYNTAX  INTEGER {
	auto(1),
        sip(2),
        dip(3),
        both(4),
	sipsport(5),
	dip32(6),
        unsupported(2147483647)
        }
    MAX-ACCESS  read-create
    STATUS  current
    DESCRIPTION
        "Set hash parameter for the filter."
    ::= { fltNewCfgTableEntry 49 }


fltNewCfgLayer7DenyState OBJECT-TYPE
    SYNTAX  INTEGER {
        enabled(1),
        disabled(2),
        unsupported(2147483647)
        }
    MAX-ACCESS  read-create
    STATUS  current
    DESCRIPTION
        "Enable or disable layer 7 deny filtering."
    ::= { fltNewCfgTableEntry 51 }

fltNewCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgTableEntry 52 }

fltNewCfgLayer7DenyAddUrl OBJECT-TYPE
    SYNTAX  Integer32
    MAX-ACCESS  read-create
    STATUS  current
    DESCRIPTION
        "The URL Path (slbCurCfgUrlLbPathIndex) to be added to the 
         Layer 7 deny filter. A zero is returned when read."
    ::= { fltNewCfgTableEntry 53 }

fltNewCfgLayer7DenyRemUrl OBJECT-TYPE
    SYNTAX  Integer32
    MAX-ACCESS  read-create
    STATUS  current
    DESCRIPTION
        "The URL Path (slbCurCfgUrlLbPathIndex) to be removed from 
         the Layer 7 deny filter. A zero is returned when read."
    ::= { fltNewCfgTableEntry 54 }

fltNewCfgGotoFilter OBJECT-TYPE
    SYNTAX  Integer32
    MAX-ACCESS  read-create
    STATUS  current	
    DESCRIPTION
        "The filter ID for GOTO action in the new config."
    ::= { fltNewCfgTableEntry 55 }

fltNewCfgRadiusWapPersist OBJECT-TYPE
    SYNTAX  INTEGER {
        enabled(1),
        disabled(2),
        unsupported(2147483647)
        }
    MAX-ACCESS  read-create
    STATUS  current	
    DESCRIPTION
        "Enable or disable Radius/WAP persistence."
    ::= { fltNewCfgTableEntry 56 }

fltNewCfgPbind OBJECT-TYPE
    SYNTAX  INTEGER {
        enabled(1),
        disabled(2),
        unsupported(2147483647)
        }
    MAX-ACCESS  read-create
    STATUS  current	
    DESCRIPTION
        "Enable or disable filter persistent binding."
    ::= { fltNewCfgTableEntry 57 }

fltNewCfgTimeWindow OBJECT-TYPE
    SYNTAX  INTEGER (1..65535)
    MAX-ACCESS  read-create
    STATUS  current
    DESCRIPTION
        "The time window for protocol rate limiting (in seconds)."
    ::= { fltNewCfgTableEntry 58 }

fltNewCfgHoldDuration OBJECT-TYPE
    SYNTAX  INTEGER (2..65535)
    MAX-ACCESS  read-create
    STATUS  current
    DESCRIPTION
        "The hold down duration for protocol rate limiting (in minutes)."
    ::= { fltNewCfgTableEntry 59 }

fltNewCfgPatternMatch OBJECT-TYPE
    SYNTAX  INTEGER {
        enabled(1),
        disabled(2),
        unsupported(2147483647)
        }
    MAX-ACCESS  read-create
    STATUS  current	
    DESCRIPTION
        "Enable or disable binary pattern matching."
    ::= { fltNewCfgTableEntry 60 }

fltNewCfgLayer7DenyMatchAll OBJECT-TYPE
    SYNTAX  INTEGER {
        enabled(1),
        disabled(2),
        unsupported(2147483647)
        }
    MAX-ACCESS  read-create
    STATUS  current
    DESCRIPTION
        "Enable or disable match-all criteria for L7 deny string matching."
    ::= { fltNewCfgTableEntry 61 }

fltNewCfgProxyIp OBJECT-TYPE
    SYNTAX  IpAddress
    MAX-ACCESS  read-create
    STATUS  current
    DESCRIPTION
        "The client proxy IP address for NAT and REDIR filter."
        
    ::= { fltNewCfgTableEntry 62 }

fltNewCfgLayer7ParseAll OBJECT-TYPE
    SYNTAX  INTEGER {
        enabled(1),
        disabled(2),
        unsupported(2147483647)
        }
    MAX-ACCESS  read-create
    STATUS  current
    DESCRIPTION
        "Enable or disable layer 7 lookup (parsing) of all packets."
    ::= { fltNewCfgTableEntry 63 }

fltNewCfgSecurityParseAll OBJECT-TYPE
    SYNTAX  INTEGER {
        enabled(1),
        disabled(2),
        unsupported(2147483647)
        }
    MAX-ACCESS  read-create
    STATUS  current
    DESCRIPTION
        "Enable or disable pattern string lookup (parsing) of all packets."
    ::= { fltNewCfgTableEntry 64 }

fltNewCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltNewCfgTableEntry 65 }
    
fltNewCfgAddPatternMatchGroup OBJECT-TYPE
    SYNTAX  Integer32
    MAX-ACCESS  read-create
    STATUS  current
    DESCRIPTION
        "The pattern match group to be added to the 
         security filter. A zero is returned when read."
    ::= { fltNewCfgTableEntry 66 }

fltNewCfgRemPatternMatchGroup OBJECT-TYPE
    SYNTAX  Integer32
    MAX-ACCESS  read-create
    STATUS  current
    DESCRIPTION
        "The pattern match group to be to be removed from 
         the security filter. A zero is returned when read."
    ::= { fltNewCfgTableEntry 67 }

fltNewCfg8021pBitsValue OBJECT-TYPE
    SYNTAX  INTEGER (0..7)
    MAX-ACCESS  read-create
    STATUS  current
    DESCRIPTION
        "The 802.1p bits value to match."
    ::= { fltNewCfgTableEntry 68 }

fltNewCfg8021pBitsMatch OBJECT-TYPE
    SYNTAX  INTEGER {
        enabled(1),
        disabled(2),
        unsupported(2147483647)
        }
    MAX-ACCESS  read-create
    STATUS  current
    DESCRIPTION
        "Enable or disable matching on 802.1p bits in the packets."
    ::= { fltNewCfgTableEntry 69 }
 
fltNewCfgAclIpLength OBJECT-TYPE
    SYNTAX  INTEGER (0..65535)
    MAX-ACCESS  read-create
    STATUS  current 
    DESCRIPTION
        "Set the IP maximum packet length in bytes. A value can be either 0 
         which indicates 'any' length or between 64 and 65535."
    ::= { fltNewCfgTableEntry 70 }	

fltNewCfgIdsGroup OBJECT-TYPE
    SYNTAX  Integer32
    MAX-ACCESS  read-create
    STATUS  current
    DESCRIPTION
        "The real server group for IDS load balancing. A value of 0 indicates
	 'none'." 
    ::= { fltNewCfgTableEntry 71 }
    
fltNewCfgEgressPip OBJECT-TYPE
    SYNTAX  INTEGER {
        enabled(1),
        disabled(2),
        unsupported(2147483647)
        }
    MAX-ACCESS  read-create
    STATUS  current
    DESCRIPTION
        "Enable or disable pip selection based on egress port/vlan."
    ::= { fltNewCfgTableEntry 72 }
    
fltNewCfgDbind OBJECT-TYPE
    SYNTAX  INTEGER {
        enabled(1),
        disabled(2),
	forceproxy(3),
        unsupported(2147483647)
        }
    MAX-ACCESS  read-create
    STATUS  current	
    DESCRIPTION
        "Enable or disable filter delayed binding."
    ::= { fltNewCfgTableEntry 73 }

fltNewCfgRevBwmContract OBJECT-TYPE
    SYNTAX  Integer32
    MAX-ACCESS  read-create
    STATUS  current
    DESCRIPTION
	"Filt reverse session BWM contract number."
    ::= { fltNewCfgTableEntry 74 }	

fltNewCfgReverse OBJECT-TYPE
    SYNTAX  INTEGER {
        enabled(1),
        disabled(2),
        unsupported(2147483647)
        }
    MAX-ACCESS  read-create
    STATUS  current	
    DESCRIPTION
        "Enable or disable creating session for reverse side traffic."
    ::= { fltNewCfgTableEntry 75 }

fltNewCfgParseChn OBJECT-TYPE
    SYNTAX  INTEGER {
	enabled(1),
	disabled(2),
        unsupported(2147483647)
	}
    MAX-ACCESS  read-create
    STATUS  current 
    DESCRIPTION
        "Enable or disable chained pgroup match criteria for l7 filtering."	 
    ::= { fltNewCfgTableEntry 76}


fltNewCfgRtpBwmContract OBJECT-TYPE
    SYNTAX  Integer32
    MAX-ACCESS  read-create
    STATUS  current
    DESCRIPTION
        "BWM contract for SIP RTP traffic."
    ::= { fltNewCfgTableEntry 77 }

fltNewCfgSipParsing OBJECT-TYPE
    SYNTAX  INTEGER {
        enabled(1),
        disabled(2),
        unsupported(2147483647)
        }
    MAX-ACCESS  read-create
    STATUS  current
    DESCRIPTION
        "Enable or disable SIP NAT."
    ::= { fltNewCfgTableEntry 78 }


    fltNewCfgSessionMirror  OBJECT-TYPE
    SYNTAX  INTEGER {
        enabled(1),
        disabled(2),
        unsupported(2147483647)
        }
    MAX-ACCESS  read-create
    STATUS  current
    DESCRIPTION
        "Enable or disable session mirroring."
    ::= { fltNewCfgTableEntry 79 }


fltNewCfgIpVer OBJECT-TYPE
    SYNTAX  INTEGER{
        ipv4(1),
        ipv6(2),
        unsupported(2147483647)
        }
    MAX-ACCESS  read-create
    STATUS  current
    DESCRIPTION
        "The type of IP address."
    ::= { fltNewCfgTableEntry 80 }

fltNewCfgIpv6Sip  OBJECT-TYPE
    SYNTAX   DisplayString (SIZE(0..40))
    MAX-ACCESS  read-create
    STATUS  current
    DESCRIPTION
        "The source IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgTableEntry 81 }

fltNewCfgIpv6Sprefix   OBJECT-TYPE
    SYNTAX   INTEGER(0..128) 
    MAX-ACCESS  read-create
    STATUS  current
    DESCRIPTION
        "The prefix length associated with source IP address ."
    ::= { fltNewCfgTableEntry 82 }

fltNewCfgIpv6Dip   OBJECT-TYPE
    SYNTAX   DisplayString (SIZE(0..40))
    MAX-ACCESS  read-create
    STATUS  current
    DESCRIPTION
        "The destination  IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgTableEntry 83 }

fltNewCfgIpv6Dprefix   OBJECT-TYPE
    SYNTAX  INTEGER(0..128) 
    MAX-ACCESS  read-create
    STATUS  current
    DESCRIPTION
        "The prefix length associated with destination IP address ."
    ::= { fltNewCfgTableEntry 84 }

fltNewCfgHdrHash OBJECT-TYPE
       SYNTAX  INTEGER {
        none(1),
        headerhash(2),
        unsupported(2147483647)
        }
    MAX-ACCESS read-create
    STATUS current
    DESCRIPTION
        "The header hash filter."
    ::= { fltNewCfgTableEntry 85 }

fltNewCfgHdrName OBJECT-TYPE
    SYNTAX DisplayString (SIZE(0..31))
    MAX-ACCESS read-create
    STATUS current
    DESCRIPTION
        "The header name of the filter. Headerhash should be
         enabled before header name is configured."
    ::= { fltNewCfgTableEntry 86 }

fltNewCfgHdrHashLen OBJECT-TYPE
    SYNTAX  INTEGER (1..255)
    MAX-ACCESS  read-create
    STATUS  current
    DESCRIPTION
        "The header hash length of the filter. Headerhash should be
         enabled before hash length is configured."
    ::= { fltNewCfgTableEntry 87 }

fltNewCfgL3Filter OBJECT-TYPE
    SYNTAX  INTEGER {
        enabled(1),
        disabled(2),
        unsupported(2147483647)
    }
    MAX-ACCESS  read-create
    STATUS  current
    DESCRIPTION
        "The L3 filter processing state for this filter."
    ::= { fltNewCfgTableEntry 88}


fltNewCfgNatIp OBJECT-TYPE
    SYNTAX  IpAddress
    MAX-ACCESS  read-write
    STATUS  current
    DESCRIPTION
        "The nat IP address to be filtered."
    ::= { fltNewCfgTableEntry 89 }

fltNewCfgIpv6Nip   OBJECT-TYPE
    SYNTAX   DisplayString (SIZE(0..40))
    MAX-ACCESS  read-write
    STATUS  current
    DESCRIPTION
        "The nat IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgTableEntry 90 }

fltNewCfgIpv6Proxy  OBJECT-TYPE
    SYNTAX   DisplayString (SIZE(0..40))
    MAX-ACCESS  read-write
    STATUS  current
    DESCRIPTION
        "The proxy IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgTableEntry 91 }
    
fltNewCfgL7SipFilt OBJECT-TYPE
    SYNTAX  INTEGER {
        enabled(1),
        disabled(2),
        unsupported(2147483647)
        }
    MAX-ACCESS  read-write
    STATUS  current
    DESCRIPTION
        "Enable/Disable L7 application SIP UDP filtering."
    ::= { fltNewCfgTableEntry 92 }

fltNewCfgNatMcastVlan OBJECT-TYPE
    SYNTAX  INTEGER (0..4090)
    MAX-ACCESS  read-write
    STATUS  current
    DESCRIPTION
        "Multicast VLAN."
    ::= { fltNewCfgTableEntry 93 }

fltNewCfgNbind OBJECT-TYPE
    SYNTAX  INTEGER {
        enabled(1),
        disabled(2),
        unsupported(2147483647)
    }
    MAX-ACCESS  read-create
    STATUS  current
    DESCRIPTION
        "Enable or disable subnet binding for redirection."
    ::= { fltNewCfgTableEntry 94 }

fltNewCfgLayer7InvertAction OBJECT-TYPE
    SYNTAX  INTEGER {
        enabled(1),
        disabled(2),
        unsupported(2147483647)
        }
    MAX-ACCESS  read-create
    STATUS  current
    DESCRIPTION
        "Enable or disable invert action for layer 7 string matching."
    ::= { fltNewCfgTableEntry 95 }

fltNewCfgSrcClassId  OBJECT-TYPE
    SYNTAX   DisplayString (SIZE(0..32))
    MAX-ACCESS  read-create
    STATUS  current
    DESCRIPTION
        "The source network class ID to be filtered."
    ::= { fltNewCfgTableEntry 96 }

fltNewCfgDstClassId  OBJECT-TYPE
    SYNTAX   DisplayString (SIZE(0..32))
    MAX-ACCESS  read-create
    STATUS  current
    DESCRIPTION
        "The destination network class ID to be filtered."
    ::= { fltNewCfgTableEntry 97 }

fltNewCfgRtsrcmac OBJECT-TYPE
    SYNTAX  INTEGER {
        enabled(1),
        disabled(2),
        unsupported(2147483647)
        }
    MAX-ACCESS  read-create
    STATUS  current
    DESCRIPTION
        "Enable or disable return to source mac addr."
    ::= { fltNewCfgTableEntry 98 }

fltNewCfgRtproxy OBJECT-TYPE
    SYNTAX  INTEGER {
        enabled(1),
        disabled(2),
        unsupported(2147483647)
        }
    MAX-ACCESS  read-create
    STATUS  current
    DESCRIPTION
        "Enable or disable redirect to proxy server."
    ::= { fltNewCfgTableEntry 99 }

fltNewCfgSesslog OBJECT-TYPE
    SYNTAX  INTEGER {
        enabled(1),
        disabled(2),
        unsupported(2147483647)
        }
    MAX-ACCESS  read-create
    STATUS  current
    DESCRIPTION
        "Enable or disable session logging."
    ::= { fltNewCfgTableEntry 100 }

fltNewCfgCntclass OBJECT-TYPE
    SYNTAX   DisplayString (SIZE(0..32))
    MAX-ACCESS  read-create
    STATUS  current
    DESCRIPTION
        "The cntclass of the filter."
    ::= { fltNewCfgTableEntry 101 }

fltNewCfgApplicType OBJECT-TYPE
    SYNTAX  INTEGER {
        none(1),
        basic(2),
        http(3),
        sip(4),
        dns(5),
        smtp(6),
        pop3(7),
        imap(8),
        ftp(9),
        unsupported(2147483647)
    }
    MAX-ACCESS  read-create
    STATUS  current
    DESCRIPTION
        "Application type for this filter."
    ::= { fltNewCfgTableEntry 102 }

fltNewCfgRtsport OBJECT-TYPE
    SYNTAX  INTEGER {
        mod5060(1),
        preserve(2),
        disabled(3),
        unsupported(2147483647)
    }
    MAX-ACCESS  read-create
    STATUS  current
    DESCRIPTION
        "Source port modification for SIP.
         the mod5060 indicates modification of source port to 5060,
         preserve indicates to retain the source port."
    ::= { fltNewCfgTableEntry 103 }

fltNewCfgSrcAddrType OBJECT-TYPE
    SYNTAX  INTEGER {
        ipAddress(1),
        network(2),
        unsupported(2147483647)
    }
    MAX-ACCESS  read-create
    STATUS  current
    DESCRIPTION
         "Source address type from address and network for NAT filter."
    ::= { fltNewCfgTableEntry 104 }

fltNewCfgDstAddrType OBJECT-TYPE
    SYNTAX  INTEGER {
        ipAddress(1),
        network(2),
        unsupported(2147483647)
    }
    MAX-ACCESS  read-create
    STATUS  current
    DESCRIPTION
        "Destination address type from address and network for NAT filter."
    ::= { fltNewCfgTableEntry 105 }

fltNewCfgCosStr OBJECT-TYPE
    SYNTAX   DisplayString (SIZE(0..32))
    MAX-ACCESS  read-create
    STATUS  current
    DESCRIPTION
        "The class of service of the filter.
	Empty string - ignore cos
	'Any' string - ignore string use only the source IP
	Specific string - match only if the string matches"
    ::= { fltNewCfgTableEntry 106 }

fltNewCfgUdpAge OBJECT-TYPE
    SYNTAX  INTEGER {
        onlydns(1),
        disabled(2),
        enabled(3),
        unsupported(2147483647)
    }
    MAX-ACCESS  read-create
    STATUS  current
    DESCRIPTION
        "Udp Aging type for this filter."
    ::= { fltNewCfgTableEntry 107 }

fltNewCfgFeTcpPolId OBJECT-TYPE
    SYNTAX   DisplayString (SIZE(0..32))
    MAX-ACCESS  read-create
    STATUS  current
    DESCRIPTION
        "frontend TCP optimization policy"
    ::= { fltNewCfgTableEntry 108 }

fltNewCfgBeTcpPolId OBJECT-TYPE
    SYNTAX   DisplayString (SIZE(0..32))
    MAX-ACCESS  read-create
    STATUS  current
    DESCRIPTION
        "backend TCP optimization policy"
    ::= { fltNewCfgTableEntry 109 }
    
fltNewCfgComppol OBJECT-TYPE
    SYNTAX   DisplayString (SIZE(0..32))
    MAX-ACCESS  read-create
    STATUS  current
    DESCRIPTION
        "Compression policy name associated with this filter."
    ::= { fltNewCfgTableEntry 110 }

fltNewCfgSslInspectionEna OBJECT-TYPE
    SYNTAX  INTEGER {
        enabled(1),
        disabled(2),
        unsupported(2147483647)
        }
    MAX-ACCESS  read-create
    STATUS  current
    DESCRIPTION
        "Enable or disable SSL session inspection."
    ::= { fltNewCfgTableEntry 111 }
    
fltNewCfgSrvCertGroup OBJECT-TYPE
    SYNTAX  INTEGER {
        group(1),
        cert(2),
	none(3),
        unsupported(2147483647)
        }
    MAX-ACCESS  read-create
    STATUS  current
    DESCRIPTION
        "Set Certificate group or cert."
    ::= { fltNewCfgTableEntry 112 }

fltNewCfgSrvCert OBJECT-TYPE
    SYNTAX   DisplayString (SIZE(0..128))
    MAX-ACCESS  read-create
    STATUS  current
    DESCRIPTION
        "Server certificate / group name associated with this filter."
    ::= { fltNewCfgTableEntry 113 }
    
fltNewCfgSslPolicy OBJECT-TYPE
    SYNTAX   DisplayString (SIZE(0..32))
    MAX-ACCESS  read-create
    STATUS  current
    DESCRIPTION
        "SSL policy name associated with this filter."
    ::= { fltNewCfgTableEntry 114 }

fltNewCfgMatchDev OBJECT-TYPE
    SYNTAX  INTEGER {
        allexclif(1),
        all(2),
        none(3),
        unsupported(2147483647)
    }
    MAX-ACCESS  read-create
    STATUS  current
    DESCRIPTION
        "Match device IP addresses in this filter:
         allexclif : match all device IPs, but exclude interface IPs
         all       : match all device IPs
         none      : match no device IPs"
    ::= { fltNewCfgTableEntry 115 }
   
fltNewCfgSslL7Action OBJECT-TYPE
   SYNTAX  INTEGER {
       none(1),
       bypass(2),
       inspect(3),
       unsupported(2147483647)
   }
   MAX-ACCESS  read-create
   STATUS  current
   DESCRIPTION
       "Set SSL inspection action on L7 match."
   ::= { fltNewCfgTableEntry 116 }

fltNewCfgFallback OBJECT-TYPE
    SYNTAX  INTEGER {
        allow(1),
        deny(2),
        goto(5),
        contFlow(6),
        unsupported(2147483647)
        }
    MAX-ACCESS  read-create
    STATUS  current
    DESCRIPTION
        "Fallback action (group down)."
    ::= { fltNewCfgTableEntry 117 }

fltNewCfgFbgoto OBJECT-TYPE
    SYNTAX  Integer32
    MAX-ACCESS  read-create
    STATUS  current	
    DESCRIPTION
        "The filter ID for GOTO fallback action in the new config."
    ::= { fltNewCfgTableEntry 118 }

fltNewCfgVpnFlood OBJECT-TYPE
    SYNTAX  INTEGER {
        enabled(1),
        disabled(2),
        unsupported(2147483647)
    }
    MAX-ACCESS  read-create
    STATUS  current
    DESCRIPTION
        "Enable or disable Two Way VPN LB."
    ::= { fltNewCfgTableEntry 119 }


fltNewCfgUrlFltPol OBJECT-TYPE
    SYNTAX   DisplayString (SIZE(0..32))
    MAX-ACCESS  read-create
    STATUS  current
    DESCRIPTION
        "The url filter policy of the filter."
    ::= { fltNewCfgTableEntry 120 }

fltNewCfgPorts	OBJECT-TYPE
    SYNTAX  OCTET STRING
    MAX-ACCESS  read-only
    STATUS  current
    DESCRIPTION
        "The port list in the filter. The ports are presented in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the filter
		   0 - The represented port does not belong to the filter"
    ::= { fltNewCfgTableEntry 121 }

fltNewCfgAddPort OBJECT-TYPE
    SYNTAX  Integer32
    MAX-ACCESS  read-create
    STATUS  current
    DESCRIPTION
        "The port to be added to the specified filter.  A '0' value is 
         returned when read."
    ::= { fltNewCfgTableEntry 122 }

fltNewCfgRemovePort OBJECT-TYPE
    SYNTAX  Integer32
    MAX-ACCESS  read-create
    STATUS  current
    DESCRIPTION
        "The port to be removed from the specified filter.  A '0'
         value is returned when read."
    ::= { fltNewCfgTableEntry 123 }

fltNewCfgFbport OBJECT-TYPE
    SYNTAX  Integer32
    MAX-ACCESS  read-create
    STATUS  current	
    DESCRIPTION
        "The ingress port for fallback action continueFlow in the new config."
    ::= { fltNewCfgTableEntry 124 }
    
fltNewCfgSetIndex OBJECT-TYPE
    SYNTAX  Integer32
    MAX-ACCESS  read-create
    STATUS  current	
    DESCRIPTION
        "Group Index of filters on same tunnel."
    ::= { fltNewCfgTableEntry 125 }

fltNewCfgMacToMe OBJECT-TYPE
    SYNTAX  INTEGER {
        enabled(1),
        disabled(2),
        unsupported(2147483647)
    }
    MAX-ACCESS  read-create
    STATUS  current
    DESCRIPTION
        "Enable/disable matching traffic to device mac addresses."
    ::= { fltNewCfgTableEntry 126 }

fltNewCfgFbvlan OBJECT-TYPE
    SYNTAX  INTEGER (0..4090)
    MAX-ACCESS  read-create
    STATUS  current
    DESCRIPTION
        "The ingress VLAN ID for fallback action continueFlow in the new config."
    ::= { fltNewCfgTableEntry 127 }

fltNewCfgUrlfmode OBJECT-TYPE
    SYNTAX  INTEGER (0..1)
    MAX-ACCESS  read-create
    STATUS  current
    DESCRIPTION
        "URL filter classification mode."
    ::= { fltNewCfgTableEntry 128 }

fltNewCfgExtendedTable OBJECT-TYPE
    SYNTAX  SEQUENCE OF FltNewCfgExtendedTableEntry
    MAX-ACCESS  not-accessible
    STATUS  current
    DESCRIPTION
        "The filtering table in the new configuration block.
         Note:This mib is not supported for VX instance of Virtualization."
    ::= { filterCfg 12 }

fltNewCfgExtendedTableEntry OBJECT-TYPE
    SYNTAX  FltNewCfgExtendedTableEntry
    MAX-ACCESS  not-accessible
    STATUS  current
    DESCRIPTION
        "A row in the filtering table."
    INDEX   { fltNewCfgExtendedIndx }
    ::= { fltNewCfgExtendedTable 1 }

FltNewCfgExtendedTableEntry ::= SEQUENCE {
    fltNewCfgExtendedIndx             Integer32,
    fltNewCfgExtendedSecwa            DisplayString,
    fltNewCfgExtendedLayer7DenyState  INTEGER,
    fltNewCfgExtendedLayer7DenyUrlBmap OCTET STRING,
    fltNewCfgExtendedLayer7DenyAddUrl Integer32,
    fltNewCfgExtendedLayer7DenyRemUrl Integer32,
    fltNewCfgExtendedGotoFilter       Integer32,
    fltNewCfgExtendedRadiusWapPersist INTEGER,
    fltNewCfgExtendedPbind            INTEGER,
    fltNewCfgExtendedTimeWindow       INTEGER,
    fltNewCfgExtendedHoldDuration     INTEGER,
    fltNewCfgExtendedProxyIp          IpAddress,
    fltNewCfgExtendedPatternMatch     INTEGER,
    fltNewCfgExtendedLayer7DenyMatchAll INTEGER,
    fltNewCfgExtendedLayer7ParseAll   INTEGER,
    fltNewCfgExtendedSecurityParseAll INTEGER,
    fltNewCfgExtendedPatternMatchGroupBmap OCTET STRING,
    fltNewCfgExtendedAddPatternMatchGroup  Integer32,
    fltNewCfgExtendedRemPatternMatchGroup Integer32,
    fltNewCfgExtended8021pBitsValue   INTEGER,
    fltNewCfgExtended8021pBitsMatch   INTEGER,
    fltNewCfgExtendedAclIpLength      INTEGER,
    fltNewCfgExtendedIdsGroup         Integer32,
    fltNewCfgExtendedEgressPip        INTEGER,
    fltNewCfgExtendedDbind            INTEGER,
    fltNewCfgExtendedReverse          INTEGER,
    fltNewCfgExtendedRevBwmContract   Integer32,
    fltNewCfgExtendedParseChn         INTEGER,
    fltNewCfgExtendedRtpBwmContract   Integer32,
    fltNewCfgExtendedSipParsing       INTEGER,
    fltNewCfgExtendedSessionMirror    INTEGER,
    fltNewCfgExtendedIpVer            INTEGER,
    fltNewCfgExtendedIpv6Sip          DisplayString,
    fltNewCfgExtendedIpv6Sprefix      INTEGER,
    fltNewCfgExtendedIpv6Dip          DisplayString,
    fltNewCfgExtendedIpv6Dprefix      INTEGER,
    fltNewCfgExtendedHdrHash          INTEGER,
    fltNewCfgExtendedHdrName          DisplayString,
    fltNewCfgExtendedHdrHashLen       INTEGER,
    fltNewCfgExtendedNatIp            IpAddress,
    fltNewCfgExtendedIpv6Nip          DisplayString,
    fltNewCfgExtendedIpv6Proxy        DisplayString,    
    fltNewCfgExtendedL7SipFilt        INTEGER,
    fltNewCfgExtendedL3State          INTEGER,
    fltNewCfgExtendedNatMcastVlan     INTEGER,
    fltNewCfgExtendedNbind            INTEGER,
    fltNewCfgExtendedRedirGroup       DisplayString,
    fltNewCfgExtendedIdsGroupEnh      DisplayString,
    fltNewCfgSourceIp                 DisplayString,
    fltNewCfgDestIp                   DisplayString,
    fltNewCfgSourceMask               DisplayString,
    fltNewCfgDestMask                 DisplayString,
    fltNewCfgExtendedProx             INTEGER,
    fltNewCfgExtendedReportState      INTEGER,
    fltNewCfgExtendedReportLocation   INTEGER,
    fltNewCfgExtendedReportPurpose    INTEGER,
    fltNewCfgExtendedReportAppl       INTEGER,
    fltNewCfgExtendedReportDir        INTEGER,
    fltNewCfgExtendedIcapPol          DisplayString,
    fltNewCfgExtendedTrafficEventPol  DisplayString,
    fltNewCfgExtendedDpmReportState   INTEGER,    
    fltNewCfgRtSrcTnl                 INTEGER
}

fltNewCfgExtendedIndx OBJECT-TYPE
    SYNTAX  Integer32
    MAX-ACCESS  read-only
    STATUS  current
    DESCRIPTION
        "The filtering table index."
    ::= { fltNewCfgExtendedTableEntry 1 }

fltNewCfgExtendedSecwa OBJECT-TYPE
    SYNTAX DisplayString (SIZE(1..32))
    MAX-ACCESS  read-create
    STATUS  current
    DESCRIPTION
         "Filter security web application."
    ::= { fltNewCfgExtendedTableEntry 2 }

fltNewCfgExtendedLayer7DenyState OBJECT-TYPE
    SYNTAX  INTEGER {
        enabled(1),
        disabled(2),
        unsupported(2147483647)
        }
    MAX-ACCESS  read-create
    STATUS  current
    DESCRIPTION
        "Enable or disable layer 7 deny filtering."
    ::= { fltNewCfgExtendedTableEntry 3 }

fltNewCfgExtendedLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgExtendedTableEntry 4 }

fltNewCfgExtendedLayer7DenyAddUrl OBJECT-TYPE
    SYNTAX  Integer32
    MAX-ACCESS  read-create
    STATUS  current
    DESCRIPTION
        "The URL Path (slbCurCfgUrlLbPathIndex) to be added to the 
         Layer 7 deny filter. A zero is returned when read."
    ::= { fltNewCfgExtendedTableEntry 5 }

fltNewCfgExtendedLayer7DenyRemUrl OBJECT-TYPE
    SYNTAX  Integer32
    MAX-ACCESS  read-create
    STATUS  current
    DESCRIPTION
        "The URL Path (slbCurCfgUrlLbPathIndex) to be removed from 
         the Layer 7 deny filter. A zero is returned when read."
    ::= { fltNewCfgExtendedTableEntry 6}

fltNewCfgExtendedGotoFilter OBJECT-TYPE
    SYNTAX  Integer32
    MAX-ACCESS  read-create
    STATUS  current	
    DESCRIPTION
        "The filter ID for GOTO action in the new config."
    ::= { fltNewCfgExtendedTableEntry 7 }

fltNewCfgExtendedRadiusWapPersist OBJECT-TYPE
    SYNTAX  INTEGER {
        enabled(1),
        disabled(2),
        unsupported(2147483647)
        }
    MAX-ACCESS  read-create
    STATUS  current	
    DESCRIPTION
        "Enable or disable Radius/WAP persistence."
    ::= { fltNewCfgExtendedTableEntry 8 }

fltNewCfgExtendedPbind OBJECT-TYPE
    SYNTAX  INTEGER {
        enabled(1),
        disabled(2),
        unsupported(2147483647)
        }
    MAX-ACCESS  read-create
    STATUS  current	
    DESCRIPTION
        "Enable or disable filter persistent binding."
    ::= { fltNewCfgExtendedTableEntry 9 }

fltNewCfgExtendedTimeWindow OBJECT-TYPE
    SYNTAX  INTEGER (1..65535)
    MAX-ACCESS  read-create
    STATUS  current
    DESCRIPTION
        "The time window for protocol rate limiting (in seconds)."
    ::= { fltNewCfgExtendedTableEntry 10 }

fltNewCfgExtendedHoldDuration OBJECT-TYPE
    SYNTAX  INTEGER (2..65535)
    MAX-ACCESS  read-create
    STATUS  current
    DESCRIPTION
        "The hold down duration for protocol rate limiting (in minutes)."
    ::= { fltNewCfgExtendedTableEntry 11 }

fltNewCfgExtendedPatternMatch OBJECT-TYPE
    SYNTAX  INTEGER {
        enabled(1),
        disabled(2),
        unsupported(2147483647)
        }
    MAX-ACCESS  read-create
    STATUS  current	
    DESCRIPTION
        "Enable or disable binary pattern matching."
    ::= { fltNewCfgExtendedTableEntry 12 }

fltNewCfgExtendedLayer7DenyMatchAll OBJECT-TYPE
    SYNTAX  INTEGER {
        enabled(1),
        disabled(2),
        unsupported(2147483647)
        }
    MAX-ACCESS  read-create
    STATUS  current
    DESCRIPTION
        "Enable or disable match-all criteria for L7 deny string matching."
    ::= { fltNewCfgExtendedTableEntry 13 }

fltNewCfgExtendedProxyIp OBJECT-TYPE
    SYNTAX  IpAddress
    MAX-ACCESS  read-create
    STATUS  current
    DESCRIPTION
        "The client proxy IP address for NAT and REDIR filter."
        
    ::= { fltNewCfgExtendedTableEntry 14 }

fltNewCfgExtendedLayer7ParseAll OBJECT-TYPE
    SYNTAX  INTEGER {
        enabled(1),
        disabled(2),
        unsupported(2147483647)
        }
    MAX-ACCESS  read-create
    STATUS  current
    DESCRIPTION
        "Enable or disable layer 7 lookup (parsing) of all packets."
    ::= { fltNewCfgExtendedTableEntry 15 }

fltNewCfgExtendedSecurityParseAll OBJECT-TYPE
    SYNTAX  INTEGER {
        enabled(1),
        disabled(2),
        unsupported(2147483647)
        }
    MAX-ACCESS  read-create
    STATUS  current
    DESCRIPTION
        "Enable or disable pattern string lookup (parsing) of all packets."
    ::= { fltNewCfgExtendedTableEntry 16 }

fltNewCfgExtendedPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltNewCfgExtendedTableEntry 17 }
    
fltNewCfgExtendedAddPatternMatchGroup OBJECT-TYPE
    SYNTAX  Integer32
    MAX-ACCESS  read-create
    STATUS  current
    DESCRIPTION
        "The pattern match group to be added to the 
         security filter. A zero is returned when read."
    ::= { fltNewCfgExtendedTableEntry 18 }

fltNewCfgExtendedRemPatternMatchGroup OBJECT-TYPE
    SYNTAX  Integer32
    MAX-ACCESS  read-create
    STATUS  current
    DESCRIPTION
        "The pattern match group to be to be removed from 
         the security filter. A zero is returned when read."
    ::= { fltNewCfgExtendedTableEntry 19 }

fltNewCfgExtended8021pBitsValue OBJECT-TYPE
    SYNTAX  INTEGER (0..7)
    MAX-ACCESS  read-create
    STATUS  current
    DESCRIPTION
        "The 802.1p bits value to match."
    ::= { fltNewCfgExtendedTableEntry 20 }

fltNewCfgExtended8021pBitsMatch OBJECT-TYPE
    SYNTAX  INTEGER {
        enabled(1),
        disabled(2),
        unsupported(2147483647)
        }
    MAX-ACCESS  read-create
    STATUS  current
    DESCRIPTION
        "Enable or disable matching on 802.1p bits in the packets."
    ::= { fltNewCfgExtendedTableEntry 21 }
 
fltNewCfgExtendedAclIpLength OBJECT-TYPE
    SYNTAX  INTEGER (0..65535)
    MAX-ACCESS  read-create
    STATUS  current 
    DESCRIPTION
        "Set the IP maximum packet length in bytes. A value can be either 0 
         which indicates 'any' length or between 64 and 65535."
    ::= { fltNewCfgExtendedTableEntry 22 }	

fltNewCfgExtendedIdsGroup OBJECT-TYPE
    SYNTAX  Integer32
    MAX-ACCESS  read-create
    STATUS  current
    DESCRIPTION
        "The real server group for IDS load balancing. A value of 0 indicates
	 'none'." 
    ::= { fltNewCfgExtendedTableEntry 23 }
    
fltNewCfgExtendedEgressPip OBJECT-TYPE
    SYNTAX  INTEGER {
        enabled(1),
        disabled(2),
        unsupported(2147483647)
        }
    MAX-ACCESS  read-create
    STATUS  current
    DESCRIPTION
        "Enable or disable pip selection based on egress port/vlan."
    ::= { fltNewCfgExtendedTableEntry 24 }
    
fltNewCfgExtendedDbind OBJECT-TYPE
    SYNTAX  INTEGER {
        enabled(1),
        disabled(2),
        unsupported(2147483647)
        }
    MAX-ACCESS  read-create
    STATUS  current	
    DESCRIPTION
        "Enable or disable filter delayed binding."
    ::= { fltNewCfgExtendedTableEntry 25 }

fltNewCfgExtendedRevBwmContract OBJECT-TYPE
    SYNTAX  Integer32
    MAX-ACCESS  read-create
    STATUS  current
    DESCRIPTION
	"Filt reverse session BWM contract number."
    ::= { fltNewCfgExtendedTableEntry 26 }	

fltNewCfgExtendedReverse OBJECT-TYPE
    SYNTAX  INTEGER {
        enabled(1),
        disabled(2),
        unsupported(2147483647)
        }
    MAX-ACCESS  read-create
    STATUS  current	
    DESCRIPTION
        "Enable or disable creating session for reverse side traffic."
    ::= { fltNewCfgExtendedTableEntry 27 }

fltNewCfgExtendedParseChn OBJECT-TYPE
    SYNTAX  INTEGER {
	enabled(1),
	disabled(2),
        unsupported(2147483647)
	}
    MAX-ACCESS  read-create
    STATUS  current 
    DESCRIPTION
        "Enable or disable chained pgroup match criteria for l7 filtering."	 
    ::= { fltNewCfgExtendedTableEntry 28}


fltNewCfgExtendedRtpBwmContract OBJECT-TYPE
    SYNTAX  Integer32
    MAX-ACCESS  read-create
    STATUS  current
    DESCRIPTION
        "BWM contract for SIP RTP traffic."
    ::= { fltNewCfgExtendedTableEntry 29 }

fltNewCfgExtendedSipParsing OBJECT-TYPE
    SYNTAX  INTEGER {
        enabled(1),
        disabled(2),
        unsupported(2147483647)
        }
    MAX-ACCESS  read-create
    STATUS  current
    DESCRIPTION
        "Enable or disable SIP NAT."
    ::= { fltNewCfgExtendedTableEntry 30 }


    fltNewCfgExtendedSessionMirror  OBJECT-TYPE
    SYNTAX  INTEGER {
        enabled(1),
        disabled(2),
        unsupported(2147483647)
        }
    MAX-ACCESS  read-create
    STATUS  current
    DESCRIPTION
        "Enable or disable session mirroring."
    ::= { fltNewCfgExtendedTableEntry 31 }


fltNewCfgExtendedIpVer OBJECT-TYPE
    SYNTAX  INTEGER{
        ipv4(1),
        ipv6(2),
        unsupported(2147483647)
        }
    MAX-ACCESS  read-create
    STATUS  current
    DESCRIPTION
        "The type of IP address."
    ::= { fltNewCfgExtendedTableEntry 32 }

fltNewCfgExtendedIpv6Sip  OBJECT-TYPE
    SYNTAX   DisplayString (SIZE(0..40))
    MAX-ACCESS  read-create
    STATUS  current
    DESCRIPTION
        "The source IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 33 }

fltNewCfgExtendedIpv6Sprefix   OBJECT-TYPE
    SYNTAX   INTEGER(0..128) 
    MAX-ACCESS  read-create
    STATUS  current
    DESCRIPTION
        "The prefix length associated with source IP address ."
    ::= { fltNewCfgExtendedTableEntry 34 }

fltNewCfgExtendedIpv6Dip   OBJECT-TYPE
    SYNTAX   DisplayString (SIZE(0..40))
    MAX-ACCESS  read-create
    STATUS  current
    DESCRIPTION
        "The destination  IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 35 }

fltNewCfgExtendedIpv6Dprefix   OBJECT-TYPE
    SYNTAX  INTEGER(0..128) 
    MAX-ACCESS  read-create
    STATUS  current
    DESCRIPTION
        "The prefix length associated with destination IP address ."
    ::= {fltNewCfgExtendedTableEntry  36 }

fltNewCfgExtendedHdrHash OBJECT-TYPE
       SYNTAX  INTEGER {
        none(1),
        headerhash(2),
        unsupported(2147483647)
        }
    MAX-ACCESS read-create
    STATUS current
    DESCRIPTION
        "The header hash filter."
    ::= { fltNewCfgExtendedTableEntry 37 }

fltNewCfgExtendedHdrName OBJECT-TYPE
    SYNTAX DisplayString (SIZE(0..31))
    MAX-ACCESS read-create
    STATUS current
    DESCRIPTION
        "The header name of the filter. Headerhash should be
         enabled before header name is configured."
    ::= { fltNewCfgExtendedTableEntry 38 }

fltNewCfgExtendedHdrHashLen OBJECT-TYPE
    SYNTAX  INTEGER (1..255)
    MAX-ACCESS  read-create
    STATUS  current
    DESCRIPTION
        "The header hash length of the filter. Headerhash should be
         enabled before hash length is configured."
    ::= { fltNewCfgExtendedTableEntry 39 }

fltNewCfgExtendedNatIp OBJECT-TYPE
    SYNTAX  IpAddress
    MAX-ACCESS  read-write
    STATUS  current
    DESCRIPTION
        "The nat IP address to be filtered."
    ::= { fltNewCfgExtendedTableEntry 40 }

fltNewCfgExtendedIpv6Nip   OBJECT-TYPE
    SYNTAX   DisplayString (SIZE(0..40))
    MAX-ACCESS  read-write
    STATUS  current
    DESCRIPTION
        "The nat IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 41 }

fltNewCfgExtendedIpv6Proxy  OBJECT-TYPE
    SYNTAX   DisplayString (SIZE(0..40))
    MAX-ACCESS  read-write
    STATUS  current
    DESCRIPTION
        "The proxy IPv6 address to be filtered. Address should be 4-byte
         hexadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 42 }
    
fltNewCfgExtendedL7SipFilt OBJECT-TYPE
    SYNTAX  INTEGER {
        enabled(1),
        disabled(2),
        unsupported(2147483647)
        }
    MAX-ACCESS  read-write
    STATUS  current
    DESCRIPTION
        "Enable/Disable L7 application SIP UDP filtering."
    ::= { fltNewCfgExtendedTableEntry 43 }

fltNewCfgExtendedNatMcastVlan OBJECT-TYPE
    SYNTAX  INTEGER (0..4090)
    MAX-ACCESS  read-write
    STATUS  current
    DESCRIPTION
        "Multicast VLAN."
    ::= { fltNewCfgExtendedTableEntry 44 }

fltNewCfgExtendedNbind OBJECT-TYPE
    SYNTAX  INTEGER {
        enabled(1),
        disabled(2),
        unsupported(2147483647)
    }
    MAX-ACCESS  read-create
    STATUS  current
    DESCRIPTION
        "Enable or disable subnet binding for redirection."
    ::= { fltNewCfgExtendedTableEntry 45 }

fltNewCfgExtendedL3State OBJECT-TYPE
    SYNTAX  INTEGER {
        enabled(1),
        disabled(2),
        unsupported(2147483647)
    }
    MAX-ACCESS  read-create
    STATUS  current
    DESCRIPTION
        "The L3 filter processing state for this filter."
    ::= { fltNewCfgExtendedTableEntry 46 }


fltNewCfgExtendedRedirGroup OBJECT-TYPE
    SYNTAX DisplayString (SIZE(1..255)) 
    MAX-ACCESS  read-create
    STATUS  current
    DESCRIPTION
        "The real server group to be redirected to."
    ::= { fltNewCfgExtendedTableEntry 47 }

fltNewCfgExtendedIdsGroupEnh OBJECT-TYPE
    SYNTAX DisplayString (SIZE(1..255))
    MAX-ACCESS  read-create
    STATUS  current
    DESCRIPTION
        "The real server group for IDS load balancing. A NULL string indicates
         'none'."
    ::= { fltNewCfgExtendedTableEntry 48 }

fltNewCfgSourceIp OBJECT-TYPE
    SYNTAX DisplayString (SIZE(1..40))    
    MAX-ACCESS  read-create
    STATUS  current
    DESCRIPTION
        "Filter source Ip. It can be IPv4/IPv6."
    ::= { fltNewCfgExtendedTableEntry 49 }         

fltNewCfgDestIp OBJECT-TYPE
    SYNTAX DisplayString (SIZE(1..40))
    MAX-ACCESS  read-create
    STATUS  current
    DESCRIPTION
        "Filter Destination Ip. It can be IPv4/IPv6."
    ::= { fltNewCfgExtendedTableEntry 50 }

fltNewCfgSourceMask OBJECT-TYPE
    SYNTAX DisplayString (SIZE(1..32))
    MAX-ACCESS  read-create
    STATUS  current
    DESCRIPTION
         "Filter Mask or Prefix."
    ::= { fltNewCfgExtendedTableEntry 51 }

fltNewCfgDestMask OBJECT-TYPE
    SYNTAX DisplayString (SIZE(1..32))
    MAX-ACCESS  read-create
    STATUS  current
    DESCRIPTION
         "Filter Mask or Prefix."
    ::= { fltNewCfgExtendedTableEntry 52 }

fltNewCfgExtendedProx OBJECT-TYPE
    SYNTAX  INTEGER {
        enabled(1),
        disabled(2),
        unsupported(2147483647)
    }
    MAX-ACCESS  read-create
    STATUS  current
    DESCRIPTION
        "Enable or disable Outbound LLB based on proximity."
    ::= { fltNewCfgExtendedTableEntry 53 }

fltNewCfgExtendedReportState OBJECT-TYPE
    SYNTAX  INTEGER {
        disabled(0),
        enabled(1),
        unsupported(2147483647)
        }
    MAX-ACCESS  read-create
    STATUS  current
    DESCRIPTION
        "Enable or disable filter inspect reporting."
    ::= { fltNewCfgExtendedTableEntry 54 }

fltNewCfgExtendedReportLocation OBJECT-TYPE
    SYNTAX  INTEGER {
        none(0),
        clientside(1),
        serverside(2),
        unsupported(2147483647)
        }
    MAX-ACCESS  read-create
    STATUS  current
    DESCRIPTION
        "Set filter location client/server or none as default value."
    ::= { fltNewCfgExtendedTableEntry 55 }

fltNewCfgExtendedReportPurpose OBJECT-TYPE
    SYNTAX  INTEGER {
        none(0),
        bypass(1),
        inspect(2),
        unsupported(2147483647)
        }
    MAX-ACCESS  read-create
    STATUS  current
    DESCRIPTION
        "Set filter purpose bypass/inspect or none as default value."
    ::= { fltNewCfgExtendedTableEntry 56 }

fltNewCfgExtendedReportAppl OBJECT-TYPE
    SYNTAX  INTEGER {
        none(0),
        https(1),
        http(2),
        unsupported(2147483647)
        }
    MAX-ACCESS  read-create
    STATUS  current
    DESCRIPTION
        "Set filter application https/http or none as default value."
    ::= { fltNewCfgExtendedTableEntry 57 }

fltNewCfgExtendedReportDir OBJECT-TYPE
    SYNTAX  INTEGER {
        outbound(0),
        inbound(1),
        none(2),
        unsupported(2147483647)
        }
    MAX-ACCESS  read-create
    STATUS  current
    DESCRIPTION
        "Set filter direction none/inbound/outbound."
    ::= { fltNewCfgExtendedTableEntry 58 }

fltNewCfgExtendedIcapPol OBJECT-TYPE
    SYNTAX DisplayString (SIZE(1..32))
    MAX-ACCESS  read-create
    STATUS  current
    DESCRIPTION
         "Filter IcapPol."
    ::= { fltNewCfgExtendedTableEntry 59 }


fltNewCfgExtendedTrafficEventPol OBJECT-TYPE
    SYNTAX   DisplayString (SIZE(0..128))
    MAX-ACCESS  read-create
    STATUS  current
    DESCRIPTION
        "The traffic event policy of the filter."
    ::= { fltNewCfgExtendedTableEntry 60 }

fltNewCfgExtendedDpmReportState OBJECT-TYPE
    SYNTAX  INTEGER {
        disabled(0),
        enabled(1),
        unsupported(2147483647)
    }
    MAX-ACCESS  read-create
    STATUS  current
    DESCRIPTION
         "Enable or disable filter DPm reporting."
    ::= { fltNewCfgExtendedTableEntry 61 }

fltNewCfgRtSrcTnl OBJECT-TYPE
    SYNTAX  INTEGER {
        enabled(1),
        disabled(2),
        unsupported(2147483647)
        }
    MAX-ACCESS  read-create
    STATUS  current
    DESCRIPTION
        "Enable or disable Return to Source Tunnel."
    ::= { fltNewCfgExtendedTableEntry 62 }

-- Filtering Port Table

fltCurCfgPortTable OBJECT-TYPE
    SYNTAX  SEQUENCE OF FltCurCfgPortTableEntry
    MAX-ACCESS  not-accessible
    STATUS  current
    DESCRIPTION
        "The filtering port table in the current configuration block.
         Note:This mib is not supported for VX instance of Virtualization."
    ::= { filterCfg 4 }

fltCurCfgPortTableEntry OBJECT-TYPE
    SYNTAX  FltCurCfgPortTableEntry
    MAX-ACCESS  not-accessible
    STATUS  current
    DESCRIPTION
        "A row in the filtering port table."
    INDEX   { fltCurCfgPortIndx }
    ::= { fltCurCfgPortTable 1 }

FltCurCfgPortTableEntry ::= SEQUENCE {
    fltCurCfgPortIndx         Integer32,
    fltCurCfgPortState        INTEGER,
    fltCurCfgPortFiltBmap     OCTET STRING
    }

fltCurCfgPortIndx OBJECT-TYPE
    SYNTAX  Integer32
    MAX-ACCESS  read-only
    STATUS  current
    DESCRIPTION
        "The port index."
    ::= { fltCurCfgPortTableEntry 1 }

fltCurCfgPortState OBJECT-TYPE
    SYNTAX  INTEGER {
        enabled(1),
        disabled(2),
        unsupported(2147483647)
        }
    MAX-ACCESS  read-only
    STATUS  current
    DESCRIPTION
        "Enable or disable filtering."
    ::= { fltCurCfgPortTableEntry 2 }

fltCurCfgPortFiltBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { fltCurCfgPortTableEntry 3 }

fltNewCfgPortTable OBJECT-TYPE
    SYNTAX  SEQUENCE OF FltNewCfgPortTableEntry
    MAX-ACCESS  not-accessible
    STATUS  current
    DESCRIPTION
        "The filtering port table in the new configuration block.
         Note:This mib is not supported for VX instance of Virtualization."
    ::= { filterCfg 5 }

fltNewCfgPortTableEntry OBJECT-TYPE
    SYNTAX  FltNewCfgPortTableEntry
    MAX-ACCESS  not-accessible
    STATUS  current
    DESCRIPTION
        "A row in the filtering port table."
    INDEX   { fltNewCfgPortIndx }
    ::= { fltNewCfgPortTable 1 }

FltNewCfgPortTableEntry ::= SEQUENCE {
    fltNewCfgPortIndx         Integer32,
    fltNewCfgPortState        INTEGER,
    fltNewCfgPortFiltBmap     OCTET STRING,
    fltNewCfgPortAddFiltRule  Integer32,
    fltNewCfgPortRemFiltRule  Integer32
    }

fltNewCfgPortIndx OBJECT-TYPE
    SYNTAX  Integer32
    MAX-ACCESS  read-only
    STATUS  current
    DESCRIPTION
        "The port index."
    ::= { fltNewCfgPortTableEntry 1 }

fltNewCfgPortState OBJECT-TYPE
    SYNTAX  INTEGER {
        enabled(1),
        disabled(2),
        unsupported(2147483647)
        }
    MAX-ACCESS  read-create
    STATUS  current
    DESCRIPTION
        "Enable or disable filtering."
    ::= { fltNewCfgPortTableEntry 2 }

fltNewCfgPortFiltBmap OBJECT-TYPE
    SYNTAX  OCTET STRING (SIZE(0..256))
    MAX-ACCESS  read-create
    STATUS  current
    DESCRIPTION
        "The filtering rules applied to the port.  The filtering rules
         are presented in bitmap format.

         in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltNewCfgTable)

         where x : 1 - The represented filter rule applied to the port
		   0 - The represented filter rule not applied to the port "
    ::= { fltNewCfgPortTableEntry 3 }

fltNewCfgPortAddFiltRule OBJECT-TYPE
    SYNTAX  Integer32
    MAX-ACCESS  read-create
    STATUS  current
    DESCRIPTION
        "This is an action object to add filtering rule to a port. The value 
         specified with this object is the index to the fltNewCfgTable for 
         which filtering rule to be added to the port. The range of the 
         valid index is between 1 and fltCurCfgTableMaxSize. When read, the 
         value '0' is returned always."
    ::= { fltNewCfgPortTableEntry 4 }

fltNewCfgPortRemFiltRule OBJECT-TYPE
    SYNTAX  Integer32
    MAX-ACCESS  read-create
    STATUS  current
    DESCRIPTION
        "This is an action object to remove filtering rule from a port.	The 
         value specified with this object is the index to the fltNewCfgTable 
         for which filtering rule to be removed from the port. The range of 
         the valid index is between 1 and fltCurCfgTableMaxSize.  When read, 
         the value '0' is returned always."
    ::= { fltNewCfgPortTableEntry 5 }

-- URL based BWM filtering table
fltUrlBwmTableMaxSize OBJECT-TYPE
    SYNTAX Integer32
    MAX-ACCESS read-only
    STATUS current
    DESCRIPTION
        "The maximum number of URL based BWM entries.
         Note:This mib is not supported for VX instance of Virtualization."
    ::= { filterCfg 6 }

fltCurCfgUrlBwmTable OBJECT-TYPE
    SYNTAX  SEQUENCE OF FltCurCfgUrlBwmEntry
    MAX-ACCESS  not-accessible
    STATUS  current
    DESCRIPTION
        "The table of URL based BWM for filtering.
         Note:This mib is not supported for VX instance of Virtualization."
    ::= { filterCfg 7 }

fltCurCfgUrlBwmEntry OBJECT-TYPE
    SYNTAX  FltCurCfgUrlBwmEntry
    MAX-ACCESS  not-accessible
    STATUS  current
    DESCRIPTION
        "A row in the URL based BWM filtering table."
    INDEX   { fltCurCfgUrlBwmFltIndex, fltCurCfgUrlBwmUrlId }
    ::= { fltCurCfgUrlBwmTable 1 }

FltCurCfgUrlBwmEntry ::= SEQUENCE {
    fltCurCfgUrlBwmFltIndex        Integer32,
    fltCurCfgUrlBwmUrlId           Integer32,
    fltCurCfgUrlReverseBwmContract Integer32,
    fltCurCfgUrlBwmContract        Integer32  
    }

fltCurCfgUrlBwmFltIndex OBJECT-TYPE
    SYNTAX  Integer32
    MAX-ACCESS  read-only
    STATUS  current
    DESCRIPTION
        "The number of the filter." 
    ::= { fltCurCfgUrlBwmEntry 1 }

fltCurCfgUrlBwmUrlId OBJECT-TYPE  
    SYNTAX  Integer32  
    MAX-ACCESS  read-only  
    STATUS  current  
    DESCRIPTION 
        "The URL Path Identifier."  
    ::= { fltCurCfgUrlBwmEntry 2 } 

fltCurCfgUrlBwmContract OBJECT-TYPE  
    SYNTAX  Integer32  
    MAX-ACCESS  read-only  
    STATUS  current  
    DESCRIPTION 
        "The BW contract."  
    ::= { fltCurCfgUrlBwmEntry 3 } 

fltCurCfgUrlReverseBwmContract OBJECT-TYPE  
    SYNTAX  Integer32  
    MAX-ACCESS  read-only  
    STATUS  current  
    DESCRIPTION 
        "The BWM contract for reverse traffic."  
    ::= { fltCurCfgUrlBwmEntry 4 } 

fltNewCfgUrlBwmTable OBJECT-TYPE
    SYNTAX  SEQUENCE OF FltNewCfgUrlBwmEntry
    MAX-ACCESS  not-accessible
    STATUS  current
    DESCRIPTION
        "The table of URL based BWM for filtering.
         Note:This mib is not supported for VX instance of Virtualization."
    ::= { filterCfg 8 }

fltNewCfgUrlBwmEntry OBJECT-TYPE
    SYNTAX  FltNewCfgUrlBwmEntry
    MAX-ACCESS  not-accessible
    STATUS  current
    DESCRIPTION
        "A row in the URL based BWM filtering table."
    INDEX   { fltNewCfgUrlBwmFltIndex, fltNewCfgUrlBwmUrlId }
    ::= { fltNewCfgUrlBwmTable 1 }

FltNewCfgUrlBwmEntry ::= SEQUENCE {
    fltNewCfgUrlBwmFltIndex        Integer32,
    fltNewCfgUrlBwmUrlId           Integer32,
    fltNewCfgUrlBwmContract        Integer32,
    fltNewCfgUrlReverseBwmContract Integer32,
    fltNewCfgUrlBwmDelete          INTEGER
    }

fltNewCfgUrlBwmFltIndex OBJECT-TYPE
    SYNTAX  Integer32
    MAX-ACCESS  read-only
    STATUS  current
    DESCRIPTION
        "The number of the filter." 
    ::= { fltNewCfgUrlBwmEntry 1 }

fltNewCfgUrlBwmUrlId OBJECT-TYPE  
    SYNTAX  Integer32  
    MAX-ACCESS  read-only  
    STATUS  current  
    DESCRIPTION 
        "The URL Path Identifier."  
    ::= { fltNewCfgUrlBwmEntry 2 } 

fltNewCfgUrlBwmContract OBJECT-TYPE  
    SYNTAX  Integer32  
    MAX-ACCESS  read-create  
    STATUS  current  
    DESCRIPTION 
        "The BW traffic contract."  
    ::= { fltNewCfgUrlBwmEntry 3 } 

fltNewCfgUrlBwmDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { fltNewCfgUrlBwmEntry 4 }

fltNewCfgUrlReverseBwmContract OBJECT-TYPE  
    SYNTAX  Integer32  
    MAX-ACCESS  read-create  
    STATUS  current  
    DESCRIPTION 
        "The BWM contract for reverse traffic."  
    ::= { fltNewCfgUrlBwmEntry 5 }

-- Filter HTTP Redirection Mapping Table

fltCfgHttpRedirMappingTableMaxSize OBJECT-TYPE
    SYNTAX  Integer32 
    MAX-ACCESS  read-only 
    STATUS  current 
    DESCRIPTION 
        "The maximum number of entries in HttpRedirMappingTable.
         Note:This mib is not supported for VX instance of Virtualization." 
    ::= { filterCfg 9 }

fltCurCfgHttpRedirMappingTable OBJECT-TYPE
    SYNTAX  SEQUENCE OF FltCurCfgHttpRedirMappingEntry
    MAX-ACCESS  not-accessible
    STATUS  current
    DESCRIPTION
        "The table of HTTP redirection mapping table.
         Note:This mib is not supported for VX instance of Virtualization."
    ::= { filterCfg 10 }

fltCurCfgHttpRedirMappingEntry OBJECT-TYPE
    SYNTAX  FltCurCfgHttpRedirMappingEntry
    MAX-ACCESS  not-accessible
    STATUS  current
    DESCRIPTION
        "A row in the HTTP redirect mapping table."
    INDEX   { fltCurCfgHttpRedirMappingFilter, 
              fltCurCfgHttpRedirMappingFromStr }
    ::= { fltCurCfgHttpRedirMappingTable 1 }

FltCurCfgHttpRedirMappingEntry ::= SEQUENCE {
    fltCurCfgHttpRedirMappingFilter   Integer32,
    fltCurCfgHttpRedirMappingFromStr  INTEGER,
    fltCurCfgHttpRedirMappingToStr    INTEGER
    }

fltCurCfgHttpRedirMappingFilter OBJECT-TYPE
    SYNTAX  Integer32
    MAX-ACCESS  read-only
    STATUS  current
    DESCRIPTION
        "The filter number."
    ::= { fltCurCfgHttpRedirMappingEntry 1 }

fltCurCfgHttpRedirMappingFromStr OBJECT-TYPE 
    SYNTAX  INTEGER (1..1024)
    MAX-ACCESS  read-only 
    STATUS  current 
    DESCRIPTION 
        "This index is the string ID of Layer7 string table. 
         If HTTP request matches this string, then switch issues 
         a HTTP REDIRECT to client with the 
         fltCurCfgHttpRedirMappingToStr string." 
    ::= { fltCurCfgHttpRedirMappingEntry 2 }

fltCurCfgHttpRedirMappingToStr OBJECT-TYPE  
    SYNTAX  INTEGER (2..1024)
    MAX-ACCESS  read-only  
    STATUS  current  
    DESCRIPTION 
        "The string ID of Layer7 string table. The switch sends 
         HTTP Redirect back to client with this string when HTTP
         request matches the fltCurCfgHttpRedirMappingFromStr string"
    ::= { fltCurCfgHttpRedirMappingEntry 3 } 

fltNewCfgHttpRedirMappingTable OBJECT-TYPE
    SYNTAX  SEQUENCE OF FltNewCfgHttpRedirMappingEntry
    MAX-ACCESS  not-accessible
    STATUS  current
    DESCRIPTION
        "The table of HTTP redirection mapping table.
         Note:This mib is not supported for VX instance of Virtualization."
    ::= { filterCfg 11 }

fltNewCfgHttpRedirMappingEntry OBJECT-TYPE
    SYNTAX  FltNewCfgHttpRedirMappingEntry
    MAX-ACCESS  not-accessible
    STATUS  current
    DESCRIPTION
        "A row in the HTTP redirect mapping table."
    INDEX   { fltNewCfgHttpRedirMappingFilter, 
              fltNewCfgHttpRedirMappingFromStr }
    ::= { fltNewCfgHttpRedirMappingTable 1 }

FltNewCfgHttpRedirMappingEntry ::= SEQUENCE {
    fltNewCfgHttpRedirMappingFilter    Integer32,
    fltNewCfgHttpRedirMappingFromStr   INTEGER,
    fltNewCfgHttpRedirMappingToStr     INTEGER,
    fltNewCfgHttpRedirMappingDelete    INTEGER
    }

fltNewCfgHttpRedirMappingFilter OBJECT-TYPE
    SYNTAX  Integer32
    MAX-ACCESS  read-only
    STATUS  current
    DESCRIPTION
        "The filter number."
    ::= { fltNewCfgHttpRedirMappingEntry 1 }

fltNewCfgHttpRedirMappingFromStr OBJECT-TYPE  
    SYNTAX  INTEGER (1..1024)
    MAX-ACCESS  read-only  
    STATUS  current  
    DESCRIPTION 
        "The string ID of Layer7 string table. If HTTP request 
         matches this string then switch issues a HTTP REDIRECT 
         to client with the fltNewCfgHttpRedirMappingToStr string."  
    ::= { fltNewCfgHttpRedirMappingEntry 2 } 

fltNewCfgHttpRedirMappingToStr OBJECT-TYPE  
    SYNTAX  INTEGER (2..1024)
    MAX-ACCESS  read-create  
    STATUS  current  
    DESCRIPTION 
        "The string ID of Layer7 string table. The switch sends 
         HTTP Redirect back to client with this string when the
         HTTP request matches fltNewCfgHttpRedirMappingFromStr 
         string."
    ::= { fltNewCfgHttpRedirMappingEntry 4 } 

fltNewCfgHttpRedirMappingDelete OBJECT-TYPE
    SYNTAX  INTEGER {
        other(1),
        delete(2),
        unsupported(2147483647)
        }
    MAX-ACCESS  read-create
    STATUS  current
    DESCRIPTION
        "By setting the value to delete(2), the entire row is deleted."
    ::= { fltNewCfgHttpRedirMappingEntry 6 }

--AppShapes for filters

slbCurCfgFiltAppShapeTable OBJECT-TYPE
    SYNTAX  SEQUENCE OF SlbCurCfgFiltAppShapeEntry
    MAX-ACCESS  not-accessible
    STATUS  current
    DESCRIPTION
        "The table of App Rules added to filters.
         Note:This mib is not supported for VX instance of Virtualization."
     ::= { filterCfg 13 }

slbCurCfgFiltAppShapeEntry OBJECT-TYPE
    SYNTAX  SlbCurCfgFiltAppShapeEntry
    MAX-ACCESS  not-accessible
    STATUS  current
    DESCRIPTION
        "A row in the  AppShape Based Filter Rules table."
    INDEX  { slbCurCfgFiltAppShapeFiltIndex, slbCurCfgFiltAppShapePriority }
    ::= { slbCurCfgFiltAppShapeTable 1 }

SlbCurCfgFiltAppShapeEntry ::= SEQUENCE {
        slbCurCfgFiltAppShapeFiltIndex		   Integer32,
        slbCurCfgFiltAppShapePriority          Integer32,
        slbCurCfgFiltAppShapeIndex             DisplayString
    }

slbCurCfgFiltAppShapeFiltIndex OBJECT-TYPE
    SYNTAX  Integer32
    MAX-ACCESS  read-only
    STATUS  current
    DESCRIPTION
        "The number of the filter."
    ::= { slbCurCfgFiltAppShapeEntry  1 }
	
	
slbCurCfgFiltAppShapePriority OBJECT-TYPE
    SYNTAX  Integer32
    MAX-ACCESS  read-only
    STATUS  current
    DESCRIPTION
        "The AppShape priority."
    ::= { slbCurCfgFiltAppShapeEntry  2 }

slbCurCfgFiltAppShapeIndex OBJECT-TYPE
    SYNTAX  DisplayString (SIZE(0..128))
    MAX-ACCESS  read-only
    STATUS  current
    DESCRIPTION
        "The AppShape ID added to the filter"
    ::= { slbCurCfgFiltAppShapeEntry  3 }

slbNewCfgFiltAppShapeTable OBJECT-TYPE
    SYNTAX  SEQUENCE OF SlbNewCfgFiltAppShapeEntry
    MAX-ACCESS  not-accessible
    STATUS  current
    DESCRIPTION
        "The table of AppShape based Filter Rules.
         Note:This mib is not supported for VX instance of Virtualization."
    ::= { filterCfg 14 }

slbNewCfgFiltAppShapeEntry OBJECT-TYPE
    SYNTAX  SlbNewCfgFiltAppShapeEntry
    MAX-ACCESS  not-accessible
    STATUS  current
    DESCRIPTION
        "A row in the AppShape Based Filter Rules table."
    INDEX  { slbNewCfgFiltAppShapeFiltIndex, slbNewCfgFiltAppShapePriority }
    ::= { slbNewCfgFiltAppShapeTable 1 }

SlbNewCfgFiltAppShapeEntry ::= SEQUENCE {
    slbNewCfgFiltAppShapeFiltIndex         Integer32,
    slbNewCfgFiltAppShapePriority          Integer32,
    slbNewCfgFiltAppShapeIndex             DisplayString,
    slbNewCfgFiltAppShapeDelete            INTEGER
    }
	
slbNewCfgFiltAppShapeFiltIndex OBJECT-TYPE
    SYNTAX  Integer32
    MAX-ACCESS  read-only
    STATUS  current
    DESCRIPTION
        "The number of the filter."
    ::= { slbNewCfgFiltAppShapeEntry  1 }

slbNewCfgFiltAppShapePriority OBJECT-TYPE
    SYNTAX  Integer32
    MAX-ACCESS  read-only
    STATUS  current
    DESCRIPTION
        "The AppShape priority."
    ::= { slbNewCfgFiltAppShapeEntry  2 }

slbNewCfgFiltAppShapeIndex OBJECT-TYPE
    SYNTAX  DisplayString (SIZE(0..128))
    MAX-ACCESS  read-create
    STATUS  current
    DESCRIPTION
        "The AppShape ID added to the filter"
    ::= { slbNewCfgFiltAppShapeEntry  3 }

slbNewCfgFiltAppShapeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgFiltAppShapeEntry 4 }

-- Global SLB General Configuration

gslbCurCfgGenState OBJECT-TYPE
    SYNTAX  INTEGER {
        on(1),
        off(2),
        unsupported(2147483647)
        }
     MAX-ACCESS  read-only
     STATUS  current
     DESCRIPTION
         "Turn on or off Distributed Server Load Balance.
          Note:This mib is not supported for VX instance of Virtualization."
    ::= { gslbGeneralCfg 1 }

gslbNewCfgGenState OBJECT-TYPE
    SYNTAX  INTEGER {
        on(1),
        off(2),
        unsupported(2147483647)
        }
    MAX-ACCESS  read-write
    STATUS  current
    DESCRIPTION
        "Turn on or off Distributed Server Load Balance.
         Note:This mib is not supported for VX instance of Virtualization."
    ::= { gslbGeneralCfg 2 }

gslbCurCfgGenHttpRedirect OBJECT-TYPE
    SYNTAX  INTEGER {
        enabled(1),
        disabled(2),
        unsupported(2147483647)
        }
    MAX-ACCESS  read-only
    STATUS  current
    DESCRIPTION
        "Enable/Disable HTTP redirect based GSLB in
         the current_configuration block.
         Note:This mib is not supported for VX instance of Virtualization."
    ::= { gslbGeneralCfg 7 }

gslbNewCfgGenHttpRedirect OBJECT-TYPE
    SYNTAX  INTEGER {
        enabled(1),
        disabled(2),
        unsupported(2147483647)
        }
    MAX-ACCESS  read-write
    STATUS  current
    DESCRIPTION
        "Enable/Disable HTTP redirect based GSLB in
         the new_configuration block.
         Note:This mib is not supported for VX instance of Virtualization."
    ::= { gslbGeneralCfg 8 }


gslbCurCfgGenMinco OBJECT-TYPE
    SYNTAX  INTEGER (0..65535)
    MAX-ACCESS  read-only
    STATUS  current
    DESCRIPTION
        "Minmum number of site connections in the current_configuration block.
         Note:This mib is not supported for VX instance of Virtualization."
    ::= { gslbGeneralCfg 13 }

gslbNewCfgGenMinco OBJECT-TYPE
    SYNTAX  INTEGER (0..65535)
    MAX-ACCESS  read-write
    STATUS  current
    DESCRIPTION
        "Minmum number of site connections in the new_configuration block.
         Note:This mib is not supported for VX instance of Virtualization."
    ::= { gslbGeneralCfg 14 }

gslbCurCfgGenUsern OBJECT-TYPE
    SYNTAX  INTEGER {
        enabled(1),
        disabled(2),
        unsupported(2147483647)
        }
    MAX-ACCESS  read-only
    STATUS  current
    DESCRIPTION
        "Enable/Disable HTTP redirect to real server name.
         Note:This mib is not supported for VX instance of Virtualization."
    ::= { gslbGeneralCfg 17 }

gslbNewCfgGenUsern OBJECT-TYPE
    SYNTAX  INTEGER {
        enabled(1),
        disabled(2),
        unsupported(2147483647)
        }
    MAX-ACCESS  read-write
    STATUS  current
    DESCRIPTION
        "Enable/Disable HTTP redirect to real server name.
         Note:This mib is not supported for VX instance of Virtualization."
    ::= { gslbGeneralCfg 18 }

gslbCurCfgGenNoremote OBJECT-TYPE
    SYNTAX INTEGER {
        enabled(1),
        disabled(2),
        unsupported(2147483647)
        }
    MAX-ACCESS read-only
    STATUS current
    DESCRIPTION
        "Enable/Disable no remote real SLB. Enabling will prevent the 
         switch from load balancing incoming traffic to remote reals in
         the event that all local reals are down.
         Note:This mib is not supported for VX instance of Virtualization."
    ::= { gslbGeneralCfg 25 }

gslbNewCfgGenNoremote OBJECT-TYPE
    SYNTAX INTEGER {
        enabled(1),
        disabled(2),
        unsupported(2147483647)
        }
    MAX-ACCESS read-write
    STATUS current
    DESCRIPTION
        "Enable/Disable no remote real SLB. Enabling will prevent the 
         switch from load balancing incoming traffic to remote reals in 
         the event that all local reals are down.
         Note:This mib is not supported for VX instance of Virtualization."
    ::= { gslbGeneralCfg 26 }

gslbCurCfgGenEncrypt OBJECT-TYPE
    SYNTAX INTEGER {
        enabled(1),
        disabled(2),
        unsupported(2147483647)
        }
    MAX-ACCESS read-only
    STATUS current
    DESCRIPTION
        "Enable/Disable encrypting remote site update.
         Note:This mib is not supported for VX instance of Virtualization."
    ::= { gslbGeneralCfg 27 }

gslbNewCfgGenEncrypt OBJECT-TYPE
    SYNTAX INTEGER {
        enabled(1),
        disabled(2),
        unsupported(2147483647)
        }
    MAX-ACCESS read-write
    STATUS current
    DESCRIPTION
        "Enable/Disable encrypting remote site update.
         Note:This mib is not supported for VX instance of Virtualization."
    ::= { gslbGeneralCfg 28 }

gslbCurCfgGenRemSiteUpdatePort OBJECT-TYPE
    SYNTAX  INTEGER (1..65535)
    MAX-ACCESS  read-only
    STATUS  current
    DESCRIPTION
        "TCP port number for remote site updates in
         the current configuration block.
         Note:This mib is not supported for VX instance of Virtualization."
    ::= { gslbGeneralCfg 29 }

gslbNewCfgGenRemSiteUpdatePort OBJECT-TYPE
    SYNTAX  INTEGER (1..65535)
    MAX-ACCESS  read-write
    STATUS  current
    DESCRIPTION
        "TCP port number for remote site updates in
         the new configuration block.
         Note:This mib is not supported for VX instance of Virtualization."
    ::= { gslbGeneralCfg 30 }

gslbCurCfgGenSessUtilCap OBJECT-TYPE
    SYNTAX  INTEGER (1..100)
    MAX-ACCESS  read-only
    STATUS  current
    DESCRIPTION
        "Session utilization capacity threshold in
         the current configuration block.
         Note:This mib is not supported for VX instance of Virtualization."
    ::= { gslbGeneralCfg 31 }

gslbNewCfgGenSessUtilCap OBJECT-TYPE
    SYNTAX  INTEGER (1..100)
    MAX-ACCESS  read-write
    STATUS  current
    DESCRIPTION
        "Session utilization capacity threshold in
         the new configuration block.
         Note:This mib is not supported for VX instance of Virtualization."
    ::= { gslbGeneralCfg 32 }

gslbCurCfgGenCpuUtilCap OBJECT-TYPE
    SYNTAX  INTEGER (1..100)
    MAX-ACCESS  read-only
    STATUS  current
    DESCRIPTION
        "CPU utilization capacity threshold in
         the current configuration block.
         Note:This mib is not supported for VX instance of Virtualization."
    ::= { gslbGeneralCfg 33 }

gslbNewCfgGenCpuUtilCap OBJECT-TYPE
    SYNTAX  INTEGER (1..100)
    MAX-ACCESS  read-write
    STATUS  current
    DESCRIPTION
        "CPU utilization capacity threshold in
         the new configuration block.
         Note:This mib is not supported for VX instance of Virtualization."
    ::= { gslbGeneralCfg 34 }

gslbCurCfgGenSourceIpNetmask OBJECT-TYPE
    SYNTAX IpAddress
    MAX-ACCESS  read-only
    STATUS  current
    DESCRIPTION
        "Source IP netmask for DNS persistence cache in
         the current configuration block.
         Note:This mib is not supported for VX instance of Virtualization."
    ::= { gslbGeneralCfg 35 }

gslbNewCfgGenSourceIpNetmask OBJECT-TYPE
    SYNTAX IpAddress
    MAX-ACCESS  read-write
    STATUS  current
    DESCRIPTION
        "Source IP netmask for DNS persistence cache in
         the new configuration block.
         Note:This mib is not supported for VX instance of Virtualization."
    ::= { gslbGeneralCfg 36 }

gslbCurCfgGenTimeout OBJECT-TYPE
    SYNTAX  INTEGER (1..1440)
    MAX-ACCESS  read-only
    STATUS  current
    DESCRIPTION
        "Timeout in minutes for DNS persistence cache in
         the current configuration block.
         Note:This mib is not supported for VX instance of Virtualization."
    ::= { gslbGeneralCfg 37 }

gslbNewCfgGenTimeout OBJECT-TYPE
    SYNTAX  INTEGER (1..1440)
    MAX-ACCESS  read-write
    STATUS  current
    DESCRIPTION
        "Timeout in minutes for DNS persistence cache in
         the new configuration block.
         Note:This mib is not supported for VX instance of Virtualization."
    ::= { gslbGeneralCfg 38 }

gslbCurCfgGenDnsDirect OBJECT-TYPE
    SYNTAX  INTEGER {
        enabled(1),
        disabled(2),
        unsupported(2147483647)
        }
    MAX-ACCESS  read-only
    STATUS  current
    DESCRIPTION
        "Enable/Disable authoritative DNS direct based Global SLB in
        the current configuration block.
        Note:This mib is not supported for VX instance of Virtualization."
    ::= { gslbGeneralCfg 39 }

gslbNewCfgGenDnsDirect OBJECT-TYPE
    SYNTAX  INTEGER {
        enabled(1),
        disabled(2),
        unsupported(2147483647)
        }
    MAX-ACCESS  read-write
    STATUS  current
    DESCRIPTION
        "Enable/Disable authoritative DNS direct based Global SLB in
        the new configuration block.
        Note:This mib is not supported for VX instance of Virtualization."
    ::= { gslbGeneralCfg 40 }

gslbCurCfgGenRemSiteUpdateVersion OBJECT-TYPE
    SYNTAX  INTEGER (1..5)
    MAX-ACCESS  read-only
    STATUS  current
    DESCRIPTION
        "DSSP version 1,2,3,4 or 5 to send out remote site updates in
        the current configuration block.
        Note:This mib is not supported for VX instance of Virtualization."
    ::= { gslbGeneralCfg 41 }

gslbNewCfgGenRemSiteUpdateVersion OBJECT-TYPE
    SYNTAX  INTEGER (1..5)
    MAX-ACCESS  read-write
    STATUS  current
    DESCRIPTION
        "DSSP version 1,2,3,4 or 5 to send out remote site updates in
        the new configuration block.
        Note:This mib is not supported for VX instance of Virtualization."
    ::= { gslbGeneralCfg 42 }

gslbCurCfgGenHostname OBJECT-TYPE
    SYNTAX  INTEGER {
        enabled(1),
        disabled(2),
        unsupported(2147483647)
        }
    MAX-ACCESS  read-only
    STATUS  current
    DESCRIPTION
        "Enable/Disable virtual service hostname matching in
        the current configuration block.
        Note:This mib is not supported for VX instance of Virtualization."
    ::= { gslbGeneralCfg 43 }

gslbNewCfgGenHostname OBJECT-TYPE
    SYNTAX  INTEGER {
        enabled(1),
        disabled(2),
        unsupported(2147483647)
        }
    MAX-ACCESS  read-write
    STATUS  current
    DESCRIPTION
        "Enable/Disable virtual service hostname matching in
        the new configuration block.
        Note:This mib is not supported for VX instance of Virtualization."
    ::= { gslbGeneralCfg 44 }

gslbCurCfgGenRemSiteUpdateIntervalSeconds OBJECT-TYPE
    SYNTAX  INTEGER (10..7200)
    MAX-ACCESS  read-only
    STATUS  current
    DESCRIPTION
        "The time interval in seconds for updating remote site status
         in the current_configuration block.
         Note:This mib is not supported for VX instance of Virtualization."
    ::= { gslbGeneralCfg 45 }

gslbNewCfgGenRemSiteUpdateIntervalSeconds OBJECT-TYPE
    SYNTAX  INTEGER (10..7200)
    MAX-ACCESS  read-write
    STATUS  current
    DESCRIPTION
        "The time interval in seconds for updating remote site status
         in the new_configuration block.
         Note:This mib is not supported for VX instance of Virtualization."
    ::= { gslbGeneralCfg 46 }

gslbCurCfgGenNoResp OBJECT-TYPE
    SYNTAX  INTEGER (1..5)
    MAX-ACCESS  read-only
    STATUS  current
    DESCRIPTION
        "DNS response code when no server is returned for the current_configuration block.
         Note:This mib is not supported for VX instance of Virtualization."
    ::= { gslbGeneralCfg 47 }

gslbNewCfgGenNoResp OBJECT-TYPE
    SYNTAX  INTEGER (1..5)
    MAX-ACCESS  read-write
    STATUS  current
    DESCRIPTION
        "DNS response code when no server is returned for the new_configuration block.
         Note:This mib is not supported for VX instance of Virtualization."
    ::= { gslbGeneralCfg 48 }

gslbCurCfgProximityTime OBJECT-TYPE
    SYNTAX  INTEGER (1..24)
    MAX-ACCESS  read-only
    STATUS  current
    DESCRIPTION
        "Current_configuration block maximum time allowed for Client Proximity calculation.
         Note:This mib is not supported for VX instance of Virtualization."
    ::= { gslbGeneralCfg 49 }

gslbNewCfgProximityTime OBJECT-TYPE
    SYNTAX  INTEGER (1..24)
    MAX-ACCESS  read-write
    STATUS  current
    DESCRIPTION
        "New_configuration block maximum time allowed for Client Proximity calculation.
         Note:This mib is not supported for VX instance of Virtualization."
    ::= { gslbGeneralCfg 50 }

gslbCurCfgProximityMask OBJECT-TYPE
    SYNTAX  INTEGER (8..24)
    MAX-ACCESS  read-only
    STATUS  current
    DESCRIPTION
        "Client Proximity default netmask of the client cache for the current_configuration block.
         Note:This mib is not supported for VX instance of Virtualization."
    ::= { gslbGeneralCfg 51 }

gslbNewCfgProximityMask OBJECT-TYPE
    SYNTAX  INTEGER (8..24)
    MAX-ACCESS  read-write
    STATUS  current
    DESCRIPTION
        "Client Proximity default netmask of the client cache for the new_configuration block.
         Note:This mib is not supported for VX instance of Virtualization."
    ::= { gslbGeneralCfg 52 }

gslbCurCfgProximityAge OBJECT-TYPE
    SYNTAX  INTEGER (0..10080)
    MAX-ACCESS  read-only
    STATUS  current
    DESCRIPTION
        "Client Proximity Age timeout of each client network entries for the current_configuration block.
         Note:This mib is not supported for VX instance of Virtualization."
    ::= { gslbGeneralCfg 53 }

gslbNewCfgProximityAge OBJECT-TYPE
    SYNTAX  INTEGER (0..10080)
    MAX-ACCESS  read-write
    STATUS  current
    DESCRIPTION
        "Client Proximity Age timeout of each client network entries for the new_configuration block.
         Note:This mib is not supported for VX instance of Virtualization."
    ::= { gslbGeneralCfg 54 }

gslbCurCfgGenSourceIpv6Prefix OBJECT-TYPE
    SYNTAX INTEGER (0..128)
    MAX-ACCESS  read-only
    STATUS  current
    DESCRIPTION
        "Source IPv6 prefix for DNS persistence cache in
         the current configuration block.
         Note:This mib is not supported for VX instance of Virtualization."
    ::= { gslbGeneralCfg 55 }

gslbNewCfgGenSourceIpv6Prefix OBJECT-TYPE
    SYNTAX INTEGER (0..128)
    MAX-ACCESS  read-write
    STATUS  current
    DESCRIPTION
        "Source IPv6 prefix for DNS persistence cache in
         the new configuration block.
         Note:This mib is not supported for VX instance of Virtualization."
    ::= { gslbGeneralCfg 56 }

gslbCurCfgGenDsync OBJECT-TYPE
    SYNTAX  INTEGER {
        enabled(1),
        disabled(2),
        unsupported(2147483647)
        }
    MAX-ACCESS  read-only
    STATUS  current
    DESCRIPTION
        "Enable/Disable sync of DNS persistence cache with remote sites.
         Note:This mib is not supported for VX instance of Virtualization."
    ::= { gslbGeneralCfg 57 }

gslbNewCfgGenDsync OBJECT-TYPE
    SYNTAX  INTEGER {
        enabled(1),
        disabled(2),
        unsupported(2147483647)
        }
    MAX-ACCESS  read-write
    STATUS  current
    DESCRIPTION
        "Enable/Disable sync of DNS persistence cache with remote sites.
         Note:This mib is not supported for VX instance of Virtualization."
    ::= { gslbGeneralCfg 58 }


gslbCurCfgProximityTimeAfterCalc OBJECT-TYPE
    SYNTAX  INTEGER (5..120)
    MAX-ACCESS  read-only
    STATUS  current
    DESCRIPTION
        "Current block maximum time allowed for Client Proximity, after calculation: multiplication by 5.
         Note:This mib is not supported for VX instance of Virtualization."
    ::= { gslbGeneralCfg 59 }

gslbNewCfgProximityTimeAfterCalc OBJECT-TYPE
    SYNTAX  INTEGER (5..120)
    MAX-ACCESS  read-only
    STATUS  current
    DESCRIPTION
        "New block maximum time allowed for Client Proximity, after calculation: multiplication by 5.
         Note:This mib is not supported for VX instance of Virtualization."
    ::= { gslbGeneralCfg 60 }

gslbCurCfgGenServcDownDnsRsp OBJECT-TYPE
    SYNTAX  INTEGER {
        norsp(1),
        srvfail(2),
        unsupported(2147483647)
        }
    MAX-ACCESS  read-only
    STATUS  current
    DESCRIPTION
        "The DNS down response in case of service failure.
         Note:This mib is not supported for VX instance of Virtualization."
    ::= { gslbGeneralCfg 61 }

gslbNewCfgGenServcDownDnsRsp OBJECT-TYPE
    SYNTAX  INTEGER {
        norsp(1),
        srvfail(2),
        unsupported(2147483647)
        }
    MAX-ACCESS  read-write
    STATUS  current
    DESCRIPTION
        "Set the DNS down response in case of service failure.
         Note:This mib is not supported for VX instance of Virtualization."
    ::= { gslbGeneralCfg 62 }

gslbCurCfgGenDssphc OBJECT-TYPE
    SYNTAX  INTEGER {
        enabled(1),
        disabled(2),
        unsupported(2147483647)
        }
    MAX-ACCESS  read-only
    STATUS obsolete 
    DESCRIPTION
        "Enable/Disable DSSP health check.
         Note:This mib is not supported for VX instance of Virtualization."
    ::= { gslbGeneralCfg 63 }

gslbNewCfgGenDssphc OBJECT-TYPE
    SYNTAX  INTEGER {
        enabled(1),
        disabled(2),
        unsupported(2147483647)
        }
    MAX-ACCESS  read-write
    STATUS obsolete 
    DESCRIPTION
        "Enable/Disable DSSP health check.
         Note:This mib is not supported for VX instance of Virtualization."
    ::= { gslbGeneralCfg 64 }

gslbCurCfgGenExcludeRedir OBJECT-TYPE
    SYNTAX INTEGER {
        disabled(0),
        enabled(1),
        unsupported(2147483647)
        }
    MAX-ACCESS read-only
    STATUS current
    DESCRIPTION
        "Enable/Disable redirect service from GSLB.
         Note:This mib is not supported for VX instance of Virtualization."
    ::= { gslbGeneralCfg 65 }

gslbNewCfgGenExcludeRedir OBJECT-TYPE
    SYNTAX INTEGER {
        disabled(0),
        enabled(1),
        unsupported(2147483647)
        }
    MAX-ACCESS read-write
    STATUS current
    DESCRIPTION
        "Enable/Disable redirect service from GSLB.
         Note:This mib is not supported for VX instance of Virtualization."
    ::= { gslbGeneralCfg 66 }

-- Global SLB Remote Site Configuration

gslbRemSiteTableMaxSize OBJECT-TYPE
    SYNTAX  Integer32
    MAX-ACCESS  read-only
    STATUS  current
    DESCRIPTION
        "The maximum number of GSLB remote sites.
         Note:This mib is not supported for VX instance of Virtualization."
    ::= { gslbSitesCfg 1 }

gslbCurCfgRemSiteTable OBJECT-TYPE
    SYNTAX  SEQUENCE OF GslbCurCfgRemSiteTableEntry
    MAX-ACCESS  not-accessible
    STATUS  current
    DESCRIPTION
        "The GSLB remote site table in the current configuration block.
         Note:This mib is not supported for VX instance of Virtualization."
    ::= { gslbSitesCfg 2 }

gslbCurCfgRemSiteTableEntry OBJECT-TYPE
    SYNTAX  GslbCurCfgRemSiteTableEntry
    MAX-ACCESS  not-accessible
    STATUS  current
    DESCRIPTION
        "A row in the GSLB remote site table."
    INDEX   { gslbCurCfgRemSiteIndx }
    ::= { gslbCurCfgRemSiteTable 1 }

GslbCurCfgRemSiteTableEntry ::= SEQUENCE {
    gslbCurCfgRemSiteIndx        Integer32,
    gslbCurCfgRemSitePrimaryIp   IpAddress,
    gslbCurCfgRemSiteSecondaryIp IpAddress,
    gslbCurCfgRemSiteState       INTEGER,
    gslbCurCfgRemSiteUpdate      INTEGER,
    gslbCurCfgRemSiteName        DisplayString,
    gslbCurCfgRemSitePrimaryIPVer  INTEGER,
    gslbCurCfgRemSitePrimaryIp6  DisplayString,
    gslbCurCfgRemSiteSecondaryIPVer  INTEGER,
    gslbCurCfgRemSiteSecondaryIp6 DisplayString,
    gslbCurCfgRemSitePeer            INTEGER
    }

gslbCurCfgRemSiteIndx OBJECT-TYPE
    SYNTAX  Integer32
    MAX-ACCESS  read-only
    STATUS  current
    DESCRIPTION
        "The GSLB remote site table index."
    ::= { gslbCurCfgRemSiteTableEntry 1 }

gslbCurCfgRemSitePrimaryIp OBJECT-TYPE
    SYNTAX  IpAddress
    MAX-ACCESS  read-only
    STATUS  current
    DESCRIPTION
        "The primary IP address of the remote site in the 
         current_configuration block."
    ::= { gslbCurCfgRemSiteTableEntry 2 }

gslbCurCfgRemSiteSecondaryIp OBJECT-TYPE
    SYNTAX  IpAddress
    MAX-ACCESS  read-only
    STATUS  current
    DESCRIPTION
        "The secondary IP address of the remote site in the 
	 current_configuration block."
    ::= { gslbCurCfgRemSiteTableEntry 3 }

gslbCurCfgRemSiteState OBJECT-TYPE
    SYNTAX  INTEGER {
        enabled(1),
        disabled(2),
        unsupported(2147483647)
        }
    MAX-ACCESS  read-only
    STATUS  current
    DESCRIPTION
        "Enable/Disable GSLB for the remote site in the 
         current_configuration block."
    ::= { gslbCurCfgRemSiteTableEntry 4 }

gslbCurCfgRemSiteUpdate OBJECT-TYPE
    SYNTAX  INTEGER {
        enabled(1),
        disabled(2),
        unsupported(2147483647)
        }
    MAX-ACCESS  read-only
    STATUS  current
    DESCRIPTION
        "Enable/Disable GSLB for the remote site status update in the 
         current_configuration block."
    ::= { gslbCurCfgRemSiteTableEntry 5 }

gslbCurCfgRemSiteName OBJECT-TYPE
    SYNTAX DisplayString (SIZE(0..64))
    MAX-ACCESS read-only
    STATUS current
    DESCRIPTION
	"The name of the GSLB remote site."
    ::= { gslbCurCfgRemSiteTableEntry 6 }


gslbCurCfgRemSitePrimaryIPVer OBJECT-TYPE
    SYNTAX  INTEGER{
        ipv4(1),
        ipv6(2),
        unsupported(2147483647)
        }
    MAX-ACCESS  read-only
    STATUS  current
    DESCRIPTION
        "The primary IP address version of the remote site."
    ::= { gslbCurCfgRemSiteTableEntry 8 }

gslbCurCfgRemSitePrimaryIp6 OBJECT-TYPE
   SYNTAX DisplayString (SIZE(0..40))
    MAX-ACCESS  read-only
    STATUS  current
    DESCRIPTION
    "  Primary IPV6 address of the remote site
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurCfgRemSiteTableEntry 9 }

gslbCurCfgRemSiteSecondaryIPVer OBJECT-TYPE
    SYNTAX  INTEGER{
        ipv4(1),
        ipv6(2),
        unsupported(2147483647)
        }
    MAX-ACCESS  read-only
    STATUS  current
    DESCRIPTION
        "The secondary IP address version of the remote site."
    ::= { gslbCurCfgRemSiteTableEntry 10 }

gslbCurCfgRemSiteSecondaryIp6 OBJECT-TYPE
   SYNTAX DisplayString (SIZE(0..40))
    MAX-ACCESS  read-only
    STATUS  current
    DESCRIPTION
    "  Secondary IPV6 address of the remote site
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurCfgRemSiteTableEntry 11 }

gslbCurCfgRemSitePeer OBJECT-TYPE
    SYNTAX  INTEGER {
        enabled(1),
        disabled(2),
        unsupported(2147483647)
        }
    MAX-ACCESS  read-only
    STATUS  current
    DESCRIPTION
        "Enable/Disable treatment of site as vrrp peer device."
    ::= { gslbCurCfgRemSiteTableEntry 12 }

gslbNewCfgRemSiteTable OBJECT-TYPE
    SYNTAX  SEQUENCE OF GslbNewCfgRemSiteTableEntry
    MAX-ACCESS  not-accessible
    STATUS  current
    DESCRIPTION
        "The GSLB remote site table in the current configuration block.
         Note:This mib is not supported for VX instance of Virtualization."
    ::= { gslbSitesCfg 3 }

gslbNewCfgRemSiteTableEntry OBJECT-TYPE
    SYNTAX  GslbNewCfgRemSiteTableEntry
    MAX-ACCESS  not-accessible
    STATUS  current
    DESCRIPTION
        "A row in the GSLB remote site table in the current configuration block."
    INDEX   { gslbNewCfgRemSiteIndx }
    ::= { gslbNewCfgRemSiteTable 1 }

GslbNewCfgRemSiteTableEntry ::= SEQUENCE {
    gslbNewCfgRemSiteIndx        Integer32,
    gslbNewCfgRemSitePrimaryIp   IpAddress,
    gslbNewCfgRemSiteSecondaryIp IpAddress,
    gslbNewCfgRemSiteState       INTEGER,
    gslbNewCfgRemSiteUpdate      INTEGER,
    gslbNewCfgRemSiteDelete      INTEGER,
    gslbNewCfgRemSiteName        DisplayString,
    gslbNewCfgRemSitePrimaryIPVer  INTEGER,
    gslbNewCfgRemSitePrimaryIp6  DisplayString,
    gslbNewCfgRemSiteSecondaryIPVer  INTEGER,
    gslbNewCfgRemSiteSecondaryIp6 DisplayString,
    gslbNewCfgRemSitePeer                INTEGER
    }

gslbNewCfgRemSiteIndx OBJECT-TYPE
    SYNTAX  Integer32
    MAX-ACCESS  read-only
    STATUS  current
    DESCRIPTION
        "The GSLB remote site table index."
    ::= { gslbNewCfgRemSiteTableEntry 1 }

gslbNewCfgRemSitePrimaryIp OBJECT-TYPE
    SYNTAX  IpAddress
    MAX-ACCESS  read-create
    STATUS  current
    DESCRIPTION
        "The primary IP address of the remote site in the new_configuration 
         block."
    ::= { gslbNewCfgRemSiteTableEntry 2 }

gslbNewCfgRemSiteSecondaryIp OBJECT-TYPE
    SYNTAX  IpAddress
    MAX-ACCESS  read-create
    STATUS  current
    DESCRIPTION
        "The secondary IP address of the remote site in the new_configuration 
         block."
    ::= { gslbNewCfgRemSiteTableEntry 3 }

gslbNewCfgRemSiteState OBJECT-TYPE
    SYNTAX  INTEGER {
        enabled(1),
        disabled(2),
        unsupported(2147483647)
        }
    MAX-ACCESS  read-create
    STATUS  current
    DESCRIPTION
        "Enable/Disable GSLB for the remote site in the new_configuration 
         block."
    ::= { gslbNewCfgRemSiteTableEntry 4 }

gslbNewCfgRemSiteUpdate OBJECT-TYPE
    SYNTAX  INTEGER {
        enabled(1),
        disabled(2),
        unsupported(2147483647)
        }
    MAX-ACCESS  read-create
    STATUS  current
    DESCRIPTION
        "Enable/Disable GSLB for the remote site status update in the 
         new_configuration block."
    ::= { gslbNewCfgRemSiteTableEntry 5 }

gslbNewCfgRemSiteDelete OBJECT-TYPE
    SYNTAX INTEGER {
        other(1),
        delete(2),
        unsupported(2147483647)
        }
    MAX-ACCESS read-create
    STATUS current
    DESCRIPTION
        "By setting the value to delete(2), the entire row is deleted."
    ::= { gslbNewCfgRemSiteTableEntry 6 }

gslbNewCfgRemSiteName OBJECT-TYPE
    SYNTAX DisplayString (SIZE(0..64))
    MAX-ACCESS read-create
    STATUS current
    DESCRIPTION
	"The name of the GSLB remote site."
    ::= { gslbNewCfgRemSiteTableEntry 7 }


gslbNewCfgRemSitePrimaryIPVer OBJECT-TYPE
    SYNTAX  INTEGER{
        ipv4(1),
        ipv6(2),
        unsupported(2147483647)
        }
    MAX-ACCESS  read-create
    STATUS  current
    DESCRIPTION
        "The primary IP address version of the remote site."
    ::= { gslbNewCfgRemSiteTableEntry 9 }

gslbNewCfgRemSitePrimaryIp6 OBJECT-TYPE
   SYNTAX DisplayString (SIZE(0..40))
    MAX-ACCESS  read-create
    STATUS  current
    DESCRIPTION
    "  Primary IPV6 address of the remote site
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewCfgRemSiteTableEntry 10 }

gslbNewCfgRemSiteSecondaryIPVer OBJECT-TYPE
    SYNTAX  INTEGER{
        ipv4(1),
        ipv6(2),
        unsupported(2147483647)
        }
    MAX-ACCESS  read-create
    STATUS  current
    DESCRIPTION
        "The secondary IP address version of the remote site."
    ::= { gslbNewCfgRemSiteTableEntry 11 }

gslbNewCfgRemSiteSecondaryIp6 OBJECT-TYPE
   SYNTAX DisplayString (SIZE(0..40))
    MAX-ACCESS  read-create
    STATUS  current
    DESCRIPTION
    "  Secondary IPV6 address of the remote site
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewCfgRemSiteTableEntry 12 }

gslbNewCfgRemSitePeer OBJECT-TYPE
    SYNTAX  INTEGER {
        enabled(1),
        disabled(2),
        unsupported(2147483647)
        }
    MAX-ACCESS  read-create
    STATUS  current
    DESCRIPTION
        "Enable/Disable treatment of site as vrrp peer device."
    ::= { gslbNewCfgRemSiteTableEntry 13 }

-- Global SLB Enhanced Network Configuration

gslbEnhNetworkTableMaxSize OBJECT-TYPE
    SYNTAX  Integer32
    MAX-ACCESS  read-only
    STATUS  current
    DESCRIPTION
        "The maximum number of Global SLB networks.
         Note:This mib is not supported for VX instance of Virtualization."
    ::= { gslbEnhNetworkCfg 1 }

gslbCurCfgEnhNetworkTable OBJECT-TYPE
    SYNTAX SEQUENCE OF GslbCurCfgEnhNetworkTableEntry
    MAX-ACCESS not-accessible
    STATUS current
    DESCRIPTION
        "The table of network preference in the current_config.
         Note:This mib is not supported for VX instance of Virtualization."
    ::= { gslbEnhNetworkCfg 2 }

gslbCurCfgEnhNetworkTableEntry OBJECT-TYPE
    SYNTAX GslbCurCfgEnhNetworkTableEntry
    MAX-ACCESS not-accessible
    STATUS current
    DESCRIPTION
        "The table about a network preference entry configuration."
    INDEX { gslbCurCfgEnhNetworkIndx }
    ::= { gslbCurCfgEnhNetworkTable 1 }

GslbCurCfgEnhNetworkTableEntry ::= SEQUENCE {
    gslbCurCfgEnhNetworkIndx       Integer32,
    gslbCurCfgEnhNetworkState      INTEGER,
    gslbCurCfgEnhNetworkSourceIp   IpAddress,
    gslbCurCfgEnhNetworkNetMask    IpAddress,
    gslbCurCfgEnhNetworkSourceIpV6  	     DisplayString,
    gslbCurCfgEnhNetworkVer      	     INTEGER,
    gslbCurCfgEnhNetworkSprefix      	     INTEGER,
    gslbCurCfgEnhNetworkClassId              DisplayString,
    gslbCurCfgEnhNetworkClientAddrSrc        INTEGER,
    gslbCurCfgEnhNetworkServType             INTEGER,
    gslbCurCfgEnhNetworkServIp               DisplayString,
    gslbCurCfgEnhNetworkSrcAddrType          INTEGER,
    gslbCurCfgEnhNetworkWanGrp               DisplayString,
    gslbCurCfgEnhNetworkName                 DisplayString
    }

gslbCurCfgEnhNetworkIndx  OBJECT-TYPE
    SYNTAX Integer32
    MAX-ACCESS read-only
    STATUS current
    DESCRIPTION
        "The current network preference table index."
    ::= { gslbCurCfgEnhNetworkTableEntry 1 }

gslbCurCfgEnhNetworkState OBJECT-TYPE
    SYNTAX  INTEGER {
        enabled(1),
        disabled(2),
        unsupported(2147483647)
        }
    MAX-ACCESS  read-only
    STATUS  current
    DESCRIPTION
        "Enable/Disable Global SLB for the network in the
         current_configuration block."
    ::= { gslbCurCfgEnhNetworkTableEntry 2 }

gslbCurCfgEnhNetworkSourceIp OBJECT-TYPE
    SYNTAX IpAddress
    MAX-ACCESS read-only
    STATUS current
    DESCRIPTION
        "The Source IP address of the network preference table."
    ::= { gslbCurCfgEnhNetworkTableEntry 3 }

gslbCurCfgEnhNetworkNetMask OBJECT-TYPE
    SYNTAX IpAddress
    MAX-ACCESS read-only
    STATUS current
    DESCRIPTION
        "The Net mask of the network preference table."
    ::= { gslbCurCfgEnhNetworkTableEntry 4 }

gslbCurCfgEnhNetworkSourceIpV6 OBJECT-TYPE
   SYNTAX DisplayString (SIZE(0..40))
    MAX-ACCESS read-only
    STATUS  current
    DESCRIPTION
    "  The Source IPV6 address of the network table
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurCfgEnhNetworkTableEntry 7 }

gslbCurCfgEnhNetworkVer OBJECT-TYPE
    SYNTAX  INTEGER{
        ipv4(1),
        ipv6(2),
        unsupported(2147483647)
        }
    MAX-ACCESS  read-only
    STATUS  current
    DESCRIPTION
        "The secondary IP address version of the remote site."
    ::= { gslbCurCfgEnhNetworkTableEntry 8 }

gslbCurCfgEnhNetworkSprefix OBJECT-TYPE
    SYNTAX   INTEGER(0..128) 
    MAX-ACCESS read-only
    STATUS  current
    DESCRIPTION
        "The prefix length associated with the source IPV6 address of the network table."
    ::= { gslbCurCfgEnhNetworkTableEntry 9 }

gslbCurCfgEnhNetworkClassId OBJECT-TYPE
    SYNTAX DisplayString (SIZE(0..32))
    MAX-ACCESS read-only
    STATUS  current
    DESCRIPTION
        "This is for gslb network sip value as any or network class ID."
    ::= { gslbCurCfgEnhNetworkTableEntry 10 }

gslbCurCfgEnhNetworkClientAddrSrc OBJECT-TYPE
    SYNTAX  INTEGER{
        ldns(1),
        ecs(2),
        unsupported(2147483647)
        }
    MAX-ACCESS  read-only
    STATUS  current
    DESCRIPTION
        "Client address source either LDNS or ECS."
    ::= { gslbCurCfgEnhNetworkTableEntry 11 }

gslbCurCfgEnhNetworkServType OBJECT-TYPE
    SYNTAX  INTEGER {
        group(0),
        server(1),
        unsupported(2147483647)
        }     
    MAX-ACCESS  read-only
    STATUS  current
    DESCRIPTION
        "Global SLB local server type for Smart nat in the new_configuration block."
    ::= { gslbCurCfgEnhNetworkTableEntry 12 }

gslbCurCfgEnhNetworkServIp OBJECT-TYPE
    SYNTAX DisplayString (SIZE(0..40))    
    MAX-ACCESS read-only
    STATUS current
    DESCRIPTION
        "The Local Server IP address.IPV4/V6"
    ::= { gslbCurCfgEnhNetworkTableEntry 13 }

gslbCurCfgEnhNetworkSrcAddrType OBJECT-TYPE
    SYNTAX INTEGER {
        address(1),
        network(2),
        unsupported(2147483647)
        }
    MAX-ACCESS read-only
    STATUS current
    DESCRIPTION
        "Global SLB network type fron any one as address or network."
    ::= { gslbCurCfgEnhNetworkTableEntry 14}

gslbCurCfgEnhNetworkWanGrp OBJECT-TYPE
    SYNTAX DisplayString (SIZE(0..255))
    MAX-ACCESS read-only
    STATUS current
    DESCRIPTION
        "The Local Server WAN Group (optional), applicable only for servtype server."
    ::= { gslbCurCfgEnhNetworkTableEntry 15 }

gslbCurCfgEnhNetworkName OBJECT-TYPE
    SYNTAX DisplayString (SIZE(0..31))
    MAX-ACCESS read-only
    STATUS current
    DESCRIPTION
        "The client network descriptive name."
    ::= { gslbCurCfgEnhNetworkTableEntry 16 }


gslbNewCfgEnhNetworkTable OBJECT-TYPE
    SYNTAX SEQUENCE OF GslbNewCfgEnhNetworkTableEntry
    MAX-ACCESS not-accessible
    STATUS current
    DESCRIPTION
        "The table of network preference in the new_config.
         Note:This mib is not supported for VX instance of Virtualization."
    ::= { gslbEnhNetworkCfg 3 }

gslbNewCfgEnhNetworkTableEntry OBJECT-TYPE
    SYNTAX GslbNewCfgEnhNetworkTableEntry
    MAX-ACCESS not-accessible
    STATUS current
    DESCRIPTION
        "The table about a network preference entry configuration."
    INDEX { gslbNewCfgEnhNetworkIndx }
    ::= { gslbNewCfgEnhNetworkTable 1 }

GslbNewCfgEnhNetworkTableEntry ::= SEQUENCE {
    gslbNewCfgEnhNetworkIndx       Integer32,
    gslbNewCfgEnhNetworkState      INTEGER,
    gslbNewCfgEnhNetworkSourceIp   IpAddress,
    gslbNewCfgEnhNetworkNetMask    IpAddress,
    gslbNewCfgEnhNetworkDelete     INTEGER,
    gslbNewCfgEnhNetworkAddVirtServer        Integer32,
    gslbNewCfgEnhNetworkRemoveVirtServer     Integer32,
    gslbNewCfgEnhNetworkAddRemRealServer     Integer32,
    gslbNewCfgEnhNetworkRemoveRemRealServer  Integer32,
    gslbNewCfgEnhNetworkSourceIpV6  	     DisplayString,
    gslbNewCfgEnhNetworkVer      	     INTEGER,
    gslbNewCfgEnhNetworkSprefix      	     INTEGER,
    gslbNewCfgEnhNetworkAddRealServerAlphaNum DisplayString,
    gslbNewCfgEnhNetworkRemRealServerAlphaNum DisplayString,
    gslbNewCfgEnhNetworkAddEnhVirtServer     DisplayString,
    gslbNewCfgEnhNetworkRemoveEnhVirtServer  DisplayString,
    gslbNewCfgEnhNetworkClassId              DisplayString,
    gslbNewCfgEnhNetworkClientAddrSrc        INTEGER,
    gslbNewCfgEnhNetworkServType             INTEGER,
    gslbNewCfgEnhNetworkServIp               DisplayString,
    gslbNewCfgEnhNetworkSrcAddrType          INTEGER,
    gslbNewCfgEnhNetworkWanGrp               DisplayString,
    gslbNewCfgEnhNetworkName  	     	     DisplayString
    }

gslbNewCfgEnhNetworkIndx  OBJECT-TYPE
    SYNTAX Integer32
    MAX-ACCESS read-only
    STATUS current
    DESCRIPTION
        "The new network preference table index."
    ::= { gslbNewCfgEnhNetworkTableEntry 1 }

gslbNewCfgEnhNetworkState OBJECT-TYPE
    SYNTAX  INTEGER {
        enabled(1),
        disabled(2),
        unsupported(2147483647)
        }
    MAX-ACCESS  read-create
    STATUS  current
    DESCRIPTION
        "Enable/Disable Global SLB for the network in
        the new_configuration block."
    ::= { gslbNewCfgEnhNetworkTableEntry 2 }

gslbNewCfgEnhNetworkSourceIp OBJECT-TYPE
    SYNTAX IpAddress
    MAX-ACCESS read-create
    STATUS current
    DESCRIPTION
        "The Source IP address of the network table."
    ::= { gslbNewCfgEnhNetworkTableEntry 3 }

gslbNewCfgEnhNetworkNetMask OBJECT-TYPE
    SYNTAX IpAddress
    MAX-ACCESS read-create
    STATUS current
    DESCRIPTION
        "The Net mask of the network preference table."
    ::= { gslbNewCfgEnhNetworkTableEntry 4 }

gslbNewCfgEnhNetworkDelete OBJECT-TYPE
    SYNTAX INTEGER {
        other(1),
        delete(2),
        unsupported(2147483647)
        }
    MAX-ACCESS read-create
    STATUS current
    DESCRIPTION
        "By setting the value to delete(2), the entire row is deleted."
    ::= { gslbNewCfgEnhNetworkTableEntry 5}

gslbNewCfgEnhNetworkAddVirtServer OBJECT-TYPE
    SYNTAX  Integer32
    MAX-ACCESS  read-create
    STATUS  current
    DESCRIPTION
        "The virtual server to be added to the network. When read, 0 is returned."
    ::= { gslbNewCfgEnhNetworkTableEntry 8 }

gslbNewCfgEnhNetworkRemoveVirtServer OBJECT-TYPE
    SYNTAX  Integer32
    MAX-ACCESS  read-create
    STATUS  current
    DESCRIPTION
        "The virtual server to be removed from the network. When read, 0 is returned."
    ::= { gslbNewCfgEnhNetworkTableEntry 9 }

gslbNewCfgEnhNetworkAddRemRealServer OBJECT-TYPE
    SYNTAX  Integer32
    MAX-ACCESS  read-create
    STATUS  current
    DESCRIPTION
        "The remote real server to be added to the network. When read, 0 is returned."
    ::= { gslbNewCfgEnhNetworkTableEntry 10 }

gslbNewCfgEnhNetworkRemoveRemRealServer OBJECT-TYPE
    SYNTAX  Integer32
    MAX-ACCESS  read-create
    STATUS  current
    DESCRIPTION
        "The remote real server to be removed from the network. When read, 0 is returned."
    ::= { gslbNewCfgEnhNetworkTableEntry 11 }

gslbNewCfgEnhNetworkSourceIpV6 OBJECT-TYPE
   SYNTAX DisplayString (SIZE(0..40))
    MAX-ACCESS  read-create
    STATUS  current
    DESCRIPTION
    "  The Source IPV6 address of the network table
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewCfgEnhNetworkTableEntry 12 }

gslbNewCfgEnhNetworkVer OBJECT-TYPE
    SYNTAX  INTEGER{
        ipv4(1),
        ipv6(2),
        unsupported(2147483647)
        }
    MAX-ACCESS  read-create
    STATUS  current
    DESCRIPTION
        "The secondary IP address version of the remote site."
    ::= { gslbNewCfgEnhNetworkTableEntry 13 }

gslbNewCfgEnhNetworkSprefix OBJECT-TYPE
    SYNTAX   INTEGER(0..128) 
    MAX-ACCESS  read-create
    STATUS  current
    DESCRIPTION
        "The prefix length associated with the source IPV6 address of the network table."
    ::= { gslbNewCfgEnhNetworkTableEntry 14 }

gslbNewCfgEnhNetworkAddRealServerAlphaNum OBJECT-TYPE 
    SYNTAX DisplayString (SIZE(0..255))
    MAX-ACCESS  read-create
    STATUS  current
    DESCRIPTION
        "The remote real server in alpha numeric to be added to the network." 
    ::= { gslbNewCfgEnhNetworkTableEntry 15 }

gslbNewCfgEnhNetworkRemRealServerAlphaNum OBJECT-TYPE
    SYNTAX DisplayString (SIZE(0..255))
    MAX-ACCESS  read-create
    STATUS  current
    DESCRIPTION
        "The remote real server to be removed from the network."
    ::= { gslbNewCfgEnhNetworkTableEntry 16 }

gslbNewCfgEnhNetworkAddEnhVirtServer OBJECT-TYPE
    SYNTAX DisplayString (SIZE(0..255))
    MAX-ACCESS  read-create
    STATUS  current
    DESCRIPTION
        "The remote virtual server in alpha numeric to be added to the network."
    ::= { gslbNewCfgEnhNetworkTableEntry 17 }

gslbNewCfgEnhNetworkRemoveEnhVirtServer OBJECT-TYPE
    SYNTAX DisplayString (SIZE(0..255))
    MAX-ACCESS  read-create
    STATUS  current
    DESCRIPTION
        "The remote virtual server to be removed from the network."
    ::= { gslbNewCfgEnhNetworkTableEntry 18 }

gslbNewCfgEnhNetworkClassId OBJECT-TYPE
    SYNTAX DisplayString (SIZE(0..32))
    MAX-ACCESS  read-create
    STATUS  current
    DESCRIPTION
        "The gslb network sip value as any or network class ID to be added to the network."
    ::= { gslbNewCfgEnhNetworkTableEntry 19 }

gslbNewCfgEnhNetworkClientAddrSrc OBJECT-TYPE
    SYNTAX  INTEGER{
        ldns(1),
        ecs(2),
        unsupported(2147483647)
        }
    MAX-ACCESS  read-create
    STATUS  current
    DESCRIPTION
        "Client address source configuration either LDNS or ECS to be added to the network."
    ::= { gslbNewCfgEnhNetworkTableEntry 20 }

gslbNewCfgEnhNetworkServType OBJECT-TYPE
    SYNTAX  INTEGER {
        group(0),
        server(1),
        unsupported(2147483647)
        }     
    MAX-ACCESS  read-create
    STATUS  current
    DESCRIPTION
        "Global SLB local server type for Smart nat in the new_configuration block."
    ::= { gslbNewCfgEnhNetworkTableEntry 21 }

gslbNewCfgEnhNetworkServIp OBJECT-TYPE
    SYNTAX DisplayString (SIZE(0..40))    
    MAX-ACCESS read-create
    STATUS current
    DESCRIPTION
        "The Local Server IP address.IPV4/V6"
    ::= { gslbNewCfgEnhNetworkTableEntry 22 }

gslbNewCfgEnhNetworkSrcAddrType OBJECT-TYPE
    SYNTAX INTEGER {
        address(1),
        network(2),
        unsupported(2147483647)
        }
    MAX-ACCESS read-create
    STATUS current
    DESCRIPTION
        "The gslb network type either address or network to be added to the network."
    ::= { gslbNewCfgEnhNetworkTableEntry 23}

gslbNewCfgEnhNetworkWanGrp OBJECT-TYPE
    SYNTAX DisplayString (SIZE(0..255))
    MAX-ACCESS read-create
    STATUS current
    DESCRIPTION
        "The Local Server WAN Group (optional), applicable only for servtype server."
    ::= { gslbNewCfgEnhNetworkTableEntry 24 }

gslbNewCfgEnhNetworkName OBJECT-TYPE
    SYNTAX DisplayString (SIZE(0..31))
    MAX-ACCESS read-create
    STATUS current
    DESCRIPTION
        "The client network descriptive name."
    ::= { gslbNewCfgEnhNetworkTableEntry 25 }


--Gslb network table virt/real preference table start

gslbCurCfgEnhNetworkVirtPrefTable OBJECT-TYPE
    SYNTAX SEQUENCE OF GslbCurCfgEnhNetworkVirtPrefTableEntry
    MAX-ACCESS not-accessible
    STATUS current
    DESCRIPTION
        "The table of network virt  preference in the cur_config.
         Note:This mib is not supported for VX instance of Virtualization."
    ::= { gslbEnhNetworkCfg 4 }

gslbCurCfgEnhNetworkVirtPrefTableEntry OBJECT-TYPE
    SYNTAX GslbCurCfgEnhNetworkVirtPrefTableEntry
    MAX-ACCESS not-accessible
    STATUS current
    DESCRIPTION
        "The table about a network virt preference entry configuration."
    INDEX { gslbCurCfgEnhNetworkVirtIndx , gslbCurCfgEnhNetworkVirtServerIndx}
    ::= { gslbCurCfgEnhNetworkVirtPrefTable 1 }

GslbCurCfgEnhNetworkVirtPrefTableEntry ::= SEQUENCE {
    gslbCurCfgEnhNetworkVirtIndx       Integer32,
    gslbCurCfgEnhNetworkVirtServerIndx      Integer32,
    gslbCurCfgEnhNetworkVirtServerPref   Integer32
    }

gslbCurCfgEnhNetworkVirtIndx  OBJECT-TYPE
    SYNTAX Integer32
    MAX-ACCESS read-only
    STATUS current
    DESCRIPTION
        "The current network preference table index."
    ::= { gslbCurCfgEnhNetworkVirtPrefTableEntry 1 }

gslbCurCfgEnhNetworkVirtServerIndx  OBJECT-TYPE
    SYNTAX Integer32
    MAX-ACCESS read-only
    STATUS current
    DESCRIPTION
        "The current network preference table server index."
    ::= { gslbCurCfgEnhNetworkVirtPrefTableEntry 2 }

gslbCurCfgEnhNetworkVirtServerPref OBJECT-TYPE
    SYNTAX Integer32
    MAX-ACCESS  read-only
    STATUS  current
    DESCRIPTION
        "current virtual server preference to network"
    ::= { gslbCurCfgEnhNetworkVirtPrefTableEntry 3 }

gslbNewCfgEnhNetworkVirtPrefTable OBJECT-TYPE
    SYNTAX SEQUENCE OF GslbNewCfgEnhNetworkVirtPrefTableEntry
    MAX-ACCESS not-accessible
    STATUS current
    DESCRIPTION
        "The table of network virt preference in the new_config.
         Note:This mib is not supported for VX instance of Virtualization."
    ::= { gslbEnhNetworkCfg 5 }

gslbNewCfgEnhNetworkVirtPrefTableEntry OBJECT-TYPE
    SYNTAX GslbNewCfgEnhNetworkVirtPrefTableEntry
    MAX-ACCESS not-accessible
    STATUS current
    DESCRIPTION
        "The table about a network virt  preference entry configuration."
    INDEX { gslbNewCfgEnhNetworkVirtIndx , gslbNewCfgEnhNetworkVirtServerIndx}
    ::= { gslbNewCfgEnhNetworkVirtPrefTable 1 }

GslbNewCfgEnhNetworkVirtPrefTableEntry ::= SEQUENCE {
    gslbNewCfgEnhNetworkVirtIndx       Integer32,
    gslbNewCfgEnhNetworkVirtServerIndx      Integer32,
    gslbNewCfgEnhNetworkVirtServerPref   Integer32
    }

gslbNewCfgEnhNetworkVirtIndx  OBJECT-TYPE
    SYNTAX Integer32
    MAX-ACCESS read-only
    STATUS current
    DESCRIPTION
        "The new network preference table index."
    ::= { gslbNewCfgEnhNetworkVirtPrefTableEntry 1 }

gslbNewCfgEnhNetworkVirtServerIndx  OBJECT-TYPE
    SYNTAX Integer32
    MAX-ACCESS read-only
    STATUS current
    DESCRIPTION
        "The new network preference server table index."
    ::= { gslbNewCfgEnhNetworkVirtPrefTableEntry 2 }

gslbNewCfgEnhNetworkVirtServerPref OBJECT-TYPE
    SYNTAX Integer32
    MAX-ACCESS  read-create
    STATUS  current
    DESCRIPTION
        "Add virtual server preference to network.
        Set Zero to remove virtual server from network"
    ::= { gslbNewCfgEnhNetworkVirtPrefTableEntry 3 }

gslbCurCfgEnhNetworkRealPrefTable OBJECT-TYPE
    SYNTAX SEQUENCE OF GslbCurCfgEnhNetworkRealPrefTableEntry
    MAX-ACCESS not-accessible
    STATUS current
    DESCRIPTION
        "The table of network remote real  preference in the cur_config.
         Note:This mib is not supported for VX instance of Virtualization."
    ::= { gslbEnhNetworkCfg 6 }

gslbCurCfgEnhNetworkRealPrefTableEntry OBJECT-TYPE
    SYNTAX GslbCurCfgEnhNetworkRealPrefTableEntry
    MAX-ACCESS not-accessible
    STATUS current
    DESCRIPTION
        "The table about a network remote real preference entry configuration."
    INDEX { gslbCurCfgEnhNetworkRealIndx , gslbCurCfgEnhNetworkRealServerIndx}
    ::= { gslbCurCfgEnhNetworkRealPrefTable 1 }

GslbCurCfgEnhNetworkRealPrefTableEntry ::= SEQUENCE {
    gslbCurCfgEnhNetworkRealIndx       Integer32,
    gslbCurCfgEnhNetworkRealServerIndx      Integer32,
    gslbCurCfgEnhNetworkRealServerPref   Integer32
    }

gslbCurCfgEnhNetworkRealIndx  OBJECT-TYPE
    SYNTAX Integer32
    MAX-ACCESS read-only
    STATUS current
    DESCRIPTION
        "The new network remote real preference  table index."
    ::= { gslbCurCfgEnhNetworkRealPrefTableEntry 1 }

gslbCurCfgEnhNetworkRealServerIndx  OBJECT-TYPE
    SYNTAX Integer32
    MAX-ACCESS read-only
    STATUS current
    DESCRIPTION
        "The new network remote real preference server table index."
    ::= { gslbCurCfgEnhNetworkRealPrefTableEntry 2 }

gslbCurCfgEnhNetworkRealServerPref OBJECT-TYPE
    SYNTAX Integer32
    MAX-ACCESS  read-only
    STATUS  current
    DESCRIPTION
        "Add remote real server preference to network"
    ::= { gslbCurCfgEnhNetworkRealPrefTableEntry 3 }

gslbNewCfgEnhNetworkRealPrefTable OBJECT-TYPE
    SYNTAX SEQUENCE OF GslbNewCfgEnhNetworkRealPrefTableEntry
    MAX-ACCESS not-accessible
    STATUS current
    DESCRIPTION
        "The table of network remote real preference in the new_config.
         Note:This mib is not supported for VX instance of Virtualization."
    ::= { gslbEnhNetworkCfg 7 }

gslbNewCfgEnhNetworkRealPrefTableEntry OBJECT-TYPE
    SYNTAX GslbNewCfgEnhNetworkRealPrefTableEntry
    MAX-ACCESS not-accessible
    STATUS current
    DESCRIPTION
        "The table about a network remote real preference entry configuration."
    INDEX { gslbNewCfgEnhNetworkRealIndx , gslbNewCfgEnhNetworkRealServerIndx}
    ::= { gslbNewCfgEnhNetworkRealPrefTable 1 }

GslbNewCfgEnhNetworkRealPrefTableEntry ::= SEQUENCE {
    gslbNewCfgEnhNetworkRealIndx       		Integer32,
    gslbNewCfgEnhNetworkRealServerIndx      	Integer32,
    gslbNewCfgEnhNetworkRealServerPref  	Integer32
    }

gslbNewCfgEnhNetworkRealIndx  OBJECT-TYPE
    SYNTAX Integer32
    MAX-ACCESS read-only
    STATUS current
    DESCRIPTION
        "The new network preference table index."
    ::= { gslbNewCfgEnhNetworkRealPrefTableEntry 1 }

gslbNewCfgEnhNetworkRealServerIndx  OBJECT-TYPE
    SYNTAX Integer32
    MAX-ACCESS read-only
    STATUS current
    DESCRIPTION
        "The new network preference server table index."
    ::= { gslbNewCfgEnhNetworkRealPrefTableEntry 2 }

gslbNewCfgEnhNetworkRealServerPref OBJECT-TYPE
    SYNTAX Integer32
    MAX-ACCESS  read-create
    STATUS  current
    DESCRIPTION
        "Add remote real server preference to network.
        Set Zero to remove the remote real server from network"
    ::= { gslbNewCfgEnhNetworkRealPrefTableEntry 3 }

gslbCurCfgEnhNetAlphaNumVirtPrefTable OBJECT-TYPE
    SYNTAX SEQUENCE OF GslbCurCfgEnhNetAlphaNumVirtPrefTableEntry
    MAX-ACCESS not-accessible
    STATUS current
    DESCRIPTION
        "The table of network virt  preference in the cur_config.
         Note:This mib is not supported for VX instance of Virtualization."
    ::= { gslbEnhNetworkCfg 8 }

gslbCurCfgEnhNetAlphaNumVirtPrefTableEntry OBJECT-TYPE
    SYNTAX GslbCurCfgEnhNetAlphaNumVirtPrefTableEntry
    MAX-ACCESS not-accessible
    STATUS current
    DESCRIPTION
        "The table about a network virt preference entry configuration."
    INDEX { gslbCurCfgEnhNetAlphaNumVirtIndx , gslbCurCfgEnhNetAlphaNumVirtServerIndx}
    ::= { gslbCurCfgEnhNetAlphaNumVirtPrefTable 1 }

GslbCurCfgEnhNetAlphaNumVirtPrefTableEntry ::= SEQUENCE {
    gslbCurCfgEnhNetAlphaNumVirtIndx         Integer32,
    gslbCurCfgEnhNetAlphaNumVirtServerIndx   DisplayString,
    gslbCurCfgEnhNetAlphaNumVirtServerPref   Integer32
    }

gslbCurCfgEnhNetAlphaNumVirtIndx  OBJECT-TYPE
    SYNTAX Integer32
    MAX-ACCESS read-only
    STATUS current
    DESCRIPTION
        "The current network preference table index."
    ::= { gslbCurCfgEnhNetAlphaNumVirtPrefTableEntry 1 }

gslbCurCfgEnhNetAlphaNumVirtServerIndx  OBJECT-TYPE
    SYNTAX DisplayString  ( SIZE ( 1 .. 255  ) )
    MAX-ACCESS read-only
    STATUS current
    DESCRIPTION
        "The current network preference table server index."
    ::= { gslbCurCfgEnhNetAlphaNumVirtPrefTableEntry 2 }

gslbCurCfgEnhNetAlphaNumVirtServerPref OBJECT-TYPE
    SYNTAX Integer32
    MAX-ACCESS  read-only
    STATUS  current
    DESCRIPTION
        "current virtual server preference to network"
    ::= { gslbCurCfgEnhNetAlphaNumVirtPrefTableEntry 3 }

gslbNewCfgEnhNetAlphaNumVirtPrefTable OBJECT-TYPE
    SYNTAX SEQUENCE OF GslbNewCfgEnhNetAlphaNumVirtPrefTableEntry
    MAX-ACCESS not-accessible
    STATUS current
    DESCRIPTION
        "The table of network virt preference in the new_config.
         Note:This mib is not supported for VX instance of Virtualization."
    ::= { gslbEnhNetworkCfg 9 }

gslbNewCfgEnhNetAlphaNumVirtPrefTableEntry OBJECT-TYPE
    SYNTAX GslbNewCfgEnhNetAlphaNumVirtPrefTableEntry
    MAX-ACCESS not-accessible
    STATUS current
    DESCRIPTION
        "The table about a network virt  preference entry configuration."
    INDEX { gslbNewCfgEnhNetAlphaNumVirtIndx , gslbNewCfgEnhNetAlphaNumVirtServerIndx}
    ::= { gslbNewCfgEnhNetAlphaNumVirtPrefTable 1 }

GslbNewCfgEnhNetAlphaNumVirtPrefTableEntry ::= SEQUENCE {
    gslbNewCfgEnhNetAlphaNumVirtIndx         Integer32,
    gslbNewCfgEnhNetAlphaNumVirtServerIndx   DisplayString,
    gslbNewCfgEnhNetAlphaNumVirtServerPref   Integer32,
    gslbNewCfgEnhNetAlphaNumVirtServerDelete   Integer32
    }

gslbNewCfgEnhNetAlphaNumVirtIndx  OBJECT-TYPE
    SYNTAX Integer32
    MAX-ACCESS read-only
    STATUS current
    DESCRIPTION
        "The new network preference table index."
    ::= { gslbNewCfgEnhNetAlphaNumVirtPrefTableEntry 1 }

gslbNewCfgEnhNetAlphaNumVirtServerIndx  OBJECT-TYPE
    SYNTAX DisplayString  ( SIZE ( 1 .. 255  ) )
    MAX-ACCESS read-only
    STATUS current
    DESCRIPTION
        "The new network preference server table index."
    ::= { gslbNewCfgEnhNetAlphaNumVirtPrefTableEntry 2 }

gslbNewCfgEnhNetAlphaNumVirtServerPref OBJECT-TYPE
    SYNTAX Integer32
    MAX-ACCESS  read-create
    STATUS  current
    DESCRIPTION
        "Add virtual server preference to network.
        Set Zero to remove virtual server from network.
	When read, the value '0' is always returned."
    ::= { gslbNewCfgEnhNetAlphaNumVirtPrefTableEntry 3 }

gslbNewCfgEnhNetAlphaNumVirtServerDelete OBJECT-TYPE
    SYNTAX Integer32
    MAX-ACCESS  read-create
    STATUS  current
    DESCRIPTION
        "rem virtual server preference to network.
        Set Zero to remove virtual server from network.
        When read, the value '0' is always returned"
    ::= { gslbNewCfgEnhNetAlphaNumVirtPrefTableEntry 4 }

gslbCurCfgEnhNetAlphaNumRealPrefTable OBJECT-TYPE
    SYNTAX SEQUENCE OF GslbCurCfgEnhNetAlphaNumRealPrefTableEntry
    MAX-ACCESS not-accessible
    STATUS current
    DESCRIPTION
        "The table of network remote real  preference in the cur_config.
         Note:This mib is not supported for VX instance of Virtualization."
    ::= { gslbEnhNetworkCfg 10 }

gslbCurCfgEnhNetAlphaNumRealPrefTableEntry OBJECT-TYPE
    SYNTAX GslbCurCfgEnhNetAlphaNumRealPrefTableEntry
    MAX-ACCESS not-accessible
    STATUS current
    DESCRIPTION
        "The table about a network remote real preference entry configuration."
    INDEX { gslbCurCfgEnhNetAlphaNumRealIndx , gslbCurCfgEnhNetAlphaNumRealServerIndx}
    ::= { gslbCurCfgEnhNetAlphaNumRealPrefTable 1 }

GslbCurCfgEnhNetAlphaNumRealPrefTableEntry ::= SEQUENCE {
    gslbCurCfgEnhNetAlphaNumRealIndx         Integer32,
    gslbCurCfgEnhNetAlphaNumRealServerIndx   DisplayString,
    gslbCurCfgEnhNetAlphaNumRealServerPref   Integer32
    }

gslbCurCfgEnhNetAlphaNumRealIndx  OBJECT-TYPE
    SYNTAX Integer32
    MAX-ACCESS read-only
    STATUS current
    DESCRIPTION
        "The new network remote real preference  table index."
    ::= { gslbCurCfgEnhNetAlphaNumRealPrefTableEntry 1 }

gslbCurCfgEnhNetAlphaNumRealServerIndx  OBJECT-TYPE
    SYNTAX DisplayString  ( SIZE ( 1 .. 255  ) )
    MAX-ACCESS read-only
    STATUS current
    DESCRIPTION
        "The new network remote real preference server table index."
    ::= { gslbCurCfgEnhNetAlphaNumRealPrefTableEntry 2 }

gslbCurCfgEnhNetAlphaNumRealServerPref OBJECT-TYPE
    SYNTAX Integer32
    MAX-ACCESS  read-only
    STATUS  current
    DESCRIPTION
        "Add remote real server preference to network"
    ::= { gslbCurCfgEnhNetAlphaNumRealPrefTableEntry 3 }

gslbNewCfgEnhNetAlphaNumRealPrefTable OBJECT-TYPE
    SYNTAX SEQUENCE OF GslbNewCfgEnhNetAlphaNumRealPrefTableEntry
    MAX-ACCESS not-accessible
    STATUS current
    DESCRIPTION
        "The table of network remote real preference in the new_config.
         Note:This mib is not supported for VX instance of Virtualization."
    ::= { gslbEnhNetworkCfg 11 }

gslbNewCfgEnhNetAlphaNumRealPrefTableEntry OBJECT-TYPE
    SYNTAX GslbNewCfgEnhNetAlphaNumRealPrefTableEntry
    MAX-ACCESS not-accessible
    STATUS current
    DESCRIPTION
        "The table about a network remote real preference entry configuration."
    INDEX { gslbNewCfgEnhNetAlphaNumRealIndx , gslbNewCfgEnhNetAlphaNumRealServerIndx}
    ::= { gslbNewCfgEnhNetAlphaNumRealPrefTable 1 }

GslbNewCfgEnhNetAlphaNumRealPrefTableEntry ::= SEQUENCE {
    gslbNewCfgEnhNetAlphaNumRealIndx         Integer32,
    gslbNewCfgEnhNetAlphaNumRealServerIndx   DisplayString,
    gslbNewCfgEnhNetAlphaNumRealServerPref   Integer32,
    gslbNewCfgEnhNetAlphaNumRealServerDelete   Integer32
    }

gslbNewCfgEnhNetAlphaNumRealIndx  OBJECT-TYPE
    SYNTAX Integer32
    MAX-ACCESS read-only
    STATUS current
    DESCRIPTION
        "The new network preference table index."
    ::= { gslbNewCfgEnhNetAlphaNumRealPrefTableEntry 1 }

gslbNewCfgEnhNetAlphaNumRealServerIndx  OBJECT-TYPE
    SYNTAX DisplayString  ( SIZE ( 1 .. 255  ) )
    MAX-ACCESS read-only
    STATUS current
    DESCRIPTION
        "The new network preference server table index."
    ::= { gslbNewCfgEnhNetAlphaNumRealPrefTableEntry 2 }

gslbNewCfgEnhNetAlphaNumRealServerPref OBJECT-TYPE
    SYNTAX Integer32
    MAX-ACCESS  read-create
    STATUS  current
    DESCRIPTION
        "Add remote real server preference to network.
        Set Zero to remove the remote real server from network"
    ::= { gslbNewCfgEnhNetAlphaNumRealPrefTableEntry 3 }

gslbNewCfgEnhNetAlphaNumRealServerDelete OBJECT-TYPE
    SYNTAX Integer32
    MAX-ACCESS  read-create
    STATUS  current
    DESCRIPTION
        "Del remote real server preference to network.
        Set Zero to remove the remote real server from network.
        When read, the value '0' is always returned"
    ::= { gslbNewCfgEnhNetAlphaNumRealPrefTableEntry 4 }

--Gslb network table virt/real preference table end

gslbEnhNetworkRealsTable OBJECT-TYPE
    SYNTAX SEQUENCE OF GslbEnhNetworkRealsTableEntry
    MAX-ACCESS not-accessible
    STATUS current
    DESCRIPTION
        "The table of network Reals in the new config.
         Note:This mib is not supported for VX instance of Virtualization."
    ::= { gslbEnhNetworkCfg 12 }

gslbEnhNetworkRealsTableEntry OBJECT-TYPE
    SYNTAX GslbEnhNetworkRealsTableEntry
    MAX-ACCESS not-accessible
    STATUS current
    DESCRIPTION
        "The table about a network preference entry configuration."
    INDEX { gslbEnhNetworkIndx, gslbEnhNetworkRealIndx }
    ::= { gslbEnhNetworkRealsTable 1 }

GslbEnhNetworkRealsTableEntry ::= SEQUENCE {
    gslbEnhNetworkIndx       Integer32,
    gslbEnhNetworkRealIndx   DisplayString
  }

gslbEnhNetworkIndx  OBJECT-TYPE
    SYNTAX Integer32
    MAX-ACCESS read-only
    STATUS current
    DESCRIPTION
        "The network table index."
    ::= { gslbEnhNetworkRealsTableEntry 1 }

gslbEnhNetworkRealIndx OBJECT-TYPE
    SYNTAX DisplayString (SIZE(1..255)) 
    MAX-ACCESS read-only
    STATUS current
    DESCRIPTION
        "The network real table AlphaNumeric index."
    ::= { gslbEnhNetworkRealsTableEntry 2 }

gslbEnhNetworkVirtsTable OBJECT-TYPE
    SYNTAX SEQUENCE OF GslbEnhNetworkVirtsTableEntry
    MAX-ACCESS not-accessible
    STATUS current
    DESCRIPTION
        "The table of network virtual servers in the new config.
         Note:This mib is not supported for VX instance of Virtualization."
    ::= { gslbEnhNetworkCfg 13 }

gslbEnhNetworkVirtsTableEntry OBJECT-TYPE
    SYNTAX GslbEnhNetworkVirtsTableEntry
    MAX-ACCESS not-accessible
    STATUS current
    DESCRIPTION
        "The table about a network preference entry configuration."
    INDEX { gslbEnhNetworkIndex, gslbEnhNetworkVirtIndx }
    ::= { gslbEnhNetworkVirtsTable 1 }

GslbEnhNetworkVirtsTableEntry ::= SEQUENCE {
    gslbEnhNetworkIndex       Integer32,
    gslbEnhNetworkVirtIndx   DisplayString
  }

gslbEnhNetworkIndex  OBJECT-TYPE
    SYNTAX Integer32
    MAX-ACCESS read-only
    STATUS current
    DESCRIPTION
        "The network table index."
    ::= { gslbEnhNetworkVirtsTableEntry 1 }

gslbEnhNetworkVirtIndx OBJECT-TYPE
    SYNTAX DisplayString (SIZE(1..255))
    MAX-ACCESS read-only
    STATUS current
    DESCRIPTION
        "The network virtual server table AlphaNumeric index."
    ::= { gslbEnhNetworkVirtsTableEntry 2 }

	
-- Global SLB Rule Configuration

gslbRuleTableMaxSize OBJECT-TYPE
    SYNTAX  Integer32
    MAX-ACCESS  read-only
    STATUS  current
    DESCRIPTION
        "The maximum number of Global SLB rules.
         Note:This mib is not supported for VX instance of Virtualization."
    ::= { gslbRuleCfg 1 }

gslbCurCfgRuleTable OBJECT-TYPE
    SYNTAX SEQUENCE OF GslbCurCfgRuleTableEntry
    MAX-ACCESS not-accessible
    STATUS current
    DESCRIPTION
        "The rule table in the current configuration block.
         Note:This mib is not supported for VX instance of Virtualization."
    ::= { gslbRuleCfg 2 }

gslbCurCfgRuleTableEntry OBJECT-TYPE
    SYNTAX GslbCurCfgRuleTableEntry
    MAX-ACCESS not-accessible
    STATUS current
    DESCRIPTION
        "An entry in the rule table in the current configuration block."
    INDEX { gslbCurCfgRuleIndx }
    ::= { gslbCurCfgRuleTable 1 }

GslbCurCfgRuleTableEntry ::= SEQUENCE {
    gslbCurCfgRuleIndx         Integer32,
    gslbCurCfgRuleState        INTEGER,
    gslbCurCfgRuleStartHour    INTEGER,
    gslbCurCfgRuleStartMin     INTEGER,
    gslbCurCfgRuleEndHour      INTEGER,
    gslbCurCfgRuleEndMin       INTEGER,
    gslbCurCfgRuleTTL          INTEGER,
    gslbCurCfgRuleRR           INTEGER,
    gslbCurCfgRuleDname        DisplayString,
    gslbCurCfgRuleIpNetMask    IpAddress,
    gslbCurCfgRuleTimeout      INTEGER,
    gslbCurCfgRuleIpv6Prefix   INTEGER,
    gslbCurCfgRuleType         INTEGER,
    gslbCurCfgRuleName         DisplayString,
    gslbCurCfgRulePort         INTEGER,
    gslbCurCfgRuleEdnsPrst     INTEGER,
    gslbCurCfgRulePersist      INTEGER,
    gslbCurCfgRuleNetworkFallback   INTEGER,
    gslbCurCfgRuleNamesrvr      DisplayString
    }

gslbCurCfgRuleIndx  OBJECT-TYPE
    SYNTAX Integer32
    MAX-ACCESS read-only
    STATUS current
    DESCRIPTION
        "The rule table index in the current configuration block."
    ::= { gslbCurCfgRuleTableEntry 1 }

gslbCurCfgRuleState OBJECT-TYPE
    SYNTAX  INTEGER {
        enabled(1),
        disabled(2),
        unsupported(2147483647)
        }
    MAX-ACCESS  read-only
    STATUS  current
    DESCRIPTION
        "Enable/Disable the rule in
         the current configuration block."
    ::= { gslbCurCfgRuleTableEntry 2 }

gslbCurCfgRuleStartHour OBJECT-TYPE
    SYNTAX  INTEGER (0..23)
    MAX-ACCESS  read-only
    STATUS  current
    DESCRIPTION
        "Start hour in 24-hour format for the rule in
         the current configuration block."
    ::= { gslbCurCfgRuleTableEntry 3 }

gslbCurCfgRuleStartMin OBJECT-TYPE
    SYNTAX  INTEGER (0..59)
    MAX-ACCESS  read-only
    STATUS  current
    DESCRIPTION
        "Start minutes for the rule in
         the current configuration block."
    ::= { gslbCurCfgRuleTableEntry 4 }

gslbCurCfgRuleEndHour OBJECT-TYPE
    SYNTAX  INTEGER (0..23)
    MAX-ACCESS  read-only
    STATUS  current
    DESCRIPTION
        "End hour in 24-hour format for the rule in
         the current configuration block."
    ::= { gslbCurCfgRuleTableEntry 5 }

gslbCurCfgRuleEndMin OBJECT-TYPE
    SYNTAX  INTEGER (0..59)
    MAX-ACCESS  read-only
    STATUS  current
    DESCRIPTION
        "End minutes for the rule in
         the current configuration block."
    ::= { gslbCurCfgRuleTableEntry 6 }

gslbCurCfgRuleTTL OBJECT-TYPE
    SYNTAX  INTEGER (0..65535)
    MAX-ACCESS  read-only
    STATUS  current
    DESCRIPTION
        "Time to live in seconds of DNS resource records for the rule in
         the current configuration block."
    ::= { gslbCurCfgRuleTableEntry 7 }

gslbCurCfgRuleRR OBJECT-TYPE
    SYNTAX  INTEGER (1..10)
    MAX-ACCESS  read-only
    STATUS  current
    DESCRIPTION
        "DNS resource records in DNS response for the rule in
         the current configuration block."
    ::= { gslbCurCfgRuleTableEntry 8 }

gslbCurCfgRuleDname OBJECT-TYPE
    SYNTAX DisplayString (SIZE(0..253))
    MAX-ACCESS read-only
    STATUS current
    DESCRIPTION
        "Network preference domain name for rule."
    ::= { gslbCurCfgRuleTableEntry 9 }

gslbCurCfgRuleIpNetMask OBJECT-TYPE
    SYNTAX IpAddress
    MAX-ACCESS  read-only
    STATUS  current
    DESCRIPTION
        "Source IP netmask for phash in
         the current configuration block."
    ::= { gslbCurCfgRuleTableEntry 10 }

gslbCurCfgRuleTimeout OBJECT-TYPE
    SYNTAX  INTEGER (0..1440)
    MAX-ACCESS  read-only
    STATUS  current
    DESCRIPTION
        "Timeout in minutes for phash in
         the current configuration block."
    ::= { gslbCurCfgRuleTableEntry 11 }

gslbCurCfgRuleIpv6Prefix OBJECT-TYPE
    SYNTAX INTEGER (0..128)
    MAX-ACCESS  read-only
    STATUS  current
    DESCRIPTION
        "Source IPv6 prefix for phash in
         the current configuration block."
    ::= { gslbCurCfgRuleTableEntry 12 }

gslbCurCfgRuleType OBJECT-TYPE
    SYNTAX INTEGER {
        gslb(0),
        inboundllb(1),
        unsupported(2147483647)
        }
    MAX-ACCESS read-only
    STATUS current
    DESCRIPTION
        "Rule type."
    ::= { gslbCurCfgRuleTableEntry 13 }

gslbCurCfgRuleName OBJECT-TYPE
    SYNTAX DisplayString (SIZE(0..128))
    MAX-ACCESS read-only
    STATUS current
    DESCRIPTION
        "Rule name"
    ::= { gslbCurCfgRuleTableEntry 14 }

gslbCurCfgRulePort OBJECT-TYPE
    SYNTAX INTEGER (1..65535)
    MAX-ACCESS read-only
    STATUS current
    DESCRIPTION
        "Rule port."
    ::= { gslbCurCfgRuleTableEntry 15 }

gslbCurCfgRuleEdnsPrst OBJECT-TYPE
    SYNTAX  INTEGER {
        enabled(1),
        disabled(2),
        unsupported(2147483647)
        }
    MAX-ACCESS read-only
    STATUS current
    DESCRIPTION
        "Persist on EDNS value."
    ::= { gslbCurCfgRuleTableEntry 16 }

gslbCurCfgRulePersist OBJECT-TYPE
    SYNTAX  INTEGER {
        domain(1),
        ip(2),
        unsupported(2147483647)
        }
    MAX-ACCESS read-only
    STATUS current
    DESCRIPTION
        "Persistence/hash parameter for rule."
    ::= { gslbCurCfgRuleTableEntry 17 }

gslbCurCfgRuleNetworkFallback OBJECT-TYPE
    SYNTAX  INTEGER {
        enabled(1),
        disabled(2),
        unsupported(2147483647)
        }
    MAX-ACCESS read-only
    STATUS current
    DESCRIPTION
        "Current state of Rule Network metric fallback."
    ::= { gslbCurCfgRuleTableEntry 18 }

gslbCurCfgRuleNamesrvr OBJECT-TYPE
    SYNTAX DisplayString (SIZE(0..128))
    MAX-ACCESS read-only
    STATUS current
    DESCRIPTION
        "DNS Nameserver group for rule."
    ::= { gslbCurCfgRuleTableEntry 19 }

gslbNewCfgRuleTable OBJECT-TYPE
    SYNTAX SEQUENCE OF GslbNewCfgRuleTableEntry
    MAX-ACCESS not-accessible
    STATUS current
    DESCRIPTION
        "The rule table in the new configuration block.
         Note:This mib is not supported for VX instance of Virtualization."
    ::= { gslbRuleCfg 3 }

gslbNewCfgRuleTableEntry OBJECT-TYPE
    SYNTAX GslbNewCfgRuleTableEntry
    MAX-ACCESS not-accessible
    STATUS current
    DESCRIPTION
        "An entry in the rule table in the new configuration block."
    INDEX { gslbNewCfgRuleIndx }
    ::= { gslbNewCfgRuleTable 1 }

GslbNewCfgRuleTableEntry ::= SEQUENCE {
    gslbNewCfgRuleIndx         Integer32,
    gslbNewCfgRuleState        INTEGER,
    gslbNewCfgRuleStartHour    INTEGER,
    gslbNewCfgRuleStartMin     INTEGER,
    gslbNewCfgRuleEndHour      INTEGER,
    gslbNewCfgRuleEndMin       INTEGER,
    gslbNewCfgRuleTTL          INTEGER,
    gslbNewCfgRuleRR           INTEGER,
    gslbNewCfgRuleDname        DisplayString, 
    gslbNewCfgRuleDelete       INTEGER,
    gslbNewCfgRuleIpNetMask    IpAddress,
    gslbNewCfgRuleTimeout      INTEGER,
    gslbNewCfgRuleIpv6Prefix   INTEGER,
    gslbNewCfgRuleType         INTEGER,
    gslbNewCfgRuleName         DisplayString,
    gslbNewCfgRulePort         INTEGER,
    gslbNewCfgRuleEdnsPrst     INTEGER,
    gslbNewCfgRulePersist      INTEGER,
    gslbNewCfgRuleNetworkFallback   INTEGER,
    gslbNewCfgRuleNamesrvr      DisplayString
    }

gslbNewCfgRuleIndx  OBJECT-TYPE
    SYNTAX Integer32
    MAX-ACCESS read-only
    STATUS current
    DESCRIPTION
        "The rule table index in the new configuration block."
    ::= { gslbNewCfgRuleTableEntry 1 }

gslbNewCfgRuleState OBJECT-TYPE
    SYNTAX  INTEGER {
        enabled(1),
        disabled(2),
        unsupported(2147483647)
        }
    MAX-ACCESS  read-create
    STATUS  current
    DESCRIPTION
        "Enable/Disable the rule in
         the new configuration block."
    ::= { gslbNewCfgRuleTableEntry 2 }

gslbNewCfgRuleStartHour OBJECT-TYPE
    SYNTAX  INTEGER (0..23)
    MAX-ACCESS  read-write
    STATUS  current
    DESCRIPTION
        "Start hour in 24-hour format for the rule in
         the new configuration block."
    ::= { gslbNewCfgRuleTableEntry 3 }

gslbNewCfgRuleStartMin OBJECT-TYPE
    SYNTAX  INTEGER (0..59)
    MAX-ACCESS  read-write
    STATUS  current
    DESCRIPTION
        "Start minutes for the rule in
         the new configuration block."
    ::= { gslbNewCfgRuleTableEntry 4 }

gslbNewCfgRuleEndHour OBJECT-TYPE
    SYNTAX  INTEGER (0..23)
    MAX-ACCESS  read-write
    STATUS  current
    DESCRIPTION
        "End hour in 24-hour format for the rule in
         the new configuration block."
    ::= { gslbNewCfgRuleTableEntry 5 }

gslbNewCfgRuleEndMin OBJECT-TYPE
    SYNTAX  INTEGER (0..59)
    MAX-ACCESS  read-write
    STATUS  current
    DESCRIPTION
        "End minutes for the rule in
         the new configuration block."
    ::= { gslbNewCfgRuleTableEntry 6 }

gslbNewCfgRuleTTL OBJECT-TYPE
    SYNTAX  INTEGER (0..65535)
    MAX-ACCESS  read-write
    STATUS  current
    DESCRIPTION
        "Time to live in seconds of DNS resource records for the rule in
         the new configuration block."
    ::= { gslbNewCfgRuleTableEntry 7 }

gslbNewCfgRuleRR OBJECT-TYPE
    SYNTAX  INTEGER (1..10)
    MAX-ACCESS  read-write
    STATUS  current
    DESCRIPTION
        "DNS resource records in DNS response for the rule in
         the new configuration block."
    ::= { gslbNewCfgRuleTableEntry 8 }

gslbNewCfgRuleDname OBJECT-TYPE
    SYNTAX DisplayString (SIZE(0..253))
    MAX-ACCESS read-create
    STATUS current
    DESCRIPTION
        "Network preference domain name for rule"
    ::= { gslbNewCfgRuleTableEntry 10 }

gslbNewCfgRuleDelete OBJECT-TYPE
    SYNTAX INTEGER {
        other(1),
        delete(2),
        unsupported(2147483647)
        }
    MAX-ACCESS read-create
    STATUS current
    DESCRIPTION
        "By setting the value to delete(2), the entire row is deleted."
    ::= { gslbNewCfgRuleTableEntry 9 }

gslbNewCfgRuleIpNetMask OBJECT-TYPE
    SYNTAX IpAddress
    MAX-ACCESS  read-write
    STATUS  current
    DESCRIPTION
        "Source IP netmask for phash in
         the new configuration block."
    ::= { gslbNewCfgRuleTableEntry 11 }

gslbNewCfgRuleTimeout OBJECT-TYPE
    SYNTAX  INTEGER (0..1440)
    MAX-ACCESS  read-write
    STATUS  current
    DESCRIPTION
        "Timeout in minutes for phash in
         the new configuration block."
    ::= { gslbNewCfgRuleTableEntry 12 }

gslbNewCfgRuleIpv6Prefix OBJECT-TYPE
    SYNTAX INTEGER (0..128)
    MAX-ACCESS  read-write
    STATUS  current
    DESCRIPTION
        "Source IPv6 prefix for phash in
         the new configuration block."
    ::= { gslbNewCfgRuleTableEntry 13 }

gslbNewCfgRuleType OBJECT-TYPE
    SYNTAX INTEGER {
        gslb(0),
        inboundllb(1),
        unsupported(2147483647)
        }
    MAX-ACCESS read-write
    STATUS current
    DESCRIPTION
        "Rule type."
    ::= { gslbNewCfgRuleTableEntry 14 }

gslbNewCfgRuleName OBJECT-TYPE
    SYNTAX DisplayString (SIZE(0..128))
    MAX-ACCESS read-write
    STATUS current
    DESCRIPTION
        "Rule name"
    ::= { gslbNewCfgRuleTableEntry 15 }

gslbNewCfgRulePort OBJECT-TYPE
    SYNTAX INTEGER (1..65535)
    MAX-ACCESS read-write
    STATUS current
    DESCRIPTION
        "Rule port."
    ::= { gslbNewCfgRuleTableEntry 16 }

gslbNewCfgRuleEdnsPrst OBJECT-TYPE
    SYNTAX  INTEGER {
        enabled(1),
        disabled(2),
        unsupported(2147483647)
        }
    MAX-ACCESS read-write
    STATUS current
    DESCRIPTION
        "Persist on EDNS value."
    ::= { gslbNewCfgRuleTableEntry 17 }

gslbNewCfgRulePersist OBJECT-TYPE
    SYNTAX  INTEGER {
        domain(1),
        ip(2),
        unsupported(2147483647)
        }
    MAX-ACCESS read-write
    STATUS current
    DESCRIPTION
        "Set persistence/hash parameter for rule."
    ::= { gslbNewCfgRuleTableEntry 18 }

gslbNewCfgRuleNetworkFallback OBJECT-TYPE
    SYNTAX  INTEGER {
        enabled(1),
        disabled(2),
        unsupported(2147483647)
        }
    MAX-ACCESS read-write
    STATUS current
    DESCRIPTION
        "Set Rule Network metric fallback to enable/disable."
    ::= { gslbNewCfgRuleTableEntry 19 }

gslbNewCfgRuleNamesrvr OBJECT-TYPE
    SYNTAX DisplayString (SIZE(0..128))
    MAX-ACCESS read-create
    STATUS current
    DESCRIPTION
        "DNS Nameserver group for rule"
    ::= { gslbNewCfgRuleTableEntry 20 }

-- Global SLB Metric Configuration

gslbMetricTableMaxSize OBJECT-TYPE
    SYNTAX Integer32
    MAX-ACCESS read-only
    STATUS current
    DESCRIPTION
        "The maximum number of Global SLB metrics for each Global SLB rule.
         Note:This mib is not supported for VX instance of Virtualization."
    ::= { gslbRuleCfg 4 }

gslbCurCfgMetricTable OBJECT-TYPE
    SYNTAX SEQUENCE OF GslbCurCfgMetricTableEntry
    MAX-ACCESS not-accessible
    STATUS current
    DESCRIPTION
        "The metric table in the current configuration block.
         Note:This mib is not supported for VX instance of Virtualization."
    ::= { gslbRuleCfg 5 }

gslbCurCfgMetricTableEntry OBJECT-TYPE
    SYNTAX GslbCurCfgMetricTableEntry
    MAX-ACCESS not-accessible
    STATUS current
    DESCRIPTION
        "An entry in the metric table in the current configuration block."
    INDEX { gslbCurCfgRuleMetricIndx, gslbCurCfgMetricIndx }
    ::= { gslbCurCfgMetricTable 1 }

GslbCurCfgMetricTableEntry ::= SEQUENCE {
    gslbCurCfgRuleMetricIndx        Integer32,
    gslbCurCfgMetricIndx            Integer32,
    gslbCurCfgMetricMetric          INTEGER,
    gslbCurCfgMetricNetworkBmap     OCTET STRING
    }

gslbCurCfgRuleMetricIndx  OBJECT-TYPE
    SYNTAX Integer32
    MAX-ACCESS read-only
    STATUS current
    DESCRIPTION
        "The rule table index in the current configuration block."
    ::= { gslbCurCfgMetricTableEntry 1 }

gslbCurCfgMetricIndx  OBJECT-TYPE
    SYNTAX Integer32
    MAX-ACCESS read-only
    STATUS current
    DESCRIPTION
        "The metric table index in the current configuration block."
    ::= { gslbCurCfgMetricTableEntry 2 }

gslbCurCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15),
        phash(16),
        proximity(17),
        bandwidth(18),
	absleastconns(19),
        unsupported(2147483647)
        }
    MAX-ACCESS read-only
    STATUS current
    DESCRIPTION
        "The metric to use to select next server in
         the current configuration block."
    ::= { gslbCurCfgMetricTableEntry 3 }

gslbCurCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbCurCfgMetricTableEntry 4 }

gslbNewCfgMetricTable OBJECT-TYPE
    SYNTAX SEQUENCE OF GslbNewCfgMetricTableEntry
    MAX-ACCESS not-accessible
    STATUS current
    DESCRIPTION
        "The metric table in the current configuration block.
         Note:This mib is not supported for VX instance of Virtualization."
    ::= { gslbRuleCfg 6 }

gslbNewCfgMetricTableEntry OBJECT-TYPE
    SYNTAX GslbNewCfgMetricTableEntry
    MAX-ACCESS not-accessible
    STATUS current
    DESCRIPTION
        "An entry in the metric table in the current configuration block."
    INDEX { gslbNewCfgRuleMetricIndx, gslbNewCfgMetricIndx }
    ::= { gslbNewCfgMetricTable 1 }

GslbNewCfgMetricTableEntry ::= SEQUENCE {
    gslbNewCfgRuleMetricIndx        Integer32,
    gslbNewCfgMetricIndx            Integer32,
    gslbNewCfgMetricMetric          INTEGER,
    gslbNewCfgMetricNetworkBmap     OCTET STRING,
    gslbNewCfgMetricAddNetwork      Integer32,
    gslbNewCfgMetricRemNetwork      Integer32
    }

gslbNewCfgRuleMetricIndx  OBJECT-TYPE
    SYNTAX Integer32
    MAX-ACCESS read-only
    STATUS current
    DESCRIPTION
        "The rule table index in the new configuration block."
    ::= { gslbNewCfgMetricTableEntry 1 }

gslbNewCfgMetricIndx  OBJECT-TYPE
    SYNTAX Integer32
    MAX-ACCESS read-only
    STATUS current
    DESCRIPTION
        "The metric table index in the new configuration block."
    ::= { gslbNewCfgMetricTableEntry 2 }

gslbNewCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15),
        phash(16),
        proximity(17),
        bandwidth(18),
	absleastconns(19),
        unsupported(2147483647)
        }
    MAX-ACCESS read-write
    STATUS current
    DESCRIPTION
        "The metric to use to select next server in
         the new configuration block."
    ::= { gslbNewCfgMetricTableEntry 3 }

gslbNewCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbNewCfgMetricTableEntry 4 }

gslbNewCfgMetricAddNetwork OBJECT-TYPE
    SYNTAX  Integer32
    MAX-ACCESS read-write
    STATUS  current
    DESCRIPTION
        "This is an action object to add network to a metric. The range of the
         valid index is between 1 and gslbEnhNetworkTableMaxSize. When read, the
         value '0' is returned always."
    ::= { gslbNewCfgMetricTableEntry 5 }

gslbNewCfgMetricRemNetwork OBJECT-TYPE
    SYNTAX  Integer32
    MAX-ACCESS read-write
    STATUS  current
    DESCRIPTION
        "This is an action object to remove network to a metric. The range of the
         valid index is between 1 and gslbEnhNetworkTableMaxSize. When read, the
         value '0' is returned always."
    ::= { gslbNewCfgMetricTableEntry 6 }


-- DNS SEC - Global

gslbCurCfgDnsSecGlobalEnabled OBJECT-TYPE
    SYNTAX INTEGER {
        enabled(1),
        disabled(2),
        unsupported(2147483647)
        }
    MAX-ACCESS read-only
    STATUS current
    DESCRIPTION
        "Note:This mib is not supported for VX instance of Virtualization."
    ::= { gslbDnsSecGlobalCfg 1 }

gslbNewCfgDnsSecGlobalEnabled OBJECT-TYPE
    SYNTAX INTEGER {
        enabled(1),
        disabled(2),
        unsupported(2147483647)
        }
    MAX-ACCESS read-write
    STATUS current
    DESCRIPTION
        "Enable/Disable DNSSEC feature.
         Note:This mib is not supported for VX instance of Virtualization."
    ::= { gslbDnsSecGlobalCfg 2 }

gslbCurCfgDnsSecGlobalRollTm OBJECT-TYPE
    SYNTAX INTEGER (1..168)
    MAX-ACCESS read-only
    STATUS current
    DESCRIPTION
        "Automatic Roll Over Timer - In Hours.
         Note:This mib is not supported for VX instance of Virtualization."
    ::= { gslbDnsSecGlobalCfg 3 }

gslbNewCfgDnsSecGlobalRollTm OBJECT-TYPE
    SYNTAX INTEGER (1..168)
    MAX-ACCESS read-write
    STATUS current
    DESCRIPTION
        "Automatic Roll Over Timer - In Hours.
         Note:This mib is not supported for VX instance of Virtualization."
    ::= { gslbDnsSecGlobalCfg 4 }

gslbCurCfgDnsSecGlobalType OBJECT-TYPE
    SYNTAX INTEGER {
        nsec(1),
        nsec3(2),
        unsupported(2147483647)
        }
    MAX-ACCESS read-only
    STATUS current
    DESCRIPTION
        "Automatic Roll Over Timer - In Hours.
         Note:This mib is not supported for VX instance of Virtualization."
    ::= { gslbDnsSecGlobalCfg 5 }

gslbNewCfgDnsSecGlobalType OBJECT-TYPE
    SYNTAX INTEGER {
        nsec(1),
        nsec3(2),
        unsupported(2147483647)
        }
    MAX-ACCESS read-write
    STATUS current
    DESCRIPTION
        "NSEC type - NSEC or NSEC3.
         Note:This mib is not supported for VX instance of Virtualization."
    ::= { gslbDnsSecGlobalCfg 6 }

gslbCurCfgDnsSecGlobalKskRollTm OBJECT-TYPE
    SYNTAX INTEGER (1..168)
    MAX-ACCESS read-only
    STATUS current
    DESCRIPTION
        "Automatic KSK Roll Over Timer - In Hours.
         Note:This mib is not supported for VX instance of Virtualization."
    ::= { gslbDnsSecGlobalCfg 9 }

gslbNewCfgDnsSecGlobalKskRollTm OBJECT-TYPE
    SYNTAX INTEGER (1..168)
    MAX-ACCESS read-write
    STATUS current
    DESCRIPTION
        "Automatic KSK Roll Over Timer - In Hours.
         Note:This mib is not supported for VX instance of Virtualization."
    ::= { gslbDnsSecGlobalCfg 10 }


gslbCurCfgDnsSecGlobalNsec3SaltLen OBJECT-TYPE
    SYNTAX INTEGER (1..255)
    MAX-ACCESS read-only
    STATUS current
    DESCRIPTION
        "NSEC3 Salt Length in bytes.
         Note:This mib is not supported for VX instance of Virtualization."
    ::= { gslbDnsSecGlobalCfg 11 }

gslbNewCfgDnsSecGlobalNsec3SaltLen OBJECT-TYPE
    SYNTAX INTEGER (1..255)
    MAX-ACCESS read-write
    STATUS current
    DESCRIPTION
        "NSEC3 Salt Length in bytes.
         Note:This mib is not supported for VX instance of Virtualization."
    ::= { gslbDnsSecGlobalCfg 12 }

gslbCurCfgDnsSecGlobalNsec3SaltLifetime OBJECT-TYPE
    SYNTAX INTEGER (86400..2419200)
    MAX-ACCESS read-only
    STATUS current
    DESCRIPTION
        "NSEC3 Salt Lifetime in seconds.
         Note:This mib is not supported for VX instance of Virtualization."
    ::= { gslbDnsSecGlobalCfg 13 }

gslbNewCfgDnsSecGlobalNsec3SaltLifetime OBJECT-TYPE
    SYNTAX INTEGER (86400..2419200)
    MAX-ACCESS read-write
    STATUS current
    DESCRIPTION
        "NSEC3 Salt Lifetime in seconds.
         Note:This mib is not supported for VX instance of Virtualization."
    ::= { gslbDnsSecGlobalCfg 14 }

gslbCurCfgDnsSecGlobalNsec3HashIterations OBJECT-TYPE
    SYNTAX INTEGER (0..500)
    MAX-ACCESS read-only
    STATUS current
    DESCRIPTION
        "NSEC3 Salt Hash Iterations.
         Note:This mib is not supported for VX instance of Virtualization."
    ::= { gslbDnsSecGlobalCfg 15 }

gslbNewCfgDnsSecGlobalNsec3HashIterations OBJECT-TYPE
    SYNTAX INTEGER (0..500)
    MAX-ACCESS read-write
    STATUS current
    DESCRIPTION
        "NSEC3 Salt Hash Iterations.
         Note:This mib is not supported for VX instance of Virtualization."
    ::= { gslbDnsSecGlobalCfg 16 }

gslbCurCfgDnsSecGlobalSMPTServerUserName OBJECT-TYPE
    SYNTAX   DisplayString (SIZE(0..20))
    MAX-ACCESS  read-only
    STATUS  current
    DESCRIPTION
        "SMPT Server User Name.
         Note:This mib is not supported for VX instance of Virtualization."
    ::= { gslbDnsSecGlobalCfg  17 }

gslbNewCfgDnsSecGlobalSMPTServerUserName OBJECT-TYPE
    SYNTAX   DisplayString (SIZE(0..20))
    MAX-ACCESS  read-write
    STATUS  current
    DESCRIPTION
        "SMPT Server User Name.
         Note:This mib is not supported for VX instance of Virtualization."
    ::= { gslbDnsSecGlobalCfg  18 }


gslbCurCfgDnsSecGlobalNsec3Algorithm OBJECT-TYPE
   SYNTAX INTEGER {
        sha1(1),
        sha256(2),
        unsupported(2147483647)
        }
    MAX-ACCESS  read-only
    STATUS  current
    DESCRIPTION
        "NSEC3 Hash Algorithm.
         Note:This mib is not supported for VX instance of Virtualization."
    ::= { gslbDnsSecGlobalCfg  19 }

gslbNewCfgDnsSecGlobalNsec3Algorithm OBJECT-TYPE
   SYNTAX INTEGER {
        sha1(1),
        sha256(2),
        unsupported(2147483647)
        }
    MAX-ACCESS  read-write
    STATUS  current
    DESCRIPTION
        "NSEC3 Hash Algorithm.
         Note:This mib is not supported for VX instance of Virtualization."
    ::= { gslbDnsSecGlobalCfg  20 }

gslbCurCfgDnsSecGlobalKeyMaster OBJECT-TYPE
   SYNTAX INTEGER {
        enabled(1),
        disabled(2),
        unsupported(2147483647)
        }
    MAX-ACCESS  read-only
    STATUS  current
    DESCRIPTION
        "Key master for VRRP configurations.
         Note:This mib is not supported for VX instance of Virtualization."
    ::= { gslbDnsSecGlobalCfg  21 }

gslbNewCfgDnsSecGlobalKeyMaster OBJECT-TYPE
   SYNTAX INTEGER {
        enabled(1),
        disabled(2),
        unsupported(2147483647)
        }
    MAX-ACCESS  read-write
    STATUS  current
    DESCRIPTION
        "Key master for VRRP configurations.
         Note:This mib is not supported for VX instance of Virtualization."
    ::= { gslbDnsSecGlobalCfg  22 }

gslbCurDnsSecKeyTable OBJECT-TYPE
    SYNTAX  SEQUENCE OF GslbCurDnsSecKeyEntry
    MAX-ACCESS  not-accessible
    STATUS  current
    DESCRIPTION
        "Note:This mib is not supported for VX instance of Virtualization."
    ::= { gslbDnsSecKeyCfg 1 }

gslbCurDnsSecKeyEntry OBJECT-TYPE
    SYNTAX  GslbCurDnsSecKeyEntry
    MAX-ACCESS  not-accessible
    STATUS  current
    DESCRIPTION
        "."
    INDEX   { gslbCurDnsSecKeyID }
    ::= { gslbCurDnsSecKeyTable 1 }

GslbCurDnsSecKeyEntry ::= SEQUENCE {
    gslbCurDnsSecKeyID                DisplayString,
    gslbCurDnsSecKeyUseCount          INTEGER,
    gslbCurDnsSecKeyType              INTEGER,
    gslbCurDnsSecKeyStatus            INTEGER,
    gslbCurDnsSecKeySize              INTEGER,
    gslbCurDnsSecKeyAlgo              INTEGER,
    gslbCurDnsSecKeyTTL               INTEGER,
    gslbCurDnsSecKeyExpPeriod         Unsigned32,
    gslbCurDnsSecKeyRollOverPeriod    Unsigned32,
    gslbCurDnsSecKeyValidityPeriod    Unsigned32,
    gslbCurDnsSecKeyPublicationPeriod Unsigned32
    }

gslbCurDnsSecKeyID OBJECT-TYPE
    SYNTAX   DisplayString (SIZE(0..32))
    MAX-ACCESS  read-only
    STATUS  current
    DESCRIPTION
        "DNS Sec Table Key."
    ::= { gslbCurDnsSecKeyEntry  1 }

gslbCurDnsSecKeyUseCount OBJECT-TYPE
    SYNTAX  INTEGER (0..65534)
    MAX-ACCESS  read-only
    STATUS  current
    DESCRIPTION
        "Usage count."
    ::= { gslbCurDnsSecKeyEntry 2 }

gslbCurDnsSecKeyType OBJECT-TYPE
    SYNTAX INTEGER {
        keyTypeKSK(1),
        keyTypeZSK(2),
        keyTypeInvalid(3),
        unsupported(2147483647)
        }
    MAX-ACCESS  read-only
    STATUS  current
    DESCRIPTION
        "KSK or ZSK."
    ::= { gslbCurDnsSecKeyEntry 3 }

gslbCurDnsSecKeyStatus OBJECT-TYPE
    SYNTAX INTEGER {
        enable(1),
        disable(2),
        unsupported(2147483647)
        }
    MAX-ACCESS  read-only
    STATUS  current
    DESCRIPTION
        "Key status."
    ::= { gslbCurDnsSecKeyEntry 4 }

gslbCurDnsSecKeySize OBJECT-TYPE
    SYNTAX INTEGER {
        keySize1024(1),
        keySize2048(2),
        keySize4096(3),
        keySizeInvalid(4),
        unsupported(2147483647)
        }
    MAX-ACCESS  read-only
    STATUS  current
    DESCRIPTION
        "Size of key (bits)."
    ::= { gslbCurDnsSecKeyEntry 5 }

gslbCurDnsSecKeyAlgo OBJECT-TYPE
    SYNTAX INTEGER {
        keyAlgoRsaSha1(1),
        keyAlgoRsaSha256(2),
        keyAlgoRsaSha512(3),
        unsupported(2147483647)
        }
    MAX-ACCESS  read-only
    STATUS  current
    DESCRIPTION
        "Signing algorithm."
    ::= { gslbCurDnsSecKeyEntry 6 }

gslbCurDnsSecKeyTTL OBJECT-TYPE
    SYNTAX  INTEGER (0..86400)
    MAX-ACCESS  read-only
    STATUS  current
    DESCRIPTION
        "DNSSEC - TTL in Seconds."
    ::= { gslbCurDnsSecKeyEntry 7 }

gslbCurDnsSecKeyExpPeriod OBJECT-TYPE
    SYNTAX      Unsigned32 (1..'ffffffff'h)
    MAX-ACCESS  read-only
    STATUS  current
    DESCRIPTION
        "Expiration period in Seconds."
    ::= { gslbCurDnsSecKeyEntry 8 }

gslbCurDnsSecKeyRollOverPeriod OBJECT-TYPE
    SYNTAX      Unsigned32 (1..'ffffffff'h)
    MAX-ACCESS  read-only
    STATUS  current
    DESCRIPTION
        "RollOver period in Seconds."
    ::= { gslbCurDnsSecKeyEntry 9 }

gslbCurDnsSecKeyValidityPeriod OBJECT-TYPE
    SYNTAX      Unsigned32 (1..'ffffffff'h)
    MAX-ACCESS  read-only
    STATUS  current
    DESCRIPTION
        "Signature validity period in Seconds."
    ::= { gslbCurDnsSecKeyEntry 10 }

gslbCurDnsSecKeyPublicationPeriod OBJECT-TYPE
    SYNTAX      Unsigned32 (1..'ffffffff'h)
    MAX-ACCESS  read-only
    STATUS  current
    DESCRIPTION
        "Signature publication period in Seconds."
    ::= { gslbCurDnsSecKeyEntry 11 }

gslbNewDnsSecKeyTable OBJECT-TYPE
    SYNTAX  SEQUENCE OF GslbNewDnsSecKeyEntry
    MAX-ACCESS  not-accessible
    STATUS  current
    DESCRIPTION
        "Note:This mib is not supported for VX instance of Virtualization."
    ::= { gslbDnsSecKeyCfg 2 }

gslbNewDnsSecKeyEntry OBJECT-TYPE
    SYNTAX  GslbNewDnsSecKeyEntry
    MAX-ACCESS  not-accessible
    STATUS  current
    DESCRIPTION
        "."
    INDEX   { gslbNewDnsSecKeyID }
    ::= { gslbNewDnsSecKeyTable 1 }

GslbNewDnsSecKeyEntry ::= SEQUENCE {
    gslbNewDnsSecKeyID                DisplayString,
    gslbNewDnsSecKeyUseCount          INTEGER,
    gslbNewDnsSecKeyType              INTEGER,
    gslbNewDnsSecKeyStatus            INTEGER,
    gslbNewDnsSecKeySize              INTEGER,
    gslbNewDnsSecKeyAlgo              INTEGER,
    gslbNewDnsSecKeyTTL               INTEGER,
    gslbNewDnsSecKeyExpPeriod         Unsigned32,
    gslbNewDnsSecKeyRollOverPeriod    Unsigned32,
    gslbNewDnsSecKeyValidityPeriod    Unsigned32,
    gslbNewDnsSecKeyPublicationPeriod Unsigned32,
    gslbNewDnsSecKeyDelete            INTEGER,
    gslbNewDnsSecKeyGenerate          INTEGER,
    gslbNewDnsSecKeyGenerateStatus    INTEGER
    }

gslbNewDnsSecKeyID OBJECT-TYPE
    SYNTAX   DisplayString (SIZE(0..32))
    MAX-ACCESS  read-create
    STATUS  current
    DESCRIPTION
        "DNS Sec Table Key."
    ::= { gslbNewDnsSecKeyEntry  1 }

gslbNewDnsSecKeyUseCount OBJECT-TYPE
    SYNTAX  INTEGER (0..65534)
    MAX-ACCESS  read-only
    STATUS  current
    DESCRIPTION
        "Usage count."
    ::= { gslbNewDnsSecKeyEntry 2 }

gslbNewDnsSecKeyType OBJECT-TYPE
    SYNTAX INTEGER {
        keyTypeKSK(1),
        keyTypeZSK(2),
        keyTypeInvalid(3),
        unsupported(2147483647)
        }
    MAX-ACCESS  read-create
    STATUS  current
    DESCRIPTION
        "KSK or ZSK."
    ::= { gslbNewDnsSecKeyEntry 3 }

gslbNewDnsSecKeyStatus OBJECT-TYPE
    SYNTAX INTEGER {
        enable(1),
        disable(2),
        unsupported(2147483647)
        }
    MAX-ACCESS  read-write
    STATUS  current
    DESCRIPTION
        "Key state."
    ::= { gslbNewDnsSecKeyEntry 4 }

gslbNewDnsSecKeySize OBJECT-TYPE
    SYNTAX INTEGER {
        keySize1024(1),
        keySize2048(2),
        keySize4096(3),
        keySizeInvalid(4),
        unsupported(2147483647)
        }
    MAX-ACCESS  read-create
    STATUS  current
    DESCRIPTION
        "Size of key (bits)."
    ::= { gslbNewDnsSecKeyEntry 5 }

gslbNewDnsSecKeyAlgo OBJECT-TYPE
    SYNTAX INTEGER {
        keyAlgoRsaSha1(1),
        keyAlgoRsaSha256(2),
        keyAlgoRsaSha512(3),
        unsupported(2147483647)
        }
    MAX-ACCESS  read-create
    STATUS  current
    DESCRIPTION
        "Signing algorithm."
    ::= { gslbNewDnsSecKeyEntry 6 }

gslbNewDnsSecKeyTTL OBJECT-TYPE
    SYNTAX  INTEGER (0..86400)
    MAX-ACCESS  read-write
    STATUS  current
    DESCRIPTION
        "DNSSEC - TTL."
    ::= { gslbNewDnsSecKeyEntry 7 }

gslbNewDnsSecKeyExpPeriod OBJECT-TYPE
    SYNTAX      Unsigned32 (1..'ffffffff'h)
    MAX-ACCESS  read-write
    STATUS  current
    DESCRIPTION
        "Expiration period in Seconds."
    ::= { gslbNewDnsSecKeyEntry 8 }

gslbNewDnsSecKeyRollOverPeriod OBJECT-TYPE
    SYNTAX      Unsigned32 (1..'ffffffff'h)
    MAX-ACCESS  read-write
    STATUS  current
    DESCRIPTION
        "RollOver period in Seconds."
    ::= { gslbNewDnsSecKeyEntry 9 }

gslbNewDnsSecKeyValidityPeriod OBJECT-TYPE
    SYNTAX      Unsigned32 (1..'ffffffff'h)
    MAX-ACCESS  read-write
    STATUS  current
    DESCRIPTION
        "Signature validity period in Seconds."
    ::= { gslbNewDnsSecKeyEntry 10 }

gslbNewDnsSecKeyPublicationPeriod OBJECT-TYPE
    SYNTAX      Unsigned32 (1..'ffffffff'h)
    MAX-ACCESS  read-write
    STATUS  current
    DESCRIPTION
        "Signature publication period in Seconds."
    ::= { gslbNewDnsSecKeyEntry 11 }

gslbNewDnsSecKeyDelete OBJECT-TYPE
    SYNTAX  INTEGER {
        other(1),
        delete(2),
        unsupported(2147483647)
        }
    MAX-ACCESS  read-create
    STATUS  current
    DESCRIPTION
        "By setting the value to delete(2), the entire row is deleted."
    ::= { gslbNewDnsSecKeyEntry 13 }

gslbNewDnsSecKeyGenerate OBJECT-TYPE
    SYNTAX  INTEGER {
        other(1),
        generate(2),
        unsupported(2147483647)
        }
    MAX-ACCESS  read-create
    STATUS  current
    DESCRIPTION
        "By setting the value to generate(2), the key will be generated."
    ::= { gslbNewDnsSecKeyEntry 14 }

gslbNewDnsSecKeyGenerateStatus OBJECT-TYPE
    SYNTAX  INTEGER {
        notGenerated(1),
        generated(2),
        inProgress(3),
        unsupported(2147483647)
        }
    MAX-ACCESS  read-only
    STATUS  current
    DESCRIPTION
        "Returns the generate status."
    ::= { gslbNewDnsSecKeyEntry 15 }

gslbCurDnsSecZoneTable OBJECT-TYPE
    SYNTAX  SEQUENCE OF GslbCurDnsSecZoneEntry
    MAX-ACCESS  not-accessible
    STATUS  current
    DESCRIPTION
        "Note:This mib is not supported for VX instance of Virtualization."
    ::= { gslbDnsSecZoneCfg 1 }

gslbCurDnsSecZoneEntry OBJECT-TYPE
    SYNTAX  GslbCurDnsSecZoneEntry
    MAX-ACCESS  not-accessible
    STATUS  current
    DESCRIPTION
        "."
    INDEX   { gslbCurDnsSecZoneID }
    ::= { gslbCurDnsSecZoneTable 1 }

GslbCurDnsSecZoneEntry ::= SEQUENCE {
    gslbCurDnsSecZoneID               DisplayString,
    gslbCurDnsSecZoneName             DisplayString,
    gslbCurDnsSecZoneKSK1             DisplayString,
    gslbCurDnsSecZoneKSK2             DisplayString,
    gslbCurDnsSecZoneKSK3             DisplayString,
    gslbCurDnsSecZoneZSK1             DisplayString,
    gslbCurDnsSecZoneZSK2             DisplayString,
    gslbCurDnsSecZoneZSK3             DisplayString,
    gslbCurDnsSecZoneStatus           INTEGER,
    gslbCurDnsSecZoneParentIPVer      INTEGER,
    gslbCurDnsSecZoneParentIPv4       IpAddress,
    gslbCurDnsSecZoneParentIPv6       DisplayString,
    gslbCurDnsSecZoneParentHost       DisplayString
    }

gslbCurDnsSecZoneID OBJECT-TYPE
    SYNTAX   DisplayString (SIZE(0..32))
    MAX-ACCESS  read-only
    STATUS  current
    DESCRIPTION
        "Zone ID."
    ::= { gslbCurDnsSecZoneEntry  1 }

gslbCurDnsSecZoneName OBJECT-TYPE
    SYNTAX   DisplayString (SIZE(0..65))
    MAX-ACCESS  read-only
    STATUS  current
    DESCRIPTION
        "Zone name (virt's dname)."
    ::= { gslbCurDnsSecZoneEntry  2 }

gslbCurDnsSecZoneKSK1 OBJECT-TYPE
    SYNTAX   DisplayString (SIZE(0..32))
    MAX-ACCESS  read-only
    STATUS  current
    DESCRIPTION
        "KSK 1 of the zone."
    ::= { gslbCurDnsSecZoneEntry  3 }

gslbCurDnsSecZoneKSK2 OBJECT-TYPE
    SYNTAX   DisplayString (SIZE(0..32))
    MAX-ACCESS  read-only
    STATUS  current
    DESCRIPTION
        "KSK 2 of the zone."
    ::= { gslbCurDnsSecZoneEntry  4 }

gslbCurDnsSecZoneKSK3 OBJECT-TYPE
    SYNTAX   DisplayString (SIZE(0..32))
    MAX-ACCESS  read-only
    STATUS  current
    DESCRIPTION
        "KSK 3 of the zone."
    ::= { gslbCurDnsSecZoneEntry  5 }

gslbCurDnsSecZoneZSK1 OBJECT-TYPE
    SYNTAX   DisplayString (SIZE(0..32))
    MAX-ACCESS  read-only
    STATUS  current
    DESCRIPTION
        "ZSK 1 of the zone."
    ::= { gslbCurDnsSecZoneEntry  6 }

gslbCurDnsSecZoneZSK2 OBJECT-TYPE
    SYNTAX   DisplayString (SIZE(0..32))
    MAX-ACCESS  read-only
    STATUS  current
    DESCRIPTION
        "ZSK 2 of the zone."
    ::= { gslbCurDnsSecZoneEntry  7 }

gslbCurDnsSecZoneZSK3 OBJECT-TYPE
    SYNTAX   DisplayString (SIZE(0..32))
    MAX-ACCESS  read-only
    STATUS  current
    DESCRIPTION
        "ZSK 1 of the zone."
    ::= { gslbCurDnsSecZoneEntry  8 }

gslbCurDnsSecZoneStatus OBJECT-TYPE
    SYNTAX INTEGER {
        enable(1),
        disable(2),
        unsupported(2147483647)
        }
    MAX-ACCESS  read-only
    STATUS  current
    DESCRIPTION
        "Zone status - Enabled/Disabled."
    ::= { gslbCurDnsSecZoneEntry 9 }

gslbCurDnsSecZoneParentIPVer OBJECT-TYPE
    SYNTAX  INTEGER{
        ipv4(1),
        ipv6(2),
        unsupported(2147483647)
        }
    MAX-ACCESS  read-only
    STATUS  current
    DESCRIPTION
        "The type of IP address."
    ::= { gslbCurDnsSecZoneEntry 10 }

gslbCurDnsSecZoneParentIPv4 OBJECT-TYPE
    SYNTAX IpAddress
    MAX-ACCESS  read-only
    STATUS  current
    DESCRIPTION
        "Parent IP."
    ::= { gslbCurDnsSecZoneEntry 11 }

gslbCurDnsSecZoneParentIPv6 OBJECT-TYPE
   SYNTAX DisplayString (SIZE(0..40))
    MAX-ACCESS  read-only
    STATUS  current
    DESCRIPTION
    "  IPV6 address of the Parent IP
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurDnsSecZoneEntry 12 }

gslbCurDnsSecZoneParentHost OBJECT-TYPE
   SYNTAX DisplayString (SIZE(0..65))
    MAX-ACCESS  read-only
    STATUS  current
    DESCRIPTION
    "Parent Hostname/IPv4 Address/IPv6 Address."
   ::= { gslbCurDnsSecZoneEntry 13 }

gslbNewDnsSecZoneTable OBJECT-TYPE
    SYNTAX  SEQUENCE OF GslbNewDnsSecZoneEntry
    MAX-ACCESS  not-accessible
    STATUS  current
    DESCRIPTION
        "Note:This mib is not supported for VX instance of Virtualization."
    ::= { gslbDnsSecZoneCfg 2 }

gslbNewDnsSecZoneEntry OBJECT-TYPE
    SYNTAX  GslbNewDnsSecZoneEntry
    MAX-ACCESS  not-accessible
    STATUS  current
    DESCRIPTION
        "."
    INDEX   { gslbNewDnsSecZoneID }
    ::= { gslbNewDnsSecZoneTable 1 }

GslbNewDnsSecZoneEntry ::= SEQUENCE {
    gslbNewDnsSecZoneID               DisplayString,
    gslbNewDnsSecZoneName             DisplayString,
    gslbNewDnsSecZoneKSK1             DisplayString,
    gslbNewDnsSecZoneKSK2             DisplayString,
    gslbNewDnsSecZoneKSK3             DisplayString,
    gslbNewDnsSecZoneZSK1             DisplayString,
    gslbNewDnsSecZoneZSK2             DisplayString,
    gslbNewDnsSecZoneZSK3             DisplayString,
    gslbNewDnsSecZoneStatus           INTEGER,
    gslbNewDnsSecZoneParentIPVer      INTEGER,
    gslbNewDnsSecZoneParentIPv4       IpAddress,
    gslbNewDnsSecZoneParentIPv6       DisplayString,
    gslbNewDnsSecZoneParentHost       DisplayString,
    gslbNewDnsSecZoneDelete           INTEGER
    }

gslbNewDnsSecZoneID OBJECT-TYPE
    SYNTAX   DisplayString (SIZE(0..32))
    MAX-ACCESS  read-create
    STATUS  current
    DESCRIPTION
        "Zone ID."
    ::= { gslbNewDnsSecZoneEntry  1 }

gslbNewDnsSecZoneName OBJECT-TYPE
    SYNTAX   DisplayString (SIZE(0..65))
    MAX-ACCESS  read-write
    STATUS  current
    DESCRIPTION
        "Zone name (virt's dname)."
    ::= { gslbNewDnsSecZoneEntry  2 }

gslbNewDnsSecZoneKSK1 OBJECT-TYPE
    SYNTAX   DisplayString (SIZE(0..32))
    MAX-ACCESS  read-write
    STATUS  current
    DESCRIPTION
        "KSK 1 of the zone."
    ::= { gslbNewDnsSecZoneEntry  3 }

gslbNewDnsSecZoneKSK2 OBJECT-TYPE
    SYNTAX   DisplayString (SIZE(0..32))
    MAX-ACCESS  read-write
    STATUS  current
    DESCRIPTION
        "KSK 2 of the zone."
    ::= { gslbNewDnsSecZoneEntry  4 }

gslbNewDnsSecZoneKSK3 OBJECT-TYPE
    SYNTAX   DisplayString (SIZE(0..32))
    MAX-ACCESS  read-write
    STATUS  current
    DESCRIPTION
        "KSK 3 of the zone."
    ::= { gslbNewDnsSecZoneEntry  5 }

gslbNewDnsSecZoneZSK1 OBJECT-TYPE
    SYNTAX   DisplayString (SIZE(0..32))
    MAX-ACCESS  read-write
    STATUS  current
    DESCRIPTION
        "ZSK 1 of the zone."
    ::= { gslbNewDnsSecZoneEntry  6 }

gslbNewDnsSecZoneZSK2 OBJECT-TYPE
    SYNTAX   DisplayString (SIZE(0..32))
    MAX-ACCESS  read-write
    STATUS  current
    DESCRIPTION
        "ZSK 2 of the zone."
    ::= { gslbNewDnsSecZoneEntry  7 }

gslbNewDnsSecZoneZSK3 OBJECT-TYPE
    SYNTAX   DisplayString (SIZE(0..32))
    MAX-ACCESS  read-write
    STATUS  current
    DESCRIPTION
        "ZSK 3 of the zone."
    ::= { gslbNewDnsSecZoneEntry  8 }

gslbNewDnsSecZoneStatus OBJECT-TYPE
    SYNTAX INTEGER {
        enable(1),
        disable(2),
        unsupported(2147483647)
        }
    MAX-ACCESS  read-write
    STATUS  current
    DESCRIPTION
        "Zone status - Enabled/Disabled."
    ::= { gslbNewDnsSecZoneEntry 9 }

gslbNewDnsSecZoneParentIPVer OBJECT-TYPE
    SYNTAX  INTEGER{
        ipv4(1),
        ipv6(2),
        unsupported(2147483647)
        }
    MAX-ACCESS  read-only
    STATUS  current
    DESCRIPTION
        "The type of IP address."
    ::= { gslbNewDnsSecZoneEntry 10 }

gslbNewDnsSecZoneParentIPv4 OBJECT-TYPE
    SYNTAX IpAddress
    MAX-ACCESS  read-write
    STATUS  current
    DESCRIPTION
        "IPV4 address of the Parent IP."
    ::= { gslbNewDnsSecZoneEntry 11 }

gslbNewDnsSecZoneParentIPv6 OBJECT-TYPE
   SYNTAX DisplayString (SIZE(0..40))
    MAX-ACCESS  read-write
    STATUS  current
    DESCRIPTION
    "  IPV6 address of the Parent IP
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewDnsSecZoneEntry 12 }


gslbNewDnsSecZoneDelete OBJECT-TYPE
    SYNTAX  INTEGER {
        other(1),
        delete(2),
        unsupported(2147483647)
        }
    MAX-ACCESS  read-write
    STATUS  current
    DESCRIPTION
        "By setting the value to delete(2), the entire row is deleted."
    ::= { gslbNewDnsSecZoneEntry 13 }

gslbNewDnsSecZoneParentHost OBJECT-TYPE
   SYNTAX DisplayString (SIZE(0..65))
    MAX-ACCESS  read-write
    STATUS  current
    DESCRIPTION
    "Parent Hostname/IPv4 Address/IPv6 Address."
   ::= { gslbNewDnsSecZoneEntry 14 }

-- DNS SEC - Import/Export

gslbDnsSecImportExportSCPHostName OBJECT-TYPE
    SYNTAX   DisplayString (SIZE(0..128))
    MAX-ACCESS read-write
    STATUS current
    DESCRIPTION
        "SCP Server Host Name or Server IP Address.
         Note:This mib is not supported for VX instance of Virtualization."
    ::= { gslbDnsSecImportExport 1 }

gslbDnsSecImportExportSCPFileName OBJECT-TYPE
    SYNTAX   DisplayString (SIZE(0..128))
    MAX-ACCESS read-write
    STATUS current
    DESCRIPTION
        "SCP Server File name.
         Note:This mib is not supported for VX instance of Virtualization."
    ::= { gslbDnsSecImportExport 2 }

gslbDnsSecImportExportSCPUserName OBJECT-TYPE
    SYNTAX   DisplayString (SIZE(0..128))
    MAX-ACCESS read-write
    STATUS current
    DESCRIPTION
        "SCP Server User Name.
         Note:This mib is not supported for VX instance of Virtualization."
    ::= { gslbDnsSecImportExport 3 }

gslbDnsSecImportExportSCPPassword OBJECT-TYPE
    SYNTAX   DisplayString (SIZE(0..128))
    MAX-ACCESS read-write
    STATUS current
    DESCRIPTION
        "SCP Server Password.
         Note:This mib is not supported for VX instance of Virtualization."
    ::= { gslbDnsSecImportExport 4 }

gslbDnsSecImportExportKeyID OBJECT-TYPE
    SYNTAX   DisplayString (SIZE(0..32))
    MAX-ACCESS read-write
    STATUS current
    DESCRIPTION
        "DNSSEC Key ID.
         Note:This mib is not supported for VX instance of Virtualization."
    ::= { gslbDnsSecImportExport 5 }

gslbDnsSecImportExportZoneID OBJECT-TYPE
    SYNTAX   DisplayString (SIZE(0..32))
    MAX-ACCESS read-write
    STATUS current
    DESCRIPTION
        "DNSSEC Zone ID.
         Note:This mib is not supported for VX instance of Virtualization."
    ::= { gslbDnsSecImportExport 6 }

gslbDnsSecImportExportPassphrase OBJECT-TYPE
    SYNTAX   DisplayString (SIZE(0..40))
    MAX-ACCESS read-write
    STATUS current
    DESCRIPTION
        "Passphrase.
         Note:This mib is not supported for VX instance of Virtualization."
    ::= { gslbDnsSecImportExport 7 }

gslbDnsSecImportExportComponentType OBJECT-TYPE
    SYNTAX  INTEGER {
        none(0),
        key(1),
        dnskey(2),
        dsrecord(3),
        unsupported(2147483647)
        }
    MAX-ACCESS  read-write
    STATUS  current
    DESCRIPTION
        "Component type to import/export: key, dnskey or ds record.
         Currently only the key is Supported.
         Note:This mib is not supported for VX instance of Virtualization."
    ::= { gslbDnsSecImportExport 8 }

gslbDnsSecImportExportPortType OBJECT-TYPE
    SYNTAX  INTEGER {
        data(0),
        mgmt(1),
        unsupported(2147483647)
        }
    MAX-ACCESS  read-write
    STATUS  current
    DESCRIPTION
        "The port type: management or data.
         Note:This mib is not supported for VX instance of Virtualization."
    ::= { gslbDnsSecImportExport 9 }

gslbDnsSecImportExportImpKeyType OBJECT-TYPE
    SYNTAX INTEGER {
        keyTypeKSK(1),
        keyTypeZSK(2),
        unsupported(2147483647)
        }
    MAX-ACCESS  read-write
    STATUS  current
    DESCRIPTION
        "KSK or ZSK.
         Note:This mib is not supported for VX instance of Virtualization."
    ::= { gslbDnsSecImportExport 10 }

gslbDnsSecImportExportImpKeyStatus OBJECT-TYPE
    SYNTAX INTEGER {
        enable(1),
        disable(2),
        unsupported(2147483647)
        }
    MAX-ACCESS  read-write
    STATUS  current
    DESCRIPTION
        "Key status.
         Note:This mib is not supported for VX instance of Virtualization."
    ::= { gslbDnsSecImportExport 11 }

gslbDnsSecImportExportImpKeySize OBJECT-TYPE
    SYNTAX INTEGER {
        keySize1024(1),
        keySize2048(2),
        keySize4096(3),
        unsupported(2147483647)
        }
    MAX-ACCESS  read-only
    STATUS  current
    DESCRIPTION
        "Size of key (bits).
         Note:This mib is not supported for VX instance of Virtualization."
    ::= { gslbDnsSecImportExport 12 }

gslbDnsSecImportExportImpKeyAlgo OBJECT-TYPE
    SYNTAX INTEGER {
        keyAlgoRsaSha1(1),
        keyAlgoRsaSha256(2),
        keyAlgoRsaSha512(3),
        unsupported(2147483647)
        }
    MAX-ACCESS  read-write
    STATUS  current
    DESCRIPTION
        "Signing algorithm.
         Note:This mib is not supported for VX instance of Virtualization."
    ::= { gslbDnsSecImportExport 13 }

gslbDnsSecImportExportImpKeyTTL OBJECT-TYPE
    SYNTAX  INTEGER (0..86400)
    MAX-ACCESS  read-write
    STATUS  current
    DESCRIPTION
        "DNSSEC - TTL in Seconds.
         Note:This mib is not supported for VX instance of Virtualization."
    ::= { gslbDnsSecImportExport 14 }

gslbDnsSecImportExportImpKeyExpPeriod OBJECT-TYPE
    SYNTAX      Unsigned32 (1..'ffffffff'h)
    MAX-ACCESS  read-write
    STATUS  current
    DESCRIPTION
        "Expiration period in Seconds.
         Note:This mib is not supported for VX instance of Virtualization."
    ::= { gslbDnsSecImportExport 15 }

gslbDnsSecImportExportImpKeyRollOverPeriod OBJECT-TYPE
    SYNTAX      Unsigned32 (1..'ffffffff'h)
    MAX-ACCESS  read-write
    STATUS  current
    DESCRIPTION
        "RollOver period in Seconds.
         Note:This mib is not supported for VX instance of Virtualization."
    ::= { gslbDnsSecImportExport 16 }

gslbDnsSecImportExportImpKeyValidityPeriod OBJECT-TYPE
    SYNTAX      Unsigned32 (1..'ffffffff'h)
    MAX-ACCESS  read-write
    STATUS  current
    DESCRIPTION
        "Signature validity period in Seconds.
         Note:This mib is not supported for VX instance of Virtualization."
    ::= { gslbDnsSecImportExport 17 }

gslbDnsSecImportExportImpKeyPublicationPeriod OBJECT-TYPE
    SYNTAX      Unsigned32 (1..'ffffffff'h)
    MAX-ACCESS  read-write
    STATUS  current
    DESCRIPTION
        "Signature publication period in Seconds.
         Note:This mib is not supported for VX instance of Virtualization."
    ::= { gslbDnsSecImportExport 18 }

gslbDnsSecImportExportAction OBJECT-TYPE
    SYNTAX  INTEGER {
        none(0),
        import(1),
        export(2),
        unsupported(2147483647)
        }
    MAX-ACCESS  read-write
    STATUS  current
    DESCRIPTION
        "Component type to import/export: key or dnskey.
         Note:This mib is not supported for VX instance of Virtualization."
    ::= { gslbDnsSecImportExport 19 }


-- DNS Responder VIP Configuration

gslbCurDnsResVipTable OBJECT-TYPE
    SYNTAX  SEQUENCE OF GslbCurDnsResVipEntry
    MAX-ACCESS  not-accessible
    STATUS  current
    DESCRIPTION
        "Note:This mib is not supported for VX instance of Virtualization."
    ::= { gslbDnsResVipCfg 1 }

gslbCurDnsResVipEntry OBJECT-TYPE
    SYNTAX  GslbCurDnsResVipEntry
    MAX-ACCESS  not-accessible
    STATUS  current
    DESCRIPTION
        "."
    INDEX   { gslbCurDnsResVipIndex1, gslbCurDnsResVipIndex2 }
    ::= { gslbCurDnsResVipTable 1 }

GslbCurDnsResVipEntry ::= SEQUENCE {
    gslbCurDnsResVipIndex1       INTEGER,
    gslbCurDnsResVipIndex2       INTEGER,
    gslbCurDnsResVipName         DisplayString,
    gslbCurDnsResVipIPVer        INTEGER,
    gslbCurDnsResVipV4           IpAddress,
    gslbCurDnsResVipV6           DisplayString,
    gslbCurDnsResVipStatus       INTEGER
    }

gslbCurDnsResVipIndex1 OBJECT-TYPE
    SYNTAX INTEGER (1..1024)
    MAX-ACCESS  read-only
    STATUS  current
    DESCRIPTION
        "DNS Responder VIP Index 1."
    ::= { gslbCurDnsResVipEntry  1 }

gslbCurDnsResVipIndex2 OBJECT-TYPE
    SYNTAX INTEGER (1..1024)
    MAX-ACCESS  read-only
    STATUS  current
    DESCRIPTION
        "DNS Responder VIP Index 2."
    ::= { gslbCurDnsResVipEntry  2 }

gslbCurDnsResVipName OBJECT-TYPE
    SYNTAX   DisplayString (SIZE(0..32))
    MAX-ACCESS  read-only
    STATUS  current
    DESCRIPTION
        "DNS Responder VIP Name."
    ::= { gslbCurDnsResVipEntry  3 }

gslbCurDnsResVipIPVer OBJECT-TYPE
    SYNTAX  INTEGER{
        ipv4(1),
        ipv6(2),
        unsupported(2147483647)
        }
    MAX-ACCESS  read-only
    STATUS  current
    DESCRIPTION
        "The type of IP address of DNS Responder VIP."
    ::= { gslbCurDnsResVipEntry 4 }

gslbCurDnsResVipV4 OBJECT-TYPE
    SYNTAX IpAddress
    MAX-ACCESS  read-only
    STATUS  current
    DESCRIPTION
        "IPV4 address of the DNS Responder VIP."
    ::= { gslbCurDnsResVipEntry 5 }

gslbCurDnsResVipV6 OBJECT-TYPE
   SYNTAX DisplayString (SIZE(0..40))
    MAX-ACCESS  read-only
    STATUS  current
    DESCRIPTION
    "  IPV6 address of the DNS Responder VIP
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurDnsResVipEntry 6 }

gslbCurDnsResVipStatus OBJECT-TYPE
    SYNTAX INTEGER {
        enable(1),
        disable(2),
        unsupported(2147483647)
        }
    MAX-ACCESS  read-only
    STATUS  current
    DESCRIPTION
        "Zone status - Enabled/Disabled."
    ::= { gslbCurDnsResVipEntry 7 }


gslbNewDnsResVipTable OBJECT-TYPE
    SYNTAX  SEQUENCE OF GslbNewDnsResVipEntry
    MAX-ACCESS  not-accessible
    STATUS  current
    DESCRIPTION
        "Note:This mib is not supported for VX instance of Virtualization."
    ::= { gslbDnsResVipCfg 2 }

gslbNewDnsResVipEntry OBJECT-TYPE
    SYNTAX  GslbNewDnsResVipEntry
    MAX-ACCESS  not-accessible
    STATUS  current
    DESCRIPTION
        "."
    INDEX   { gslbNewDnsResVipIndex1, gslbNewDnsResVipIndex2 }
    ::= { gslbNewDnsResVipTable 1 }

GslbNewDnsResVipEntry ::= SEQUENCE {
    gslbNewDnsResVipIndex1       INTEGER,
    gslbNewDnsResVipIndex2       INTEGER,
    gslbNewDnsResVipName         DisplayString,
    gslbNewDnsResVipIPVer        INTEGER,
    gslbNewDnsResVipV4           IpAddress,
    gslbNewDnsResVipV6           DisplayString,
    gslbNewDnsResVipStatus       INTEGER,
    gslbNewDnsResVipDelete       INTEGER
    }

gslbNewDnsResVipIndex1 OBJECT-TYPE
    SYNTAX INTEGER (1..1024)
    MAX-ACCESS  read-create
    STATUS  current
    DESCRIPTION
        "DNS Responder VIP Index 1."
    ::= { gslbNewDnsResVipEntry  1 }

gslbNewDnsResVipIndex2 OBJECT-TYPE
    SYNTAX INTEGER (1..1024)
    MAX-ACCESS  read-create
    STATUS  current
    DESCRIPTION
        "DNS Responder VIP Index 2."
    ::= { gslbNewDnsResVipEntry  2 }

gslbNewDnsResVipName OBJECT-TYPE
    SYNTAX   DisplayString (SIZE(0..25))
    MAX-ACCESS  read-write
    STATUS  current
    DESCRIPTION
        "DNS Responder VIP Name."
    ::= { gslbNewDnsResVipEntry  3 }

gslbNewDnsResVipIPVer OBJECT-TYPE
    SYNTAX  INTEGER{
        ipv4(1),
        ipv6(2),
        unsupported(2147483647)
        }
    MAX-ACCESS  read-write
    STATUS  current
    DESCRIPTION
        "The type of IP address of DNS Responder VIP."
    ::= { gslbNewDnsResVipEntry 4 }

gslbNewDnsResVipV4 OBJECT-TYPE
    SYNTAX IpAddress
    MAX-ACCESS  read-write
    STATUS  current
    DESCRIPTION
        "IPV4 address of the DNS Responder VIP."
    ::= { gslbNewDnsResVipEntry 5 }

gslbNewDnsResVipV6 OBJECT-TYPE
   SYNTAX DisplayString (SIZE(0..40))
    MAX-ACCESS  read-write
    STATUS  current
    DESCRIPTION
    "  IPV6 address of the DNS Responder VIP
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewDnsResVipEntry 6 }

gslbNewDnsResVipStatus OBJECT-TYPE
    SYNTAX INTEGER {
        enable(1),
        disable(2),
        unsupported(2147483647)
        }
    MAX-ACCESS  read-write
    STATUS  current
    DESCRIPTION
        "Zone status - Enabled/Disabled."
    ::= { gslbNewDnsResVipEntry 7 }

gslbNewDnsResVipDelete OBJECT-TYPE
    SYNTAX  INTEGER {
        other(1),
        delete(2),
        unsupported(2147483647)
        }
    MAX-ACCESS  read-write
    STATUS  current
    DESCRIPTION
        "By setting the value to delete(2), the entire row is deleted."
    ::= { gslbNewDnsResVipEntry 8 }


gslbDnsResVipEmptyIndexesTable OBJECT-TYPE
    SYNTAX  SEQUENCE OF GslbDnsResVipEmptyIndexesEntry
    MAX-ACCESS  not-accessible
    STATUS  current
    DESCRIPTION
        "Note:This mib is not supported for VX instance of Virtualization."
    ::= { gslbDnsResVipCfg 3 }

gslbDnsResVipEmptyIndexesEntry OBJECT-TYPE
    SYNTAX  GslbDnsResVipEmptyIndexesEntry
    MAX-ACCESS  not-accessible
    STATUS  current
    DESCRIPTION
        "."
    INDEX   { gslbDnsResVipEmptyIndexesIndex }
    ::= { gslbDnsResVipEmptyIndexesTable 1 }

GslbDnsResVipEmptyIndexesEntry ::= SEQUENCE {
    gslbDnsResVipEmptyIndexesIndex       INTEGER
    }

gslbDnsResVipEmptyIndexesIndex OBJECT-TYPE
    SYNTAX INTEGER (1..1024)
    MAX-ACCESS  read-only
    STATUS  current
    DESCRIPTION
        "DNS Responder VIP Index."
    ::= { gslbDnsResVipEmptyIndexesEntry  1 }

gslbCurEnhDnsResVipTable OBJECT-TYPE
    SYNTAX  SEQUENCE OF GslbCurEnhDnsResVipEntry
    MAX-ACCESS  not-accessible
    STATUS  current
    DESCRIPTION
        "Note:This mib is not supported for VX instance of Virtualization."
    ::= { gslbDnsResVipCfg 4 }

gslbCurEnhDnsResVipEntry OBJECT-TYPE
    SYNTAX  GslbCurEnhDnsResVipEntry
    MAX-ACCESS  not-accessible
    STATUS  current
    DESCRIPTION
        "."
    INDEX   { gslbCurEnhDnsResVipIndex1, gslbCurEnhDnsResVipIndex2 }
    ::= { gslbCurEnhDnsResVipTable 1 }

GslbCurEnhDnsResVipEntry ::= SEQUENCE {
    gslbCurEnhDnsResVipIndex1       DisplayString,
    gslbCurEnhDnsResVipIndex2       DisplayString,
    gslbCurEnhDnsResVipName         DisplayString,
    gslbCurEnhDnsResVipIPVer        INTEGER,
    gslbCurEnhDnsResVipV4           IpAddress,
    gslbCurEnhDnsResVipV6           DisplayString,
    gslbCurEnhDnsResVipStatus       INTEGER,
    gslbCurEnhDnsResVipRtsrcmac     INTEGER
    }

gslbCurEnhDnsResVipIndex1 OBJECT-TYPE
    SYNTAX DisplayString (SIZE(0..255))
    MAX-ACCESS  read-only
    STATUS  current
    DESCRIPTION
        "DNS Responder VIP Index 1."
    ::= { gslbCurEnhDnsResVipEntry  1 }

gslbCurEnhDnsResVipIndex2 OBJECT-TYPE
    SYNTAX DisplayString (SIZE(0..255))
    MAX-ACCESS  read-only
    STATUS  current
    DESCRIPTION
        "DNS Responder VIP Index 2."
    ::= { gslbCurEnhDnsResVipEntry  2 }

gslbCurEnhDnsResVipName OBJECT-TYPE
    SYNTAX   DisplayString (SIZE(0..32))
    MAX-ACCESS  read-only
    STATUS  current
    DESCRIPTION
        "DNS Responder VIP Name."
    ::= { gslbCurEnhDnsResVipEntry  3 }

gslbCurEnhDnsResVipIPVer OBJECT-TYPE
    SYNTAX  INTEGER{
        ipv4(1),
        ipv6(2),
        unsupported(2147483647)
        }
    MAX-ACCESS  read-only
    STATUS  current
    DESCRIPTION
        "The type of IP address of DNS Responder VIP."
    ::= { gslbCurEnhDnsResVipEntry 4 }

gslbCurEnhDnsResVipV4 OBJECT-TYPE
    SYNTAX IpAddress
    MAX-ACCESS  read-only
    STATUS  current
    DESCRIPTION
        "IPV4 address of the DNS Responder VIP."
    ::= { gslbCurEnhDnsResVipEntry 5 }

gslbCurEnhDnsResVipV6 OBJECT-TYPE
   SYNTAX DisplayString (SIZE(0..40))
    MAX-ACCESS  read-only
    STATUS  current
    DESCRIPTION
    "  IPV6 address of the DNS Responder VIP
       Address should be 4-byte hexadecimal colon notation. Valid IPv6 address should be in
       any of the following forms xxxx:xxxx:xxxx:xxxx:xxxx:xxxx:xxxx:xxxx or xxxx::xxxx:xxxx:xxxx:xxxx or ::xxxx "
   ::= { gslbCurEnhDnsResVipEntry 6 }

gslbCurEnhDnsResVipStatus OBJECT-TYPE
    SYNTAX INTEGER {
        enable(1),
        disable(2),
        unsupported(2147483647)
        }
    MAX-ACCESS  read-only
    STATUS  current
    DESCRIPTION
        "Zone status - Enabled/Disabled."
    ::= { gslbCurEnhDnsResVipEntry 7 }
    
gslbCurEnhDnsResVipRtsrcmac OBJECT-TYPE
    SYNTAX INTEGER {
        enable(1),
        disable(2),
        unsupported(2147483647)
        }
    MAX-ACCESS  read-only
    STATUS  current
    DESCRIPTION
        "Enabling/Disabling this will enable/disable rtsrcmac in both virtual servers that comprise this DNS Responder."
    ::= { gslbCurEnhDnsResVipEntry 8 }


gslbNewEnhDnsResVipTable OBJECT-TYPE
    SYNTAX  SEQUENCE OF GslbNewEnhDnsResVipEntry
    MAX-ACCESS  not-accessible
    STATUS  current
    DESCRIPTION
        "Note:This mib is not supported for VX instance of Virtualization."
    ::= { gslbDnsResVipCfg 5 }

gslbNewEnhDnsResVipEntry OBJECT-TYPE
    SYNTAX  GslbNewEnhDnsResVipEntry
    MAX-ACCESS  not-accessible
    STATUS  current
    DESCRIPTION
        "."
    INDEX   { gslbNewEnhDnsResVipIndex1, gslbNewEnhDnsResVipIndex2 }
    ::= { gslbNewEnhDnsResVipTable 1 }

GslbNewEnhDnsResVipEntry ::= SEQUENCE {
    gslbNewEnhDnsResVipIndex1       DisplayString,
    gslbNewEnhDnsResVipIndex2       DisplayString,
    gslbNewEnhDnsResVipName         DisplayString,
    gslbNewEnhDnsResVipIPVer        INTEGER,
    gslbNewEnhDnsResVipV4           IpAddress,
    gslbNewEnhDnsResVipV6           DisplayString,
    gslbNewEnhDnsResVipStatus       INTEGER,
    gslbNewEnhDnsResVipDelete       INTEGER,
    gslbNewEnhDnsResVipRtsrcmac		INTEGER
    }

gslbNewEnhDnsResVipIndex1 OBJECT-TYPE
    SYNTAX DisplayString (SIZE(1..255))
    MAX-ACCESS  read-create
    STATUS  current
    DESCRIPTION
        "DNS Responder VIP Index 1."
    ::= { gslbNewEnhDnsResVipEntry  1 }

gslbNewEnhDnsResVipIndex2 OBJECT-TYPE
    SYNTAX DisplayString (SIZE(1..255))
    MAX-ACCESS  read-create
    STATUS  current
    DESCRIPTION
        "DNS Responder VIP Index 2."
    ::= { gslbNewEnhDnsResVipEntry  2 }

gslbNewEnhDnsResVipName OBJECT-TYPE
    SYNTAX   DisplayString (SIZE(0..32))
    MAX-ACCESS  read-write
    STATUS  current
    DESCRIPTION
        "DNS Responder VIP Name."
    ::= { gslbNewEnhDnsResVipEntry  3 }

gslbNewEnhDnsResVipIPVer OBJECT-TYPE
    SYNTAX  INTEGER{
        ipv4(1),
        ipv6(2),
        unsupported(2147483647)
        }
    MAX-ACCESS  read-write
    STATUS  current
    DESCRIPTION
        "The type of IP address of DNS Responder VIP."
    ::= { gslbNewEnhDnsResVipEntry 4 }

gslbNewEnhDnsResVipV4 OBJECT-TYPE
    SYNTAX IpAddress
    MAX-ACCESS  read-write
    STATUS  current
    DESCRIPTION
        "IPV4 address of the DNS Responder VIP."
    ::= { gslbNewEnhDnsResVipEntry 5 }

gslbNewEnhDnsResVipV6 OBJECT-TYPE
   SYNTAX DisplayString (SIZE(0..40))
    MAX-ACCESS  read-write
    STATUS  current
    DESCRIPTION
    "  IPV6 address of the DNS Responder VIP
       Address should be 4-byte hexadecimal colon notation. Valid IPv6 address should be in
       any of the following forms xxxx:xxxx:xxxx:xxxx:xxxx:xxxx:xxxx:xxxx or xxxx::xxxx:xxxx:xxxx:xxxx or ::xxxx "
   ::= { gslbNewEnhDnsResVipEntry 6 }

gslbNewEnhDnsResVipStatus OBJECT-TYPE
    SYNTAX INTEGER {
        enable(1),
        disable(2),
        unsupported(2147483647)
        }
    MAX-ACCESS  read-write
    STATUS  current
    DESCRIPTION
        "Zone status - Enabled/Disabled."
    ::= { gslbNewEnhDnsResVipEntry 7 }

gslbNewEnhDnsResVipDelete OBJECT-TYPE
    SYNTAX  INTEGER {
        other(1),
        delete(2),
        unsupported(2147483647)
        }
    MAX-ACCESS  read-write
    STATUS  current
    DESCRIPTION
        "By setting the value to delete(2), the entire row is deleted."
    ::= { gslbNewEnhDnsResVipEntry 8 }
    
gslbNewEnhDnsResVipRtsrcmac OBJECT-TYPE
    SYNTAX INTEGER {
        enable(1),
        disable(2),
        unsupported(2147483647)
        }
    MAX-ACCESS  read-write
    STATUS  current
    DESCRIPTION
        "Enabling/Disabling this will enable/disable rtsrcmac in both virtual servers that comprise this DNS Responder."
    ::= { gslbNewEnhDnsResVipEntry 9 }


gslbEnhDnsResVipEmptyIndexesTable OBJECT-TYPE
    SYNTAX  SEQUENCE OF GslbEnhDnsResVipEmptyIndexesEntry
    MAX-ACCESS  not-accessible
    STATUS  current
    DESCRIPTION
        "The table will display first six empty DNS Responders VIP indexes.
         Note:This mib is not supported for VX instance of Virtualization."
    ::= { gslbDnsResVipCfg 6 }

gslbEnhDnsResVipEmptyIndexesEntry OBJECT-TYPE
    SYNTAX  GslbEnhDnsResVipEmptyIndexesEntry
    MAX-ACCESS  not-accessible
    STATUS  current
    DESCRIPTION
        "Note:This mib is not supported for VX instance of Virtualization."
    INDEX   { gslbEnhDnsResVipEmptyIndexesIndex }
    ::= { gslbEnhDnsResVipEmptyIndexesTable 1 }

GslbEnhDnsResVipEmptyIndexesEntry ::= SEQUENCE {
    gslbEnhDnsResVipEmptyIndexesIndex       DisplayString
    }

gslbEnhDnsResVipEmptyIndexesIndex OBJECT-TYPE
    SYNTAX DisplayString (SIZE(0..255))
    MAX-ACCESS  read-only
    STATUS  current
    DESCRIPTION
        "DNS Responder VIP Index."
    ::= { gslbEnhDnsResVipEmptyIndexesEntry  1 }

-- GSLB Proximity Menu

gslbCurCfgLLBProxAging OBJECT-TYPE
   SYNTAX  INTEGER (1..2880)
   MAX-ACCESS  read-only
   STATUS  current
   DESCRIPTION
       "current configured aging in minutes of proximity entries.
        Note:This mib is not supported for VX instance of Virtualization."
   ::= { gslbLLBProximityCfg 1 }    

gslbNewCfgLLBProxAging OBJECT-TYPE
   SYNTAX  INTEGER (1..2880)
   MAX-ACCESS  read-write
   STATUS  current
   DESCRIPTION
       "set aging in minutes of proximity entries.
        Note:This mib is not supported for VX instance of Virtualization."
   ::= { gslbLLBProximityCfg 2 }

gslbCurCfgLLBProxInterval OBJECT-TYPE
   SYNTAX  INTEGER (1..600)
   MAX-ACCESS  read-only
   STATUS  current
   DESCRIPTION
       "current configured interval between proximity check retries.
        Note:This mib is not supported for VX instance of Virtualization."
   ::= { gslbLLBProximityCfg 3 }

gslbNewCfgLLBProxInterval OBJECT-TYPE
   SYNTAX  INTEGER (1..600)
   MAX-ACCESS  read-write
   STATUS  current
   DESCRIPTION
       "set interval between proximity check retries.
        Note:This mib is not supported for VX instance of Virtualization."
   ::= { gslbLLBProximityCfg 4 }

gslbCurCfgLLBProxRetry OBJECT-TYPE
   SYNTAX  INTEGER (1..63)
   MAX-ACCESS  read-only
   STATUS  current
   DESCRIPTION
       "current configured retries for proximity checks.
        Note:This mib is not supported for VX instance of Virtualization."
   ::= { gslbLLBProximityCfg 5 }

gslbNewCfgLLBProxRetry OBJECT-TYPE
   SYNTAX  INTEGER (1..63)
   MAX-ACCESS  read-write
   STATUS  current
   DESCRIPTION
       "set retries for proximity checks.
        Note:This mib is not supported for VX instance of Virtualization."
   ::= { gslbLLBProximityCfg 6 }

gslbCurCfgLLBProxMask OBJECT-TYPE
    SYNTAX  IpAddress
    MAX-ACCESS  read-only
    STATUS  current
    DESCRIPTION
        "IPv4 subnet mask for proximity entries.
         Note:This mib is not supported for VX instance of Virtualization."
    ::= { gslbLLBProximityCfg 7 }

gslbNewCfgLLBProxMask OBJECT-TYPE
    SYNTAX  IpAddress
    MAX-ACCESS  read-write
    STATUS  current
    DESCRIPTION
        "set IPv4 subnet mask for proximity entries.
         Note:This mib is not supported for VX instance of Virtualization."
    ::= { gslbLLBProximityCfg 8 }

gslbCurCfgLLBProxPrfx OBJECT-TYPE
    SYNTAX INTEGER (1..128)
    MAX-ACCESS  read-only
    STATUS  current
    DESCRIPTION
        "IPv6 subnet prefix length for proximity entries.
         Note:This mib is not supported for VX instance of Virtualization."
    ::= { gslbLLBProximityCfg 9 }

gslbNewCfgLLBProxPrfx OBJECT-TYPE
    SYNTAX INTEGER (1..128)
    MAX-ACCESS  read-write
    STATUS  current
    DESCRIPTION
        "set IPv6 subnet prefix length for proximity entries.
         Note:This mib is not supported for VX instance of Virtualization."
    ::= { gslbLLBProximityCfg 10 }

gslbCurCfgLLBProxonOff OBJECT-TYPE
   SYNTAX  INTEGER {
       on(1),
       off(2),
       unsupported(2147483647)
       }
   MAX-ACCESS  read-only
   STATUS  current
   DESCRIPTION
       "Current status of Proximity(ON or OFF).
        Note:This mib is not supported for VX instance of Virtualization."
   ::= { gslbLLBProximityCfg 11 } 

gslbNewCfgLLBProxonOff OBJECT-TYPE
   SYNTAX  INTEGER {
       on(1),
       off(2),
       unsupported(2147483647)
       }
   MAX-ACCESS  read-write
   STATUS  current
   DESCRIPTION
       "turn Proximity processing ON or OFF.
        Note:This mib is not supported for VX instance of Virtualization."
   ::= { gslbLLBProximityCfg 12 }

gslbCurCfgLocalDnsTable OBJECT-TYPE
    SYNTAX  SEQUENCE OF GslbCurCfgLocalDnsEntry
    MAX-ACCESS  not-accessible
    STATUS  current
    DESCRIPTION
        "The table of proximity localdns in the current_config.
         Note:This mib is not supported for VX instance of Virtualization."
    ::= { gslbLLBProximityCfg 13 }

gslbCurCfgLocalDnsEntry OBJECT-TYPE
     SYNTAX  GslbCurCfgLocalDnsEntry
     MAX-ACCESS  not-accessible
     STATUS  current
     DESCRIPTION
         "Information about proximity localdns."
     INDEX { gslbCurCfgLocalDnsIndex }
     ::= { gslbCurCfgLocalDnsTable 1 }

GslbCurCfgLocalDnsEntry ::= SEQUENCE {
    gslbCurCfgLocalDnsIndex   Integer32,
    gslbCurCfgLocalDnsAddr    IpAddress,
    gslbCurCfgLocalDnsv6Addr  DisplayString,
    gslbCurCfgLocalDnsVersion INTEGER
    }

gslbCurCfgLocalDnsIndex OBJECT-TYPE
     SYNTAX Integer32
     MAX-ACCESS read-only
     STATUS current
     DESCRIPTION
         "The index for localdns."
     ::= { gslbCurCfgLocalDnsEntry 1 } 

gslbCurCfgLocalDnsAddr OBJECT-TYPE
    SYNTAX IpAddress
    MAX-ACCESS read-only
    STATUS current
    DESCRIPTION
        "local DNS server IPv4 address."
    ::= { gslbCurCfgLocalDnsEntry 2 }

gslbCurCfgLocalDnsv6Addr OBJECT-TYPE
    SYNTAX DisplayString (SIZE(0..40))
    MAX-ACCESS read-only
    STATUS current
    DESCRIPTION
        "local DNS server IPv6 address.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { gslbCurCfgLocalDnsEntry 3 }

gslbCurCfgLocalDnsVersion OBJECT-TYPE
    SYNTAX  INTEGER {
        unknown(0),
        ipv4(4),
        ipv6(6),
        unsupported(2147483647)
        }
    MAX-ACCESS read-only
    STATUS current
    DESCRIPTION
        "The IP version of the localdns."
    ::= { gslbCurCfgLocalDnsEntry 4 }

-- LP Wizard DNS responders

gslbCurDnsResLPWizardFirstIpVersion OBJECT-TYPE
	SYNTAX  INTEGER{
        ipv4(1),
        ipv6(2),
        unsupported(2147483647)
    }
	MAX-ACCESS read-only
	STATUS current
	DESCRIPTION
		"For the startup LP wizard, holds the IP version of the first DNS responder.
                 Note:This mib is not supported for VX instance of Virtualization."
 	::= { gslbLPWizardDnsRespCfg 1 }

gslbNewDnsResLPWizardFirstIpVersion OBJECT-TYPE
	SYNTAX  INTEGER{
        ipv4(1),
        ipv6(2),
        unsupported(2147483647)
    }
	MAX-ACCESS read-create
	STATUS current
	DESCRIPTION
		"For the startup LP wizard, holds the IP version of the first DNS responder.
                 Note:This mib is not supported for VX instance of Virtualization."
 	::= { gslbLPWizardDnsRespCfg 2 }
 	
gslbCurDnsResLPWizardSecondIpVersion OBJECT-TYPE
	SYNTAX  INTEGER{
        ipv4(1),
        ipv6(2),
        unsupported(2147483647)
    }
	MAX-ACCESS read-only
	STATUS current
	DESCRIPTION
		"For the startup LP wizard, holds the IP version of the second DNS responder.
                 Note:This mib is not supported for VX instance of Virtualization."
 	::= { gslbLPWizardDnsRespCfg 3 }

gslbNewDnsResLPWizardSecondIpVersion OBJECT-TYPE
	SYNTAX  INTEGER{
        ipv4(1),
        ipv6(2),
        unsupported(2147483647)
    }
	MAX-ACCESS read-create
	STATUS current
	DESCRIPTION
		"For the startup LP wizard, holds the IP version of the second DNS responder.
                 Note:This mib is not supported for VX instance of Virtualization."
 	::= { gslbLPWizardDnsRespCfg 4 }
 	
gslbCurDnsResLPWizardThirdIpVersion OBJECT-TYPE
	SYNTAX  INTEGER{
        ipv4(1),
        ipv6(2),
        unsupported(2147483647)
    }
	MAX-ACCESS read-only
	STATUS current
	DESCRIPTION
		"For the startup LP wizard, holds the IP version of the third DNS responder.
                 Note:This mib is not supported for VX instance of Virtualization."
 	::= { gslbLPWizardDnsRespCfg 5 }

gslbNewDnsResLPWizardThirdIpVersion OBJECT-TYPE
	SYNTAX  INTEGER{
        ipv4(1),
        ipv6(2),
        unsupported(2147483647)
    }
	MAX-ACCESS read-create
	STATUS current
	DESCRIPTION
		"For the startup LP wizard, holds the IP version of the third DNS responder.
                 Note:This mib is not supported for VX instance of Virtualization."
 	::= { gslbLPWizardDnsRespCfg 6 }
 	
gslbCurDnsResLPWizardFirstIpv4Addr OBJECT-TYPE
	SYNTAX IpAddress
	MAX-ACCESS read-only
	STATUS current
	DESCRIPTION
		"For the startup LP wizard, holds the IPv4 address of the first DNS responder.
                 Note:This mib is not supported for VX instance of Virtualization."
 	::= { gslbLPWizardDnsRespCfg 7 }
 	
gslbCurDnsResLPWizardFirstIpv6Addr OBJECT-TYPE
	SYNTAX DisplayString (SIZE(0..50))
	MAX-ACCESS read-only
	STATUS current
	DESCRIPTION
		"For the startup LP wizard, holds the IPv6 address of the first DNS responder.
                 Note:This mib is not supported for VX instance of Virtualization."
 	::= { gslbLPWizardDnsRespCfg 8 }

gslbNewDnsResLPWizardFirstIpv4Addr OBJECT-TYPE
	SYNTAX IpAddress
	MAX-ACCESS read-create
	STATUS current
	DESCRIPTION
		"For the startup LP wizard, holds the IPv4 address of the first DNS responder.
                 Note:This mib is not supported for VX instance of Virtualization."
 	::= { gslbLPWizardDnsRespCfg 9 }
 	
gslbNewDnsResLPWizardFirstIpv6Addr OBJECT-TYPE
	SYNTAX DisplayString (SIZE(0..50))
	MAX-ACCESS read-create
	STATUS current
	DESCRIPTION
		"For the startup LP wizard, holds the IPv6 address of the first DNS responder.
                 Note:This mib is not supported for VX instance of Virtualization."
 	::= { gslbLPWizardDnsRespCfg 10 }
 	
gslbCurDnsResLPWizardSecondIpv4Addr OBJECT-TYPE
	SYNTAX IpAddress
	MAX-ACCESS read-only
	STATUS current
	DESCRIPTION
		"For the startup LP wizard, holds the IPv4 address of the second DNS responder.
                 Note:This mib is not supported for VX instance of Virtualization."
 	::= { gslbLPWizardDnsRespCfg 11 }
 	
gslbCurDnsResLPWizardSecondIpv6Addr OBJECT-TYPE
	SYNTAX DisplayString (SIZE(0..50))
	MAX-ACCESS read-only
	STATUS current
	DESCRIPTION
		"For the startup LP wizard, holds the IPv6 address of the second DNS responder.
                 Note:This mib is not supported for VX instance of Virtualization."
 	::= { gslbLPWizardDnsRespCfg 12 }

gslbNewDnsResLPWizardSecondIpv4Addr OBJECT-TYPE
	SYNTAX IpAddress
	MAX-ACCESS read-create
	STATUS current
	DESCRIPTION
		"For the startup LP wizard, holds the IPv4 address of the second DNS responder.
                 Note:This mib is not supported for VX instance of Virtualization."
 	::= { gslbLPWizardDnsRespCfg 13 }
 	
gslbNewDnsResLPWizardSecondIpv6Addr OBJECT-TYPE
	SYNTAX DisplayString (SIZE(0..50))
	MAX-ACCESS read-create
	STATUS current
	DESCRIPTION
		"For the startup LP wizard, holds the IPv6 address of the second DNS responder.
                 Note:This mib is not supported for VX instance of Virtualization."
 	::= { gslbLPWizardDnsRespCfg 14 }
 	
gslbCurDnsResLPWizardThirdIpv4Addr OBJECT-TYPE
	SYNTAX IpAddress
	MAX-ACCESS read-only
	STATUS current
	DESCRIPTION
		"For the startup LP wizard, holds the IPv4 address of the third DNS responder.
                 Note:This mib is not supported for VX instance of Virtualization."
 	::= { gslbLPWizardDnsRespCfg 15 }
 	
gslbCurDnsResLPWizardThirdIpv6Addr OBJECT-TYPE
	SYNTAX DisplayString (SIZE(0..50))
	MAX-ACCESS read-only
	STATUS current
	DESCRIPTION
		"For the startup LP wizard, holds the IPv6 address of the third DNS responder.
                 Note:This mib is not supported for VX instance of Virtualization."
 	::= { gslbLPWizardDnsRespCfg 16 }

gslbNewDnsResLPWizardThirdIpv4Addr OBJECT-TYPE
	SYNTAX IpAddress
	MAX-ACCESS read-create
	STATUS current
	DESCRIPTION
		"For the startup LP wizard, holds the IPv4 address of the third DNS responder.
                 Note:This mib is not supported for VX instance of Virtualization."
 	::= { gslbLPWizardDnsRespCfg 17 }
 	
gslbNewDnsResLPWizardThirdIpv6Addr OBJECT-TYPE
	SYNTAX DisplayString (SIZE(0..50))
	MAX-ACCESS read-create
	STATUS current
	DESCRIPTION
		"For the startup LP wizard, holds the IPv6 address of the third DNS responder.
                 Note:This mib is not supported for VX instance of Virtualization."
 	::= { gslbLPWizardDnsRespCfg 18 }

-- DNS Proxy Menu Start
gslbCurDnsProxyDefaultgroup OBJECT-TYPE
    SYNTAX  DisplayString (SIZE(1..255))
    MAX-ACCESS  read-only
    STATUS  current
    DESCRIPTION
        "The default real server group ID.
         Note:This mib is not supported for VX instance of Virtualization."
    ::= { gslbDnsProxyCfg 1 }

gslbNewDnsProxyDefaultgroup OBJECT-TYPE
    SYNTAX  DisplayString (SIZE(1..255))
    MAX-ACCESS  read-create
    STATUS  current
    DESCRIPTION
        "The default real server group ID.
         Note:This mib is not supported for VX instance of Virtualization."
    ::= { gslbDnsProxyCfg 2 }

gslbCurDnsProxyDomainTable OBJECT-TYPE
    SYNTAX  SEQUENCE OF GslbCurDnsProxyDomainEntry
    MAX-ACCESS  not-accessible
    STATUS  current
    DESCRIPTION
        "The table of domain entries in current config.
         Note:This mib is not supported for VX instance of Virtualization."
    ::= { gslbDnsProxyCfg 3 }

gslbCurDnsProxyDomainEntry OBJECT-TYPE
    SYNTAX  GslbCurDnsProxyDomainEntry
    MAX-ACCESS  not-accessible
    STATUS  current
    DESCRIPTION
        "Information about domain entry."
    INDEX   { gslbCurDnsProxyDomainId }
    ::= { gslbCurDnsProxyDomainTable 1 }

GslbCurDnsProxyDomainEntry ::= SEQUENCE {
    gslbCurDnsProxyDomainId           Integer32,
    gslbCurDnsProxyDomainName         DisplayString,
    gslbCurDnsProxyDomainGroup        DisplayString,
    gslbCurDnsProxyDomainState        INTEGER
    }

gslbCurDnsProxyDomainId OBJECT-TYPE
    SYNTAX Integer32
    MAX-ACCESS read-only
    STATUS current
    DESCRIPTION
        "DNS Proxy table index in the current configuration block."
    ::= { gslbCurDnsProxyDomainEntry 1 }

gslbCurDnsProxyDomainName OBJECT-TYPE
    SYNTAX DisplayString (SIZE(0..254))
    MAX-ACCESS read-only
    STATUS current
    DESCRIPTION
        "DNS Proxy Domain name."
    ::= { gslbCurDnsProxyDomainEntry  2 }

gslbCurDnsProxyDomainGroup OBJECT-TYPE
    SYNTAX   DisplayString (SIZE(1..255))
    MAX-ACCESS  read-only
    STATUS  current
    DESCRIPTION
        "DNS Proxy Domain group."
    ::= { gslbCurDnsProxyDomainEntry  3 }

gslbCurDnsProxyDomainState OBJECT-TYPE
    SYNTAX  INTEGER {
        enabled(1),
        disabled(2),
        unsupported(2147483647)
        }
    MAX-ACCESS  read-only
    STATUS  current
    DESCRIPTION
        "Enable/Disable the proxy entry."
    ::= { gslbCurDnsProxyDomainEntry 4 }

gslbNewDnsProxyDomainTable OBJECT-TYPE
    SYNTAX  SEQUENCE OF GslbNewDnsProxyDomainEntry
    MAX-ACCESS  not-accessible
    STATUS  current
    DESCRIPTION
        "The table of domain entries in new config.
         Note:This mib is not supported for VX instance of Virtualization."
    ::= { gslbDnsProxyCfg 4 }

gslbNewDnsProxyDomainEntry OBJECT-TYPE
    SYNTAX  GslbNewDnsProxyDomainEntry
    MAX-ACCESS  not-accessible
    STATUS  current
    DESCRIPTION
        "Information about domain entry."
    INDEX   { gslbNewDnsProxyDomainId }
    ::= { gslbNewDnsProxyDomainTable 1 }

GslbNewDnsProxyDomainEntry ::= SEQUENCE {
    gslbNewDnsProxyDomainId           Integer32,
    gslbNewDnsProxyDomainName         DisplayString,
    gslbNewDnsProxyDomainGroup        DisplayString,
    gslbNewDnsProxyDomainDelete       INTEGER,
    gslbNewDnsProxyDomainState        INTEGER
    }

gslbNewDnsProxyDomainId OBJECT-TYPE
    SYNTAX Integer32
    MAX-ACCESS read-only
    STATUS current
    DESCRIPTION
        "DNS Proxy table index in the new configuration block."
    ::= { gslbNewDnsProxyDomainEntry 1 }

gslbNewDnsProxyDomainName OBJECT-TYPE
    SYNTAX   DisplayString (SIZE(0..254))
    MAX-ACCESS  read-create
    STATUS  current
    DESCRIPTION
        "DNS Proxy Domain name."
    ::= { gslbNewDnsProxyDomainEntry 2 }

gslbNewDnsProxyDomainGroup OBJECT-TYPE
    SYNTAX   DisplayString (SIZE(1..255))
    MAX-ACCESS  read-create
    STATUS  current
    DESCRIPTION
        "DNS Proxy Domain group."
    ::= { gslbNewDnsProxyDomainEntry 3 }

gslbNewDnsProxyDomainDelete OBJECT-TYPE
    SYNTAX INTEGER {
        other(1),
        delete(2),
        unsupported(2147483647)
        }
    MAX-ACCESS read-create
    STATUS current
    DESCRIPTION
        "By setting the value to delete(2), the domain entry is deleted."
    ::= { gslbNewDnsProxyDomainEntry 4 }

gslbNewDnsProxyDomainState OBJECT-TYPE
    SYNTAX  INTEGER {
        enabled(1),
        disabled(2),
        unsupported(2147483647)
        }
    MAX-ACCESS  read-create
    STATUS  current
    DESCRIPTION
        "Enable/Disable the proxy entry."
    ::= { gslbNewDnsProxyDomainEntry 5 }

-- DNS Proxy Menu End

-- DNS SOA Start
gslbCurDnsSoaDefaultRefresh OBJECT-TYPE
    SYNTAX  Counter32
    MAX-ACCESS  read-only
    STATUS  current
    DESCRIPTION
        "DNS SOA default refresh (common for all zones).
         Note:This mib is not supported for VX instance of Virtualization."
    ::= { gslbDnsSoaCfg 1 }

gslbCurDnsSoaDefaultRetry OBJECT-TYPE
    SYNTAX  Counter32
    MAX-ACCESS  read-only
    STATUS  current
    DESCRIPTION
        "DNS SOA default retry (common for all zones).
         Note:This mib is not supported for VX instance of Virtualization."
    ::= { gslbDnsSoaCfg 2 }

gslbCurDnsSoaDefaultExpire OBJECT-TYPE
    SYNTAX  Counter32
    MAX-ACCESS  read-only
    STATUS  current
    DESCRIPTION
        "DNS SOA default expire (common for all zones).
         Note:This mib is not supported for VX instance of Virtualization."
    ::= { gslbDnsSoaCfg 3 }

gslbCurDnsSoaDefaultMinTtl OBJECT-TYPE
    SYNTAX  Counter32
    MAX-ACCESS  read-only
    STATUS  current
    DESCRIPTION
        "DNS SOA default min-ttl (common for all zones).
         Note:This mib is not supported for VX instance of Virtualization."
    ::= { gslbDnsSoaCfg 4 }

gslbCurDnsSoaZoneTableMaxEntries OBJECT-TYPE
    SYNTAX  Counter32
    MAX-ACCESS  read-only
    STATUS  current
    DESCRIPTION
        "DNS SOA zone table maximum zone entries.
         Note:This mib is not supported for VX instance of Virtualization."
    ::= { gslbDnsSoaCfg 5 }

gslbCurDnsSoaZoneTable OBJECT-TYPE
    SYNTAX  SEQUENCE OF GslbCurDnsSoaZoneEntry
    MAX-ACCESS  not-accessible
    STATUS  current
    DESCRIPTION
        "DNS SOA current config zone table.
         Note:This mib is not supported for VX instance of Virtualization."
    ::= { gslbDnsSoaCfg 6 }

gslbCurDnsSoaZoneEntry OBJECT-TYPE
    SYNTAX  GslbCurDnsSoaZoneEntry
    MAX-ACCESS  not-accessible
    STATUS  current
    DESCRIPTION
        "DNS SOA current config zone table entry."
    INDEX   { gslbCurDnsSoaZoneId }
    ::= { gslbCurDnsSoaZoneTable 1 }

GslbCurDnsSoaZoneEntry ::= SEQUENCE {
    gslbCurDnsSoaZoneId           DisplayString,
    gslbCurDnsSoaZoneName         DisplayString,
    gslbCurDnsSoaZoneNameServ     DisplayString,
    gslbCurDnsSoaZoneRespMail     DisplayString,
    gslbCurDnsSoaZoneSerial       Counter32
    }

gslbCurDnsSoaZoneId OBJECT-TYPE
    SYNTAX  DisplayString (SIZE(1..32))
    MAX-ACCESS read-only
    STATUS current
    DESCRIPTION
        "DNS SOA current config zone entry alphanumeric index."
    ::= { gslbCurDnsSoaZoneEntry 1 }

gslbCurDnsSoaZoneName OBJECT-TYPE
    SYNTAX DisplayString (SIZE(1..255))
    MAX-ACCESS read-only
    STATUS current
    DESCRIPTION
        "DNS SOA current config zone entry zone name to match."
    ::= { gslbCurDnsSoaZoneEntry  2 }

gslbCurDnsSoaZoneNameServ OBJECT-TYPE
    SYNTAX   DisplayString (SIZE(1..255))
    MAX-ACCESS  read-only
    STATUS  current
    DESCRIPTION
        "DNS SOA current config zone entry primary nameserver for the zone."
    ::= { gslbCurDnsSoaZoneEntry  3 }

gslbCurDnsSoaZoneRespMail OBJECT-TYPE
    SYNTAX   DisplayString (SIZE(1..255))
    MAX-ACCESS  read-only
    STATUS  current
    DESCRIPTION
        "DNS SOA current config zone entry primary resposible mail for the zone."
    ::= { gslbCurDnsSoaZoneEntry  4 }

gslbCurDnsSoaZoneSerial OBJECT-TYPE
    SYNTAX  Counter32
    MAX-ACCESS  read-only
    STATUS  current
    DESCRIPTION
        "DNS SOA current config zone entry generated serial for any change in the zone."
    ::= { gslbCurDnsSoaZoneEntry 5 }

gslbNewDnsSoaZoneTable OBJECT-TYPE
    SYNTAX  SEQUENCE OF GslbNewDnsSoaZoneEntry
    MAX-ACCESS  not-accessible
    STATUS  current
    DESCRIPTION
        "DNS SOA new config zone table.
         Note:This mib is not supported for VX instance of Virtualization."
    ::= { gslbDnsSoaCfg 7 }

gslbNewDnsSoaZoneEntry OBJECT-TYPE
    SYNTAX  GslbNewDnsSoaZoneEntry
    MAX-ACCESS  not-accessible
    STATUS  current
    DESCRIPTION
        "DNS SOA new config zone table entry."
    INDEX   { gslbNewDnsSoaZoneId }
    ::= { gslbNewDnsSoaZoneTable 1 }

GslbNewDnsSoaZoneEntry ::= SEQUENCE {
    gslbNewDnsSoaZoneId           DisplayString,
    gslbNewDnsSoaZoneName         DisplayString,
    gslbNewDnsSoaZoneNameServ     DisplayString,
    gslbNewDnsSoaZoneRespMail     DisplayString,
    gslbNewDnsSoaZoneSerial       Counter32,
    gslbNewDnsSoaZoneDelete       INTEGER
    }

gslbNewDnsSoaZoneId OBJECT-TYPE
    SYNTAX  DisplayString (SIZE(1..32))
    MAX-ACCESS read-create
    STATUS current
    DESCRIPTION
        "DNS SOA new config zone entry alphanumeric index."
    ::= { gslbNewDnsSoaZoneEntry 1 }

gslbNewDnsSoaZoneName OBJECT-TYPE
    SYNTAX  DisplayString (SIZE(1..255))
    MAX-ACCESS  read-create
    STATUS  current
    DESCRIPTION
        "DNS SOA new config zone entry zone name to match."
    ::= { gslbNewDnsSoaZoneEntry 2 }

gslbNewDnsSoaZoneNameServ OBJECT-TYPE
    SYNTAX   DisplayString (SIZE(1..255))
    MAX-ACCESS  read-create
    STATUS  current
    DESCRIPTION
        "DNS SOA new config zone entry primary nameserver for the zone."
    ::= { gslbNewDnsSoaZoneEntry 3 }

gslbNewDnsSoaZoneRespMail OBJECT-TYPE
    SYNTAX   DisplayString (SIZE(1..255))
    MAX-ACCESS  read-create
    STATUS  current
    DESCRIPTION
        "DNS SOA new config zone entry primary responsible mail for the zone."
    ::= { gslbNewDnsSoaZoneEntry 4 }

gslbNewDnsSoaZoneSerial OBJECT-TYPE
    SYNTAX   Counter32
    MAX-ACCESS  read-only
    STATUS  current
    DESCRIPTION
        "DNS SOA new config zone entry generated serial, read-only."
    ::= { gslbNewDnsSoaZoneEntry 5 }

gslbNewDnsSoaZoneDelete OBJECT-TYPE
    SYNTAX INTEGER {
        other(1),
        delete(2),
        unsupported(2147483647)
        }
    MAX-ACCESS read-create
    STATUS current
    DESCRIPTION
        "DNS SOA new config zone entry delete operation by setting (2), (1) is ignored"
    ::= { gslbNewDnsSoaZoneEntry 6 }

-- DNS SOA End

-- DNS CAA Start
gslbCurDnsCaaRecordTable OBJECT-TYPE
    SYNTAX  SEQUENCE OF GslbCurDnsCaaRecordEntry
    MAX-ACCESS  not-accessible
    STATUS  current
    DESCRIPTION
        "DNS CAA config Record table.
         Note:This mib is not supported for VX instance of Virtualization."
    ::= { gslbDnsCaaCfg 1 }

gslbCurDnsCaaRecordEntry OBJECT-TYPE
    SYNTAX  GslbCurDnsCaaRecordEntry
    MAX-ACCESS  not-accessible
    STATUS  current
    DESCRIPTION
        "DNS CAA config Record table entry."
    INDEX   { gslbCurDnsCaaRecordId }
    ::= { gslbCurDnsCaaRecordTable 1 }

GslbCurDnsCaaRecordEntry ::= SEQUENCE {
    gslbCurDnsCaaRecordId           DisplayString,
    gslbCurDnsCaaRecordDomainName   DisplayString,
    gslbCurDnsCaaRecordType         INTEGER,
    gslbCurDnsCaaRecordValue        DisplayString,
    gslbCurDnsCaaRecordTtl          INTEGER
    }

gslbCurDnsCaaRecordId OBJECT-TYPE
    SYNTAX  DisplayString (SIZE(1..127))
    MAX-ACCESS read-only
    STATUS current
    DESCRIPTION
        "DNS CAA config Record entry alphanumeric index."
    ::= { gslbCurDnsCaaRecordEntry 1 }

gslbCurDnsCaaRecordDomainName OBJECT-TYPE
    SYNTAX DisplayString (SIZE(1..255))
    MAX-ACCESS read-only
    STATUS current
    DESCRIPTION
        "DNS CAA config Record entry domain name."
    ::= { gslbCurDnsCaaRecordEntry  2 }

gslbCurDnsCaaRecordType OBJECT-TYPE
    SYNTAX   INTEGER {
        issue(0),
        issuewild(1),
        iodef(2),
        unsupported(2147483647)
    }
    MAX-ACCESS  read-only
    STATUS  current
    DESCRIPTION
        "DNS CAA config Record entry Record Type."
    ::= { gslbCurDnsCaaRecordEntry  3 }

gslbCurDnsCaaRecordValue OBJECT-TYPE
    SYNTAX   DisplayString (SIZE(1..255))
    MAX-ACCESS  read-only
    STATUS  current
    DESCRIPTION
        "DNS CAA config Record value."
    ::= { gslbCurDnsCaaRecordEntry  4 }

gslbCurDnsCaaRecordTtl OBJECT-TYPE
    SYNTAX  INTEGER (1..86400)
    MAX-ACCESS  read-only
    STATUS  current
    DESCRIPTION
        "DNS CAA config Record TTL."
    ::= { gslbCurDnsCaaRecordEntry 5 }

gslbNewDnsCaaRecordTable OBJECT-TYPE
    SYNTAX  SEQUENCE OF GslbNewDnsCaaRecordEntry
    MAX-ACCESS  not-accessible
    STATUS  current
    DESCRIPTION
        "DNS CAA config record table.
         Note:This mib is not supported for VX instance of Virtualization."
    ::= { gslbDnsCaaCfg 2 }

gslbNewDnsCaaRecordEntry OBJECT-TYPE
    SYNTAX  GslbNewDnsCaaRecordEntry
    MAX-ACCESS  not-accessible
    STATUS  current
    DESCRIPTION
        "DNS CAA config record table entry."
    INDEX   { gslbNewDnsCaaRecordId }
    ::= { gslbNewDnsCaaRecordTable 1 }

GslbNewDnsCaaRecordEntry ::= SEQUENCE {
    gslbNewDnsCaaRecordId           DisplayString,
    gslbNewDnsCaaRecordDomainName   DisplayString,
    gslbNewDnsCaaRecordType         INTEGER,
    gslbNewDnsCaaRecordValue        DisplayString,
    gslbNewDnsCaaRecordTtl          INTEGER,
    gslbNewDnsCaaRecordDelete       INTEGER
    }

gslbNewDnsCaaRecordId OBJECT-TYPE
    SYNTAX  DisplayString (SIZE(1..127))
    MAX-ACCESS read-create
    STATUS current
    DESCRIPTION
        "DNS CAA config record entry, alphanumeric index."
    ::= { gslbNewDnsCaaRecordEntry 1 }

gslbNewDnsCaaRecordDomainName OBJECT-TYPE
    SYNTAX  DisplayString (SIZE(1..255))
    MAX-ACCESS  read-create
    STATUS  current
    DESCRIPTION
        "DNS CAA config record entry, domain name to match."
    ::= { gslbNewDnsCaaRecordEntry 2 }

gslbNewDnsCaaRecordType OBJECT-TYPE
    SYNTAX   INTEGER {
        issue(0),
        issuewild(1),
        iodef(2),
        unsupported(2147483647)
    }
    MAX-ACCESS  read-create
    STATUS  current
    DESCRIPTION
        "DNS CAA config record entry, record type."
    ::= { gslbNewDnsCaaRecordEntry 3 }

gslbNewDnsCaaRecordValue OBJECT-TYPE
    SYNTAX   DisplayString (SIZE(1..255))
    MAX-ACCESS  read-create
    STATUS  current
    DESCRIPTION
        "DNS CAA config record entry, record value."
    ::= { gslbNewDnsCaaRecordEntry 4 }

gslbNewDnsCaaRecordTtl OBJECT-TYPE
    SYNTAX   INTEGER (1..86400)
    MAX-ACCESS  read-create
    STATUS  current
    DESCRIPTION
        "DNS CAA config record entry, record ttl."
    ::= { gslbNewDnsCaaRecordEntry 5 }

gslbNewDnsCaaRecordDelete OBJECT-TYPE
    SYNTAX INTEGER {
        other(1),
        delete(2),
        unsupported(2147483647)
        }
    MAX-ACCESS read-create
    STATUS current
    DESCRIPTION
        "DNS CAA config record entry delete operation by setting (2), (1) is ignored"
    ::= { gslbNewDnsCaaRecordEntry 6 }

-- DNS CAA End

gslbNewCfgLocalDnsTable OBJECT-TYPE
     SYNTAX SEQUENCE OF GslbNewCfgLocalDnsEntry
     MAX-ACCESS not-accessible
     STATUS current
     DESCRIPTION
         "Gslb LLB Proxmity Local Dns table,
          Note:This mib is not supported for VX instance of Virtualization."
     ::= { gslbLLBProximityCfg 14 }

gslbNewCfgLocalDnsEntry OBJECT-TYPE
     SYNTAX GslbNewCfgLocalDnsEntry
     MAX-ACCESS not-accessible
     STATUS current
     DESCRIPTION
         "Information about proximity local dns configuration."
     INDEX { gslbNewCfgLocalDnsIndex }
     ::= { gslbNewCfgLocalDnsTable 1 }

GslbNewCfgLocalDnsEntry ::= SEQUENCE {
     gslbNewCfgLocalDnsIndex      Integer32,
     gslbNewCfgLocalDnsAddr       IpAddress,
     gslbNewCfgLocalDnsv6Addr     DisplayString,
     gslbNewCfgLocalDnsDelete     INTEGER,
     gslbNewCfgLocalDnsVersion    INTEGER
     }

gslbNewCfgLocalDnsIndex OBJECT-TYPE
     SYNTAX Integer32
     MAX-ACCESS read-only
     STATUS current
     DESCRIPTION
         "The index for local dns."
     ::= { gslbNewCfgLocalDnsEntry 1 } 

gslbNewCfgLocalDnsAddr OBJECT-TYPE
     SYNTAX IpAddress    
    MAX-ACCESS read-create
    STATUS current
    DESCRIPTION
        "local DNS server IPv4 address ."
    ::= { gslbNewCfgLocalDnsEntry 2 } 

gslbNewCfgLocalDnsv6Addr OBJECT-TYPE
    SYNTAX DisplayString (SIZE(0..40))
    MAX-ACCESS read-create
    STATUS current
    DESCRIPTION
        "local DNS server IPv6 address.
         Address should be 16-byte hexadecimal colon notation.
         Valid IPv6 address should be in any of the following forms
         xxxx:xxxx:xxxx:xxxx:xxxx:xxxx:xxxx:xxxx or
         xxxx::xxxx:xxxx:xxxx:xxxx or ::xxxx
         Only new entry can be created,cannot modify existing ip."
    ::= { gslbNewCfgLocalDnsEntry 3 }    

gslbNewCfgLocalDnsDelete OBJECT-TYPE
    SYNTAX INTEGER {
        other(1),
        delete(2),
        unsupported(2147483647)
        }
    MAX-ACCESS  read-create
    STATUS  current
    DESCRIPTION
        "By setting the value to delete(2), the entire row is
         deleted."
    ::= { gslbNewCfgLocalDnsEntry 4 }

gslbNewCfgLocalDnsVersion OBJECT-TYPE
    SYNTAX  INTEGER {
        unknown(0),
        ipv4(4),
        ipv6(6),
        unsupported(2147483647)
        }
    MAX-ACCESS read-only
    STATUS current
    DESCRIPTION
        "The IP version of the local dns server."
    ::= { gslbNewCfgLocalDnsEntry 5 }

-- END GSLB PROXIMITY

-- Health Script Configuration
 
hcsTableMaxSize OBJECT-TYPE
    SYNTAX  Integer32
    MAX-ACCESS  read-only
    STATUS  current
    DESCRIPTION
        "The maximum number of scriptable health check entries.
         Note:This mib is not supported for VX instance of Virtualization."
    ::= { hcsCfg 1 }

hcsCurCfgTable OBJECT-TYPE
    SYNTAX  SEQUENCE OF HcsCurCfgTableEntry
    MAX-ACCESS  not-accessible
    STATUS  current
    DESCRIPTION
        "The scriptable health check table in the current configuration block.
         Note:This mib is not supported for VX instance of Virtualization."
    ::= { hcsCfg 2 }

hcsCurCfgTableEntry OBJECT-TYPE
    SYNTAX  HcsCurCfgTableEntry
    MAX-ACCESS  not-accessible
    STATUS  current
    DESCRIPTION
        "A row in the scriptable health check table."
    INDEX   { hcsCurCfgScriptIndex }
    ::= { hcsCurCfgTable 1 }

HcsCurCfgTableEntry ::= SEQUENCE {
    hcsCurCfgScriptIndex     Integer32,
    hcsCurCfgScriptString    OCTET STRING
    }

hcsCurCfgScriptIndex OBJECT-TYPE
    SYNTAX Integer32
    MAX-ACCESS read-only
    STATUS current
    DESCRIPTION
        "The index in the scriptable health check table."
    ::= { hcsCurCfgTableEntry 1 }

hcsCurCfgScriptString OBJECT-TYPE
    SYNTAX OCTET STRING 
    MAX-ACCESS read-only
    STATUS current
    DESCRIPTION
        "The scriptable health check string."
    ::= { hcsCurCfgTableEntry 2 }

hcsNewCfgTable OBJECT-TYPE
    SYNTAX  SEQUENCE OF HcsNewCfgTableEntry
    MAX-ACCESS  not-accessible
    STATUS  current
    DESCRIPTION
        "The scriptable health check table in the new configuration block.
         Note:This mib is not supported for VX instance of Virtualization."
    ::= { hcsCfg 3 }

hcsNewCfgTableEntry OBJECT-TYPE
    SYNTAX  HcsNewCfgTableEntry
    MAX-ACCESS  not-accessible
    STATUS  current
    DESCRIPTION
        "A row in the scriptable health check table."
    INDEX   { hcsNewCfgScriptIndex }
    ::= { hcsNewCfgTable 1 }

HcsNewCfgTableEntry ::= SEQUENCE {
    hcsNewCfgScriptIndex       Integer32,
    hcsNewCfgScriptString      OCTET STRING,
    hcsNewCfgAddSendCmd        DisplayString,     -- obsolete
    hcsNewCfgAddExpectCmd      DisplayString,     -- obsolete
    hcsNewCfgAddCloseCmd       INTEGER,
    hcsNewCfgRemLastCmd        INTEGER,
    hcsNewCfgAddWaitCmd        INTEGER,
    hcsNewCfgAddOffsetCmd      INTEGER,
    hcsNewCfgAddOpenProtCmd    DisplayString,
    hcsNewCfgAddDepthCmd       INTEGER,
    hcsNewCfgAddLongNsendCmd   OCTET STRING,
    hcsNewCfgAddLongNexpectCmd OCTET STRING,
    hcsNewCfgAddNsendCmd       DisplayString,     -- obsolete
    hcsNewCfgAddNexpectCmd     DisplayString,     -- obsolete
    hcsNewCfgAddLongBsendCmd   OCTET STRING,
    hcsNewCfgAddLongBexpectCmd OCTET STRING,
    hcsNewCfgAddLongSendCmd    OCTET STRING,
    hcsNewCfgAddLongExpectCmd  OCTET STRING,
    hcsNewCfgDeleteScript      INTEGER
    }

hcsNewCfgScriptIndex OBJECT-TYPE
    SYNTAX Integer32
    MAX-ACCESS read-only
    STATUS current
    DESCRIPTION
        "The index the scriptable health check."
    ::= { hcsNewCfgTableEntry 1 }

hcsNewCfgScriptString OBJECT-TYPE
    SYNTAX OCTET STRING
    MAX-ACCESS read-only
    STATUS current
    DESCRIPTION
        "The scriptable health check string."
    ::= { hcsNewCfgTableEntry 2 }


hcsNewCfgAddSendCmd OBJECT-TYPE
    SYNTAX DisplayString (SIZE(0..255))
    MAX-ACCESS read-create
    STATUS obsolete
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 4 }

hcsNewCfgAddExpectCmd OBJECT-TYPE
    SYNTAX DisplayString (SIZE(0..255))
    MAX-ACCESS read-create
    STATUS obsolete
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 5 }

hcsNewCfgAddCloseCmd OBJECT-TYPE
    SYNTAX INTEGER {
        other(1),
        close(2),
        unsupported(2147483647)
        }
    MAX-ACCESS read-create
    STATUS current
    DESCRIPTION
        "Add close command to end of the script. When set to the value of 2
         (add), 'close' will be appended to the script. Also, a 
         'null terminator'(\0) will be automatically appended. The null 
         terminator and the 'close' characters will be counted as characters 
         in the script.  This command is only valid for TCP."
    ::= { hcsNewCfgTableEntry 6 }

hcsNewCfgRemLastCmd OBJECT-TYPE
    SYNTAX INTEGER {
        other(1),
        remove(2),
        unsupported(2147483647)
        }
    MAX-ACCESS read-create
    STATUS current
    DESCRIPTION
        "Remove the last command from the script. When set to the value of 2
         (remove), last command will be removed from the script. When read,
         other(1) is returned."
    ::= { hcsNewCfgTableEntry 7 }

hcsNewCfgDeleteScript OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row."
    ::= { hcsNewCfgTableEntry 8 }

hcsNewCfgAddOffsetCmd OBJECT-TYPE
    SYNTAX INTEGER (1..1464)
    MAX-ACCESS read-create
    STATUS current
    DESCRIPTION
        "Append an 'offset' command to the script. The set value of this
	 object should be the offset from the beginning of the data area
	 of the TCP/UDP packet to start matching the string configured
	 in the last bexpect command. The 'offset ' characters will be
         automatically appended. Also a 'null terminator'(\0) will be 
         automatically appended. The null terminator and the 'offset '
         characters will be counted as characters in the script.  When 
	 read, the return value has no significant meaning, but a 1 is
	 always returned."
    ::= { hcsNewCfgTableEntry 9 }

hcsNewCfgAddWaitCmd OBJECT-TYPE
    SYNTAX INTEGER (1..65535)
    MAX-ACCESS read-create
    STATUS current
    DESCRIPTION
        "Append a 'wait' command to the script. The set value of this
	 object should be the maximum waiting time for the packet
	 containing the content configured in the last expect command.
	 Wait time is in units of milliseconds, and the maximum
	 supported is 65535 ms.  The 'wait ' characters will be 
	 automatically appended. Also a 'null terminator'(\0) will be
         automatically appended. The null terminator and the 'wait ' 
         characters will be counted as characters in the script. When 
	 read, the return value has no significant meaning, but a 1 is
	 always returned. "
    ::= { hcsNewCfgTableEntry 10 }

hcsNewCfgAddOpenProtCmd OBJECT-TYPE
    SYNTAX DisplayString (SIZE(0..31))
    MAX-ACCESS read-create
    STATUS current
    DESCRIPTION
        "Append an 'open' command to the script. The value of this object
         should be real server port number or name, followed by a comma,
	 and then the protocol (either tcp or udp), e.g. '80,tcp'.  Only
	 the port number or name, and tcp or udp should be set. The 'open ' 
	 characters will be automatically appended. Also a 'null terminator'
         (\0) will be automatically appended. The null terminator and the
         'open ' characters will be counted as characters in the script."
    ::= { hcsNewCfgTableEntry 11 }

hcsNewCfgAddNsendCmd OBJECT-TYPE
    SYNTAX DisplayString (SIZE(0..255))
    MAX-ACCESS read-create
    STATUS obsolete
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 12 }

hcsNewCfgAddNexpectCmd OBJECT-TYPE
    SYNTAX DisplayString (SIZE(0..255))
    MAX-ACCESS read-create
    STATUS obsolete
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 13 }

hcsNewCfgAddDepthCmd OBJECT-TYPE
    SYNTAX INTEGER (1..1464)
    MAX-ACCESS read-create
    STATUS current
    DESCRIPTION
        "Append a 'depth' command to the script. The set value of this
	 object should be the depth (search window) within the data
	 area of the TCP/UDP packet for matching the string configured
	 in the last bexpect command. The 'depth ' characters will be
         automatically appended. Also a 'null terminator'(\0) will be 
         automatically appended. The null terminator and the 'depth '
         characters will be counted as characters in the script. When 
	 read, the return value has no significant meaning, but a 1 is
	 always returned."
    ::= { hcsNewCfgTableEntry 14 }

hcsNewCfgAddLongBsendCmd OBJECT-TYPE
    SYNTAX OCTET STRING (SIZE(0..506))
    MAX-ACCESS read-create
    STATUS current
    DESCRIPTION
        "Append a 'bsend' command to the script. The set value of this
	 object should be the exact binary data in hex format to be sent 
         on the port opened with the 'open' command. The 'bsend ' characters 
         will be automatically appended. Also a 'null terminator' (\0)
	 will be automatically appended. The null terminator and the 'bsend '
	 characters will be counted as characters in the script."
    ::= { hcsNewCfgTableEntry 15 }

hcsNewCfgAddLongBexpectCmd OBJECT-TYPE
    SYNTAX OCTET STRING (SIZE(0..504))
    MAX-ACCESS read-create
    STATUS current
    DESCRIPTION
        "Append a 'bexpect' command to the script. The set value of this 
	 object should be the exact binary data in hex format expected to
	 be received on the port opened with the 'open' command. The value 
         could also be a single wildcard character '*' which means any 
         received content will be accepted.  The 'bexpect ' characters 
	 will be automatically appended.  Also a 'null terminator'(\0)
	 will be automatically appended.  The null terminator and the 
	 'bexpect ' characters will be counted as characters in the script."
    ::= { hcsNewCfgTableEntry 16 }

hcsNewCfgAddLongSendCmd OBJECT-TYPE
    SYNTAX OCTET STRING (SIZE(0..507))
    MAX-ACCESS read-create
    STATUS current
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 17 }

hcsNewCfgAddLongExpectCmd OBJECT-TYPE
    SYNTAX OCTET STRING (SIZE(0..505))
    MAX-ACCESS read-create
    STATUS current
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 18 }

hcsNewCfgAddLongNsendCmd OBJECT-TYPE
    SYNTAX OCTET STRING (SIZE(0..506))
    MAX-ACCESS read-create
    STATUS current
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 19 }

hcsNewCfgAddLongNexpectCmd OBJECT-TYPE
    SYNTAX OCTET STRING (SIZE(0..504))
    MAX-ACCESS read-create
    STATUS current
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 20 }

-- SNMP health check configuration 
 
snmphcTableMaxSize OBJECT-TYPE
    SYNTAX  Integer32
    MAX-ACCESS  read-only
    STATUS  current
    DESCRIPTION
        "The maximum number of SNMP health check entries.
         Note:This mib is not supported for VX instance of Virtualization."
    ::= { snmphcCfg 1 }

snmphcCurCfgTable OBJECT-TYPE
    SYNTAX  SEQUENCE OF SnmphcCurCfgTableEntry
    MAX-ACCESS  not-accessible
    STATUS  current
    DESCRIPTION
        "The SNMP health check table in the current configuration block.
         Note:This mib is not supported for VX instance of Virtualization."
    ::= { snmphcCfg 2 }

snmphcCurCfgTableEntry OBJECT-TYPE
    SYNTAX  SnmphcCurCfgTableEntry
    MAX-ACCESS  not-accessible
    STATUS  current
    DESCRIPTION
        "A row in the SNMP health check table."
    INDEX   { snmphcCurCfgIndex }
    ::= { snmphcCurCfgTable 1 }

SnmphcCurCfgTableEntry ::= SEQUENCE {
    snmphcCurCfgIndex          Integer32,
    snmphcCurCfgOid            DisplayString,
    snmphcCurCfgCommString     DisplayString,
    snmphcCurCfgRcvContent     DisplayString,
    snmphcCurCfgInvert         INTEGER,
    snmphcCurCfgUseWeight      INTEGER
    }

snmphcCurCfgIndex OBJECT-TYPE
    SYNTAX Integer32
    MAX-ACCESS read-only
    STATUS current
    DESCRIPTION
        "The index of the SNMP health check."
    ::= { snmphcCurCfgTableEntry 1 }

snmphcCurCfgOid OBJECT-TYPE
    SYNTAX DisplayString (SIZE(0..128))
    MAX-ACCESS read-only
    STATUS current
    DESCRIPTION
        "The OID to be sent in the SNMP get request packet."
    ::= { snmphcCurCfgTableEntry 2 }

snmphcCurCfgCommString OBJECT-TYPE
    SYNTAX DisplayString (SIZE(0..32))
    MAX-ACCESS read-only
    STATUS current
    DESCRIPTION
        "The community string to be used in the SNMP get request packet."
    ::= { snmphcCurCfgTableEntry 3 }

snmphcCurCfgRcvContent OBJECT-TYPE
    SYNTAX DisplayString (SIZE(0..64))
    MAX-ACCESS read-only
    STATUS current
    DESCRIPTION
        "The content expected in the SNMP response packet. The content  
        specified can be either a string or an integer value."
    ::= { snmphcCurCfgTableEntry 4 }

snmphcCurCfgInvert OBJECT-TYPE
    SYNTAX INTEGER {
        enabled(1),
        disabled(2),
        unsupported(2147483647)
        }
    MAX-ACCESS read-only
    STATUS current
    DESCRIPTION
        "When the invert option is enabled the health check will fail if
         the response packet contains the value specified in the 
         receive content field."
    ::= { snmphcCurCfgTableEntry 5 }

snmphcCurCfgUseWeight OBJECT-TYPE
    SYNTAX INTEGER {
        enabled(1),
        disabled(2),
        unsupported(2147483647)
        }
    MAX-ACCESS read-only
    STATUS current
    DESCRIPTION
        "When the weight option is enabled the real server weights are 
         adjusted dynamically based on the SNMP health check response."
    ::= { snmphcCurCfgTableEntry 6 }

snmphcNewCfgTable OBJECT-TYPE
    SYNTAX  SEQUENCE OF SnmphcNewCfgTableEntry
    MAX-ACCESS  not-accessible
    STATUS  current
    DESCRIPTION
        "The SNMP health check table in the new configuration block.
         Note:This mib is not supported for VX instance of Virtualization."
    ::= { snmphcCfg 3 }

snmphcNewCfgTableEntry OBJECT-TYPE
    SYNTAX  SnmphcNewCfgTableEntry
    MAX-ACCESS  not-accessible
    STATUS  current
    DESCRIPTION
        "A row in the SNMP health check table."
    INDEX   { snmphcNewCfgIndex }
    ::= { snmphcNewCfgTable 1 }

SnmphcNewCfgTableEntry ::= SEQUENCE {
    snmphcNewCfgIndex          Integer32,
    snmphcNewCfgOid            DisplayString,
    snmphcNewCfgCommString     DisplayString,
    snmphcNewCfgRcvContent     DisplayString,
    snmphcNewCfgInvert         INTEGER,
    snmphcNewCfgDeleteHc       INTEGER,
    snmphcNewCfgUseWeight      INTEGER
    }

snmphcNewCfgIndex OBJECT-TYPE
    SYNTAX Integer32
    MAX-ACCESS read-only
    STATUS current
    DESCRIPTION
        "The index of the SNMP health check."
    ::= { snmphcNewCfgTableEntry 1 }

snmphcNewCfgOid OBJECT-TYPE
    SYNTAX DisplayString (SIZE(0..128))
    MAX-ACCESS read-create
    STATUS current
    DESCRIPTION
        "The OID to be sent in the SNMP get request packet."
    ::= { snmphcNewCfgTableEntry 2 }

snmphcNewCfgCommString OBJECT-TYPE
    SYNTAX DisplayString (SIZE(0..32))
    MAX-ACCESS read-create
    STATUS current
    DESCRIPTION
        "The community string to be used in the SNMP get request packet."
    ::= { snmphcNewCfgTableEntry 3 }

snmphcNewCfgRcvContent OBJECT-TYPE
    SYNTAX DisplayString (SIZE(0..64))
    MAX-ACCESS read-create
    STATUS current
    DESCRIPTION
        "The content expected in the SNMP response packet. The content  
        specified can be either a string or an integer value."
    ::= { snmphcNewCfgTableEntry 4 }

snmphcNewCfgInvert OBJECT-TYPE
    SYNTAX INTEGER {
        enabled(1),
        disabled(2),
        unsupported(2147483647)
        }
    MAX-ACCESS read-create
    STATUS current
    DESCRIPTION
        "When the invert option is enabled the health check will fail if
         the response packet contains the value specified in the 
         receive content field."
    ::= { snmphcNewCfgTableEntry 5 }

snmphcNewCfgDeleteHc OBJECT-TYPE
    SYNTAX INTEGER {
        other(1),
        delete(2),
        unsupported(2147483647)
        }
    MAX-ACCESS read-create
    STATUS current
    DESCRIPTION
        "When set to the value of 2 (delete), the entire row is deleted.
         When read, other(1) is returned. Setting the value to anything
         other than 2(delete) has no effect on the state of the row."
    ::= { snmphcNewCfgTableEntry 6 }

snmphcNewCfgUseWeight OBJECT-TYPE
    SYNTAX INTEGER {
        enabled(1),
        disabled(2),
        unsupported(2147483647)
        }
    MAX-ACCESS read-create
    STATUS current
    DESCRIPTION
        "When the weight option is enabled the real server weights are 
         adjusted dynamically based on the SNMP health check response."
    ::= { snmphcNewCfgTableEntry 7 }

-- Table sizes in current/new configuration of various tables

curCfgFilterTableSize OBJECT-TYPE
    SYNTAX Integer32 
    MAX-ACCESS read-only 
    STATUS current 
    DESCRIPTION 
        "Indicates the number of entries in the filter table current 
         configuration.
         Note:This mib is not supported for VX instance of Virtualization." 
    ::= { layer4TableSize 1 }

newCfgFilterTableSize OBJECT-TYPE
    SYNTAX Integer32 
    MAX-ACCESS read-only 
    STATUS current 
    DESCRIPTION 
        "Indicates the number of entries in the filter table new 
         configuration.
         Note:This mib is not supported for VX instance of Virtualization." 
    ::= { layer4TableSize 2 }

curCfgRealServerTableSize OBJECT-TYPE
    SYNTAX Integer32 
    MAX-ACCESS read-only 
    STATUS current 
    DESCRIPTION 
        "Indicates the number of entries in the SLB real server table 
         current configuration.
         Note:This mib is not supported for VX instance of Virtualization." 
    ::= { layer4TableSize 3 }

newCfgRealServerTableSize OBJECT-TYPE
    SYNTAX Integer32 
    MAX-ACCESS read-only 
    STATUS current 
    DESCRIPTION 
        "Indicates the number of entries in the SLB real server table 
         new configuration.
         Note:This mib is not supported for VX instance of Virtualization." 
    ::= { layer4TableSize 4 }

curCfgRealServerGroupTableSize OBJECT-TYPE
    SYNTAX Integer32 
    MAX-ACCESS read-only 
    STATUS current 
    DESCRIPTION 
        "Indicates the number of entries in the SLB real server group table 
         current configuration.
         Note:This mib is not supported for VX instance of Virtualization."
    ::= { layer4TableSize 5 }

newCfgRealServerGroupTableSize OBJECT-TYPE
    SYNTAX Integer32 
    MAX-ACCESS read-only 
    STATUS current 
    DESCRIPTION 
        "Indicates the number of entries in the SLB real server group table 
         new configuration.
         Note:This mib is not supported for VX instance of Virtualization."
    ::= { layer4TableSize 6 }

curCfgVirtServerTableSize OBJECT-TYPE
    SYNTAX Integer32 
    MAX-ACCESS read-only 
    STATUS current 
    DESCRIPTION 
        "Indicates the number of entries in the SLB virtual server table 
         current configuration.
         Note:This mib is not supported for VX instance of Virtualization."
    ::= { layer4TableSize 7 }

newCfgVirtServerTableSize OBJECT-TYPE
    SYNTAX Integer32 
    MAX-ACCESS read-only 
    STATUS current 
    DESCRIPTION 
        "Indicates the number of entries in the SLB virtual server table 
         new configuration.
         Note:This mib is not supported for VX instance of Virtualization."
    ::= { layer4TableSize 8 }

-- PIP Table configuration 
 
pipTableMaxSize OBJECT-TYPE
    SYNTAX  Integer32
    MAX-ACCESS  read-only
    STATUS  current
    DESCRIPTION
        "The maximum number of PIP entries.
         Note:This mib is not supported for VX instance of Virtualization."
    ::= { pipTblCfg 1 }
    
pipCurCfgBaseType OBJECT-TYPE
    SYNTAX INTEGER {
        port(1),
        vlan(2),
        unsupported(2147483647)
        }
    MAX-ACCESS  read-only
    STATUS  current
    DESCRIPTION
        "The PIP base. 1 = port based, 2 = VLAN based.
         Note:This mib is not supported for VX instance of Virtualization."
    ::= { pipTblCfg 2 }
    
pipCurCfgTable OBJECT-TYPE
    SYNTAX  SEQUENCE OF PipCurCfgTableEntry
    MAX-ACCESS  not-accessible
    STATUS  current
    DESCRIPTION
        "The PIP table in the current configuration block.
         Note:This mib is not supported for VX instance of Virtualization."
    ::= { pipTblCfg 3 }

pipCurCfgTableEntry OBJECT-TYPE
    SYNTAX  PipCurCfgTableEntry
    MAX-ACCESS  not-accessible
    STATUS  current
    DESCRIPTION
        "A row in the PIP table."
    INDEX   { pipCurCfgPip }
    ::= { pipCurCfgTable 1 }

PipCurCfgTableEntry ::= SEQUENCE {
    pipCurCfgPip            IpAddress,
    pipCurCfgPortMap	    OCTET STRING,
    pipCurCfgVlanMap        OCTET STRING
    }

pipCurCfgPip OBJECT-TYPE
    SYNTAX  IpAddress
    MAX-ACCESS  read-only
    STATUS  current
    DESCRIPTION
        "Proxy IP address by the instance of the pipCurCfgIndex." 
    ::= { pipCurCfgTableEntry 1 }
    
pipCurCfgPortMap    OBJECT-TYPE
    SYNTAX  OCTET STRING (SIZE(0..8))
    MAX-ACCESS  read-only
    STATUS  current
    DESCRIPTION
        "This is a bit map of port. 
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
         
    ::= { pipCurCfgTableEntry 2 }
    
pipCurCfgVlanMap    OBJECT-TYPE
    SYNTAX  OCTET STRING (SIZE(0..512))
    MAX-ACCESS  read-only
    STATUS  current
    DESCRIPTION
        "This is a bit map of VLAN. 

         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
         
    ::= { pipCurCfgTableEntry 3 }
    
pipNewCfgBaseType OBJECT-TYPE
    SYNTAX INTEGER {
        port(1),
        vlan(2),
        unsupported(2147483647)
        }
    MAX-ACCESS  read-write
    STATUS  current
    DESCRIPTION
        "The PIP base. 1 = port based, 2 = VLAN based.
         Note:This mib is not supported for VX instance of Virtualization."
    ::= { pipTblCfg 4 }
    
pipNewCfgTable OBJECT-TYPE
    SYNTAX  SEQUENCE OF PipNewCfgTableEntry
    MAX-ACCESS  not-accessible
    STATUS  current
    DESCRIPTION
        "The PIP table in the New configuration block.
         Note:This mib is not supported for VX instance of Virtualization."
    ::= { pipTblCfg 5 }

pipNewCfgTableEntry OBJECT-TYPE
    SYNTAX  PipNewCfgTableEntry
    MAX-ACCESS  not-accessible
    STATUS  current
    DESCRIPTION
        "A row in the PIP table."
    INDEX   { pipNewCfgPip }
    ::= { pipNewCfgTable 1 }

PipNewCfgTableEntry ::= SEQUENCE {
    pipNewCfgPip                IpAddress,
    pipNewCfgPortMap            OCTET STRING,
    pipNewCfgVlanMap            OCTET STRING,
    pipNewCfgDelete             INTEGER,
    pipNewCfgAddPortVlan        Integer32,
    pipNewCfgRemovePortVlan     Integer32,
    pipNewCfgAddPort            Integer32,
    pipNewCfgAddVlan            Integer32,
    pipNewCfgRemovePort         Integer32,
    pipNewCfgRemoveVlan         Integer32
    }

pipNewCfgPip OBJECT-TYPE
    SYNTAX  IpAddress
    MAX-ACCESS  read-only
    STATUS  current
    DESCRIPTION
        "PIP address by the instance of the pipCurCfgIndex." 
    ::= { pipNewCfgTableEntry 1 }
    
pipNewCfgPortMap    OBJECT-TYPE
    SYNTAX  OCTET STRING (SIZE(0..8))
    MAX-ACCESS  read-only
    STATUS  current
    DESCRIPTION
        "The bit map of port for PIP.
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
 
    ::= { pipNewCfgTableEntry 2 }
    
pipNewCfgVlanMap    OBJECT-TYPE
    SYNTAX  OCTET STRING (SIZE(0..512))
    MAX-ACCESS  read-only
    STATUS  current
    DESCRIPTION
        "The bit map of VLAN for PIP.
         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
 
    ::= { pipNewCfgTableEntry 3 }

pipNewCfgDelete OBJECT-TYPE
    SYNTAX  INTEGER {
        other(1),
        delete(2),
        unsupported(2147483647)
        }
    MAX-ACCESS  read-create
    STATUS  current
    DESCRIPTION
        "By setting the value to delete(2), the entire row is deleted."
    ::= { pipNewCfgTableEntry 4 }

pipNewCfgAddPortVlan OBJECT-TYPE
    SYNTAX  Integer32
    MAX-ACCESS  read-create
    STATUS  current
    DESCRIPTION
        "The Port or VLAN to be associated with the PIP. When read, 0 is returned."
    ::= { pipNewCfgTableEntry 5 }

pipNewCfgRemovePortVlan OBJECT-TYPE 
    SYNTAX  Integer32 
    MAX-ACCESS  read-create 
    STATUS  current
    DESCRIPTION
        "The Port or VLAN to be disassociated from the PIP. When read, 
         0 is returned."
    ::= { pipNewCfgTableEntry 6 }

pipNewCfgAddPort OBJECT-TYPE
    SYNTAX  Integer32
    MAX-ACCESS  read-create
    STATUS  current
    DESCRIPTION
        "The Port to be associated with the PIP. When read, 0 is returned."
    ::= { pipNewCfgTableEntry 7 }

pipNewCfgAddVlan OBJECT-TYPE
    SYNTAX  Integer32
    MAX-ACCESS  read-create
    STATUS  current
    DESCRIPTION
        "The VLAN to be associated with the PIP. When read, 0 is returned."
    ::= { pipNewCfgTableEntry 8 }

pipNewCfgRemovePort OBJECT-TYPE 
    SYNTAX  Integer32 
    MAX-ACCESS  read-create 
    STATUS  current
    DESCRIPTION
        "The Port to be disassociated from the PIP. When read, 
         0 is returned."
    ::= { pipNewCfgTableEntry 9 }

pipNewCfgRemoveVlan OBJECT-TYPE 
    SYNTAX  Integer32 
    MAX-ACCESS  read-create 
    STATUS  current
    DESCRIPTION
        "The VLAN to be disassociated from the PIP. When read, 
         0 is returned."
    ::= { pipNewCfgTableEntry 10 }

-- IPv6 Proxy IP Configuration

pip6CurCfgTable OBJECT-TYPE
    SYNTAX  SEQUENCE OF Pip6CurCfgTableEntry
    MAX-ACCESS  not-accessible
    STATUS  current
    DESCRIPTION
        "The IPv6 PIP table in the current configuration block.
         Note:This mib is not supported for VX instance of Virtualization."
    ::= { pipTblCfg 6 }

pip6CurCfgTableEntry OBJECT-TYPE
    SYNTAX  Pip6CurCfgTableEntry
    MAX-ACCESS  not-accessible
    STATUS  current
    DESCRIPTION
        "A row in the IPv6 PIP table."
    INDEX   { pip6CurCfgPip }
    ::= { pip6CurCfgTable 1 }

Pip6CurCfgTableEntry ::= SEQUENCE {
    pip6CurCfgPip           DisplayString,
    pip6CurCfgPortMap	    OCTET STRING,
    pip6CurCfgVlanMap       OCTET STRING
    }

pip6CurCfgPip OBJECT-TYPE
    SYNTAX  DisplayString (SIZE(0..40))
    MAX-ACCESS  read-only
    STATUS  current
    DESCRIPTION
        "Current configured IPv6 Proxy IP address. 
	it should be of the form:

	<OID>.4.16.x.x.x.x.x.x.x.x.x.x.x.x.x.x.x.x

	Here, 4 stands for IPv6 type
	16 - stands for number of octets.
	x - the IPv6 address octets

	example: for 1111::1111 address, it should be  
	pip6CurCfgPip.4.16.17.17.0.0.0.0.0.0.0.0.0.0.0.0.17.17" 
    ::= { pip6CurCfgTableEntry 1 }
    
pip6CurCfgPortMap    OBJECT-TYPE
    SYNTAX  OCTET STRING (SIZE(0..8))
    MAX-ACCESS  read-only
    STATUS  current
    DESCRIPTION
        "This is a bit map of port. 
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
         
    ::= { pip6CurCfgTableEntry 2 }
    
pip6CurCfgVlanMap    OBJECT-TYPE
    SYNTAX  OCTET STRING (SIZE(0..512))
    MAX-ACCESS  read-only
    STATUS  current
    DESCRIPTION
        "This is a bit map of VLAN. 

         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
         
    ::= { pip6CurCfgTableEntry 3 }
    
pip6NewCfgTable OBJECT-TYPE
    SYNTAX  SEQUENCE OF Pip6NewCfgTableEntry
    MAX-ACCESS  not-accessible
    STATUS  current
    DESCRIPTION
        "The IPv6 PIP table in the New configuration block.
         Note:This mib is not supported for VX instance of Virtualization."
    ::= { pipTblCfg 7 }

pip6NewCfgTableEntry OBJECT-TYPE
    SYNTAX  Pip6NewCfgTableEntry
    MAX-ACCESS  not-accessible
    STATUS  current
    DESCRIPTION
        "A row in the IPv6 PIP table."
    INDEX   { pip6NewCfgPip }
    ::= { pip6NewCfgTable 1 }

Pip6NewCfgTableEntry ::= SEQUENCE {
    pip6NewCfgPip               DisplayString,
    pip6NewCfgPortMap           OCTET STRING,
    pip6NewCfgVlanMap           OCTET STRING,
    pip6NewCfgDelete            INTEGER,
    pip6NewCfgAddPortVlan       Integer32,
    pip6NewCfgRemovePortVlan    Integer32,
    pip6NewCfgAddPort           Integer32,
    pip6NewCfgAddVlan           Integer32,
    pip6NewCfgRemovePort        Integer32,
    pip6NewCfgRemoveVlan        Integer32
    }

pip6NewCfgPip OBJECT-TYPE
    SYNTAX DisplayString (SIZE(0..50)) 
    MAX-ACCESS  read-only
    STATUS  current
    DESCRIPTION
        "New configured IPv6 Proxy IP address.
        it should be of the form:

        <OID>.4.16.x.x.x.x.x.x.x.x.x.x.x.x.x.x.x.x

        Here, 4 stands for IPv6 type
        16 - stands for number of octets.
        x - the IPv6 address octets

        example: for 1111::1111 address, it should be
        pip6NewCfgPip.4.16.17.17.0.0.0.0.0.0.0.0.0.0.0.0.17.17"
    ::= { pip6NewCfgTableEntry 1 }
    
pip6NewCfgPortMap    OBJECT-TYPE
    SYNTAX  OCTET STRING (SIZE(0..8))
    MAX-ACCESS  read-only
    STATUS  current
    DESCRIPTION
        "The bit map of port for PIP.
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
 
    ::= { pip6NewCfgTableEntry 2 }
    
pip6NewCfgVlanMap    OBJECT-TYPE
    SYNTAX  OCTET STRING (SIZE(0..512))
    MAX-ACCESS  read-only
    STATUS  current
    DESCRIPTION
        "The bit map of VLAN for PIP.
         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
 
    ::= { pip6NewCfgTableEntry 3 }

pip6NewCfgDelete OBJECT-TYPE
    SYNTAX  INTEGER {
        other(1),
        delete(2),
        unsupported(2147483647)
        }
    MAX-ACCESS  read-create
    STATUS  current
    DESCRIPTION
        "By setting the value to delete(2), the entire row is deleted."
    ::= { pip6NewCfgTableEntry 4 }

pip6NewCfgAddPortVlan OBJECT-TYPE
    SYNTAX  Integer32
    MAX-ACCESS  read-create
    STATUS  current
    DESCRIPTION
        "The Port or VLAN to be associated with the PIP. When read, 0 is returned."
    ::= { pip6NewCfgTableEntry 5 }

pip6NewCfgRemovePortVlan OBJECT-TYPE 
    SYNTAX  Integer32 
    MAX-ACCESS  read-create 
    STATUS  current
    DESCRIPTION
        "The Port or VLAN to be disassociated from the PIP. When read, 
         0 is returned."
    ::= { pip6NewCfgTableEntry 6 }

pip6NewCfgAddPort OBJECT-TYPE
    SYNTAX  Integer32
    MAX-ACCESS  read-create
    STATUS  current
    DESCRIPTION
        "The Port to be associated with the PIP. When read, 0 is returned."
    ::= { pip6NewCfgTableEntry 7 }

pip6NewCfgAddVlan OBJECT-TYPE
    SYNTAX  Integer32
    MAX-ACCESS  read-create
    STATUS  current
    DESCRIPTION
        "The VLAN to be associated with the PIP. When read, 0 is returned."
    ::= { pip6NewCfgTableEntry 8 }

pip6NewCfgRemovePort OBJECT-TYPE 
    SYNTAX  Integer32 
    MAX-ACCESS  read-create 
    STATUS  current
    DESCRIPTION
        "The Port to be disassociated from the PIP. When read, 
         0 is returned."
    ::= { pip6NewCfgTableEntry 9 }

pip6NewCfgRemoveVlan OBJECT-TYPE 
    SYNTAX  Integer32 
    MAX-ACCESS  read-create 
    STATUS  current
    DESCRIPTION
        "The VLAN to be disassociated from the PIP. When read, 
         0 is returned."
    ::= { pip6NewCfgTableEntry 10 }


--PIP - Port Table Configuration

pipCurCfgPortTable OBJECT-TYPE
    SYNTAX  SEQUENCE OF PipCurCfgPortTableEntry
    MAX-ACCESS  not-accessible
    STATUS  current
    DESCRIPTION
        "The PIP Port table Current configuration block.
         Note:This mib is not supported for VX instance of Virtualization."
    ::= { pipTblCfg 8 }

pipCurCfgPortTableEntry OBJECT-TYPE
    SYNTAX  PipCurCfgPortTableEntry
    MAX-ACCESS  not-accessible
    STATUS  current
    DESCRIPTION
        "A row in the PIP Port table."
    INDEX   { pipCurCfgPortPip }
    ::= { pipCurCfgPortTable 1 }

PipCurCfgPortTableEntry ::= SEQUENCE {
    pipCurCfgPortPip                IpAddress,
    pipCurCfgPortPipMap             OCTET STRING
}

pipCurCfgPortPip OBJECT-TYPE
    SYNTAX  IpAddress
    MAX-ACCESS  read-only
    STATUS  current
    DESCRIPTION
        "PIP address by the instance of the pipCurCfgPortIndex." 
    ::= { pipCurCfgPortTableEntry 1 }

pipCurCfgPortPipMap    OBJECT-TYPE
    SYNTAX  OCTET STRING (SIZE(0..8))
    MAX-ACCESS  read-only
    STATUS  current
    DESCRIPTION
        "The bit map of port for PIP.in receiving order:

    OCTET 1  OCTET 2  .....
    xxxxxxxx xxxxxxxx ..... 
    ||    || |_ port 8
    ||    ||  
    ||    ||___ port 7
    ||    |____ port 6
    ||_________ port 1
    |__________ unused

    where x : 1 - PIP is used for this port.
    x : 0 - PIP Not used for this port."

    ::= { pipCurCfgPortTableEntry 2 }

pipNewCfgPortTable OBJECT-TYPE
    SYNTAX  SEQUENCE OF PipNewCfgPortTableEntry
    MAX-ACCESS  not-accessible
    STATUS  current
    DESCRIPTION
        "The PIP Port table New configuration block.
         Note:This mib is not supported for VX instance of Virtualization."
    ::= { pipTblCfg 9 }

pipNewCfgPortTableEntry OBJECT-TYPE
    SYNTAX  PipNewCfgPortTableEntry
    MAX-ACCESS  not-accessible
    STATUS  current
    DESCRIPTION
        "A row in the PIP Port table."
    INDEX   { pipNewCfgPortPip }
    ::= { pipNewCfgPortTable 1 }

    PipNewCfgPortTableEntry ::= SEQUENCE {
    pipNewCfgPortPip                IpAddress,
    pipNewCfgPortPipMap             OCTET STRING,
    pipNewCfgPortAdd                Integer32,
    pipNewCfgPortRemove             Integer32,
    pipNewCfgPortDelete             INTEGER
    }

pipNewCfgPortPip OBJECT-TYPE
    SYNTAX  IpAddress
    MAX-ACCESS  read-only
    STATUS  current
    DESCRIPTION
        "PIP address by the instance of the pipNewCfgPortIndex." 
    ::= { pipNewCfgPortTableEntry 1 }

pipNewCfgPortPipMap    OBJECT-TYPE
    SYNTAX  OCTET STRING (SIZE(0..8))
    MAX-ACCESS  read-only
    STATUS  current
    DESCRIPTION
        "The bit map of port for PIP.
        in receiving order:

    OCTET 1  OCTET 2  .....
    xxxxxxxx xxxxxxxx ..... 
    ||    || |_ port 8
    ||    ||  
    ||    ||___ port 7
    ||    |____ port 6
    ||_________ port 1
    |__________ unused

    where x : 1 - PIP is used for this port.
    x : 0 - PIP Not used for this port."

    ::= { pipNewCfgPortTableEntry 2 }


pipNewCfgPortAdd OBJECT-TYPE
    SYNTAX  Integer32
    MAX-ACCESS  read-create
    STATUS  current
    DESCRIPTION
        "The Port to be associated with the PIP. When read, 0 is returned."
    ::= { pipNewCfgPortTableEntry 3 }

pipNewCfgPortRemove OBJECT-TYPE 
    SYNTAX  Integer32 
    MAX-ACCESS  read-create 
    STATUS  current
    DESCRIPTION
        "The Port to be disassociated from the PIP. When read, 
         0 is returned."
    ::= { pipNewCfgPortTableEntry 4 }

pipNewCfgPortDelete OBJECT-TYPE
    SYNTAX  INTEGER {
        other(1),
        delete(2),
        unsupported(2147483647)
    }
    MAX-ACCESS  read-create
    STATUS  current
    DESCRIPTION
        "By setting the value to delete(2), the entire row is deleted."
    ::= { pipNewCfgPortTableEntry 5 }

--PIP - VLAN Table Configuration

    pipCurCfgVlanTable OBJECT-TYPE
    SYNTAX  SEQUENCE OF PipCurCfgVlanTableEntry
    MAX-ACCESS  not-accessible
    STATUS  current
    DESCRIPTION
        "The PIP Vlan table Current configuration block.
         Note:This mib is not supported for VX instance of Virtualization."
    ::= { pipTblCfg 10 }

    pipCurCfgVlanTableEntry OBJECT-TYPE
    SYNTAX  PipCurCfgVlanTableEntry
    MAX-ACCESS  not-accessible
    STATUS  current
    DESCRIPTION
        "A row in the PIP VLAN table."
    INDEX   { pipCurCfgVlanPip }
    ::= { pipCurCfgVlanTable 1 }

PipCurCfgVlanTableEntry ::= SEQUENCE {
    pipCurCfgVlanPip                IpAddress,
    pipCurCfgVlanPipMap            OCTET STRING
}

pipCurCfgVlanPip OBJECT-TYPE
    SYNTAX  IpAddress
    MAX-ACCESS  read-only
    STATUS  current
    DESCRIPTION
        "PIP address by the instance of the pipCurCfgIndex." 
    ::= { pipCurCfgVlanTableEntry 1 }

    pipCurCfgVlanPipMap    OBJECT-TYPE
    SYNTAX  OCTET STRING (SIZE(0..512))
    MAX-ACCESS  read-only
    STATUS  current
    DESCRIPTION
        "The bit map of VLAN for PIP.
    in receiving order:

    OCTET 1  OCTET 2  .....
    xxxxxxxx xxxxxxxx ..... 
    ||    || |_ VLAN 8
    ||    ||  
    ||    ||___ VLAN 7
    ||    |____ VLAN 6
    ||_________ VLAN 1
    |__________ unused

    where x : 1 - PIP is used for this VLAN.
    x : 0 - PIP Not used for this VLAN."

    ::= { pipCurCfgVlanTableEntry 2 }   

pipNewCfgVlanTable OBJECT-TYPE
    SYNTAX  SEQUENCE OF PipNewCfgVlanTableEntry
    MAX-ACCESS  not-accessible
    STATUS  current
    DESCRIPTION
        "The PIP Vlan table New configuration block.
         Note:This mib is not supported for VX instance of Virtualization."
    ::= { pipTblCfg 11 }

    pipNewCfgVlanTableEntry OBJECT-TYPE
    SYNTAX  PipNewCfgVlanTableEntry
    MAX-ACCESS  not-accessible
    STATUS  current
    DESCRIPTION
        "A row in the PIP table."
    INDEX   { pipNewCfgVlanPip }
    ::= { pipNewCfgVlanTable 1 }

PipNewCfgVlanTableEntry ::= SEQUENCE {
    pipNewCfgVlanPip                IpAddress,
    pipNewCfgVlanPipMap            OCTET STRING,
    pipNewCfgVlanAdd               Integer32,
    pipNewCfgVlanRemove            Integer32,
    pipNewCfgVlanDelete            INTEGER
    }

pipNewCfgVlanPip OBJECT-TYPE
    SYNTAX  IpAddress
    MAX-ACCESS  read-only
    STATUS  current
    DESCRIPTION
        "PIP address by the instance of the pipCurCfgIndex." 
    ::= { pipNewCfgVlanTableEntry 1 }

pipNewCfgVlanPipMap    OBJECT-TYPE
    SYNTAX  OCTET STRING (SIZE(0..512))
    MAX-ACCESS  read-only
    STATUS  current
    DESCRIPTION
        "The bit map of VLAN for PIP.
    in receiving order:

    OCTET 1  OCTET 2  .....
    xxxxxxxx xxxxxxxx ..... 
    ||    || |_ VLAN 8
    ||    ||  
    ||    ||___ VLAN 7
    ||    |____ VLAN 6
    ||_________ VLAN 1
    |__________ unused

    where x : 1 - PIP is used for this VLAN.
    x : 0 - PIP Not used for this VLAN."

    ::= { pipNewCfgVlanTableEntry 2 }

pipNewCfgVlanAdd OBJECT-TYPE
    SYNTAX  Integer32
    MAX-ACCESS  read-create
    STATUS  current
    DESCRIPTION
        "The VLAN to be associated with the PIP. When read, 0 is returned."
    ::= { pipNewCfgVlanTableEntry 3 }

    pipNewCfgVlanRemove OBJECT-TYPE 
    SYNTAX  Integer32 
    MAX-ACCESS  read-create 
    STATUS  current
    DESCRIPTION
        "The VLAN to be disassociated from the PIP. When read, 
         0 is returned."
    ::= { pipNewCfgVlanTableEntry 4 }

    pipNewCfgVlanDelete OBJECT-TYPE
    SYNTAX  INTEGER {
        other(1),
        delete(2),
        unsupported(2147483647)
    }
    MAX-ACCESS  read-create
    STATUS  current
    DESCRIPTION
        "By setting the value to delete(2), the entire row is deleted."
    ::= { pipNewCfgVlanTableEntry 5 }

-- Ipv6 PIP Port Table

pip6CurCfgPortTable OBJECT-TYPE
    SYNTAX  SEQUENCE OF Pip6CurCfgPortTableEntry
    MAX-ACCESS  not-accessible
    STATUS  current
    DESCRIPTION
        "The PIP Port table Current configuration block.
         Note:This mib is not supported for VX instance of Virtualization."
    ::= { pipTblCfg 12 }

pip6CurCfgPortTableEntry OBJECT-TYPE
    SYNTAX  Pip6CurCfgPortTableEntry
    MAX-ACCESS  not-accessible
    STATUS  current
    DESCRIPTION
        "A row in the Ipv6 PIP Port table."
    INDEX   { pip6CurCfgPortPip }
    ::= { pip6CurCfgPortTable 1 }

Pip6CurCfgPortTableEntry ::= SEQUENCE {
        pip6CurCfgPortPip                DisplayString,
        pip6CurCfgPortPipMap             OCTET STRING
    }

pip6CurCfgPortPip OBJECT-TYPE
    SYNTAX  DisplayString (SIZE(0..50))
    MAX-ACCESS  read-only
    STATUS  current
    DESCRIPTION
        "PIP address by the instance of the pip6CurCfgPortIndex."
    ::= { pip6CurCfgPortTableEntry 1 }

pip6CurCfgPortPipMap    OBJECT-TYPE
    SYNTAX  OCTET STRING (SIZE(0..8))
    MAX-ACCESS  read-only
    STATUS  current
    DESCRIPTION
        "The bit map of port for PIP.
        in receiving order:

    OCTET 1  OCTET 2  .....
    xxxxxxxx xxxxxxxx .....
    ||    || |_ port 8
    ||    ||
    ||    ||___ port 7
    ||    |____ port 6
    ||_________ port 1
    |__________ unused

    where x : 1 - PIP is used for this port.
    x : 0 - PIP Not used for this port."

    ::= { pip6CurCfgPortTableEntry 2 }

pip6NewCfgPortTable OBJECT-TYPE
    SYNTAX  SEQUENCE OF Pip6NewCfgPortTableEntry
    MAX-ACCESS  not-accessible
    STATUS  current
    DESCRIPTION
    "The PIP Port table New configuration block.
     Note:This mib is not supported for VX instance of Virtualization."
    ::= { pipTblCfg 13 }

pip6NewCfgPortTableEntry OBJECT-TYPE
    SYNTAX  Pip6NewCfgPortTableEntry
    MAX-ACCESS  not-accessible
    STATUS  current
    DESCRIPTION
    "A row in the PIP Port table."
    INDEX   { pip6NewCfgPortPip }
    ::= { pip6NewCfgPortTable 1 }

Pip6NewCfgPortTableEntry ::= SEQUENCE {
        pip6NewCfgPortPip            DisplayString,
        pip6NewCfgPortPipMap         OCTET STRING,
        pip6NewCfgPortAdd            Integer32,
        pip6NewCfgPortRemove         Integer32,
        pip6NewCfgPortDelete         INTEGER
    }

pip6NewCfgPortPip OBJECT-TYPE
    SYNTAX  DisplayString (SIZE(0..50))
    MAX-ACCESS  read-only
    STATUS  current
    DESCRIPTION
        "PIP address by the instance of the pip6NewCfgPortIndex."
    ::= { pip6NewCfgPortTableEntry 1 }

pip6NewCfgPortPipMap    OBJECT-TYPE
    SYNTAX  OCTET STRING (SIZE(0..8))
    MAX-ACCESS  read-only
    STATUS  current
    DESCRIPTION
        "The bit map of port for PIP.
        in receiving order:

    OCTET 1  OCTET 2  .....
    xxxxxxxx xxxxxxxx .....
    ||    || |_ port 8
    ||    ||
    ||    ||___ port 7
    ||    |____ port 6
    ||_________ port 1
    |__________ unused

    where x : 1 - PIP is used for this port.
    x : 0 - PIP Not used for this port."

    ::= { pip6NewCfgPortTableEntry 2 }


pip6NewCfgPortAdd OBJECT-TYPE
    SYNTAX  Integer32
    MAX-ACCESS  read-create
    STATUS  current
    DESCRIPTION
        "The Port to be associated with the PIP. When read, 0 is returned."
    ::= { pip6NewCfgPortTableEntry 3 }

pip6NewCfgPortRemove OBJECT-TYPE
    SYNTAX  Integer32
    MAX-ACCESS  read-create
    STATUS  current
    DESCRIPTION
        "The Port to be disassociated from the PIP. When read,
        0 is returned."
    ::= { pip6NewCfgPortTableEntry 4 }

pip6NewCfgPortDelete OBJECT-TYPE
    SYNTAX  INTEGER {
        other(1),
            delete(2),
        unsupported(2147483647)
    }
    MAX-ACCESS  read-create
    STATUS  current
    DESCRIPTION
        "By setting the value to delete(2), the entire row is deleted."
    ::= { pip6NewCfgPortTableEntry 5 }


--Ipv6 PIP - Vlan Table Configuration

pip6CurCfgVlanTable OBJECT-TYPE
    SYNTAX  SEQUENCE OF Pip6CurCfgVlanTableEntry
    MAX-ACCESS  not-accessible
    STATUS  current
    DESCRIPTION
        "The PIP Vlan table Cur configuration block.
         Note:This mib is not supported for VX instance of Virtualization."
    ::= { pipTblCfg 14 }

pip6CurCfgVlanTableEntry OBJECT-TYPE
    SYNTAX  Pip6CurCfgVlanTableEntry
    MAX-ACCESS  not-accessible
    STATUS  current
    DESCRIPTION
        "A row in the PIP table."
    INDEX   { pip6CurCfgVlanPip }
    ::= { pip6CurCfgVlanTable 1 }

    Pip6CurCfgVlanTableEntry ::= SEQUENCE {
        pip6CurCfgVlanPip               DisplayString,
        pip6CurCfgVlanPipMap            OCTET STRING
    }

pip6CurCfgVlanPip OBJECT-TYPE
    SYNTAX  DisplayString (SIZE(0..50))
    MAX-ACCESS  read-only
    STATUS  current
    DESCRIPTION
        "PIP address by the instance of the pip6CurCfgIndex."
    ::= { pip6CurCfgVlanTableEntry 1 }

pip6CurCfgVlanPipMap    OBJECT-TYPE
    SYNTAX  OCTET STRING (SIZE(0..512))
    MAX-ACCESS  read-only
    STATUS  current
    DESCRIPTION
        "The bit map of VLAN for PIP.
         in receiving order:

    OCTET 1  OCTET 2  .....
    xxxxxxxx xxxxxxxx .....
    ||    || |_ VLAN 8
    ||    ||
    ||    ||___ VLAN 7
    ||    |____ VLAN 6
    ||_________ VLAN 1
    |__________ unused

    where x : 1 - PIP is used for this VLAN.
    x : 0 - PIP Not used for this VLAN."

    ::= { pip6CurCfgVlanTableEntry 2 }

pip6NewCfgVlanTable OBJECT-TYPE
    SYNTAX  SEQUENCE OF Pip6NewCfgVlanTableEntry
    MAX-ACCESS  not-accessible
    STATUS  current
    DESCRIPTION
        "The PIP Vlan table New configuration block.
         Note:This mib is not supported for VX instance of Virtualization."
    ::= { pipTblCfg 15 }

pip6NewCfgVlanTableEntry OBJECT-TYPE
    SYNTAX  Pip6NewCfgVlanTableEntry
    MAX-ACCESS  not-accessible
    STATUS  current
    DESCRIPTION
        "A row in the PIP table."
    INDEX   { pip6NewCfgVlanPip }
    ::= { pip6NewCfgVlanTable 1 }

    Pip6NewCfgVlanTableEntry ::= SEQUENCE {
        pip6NewCfgVlanPip            DisplayString,
        pip6NewCfgVlanPipMap         OCTET STRING,
        pip6NewCfgVlanAdd            Integer32,
        pip6NewCfgVlanRemove         Integer32,
        pip6NewCfgVlanDelete         INTEGER
    }

pip6NewCfgVlanPip OBJECT-TYPE
    SYNTAX  DisplayString (SIZE(0..50))
    MAX-ACCESS  read-only
    STATUS  current
    DESCRIPTION
        "PIP address by the instance of the pip6CurCfgIndex."
    ::= { pip6NewCfgVlanTableEntry 1 }

pip6NewCfgVlanPipMap    OBJECT-TYPE
    SYNTAX  OCTET STRING (SIZE(0..512))
    MAX-ACCESS  read-only
    STATUS  current
    DESCRIPTION
        "The bit map of VLAN for PIP.
        in receiving order:

    OCTET 1  OCTET 2  .....
    xxxxxxxx xxxxxxxx .....
    ||    || |_ VLAN 8
    ||    ||
    ||    ||___ VLAN 7
    ||    |____ VLAN 6
    ||_________ VLAN 1
    |__________ unused

    where x : 1 - PIP is used for this VLAN.
    x : 0 - PIP Not used for this VLAN."

    ::= { pip6NewCfgVlanTableEntry 2 }

pip6NewCfgVlanAdd OBJECT-TYPE
    SYNTAX  Integer32
    MAX-ACCESS  read-create
    STATUS  current
    DESCRIPTION
        "The VLAN to be associated with the PIP. When read, 0 is returned."
    ::= { pip6NewCfgVlanTableEntry 3 }

pip6NewCfgVlanRemove OBJECT-TYPE
    SYNTAX  Integer32
    MAX-ACCESS  read-create
    STATUS  current
    DESCRIPTION
        "The VLAN to be disassociated from the PIP. When read,
        0 is returned."
    ::= { pip6NewCfgVlanTableEntry 4 }

pip6NewCfgVlanDelete OBJECT-TYPE
    SYNTAX  INTEGER {
        other(1),
            delete(2),
        unsupported(2147483647)
    }
    MAX-ACCESS  read-create
    STATUS  current
    DESCRIPTION
        "By setting the value to delete(2), the entire row is deleted."
    ::= { pip6NewCfgVlanTableEntry 5 }



--  SLB AppShape Table
slbCurCfgAppShapeTable OBJECT-TYPE
    SYNTAX  SEQUENCE OF SlbCurCfgAppShapeEntry
    MAX-ACCESS  not-accessible
    STATUS  current
    DESCRIPTION
       "The table of AppShape,
        Note:This mib is not supported for VX instance of Virtualization."
    ::= { appShapeCfg 1 }

slbCurCfgAppShapeEntry OBJECT-TYPE
    SYNTAX  SlbCurCfgAppShapeEntry
    MAX-ACCESS  not-accessible
    STATUS  current
    DESCRIPTION
        "A row in the slbAppShapeTable "
    INDEX   { slbCurCfgAppShapeIndex }
    ::= { slbCurCfgAppShapeTable 1 }

SlbCurCfgAppShapeEntry ::= SEQUENCE {
    slbCurCfgAppShapeIndex           DisplayString,
    slbCurCfgAppShapeName            DisplayString,
    slbCurCfgAppShapeState           INTEGER
   }

slbCurCfgAppShapeIndex OBJECT-TYPE
    SYNTAX  DisplayString (SIZE(0..128))
    MAX-ACCESS  read-only
    STATUS  current
    DESCRIPTION
        "The AppShape number"
    ::= { slbCurCfgAppShapeEntry 1 }

slbCurCfgAppShapeName OBJECT-TYPE
    SYNTAX  DisplayString (SIZE(0..128))
    MAX-ACCESS  read-only
    STATUS  current
    DESCRIPTION
        "The name of the apprule."
    ::= { slbCurCfgAppShapeEntry 2 }

slbCurCfgAppShapeState OBJECT-TYPE
 SYNTAX  INTEGER {
        enabled(1),
        disabled(2),
        unsupported(2147483647)
        }
    MAX-ACCESS  read-only
    STATUS  current
    DESCRIPTION
        "Enable or disable AppShape."
    ::= { slbCurCfgAppShapeEntry 3 }

-- Server load balancing - slb AppShape state table

slbNewCfgAppShapeTable OBJECT-TYPE
    SYNTAX  SEQUENCE OF SlbNewCfgAppShapeEntry
    MAX-ACCESS  not-accessible
    STATUS  current
    DESCRIPTION
       "The table of AppShape,
        Note:This mib is not supported for VX instance of Virtualization."
    ::= { appShapeCfg 2 }

slbNewCfgAppShapeEntry OBJECT-TYPE
    SYNTAX  SlbNewCfgAppShapeEntry
    MAX-ACCESS  not-accessible
    STATUS  current
    DESCRIPTION
        "A row in the slbAppShapeTable "
    INDEX   { slbNewCfgAppShapeIndex }
    ::= { slbNewCfgAppShapeTable 1 }

SlbNewCfgAppShapeEntry ::= SEQUENCE {
    slbNewCfgAppShapeIndex           DisplayString,
    slbNewCfgAppShapeName            DisplayString,
    slbNewCfgAppShapeState           INTEGER,
    slbNewCfgAppShapeDelete          INTEGER,
    slbNewCfgAppShapeDefault         INTEGER
   }

slbNewCfgAppShapeIndex OBJECT-TYPE
    SYNTAX  DisplayString (SIZE(0..128))
    MAX-ACCESS  read-only
    STATUS  current
    DESCRIPTION
        "The AppShape number"
    ::= { slbNewCfgAppShapeEntry 1 }

slbNewCfgAppShapeName OBJECT-TYPE
    SYNTAX  DisplayString (SIZE(0..128))
    MAX-ACCESS  read-create
    STATUS  current
    DESCRIPTION
        "The name of the Apprule."
    ::= { slbNewCfgAppShapeEntry 2 }

slbNewCfgAppShapeState OBJECT-TYPE
 SYNTAX  INTEGER {
        enabled(1),
        disabled(2),
        unsupported(2147483647)
        }
    MAX-ACCESS  read-create
    STATUS  current
    DESCRIPTION
        "Enable or disable AppShape."
    ::= { slbNewCfgAppShapeEntry 3 }

slbNewCfgAppShapeDelete OBJECT-TYPE
    SYNTAX  INTEGER {
        other(1),
        delete(2),
        unsupported(2147483647)
        }
    MAX-ACCESS  read-create
    STATUS  current
    DESCRIPTION
        "When set to the value of 2 (delete), the entire row is deleted.
         When read, other(1) is returned. Setting the value to anything
         other than 2(delete) has no effect on the state of the row."
    ::= { slbNewCfgAppShapeEntry 4 }

slbNewCfgAppShapeDefault OBJECT-TYPE
    SYNTAX  INTEGER {
        other(1),
        default(2),
        unsupported(2147483647)
        }
    MAX-ACCESS  read-create
    STATUS  current
    DESCRIPTION
        "Value of 2(default),will restore the default APM AppShape++ script.
         When read, other(1) is returned. Setting the value to anything
         other than 2(default) has no effect. Note that default is only for
         APM_script not for any other script"
    ::= { slbNewCfgAppShapeEntry 5 }
-- SLB Statistics Group

-- SLB SP Real Servers Statistics Table

slbStatSpRealServerTable OBJECT-TYPE
    SYNTAX  SEQUENCE OF SlbStatSpRealServerEntry
    MAX-ACCESS  not-accessible
    STATUS  current
    DESCRIPTION
        "The sp-server statistics table.  This table shows the statistics 
         of real servers for a particular SP.
        Note:This mib is not supported for VX instance of Virtualization."
    ::= { slbSpStats 1 }

slbStatSpRealServerEntry OBJECT-TYPE
    SYNTAX  SlbStatSpRealServerEntry
    MAX-ACCESS  not-accessible
    STATUS  current
    DESCRIPTION
        "A row in the sp-server statistics table."
    INDEX  { slbStatSpRealServerSpIndex, slbStatSpRealServerServerIndex }
    ::= { slbStatSpRealServerTable 1 }

SlbStatSpRealServerEntry ::= SEQUENCE {
    slbStatSpRealServerSpIndex               Integer32,
    slbStatSpRealServerServerIndex           Integer32,
    slbStatSpRealServerCurrSessions          Gauge32,
    slbStatSpRealServerTotalSessions         Counter32,
    slbStatSpRealServerHCOctetsLow32         Counter32,
    slbStatSpRealServerHCOctetsHigh32        Counter32,
    slbStatSpRealServerHCOctets              Counter64
    }

slbStatSpRealServerSpIndex OBJECT-TYPE
    SYNTAX  Integer32
    MAX-ACCESS  read-only
    STATUS  current
    DESCRIPTION
        "The SP index."
    ::= { slbStatSpRealServerEntry 1 }

slbStatSpRealServerServerIndex OBJECT-TYPE 
    SYNTAX  Integer32 
    MAX-ACCESS  read-only
    STATUS  current 
    DESCRIPTION 
        "The real server number that identifies the server." 
    ::= { slbStatSpRealServerEntry 2 }

slbStatSpRealServerCurrSessions OBJECT-TYPE 
    SYNTAX  Gauge32
    MAX-ACCESS  read-only
    STATUS  current 
    DESCRIPTION 
        "The current sessions for the real server on a particular SP."
    ::= { slbStatSpRealServerEntry 3 }

slbStatSpRealServerTotalSessions OBJECT-TYPE 
    SYNTAX  Counter32 
    MAX-ACCESS  read-only
    STATUS  current 
    DESCRIPTION 
        "The SP total number of sessions for the real server on a particular SP."
    ::= { slbStatSpRealServerEntry 4 }

slbStatSpRealServerHCOctetsLow32 OBJECT-TYPE
    SYNTAX  Counter32
    MAX-ACCESS  read-only
    STATUS  current
    DESCRIPTION
        "The lower 32 bit value of the total octets received and transmitted 
         out of the real server on a particular SP."
    ::= { slbStatSpRealServerEntry 5 }

slbStatSpRealServerHCOctetsHigh32 OBJECT-TYPE
    SYNTAX  Counter32
    MAX-ACCESS  read-only
    STATUS  current
    DESCRIPTION
        "The higher 32 bit value of the total octets received and transmitted 
         out of the real server on a particular SP."
    ::= { slbStatSpRealServerEntry 6 }

slbStatSpRealServerHCOctets OBJECT-TYPE
    SYNTAX  Counter64
    MAX-ACCESS  read-only
    STATUS  current
    DESCRIPTION
        "The total octets received and transmitted by the real server on a 
         particular SP."
    ::= { slbStatSpRealServerEntry 7 }

slbStatSpFltTable OBJECT-TYPE
    SYNTAX  SEQUENCE OF SlbStatSpFltEntry
    MAX-ACCESS  not-accessible
    STATUS  current
    DESCRIPTION
        "The filter statistics table.  This table shows the statistics 
         of filters for a particular SP.
         Note:This mib is not supported for VX instance of Virtualization."
    ::= { slbSpStats 4 }

slbStatSpFltEntry OBJECT-TYPE
    SYNTAX  SlbStatSpFltEntry
    MAX-ACCESS  not-accessible
    STATUS  current
    DESCRIPTION
        "A row in the filter statistics table."
    INDEX  { slbStatSpFltSpIndex, slbStatSpFltIndex }
    ::= { slbStatSpFltTable 1 }

SlbStatSpFltEntry ::= SEQUENCE {
    slbStatSpFltSpIndex               Integer32,
    slbStatSpFltIndex                 Integer32,
    slbStatSpFltFirings               Counter32,
    slbStatSpFltFiringsUnit           INTEGER,
    slbStatSpFltCurSess               Counter64,
    slbStatSpFltHighSess              Counter64,
    slbStatSpFltTotSess               Counter64,
    slbStatSpFltCurBand               Counter64,
    slbStatSpFltHighBand              Counter64,
    slbStatSpFltTotBand               Counter64,
    slbStatSpFltConnPerSec            Counter64
    }

slbStatSpFltSpIndex OBJECT-TYPE
    SYNTAX  Integer32
    MAX-ACCESS  read-only
    STATUS  current
    DESCRIPTION
        "The SP index."
    ::= { slbStatSpFltEntry 1 }

slbStatSpFltIndex OBJECT-TYPE 
    SYNTAX  Integer32 
    MAX-ACCESS  read-only
    STATUS  current 
    DESCRIPTION 
        "The filter number." 
    ::= { slbStatSpFltEntry 2 }

slbStatSpFltFirings OBJECT-TYPE 
    SYNTAX  Counter32 
    MAX-ACCESS  read-only
    STATUS  current 
    DESCRIPTION 
        "The number of instances that the received packet matches the 
         filter rule on this SP."
    ::= { slbStatSpFltEntry 3 }

slbStatSpFltFiringsUnit OBJECT-TYPE
    SYNTAX  INTEGER{
        sessions(1),
        requests(2),
        packets(3),
        unsupported(2147483647)
    }
    MAX-ACCESS  read-only
    STATUS  current
    DESCRIPTION
        "Unit of total hits for filter as sessions or requests or packets."
    ::= { slbStatSpFltEntry 4 }

slbStatSpFltCurSess OBJECT-TYPE
    SYNTAX  Counter64
    MAX-ACCESS  read-only
    STATUS  current
    DESCRIPTION
        "The current number of session for this filter on this SP."
    ::= { slbStatSpFltEntry 5 }

slbStatSpFltHighSess OBJECT-TYPE
    SYNTAX  Counter64
    MAX-ACCESS  read-only
    STATUS  current
    DESCRIPTION
        "The highest number of session for this filter on this SP."
    ::= { slbStatSpFltEntry 6 }

slbStatSpFltTotSess OBJECT-TYPE
    SYNTAX  Counter64
    MAX-ACCESS  read-only
    STATUS  current
    DESCRIPTION
        "The total number of session for this filter on this SP."
    ::= { slbStatSpFltEntry 7 }

slbStatSpFltCurBand OBJECT-TYPE
    SYNTAX  Counter64
    MAX-ACCESS  read-only
    STATUS  current
    DESCRIPTION
        "The current bandwidth for this filter in Kbps on this SP."
    ::= { slbStatSpFltEntry 8 }

slbStatSpFltHighBand OBJECT-TYPE
    SYNTAX  Counter64
    MAX-ACCESS  read-only
    STATUS  current
    DESCRIPTION
        "The highest bandwidth for this filter in Kbps on this SP."
    ::= { slbStatSpFltEntry 9 }

slbStatSpFltTotBand OBJECT-TYPE
    SYNTAX  Counter64
    MAX-ACCESS  read-only
    STATUS  current
    DESCRIPTION
        "The total bandwidth for this filter in Mb on this SP"
    ::= { slbStatSpFltEntry 10 }

slbStatSpFltConnPerSec OBJECT-TYPE
    SYNTAX  Counter64
    MAX-ACCESS  read-only
    STATUS  current
    DESCRIPTION
        "The connection per second for this filter on this SP"
    ::= { slbStatSpFltEntry 11 }

-- SLB Port Maintenance Statistics Table

slbStatSpMaintTable OBJECT-TYPE
    SYNTAX  SEQUENCE OF SlbStatSpMaintEntry
    MAX-ACCESS  not-accessible
    STATUS  current
    DESCRIPTION
        "The table of SLB SP maintenance statistics.
         Note:This mib is not supported for VX instance of Virtualization." 
    ::= { slbSpStats 5 }

slbStatSpMaintEntry OBJECT-TYPE
    SYNTAX  SlbStatSpMaintEntry
    MAX-ACCESS  not-accessible
    STATUS  current
    DESCRIPTION
        "A row in the SLB SP maintenance statistics table."
    INDEX   { slbStatSpMaintSpIndex }
    ::= { slbStatSpMaintTable 1 }
 
SlbStatSpMaintEntry ::= SEQUENCE {
    slbStatSpMaintSpIndex                   Integer32,
    slbStatSpMaintMaximumSessions           Integer32,
    slbStatSpMaintCurBindings               Gauge32,
    slbStatSpMaintCurBindings4Seconds       Gauge32,
    slbStatSpMaintCurBindings64Seconds      Gauge32,
    slbStatSpMaintTerminatedSessions        Counter32,
    slbStatSpMaintBindingFails              Counter32,
    slbStatSpMaintNonTcpFrames              Counter32,
    slbStatSpMaintTcpFragments              Counter32,
    slbStatSpMaintUdpDatagrams              Counter32,
    slbStatSpMaintIncorrectVIPs             Counter32,
    slbStatSpMaintIncorrectVports           Counter32,
    slbStatSpMaintRealServerNoAvails        Counter32,
    slbStatSpMaintFilteredDeniedFrames      Counter32,
    slbStatSpMaintLandAttacks		    Counter32,
    slbStatSpMaintIpFragTotalSessions	    Counter32,
    slbStatSpMaintIpFragCurSessions         Gauge32,
    slbStatSpMaintIpFragDiscards            Counter32,
    slbStatSpMaintIpFragTableFull           Counter32,
    slbStatSpMaintClear                     INTEGER,
    slbStatSpMaintOOSFinPktDrops            Counter32,
    slbStatSpMaintSymSessions		    Counter32,
    slbStatSpMaintSymValidSegments	    Counter32,
    slbStatSpMaintSymFragSessions	    Counter32,
    slbStatSpMaintSymSegAllocFails	    Counter32,
    slbStatSpMaintSymBufferAllocFails	    Counter32,	
    slbStatSpMaintSymConnAllocFails	    Counter32,
    slbStatSpMaintSymInvalidBuffers	    Counter32,
    slbStatSpMaintSymSegReallocFails	    Counter32,
    slbStatSpMaintSymPacketsIn		    Counter32,
    slbStatSpMaintSymPacketsWithNoData	    Counter32,
    slbStatSpMaintSymTcpPackets		    Counter32,
    slbStatSpMaintSymUdpPackets	            Counter32,
    slbStatSpMaintSymIcmpPackets	    Counter32,
    slbStatSpMaintSymOtherPackets	    Counter32,
    slbStatSpMaintSymMatchCount		    Counter32,
    slbStatSpMaintSymFetchErrors	    Counter32,
    slbStatSpMaintSymTruncPayloadToMp	    Counter32,
    slbStatSpMaintSymPacketsInFastPath	    Counter32,
    slbStatSpMaintPeakBindings		    Counter32,
    slbStatSpMaintCurAxBindings             Counter32,
    slbStatSpMaintCurAxBindings4Seconds     Counter32,
    slbStatSpMaintCurAxBindings64Seconds    Counter32,
    slbStatSpMaintPeakAxBindings		    Counter32
    }

slbStatSpMaintSpIndex OBJECT-TYPE
    SYNTAX  Integer32
    MAX-ACCESS  read-only
    STATUS  current
    DESCRIPTION
        "The SP number for which the statistics apply."
    ::= { slbStatSpMaintEntry 1 }

slbStatSpMaintMaximumSessions OBJECT-TYPE
    SYNTAX  Integer32
    MAX-ACCESS  read-only
    STATUS  current
    DESCRIPTION
        "The maximun number of entries per SP in the session table."
    ::= { slbStatSpMaintEntry 2 }

slbStatSpMaintCurBindings OBJECT-TYPE
    SYNTAX  Gauge32 
    MAX-ACCESS  read-only
    STATUS  current
    DESCRIPTION
        "The current number of sessions on the SP."
    ::= { slbStatSpMaintEntry 3 }

slbStatSpMaintCurBindings4Seconds OBJECT-TYPE
    SYNTAX  Gauge32 
    MAX-ACCESS  read-only
    STATUS  current
    DESCRIPTION
        "The 4 second average current number of sessions on the SP."
    ::= { slbStatSpMaintEntry 4 }

slbStatSpMaintCurBindings64Seconds OBJECT-TYPE
    SYNTAX  Gauge32 
    MAX-ACCESS  read-only
    STATUS  current
    DESCRIPTION
        "The 64 second average current number of sessions on the SP."
    ::= { slbStatSpMaintEntry 5 }

slbStatSpMaintTerminatedSessions OBJECT-TYPE
    SYNTAX  Counter32
    MAX-ACCESS  read-only
    STATUS  current
    DESCRIPTION
        "The count of the number of sessions closed because the server failed on the SP."
    ::= { slbStatSpMaintEntry 6 }

slbStatSpMaintBindingFails OBJECT-TYPE
    SYNTAX  Counter32
    MAX-ACCESS  read-only
    STATUS  current
    DESCRIPTION
        "The total number of binding failures on the SP. A binding failure 
         occurs when a SP runs out of session table entries."
    ::= { slbStatSpMaintEntry 7 }

slbStatSpMaintNonTcpFrames OBJECT-TYPE
    SYNTAX  Counter32
    MAX-ACCESS  read-only
    STATUS  current
    DESCRIPTION
        "The total number of non-TCP/IP frames dropped on the SP."
    ::= { slbStatSpMaintEntry 8 }

slbStatSpMaintTcpFragments OBJECT-TYPE
    SYNTAX  Counter32
    MAX-ACCESS  read-only
    STATUS  obsolete
    DESCRIPTION
        "The total number of TCP fragments dropped on the SP."
    ::= { slbStatSpMaintEntry 9 }

slbStatSpMaintUdpDatagrams OBJECT-TYPE
    SYNTAX  Counter32
    MAX-ACCESS  read-only
    STATUS  current
    DESCRIPTION
        "The total number of UDP datagrams dropped on the SP."
    ::= { slbStatSpMaintEntry 10 }

slbStatSpMaintIncorrectVIPs OBJECT-TYPE
    SYNTAX  Counter32
    MAX-ACCESS  read-only
    STATUS  current
    DESCRIPTION
        "The total number of frames with incorrect VIPs that are dropped on 
         the SP."
    ::= { slbStatSpMaintEntry 11 }

slbStatSpMaintIncorrectVports OBJECT-TYPE
    SYNTAX  Counter32
    MAX-ACCESS  read-only
    STATUS  current
    DESCRIPTION
        "The total number of frames with incorrect Virtual Port that are 
         dropped on the SP."
    ::= { slbStatSpMaintEntry 12 }

slbStatSpMaintRealServerNoAvails OBJECT-TYPE
    SYNTAX  Counter32
    MAX-ACCESS  read-only
    STATUS  current
    DESCRIPTION
        "The total number of frames that are dropped on the SP
	 because no real server is available."
    ::= { slbStatSpMaintEntry 13 }

slbStatSpMaintFilteredDeniedFrames OBJECT-TYPE
    SYNTAX  Counter32
    MAX-ACCESS  read-only
    STATUS  current
    DESCRIPTION
        "The total number of frames that are denied on the SP by the filter."
    ::= { slbStatSpMaintEntry 14 }

slbStatSpMaintLandAttacks OBJECT-TYPE
    SYNTAX  Counter32
    MAX-ACCESS  read-only
    STATUS  current
    DESCRIPTION
        "The total number of attacks on the SP that frames contain the same source
	 and destination IP addresses."
    ::= { slbStatSpMaintEntry 15 }

slbStatSpMaintIpFragTotalSessions OBJECT-TYPE
    SYNTAX  Counter32
    MAX-ACCESS  read-only
    STATUS  current
    DESCRIPTION
        "The total number of fragment sessions processed on the SP."
    ::= { slbStatSpMaintEntry 16 }

slbStatSpMaintIpFragCurSessions OBJECT-TYPE
    SYNTAX  Gauge32
    MAX-ACCESS  read-only
    STATUS  current
    DESCRIPTION
        "The number of sessions in the IP fragment binding table on the SP."
    ::= { slbStatSpMaintEntry 17 }

slbStatSpMaintIpFragDiscards OBJECT-TYPE
    SYNTAX  Counter32
    MAX-ACCESS  read-only
    STATUS  current
    DESCRIPTION
        "The total number of fragments discarded on the SP because there
         is no entry in the IP fragment binding table. "
    ::= { slbStatSpMaintEntry 18 }

slbStatSpMaintIpFragTableFull OBJECT-TYPE
    SYNTAX  Counter32
    MAX-ACCESS  read-only
    STATUS  current
    DESCRIPTION
        "The total number of times IP fragment binding table is full on the 
         SP."
    ::= { slbStatSpMaintEntry 19 }

slbStatSpMaintClear OBJECT-TYPE
    SYNTAX INTEGER {
	ok(1),
	clear(2),
        unsupported(2147483647)
	}
    MAX-ACCESS read-write
    STATUS current
    DESCRIPTION
        "This is an action object to clear the non-operational SLB statistics
         on the particular SP. 
         ok(1) is returned when read."
    ::= { slbStatSpMaintEntry 20 }

slbStatSpMaintOOSFinPktDrops OBJECT-TYPE
    SYNTAX  Counter32
    MAX-ACCESS  read-only
    STATUS  current
    DESCRIPTION
        "The total number of Out of state FIN Packets received on the SP."
    ::= { slbStatSpMaintEntry 21 }

-- START of Symantec SLB SP Maintenance Stats 
slbStatSpMaintSymSessions OBJECT-TYPE
    SYNTAX  Counter32
    MAX-ACCESS  read-only
    STATUS  current
    DESCRIPTION
        "Number of Symantec sessions."
    ::= { slbStatSpMaintEntry 22 }

slbStatSpMaintSymValidSegments OBJECT-TYPE
    SYNTAX  Counter32
    MAX-ACCESS  read-only
    STATUS  current
    DESCRIPTION
        "Number of Symantec valid segments."
    ::= { slbStatSpMaintEntry 23 }

slbStatSpMaintSymFragSessions OBJECT-TYPE
    SYNTAX  Counter32
    MAX-ACCESS  read-only
    STATUS  current
    DESCRIPTION
        "Number of Symantec fragment sessions."
    ::= { slbStatSpMaintEntry 24 }

slbStatSpMaintSymSegAllocFails OBJECT-TYPE
    SYNTAX  Counter32
    MAX-ACCESS  read-only
    STATUS  current
    DESCRIPTION
        "Number of Symantec segment allocation fails."
    ::= { slbStatSpMaintEntry 25 }

slbStatSpMaintSymBufferAllocFails OBJECT-TYPE
    SYNTAX  Counter32
    MAX-ACCESS  read-only
    STATUS  current
    DESCRIPTION
        "Number of Symantec buffers allocation fails."
    ::= { slbStatSpMaintEntry 26 }

slbStatSpMaintSymConnAllocFails OBJECT-TYPE
    SYNTAX  Counter32
    MAX-ACCESS  read-only
    STATUS  current
    DESCRIPTION
        "Number of Symantec Connection allocation fails."
    ::= { slbStatSpMaintEntry 27 }

slbStatSpMaintSymInvalidBuffers OBJECT-TYPE
    SYNTAX  Counter32
    MAX-ACCESS  read-only
    STATUS  current
    DESCRIPTION
        "Number of Symantec Invalid buffers."
    ::= { slbStatSpMaintEntry 28 }

slbStatSpMaintSymSegReallocFails OBJECT-TYPE
    SYNTAX  Counter32
    MAX-ACCESS  read-only
    STATUS  current
    DESCRIPTION
        "Number of Symantec Segment reallocation fails."
    ::= { slbStatSpMaintEntry 29 }

slbStatSpMaintSymPacketsIn OBJECT-TYPE
    SYNTAX  Counter32
    MAX-ACCESS  read-only
    STATUS  current
    DESCRIPTION
        "Symantec Deuce Inspection Stats - No. of packets in."
    ::= { slbStatSpMaintEntry 30 }

slbStatSpMaintSymPacketsWithNoData OBJECT-TYPE
    SYNTAX  Counter32
    MAX-ACCESS  read-only
    STATUS  current
    DESCRIPTION
        "Symantec Deuce Inspection Stats - No. of packets with no data."
    ::= { slbStatSpMaintEntry 31 }

slbStatSpMaintSymTcpPackets OBJECT-TYPE
    SYNTAX  Counter32
    MAX-ACCESS  read-only
    STATUS  current
    DESCRIPTION
        "Symantec Deuce Inspection Stats - No. of TCP packets"
    ::= { slbStatSpMaintEntry 32 }

slbStatSpMaintSymUdpPackets OBJECT-TYPE
    SYNTAX  Counter32
    MAX-ACCESS  read-only
    STATUS  current
    DESCRIPTION
        "Symantec Deuce Inspection Stats - No. of  UDP Packets"
    ::= { slbStatSpMaintEntry 33 }

slbStatSpMaintSymIcmpPackets OBJECT-TYPE
    SYNTAX  Counter32
    MAX-ACCESS  read-only
    STATUS  current
    DESCRIPTION
        "Symantec Deuce Inspection Stats - No. of  ICMP Packets"
    ::= { slbStatSpMaintEntry 34 }

slbStatSpMaintSymOtherPackets OBJECT-TYPE
    SYNTAX  Counter32
    MAX-ACCESS  read-only
    STATUS  current
    DESCRIPTION
        "Symantec Deuce Inspection Stats - No. of  Packets other than 
	 TCP UDP or ICMP"
    ::= { slbStatSpMaintEntry 35 }

slbStatSpMaintSymMatchCount OBJECT-TYPE
    SYNTAX  Counter32
    MAX-ACCESS  read-only
    STATUS  current
    DESCRIPTION
        "Symantec Deuce Inspection Stats - Match Count"
    ::= { slbStatSpMaintEntry 36 }

slbStatSpMaintSymFetchErrors OBJECT-TYPE
    SYNTAX  Counter32
    MAX-ACCESS  read-only
    STATUS  current
    DESCRIPTION
        "Symantec Deuce Inspection Stats - No. of Fetch Errors"
    ::= { slbStatSpMaintEntry 37 }

slbStatSpMaintSymTruncPayloadToMp OBJECT-TYPE
    SYNTAX  Counter32
    MAX-ACCESS  read-only
    STATUS  current
    DESCRIPTION
        "Symantec Deuce Inspection Stats - No. of Truncated payload to MP"
    ::= { slbStatSpMaintEntry 38 }

slbStatSpMaintSymPacketsInFastPath OBJECT-TYPE
    SYNTAX  Counter32
    MAX-ACCESS  read-only
    STATUS  current
    DESCRIPTION
        "Symantec Deuce Inspection Stats - No. of Packets in fast path"
    ::= { slbStatSpMaintEntry 39 }

slbStatSpMaintPeakBindings OBJECT-TYPE
    SYNTAX  Counter32
    MAX-ACCESS  read-only
    STATUS  current
    DESCRIPTION
        "The peak number of sessions on the SP."
    ::= { slbStatSpMaintEntry 40 }

slbStatSpMaintCurAxBindings OBJECT-TYPE
    SYNTAX  Counter32
    MAX-ACCESS  read-only
    STATUS  current
    DESCRIPTION
        "The current number of Ax sessions on the SP."
    ::= { slbStatSpMaintEntry 41 }

slbStatSpMaintCurAxBindings4Seconds OBJECT-TYPE
    SYNTAX  Counter32
    MAX-ACCESS  read-only
    STATUS  current
    DESCRIPTION
        "The 4 second average current number of Ax sessions on the SP."
    ::= { slbStatSpMaintEntry 42 }

slbStatSpMaintCurAxBindings64Seconds OBJECT-TYPE
    SYNTAX  Counter32
    MAX-ACCESS  read-only
    STATUS  current
    DESCRIPTION
        "The 64 second average current number of Ax sessions on the SP."
    ::= { slbStatSpMaintEntry 43 }

slbStatSpMaintPeakAxBindings OBJECT-TYPE
    SYNTAX  Counter32
    MAX-ACCESS  read-only
    STATUS  current
    DESCRIPTION
        "The peak number of Ax sessions on the SP."
    ::= { slbStatSpMaintEntry 44 }


-- END of Symantec SLB SP Maintenance Stats 

slbStatSpAuxSessTable OBJECT-TYPE
    SYNTAX  SEQUENCE OF SlbStatSpAuxSessEntry
    MAX-ACCESS  not-accessible
    STATUS  obsolete
    DESCRIPTION
        "The auxiliary session table statistics for a particular SP.
         Note:This mib is not supported for VX instance of Virtualization."
    ::= { slbSpStats 6 }

slbStatSpAuxSessEntry OBJECT-TYPE
    SYNTAX  SlbStatSpAuxSessEntry
    MAX-ACCESS  not-accessible
    STATUS  obsolete
    DESCRIPTION
        "The statistics of a particular auxiliary session table entry for a particular SP."
    INDEX   { slbStatSpAuxSessSpIndex, slbStatSpAuxSessIndex }
    ::= { slbStatSpAuxSessTable 1 }

SlbStatSpAuxSessEntry ::= SEQUENCE {
    slbStatSpAuxSessSpIndex             Integer32,
    slbStatSpAuxSessIndex               Integer32,
    slbStatSpAuxSessCurConn             Gauge32,
    slbStatSpAuxSessMaxConn             Integer32,
    slbStatSpAuxSessAllocFails          Counter32
    }

slbStatSpAuxSessSpIndex OBJECT-TYPE
    SYNTAX  Integer32
    MAX-ACCESS  read-only
    STATUS  obsolete
    DESCRIPTION
        "The SP number." 
    ::= { slbStatSpAuxSessEntry 1 }

slbStatSpAuxSessIndex OBJECT-TYPE
    SYNTAX  Integer32
    MAX-ACCESS  read-only
    STATUS  obsolete
    DESCRIPTION
        "The auxiliary session table number." 
    ::= { slbStatSpAuxSessEntry 2 }

slbStatSpAuxSessCurConn OBJECT-TYPE 
    SYNTAX  Gauge32
    MAX-ACCESS  read-only
    STATUS  obsolete
    DESCRIPTION 
        "The number of connections in this auxiliary sessions table on the SP."
    ::= { slbStatSpAuxSessEntry 3 }

slbStatSpAuxSessMaxConn OBJECT-TYPE 
    SYNTAX  Integer32 
    MAX-ACCESS  read-only
    STATUS  obsolete
    DESCRIPTION 
        "The maximum number of connections handled by this auxiliary session 
         table on the SP."
    ::= { slbStatSpAuxSessEntry 4 }

slbStatSpAuxSessAllocFails OBJECT-TYPE 
    SYNTAX  Counter32 
    MAX-ACCESS  read-only
    STATUS  obsolete
    DESCRIPTION 
        "The total number of allocation failures for this auxiliary session 
         table on the SP."
    ::= { slbStatSpAuxSessEntry 5 }

-- SLB SP Enhanced Real Servers Statistics Table

slbStatSpEnhRealServerTable OBJECT-TYPE
    SYNTAX  SEQUENCE OF SlbStatSpEnhRealServerEntry
    MAX-ACCESS  not-accessible
    STATUS  current
    DESCRIPTION
        "The sp-server statistics table.  This table shows the statistics
        of real servers for a particular SP.
        Note:This mib is not supported for VX instance of Virtualization."
    ::= { slbSpStats 7 }

slbStatSpEnhRealServerEntry OBJECT-TYPE
    SYNTAX  SlbStatSpEnhRealServerEntry
    MAX-ACCESS  not-accessible
    STATUS  current
    DESCRIPTION
        "A row in the sp-server statistics table.
         Note:This mib is not supported for VX instance of Virtualization."
    INDEX  { slbStatSpEnhRealServerSpIndex, slbStatSpEnhRealServerServerIndex }
    ::= { slbStatSpEnhRealServerTable 1 }

SlbStatSpEnhRealServerEntry ::= SEQUENCE {
        slbStatSpEnhRealServerSpIndex               Integer32,
        slbStatSpEnhRealServerServerIndex           DisplayString,
        slbStatSpEnhRealServerCurrSessions          Gauge32,
        slbStatSpEnhRealServerTotalSessions         Counter32,
        slbStatSpEnhRealServerHCOctetsLow32         Counter32,
        slbStatSpEnhRealServerHCOctetsHigh32        Counter32,
        slbStatSpEnhRealServerHCOctets              Counter64
    }

slbStatSpEnhRealServerSpIndex OBJECT-TYPE
    SYNTAX  Integer32
    MAX-ACCESS  read-only
    STATUS  current
    DESCRIPTION
        "The SP index."
    ::= { slbStatSpEnhRealServerEntry 1 }

slbStatSpEnhRealServerServerIndex OBJECT-TYPE
    SYNTAX  DisplayString  ( SIZE ( 1 .. 255  ) )
    MAX-ACCESS  read-only
    STATUS  current
    DESCRIPTION
        "The real server number that identifies the server."
    ::= { slbStatSpEnhRealServerEntry 2 }

slbStatSpEnhRealServerCurrSessions OBJECT-TYPE
    SYNTAX  Gauge32
    MAX-ACCESS  read-only
    STATUS  current
    DESCRIPTION
        "The current sessions for the real server."
    ::= { slbStatSpEnhRealServerEntry 3 }

slbStatSpEnhRealServerTotalSessions OBJECT-TYPE
    SYNTAX  Counter32
    MAX-ACCESS  read-only
    STATUS  current
    DESCRIPTION
        "The total number of sessions for the real server."
    ::= { slbStatSpEnhRealServerEntry 4 }

slbStatSpEnhRealServerHCOctetsLow32 OBJECT-TYPE
    SYNTAX  Counter32
    MAX-ACCESS  read-only
    STATUS  current
    DESCRIPTION
        "The lower 32 bit value of the total octets received and transmitted
         out of the real server on a particular SP."
    ::= { slbStatSpEnhRealServerEntry 5 }

slbStatSpEnhRealServerHCOctetsHigh32 OBJECT-TYPE
    SYNTAX  Counter32
    MAX-ACCESS  read-only
    STATUS  current
    DESCRIPTION
        "The higher 32 bit value of the total octets received and transmitted
         out of the real server on a particular SP."
    ::= { slbStatSpEnhRealServerEntry 6 }

slbStatSpEnhRealServerHCOctets OBJECT-TYPE
    SYNTAX  Counter64
    MAX-ACCESS  read-only
    STATUS  current
    DESCRIPTION
        "The total octets received and transmitted by the real server on a
         particular SP."
    ::= { slbStatSpEnhRealServerEntry 7 }

-- SLB SP filter real server stats per SP

slbStatSpFltRealTable OBJECT-TYPE
    SYNTAX  SEQUENCE OF SlbStatSpFltRealEntry
    MAX-ACCESS  not-accessible
    STATUS  current
    DESCRIPTION
        "The filter statistics table for real servers for a particular SP.
         Note:This mib is not supported for VX instance of Virtualization."
    ::= { slbSpStats 9 }

slbStatSpFltRealEntry OBJECT-TYPE
    SYNTAX  SlbStatSpFltRealEntry
    MAX-ACCESS  not-accessible
    STATUS  current
    DESCRIPTION
        "A row in filter statistics table according to real server.
         Note:This mib is not supported for VX instance of Virtualization."
    INDEX   { slbStatSpFltRealSpIndex, slbStatSpFltRealFltIndex, slbStatSpFltRealRealIndex }
    ::= { slbStatSpFltRealTable 1 }

SlbStatSpFltRealEntry ::= SEQUENCE {
    slbStatSpFltRealSpIndex      Integer32,
    slbStatSpFltRealFltIndex     Integer32,
    slbStatSpFltRealRealIndex    DisplayString,
    slbStatSpFltRealIPAddr       IpAddress,
    slbStatSpFltRealCurSess      Counter64,
    slbStatSpFltRealHighSess     Counter64,
    slbStatSpFltRealTotSess      Counter64,
    slbStatSpFltRealCurBand      Counter64,
    slbStatSpFltRealHighBand     Counter64,
    slbStatSpFltRealTotBand      Counter64,
    slbStatSpFltRealConnPerSec   Counter64
    }

slbStatSpFltRealSpIndex OBJECT-TYPE
    SYNTAX  Integer32
    MAX-ACCESS  read-only
    STATUS  current
    DESCRIPTION
        "The SP index."
    ::= { slbStatSpFltRealEntry 1 }

slbStatSpFltRealFltIndex OBJECT-TYPE
    SYNTAX  Integer32
    MAX-ACCESS  read-only
    STATUS  current
    DESCRIPTION
        "The number that identifies the filter."
    ::= { slbStatSpFltRealEntry 2 }

slbStatSpFltRealRealIndex OBJECT-TYPE
    SYNTAX  DisplayString (SIZE(1..255))
    MAX-ACCESS  read-only
    STATUS  current
    DESCRIPTION
        "The real server index."
    ::= { slbStatSpFltRealEntry 3 }

slbStatSpFltRealIPAddr OBJECT-TYPE
    SYNTAX  IpAddress
    MAX-ACCESS  read-only
    STATUS  current
    DESCRIPTION
        "IP address of the real server."
    ::= { slbStatSpFltRealEntry 4 }

slbStatSpFltRealCurSess OBJECT-TYPE
    SYNTAX  Counter64
    MAX-ACCESS  read-only
    STATUS  current
    DESCRIPTION
        "The current number of session for the real server on this SP."
    ::= { slbStatSpFltRealEntry 5 }

slbStatSpFltRealHighSess OBJECT-TYPE
    SYNTAX  Counter64
    MAX-ACCESS  read-only
    STATUS  current
    DESCRIPTION
        "The highest number of session for the real server on this SP."
    ::= { slbStatSpFltRealEntry 6 }

slbStatSpFltRealTotSess OBJECT-TYPE
    SYNTAX  Counter64
    MAX-ACCESS  read-only
    STATUS  current
    DESCRIPTION
        "The total number of session for the real server on this SP."
    ::= { slbStatSpFltRealEntry 7 }

slbStatSpFltRealCurBand OBJECT-TYPE
    SYNTAX  Counter64
    MAX-ACCESS  read-only
    STATUS  current
    DESCRIPTION
        "The current bandwidth for the real server in Kbps on this SP."
    ::= { slbStatSpFltRealEntry 8 }

slbStatSpFltRealHighBand OBJECT-TYPE
    SYNTAX  Counter64
    MAX-ACCESS  read-only
    STATUS  current
    DESCRIPTION
        "The highest bandwidth for the real server in Kbps on this SP."
    ::= { slbStatSpFltRealEntry 9 }

slbStatSpFltRealTotBand OBJECT-TYPE
    SYNTAX  Counter64
    MAX-ACCESS  read-only
    STATUS  current
    DESCRIPTION
        "The total bandwidth for the real server in Mb on this SP."
    ::= { slbStatSpFltRealEntry 10 }

slbStatSpFltRealConnPerSec OBJECT-TYPE
    SYNTAX  Counter64
    MAX-ACCESS  read-only
    STATUS  current
    DESCRIPTION
        "The connection per second for the real server on this SP."
    ::= { slbStatSpFltRealEntry 11 }

-- Filter Persistent session stats per SP
slbStatSpFltPsessTable OBJECT-TYPE
    SYNTAX  SEQUENCE OF SlbStatSpFltPsessEntry
    MAX-ACCESS  not-accessible
    STATUS  current
    DESCRIPTION
        "The filter persistent session statistics table.  This table shows the statistics
         of filters for a particular SP.
         Note:This mib is not supported for VX instance of Virtualization."
    ::= { slbSpStats 10 }

slbStatSpFltPsessEntry OBJECT-TYPE
    SYNTAX  SlbStatSpFltPsessEntry
    MAX-ACCESS  not-accessible
    STATUS  current
    DESCRIPTION
        "A row in the filter persistent session statistics table."
    INDEX  { slbStatSpFltSpIndex }
    ::= { slbStatSpFltPsessTable 1 }

SlbStatSpFltPsessEntry ::= SEQUENCE {
    slbStatSpFltPsessSpIndex             Integer32,
    slbStatSpFltPsessCur                 Counter64,
    slbStatSpFltPsessHigh                Counter64,
    slbStatSpFltPsessTotal               Counter64
    }

slbStatSpFltPsessSpIndex OBJECT-TYPE
    SYNTAX  Integer32
    MAX-ACCESS  read-only
    STATUS  current
    DESCRIPTION
        "The SP index."
    ::= { slbStatSpFltPsessEntry 1 }

slbStatSpFltPsessCur OBJECT-TYPE
    SYNTAX  Counter64
    MAX-ACCESS  read-only
    STATUS  current
    DESCRIPTION
        "The current number of persistent session for filters on this SP."
    ::= { slbStatSpFltPsessEntry 2 }

slbStatSpFltPsessHigh OBJECT-TYPE
    SYNTAX  Counter64
    MAX-ACCESS  read-only
    STATUS  current
    DESCRIPTION
        "The hightest number of persistent session for filters on this SP."
    ::= { slbStatSpFltPsessEntry 3 }

slbStatSpFltPsessTotal OBJECT-TYPE
    SYNTAX  Counter64
    MAX-ACCESS  read-only
    STATUS  current
    DESCRIPTION
        "The total number of persistent session for filters on this SP."
    ::= { slbStatSpFltPsessEntry 4 }


-- Virtual Server Persistent session stats per SP
slbStatSpVServerTable OBJECT-TYPE
    SYNTAX  SEQUENCE OF SlbStatSpVServerEntry
    MAX-ACCESS  not-accessible
    STATUS  current
    DESCRIPTION
        "The virtual server statistics table. This table shows the statistics
        of virtual server for a particular SP.
        Note:This mib is not supported for VX instance of Virtualization."
    ::= { slbSpStats 11 }

slbStatSpVServerEntry OBJECT-TYPE
    SYNTAX  SlbStatSpVServerEntry
    MAX-ACCESS  not-accessible
    STATUS  current
    DESCRIPTION
        "A row in the sp virtual server statistics table."
    INDEX   { slbStatSpVServerSpIndex, slbStatSpVServerIndex }
    ::= { slbStatSpVServerTable 1 }

SlbStatSpVServerEntry ::= SEQUENCE {
    slbStatSpVServerSpIndex                 Integer32,
    slbStatSpVServerIndex                   DisplayString,
    slbStatSpVServerCurrPSessions           Counter64,
    slbStatSpVServerTotalPSessions          Counter64,
    slbStatSpVServerHighestPSessions        Counter64
    }

slbStatSpVServerSpIndex OBJECT-TYPE
    SYNTAX  Integer32
    MAX-ACCESS  read-only
    STATUS  current
    DESCRIPTION
        "The SP index." 
    ::= { slbStatSpVServerEntry 1 }

slbStatSpVServerIndex OBJECT-TYPE
    SYNTAX  DisplayString (SIZE(1..255))
    MAX-ACCESS  read-only
    STATUS  current
    DESCRIPTION
        "The virtual server number that identifies the server."
    ::= { slbStatSpVServerEntry 2 }

slbStatSpVServerCurrPSessions OBJECT-TYPE
    SYNTAX  Counter64
    MAX-ACCESS  read-only
    STATUS  current
    DESCRIPTION
        "The number of persistent sessions that are currently handled by the
         virtual server on this SP."
    ::= { slbStatSpVServerEntry 3 }

slbStatSpVServerTotalPSessions OBJECT-TYPE
    SYNTAX  Counter64
    MAX-ACCESS  read-only
    STATUS  current
    DESCRIPTION
        "The total number of persistent sessions that are handled by the
        virtual server on this SP."
    ::= { slbStatSpVServerEntry 4 }

slbStatSpVServerHighestPSessions OBJECT-TYPE
    SYNTAX  Counter64
    MAX-ACCESS  read-only
    STATUS  current
    DESCRIPTION
        "The highest number of persistent sessions that have been handled
        by the virtual server on this SP."
    ::= { slbStatSpVServerEntry 5 }


-- SLB Real Servers Statistics Table

slbStatRServerTable OBJECT-TYPE
    SYNTAX  SEQUENCE OF SlbStatRServerEntry
    MAX-ACCESS  not-accessible
    STATUS  current
    DESCRIPTION
        "The real server statistics table.
         Note:This mib is not supported for VX instance of Virtualization."
    ::= { layer4Stats 2 }

slbStatRServerEntry OBJECT-TYPE
    SYNTAX  SlbStatRServerEntry
    MAX-ACCESS  not-accessible
    STATUS  current
    DESCRIPTION
        "The statistics of a particular real server."
    INDEX   { slbStatRServerIndex }
    ::= { slbStatRServerTable 1 }

SlbStatRServerEntry ::= SEQUENCE {
    slbStatRServerIndex               Integer32,
    slbStatRServerCurrSessions        Gauge32,
    slbStatRServerTotalSessions       Counter32,
    slbStatRServerFailures            Counter32,
    slbStatRServerHighestSessions     Counter32,
    slbStatRServerHCOctetsLow32       Counter32,
    slbStatRServerHCOctetsHigh32      Counter32,
    slbStatRServerHCOctets            Counter64,
    slbStatRServerUpTime              DisplayString,
    slbStatRServerDownTime            DisplayString,
    slbStatRServerLastFailureTime     DisplayString
    }

slbStatRServerIndex OBJECT-TYPE
    SYNTAX  Integer32
    MAX-ACCESS  read-only
    STATUS  current
    DESCRIPTION
        "The real server number that identifies the server." 
    ::= { slbStatRServerEntry 1 }

slbStatRServerCurrSessions OBJECT-TYPE 
    SYNTAX  Gauge32
    MAX-ACCESS  read-only
    STATUS  current 
    DESCRIPTION 
        "The number of sessions that are currently handled by the real server."
    ::= { slbStatRServerEntry 2 }

slbStatRServerTotalSessions OBJECT-TYPE 
    SYNTAX  Counter32 
    MAX-ACCESS  read-only
    STATUS  current 
    DESCRIPTION 
        "The total number of sessions that are handled by the real server."
    ::= { slbStatRServerEntry 3 }

slbStatRServerFailures OBJECT-TYPE 
    SYNTAX  Counter32 
    MAX-ACCESS  read-only
    STATUS  current 
    DESCRIPTION 
        "The total number of times that the real server is claimed down."
    ::= { slbStatRServerEntry 4 }

slbStatRServerHighestSessions OBJECT-TYPE 
    SYNTAX  Counter32 
    MAX-ACCESS  read-only
    STATUS  current 
    DESCRIPTION 
        "The highest sessions that have been handled by the real server."
    ::= { slbStatRServerEntry 5 }

slbStatRServerHCOctetsLow32 OBJECT-TYPE
    SYNTAX  Counter32
    MAX-ACCESS  read-only
    STATUS  current
    DESCRIPTION
        "The lower 32 bit value of octets received and transmitted out of the 
         real server."
    ::= { slbStatRServerEntry 6 }

slbStatRServerHCOctetsHigh32 OBJECT-TYPE
    SYNTAX  Counter32
    MAX-ACCESS  read-only
    STATUS  current
    DESCRIPTION
        "The higher 32 bit value of octets received and transmitted out
         of the real server."
    ::= { slbStatRServerEntry 7 }

slbStatRServerHCOctets OBJECT-TYPE
    SYNTAX  Counter64
    MAX-ACCESS  read-only
    STATUS  current
    DESCRIPTION
        "The total number of octets received and transmitted by the real 
         server."
    ::= { slbStatRServerEntry 8 }

slbStatRServerUpTime OBJECT-TYPE
    SYNTAX  DisplayString (SIZE(0..127))
    MAX-ACCESS  read-only
    STATUS  current
    DESCRIPTION
        "The total up time of the real server."
    ::= { slbStatRServerEntry 9 }

slbStatRServerDownTime OBJECT-TYPE
    SYNTAX  DisplayString (SIZE(0..127))
    MAX-ACCESS  read-only
    STATUS  current
    DESCRIPTION
        "The total down time of the real server."
    ::= { slbStatRServerEntry 10 }

slbStatRServerLastFailureTime OBJECT-TYPE
    SYNTAX  DisplayString (SIZE(0..127))
    MAX-ACCESS  read-only
    STATUS  current
    DESCRIPTION
        "The time-stamp when the last failure of the real server occured."
    ::= { slbStatRServerEntry 11 }

-- Real Server Rport Health Check Stats Table
slbStatRServerRportHCTable OBJECT-TYPE
    SYNTAX  SEQUENCE OF SlbStatRServerRportHCEntry
    MAX-ACCESS  not-accessible
    STATUS  current
    DESCRIPTION
        "The table of real server rport run-time health check statistics.
         Note:This mib is not supported for VX instance of Virtualization."
    ::= { layer4Stats 28 }

slbStatRServerRportHCEntry OBJECT-TYPE
    SYNTAX  SlbStatRServerRportHCEntry
    MAX-ACCESS  not-accessible
    STATUS  current
    DESCRIPTION
        "A row in the real server rport health check statistics table."
    INDEX   { slbStatRServerRportHCRealIndex, slbStatRServerRportHCServIndex  }
    ::= { slbStatRServerRportHCTable 1 }
 
SlbStatRServerRportHCEntry ::= SEQUENCE {
    slbStatRServerRportHCRealIndex         Integer32,
    slbStatRServerRportHCServIndex         Integer32,
    slbStatRServerRportHCId                DisplayString,
    slbStatRServerRportHCType              DisplayString,
    slbStatRServerRportHCStatus            INTEGER,
    slbStatRServerRportHCUptime            DisplayString,
    slbStatRServerRportHCDowntime          DisplayString,
    slbStatRServerRportHCLastValidTime     DisplayString,
    slbStatRServerRportHCAvgRespTime       Integer32,
    slbStatRServerRportHCPeakRespTime      Integer32,
    slbStatRServerRportHCLastValidRespTime Integer32,
    slbStatRServerRportHCFailureCount      Integer32
    }

slbStatRServerRportHCRealIndex OBJECT-TYPE
    SYNTAX  Integer32
    MAX-ACCESS  read-only
    STATUS  current
    DESCRIPTION
        "The real server index" 
    ::= { slbStatRServerRportHCEntry 1 }

slbStatRServerRportHCServIndex OBJECT-TYPE
    SYNTAX  Integer32
    MAX-ACCESS  read-only
    STATUS  current
    DESCRIPTION
        "The real server service index" 
    ::= { slbStatRServerRportHCEntry 2 }

slbStatRServerRportHCId OBJECT-TYPE
    SYNTAX DisplayString (SIZE(0..32))
    MAX-ACCESS  read-only
    STATUS  current
    DESCRIPTION
        "The real server runtime instance health check ID" 
    ::= { slbStatRServerRportHCEntry 3 }

slbStatRServerRportHCType OBJECT-TYPE
    SYNTAX DisplayString (SIZE(0..32))
    MAX-ACCESS  read-only
    STATUS  current
    DESCRIPTION
        "The real server runtime instance health check type"
    ::= { slbStatRServerRportHCEntry 4 }

slbStatRServerRportHCStatus OBJECT-TYPE
    SYNTAX  INTEGER {
        up(1),
        failed(2),
        blocked(3),
        overflow(4),
        disabled(5),
        unsupported(2147483647)
    } 
    MAX-ACCESS  read-only
    STATUS  current 
    DESCRIPTION
        "The real server runtime instance health check status"
    ::= { slbStatRServerRportHCEntry 5 }

slbStatRServerRportHCUptime OBJECT-TYPE
    SYNTAX  DisplayString (SIZE(0..127))
    MAX-ACCESS  read-only
    STATUS  current
    DESCRIPTION
        "The total up time of the real server health check instance."
    ::= { slbStatRServerRportHCEntry 6 }

slbStatRServerRportHCDowntime OBJECT-TYPE
    SYNTAX  DisplayString (SIZE(0..127))
    MAX-ACCESS read-only
    STATUS current
    DESCRIPTION
        "The total down time of the real server health check instance."
    ::= { slbStatRServerRportHCEntry 7 }	

slbStatRServerRportHCLastValidTime OBJECT-TYPE
    SYNTAX  DisplayString (SIZE(0..127))
    MAX-ACCESS read-only
    STATUS current
    DESCRIPTION
        "The timestamp when the last valid response of the real server
         health check instance was received."
    ::= { slbStatRServerRportHCEntry 8 }	

slbStatRServerRportHCAvgRespTime OBJECT-TYPE
    SYNTAX  Integer32
    MAX-ACCESS read-only
    STATUS current
    DESCRIPTION
        "The average response time of the health check for the real server instance."
    ::= { slbStatRServerRportHCEntry 9 }	

slbStatRServerRportHCPeakRespTime OBJECT-TYPE
    SYNTAX  Integer32
    MAX-ACCESS read-only
    STATUS current
    DESCRIPTION
        "The peak response time of the health check for the real server instance."
    ::= { slbStatRServerRportHCEntry 10 }	

slbStatRServerRportHCLastValidRespTime OBJECT-TYPE
    SYNTAX  Integer32
    MAX-ACCESS read-only
    STATUS current
    DESCRIPTION
        "The last valid response time of the health check for the real server instance."
    ::= { slbStatRServerRportHCEntry 11 }	

slbStatRServerRportHCFailureCount OBJECT-TYPE
    SYNTAX  Integer32
    MAX-ACCESS read-only
    STATUS current
    DESCRIPTION
        "The total number of times the real server health check instance state changed to FAILED."
    ::= { slbStatRServerRportHCEntry 12 }	

-- SLB Real Server Groups (alphanumeric key indexed) Statistics Table

slbStatEnhGroupTable OBJECT-TYPE
    SYNTAX  SEQUENCE OF SlbStatEnhGroupEntry
    MAX-ACCESS  not-accessible
    STATUS  current
    DESCRIPTION
        "The real server group statistics table.
         Note:This mib is not supported for VX instance of Virtualization."
    ::= { layer4Stats 29 }

slbStatEnhGroupEntry OBJECT-TYPE
    SYNTAX  SlbStatEnhGroupEntry
    MAX-ACCESS  not-accessible
    STATUS  current
    DESCRIPTION
        "The statistics of a particular real server group."
    INDEX   { slbStatEnhGroupIndex }
    ::= { slbStatEnhGroupTable 1 }

SlbStatEnhGroupEntry ::= SEQUENCE {
    slbStatEnhGroupIndex               DisplayString,
    slbStatEnhGroupCurrSessions        Gauge32,
    slbStatEnhGroupTotalSessions       Counter32,
    slbStatEnhGroupHighestSessions     Counter32,
    slbStatEnhGroupHCOctetsLow32       Counter32,
    slbStatEnhGroupHCOctetsHigh32      Counter32,
    slbStatEnhGroupWlmUpdates          Counter32,
    slbStatEnhGroupHCOctets            Counter64
    }

slbStatEnhGroupIndex OBJECT-TYPE
    SYNTAX DisplayString (SIZE(1..255))
    MAX-ACCESS  read-only
    STATUS  current
    DESCRIPTION
        "The real server group number that identifies the group."
    ::= { slbStatEnhGroupEntry 1 }

slbStatEnhGroupCurrSessions OBJECT-TYPE
    SYNTAX  Gauge32
    MAX-ACCESS  read-only
    STATUS  current
    DESCRIPTION
        "The number of sessions that are currently handled by the real server
         group."
    ::= { slbStatEnhGroupEntry 2 }

slbStatEnhGroupTotalSessions OBJECT-TYPE
    SYNTAX  Counter32
    MAX-ACCESS  read-only
    STATUS  current
    DESCRIPTION
        "The total number of sessions that are handled by the real
         server group."
    ::= { slbStatEnhGroupEntry 3 }

slbStatEnhGroupHighestSessions OBJECT-TYPE
    SYNTAX  Counter32
    MAX-ACCESS  read-only
    STATUS  current
    DESCRIPTION
        "The highest sessions that have been handled by the real server group."
    ::= { slbStatEnhGroupEntry 4 }

slbStatEnhGroupHCOctetsLow32 OBJECT-TYPE
    SYNTAX  Counter32
    MAX-ACCESS  read-only
    STATUS  current
    DESCRIPTION
        "The lower 32 bit value of octets received and transmitted out of the
         real server group."
    ::= { slbStatEnhGroupEntry 5 }

slbStatEnhGroupHCOctetsHigh32 OBJECT-TYPE
    SYNTAX  Counter32
    MAX-ACCESS  read-only
    STATUS  current
    DESCRIPTION
        "The higher 32 bit value of octets received and transmitted out
         of the real server group."
    ::= { slbStatEnhGroupEntry 6 }

slbStatEnhGroupHCOctets OBJECT-TYPE
    SYNTAX  Counter64
    MAX-ACCESS  read-only
    STATUS  current
    DESCRIPTION
        "The total octets received and transmitted by the real server group."
    ::= { slbStatEnhGroupEntry 7 }

slbStatEnhGroupWlmUpdates OBJECT-TYPE
    SYNTAX  Counter32
    MAX-ACCESS  read-only
    STATUS  current
    DESCRIPTION
        "Total weight updates from work load manager."
    ::= { slbStatEnhGroupEntry 8 }

-- SLB Real Servers Statistics Enhanced Table

slbStatEnhRServerTable OBJECT-TYPE
    SYNTAX  SEQUENCE OF SlbStatEnhRServerEntry
    MAX-ACCESS  not-accessible
    STATUS  current
    DESCRIPTION
        "The real server statistics table.
         Note:This mib is not supported for VX instance of Virtualization."
    ::= { layer4Stats 30 }

slbStatEnhRServerEntry OBJECT-TYPE
    SYNTAX  SlbStatEnhRServerEntry
    MAX-ACCESS  not-accessible
    STATUS  current
    DESCRIPTION
        "The statistics of a particular real server."
    INDEX   { slbStatEnhRServerIndex }
    ::= { slbStatEnhRServerTable 1 }

SlbStatEnhRServerEntry ::= SEQUENCE {
    slbStatEnhRServerIndex               DisplayString,
    slbStatEnhRServerCurrSessions        Gauge32,
    slbStatEnhRServerTotalSessions       Counter32,
    slbStatEnhRServerFailures            Counter32,
    slbStatEnhRServerHighestSessions     Counter32,
    slbStatEnhRServerHCOctetsLow32       Counter32,
    slbStatEnhRServerHCOctetsHigh32      Counter32,
    slbStatEnhRServerHCOctets            Counter64
}

slbStatEnhRServerIndex OBJECT-TYPE
    SYNTAX  DisplayString (SIZE(1..255))
    MAX-ACCESS  read-only
    STATUS  current
    DESCRIPTION
        "The real server index that identifies the server." 
    ::= { slbStatEnhRServerEntry 1 }

slbStatEnhRServerCurrSessions OBJECT-TYPE 
    SYNTAX  Gauge32
    MAX-ACCESS  read-only
    STATUS  current 
    DESCRIPTION 
        "The number of sessions that are currently handled by the real server."
    ::= { slbStatEnhRServerEntry 2 }

slbStatEnhRServerTotalSessions OBJECT-TYPE 
    SYNTAX  Counter32 
    MAX-ACCESS  read-only
    STATUS  current 
    DESCRIPTION 
        "The total number of sessions that are handled by the real server."
    ::= { slbStatEnhRServerEntry 3 }

slbStatEnhRServerFailures OBJECT-TYPE 
    SYNTAX  Counter32 
    MAX-ACCESS  read-only
    STATUS  current 
    DESCRIPTION 
        "The total number of times that the real server is claimed down."
    ::= { slbStatEnhRServerEntry 4 }

slbStatEnhRServerHighestSessions OBJECT-TYPE 
    SYNTAX  Counter32 
    MAX-ACCESS  read-only
    STATUS  current 
    DESCRIPTION 
        "The highest sessions that have been handled by the real server."
    ::= { slbStatEnhRServerEntry 5 }

slbStatEnhRServerHCOctetsLow32 OBJECT-TYPE
    SYNTAX  Counter32
    MAX-ACCESS  read-only
    STATUS  current
    DESCRIPTION
        "The lower 32 bit value of octets received and transmitted out of the 
         real server."
    ::= { slbStatEnhRServerEntry 6 }

slbStatEnhRServerHCOctetsHigh32 OBJECT-TYPE
    SYNTAX  Counter32
    MAX-ACCESS  read-only
    STATUS  current
    DESCRIPTION
        "The higher 32 bit value of octets received and transmitted out
         of the real server."
    ::= { slbStatEnhRServerEntry 7 }

slbStatEnhRServerHCOctets OBJECT-TYPE
    SYNTAX  Counter64
    MAX-ACCESS  read-only
    STATUS  current
    DESCRIPTION
        "The total number of octets received and transmitted by the real 
         server."
    ::= { slbStatEnhRServerEntry 8 }

-- Real Server Rport Health Check Stats Table
slbStatEnhRServerRportHCTable OBJECT-TYPE
    SYNTAX  SEQUENCE OF SlbStatEnhRServerRportHCEntry
    MAX-ACCESS  not-accessible
    STATUS  current
    DESCRIPTION
        "The table of real server rport run-time health check statistics.
         Note:This mib is not supported for VX instance of Virtualization."
    ::= { layer4Stats 31 }

slbStatEnhRServerRportHCEntry OBJECT-TYPE
    SYNTAX  SlbStatEnhRServerRportHCEntry
    MAX-ACCESS  not-accessible
    STATUS  current
    DESCRIPTION
        "A row in the real server rport health check statistics table."
    INDEX   { slbStatEnhRServerRportHCRealIndex, slbStatEnhRServerRportHCServIndex  }
    ::= { slbStatEnhRServerRportHCTable 1 }

SlbStatEnhRServerRportHCEntry ::= SEQUENCE {
    slbStatEnhRServerRportHCRealIndex         DisplayString,
    slbStatEnhRServerRportHCServIndex         Integer32,
    slbStatEnhRServerRportHCId                DisplayString,
    slbStatEnhRServerRportHCType              DisplayString,
    slbStatEnhRServerRportHCStatus            INTEGER,
    slbStatEnhRServerRportHCUptime            DisplayString,
    slbStatEnhRServerRportHCDowntime          DisplayString,
    slbStatEnhRServerRportHCLastValidTime     DisplayString,
    slbStatEnhRServerRportHCAvgRespTime       Integer32,
    slbStatEnhRServerRportHCPeakRespTime      Integer32,
    slbStatEnhRServerRportHCLastValidRespTime Integer32,
    slbStatEnhRServerRportHCFailureCount      Integer32
}

slbStatEnhRServerRportHCRealIndex OBJECT-TYPE
    SYNTAX  DisplayString (SIZE(1..255))
    MAX-ACCESS  read-only
    STATUS  current
    DESCRIPTION
        "The real server index" 
    ::= { slbStatEnhRServerRportHCEntry 1 }

slbStatEnhRServerRportHCServIndex OBJECT-TYPE
    SYNTAX  Integer32
    MAX-ACCESS  read-only
    STATUS  current
    DESCRIPTION
        "The real server service index" 
    ::= { slbStatEnhRServerRportHCEntry 2 }

slbStatEnhRServerRportHCId OBJECT-TYPE
    SYNTAX DisplayString (SIZE(0..32))
    MAX-ACCESS  read-only
    STATUS  current
    DESCRIPTION
        "The real server runtime instance health check ID" 
    ::= { slbStatEnhRServerRportHCEntry 3 }

slbStatEnhRServerRportHCType OBJECT-TYPE
    SYNTAX DisplayString (SIZE(0..32))
    MAX-ACCESS  read-only
    STATUS  current
    DESCRIPTION
        "The real server runtime instance health check type"
    ::= { slbStatEnhRServerRportHCEntry 4 }

slbStatEnhRServerRportHCStatus OBJECT-TYPE
    SYNTAX  INTEGER {
        up(1),
        failed(2),
        blocked(3),
        overflow(4),
        disabled(5),
        unsupported(2147483647)
    } 
    MAX-ACCESS  read-only
    STATUS  current 
    DESCRIPTION
        "The real server runtime instance health check status"
    ::= { slbStatEnhRServerRportHCEntry 5 }

slbStatEnhRServerRportHCUptime OBJECT-TYPE
    SYNTAX  DisplayString (SIZE(0..127))
    MAX-ACCESS  read-only
    STATUS  current
    DESCRIPTION
        "The total up time of the real server health check instance."
    ::= { slbStatEnhRServerRportHCEntry 6 }

slbStatEnhRServerRportHCDowntime OBJECT-TYPE
    SYNTAX  DisplayString (SIZE(0..127))
    MAX-ACCESS read-only
    STATUS current
    DESCRIPTION
        "The total down time of the real server health check instance."
    ::= { slbStatEnhRServerRportHCEntry 7 }    

slbStatEnhRServerRportHCLastValidTime OBJECT-TYPE
    SYNTAX  DisplayString (SIZE(0..127))
    MAX-ACCESS read-only
    STATUS current
    DESCRIPTION
        "The timestamp when the last valid response of the real server
         health check instance was received."
    ::= { slbStatEnhRServerRportHCEntry 8 }   

slbStatEnhRServerRportHCAvgRespTime OBJECT-TYPE
    SYNTAX  Integer32
    MAX-ACCESS read-only
    STATUS current
    DESCRIPTION
        "The average response time of the health check for the real server instance."
    ::= { slbStatEnhRServerRportHCEntry 9 }   

slbStatEnhRServerRportHCPeakRespTime OBJECT-TYPE
    SYNTAX  Integer32
    MAX-ACCESS read-only
    STATUS current
    DESCRIPTION
        "The peak response time of the health check for the real server instance."
    ::= { slbStatEnhRServerRportHCEntry 10 }  

slbStatEnhRServerRportHCLastValidRespTime OBJECT-TYPE
    SYNTAX  Integer32
    MAX-ACCESS read-only
    STATUS current
    DESCRIPTION
        "The last valid response time of the health check for the real server instance."
    ::= { slbStatEnhRServerRportHCEntry 11 }  

slbStatEnhRServerRportHCFailureCount OBJECT-TYPE
    SYNTAX  Integer32
    MAX-ACCESS read-only
    STATUS current
    DESCRIPTION
        "The total number of times the real server health check instance state changed to FAILED."
    ::= { slbStatEnhRServerRportHCEntry 12 }  

	
-- SLB Real Server Groups Statistics Table

slbStatGroupTable OBJECT-TYPE
    SYNTAX  SEQUENCE OF SlbStatGroupEntry
    MAX-ACCESS  not-accessible
    STATUS  current
    DESCRIPTION
        "The real server group statistics table.
         Note:This mib is not supported for VX instance of Virtualization."
    ::= { layer4Stats 3 }

slbStatGroupEntry OBJECT-TYPE
    SYNTAX  SlbStatGroupEntry
    MAX-ACCESS  not-accessible
    STATUS  current
    DESCRIPTION
        "The statistics of a particular real server group."
    INDEX   { slbStatGroupIndex }
    ::= { slbStatGroupTable 1 }

SlbStatGroupEntry ::= SEQUENCE {
    slbStatGroupIndex               Integer32,
    slbStatGroupCurrSessions        Gauge32,
    slbStatGroupTotalSessions       Counter32,
    slbStatGroupHighestSessions     Counter32,
    slbStatGroupHCOctetsLow32       Counter32,
    slbStatGroupHCOctetsHigh32      Counter32,
    slbStatGroupWlmUpdates          Counter32, 
    slbStatGroupHCOctets            Counter64
    }

slbStatGroupIndex OBJECT-TYPE
    SYNTAX  Integer32
    MAX-ACCESS  read-only
    STATUS  current
    DESCRIPTION
        "The real server group number that identifies the group." 
    ::= { slbStatGroupEntry 1 }

slbStatGroupCurrSessions OBJECT-TYPE 
    SYNTAX  Gauge32
    MAX-ACCESS  read-only
    STATUS  current 
    DESCRIPTION 
        "The number of sessions that are currently handled by the real server 
         group."
    ::= { slbStatGroupEntry 2 }

slbStatGroupTotalSessions OBJECT-TYPE 
    SYNTAX  Counter32 
    MAX-ACCESS  read-only
    STATUS  current 
    DESCRIPTION 
        "The total number of sessions that are handled by the real 
         server group."
    ::= { slbStatGroupEntry 3 }

slbStatGroupHighestSessions OBJECT-TYPE 
    SYNTAX  Counter32 
    MAX-ACCESS  read-only
    STATUS  current 
    DESCRIPTION 
        "The highest sessions that have been handled by the real server group."
    ::= { slbStatGroupEntry 4 }

slbStatGroupHCOctetsLow32 OBJECT-TYPE
    SYNTAX  Counter32
    MAX-ACCESS  read-only
    STATUS  current
    DESCRIPTION
        "The lower 32 bit value of octets received and transmitted out of the 
         real server group."
    ::= { slbStatGroupEntry 5 }

slbStatGroupHCOctetsHigh32 OBJECT-TYPE
    SYNTAX  Counter32
    MAX-ACCESS  read-only
    STATUS  current
    DESCRIPTION
        "The higher 32 bit value of octets received and transmitted out
         of the real server group."
    ::= { slbStatGroupEntry 6 }

slbStatGroupHCOctets OBJECT-TYPE
    SYNTAX  Counter64
    MAX-ACCESS  read-only
    STATUS  current
    DESCRIPTION
        "The total octets received and transmitted by the real server group."
    ::= { slbStatGroupEntry 7 }

slbStatGroupWlmUpdates OBJECT-TYPE
    SYNTAX  Counter32
    MAX-ACCESS  read-only
    STATUS  current
    DESCRIPTION
        "Total weight updates from work load manager."
    ::= { slbStatGroupEntry 8 } 

-- SLB Virtual Server Statistics Table

slbStatVServerTable OBJECT-TYPE
    SYNTAX  SEQUENCE OF SlbStatVServerEntry
    MAX-ACCESS  not-accessible
    STATUS  current
    DESCRIPTION
        "The virtual server statistics table.
         Note:This mib is not supported for VX instance of Virtualization."
    ::= { layer4Stats 4 }

slbStatVServerEntry OBJECT-TYPE
    SYNTAX  SlbStatVServerEntry
    MAX-ACCESS  not-accessible
    STATUS  current
    DESCRIPTION
        "The statistics of a particular virtual server group."
    INDEX   { slbStatVServerIndex }
    ::= { slbStatVServerTable 1 }

SlbStatVServerEntry ::= SEQUENCE {
    slbStatVServerIndex                   Integer32,
    slbStatVServerCurrSessions            Gauge32,
    slbStatVServerTotalSessions           Counter32,
    slbStatVServerHighestSessions         Counter32,
    slbStatVServerHCOctetsLow32           Counter32,
    slbStatVServerHCOctetsHigh32          Counter32,
    slbStatVServerHeaderHits              Counter32,
    slbStatVServerHeaderMisses            Counter32,
    slbStatVServerHeaderTotalSessions     Counter32,
    slbStatVServerCookieRewrites          Counter32,
    slbStatVServerCookieInserts           Counter32,
    slbStatVServerHCOctets                Counter64,
    slbStatVServerIpAddress               DisplayString 
    }

slbStatVServerIndex OBJECT-TYPE
    SYNTAX  Integer32
    MAX-ACCESS  read-only
    STATUS  current
    DESCRIPTION
        "The virtual server number that identifies the server." 
    ::= { slbStatVServerEntry 1 }

slbStatVServerCurrSessions OBJECT-TYPE 
    SYNTAX  Gauge32
    MAX-ACCESS  read-only
    STATUS  current 
    DESCRIPTION 
        "The number of sessions that are currently handled by the 
         virtual server."
    ::= { slbStatVServerEntry 2 }

slbStatVServerTotalSessions OBJECT-TYPE 
    SYNTAX  Counter32 
    MAX-ACCESS  read-only
    STATUS  current 
    DESCRIPTION 
        "The total number of sessions that are handled by the virtual server."
    ::= { slbStatVServerEntry 3 }

slbStatVServerHighestSessions OBJECT-TYPE 
    SYNTAX  Counter32 
    MAX-ACCESS  read-only
    STATUS  current 
    DESCRIPTION 
        "The highest sessions that have been handled by the virtual server."
    ::= { slbStatVServerEntry 4 }

slbStatVServerHCOctetsLow32 OBJECT-TYPE
    SYNTAX  Counter32
    MAX-ACCESS  read-only
    STATUS  current
    DESCRIPTION
        "The lower 32 bit value of octets received and transmitted out
         of the virtual server."
    ::= { slbStatVServerEntry 5 }

slbStatVServerHCOctetsHigh32 OBJECT-TYPE
    SYNTAX  Counter32
    MAX-ACCESS  read-only
    STATUS  current
    DESCRIPTION
        "The higher 32 bit value of octets received and transmitted out
         of the virtual server."
    ::= { slbStatVServerEntry 6 }


--  HTTP Header LB stats 
slbStatVServerHeaderHits OBJECT-TYPE 
    SYNTAX  Counter32 
    MAX-ACCESS  read-only
    STATUS  current 
    DESCRIPTION 
        "The current HTTP header hits." 
    ::= { slbStatVServerEntry 8 }

slbStatVServerHeaderMisses OBJECT-TYPE 
    SYNTAX  Counter32 
    MAX-ACCESS  read-only
    STATUS  current 
    DESCRIPTION 
        "The current HTTP header misses."  
    ::= { slbStatVServerEntry 9 }

slbStatVServerHeaderTotalSessions OBJECT-TYPE 
    SYNTAX  Counter32 
    MAX-ACCESS  read-only
    STATUS  current 
    DESCRIPTION 
        "The total HTTP header sessions."
    ::= { slbStatVServerEntry 10 }

-- Cookie Statistics 
slbStatVServerCookieRewrites OBJECT-TYPE 
    SYNTAX  Counter32 
    MAX-ACCESS  read-only
    STATUS  current 
    DESCRIPTION 
        "The total Cookie Rewrites."
    ::= { slbStatVServerEntry 11 }

slbStatVServerCookieInserts OBJECT-TYPE 
    SYNTAX  Counter32 
    MAX-ACCESS  read-only
    STATUS  current 
    DESCRIPTION 
        "The total Cookie Inserts."
    ::= { slbStatVServerEntry 12 }

slbStatVServerHCOctets OBJECT-TYPE
    SYNTAX  Counter64
    MAX-ACCESS  read-only
    STATUS  current
    DESCRIPTION
        "The total octets received and transmitted by the virtual server."
    ::= { slbStatVServerEntry 13 }

slbStatVServerIpAddress   OBJECT-TYPE
    SYNTAX  DisplayString 
    MAX-ACCESS  read-only 
    STATUS  current
    DESCRIPTION
        "IP address of the virtual server." 
    ::= { slbStatVServerEntry  14 }

-- SLB Maintenance Statistics 

slbStatMaintMaximumSessions OBJECT-TYPE
    SYNTAX  Integer32
    MAX-ACCESS  read-only
    STATUS  current
    DESCRIPTION
        "The maximun number entries in the session table.
         Note:This mib is not supported for VX instance of Virtualization."
    ::= { slbMaintStats 1 }

slbStatMaintCurBindings OBJECT-TYPE
    SYNTAX  Gauge32 
    MAX-ACCESS  read-only
    STATUS  current
    DESCRIPTION
        "The current number of bindings on the port.
         Note:This mib is not supported for VX instance of Virtualization."
    ::= { slbMaintStats 2 }

slbStatMaintCurBindings4Seconds OBJECT-TYPE
    SYNTAX  Gauge32 
    MAX-ACCESS  read-only
    STATUS  current
    DESCRIPTION
        "The 4 second average current number of bindings on the port.
         Note:This mib is not supported for VX instance of Virtualization."
    ::= { slbMaintStats 3 }

slbStatMaintCurBindings64Seconds OBJECT-TYPE
    SYNTAX  Gauge32 
    MAX-ACCESS  read-only
    STATUS  current
    DESCRIPTION
        "The 64 second average current number of bindings on the port.
         Note:This mib is not supported for VX instance of Virtualization."
    ::= { slbMaintStats 4 }

slbStatMaintTerminatedSessions OBJECT-TYPE
    SYNTAX  Counter32
    MAX-ACCESS  read-only
    STATUS  current
    DESCRIPTION
        "The count of the number of sessions closed because the server failed.
         Note:This mib is not supported for VX instance of Virtualization."
    ::= { slbMaintStats 5 }

slbStatMaintAllocFailures OBJECT-TYPE
    SYNTAX  Counter32
    MAX-ACCESS  read-only
    STATUS  current
    DESCRIPTION
        "The total number of Binding failures on the port. A Binding Failure 
         occurs when a port runs out of binding table entries.
         Note:This mib is not supported for VX instance of Virtualization."
    ::= { slbMaintStats 6 }

slbStatMaintNonTcpFrames OBJECT-TYPE
    SYNTAX  Counter32
    MAX-ACCESS  read-only
    STATUS  current
    DESCRIPTION
        "The total number of non-TCP/IP frames dropped on the port.
         Note:This mib is not supported for VX instance of Virtualization."
    ::= { slbMaintStats 7 }

slbStatMaintTcpFragments OBJECT-TYPE
    SYNTAX  Counter32
    MAX-ACCESS  read-only
    STATUS  current
    DESCRIPTION
        "The total number of TCP fragments dropped on the port.
         Note:This mib is not supported for VX instance of Virtualization."
    ::= { slbMaintStats 8 }

slbStatMaintUdpDatagrams OBJECT-TYPE
    SYNTAX  Counter32
    MAX-ACCESS  read-only
    STATUS  current
    DESCRIPTION
        "The total number of UDP datagrams dropped on the port.
         Note:This mib is not supported for VX instance of Virtualization."
    ::= { slbMaintStats 9 }

slbIncorrectVirtServs OBJECT-TYPE 
    SYNTAX  Counter32 
    MAX-ACCESS  read-only
    STATUS  current 
    DESCRIPTION 
        "Incorrect Virtual Servers specified for Server Load Balancing.
         Note:This mib is not supported for VX instance of Virtualization."
    ::= { slbMaintStats  10}

slbIncorrectVports OBJECT-TYPE 
    SYNTAX  Counter32  
    MAX-ACCESS  read-only
    STATUS  current 
    DESCRIPTION 
        "Incorrect Virtual ports specified for Server Load Balancing.
         Note:This mib is not supported for VX instance of Virtualization."
    ::= { slbMaintStats 11 }

slbNoRealServs OBJECT-TYPE 
    SYNTAX  Counter32  
    MAX-ACCESS  read-only
    STATUS  current 
    DESCRIPTION 
        "No Real Servers available for Server Load Balancing.
         Note:This mib is not supported for VX instance of Virtualization."
    ::= { slbMaintStats 12 }

slbStatMaintBackupServActs OBJECT-TYPE
    SYNTAX  Counter32
    MAX-ACCESS  read-only
    STATUS  current
    DESCRIPTION
        "The total number of times that backup servers become active due 
         to failure of primary servers.
         Note:This mib is not supported for VX instance of Virtualization."
    ::= { slbMaintStats 13 }

slbStatMaintOverflowServActs OBJECT-TYPE
    SYNTAX  Counter32
    MAX-ACCESS  read-only
    STATUS  current
    DESCRIPTION
        "The total number of times that backup servers become
	 active due to primary servers reach overflow situation.
         Note:This mib is not supported for VX instance of Virtualization."
    ::= { slbMaintStats 14 }

slbStatMaintFilteredDeniedFrames OBJECT-TYPE
    SYNTAX  Counter32
    MAX-ACCESS  read-only
    STATUS  current
    DESCRIPTION
        "The total number of frames that are denied on the port by the filter.
         Note:This mib is not supported for VX instance of Virtualization."
    ::= { slbMaintStats 15 }

slbStatMaintLandAttacks OBJECT-TYPE
    SYNTAX  Counter32
    MAX-ACCESS  read-only
    STATUS  current
    DESCRIPTION
        "The total number of attacks that frames contain the same source
	 and destination IP addresses.
         Note:This mib is not supported for VX instance of Virtualization."
    ::= { slbMaintStats 16 }

slbStatMaintIpFragTotalSessions OBJECT-TYPE
    SYNTAX  Counter32
    MAX-ACCESS  read-only
    STATUS  current
    DESCRIPTION
        "The total number of fragment sessions processed.
         Note:This mib is not supported for VX instance of Virtualization."
    ::= { slbMaintStats 17 }

slbStatMaintIpFragCurSessions OBJECT-TYPE
    SYNTAX  Gauge32
    MAX-ACCESS  read-only
    STATUS  current
    DESCRIPTION
        "The number of sessions in the IP fragment binding table.
         Note:This mib is not supported for VX instance of Virtualization."
    ::= { slbMaintStats 18 }

slbStatMaintIpFragDiscards OBJECT-TYPE
    SYNTAX  Counter32
    MAX-ACCESS  read-only
    STATUS  current
    DESCRIPTION
        "The total number of fragmemts discarded on the SP because there
         is no entry in the IP fragment binding table.
         Note:This mib is not supported for VX instance of Virtualization."
    ::= { slbMaintStats 19 }

slbStatMaintIpFragTableFull OBJECT-TYPE
    SYNTAX  Counter32
    MAX-ACCESS  read-only
    STATUS  current
    DESCRIPTION
        "The total number times IP fragment binding table is full on the SP.
         Note:This mib is not supported for VX instance of Virtualization."
    ::= { slbMaintStats 20 }

slbStatMaintIp6CurrSessions OBJECT-TYPE
    SYNTAX  Counter32
    MAX-ACCESS  read-only
    STATUS  current
    DESCRIPTION
        "The number of sessions  for ipv6.
         Note:This mib is not supported for VX instance of Virtualization."
    ::= { slbMaintStats 21 }

slbIncorrectIp6Vip  OBJECT-TYPE 
    SYNTAX  Counter32 
    MAX-ACCESS  read-only
    STATUS  current 
    DESCRIPTION 
        "Incorrect Ip6 VIPs specified for server load balancing.
         Note:This mib is not supported for VX instance of Virtualization."
    ::= { slbMaintStats  22}

slbIncorrectIp6Vports OBJECT-TYPE 
    SYNTAX  Counter32  
    MAX-ACCESS  read-only
    STATUS  current 
    DESCRIPTION 
        "Incorrect Ip6 virtual ports specified for server load balancing.
         Note:This mib is not supported for VX instance of Virtualization."
    ::= { slbMaintStats 23 }

slbStatMaintIp6PktDropped OBJECT-TYPE
    SYNTAX  Counter32
    MAX-ACCESS  read-only
    STATUS  current
    DESCRIPTION
        "The total number of Ip6 pacekets dropped.
         Note:This mib is not supported for VX instance of Virtualization."
    ::= { slbMaintStats 24 }


slbStatMaintOOSFinPktDrops OBJECT-TYPE
    SYNTAX  Counter32
    MAX-ACCESS  read-only
    STATUS  current
    DESCRIPTION
        "The total number Out of state FIN Packet drops.
         Note:This mib is not supported for VX instance of Virtualization."
    ::= { slbMaintStats 25 }

-- START of Symantec SLB Maintenance Stats
slbStatMaintSymSessions OBJECT-TYPE
    SYNTAX  Counter32
    MAX-ACCESS  read-only
    STATUS  current
    DESCRIPTION
        "Total number of Symantec sessions.
         Note:This mib is not supported for VX instance of Virtualization."
    ::= { slbMaintStats 26 }

slbStatMaintSymValidSegments OBJECT-TYPE
    SYNTAX  Counter32
    MAX-ACCESS  read-only
    STATUS  current
    DESCRIPTION
        "Total number of Symantec valid segments.
         Note:This mib is not supported for VX instance of Virtualization."
    ::= { slbMaintStats 27 }

slbStatMaintSymFragSessions OBJECT-TYPE
    SYNTAX  Counter32
    MAX-ACCESS  read-only
    STATUS  current
    DESCRIPTION
        "Total number of Symantec fragment sessions.
         Note:This mib is not supported for VX instance of Virtualization."
    ::= { slbMaintStats 28 }

slbStatMaintSymSegAllocFails OBJECT-TYPE
    SYNTAX  Counter32
    MAX-ACCESS  read-only
    STATUS  current
    DESCRIPTION
        "Total number of Symantec segment allocation fails.
         Note:This mib is not supported for VX instance of Virtualization."
    ::= { slbMaintStats 29 }

	-- Sunil Start
-- SLB Virtual Server Statistics Table

slbStatEnhVServerTable OBJECT-TYPE
    SYNTAX  SEQUENCE OF SlbStatEnhVServerEntry
    MAX-ACCESS  not-accessible
    STATUS  current
    DESCRIPTION
        "The virtual server statistics table.
         Note:This mib is not supported for VX instance of Virtualization."
    ::= { layer4Stats 32 }

slbStatEnhVServerEntry OBJECT-TYPE
    SYNTAX  SlbStatEnhVServerEntry
    MAX-ACCESS  not-accessible
    STATUS  current
    DESCRIPTION
        "The statistics of a particular virtual server group.
         Note:This mib is not supported for VX instance of Virtualization."
    INDEX   { slbStatEnhVServerIndex }
    ::= { slbStatEnhVServerTable 1 }

SlbStatEnhVServerEntry ::= SEQUENCE {
    slbStatEnhVServerIndex                   DisplayString,
    slbStatEnhVServerCurrSessions            Gauge32,
    slbStatEnhVServerTotalSessions           Counter32,
    slbStatEnhVServerHighestSessions         Counter32,
    slbStatEnhVServerHCOctetsLow32           Counter32,
    slbStatEnhVServerHCOctetsHigh32          Counter32,
    slbStatEnhVServerHeaderHits              Counter32,
    slbStatEnhVServerHeaderMisses            Counter32,
    slbStatEnhVServerHeaderTotalSessions     Counter32,
    slbStatEnhVServerCookieRewrites          Counter32,
    slbStatEnhVServerCookieInserts           Counter32,
    slbStatEnhVServerHCOctets                Counter64,
    slbStatEnhVServerIpAddress               DisplayString,
    slbStatEnhVServerSessionsPerSec          Counter32,
    slbStatEnhVServerOctetsPerSec            DisplayString,
    slbStatEnhVServerCurrPSessions           Counter64,
    slbStatEnhVServerTotalPSessions          Counter64,
    slbStatEnhVServerHighestPSessions        Counter64
}

slbStatEnhVServerIndex OBJECT-TYPE
    SYNTAX  DisplayString (SIZE(1..255))
    MAX-ACCESS  read-only
    STATUS  current
    DESCRIPTION
        "The virtual server number that identifies the server."
    ::= { slbStatEnhVServerEntry 1 }

slbStatEnhVServerCurrSessions OBJECT-TYPE
    SYNTAX  Gauge32
    MAX-ACCESS  read-only
    STATUS  current
    DESCRIPTION
        "The number of sessions that are currently handled by the
         virtual server."
    ::= { slbStatEnhVServerEntry 2 }

slbStatEnhVServerTotalSessions OBJECT-TYPE
    SYNTAX  Counter32
    MAX-ACCESS  read-only
    STATUS  current
    DESCRIPTION
        "The total number of sessions that are handled by the virtual server."
    ::= { slbStatEnhVServerEntry 3 }

slbStatEnhVServerHighestSessions OBJECT-TYPE
    SYNTAX  Counter32
    MAX-ACCESS  read-only
    STATUS  current
    DESCRIPTION
        "The highest sessions that have been handled by the virtual server."
    ::= { slbStatEnhVServerEntry 4 }

slbStatEnhVServerHCOctetsLow32 OBJECT-TYPE
    SYNTAX  Counter32
    MAX-ACCESS  read-only
    STATUS  current
    DESCRIPTION
        "The lower 32 bit value of octets received and transmitted out
         of the virtual server."
    ::= { slbStatEnhVServerEntry 5 }

slbStatEnhVServerHCOctetsHigh32 OBJECT-TYPE
    SYNTAX  Counter32
    MAX-ACCESS  read-only
    STATUS  current
    DESCRIPTION
        "The higher 32 bit value of octets received and transmitted out
         of the virtual server."
    ::= { slbStatEnhVServerEntry 6 }


--  HTTP Header LB stats
slbStatEnhVServerHeaderHits OBJECT-TYPE
    SYNTAX  Counter32
    MAX-ACCESS  read-only
    STATUS  current
    DESCRIPTION
        "The current HTTP header hits."
    ::= { slbStatEnhVServerEntry 8 }

slbStatEnhVServerHeaderMisses OBJECT-TYPE
    SYNTAX  Counter32
    MAX-ACCESS  read-only
    STATUS  current
    DESCRIPTION
        "The current HTTP header misses."
    ::= { slbStatEnhVServerEntry 9 }

slbStatEnhVServerHeaderTotalSessions OBJECT-TYPE
    SYNTAX  Counter32
    MAX-ACCESS  read-only
    STATUS  current
    DESCRIPTION
        "The total HTTP header sessions."
    ::= { slbStatEnhVServerEntry 10 }

-- Cookie Statistics
slbStatEnhVServerCookieRewrites OBJECT-TYPE
    SYNTAX  Counter32
    MAX-ACCESS  read-only
    STATUS  current
    DESCRIPTION
      "The total Cookie Rewrites."
    ::= { slbStatEnhVServerEntry 11 }

slbStatEnhVServerCookieInserts OBJECT-TYPE
    SYNTAX  Counter32
    MAX-ACCESS  read-only
    STATUS  current
    DESCRIPTION
        "The total Cookie Inserts."
    ::= { slbStatEnhVServerEntry 12 }

slbStatEnhVServerHCOctets OBJECT-TYPE
    SYNTAX  Counter64
    MAX-ACCESS  read-only
    STATUS  current
    DESCRIPTION
        "The total octets received and transmitted by the virtual server."
    ::= { slbStatEnhVServerEntry 13 }

slbStatEnhVServerIpAddress   OBJECT-TYPE
    SYNTAX  DisplayString (SIZE(0..32))
    MAX-ACCESS  read-only
    STATUS  current
    DESCRIPTION
        "IP address of the virtual server."
    ::= { slbStatEnhVServerEntry  14 }

slbStatEnhVServerSessionsPerSec OBJECT-TYPE
    SYNTAX  Counter32
    MAX-ACCESS  read-only
    STATUS  current
    DESCRIPTION
        "Number of Sessions handled by the virtual server per second."
    ::= { slbStatEnhVServerEntry 15 }


slbStatEnhVServerOctetsPerSec OBJECT-TYPE
    SYNTAX  DisplayString (SIZE(1..24))
    MAX-ACCESS  read-only
    STATUS  current
    DESCRIPTION
        "Number of Mbps received and transmitted by the virtual server per second."
    ::= { slbStatEnhVServerEntry 16 }

slbStatEnhVServerCurrPSessions OBJECT-TYPE
    SYNTAX  Counter64
    MAX-ACCESS  read-only
    STATUS  current
    DESCRIPTION
        "The number of persistent sessions that are currently handled by the
         virtual server."
    ::= { slbStatEnhVServerEntry 17 }

slbStatEnhVServerTotalPSessions OBJECT-TYPE
    SYNTAX  Counter64
    MAX-ACCESS  read-only
    STATUS  current
    DESCRIPTION
        "The total number of persistent sessions that are handled by the virtual server."
    ::= { slbStatEnhVServerEntry 18 }

slbStatEnhVServerHighestPSessions OBJECT-TYPE
    SYNTAX  Counter64
    MAX-ACCESS  read-only
    STATUS  current
    DESCRIPTION
        "The highest persistent sessions that have been handled by the virtual server."
    ::= { slbStatEnhVServerEntry 19 }

-- Sunil End

slbStatEnhRServerCpTable OBJECT-TYPE
    SYNTAX  SEQUENCE OF SlbStatEnhRServerCpEntry
    MAX-ACCESS  not-accessible
    STATUS  current
    DESCRIPTION
        "The real server statistics table.
         Note:This mib is not supported for VX instance of Virtualization."
    ::= { layer4Stats 34 }

slbStatEnhRServerCpEntry OBJECT-TYPE
    SYNTAX  SlbStatEnhRServerCpEntry
    MAX-ACCESS  not-accessible
    STATUS  current
    DESCRIPTION
        "The statistics of a particular real server."
    INDEX   { slbStatEnhRServerIndexCp }
    ::= { slbStatEnhRServerCpTable 1 }

SlbStatEnhRServerCpEntry ::= SEQUENCE {
    slbStatEnhRServerIndexCp               DisplayString,
    slbStatEnhRServerCurrSessionsCp        Gauge32,
    slbStatEnhRServerTotalSessionsCp       Counter32,
    slbStatEnhRServerFailuresCp            Counter32,
    slbStatEnhRServerHighestSessionsCp     Counter32,
    slbStatEnhRServerHCOctetsLow32Cp       Counter32,
    slbStatEnhRServerHCOctetsHigh32Cp      Counter32,
    slbStatEnhRServerHCOctetsCp            Counter64
}

slbStatEnhRServerIndexCp OBJECT-TYPE
    SYNTAX  DisplayString (SIZE(1..255))
    MAX-ACCESS  read-only
    STATUS  current
    DESCRIPTION
        "The real server index that identifies the server."
    ::= { slbStatEnhRServerCpEntry 1 }

slbStatEnhRServerCurrSessionsCp OBJECT-TYPE
    SYNTAX  Gauge32
    MAX-ACCESS  read-only
    STATUS  current
    DESCRIPTION
        "The number of sessions that are currently handled by the real server."
    ::= { slbStatEnhRServerCpEntry 2 }

slbStatEnhRServerTotalSessionsCp OBJECT-TYPE
    SYNTAX  Counter32
    MAX-ACCESS  read-only
    STATUS  current
    DESCRIPTION
        "The total number of sessions that are handled by the real server."
    ::= { slbStatEnhRServerCpEntry 3 }

slbStatEnhRServerFailuresCp OBJECT-TYPE
    SYNTAX  Counter32
    MAX-ACCESS  read-only
    STATUS  current
    DESCRIPTION
        "The total number of times that the real server is claimed down."
    ::= { slbStatEnhRServerCpEntry 4 }


slbStatEnhRServerHighestSessionsCp OBJECT-TYPE
    SYNTAX  Counter32
    MAX-ACCESS  read-only
    STATUS  current
    DESCRIPTION
        "The highest sessions that have been handled by the real server."
    ::= { slbStatEnhRServerCpEntry 5 }

slbStatEnhRServerHCOctetsLow32Cp OBJECT-TYPE
    SYNTAX  Counter32
    MAX-ACCESS  read-only
    STATUS  current
    DESCRIPTION
        "The lower 32 bit value of octets received and transmitted out of the
         real server."
    ::= { slbStatEnhRServerCpEntry 6 }

slbStatEnhRServerHCOctetsHigh32Cp OBJECT-TYPE
    SYNTAX  Counter32
    MAX-ACCESS  read-only
    STATUS  current
    DESCRIPTION
        "The higher 32 bit value of octets received and transmitted out
         of the real server."
    ::= { slbStatEnhRServerCpEntry 7 }

slbStatEnhRServerHCOctetsCp OBJECT-TYPE
    SYNTAX  Counter64
    MAX-ACCESS  read-only
    STATUS  current
    DESCRIPTION
        "The total number of octets received and transmitted by the real
         server."
    ::= { slbStatEnhRServerCpEntry 8 }

slbStatLinkpfRServerTable OBJECT-TYPE
    SYNTAX  SEQUENCE OF SlbStatLinkpfRServerEntry
    MAX-ACCESS  not-accessible
    STATUS  current
    DESCRIPTION
        "The link proof real server statistics table.
         Note:This mib is not supported for VX instance of Virtualization."
    ::= { layer4Stats 35 }

slbStatLinkpfRServerEntry OBJECT-TYPE
    SYNTAX  SlbStatLinkpfRServerEntry
    MAX-ACCESS  not-accessible
    STATUS  current
    DESCRIPTION
        "The statistics of link proof real server."
    INDEX   { slbStatLinkpfRServerIndex }
    ::= { slbStatLinkpfRServerTable 1 }

SlbStatLinkpfRServerEntry ::= SEQUENCE {
    slbStatLinkpfRServerIndex           DisplayString,
    slbStatLinkpfRServerIpAddr          IpAddress,
    slbStatLinkpfRServerUpBwCurr        DisplayString,
    slbStatLinkpfRServerUpBwUsage       DisplayString,
    slbStatLinkpfRServerDwBwCurr        DisplayString,
    slbStatLinkpfRServerDwBwUSage       DisplayString,
    slbStatLinkpfRServerTotCurrbw       DisplayString,
    slbStatLinkpfRServerTotCurrUsage    DisplayString,
    slbStatLinkpfRServerCurrSess        Gauge32,
    slbStatLinkpfRServerUpBwPeak        DisplayString,
    slbStatLinkpfRServerUpBwPeakPer     DisplayString,
    slbStatLinkpfRServerUpBwPeakTmSt    DisplayString,
    slbStatLinkpfRServerDnBwPeak        DisplayString,
    slbStatLinkpfRServerDnBwPeakPer     DisplayString,
    slbStatLinkpfRServerDnBwPeakTmSt    DisplayString,
    slbStatLinkpfRServerTotBwPeak       DisplayString,
    slbStatLinkpfRServerTotBwPeakPer    DisplayString,
    slbStatLinkpfRServerTotBwPeakTmSt   DisplayString,
    slbStatLinkpfRServerLastTranfetTmSt DisplayString,
    slbStatLinkpfRServerUpBwTot         DisplayString,
    slbStatLinkpfRServerDnBwTot         DisplayString,
    slbStatLinkpfRServerUpDnBwTot       DisplayString,
    slbStatLinkpfRServerState           INTEGER
}
slbStatLinkpfRServerIndex OBJECT-TYPE
    SYNTAX  DisplayString (SIZE(1..255))
    MAX-ACCESS  read-only
    STATUS  current
    DESCRIPTION
        "The WAN Link real server index that identifies the server."
    ::= { slbStatLinkpfRServerEntry 1 }

slbStatLinkpfRServerIpAddr OBJECT-TYPE
    SYNTAX  IpAddress
    MAX-ACCESS  read-only
    STATUS  current
    DESCRIPTION
        "IP address of the WAN Link real server identified by the instance of the
         slbStatLinkpfRServerIndex."
    ::= { slbStatLinkpfRServerEntry 2 }

slbStatLinkpfRServerUpBwCurr OBJECT-TYPE
    SYNTAX  DisplayString (SIZE(0..20))
    MAX-ACCESS  read-only
    STATUS  current
    DESCRIPTION
        "The total number of current upload bandwidth by WAN Link real server."
    ::= { slbStatLinkpfRServerEntry 3 }

slbStatLinkpfRServerUpBwUsage OBJECT-TYPE
    SYNTAX  DisplayString (SIZE(0..5))
    MAX-ACCESS  read-only
    STATUS  current
    DESCRIPTION
        "The Usuage of upload bandwidth by WAN Link real server."
    ::= { slbStatLinkpfRServerEntry 4 }

slbStatLinkpfRServerDwBwCurr OBJECT-TYPE
    SYNTAX  DisplayString (SIZE(0..20))
    MAX-ACCESS  read-only
    STATUS  current
    DESCRIPTION
        "The total number of current download bandwidth by WAN Link real server."
    ::= { slbStatLinkpfRServerEntry 5 }

slbStatLinkpfRServerDwBwUSage OBJECT-TYPE
    SYNTAX  DisplayString (SIZE(0..5))
    MAX-ACCESS  read-only
    STATUS  current
    DESCRIPTION
        "The Usuage of download bandwidth by WAN Link real server."
    ::= { slbStatLinkpfRServerEntry 6 }

slbStatLinkpfRServerTotCurrbw OBJECT-TYPE
    SYNTAX  DisplayString (SIZE(0..20))
    MAX-ACCESS  read-only
    STATUS  current
    DESCRIPTION
        "The total number of upload and download bandwidth by WAN Link real server."
    ::= { slbStatLinkpfRServerEntry 7 }

slbStatLinkpfRServerTotCurrUsage OBJECT-TYPE
    SYNTAX  DisplayString (SIZE(0..5))
    MAX-ACCESS  read-only
    STATUS  current
    DESCRIPTION
        "The Total Usuage of upload and Download bandwidth by WAN Link real server."
    ::= { slbStatLinkpfRServerEntry 8 }

slbStatLinkpfRServerCurrSess OBJECT-TYPE
    SYNTAX Gauge32
    MAX-ACCESS  read-only
    STATUS  current
    DESCRIPTION
        "The current number of session by WAN Link real server."
    ::= { slbStatLinkpfRServerEntry 9 }

slbStatLinkpfRServerUpBwPeak OBJECT-TYPE
    SYNTAX  DisplayString (SIZE(0..20))
    MAX-ACCESS  read-only
    STATUS  current
    DESCRIPTION
        "Upload peak bandwidth by WAN Link real server."
    ::= { slbStatLinkpfRServerEntry 10 }

slbStatLinkpfRServerUpBwPeakPer OBJECT-TYPE
    SYNTAX  DisplayString (SIZE(0..5))
    MAX-ACCESS  read-only
    STATUS  current
    DESCRIPTION
        "Upload per peak bandwidth by WAN Link real server."
    ::= { slbStatLinkpfRServerEntry 11 }

slbStatLinkpfRServerUpBwPeakTmSt OBJECT-TYPE
    SYNTAX  DisplayString (SIZE(0..32))
    MAX-ACCESS  read-only
    STATUS  current
    DESCRIPTION
        "Upload peak bandwidth time stamp by WAN Link real server."
    ::= { slbStatLinkpfRServerEntry 12 }

slbStatLinkpfRServerDnBwPeak OBJECT-TYPE
    SYNTAX  DisplayString (SIZE(0..20))
    MAX-ACCESS  read-only
    STATUS  current
    DESCRIPTION
        "Download peak bandwidth by WAN Link real server."
    ::= { slbStatLinkpfRServerEntry 13 }

slbStatLinkpfRServerDnBwPeakPer OBJECT-TYPE
    SYNTAX  DisplayString (SIZE(0..5))
    MAX-ACCESS  read-only
    STATUS  current
    DESCRIPTION
        "Download per peak bandwidth by WAN Link real server."
    ::= { slbStatLinkpfRServerEntry 14 }

slbStatLinkpfRServerDnBwPeakTmSt OBJECT-TYPE
    SYNTAX  DisplayString (SIZE(0..32))
    MAX-ACCESS  read-only
    STATUS  current
    DESCRIPTION
        "Download peak bandwidth time stamp by WAN Link real server."
    ::= { slbStatLinkpfRServerEntry 15 }

slbStatLinkpfRServerTotBwPeak OBJECT-TYPE
    SYNTAX  DisplayString (SIZE(0..20))
    MAX-ACCESS  read-only
    STATUS  current
    DESCRIPTION
        "Total peak bandwidth by WAN Link real server."
    ::= { slbStatLinkpfRServerEntry 16 }

slbStatLinkpfRServerTotBwPeakPer OBJECT-TYPE
    SYNTAX  DisplayString (SIZE(0..5))
    MAX-ACCESS  read-only
    STATUS  current
    DESCRIPTION
        "Total per peak bandwidth by WAN Link real server."
    ::= { slbStatLinkpfRServerEntry 17 }

slbStatLinkpfRServerTotBwPeakTmSt OBJECT-TYPE
    SYNTAX  DisplayString (SIZE(0..32))
    MAX-ACCESS  read-only
    STATUS  current
    DESCRIPTION
        "Total bandwidth peak time stamp of the WAN link real server."
    ::= { slbStatLinkpfRServerEntry 18 }

slbStatLinkpfRServerLastTranfetTmSt OBJECT-TYPE
    SYNTAX  DisplayString (SIZE(0..32))
    MAX-ACCESS  read-only
    STATUS  current
    DESCRIPTION
        "Last clear time stamp of the WAN Link real server ."
    ::= { slbStatLinkpfRServerEntry 19 }

slbStatLinkpfRServerUpBwTot OBJECT-TYPE
    SYNTAX  DisplayString (SIZE(0..20))
    MAX-ACCESS  read-only
    STATUS  current
    DESCRIPTION
        "The total upload bandwidth by WAN Link real server."
    ::= { slbStatLinkpfRServerEntry 20 }

slbStatLinkpfRServerDnBwTot OBJECT-TYPE
    SYNTAX  DisplayString (SIZE(0..20))
    MAX-ACCESS  read-only
    STATUS  current
    DESCRIPTION
        "The total download bandwidth by WAN Link real server."
    ::= { slbStatLinkpfRServerEntry 21 }

slbStatLinkpfRServerUpDnBwTot OBJECT-TYPE
    SYNTAX  DisplayString (SIZE(0..20))
    MAX-ACCESS  read-only
    STATUS  current
    DESCRIPTION
        "The total upload and download Bandwidth by WAN Link real server."
    ::= { slbStatLinkpfRServerEntry 22 }

slbStatLinkpfRServerState OBJECT-TYPE
    SYNTAX  INTEGER {
        running(1),
        failed(2),
        disabled(3),
        unsupported(2147483647)
    }
    MAX-ACCESS  read-only
    STATUS  current
    DESCRIPTION
        "The state of the wan link real server."
    ::= { slbStatLinkpfRServerEntry 23 }

slbStatLinkpfIpTable OBJECT-TYPE
    SYNTAX  SEQUENCE OF SlbStatLinkpfIpEntry
    MAX-ACCESS  not-accessible
    STATUS  current
    DESCRIPTION
        "The link proof real server statistics table.
         Note:This mib is not supported for VX instance of Virtualization."
    ::= { layer4Stats 36 }

slbStatLinkpfIpEntry OBJECT-TYPE
    SYNTAX  SlbStatLinkpfIpEntry
    MAX-ACCESS  not-accessible
    STATUS  current
    DESCRIPTION
        "The statistics of link proof real server."
    INDEX   { slbStatLinkpfIpIndex }
    ::= { slbStatLinkpfIpTable 1 }

SlbStatLinkpfIpEntry ::= SEQUENCE {
    slbStatLinkpfIpIndex           DisplayString,
    slbStatLinkpfIpUpBwCurr        DisplayString,
    slbStatLinkpfIpUpBwCurrUsage   DisplayString,
    slbStatLinkpfIpDnBwCurr        DisplayString,
    slbStatLinkpfIpDnBwCurrUsage   DisplayString,
    slbStatLinkpfIpTotBwCurr       DisplayString,
    slbStatLinkpfIpTotBwCurrUsage  DisplayString,
    slbStatLinkpfIpCurrSessions    Gauge32,
    slbStatLinkpfIpUpBwPeak        DisplayString,
    slbStatLinkpfIpUpBwPeakPer     DisplayString,
    slbStatLinkpfIpUpBwPeakTmSt    DisplayString,
    slbStatLinkpfIpDnBwPeak        DisplayString,
    slbStatLinkpfIpDnBwPeakPer     DisplayString,
    slbStatLinkpfIpDnBwPeakTmSt    DisplayString,
    slbStatLinkpfIpTotBwPeak       DisplayString,
    slbStatLinkpfIpTotBwPeakPer    DisplayString,
    slbStatLinkpfIpTotBwPeakTmSt   DisplayString,
    slbStatLinkpfIpLastClearTmSt DisplayString,
    slbStatLinkpfIpUpBwTot         DisplayString,
    slbStatLinkpfIpDnBwTot         DisplayString,
    slbStatLinkpfIpUpDnBwTot       DisplayString
}

slbStatLinkpfIpIndex OBJECT-TYPE
    SYNTAX  DisplayString (SIZE(1..40))
    MAX-ACCESS  read-only
    STATUS  current
    DESCRIPTION
        "The WAN Link real server IP that identifies the server."
    ::= { slbStatLinkpfIpEntry 1 }

slbStatLinkpfIpUpBwCurr OBJECT-TYPE
    SYNTAX  DisplayString (SIZE(0..20))
    MAX-ACCESS  read-only
    STATUS  current
    DESCRIPTION
        "The total number of current upload bandwidth by WAN Link real servers with same IP."
    ::= { slbStatLinkpfIpEntry 2 }

slbStatLinkpfIpUpBwCurrUsage OBJECT-TYPE
    SYNTAX  DisplayString (SIZE(0..10))
    MAX-ACCESS  read-only
    STATUS  current
    DESCRIPTION
        "The total number of current upload bandwidth Usages by WAN Link real servers with same IP."
    ::= { slbStatLinkpfIpEntry 3 }

slbStatLinkpfIpDnBwCurr OBJECT-TYPE
    SYNTAX  DisplayString (SIZE(0..20))
    MAX-ACCESS  read-only
    STATUS  current
    DESCRIPTION
        "The total number of current download bandwidth by WAN Link real servers with same IP."
    ::= { slbStatLinkpfIpEntry 4 }

slbStatLinkpfIpDnBwCurrUsage OBJECT-TYPE
    SYNTAX  DisplayString (SIZE(0..10))
    MAX-ACCESS  read-only
    STATUS  current
    DESCRIPTION
        "The total number of current upload bandwidth Usages by WAN Link real servers with same IP."
    ::= { slbStatLinkpfIpEntry 5 }

slbStatLinkpfIpTotBwCurr OBJECT-TYPE
    SYNTAX  DisplayString (SIZE(0..20))
    MAX-ACCESS  read-only
    STATUS  current
    DESCRIPTION
        "The total number of current upload and download bandwidth by WAN Link real servers with same IP."
    ::= { slbStatLinkpfIpEntry 6 }

slbStatLinkpfIpTotBwCurrUsage OBJECT-TYPE
    SYNTAX  DisplayString (SIZE(0..10))
    MAX-ACCESS  read-only
    STATUS  current
    DESCRIPTION
        "The total number of current upload bandwidth Usages by WAN Link real servers with same IP."
    ::= { slbStatLinkpfIpEntry 7 }

slbStatLinkpfIpCurrSessions OBJECT-TYPE
    SYNTAX  Gauge32
    MAX-ACCESS  read-only
    STATUS  current
    DESCRIPTION
        "The total number of current sessions that are handle by WAN Link real servers with same IP."
    ::= { slbStatLinkpfIpEntry 8 }

slbStatLinkpfIpUpBwPeak OBJECT-TYPE
    SYNTAX  DisplayString (SIZE(0..20))
    MAX-ACCESS  read-only
    STATUS  current
    DESCRIPTION
        "The total number of current upload bandwidth by WAN Link real servers with same IP."
    ::= { slbStatLinkpfIpEntry 9 }

slbStatLinkpfIpUpBwPeakPer OBJECT-TYPE
    SYNTAX  DisplayString (SIZE(0..10))
    MAX-ACCESS  read-only
    STATUS  current
    DESCRIPTION
        "The total number of current upload bandwidth Usages by WAN Link real servers with same IP."
    ::= { slbStatLinkpfIpEntry 10 }

slbStatLinkpfIpUpBwPeakTmSt OBJECT-TYPE
    SYNTAX  DisplayString (SIZE(0..32))
    MAX-ACCESS  read-only
    STATUS  current
    DESCRIPTION
        "The total number of current upload bandwidth peak time stamp by WAN Link real server with same IP."
    ::= { slbStatLinkpfIpEntry 11 }

slbStatLinkpfIpDnBwPeak OBJECT-TYPE
    SYNTAX  DisplayString (SIZE(0..20))
    MAX-ACCESS  read-only
    STATUS  current
    DESCRIPTION
        "The total number of current download bandwidth by WAN Link real servers with same IP."
    ::= { slbStatLinkpfIpEntry 12 }

slbStatLinkpfIpDnBwPeakPer OBJECT-TYPE
    SYNTAX  DisplayString (SIZE(0..10))
    MAX-ACCESS  read-only
    STATUS  current
    DESCRIPTION
        "The total number of current upload bandwidth Usages by WAN Link real servers with same IP."
    ::= { slbStatLinkpfIpEntry 13 }

slbStatLinkpfIpDnBwPeakTmSt OBJECT-TYPE
    SYNTAX  DisplayString (SIZE(0..32))
    MAX-ACCESS  read-only
    STATUS  current
    DESCRIPTION
        "The total number of current upload bandwidth peak time stamp by WAN Link real server with same IP."
    ::= { slbStatLinkpfIpEntry 14 }

slbStatLinkpfIpTotBwPeak OBJECT-TYPE
    SYNTAX  DisplayString (SIZE(0..20))
    MAX-ACCESS  read-only
    STATUS  current
    DESCRIPTION
        "The total number of current download and download bandwidth by WAN Link real servers with same IP."
    ::= { slbStatLinkpfIpEntry 15 }

slbStatLinkpfIpTotBwPeakPer OBJECT-TYPE
    SYNTAX  DisplayString (SIZE(0..10))
    MAX-ACCESS  read-only
    STATUS  current
    DESCRIPTION
        "The total number of current upload and download bandwidth Usages by WAN Link real servers with same IP."
    ::= { slbStatLinkpfIpEntry 16 }

slbStatLinkpfIpTotBwPeakTmSt OBJECT-TYPE
    SYNTAX  DisplayString (SIZE(0..32))
    MAX-ACCESS  read-only
    STATUS  current
    DESCRIPTION
        "The total number of current upload and download bandwidth peak time stamp by WAN Link real server with same IP."
    ::= { slbStatLinkpfIpEntry 17 }

slbStatLinkpfIpLastClearTmSt OBJECT-TYPE
    SYNTAX  DisplayString (SIZE(0..32))
    MAX-ACCESS  read-only
    STATUS  current
    DESCRIPTION
        "Last clear time stamp by WAN Link real server with same IP."
    ::= { slbStatLinkpfIpEntry 18 }

slbStatLinkpfIpUpBwTot OBJECT-TYPE
    SYNTAX  DisplayString (SIZE(0..20))
    MAX-ACCESS  read-only
    STATUS  current
    DESCRIPTION
        "The total number of upload bandwidth by WAN Link real servers with same IP."
    ::= { slbStatLinkpfIpEntry 19 }

slbStatLinkpfIpDnBwTot OBJECT-TYPE
    SYNTAX  DisplayString (SIZE(0..20))
    MAX-ACCESS  read-only
    STATUS  current
    DESCRIPTION
        "The total number of download bandwidth by WAN Link real servers with same IP."
    ::= { slbStatLinkpfIpEntry 20 }

slbStatLinkpfIpUpDnBwTot OBJECT-TYPE
    SYNTAX  DisplayString (SIZE(0..20))
    MAX-ACCESS  read-only
    STATUS  current
    DESCRIPTION
        "The total number of upload and download bandwidth by WAN Link real servers with same IP."
    ::= { slbStatLinkpfIpEntry 21 }

slbStatLinkpfGroupTable OBJECT-TYPE
    SYNTAX  SEQUENCE OF SlbStatLinkpfGroupEntry
    MAX-ACCESS  not-accessible
    STATUS  current
    DESCRIPTION
        "The link proof real server group statistics table.
         Note:This mib is not supported for VX instance of Virtualization."
    ::= { layer4Stats 37 }

slbStatLinkpfGroupEntry OBJECT-TYPE
    SYNTAX  SlbStatLinkpfGroupEntry
    MAX-ACCESS  not-accessible
    STATUS  current
    DESCRIPTION
        "The statistics of link proof real server."
    INDEX   { slbStatLinkpfGroupIndex }
    ::= { slbStatLinkpfGroupTable 1 }

SlbStatLinkpfGroupEntry ::= SEQUENCE {
    slbStatLinkpfGroupIndex          DisplayString,
    slbStatLinkpfGroupCurrUpBw       DisplayString,
    slbStatLinkpfGroupCurrDnBw       DisplayString,
    slbStatLinkpfGroupCurrTotBw      DisplayString,
    slbStatLinkpfGroupCurrSess       Gauge32,
    slbStatLinkpfGroupLastClearTmSt  DisplayString,
    slbStatLinkpfGroupTotUpBw        DisplayString,
    slbStatLinkpfGroupTotDnBw        DisplayString,
    slbStatLinkpfGroupTotBw          DisplayString
}

slbStatLinkpfGroupIndex OBJECT-TYPE
    SYNTAX  DisplayString (SIZE(1..255))
    MAX-ACCESS  read-only
    STATUS  current
    DESCRIPTION
        "The WAN Link real server group index that identifies the group."
    ::= { slbStatLinkpfGroupEntry 1 }

slbStatLinkpfGroupCurrUpBw OBJECT-TYPE
    SYNTAX  DisplayString (SIZE(0..20))
    MAX-ACCESS  read-only
    STATUS  current
    DESCRIPTION
        "The total current upload bandwidth by WAN Link group for all WAN Link real server."
    ::= { slbStatLinkpfGroupEntry 2 }

slbStatLinkpfGroupCurrDnBw OBJECT-TYPE
    SYNTAX  DisplayString (SIZE(0..20))
    MAX-ACCESS  read-only
    STATUS  current
    DESCRIPTION
        "The total current download bandwidth by WAN Link group for all WAN Link real server."
    ::= { slbStatLinkpfGroupEntry 3 }

slbStatLinkpfGroupCurrTotBw OBJECT-TYPE
    SYNTAX  DisplayString (SIZE(0..20))
    MAX-ACCESS  read-only
    STATUS  current
    DESCRIPTION
        "The total upload and download bandwidth by WAN Link group for all WAN Link real server."
    ::= { slbStatLinkpfGroupEntry 4 }

slbStatLinkpfGroupCurrSess OBJECT-TYPE
    SYNTAX  Gauge32
    MAX-ACCESS  read-only
    STATUS  current
    DESCRIPTION
        "The number of sessions that are currently handled by the WAN Link group."
    ::= { slbStatLinkpfGroupEntry 5 }

slbStatLinkpfGroupLastClearTmSt OBJECT-TYPE
    SYNTAX  DisplayString (SIZE(0..32))
    MAX-ACCESS  read-only
    STATUS  current
    DESCRIPTION
        "Last reset or clear time stamp for this group."
    ::= { slbStatLinkpfGroupEntry 6 }

slbStatLinkpfGroupTotUpBw OBJECT-TYPE
    SYNTAX  DisplayString (SIZE(0..20))
    MAX-ACCESS  read-only
    STATUS  current
    DESCRIPTION
        "The total upload bandwidth that are handle by WAN Link group for all WAN Link real server."
    ::= { slbStatLinkpfGroupEntry 7 }

slbStatLinkpfGroupTotDnBw OBJECT-TYPE
   SYNTAX  DisplayString (SIZE(0..20))
    MAX-ACCESS  read-only
    STATUS  current
    DESCRIPTION
        "The total download bandwidth that are handle by WAN Link group for all WAN Link real server."
    ::= { slbStatLinkpfGroupEntry 8 }

slbStatLinkpfGroupTotBw OBJECT-TYPE
    SYNTAX  DisplayString (SIZE(0..20))
    MAX-ACCESS  read-only
    STATUS  current
    DESCRIPTION
        "The total upload and download bandwidth that are handle by WAN Link group for all WAN Link real server."
    ::= { slbStatLinkpfGroupEntry 9 }

slbStatLinkpfClear OBJECT IDENTIFIER ::= { layer4Stats 38 }

slbStatLinkpfClearWanLinkServer OBJECT-TYPE
    SYNTAX DisplayString (SIZE(0..32))
    MAX-ACCESS  read-create
    STATUS  current
    DESCRIPTION
        "Clear WAN Link real server stats for given Real server Index.
         Note:This mib is not supported for VX instance of Virtualization."
    ::= { slbStatLinkpfClear 1 }

slbStatLinkpfClearWanLinkIP OBJECT-TYPE
    SYNTAX DisplayString (SIZE(0..40))
    MAX-ACCESS  read-create
    STATUS  current
    DESCRIPTION
        "Clear WAN Link real server stats for given Real server IP. It can be IPv4/IPv6.
         Note:This mib is not supported for VX instance of Virtualization."
    ::= { slbStatLinkpfClear 2 }

slbStatLinkpfClearAll OBJECT-TYPE
    SYNTAX INTEGER {
        ok(1),
        clearAll(2),
        unsupported(2147483647)
    }
    MAX-ACCESS  read-create
    STATUS  current
    DESCRIPTION
        "This is an action object to clear the WAN Link statistics.
         ok(1) is returned when read.
         Note:This mib is not supported for VX instance of Virtualization."
    ::= { slbStatLinkpfClear 3 }

slbStatLinkpfSmartNATID OBJECT-TYPE
    SYNTAX DisplayString (SIZE(0..32))
    MAX-ACCESS  read-create
    STATUS  current
    DESCRIPTION
        "Clear SmartNAT stats for given SmartNAT Index.
         Note:This mib is not supported for VX instance of Virtualization."
    ::= { slbStatLinkpfClear 4 }

slbStatLinkpfSmartNATAll OBJECT-TYPE
    SYNTAX INTEGER {
        ok(1),
        clearAll(2),
        nonat(3),
        static(4),
        dynamic(5),
        unsupported(2147483647)
    }
    MAX-ACCESS  read-create
    STATUS  current
    DESCRIPTION
        "Clear SmartNAT stats for all SmartNAT entries.
         Note:This mib is not supported for VX instance of Virtualization."
    ::= { slbStatLinkpfClear 5 }

slbStatLinkpfSmartNATTable OBJECT-TYPE
    SYNTAX  SEQUENCE OF SlbStatLinkpfSmartNATEntry
    MAX-ACCESS  not-accessible
    STATUS  current
    DESCRIPTION
        "The link proof SmartNAT statistics table.
         Note:This mib is not supported for VX instance of Virtualization."
    ::= { layer4Stats 40 }

slbStatLinkpfSmartNATEntry OBJECT-TYPE
    SYNTAX  SlbStatLinkpfSmartNATEntry
    MAX-ACCESS  not-accessible
    STATUS  current
    DESCRIPTION
        "The statistics of link proof SmartNAT entry."
    INDEX   { slbStatLinkpfSmartNATIndex }
    ::= { slbStatLinkpfSmartNATTable 1 }

SlbStatLinkpfSmartNATEntry ::= SEQUENCE {
    slbStatLinkpfSmartNATIndex           DisplayString,
    slbStatLinkpfSmartNATCurrSess        Gauge32,
    slbStatLinkpfSmartNATTotSess         Gauge32,
    slbStatLinkpfSmartNATType            INTEGER
}

slbStatLinkpfSmartNATIndex OBJECT-TYPE
    SYNTAX  DisplayString (SIZE(1..32))
    MAX-ACCESS  read-only
    STATUS  current
    DESCRIPTION
        "The SmartNAT index that identifies the SmartNAT entry."
    ::= { slbStatLinkpfSmartNATEntry 1 }

slbStatLinkpfSmartNATCurrSess OBJECT-TYPE
    SYNTAX  Gauge32
    MAX-ACCESS  read-only
    STATUS  current
    DESCRIPTION
        "The number of sessions that are currently handled by this SmartNAT entry."
    ::= { slbStatLinkpfSmartNATEntry 2 }

slbStatLinkpfSmartNATTotSess OBJECT-TYPE
    SYNTAX  Gauge32
    MAX-ACCESS  read-only
    STATUS  current
    DESCRIPTION
        "Total number of sessions that are handled by this SmartNAT entry."
    ::= { slbStatLinkpfSmartNATEntry 3 }

slbStatLinkpfSmartNATType OBJECT-TYPE
    SYNTAX  INTEGER {
        nonat(0),
        static(1),
        dynamic(2),
        unsupported(2147483647)
    }
    MAX-ACCESS  read-only
    STATUS  current
    DESCRIPTION
        "NAT type of sessions that are handled by this SmartNAT entry."
    ::= { slbStatLinkpfSmartNATEntry 4 }

slbStatMaintSymBufferAllocFails OBJECT-TYPE
    SYNTAX  Counter32
    MAX-ACCESS  read-only
    STATUS  current
    DESCRIPTION
        "Total number of Symantec buffers allocation fails.
         Note:This mib is not supported for VX instance of Virtualization."
    ::= { slbMaintStats 30 }

slbStatMaintSymConnAllocFails OBJECT-TYPE
    SYNTAX  Counter32
    MAX-ACCESS  read-only
    STATUS  current
    DESCRIPTION
        "Total number of Symantec Connection allocation fails.
         Note:This mib is not supported for VX instance of Virtualization."
    ::= { slbMaintStats 31 }

slbStatMaintSymInvalidBuffers OBJECT-TYPE
    SYNTAX  Counter32
    MAX-ACCESS  read-only
    STATUS  current
    DESCRIPTION
        "Total number of Symantec Invalid buffers.
         Note:This mib is not supported for VX instance of Virtualization."
    ::= { slbMaintStats 32 }

slbStatMaintSymSegReallocFails OBJECT-TYPE
    SYNTAX  Counter32
    MAX-ACCESS  read-only
    STATUS  current
    DESCRIPTION
        "Total number of Symantec Segment reallocation fails.
         Note:This mib is not supported for VX instance of Virtualization."
    ::= { slbMaintStats 33 }

slbStatMaintSymPacketsIn OBJECT-TYPE
    SYNTAX  Counter32
    MAX-ACCESS  read-only
    STATUS  current
    DESCRIPTION
        "Symantec Deuce Inspection Stats - Total no. of Packets in.
         Note:This mib is not supported for VX instance of Virtualization."
    ::= { slbMaintStats 34 }

slbStatMaintSymPacketsWithNoData OBJECT-TYPE
    SYNTAX  Counter32
    MAX-ACCESS  read-only
    STATUS  current
    DESCRIPTION
        "Symantec Deuce Inspection Stats - Total no. of Packets with no data.
         Note:This mib is not supported for VX instance of Virtualization."
    ::= { slbMaintStats 35 }

slbStatMaintSymTcpPackets OBJECT-TYPE
    SYNTAX  Counter32
    MAX-ACCESS  read-only
    STATUS  current
    DESCRIPTION
        "Symantec Deuce Inspection Stats - Total no. of TCP packets.
         Note:This mib is not supported for VX instance of Virtualization."
    ::= { slbMaintStats 36 }

slbStatMaintSymUdpPackets OBJECT-TYPE
    SYNTAX  Counter32
    MAX-ACCESS  read-only
    STATUS  current
    DESCRIPTION
        "Symantec Deuce Inspection Stats - Total no. of UDP Packets.
         Note:This mib is not supported for VX instance of Virtualization."
    ::= { slbMaintStats 37 }

slbStatMaintSymIcmpPackets OBJECT-TYPE
    SYNTAX  Counter32
    MAX-ACCESS  read-only
    STATUS  current
    DESCRIPTION
        "Symantec Deuce Inspection Stats - Total no. of ICMP Packets.
         Note:This mib is not supported for VX instance of Virtualization."
    ::= { slbMaintStats 38 }

slbStatMaintSymOtherPackets OBJECT-TYPE
    SYNTAX  Counter32
    MAX-ACCESS  read-only
    STATUS  current
    DESCRIPTION
        "Symantec Deuce Inspection Stats - Total no. of Packets 
	 other than TCP UDP or ICMP.
         Note:This mib is not supported for VX instance of Virtualization."
    ::= { slbMaintStats 39 }

slbStatMaintSymMatchCount OBJECT-TYPE
    SYNTAX  Counter32
    MAX-ACCESS  read-only
    STATUS  current
    DESCRIPTION
        "Symantec Deuce Inspection Stats - Total Match Count.
         Note:This mib is not supported for VX instance of Virtualization."
    ::= { slbMaintStats 40 }

slbStatMaintSymFetchErrors OBJECT-TYPE
    SYNTAX  Counter32
    MAX-ACCESS  read-only
    STATUS  current
    DESCRIPTION
        "Symantec Deuce Inspection Stats - Total no. of Fetch Errors.
         Note:This mib is not supported for VX instance of Virtualization."
    ::= { slbMaintStats 41 }

slbStatMaintSymTruncPayloadToMp OBJECT-TYPE
    SYNTAX  Counter32
    MAX-ACCESS  read-only
    STATUS  current
    DESCRIPTION
        "Symantec Deuce Inspection Stats - Total no. of Truncated 
	 payload to MP.
         Note:This mib is not supported for VX instance of Virtualization."
    ::= { slbMaintStats 42 }

slbStatMaintSymPacketsInFastPath OBJECT-TYPE
    SYNTAX  Counter32
    MAX-ACCESS  read-only
    STATUS  current
    DESCRIPTION
        "Symantec Deuce Inspection Stats - Total no. of Packets in 
	 fast path.
         Note:This mib is not supported for VX instance of Virtualization."
    ::= { slbMaintStats 43 }

slbStatMaintPeakBindings OBJECT-TYPE
    SYNTAX  Gauge32 
    MAX-ACCESS  read-only
    STATUS  current
    DESCRIPTION
        "The peak number of bindings on the port.
         Note:This mib is not supported for VX instance of Virtualization."
    ::= { slbMaintStats 44 }

slbStatMaintCurAxBindings OBJECT-TYPE
    SYNTAX  Gauge32 
    MAX-ACCESS  read-only
    STATUS  current
    DESCRIPTION
        "The current number of Ax bindings on the port.
         Note:This mib is not supported for VX instance of Virtualization."
    ::= { slbMaintStats 45 }

slbStatMaintCurAxBindings4Seconds OBJECT-TYPE
    SYNTAX  Gauge32 
    MAX-ACCESS  read-only
    STATUS  current
    DESCRIPTION
        "The 4 second average current number of Ax bindings on the port.
         Note:This mib is not supported for VX instance of Virtualization."
    ::= { slbMaintStats 46 }

slbStatMaintCurAxBindings64Seconds OBJECT-TYPE
    SYNTAX  Gauge32 
    MAX-ACCESS  read-only
    STATUS  current
    DESCRIPTION
        "The 64 second average current number of Ax bindings on the port.
         Note:This mib is not supported for VX instance of Virtualization."
    ::= { slbMaintStats 47 }

slbStatMaintPeakAxBindings OBJECT-TYPE
    SYNTAX  Gauge32 
    MAX-ACCESS  read-only
    STATUS  current
    DESCRIPTION
        "The peak number of Ax bindings on the port.
         Note:This mib is not supported for VX instance of Virtualization."
    ::= { slbMaintStats 48 }

-- END of Symantec SLB Maintenance Stats 

-- Filter Statistics

fltStatTable OBJECT-TYPE
    SYNTAX  SEQUENCE OF FltStatTableEntry
    MAX-ACCESS  not-accessible
    STATUS  current
    DESCRIPTION
        "The filter statistics table.
         Note:This mib is not supported for VX instance of Virtualization."
    ::= { filterStats 1 }

fltStatTableEntry OBJECT-TYPE
    SYNTAX  FltStatTableEntry
    MAX-ACCESS  not-accessible
    STATUS  current
    DESCRIPTION
        "A row in filter statistics table.
         Note:This mib is not supported for VX instance of Virtualization."
    INDEX   { fltStatFltIndex }
    ::= { fltStatTable 1 }

FltStatTableEntry ::= SEQUENCE {
    fltStatFltIndex     Integer32,
    fltStatFltFirings	Counter32,
    fltStatFltFiringsU64  Counter64,
    fltStatFltFiringsUnit INTEGER,
    fltStatFltCurSess   Counter64,
    fltStatFltHighSess  Counter64,
    fltStatFltTotSess   Counter64,
    fltStatFltCurBand   Counter64,
    fltStatFltHighBand  Counter64,
    fltStatFltTotBand   Counter64,
    fltStatFltConnPerSec   Counter64
    }

fltStatFltIndex OBJECT-TYPE 
    SYNTAX  Integer32 
    MAX-ACCESS  read-only
    STATUS  current 
    DESCRIPTION 
        "The number that identifies the filter." 
    ::= { fltStatTableEntry 1 }

fltStatFltFirings OBJECT-TYPE 
    SYNTAX  Counter32
    MAX-ACCESS  read-only
    STATUS  current 
    DESCRIPTION 
        "The number of instances that the received packet matches the 
         filter rule."
    ::= { fltStatTableEntry 2 }

fltStatFltFiringsU64 OBJECT-TYPE
    SYNTAX  Counter64
    MAX-ACCESS  read-only
    STATUS  current
    DESCRIPTION
        "The number of instances that the received packet matches the
         filter rule."
    ::= { fltStatTableEntry 3 }

fltStatFltFiringsUnit OBJECT-TYPE
    SYNTAX  INTEGER{
        sessions(1),
        requests(2),
        packets(3),
        unsupported(2147483647)
    }
    MAX-ACCESS  read-only
    STATUS  current
    DESCRIPTION
        "Unit of total hits for filter as sessions or requests or packets."
    ::= { fltStatTableEntry 4 }

fltStatFltCurSess OBJECT-TYPE
    SYNTAX  Counter64
    MAX-ACCESS  read-only
    STATUS  current
    DESCRIPTION
        "The current number of session for this filter."
    ::= { fltStatTableEntry 5 }

fltStatFltHighSess OBJECT-TYPE
    SYNTAX  Counter64
    MAX-ACCESS  read-only
    STATUS  current
    DESCRIPTION
        "The highest number of session for this filter."
    ::= { fltStatTableEntry 6 }

fltStatFltTotSess OBJECT-TYPE
    SYNTAX  Counter64
    MAX-ACCESS  read-only
    STATUS  current
    DESCRIPTION
        "The total number of session for this filter."
    ::= { fltStatTableEntry 7 }

fltStatFltCurBand OBJECT-TYPE
    SYNTAX  Counter64
    MAX-ACCESS  read-only
    STATUS  current
    DESCRIPTION
        "The current bandwidth for this filter in Kbps."
    ::= { fltStatTableEntry 8 }

fltStatFltHighBand OBJECT-TYPE
    SYNTAX  Counter64
    MAX-ACCESS  read-only
    STATUS  current
    DESCRIPTION
        "The highest bandwidth for this filter in Kbps."
    ::= { fltStatTableEntry 9 }

fltStatFltTotBand OBJECT-TYPE
    SYNTAX  Counter64
    MAX-ACCESS  read-only
    STATUS  current
    DESCRIPTION
        "The total bandwidth for this filter in Mb"
    ::= { fltStatTableEntry 10 }

fltStatFltConnPerSec OBJECT-TYPE
    SYNTAX  Counter64
    MAX-ACCESS  read-only
    STATUS  current
    DESCRIPTION
        "The connection per second for this filter"
    ::= { fltStatTableEntry 11 }


fltRealStatTable OBJECT-TYPE
    SYNTAX  SEQUENCE OF FltRealStatTableEntry
    MAX-ACCESS  not-accessible
    STATUS  current
    DESCRIPTION
        "The filter statistics table for real servers.
         Note:This mib is not supported for VX instance of Virtualization."
    ::= { filterStats 2 }

fltRealStatTableEntry OBJECT-TYPE
    SYNTAX  FltRealStatTableEntry
    MAX-ACCESS  not-accessible
    STATUS  current
    DESCRIPTION
        "A row in filter statistics table according to real server.
         Note:This mib is not supported for VX instance of Virtualization."
    INDEX   { fltRealStatFltIndex,  slbRealStatRealIndex}
    ::= { fltRealStatTable 1 }

FltRealStatTableEntry ::= SEQUENCE {
    fltRealStatFltIndex         Integer32,
    slbRealStatRealIndex        DisplayString,
    slbRealStatRealIPAddr       IpAddress,
    fltRealStatRealCurSess      Counter64,
    fltRealStatRealHighSess     Counter64,
    fltRealStatRealTotSess      Counter64,
    fltRealStatRealCurBand      Counter64,
    fltRealStatRealHighBand     Counter64,
    fltRealStatRealTotBand      Counter64,
    fltRealStatRealConnPerSec   Counter64,
    fltRealStatRealHcReason     DisplayString
    }

fltRealStatFltIndex OBJECT-TYPE
    SYNTAX  Integer32
    MAX-ACCESS  read-only
    STATUS  current
    DESCRIPTION
        "The number that identifies the filter."
    ::= { fltRealStatTableEntry 1 }

slbRealStatRealIndex OBJECT-TYPE
    SYNTAX  DisplayString (SIZE(1..255))
    MAX-ACCESS  read-only
    STATUS  current
    DESCRIPTION
        "The real server index."
    ::= { fltRealStatTableEntry 2 }

slbRealStatRealIPAddr OBJECT-TYPE
    SYNTAX  IpAddress
    MAX-ACCESS  read-only
    STATUS  current
    DESCRIPTION
        "IP address of the real server."
    ::= { fltRealStatTableEntry 3 }

fltRealStatRealCurSess OBJECT-TYPE
    SYNTAX  Counter64
    MAX-ACCESS  read-only
    STATUS  current
    DESCRIPTION
        "The current number of session for the real server."
    ::= { fltRealStatTableEntry 4 }

fltRealStatRealHighSess OBJECT-TYPE
    SYNTAX  Counter64
    MAX-ACCESS  read-only
    STATUS  current
    DESCRIPTION
        "The highest number of session for the real server."
    ::= { fltRealStatTableEntry 5 }

fltRealStatRealTotSess OBJECT-TYPE
    SYNTAX  Counter64
    MAX-ACCESS  read-only
    STATUS  current
    DESCRIPTION
        "The total number of session for the real server."
    ::= { fltRealStatTableEntry 6 }

fltRealStatRealCurBand OBJECT-TYPE
    SYNTAX  Counter64
    MAX-ACCESS  read-only
    STATUS  current
    DESCRIPTION
        "The current bandwidth for the real server in Kbps."
    ::= { fltRealStatTableEntry 7 }

fltRealStatRealHighBand OBJECT-TYPE
    SYNTAX  Counter64
    MAX-ACCESS  read-only
    STATUS  current
    DESCRIPTION
        "The highest bandwidth for the real server in Kbps."
    ::= { fltRealStatTableEntry 8 }

fltRealStatRealTotBand OBJECT-TYPE
    SYNTAX  Counter64
    MAX-ACCESS  read-only
    STATUS  current
    DESCRIPTION
        "The total bandwidth for the real server in Mb."
    ::= { fltRealStatTableEntry 9 }

fltRealStatRealConnPerSec OBJECT-TYPE
    SYNTAX  Counter64
    MAX-ACCESS  read-only
    STATUS  current
    DESCRIPTION
        "The connection per second for the real server."
    ::= { fltRealStatTableEntry 10 }

fltRealStatRealHcReason OBJECT-TYPE
    SYNTAX  DisplayString (SIZE(1..255))
    MAX-ACCESS  read-only
    STATUS  current
    DESCRIPTION
        "The filter HC failure reason description."
    ::= { fltRealStatTableEntry 11 }


-- Persistent stats for filters
fltStatPsessCur OBJECT-TYPE
    SYNTAX Counter64
    MAX-ACCESS read-only
    STATUS current
    DESCRIPTION
        "The current number of persistent session for filters.
         Note:This mib is not supported for VX instance of Virtualization."
    ::= { fltStatPsess 1 }

fltStatPsessHigh OBJECT-TYPE
    SYNTAX Counter64
    MAX-ACCESS read-only
    STATUS current
    DESCRIPTION
        "The highest number of persistent session for filters.
         Note:This mib is not supported for VX instance of Virtualization."
    ::= { fltStatPsess 2 }

fltStatPsessTotal OBJECT-TYPE
    SYNTAX Counter64
    MAX-ACCESS read-only
    STATUS current
    DESCRIPTION
        "The total number of persistent session for filters.
         Note:This mib is not supported for VX instance of Virtualization."
    ::= { fltStatPsess 3 }

-- TrafficEvent stats for filters

fltStatTrafficEventsTable OBJECT-TYPE
    SYNTAX SEQUENCE OF FltStatTrafficEventsTableEntry
    MAX-ACCESS not-accessible
    STATUS current
    DESCRIPTION
        "Traffic Events statistics table for filters.
         Note:This mib is not supported for VX instance of Virtualization."
    ::= { trafficEventStats 2 }

fltStatTrafficEventsTableEntry OBJECT-TYPE
    SYNTAX  FltStatTrafficEventsTableEntry
    MAX-ACCESS  not-accessible
    STATUS  current
    DESCRIPTION
        "A row in traffic events per filter statistics table.
         Note:This mib is not supported for VX instance of Virtualization."
    INDEX {fltTrafficEventStatFltIndex}
    ::= { fltStatTrafficEventsTable 1 }

FltStatTrafficEventsTableEntry ::= SEQUENCE {
    fltTrafficEventStatFltIndex            Integer32,
    fltHttpReqSuccessPerSec                Counter32,
    fltHttpReqSuccessTotal                 Counter64,
    fltHttpRespSuccessPerSec               Counter32,
    fltHttpRespSuccessTotal                Counter64,
    fltFeSSLInfoSuccessPerSec              Counter32,
    fltFeSSLInfoSuccessTotal               Counter64,
    fltBeSSLInfoSuccessPerSec              Counter32,
    fltBeSSLInfoSuccessTotal               Counter64,
    fltHostNameBypassSuccessPerSec         Counter32,
    fltHostNameBypassSuccessTotal          Counter64,
    fltHttpReqFailPerSec                   Counter32,
    fltHttpReqFailTotal                    Counter64,
    fltHttpRespFailPerSec                  Counter32,
    fltHttpRespFailTotal                   Counter64,
    fltFeSSLInfoFailPerSec                 Counter32,
    fltFeSSLInfoFailTotal                  Counter64,
    fltBeSSLInfoFailPerSec                 Counter32,
    fltBeSSLInfoFailTotal                  Counter64,
    fltHostNameBypassFailPerSec            Counter32,
    fltHostNameBypassFailTotal             Counter64,
    fltEventsFieldMissingPerSec            Counter32,
    fltEventsFieldMissingTotal             Counter64,
    fltEventsAllocFailPerSec               Counter32,
    fltEventsAllocFailTotal                Counter64,
    fltEventsQueueFullPerSec               Counter32,
    fltEventsQueueFullTotal                Counter64,
    fltLayer4ReqSuccessPerSec              Counter32,
    fltLayer4ReqSuccessTotal               Counter64,
    fltLayer4ReqFailPerSec                 Counter32,
    fltLayer4ReqFailTotal                  Counter64
    }
fltTrafficEventStatFltIndex OBJECT-TYPE
    SYNTAX  Integer32
    MAX-ACCESS  read-only
    STATUS  current
    DESCRIPTION
        "Index to identify Filter."
    ::= { fltStatTrafficEventsTableEntry 1 }

fltHttpReqSuccessPerSec OBJECT-TYPE
    SYNTAX Counter32
    MAX-ACCESS  read-only
    STATUS  current
    DESCRIPTION
        "No of Http Requests sent as traffic events per second."
    ::= { fltStatTrafficEventsTableEntry 2 }

fltHttpReqSuccessTotal OBJECT-TYPE
    SYNTAX Counter64
    MAX-ACCESS  read-only
    STATUS  current
    DESCRIPTION
        "No of Http Requests sent successfully as traffic events in total."
    ::= { fltStatTrafficEventsTableEntry 3 }

fltHttpRespSuccessPerSec OBJECT-TYPE
    SYNTAX Counter32
    MAX-ACCESS  read-only
    STATUS  current
    DESCRIPTION
        "No of Http responses sent as traffic events per second."
    ::= { fltStatTrafficEventsTableEntry 4 }

fltHttpRespSuccessTotal OBJECT-TYPE
    SYNTAX Counter64
    MAX-ACCESS  read-only
    STATUS  current
    DESCRIPTION
        "No of Http responses sent successfully as traffic events in total."
    ::= { fltStatTrafficEventsTableEntry 5 }

fltFeSSLInfoSuccessPerSec OBJECT-TYPE
    SYNTAX Counter32
    MAX-ACCESS  read-only
    STATUS  current
    DESCRIPTION
        "No of fessl sent successfully as traffice events per second."
    ::= { fltStatTrafficEventsTableEntry 6 }
   
fltFeSSLInfoSuccessTotal OBJECT-TYPE
    SYNTAX Counter64
    MAX-ACCESS  read-only
    STATUS  current
    DESCRIPTION
        "No of fessl sent successfully as traffic events in total."
    ::= { fltStatTrafficEventsTableEntry 7 }

fltBeSSLInfoSuccessPerSec OBJECT-TYPE
    SYNTAX Counter32
    MAX-ACCESS  read-only
    STATUS  current
    DESCRIPTION
        "No of bessl sent successfully as traffice events per second."
    ::= { fltStatTrafficEventsTableEntry 8 }

fltBeSSLInfoSuccessTotal OBJECT-TYPE
    SYNTAX Counter64
    MAX-ACCESS  read-only
    STATUS  current
    DESCRIPTION
        "No of bessl sent successfully as traffic events in total."
    ::= { fltStatTrafficEventsTableEntry 9 }

fltHostNameBypassSuccessPerSec OBJECT-TYPE
    SYNTAX Counter32
    MAX-ACCESS  read-only
    STATUS  current
    DESCRIPTION
        "No of host names bypass sent successfully as traffice events per second."
    ::= { fltStatTrafficEventsTableEntry 10 }

fltHostNameBypassSuccessTotal OBJECT-TYPE
    SYNTAX Counter64
    MAX-ACCESS  read-only
    STATUS  current
    DESCRIPTION
        "No of host names bypass sent successfully as traffic events in total."
    ::= { fltStatTrafficEventsTableEntry 11 }

fltHttpReqFailPerSec OBJECT-TYPE
    SYNTAX Counter32
    MAX-ACCESS  read-only
    STATUS  current
    DESCRIPTION
        "No of Http requests failed to send as traffic events per second."
    ::= { fltStatTrafficEventsTableEntry 12 }

fltHttpReqFailTotal OBJECT-TYPE
    SYNTAX Counter64
    MAX-ACCESS  read-only
    STATUS  current
    DESCRIPTION
        "No of Http requests failed to send as traffic events in total."
    ::= { fltStatTrafficEventsTableEntry 13 }

fltHttpRespFailPerSec OBJECT-TYPE
    SYNTAX Counter32
    MAX-ACCESS  read-only
    STATUS  current
    DESCRIPTION
        "No of Http responses failed to send as traffic events per second."
    ::= { fltStatTrafficEventsTableEntry 14 }

fltHttpRespFailTotal OBJECT-TYPE
    SYNTAX Counter64
    MAX-ACCESS  read-only
    STATUS  current
    DESCRIPTION
        "No of Http responses failed to send as traffic events in total."
    ::= { fltStatTrafficEventsTableEntry 15 }

fltFeSSLInfoFailPerSec OBJECT-TYPE
    SYNTAX Counter32
    MAX-ACCESS  read-only
    STATUS  current
    DESCRIPTION
        "No of fessl failed to send as traffice events per second."
    ::= { fltStatTrafficEventsTableEntry 16 }

fltFeSSLInfoFailTotal OBJECT-TYPE
    SYNTAX Counter64
    MAX-ACCESS  read-only
    STATUS  current
    DESCRIPTION
        "No of fessl failed to send as traffice events in total."
    ::= { fltStatTrafficEventsTableEntry 17 }

fltBeSSLInfoFailPerSec OBJECT-TYPE
    SYNTAX Counter32
    MAX-ACCESS  read-only
    STATUS  current
    DESCRIPTION
        "No of bessl failed to send as traffice events per second."
    ::= { fltStatTrafficEventsTableEntry 18 }

fltBeSSLInfoFailTotal OBJECT-TYPE
    SYNTAX Counter64
    MAX-ACCESS  read-only
    STATUS  current
    DESCRIPTION
        "No of bessl failed to send as traffice events in total."
    ::= { fltStatTrafficEventsTableEntry 19 }

fltHostNameBypassFailPerSec OBJECT-TYPE
    SYNTAX Counter32
    MAX-ACCESS  read-only
    STATUS  current
    DESCRIPTION
        "No of host name bypass failed to send as traffic events per second."
    ::= { fltStatTrafficEventsTableEntry 20 }

fltHostNameBypassFailTotal OBJECT-TYPE
    SYNTAX Counter64
    MAX-ACCESS  read-only
    STATUS  current
    DESCRIPTION
        "No of host name bypass failed to send as traffic events in total."
    ::= { fltStatTrafficEventsTableEntry 21 }

fltEventsFieldMissingPerSec OBJECT-TYPE
    SYNTAX Counter32
    MAX-ACCESS  read-only
    STATUS  current
    DESCRIPTION
        "Event field missing failure per second."
    ::= { fltStatTrafficEventsTableEntry 22 }

fltEventsFieldMissingTotal OBJECT-TYPE
    SYNTAX Counter64
    MAX-ACCESS  read-only
    STATUS  current
    DESCRIPTION
        "Event field missing failure in total."
    ::= { fltStatTrafficEventsTableEntry 23 }

fltEventsAllocFailPerSec OBJECT-TYPE
    SYNTAX Counter32
    MAX-ACCESS  read-only
    STATUS  current
    DESCRIPTION
        "Event allocation failure per second."
    ::= { fltStatTrafficEventsTableEntry 24 }

fltEventsAllocFailTotal OBJECT-TYPE
    SYNTAX Counter64
    MAX-ACCESS  read-only
    STATUS  current
    DESCRIPTION
        "Event allocation failure in total."
    ::= { fltStatTrafficEventsTableEntry 25 }

fltEventsQueueFullPerSec OBJECT-TYPE
    SYNTAX Counter32
    MAX-ACCESS  read-only
    STATUS  current
    DESCRIPTION
        "Event queue full failure per second."
    ::= { fltStatTrafficEventsTableEntry 26 }

fltEventsQueueFullTotal OBJECT-TYPE
    SYNTAX Counter64
    MAX-ACCESS  read-only
    STATUS  current
    DESCRIPTION
        "Event queue full failure in total."
    ::= { fltStatTrafficEventsTableEntry 27 }

fltLayer4ReqSuccessPerSec OBJECT-TYPE
    SYNTAX Counter32
    MAX-ACCESS  read-only
    STATUS  current
    DESCRIPTION
        "Layer4 requests success per second."
    ::= { fltStatTrafficEventsTableEntry 28 }

fltLayer4ReqSuccessTotal OBJECT-TYPE
    SYNTAX Counter64
    MAX-ACCESS  read-only
    STATUS current
    DESCRIPTION
        "Layer4 requests success in total."
    ::= { fltStatTrafficEventsTableEntry 29 }

fltLayer4ReqFailPerSec OBJECT-TYPE
    SYNTAX Counter32
    MAX-ACCESS  read-only
    STATUS  current
    DESCRIPTION
        " Layer4 requests failed to send per second."
    ::= { fltStatTrafficEventsTableEntry 30 }

fltLayer4ReqFailTotal OBJECT-TYPE
    SYNTAX Counter64
    MAX-ACCESS  read-only
    STATUS current
    DESCRIPTION
        "Layer4 requests failed in total."
    ::= { fltStatTrafficEventsTableEntry 31 }

-- Global SLB Statitistics

-- Global SLB Remote Real Server Statistics

gslbStatRemRealServerTable OBJECT-TYPE
    SYNTAX  SEQUENCE OF GslbStatRemRealServerEntry
    MAX-ACCESS  not-accessible
    STATUS  current
    DESCRIPTION
        "The GSLB remote real server statistics table.
         Note:This mib is not supported for VX instance of Virtualization."
    ::= { gslbStats 1 }

gslbStatRemRealServerEntry OBJECT-TYPE
    SYNTAX  GslbStatRemRealServerEntry
    MAX-ACCESS  not-accessible
    STATUS  current
    DESCRIPTION
        "A row in the remote real server statistics table.
         Note:This mib is not supported for VX instance of Virtualization."
    INDEX   { gslbStatRemRealServerIndex }
    ::= { gslbStatRemRealServerTable 1 }

GslbStatRemRealServerEntry ::=	SEQUENCE {
    gslbStatRemRealServerIndex          Integer32,
    gslbStatRemRealServerDnsHandoffs    Counter32,
    gslbStatRemRealServerHttpRedirs     Counter32
    }

gslbStatRemRealServerIndex OBJECT-TYPE 
    SYNTAX  Integer32 
    MAX-ACCESS  read-only
    STATUS  current 
    DESCRIPTION 
        "The server number that identifies the remote real server." 
    ::= { gslbStatRemRealServerEntry 1 }

gslbStatRemRealServerDnsHandoffs OBJECT-TYPE 
    SYNTAX  Counter32 
    MAX-ACCESS  read-only
    STATUS  current 
    DESCRIPTION 
        "The number of DNS handoffs by the remote real server."
    ::= { gslbStatRemRealServerEntry 2 }

gslbStatRemRealServerHttpRedirs OBJECT-TYPE 
    SYNTAX  Counter32 
    MAX-ACCESS  read-only
    STATUS  current 
    DESCRIPTION 
        "The number of HTTP redirections by the remote real server."
    ::= { gslbStatRemRealServerEntry 3 }

gslbStatsClear OBJECT-TYPE
    SYNTAX INTEGER {
        ok(1),
        clear(2),
        unsupported(2147483647)
        }
    MAX-ACCESS read-write
    STATUS current
    DESCRIPTION
        "This is an action object to clear the non-operational GSLB statistics.
         ok(1) is returned when read.
         Note:This mib is not supported for VX instance of Virtualization."
    ::= { gslbStats 12 }

-- Global SLB Remote Real Server Enhanced Table Statistics

gslbStatRemEnhRealServerTable OBJECT-TYPE
    SYNTAX  SEQUENCE OF GslbStatRemEnhRealServerEntry
    MAX-ACCESS  not-accessible
    STATUS  current
    DESCRIPTION
        "The GSLB remote real server statistics table.
         Note:This mib is not supported for VX instance of Virtualization."
    ::= { gslbStats 10 }

gslbStatRemEnhRealServerEntry OBJECT-TYPE
    SYNTAX  GslbStatRemEnhRealServerEntry
    MAX-ACCESS  not-accessible
    STATUS  current
    DESCRIPTION
        "A row in the remote real server statistics table."
    INDEX   { gslbStatRemEnhRealServerIndex }
    ::= { gslbStatRemEnhRealServerTable 1 }

    GslbStatRemEnhRealServerEntry ::=  SEQUENCE {
        gslbStatRemEnhRealServerIndex              DisplayString,
        gslbStatRemEnhRealServerDnsHandoffs        Counter32,
        gslbStatRemEnhRealServerHttpRedirs         Counter32,
        gslbStatRemEnhRealServerThresholdExceeded  Counter32,
        gslbStatRemEnhRealServerIpAddress          IpAddress,
        gslbStatRemEnhRealServerIpv6Address        DisplayString,
        gslbStatRemEnhRealServerIpVer              INTEGER
    }

gslbStatRemEnhRealServerIndex OBJECT-TYPE
    SYNTAX  DisplayString (SIZE(1..255))
    MAX-ACCESS  read-only
    STATUS  current
    DESCRIPTION
        "The server number that identifies the remote real server."
    ::= { gslbStatRemEnhRealServerEntry 1 }

gslbStatRemEnhRealServerDnsHandoffs OBJECT-TYPE
    SYNTAX  Counter32
    MAX-ACCESS  read-only
    STATUS  current
    DESCRIPTION
        "The number of DNS handoffs by the remote real server."
    ::= { gslbStatRemEnhRealServerEntry 2 }

gslbStatRemEnhRealServerHttpRedirs OBJECT-TYPE
    SYNTAX  Counter32
    MAX-ACCESS  read-only
    STATUS  current
    DESCRIPTION
        "The number of HTTP redirections by the remote real server."
    ::= { gslbStatRemEnhRealServerEntry 3 }
       
gslbStatRemEnhRealServerThresholdExceeded OBJECT-TYPE
    SYNTAX  Counter32
    MAX-ACCESS  read-only
    STATUS  current
    DESCRIPTION
        "The total number of hits exceeded threshold for remote real server."
    ::= { gslbStatRemEnhRealServerEntry 4 }
	
gslbStatRemEnhRealServerIpAddress OBJECT-TYPE
    SYNTAX  IpAddress
    MAX-ACCESS  read-only
    STATUS  current
    DESCRIPTION
        "The IP address of the remote real server."
    ::= { gslbStatRemEnhRealServerEntry 5 }

 gslbStatRemEnhRealServerIpv6Address OBJECT-TYPE
     SYNTAX DisplayString (SIZE(0..40))
     MAX-ACCESS  read-only
     STATUS  current
     DESCRIPTION
         "The IPv6 address of the remote real server."
    ::= { gslbStatRemEnhRealServerEntry 6 }

gslbStatRemEnhRealServerIpVer OBJECT-TYPE
    SYNTAX  INTEGER{
        ipv4(1),
        ipv6(2),
        unsupported(2147483647)
    }
    MAX-ACCESS  read-only
    STATUS  current
    DESCRIPTION
        "The type of IP address of the remote real server."
    ::= { gslbStatRemEnhRealServerEntry 7 }

-- The Global SLB Maintenance Statistics

gslbMaintStats OBJECT IDENTIFIER ::= { gslbStats 2 }

gslbStatMaintInGoodSiteUpdates OBJECT-TYPE 
    SYNTAX  Counter32 
    MAX-ACCESS  read-only
    STATUS  current 
    DESCRIPTION 
        "The number of good DSSPv1 remote site updates received.
         Note:This mib is not supported for VX instance of Virtualization."
    ::= { gslbMaintStats 1 }

gslbStatMaintInBadSiteUpdates OBJECT-TYPE 
    SYNTAX  Counter32 
    MAX-ACCESS  read-only
    STATUS  current 
    DESCRIPTION 
        "The number of bad remote site packets received.
         Note:This mib is not supported for VX instance of Virtualization."
    ::= { gslbMaintStats 2 }

gslbStatMaintOutSiteUpdates OBJECT-TYPE
    SYNTAX  Counter32
    MAX-ACCESS  read-only
    STATUS  current
    DESCRIPTION
        "The number of DSSPv1 remote site updates sent.
         Note:This mib is not supported for VX instance of Virtualization."
    ::= { gslbMaintStats 3 }

gslbStatMaintInGoodSiteUpdates2 OBJECT-TYPE
    SYNTAX  Counter32
    MAX-ACCESS  read-only
    STATUS  current
    DESCRIPTION
        "The number of good DSSPv2 remote site updates received.
         Note:This mib is not supported for VX instance of Virtualization."
    ::= { gslbMaintStats 4 }

gslbStatMaintOutSiteUpdates2 OBJECT-TYPE
    SYNTAX  Counter32
    MAX-ACCESS  read-only
    STATUS  current
    DESCRIPTION
        "The number of DSSPv2 remote site updates sent.
         Note:This mib is not supported for VX instance of Virtualization."
    ::= { gslbMaintStats 5 }

gslbStatMaintLocalSitePers OBJECT-TYPE
    SYNTAX  Counter32
    MAX-ACCESS  read-only
    STATUS  current
    DESCRIPTION
        "The number of local site DNS persistence cache entries added.
         Note:This mib is not supported for VX instance of Virtualization."
    ::= { gslbMaintStats 8 }

gslbStatMaintInDns OBJECT-TYPE
    SYNTAX  Counter32
    MAX-ACCESS  read-only
    STATUS  current
    DESCRIPTION
        "The number of DNS queries received.
         Note:This mib is not supported for VX instance of Virtualization."
    ::= { gslbMaintStats 10 }

gslbStatMaintInBadDns OBJECT-TYPE
    SYNTAX  Counter32
    MAX-ACCESS  read-only
    STATUS  current
    DESCRIPTION
        "The number of bad DNS queries received.
         Note:This mib is not supported for VX instance of Virtualization."
    ::= { gslbMaintStats 11 }

gslbStatMaintOutDns OBJECT-TYPE
    SYNTAX  Counter32
    MAX-ACCESS  read-only
    STATUS  current
    DESCRIPTION
        "The number of DNS responses sent.
         Note:This mib is not supported for VX instance of Virtualization."
    ::= { gslbMaintStats 12 }

gslbStatMaintInHttp OBJECT-TYPE
    SYNTAX  Counter32
    MAX-ACCESS  read-only
    STATUS  current
    DESCRIPTION
        "The number of HTTP requests received.
         Note:This mib is not supported for VX instance of Virtualization."
    ::= { gslbMaintStats 13 }

gslbStatMaintInBadHttp OBJECT-TYPE
    SYNTAX  Counter32
    MAX-ACCESS  read-only
    STATUS  current
    DESCRIPTION
        "The number of bad HTTP requests received.
         Note:This mib is not supported for VX instance of Virtualization."
    ::= { gslbMaintStats 14 }

gslbStatMaintOutHttp OBJECT-TYPE
    SYNTAX  Counter32
    MAX-ACCESS  read-only
    STATUS  current
    DESCRIPTION
        "The number of HTTP responses sent.
         Note:This mib is not supported for VX instance of Virtualization."
    ::= { gslbMaintStats 15 }

gslbStatMaintNoServer OBJECT-TYPE
    SYNTAX  Counter32
    MAX-ACCESS  read-only
    STATUS  current
    DESCRIPTION
        "The number of times no server returned.
         Note:This mib is not supported for VX instance of Virtualization."
    ::= { gslbMaintStats 16 }

gslbStatMaintNoDomain OBJECT-TYPE
    SYNTAX  Counter32
    MAX-ACCESS  read-only
    STATUS  current
    DESCRIPTION
        "The number of times no matching domain.
         Note:This mib is not supported for VX instance of Virtualization."
    ::= { gslbMaintStats 17 }

gslbStatMaintHostHits OBJECT-TYPE
    SYNTAX  Counter32
    MAX-ACCESS  read-only
    STATUS  current
    DESCRIPTION
        "The number of hostname domain hits.
         Note:This mib is not supported for VX instance of Virtualization."
    ::= { gslbMaintStats 18 }

gslbStatMaintRuleHits OBJECT-TYPE
    SYNTAX  Counter32
    MAX-ACCESS  read-only
    STATUS  current
    DESCRIPTION
        "The number of network domain hits.
         Note:This mib is not supported for VX instance of Virtualization."
    ::= { gslbMaintStats 19 }

gslbStatMaintVirtHits OBJECT-TYPE
    SYNTAX  Counter32
    MAX-ACCESS  read-only
    STATUS  current
    DESCRIPTION
        "The number of basic domain hits.
         Note:This mib is not supported for VX instance of Virtualization."
    ::= { gslbMaintStats 20 }

gslbStatMaintNoServerHost OBJECT-TYPE
    SYNTAX  Counter32
    MAX-ACCESS  read-only
    STATUS  current
    DESCRIPTION
        "The number of times no server returned for hostname domain.
         Note:This mib is not supported for VX instance of Virtualization."
    ::= { gslbMaintStats 21 }

gslbStatMaintNoServerRule OBJECT-TYPE
    SYNTAX  Counter32
    MAX-ACCESS  read-only
    STATUS  current
    DESCRIPTION
        "The number of times no server returned for network domain.
         Note:This mib is not supported for VX instance of Virtualization."
    ::= { gslbMaintStats 22 }

gslbStatMaintNoServerVirt OBJECT-TYPE
    SYNTAX  Counter32
    MAX-ACCESS  read-only
    STATUS  current
    DESCRIPTION
        "The number of times no server returned for basic domain.
         Note:This mib is not supported for VX instance of Virtualization."
    ::= { gslbMaintStats 23 }

gslbStatMaintLastNoResultDomain OBJECT-TYPE
    SYNTAX DisplayString (SIZE(0..255))
    MAX-ACCESS  read-only
    STATUS  current
    DESCRIPTION
        "The last no result domain.
         Note:This mib is not supported for VX instance of Virtualization."
    ::= { gslbMaintStats 24 }

gslbStatMaintLastSrcIp OBJECT-TYPE
    SYNTAX  IpAddress
    MAX-ACCESS  read-only
    STATUS  current
    DESCRIPTION
        "The last source IP address.
         Note:This mib is not supported for VX instance of Virtualization."
    ::= { gslbMaintStats 25 }

gslbStatMaintThresholdHits OBJECT-TYPE
    SYNTAX  Counter32
    MAX-ACCESS  read-only
    STATUS  current
    DESCRIPTION
        "The number of times any servers not returned due to threshold exceeded for the corresponding server.
         Note:This mib is not supported for VX instance of Virtualization."
    ::= { gslbMaintStats 26 }

gslbStatMaintLastSrcIpV6 OBJECT-TYPE
   SYNTAX DisplayString (SIZE(0..40))
    MAX-ACCESS  read-only
    STATUS  current
    DESCRIPTION
        "The last source IPV6 address.
         Note:This mib is not supported for VX instance of Virtualization."
   ::= { gslbMaintStats 27 }

-- Global SLB Group Statistics

gslbStatGroupTable OBJECT-TYPE
    SYNTAX  SEQUENCE OF GslbStatGroupEntry
    MAX-ACCESS  not-accessible
    STATUS  current
    DESCRIPTION
        "The GSLB group statistics table.
         Note:This mib is not supported for VX instance of Virtualization."
    ::= { gslbStats 3 }

gslbStatGroupEntry OBJECT-TYPE
    SYNTAX  GslbStatGroupEntry
    MAX-ACCESS  not-accessible
    STATUS  current
    DESCRIPTION
        "A row in the GSLB group statistics table."
    INDEX   { gslbStatGroupIndex }
    ::= { gslbStatGroupTable 1 }

GslbStatGroupEntry ::=	SEQUENCE {
    gslbStatGroupIndex          Integer32,
    gslbStatGroupDnsHandoffs    Counter32,
    gslbStatGroupHttpRedirs     Counter32
    }

gslbStatGroupIndex OBJECT-TYPE 
    SYNTAX  Integer32 
    MAX-ACCESS  read-only
    STATUS  current 
    DESCRIPTION 
        "The group number that identifies the real server group." 
    ::= { gslbStatGroupEntry 1 }

gslbStatGroupDnsHandoffs OBJECT-TYPE 
    SYNTAX  Counter32 
    MAX-ACCESS  read-only
    STATUS  current 
    DESCRIPTION 
        "The total number of DNS hand-offs sent to the remote real servers in 
         the group."
    ::= { gslbStatGroupEntry 2 }

gslbStatGroupHttpRedirs OBJECT-TYPE 
    SYNTAX  Counter32 
    MAX-ACCESS  read-only
    STATUS  current 
    DESCRIPTION 
        "The total number of HTTP redirects sent to the remote real servers in 
         the group."
    ::= { gslbStatGroupEntry 3 }

-- Global SLB Virtual Server Statistics

gslbStatVirtServerTable OBJECT-TYPE
    SYNTAX  SEQUENCE OF GslbStatVirtServerEntry
    MAX-ACCESS  not-accessible
    STATUS  current
    DESCRIPTION
        "The Global SLB virtual server statistics table.
         Note:This mib is not supported for VX instance of Virtualization."
    ::= { gslbStats 4 }

gslbStatVirtServerEntry OBJECT-TYPE
    SYNTAX  GslbStatVirtServerEntry
    MAX-ACCESS  not-accessible
    STATUS  current
    DESCRIPTION
        "A row in the Global SLB virtual server statistics table."
    INDEX   { gslbStatVirtServerIdx, gslbStatVirtServerServiceIdx, 
              gslbStatVirtServerRserverIdx }
    ::= { gslbStatVirtServerTable 1 }

GslbStatVirtServerEntry ::=	SEQUENCE {
    gslbStatVirtServerIdx            Integer32,
    gslbStatVirtServerServiceIdx     Integer32,
    gslbStatVirtServerRserverIdx     Integer32,
    gslbStatVirtServerVirtPort       Integer32,
    gslbStatVirtServerIpAddress      IpAddress,
    gslbStatVirtServerResponseTime   Integer32,
    gslbStatVirtServerMinSessAvail   Gauge32,
    gslbStatVirtServerDname          DisplayString,
    gslbStatVirtServerRemSite        Integer32,
    gslbStatVirtDnsDirect            Counter32
    }
  
gslbStatVirtServerIdx OBJECT-TYPE 
    SYNTAX  Integer32 
    MAX-ACCESS  read-only
    STATUS  current 
    DESCRIPTION 
        "The virtual server number that identifies the virtual server." 
    ::= { gslbStatVirtServerEntry 1 }

gslbStatVirtServerServiceIdx OBJECT-TYPE 
    SYNTAX  Integer32 
    MAX-ACCESS  read-only
    STATUS  current 
    DESCRIPTION 
        "The virtual server service number that identifies the virtual 
         service." 
    ::= { gslbStatVirtServerEntry 2 }

gslbStatVirtServerRserverIdx OBJECT-TYPE 
    SYNTAX  Integer32 
    MAX-ACCESS  read-only
    STATUS  current 
    DESCRIPTION 
        "The real server number that identifies a remote site. A index of 
         0 indicates a local virtual server number." 
    ::= { gslbStatVirtServerEntry 3 }

gslbStatVirtServerVirtPort OBJECT-TYPE 
    SYNTAX  Integer32
    MAX-ACCESS  read-only
    STATUS  current 
    DESCRIPTION 
        "The virtual server service port."
    ::= { gslbStatVirtServerEntry 4 }

gslbStatVirtServerIpAddress OBJECT-TYPE 
    SYNTAX  IpAddress
    MAX-ACCESS  read-only
    STATUS  current 
    DESCRIPTION 
        "The IP address of the virtual server or remote real server."
    ::= { gslbStatVirtServerEntry 5 }

gslbStatVirtServerResponseTime OBJECT-TYPE 
    SYNTAX  Integer32
    MAX-ACCESS  read-only
    STATUS  current 
    DESCRIPTION 
        "The average time (current weight) that each service takes to respond
         to information exchanges with its peers The time is specified in 
         ticks of 65 milliseconds."
    ::= { gslbStatVirtServerEntry 6 }

gslbStatVirtServerMinSessAvail OBJECT-TYPE 
    SYNTAX  Gauge32
    MAX-ACCESS  read-only
    STATUS  current 
    DESCRIPTION 
        "The current number of sessions available for serving client requests.
         This number will change as client traffic loads change, or as real 
         servers under the virtual server or remote sites go in or out of 
         service."
    ::= { gslbStatVirtServerEntry 7 }

gslbStatVirtServerDname OBJECT-TYPE
    SYNTAX DisplayString (SIZE(0..64))
    MAX-ACCESS read-only
    STATUS current
    DESCRIPTION
        "The domain name of the virtual server and remote real server."
    ::= { gslbStatVirtServerEntry 8 }

gslbStatVirtServerRemSite OBJECT-TYPE
    SYNTAX Integer32
    MAX-ACCESS read-only
    STATUS current
    DESCRIPTION
        "The remote site of the remote real server. For virtual server, the remote site is 0."
    ::= { gslbStatVirtServerEntry 9 }

gslbStatVirtDnsDirect OBJECT-TYPE
    SYNTAX Counter32
    MAX-ACCESS read-only
    STATUS current
    DESCRIPTION
        "The total number of DNS directs sent to the virtual server or remote real server."
    ::= { gslbStatVirtServerEntry 10 }

-- Global SLB Remote Site Statistics

gslbStatEnhVirtServerTable OBJECT-TYPE
    SYNTAX  SEQUENCE OF GslbStatEnhVirtServerEntry
    MAX-ACCESS  not-accessible
    STATUS  current
    DESCRIPTION
        "The Global SLB virtual server statistics table.
         Note:This mib is not supported for VX instance of Virtualization."
    ::= { gslbStats 11 }

gslbStatEnhVirtServerEntry OBJECT-TYPE
    SYNTAX  GslbStatEnhVirtServerEntry
    MAX-ACCESS  not-accessible
    STATUS  current
    DESCRIPTION
        "A row in the Global SLB virtual server statistics table."
    INDEX   { gslbStatEnhVirtServerIdx, gslbStatEnhVirtServerServiceIdx,
              gslbStatEnhVirtServerRserverIdx }
    ::= { gslbStatEnhVirtServerTable 1 }

GslbStatEnhVirtServerEntry ::=     SEQUENCE {
    gslbStatEnhVirtServerIdx            DisplayString,
    gslbStatEnhVirtServerServiceIdx     Integer32,
    gslbStatEnhVirtServerRserverIdx     DisplayString,
    gslbStatEnhVirtServerVirtPort       Integer32,
    gslbStatEnhVirtServerIpAddress      IpAddress,
    gslbStatEnhVirtServerResponseTime   Integer32,
    gslbStatEnhVirtServerMinSessAvail   Gauge32,
    gslbStatEnhVirtServerDname          DisplayString,
    gslbStatEnhVirtServerRemSite        Integer32,
    gslbStatEnhVirtDnsDirect            Counter32,
    gslbStatEnhVirtServerIpv6Address    DisplayString,
    gslbStatEnhVirtServerHttpRedirs     Counter32
 }

gslbStatEnhVirtServerIdx OBJECT-TYPE
    SYNTAX DisplayString (SIZE(1..255))
    MAX-ACCESS  read-only
    STATUS  current
    DESCRIPTION
        "The virtual server number that identifies the virtual server."
    ::= { gslbStatEnhVirtServerEntry 1 }

gslbStatEnhVirtServerServiceIdx OBJECT-TYPE
    SYNTAX  Integer32
    MAX-ACCESS  read-only
    STATUS  current
    DESCRIPTION
        "The virtual server service number that identifies the virtual
         service."
    ::= { gslbStatEnhVirtServerEntry 2 }

gslbStatEnhVirtServerRserverIdx OBJECT-TYPE
    SYNTAX DisplayString (SIZE(1..255))
    MAX-ACCESS  read-only
    STATUS  current
    DESCRIPTION
        "The real server number that identifies a remote site. A index of
         0 indicates a local virtual server number."
    ::= { gslbStatEnhVirtServerEntry 3 }

gslbStatEnhVirtServerVirtPort OBJECT-TYPE
    SYNTAX  Integer32
    MAX-ACCESS  read-only
    STATUS  current
    DESCRIPTION
        "The virtual server service port."
    ::= { gslbStatEnhVirtServerEntry 4 }

gslbStatEnhVirtServerIpAddress OBJECT-TYPE
    SYNTAX  IpAddress
    MAX-ACCESS  read-only
    STATUS  current
    DESCRIPTION
        "The IP address of the virtual server or remote real server."
    ::= { gslbStatEnhVirtServerEntry 5 }

gslbStatEnhVirtServerResponseTime OBJECT-TYPE
    SYNTAX  Integer32
    MAX-ACCESS  read-only
    STATUS  current
    DESCRIPTION
      "The average time (current weight) that each service takes to respond
         to information exchanges with its peers The time is specified in
         ticks of 65 milliseconds."
    ::= { gslbStatEnhVirtServerEntry 6 }

gslbStatEnhVirtServerMinSessAvail OBJECT-TYPE
    SYNTAX  Gauge32
    MAX-ACCESS  read-only
    STATUS  current
    DESCRIPTION
        "The current number of sessions available for serving client requests.
         This number will change as client traffic loads change, or as real
         servers under the virtual server or remote sites go in or out of
         service."
    ::= { gslbStatEnhVirtServerEntry 7 }

gslbStatEnhVirtServerDname OBJECT-TYPE
    SYNTAX DisplayString (SIZE(0..64))
    MAX-ACCESS read-only
    STATUS current
    DESCRIPTION
        "The domain name of the virtual server and remote real server."
    ::= { gslbStatEnhVirtServerEntry 8 }

gslbStatEnhVirtServerRemSite OBJECT-TYPE
    SYNTAX Integer32
    MAX-ACCESS read-only
    STATUS current
    DESCRIPTION
        "The remote site of the remote real server. For virtual server, the remote site is 0."
    ::= { gslbStatEnhVirtServerEntry 9 }

gslbStatEnhVirtDnsDirect OBJECT-TYPE
    SYNTAX Counter32
    MAX-ACCESS read-only
    STATUS current
    DESCRIPTION
        "The total number of DNS directs sent to the virtual server or remote real server."
    ::= { gslbStatEnhVirtServerEntry 10 }

gslbStatEnhVirtServerIpv6Address OBJECT-TYPE
    SYNTAX DisplayString (SIZE(1..40))
    MAX-ACCESS  read-only
    STATUS  current
    DESCRIPTION
        "The IPv6 address of the virtual server or remote real server."
    ::= { gslbStatEnhVirtServerEntry 11 }

gslbStatEnhVirtServerHttpRedirs OBJECT-TYPE
    SYNTAX  Counter32
    MAX-ACCESS  read-only
    STATUS  current
    DESCRIPTION
        "The number of HTTP redirections by the remote real server."
    ::= { gslbStatEnhVirtServerEntry 12 }


gslbStatRemSiteTable OBJECT-TYPE
    SYNTAX SEQUENCE OF GslbStatRemSiteTableEntry
    MAX-ACCESS not-accessible
    STATUS current
    DESCRIPTION
        "The Global SLB remote site statistics table.
         Note:This mib is not supported for VX instance of Virtualization."
    ::= { gslbStats 5 }

gslbStatRemSiteTableEntry OBJECT-TYPE
    SYNTAX GslbStatRemSiteTableEntry
    MAX-ACCESS not-accessible
    STATUS current
    DESCRIPTION
        "A row in the Global SLB remote site statistics table."
    INDEX { gslbStatRemSiteIdx }
    ::= { gslbStatRemSiteTable 1 }

GslbStatRemSiteTableEntry ::=     SEQUENCE {
    gslbStatRemSiteIdx            Integer32,
    gslbStatRemSiteOutUpdates     Counter32,
    gslbStatRemSiteInUpdates      Counter32,
    gslbStatRemSiteOutUpdates2    Counter32,
    gslbStatRemSiteInUpdates2     Counter32,
    gslbStatRemSiteInBadUpdates   Counter32
    }

gslbStatRemSiteIdx OBJECT-TYPE
    SYNTAX Integer32
    MAX-ACCESS read-only
    STATUS current
    DESCRIPTION
        "The remote site number that identifies the remote site."
    ::= { gslbStatRemSiteTableEntry 1 }

gslbStatRemSiteOutUpdates OBJECT-TYPE
    SYNTAX Counter32
    MAX-ACCESS read-only
    STATUS current
    DESCRIPTION
        "The number of DSSPv1 remote site updates sent."
    ::= { gslbStatRemSiteTableEntry 2 }

gslbStatRemSiteInUpdates OBJECT-TYPE
    SYNTAX Counter32
    MAX-ACCESS read-only
    STATUS current
    DESCRIPTION
        "The number of good DSSPv1 remote site updates received."
    ::= { gslbStatRemSiteTableEntry 3 }

gslbStatRemSiteOutUpdates2 OBJECT-TYPE
    SYNTAX Counter32
    MAX-ACCESS read-only
    STATUS current
    DESCRIPTION
        "The number of DSSPv2 remote site updates sent."
    ::= { gslbStatRemSiteTableEntry 4 }

gslbStatRemSiteInUpdates2 OBJECT-TYPE
    SYNTAX Counter32
    MAX-ACCESS read-only
    STATUS current
    DESCRIPTION
        "The number of good DSSPv2 remote site updates received."
    ::= { gslbStatRemSiteTableEntry 5 }

gslbStatRemSiteInBadUpdates OBJECT-TYPE
    SYNTAX Counter32
    MAX-ACCESS read-only
    STATUS current
    DESCRIPTION
        "The number of bad remote site updates received."
    ::= { gslbStatRemSiteTableEntry 6 }

-- Global SLB Enhanced Network Statistics

gslbStatEnhNetworkTable OBJECT-TYPE
    SYNTAX SEQUENCE OF GslbStatEnhNetworkTableEntry
    MAX-ACCESS not-accessible
    STATUS current
    DESCRIPTION
        "The Global SLB network statistics table.
         Note:This mib is not supported for VX instance of Virtualization."
    ::= { gslbStats 6 }

gslbStatEnhNetworkTableEntry OBJECT-TYPE
    SYNTAX GslbStatEnhNetworkTableEntry
    MAX-ACCESS not-accessible
    STATUS current
    DESCRIPTION
        "A row in the Global SLB network statistics table."
    INDEX { gslbStatEnhNetworkIdx }
    ::= { gslbStatEnhNetworkTable 1 }

GslbStatEnhNetworkTableEntry ::=     SEQUENCE {
    gslbStatEnhNetworkIdx             Integer32,
    gslbStatEnhNetworkHit             Counter32,
    gslbStatEnhNetworkIpAddr          IpAddress,
    gslbStatEnhNetworkIpv6Addr        DisplayString,
    gslbStatEnhNetworkSrcType         Integer32,
    gslbStatEnhNetworkClassId         DisplayString
    }

gslbStatEnhNetworkIdx OBJECT-TYPE
    SYNTAX Integer32
    MAX-ACCESS read-only
    STATUS current
    DESCRIPTION
        "The network number that identifies the network."
    ::= { gslbStatEnhNetworkTableEntry 1 }

gslbStatEnhNetworkHit OBJECT-TYPE
    SYNTAX Counter32
    MAX-ACCESS read-only
    STATUS current
    DESCRIPTION
        "The number of times network is selected."
    ::= { gslbStatEnhNetworkTableEntry 2 }

gslbStatEnhNetworkIpAddr OBJECT-TYPE
    SYNTAX IpAddress
    MAX-ACCESS read-only
    STATUS current
    DESCRIPTION
        "The network source IP address."
    ::= { gslbStatEnhNetworkTableEntry 3 }

gslbStatEnhNetworkIpv6Addr OBJECT-TYPE
    SYNTAX DisplayString
    MAX-ACCESS read-only
    STATUS current
    DESCRIPTION
        "The network source IPv6 IP address."
    ::= { gslbStatEnhNetworkTableEntry 4 }

gslbStatEnhNetworkSrcType OBJECT-TYPE
    SYNTAX Integer32
    MAX-ACCESS read-only
    STATUS current
    DESCRIPTION
        "Source address type (1)address (2)nwclass."
    ::= { gslbStatEnhNetworkTableEntry 5 }

gslbStatEnhNetworkClassId OBJECT-TYPE
    SYNTAX DisplayString
    MAX-ACCESS read-only
    STATUS current
    DESCRIPTION
        "The network class and its region."
    ::= { gslbStatEnhNetworkTableEntry 6 }

-- Global SLB Rule Statistics

gslbStatRuleTable OBJECT-TYPE
    SYNTAX SEQUENCE OF GslbStatRuleTableEntry
    MAX-ACCESS not-accessible
    STATUS current
    DESCRIPTION
        "The Global SLB rule statistics table.
         Note:This mib is not supported for VX instance of Virtualization."
    ::= { gslbStats 7 }

gslbStatRuleTableEntry OBJECT-TYPE
    SYNTAX GslbStatRuleTableEntry
    MAX-ACCESS not-accessible
    STATUS current
    DESCRIPTION
        "A row in the Global SLB rule statistics table."
    INDEX { gslbStatRuleIdx }
    ::= { gslbStatRuleTable 1 }

GslbStatRuleTableEntry ::=     SEQUENCE {
    gslbStatRuleIdx               Integer32,
    gslbStatRuleLeastconns        Counter32,
    gslbStatRuleRoundrobin        Counter32,
    gslbStatRuleMinmisses         Counter32,
    gslbStatRuleHash              Counter32,
    gslbStatRuleResponse          Counter32,
    gslbStatRuleGeographical      Counter32,
    gslbStatRuleNetwork           Counter32,
    gslbStatRuleRandom            Counter32,
    gslbStatRuleAvailability      Counter32,
    gslbStatRuleQos               Counter32,
    gslbStatRulePersistence       Counter32,
    gslbStatRuleLocal             Counter32,
    gslbStatRuleAlways            Counter32,
    gslbStatRuleRemote            Counter32,
    gslbStatRuleTotal             Counter32,
    gslbStatRulePhash             Counter32,
    gslbStatRuleAbsLeastconns     Counter32
    }

gslbStatRuleIdx OBJECT-TYPE
    SYNTAX Integer32
    MAX-ACCESS read-only
    STATUS current
    DESCRIPTION
        "The rule number that identifies the rule."
    ::= { gslbStatRuleTableEntry 1 }

gslbStatRuleLeastconns OBJECT-TYPE
    SYNTAX Counter32
    MAX-ACCESS read-only
    STATUS current
    DESCRIPTION
        "The number of times leastconns is used."
    ::= { gslbStatRuleTableEntry 2 }

gslbStatRuleRoundrobin OBJECT-TYPE
    SYNTAX Counter32
    MAX-ACCESS read-only
    STATUS current
    DESCRIPTION
        "The number of times roundrobin is used."
    ::= { gslbStatRuleTableEntry 3 }

gslbStatRuleMinmisses OBJECT-TYPE
    SYNTAX Counter32
    MAX-ACCESS read-only
    STATUS current
    DESCRIPTION
        "The number of times minmisses is used."
    ::= { gslbStatRuleTableEntry 4 }

gslbStatRuleHash OBJECT-TYPE
    SYNTAX Counter32
    MAX-ACCESS read-only
    STATUS current
    DESCRIPTION
        "The number of times hash is used."
    ::= { gslbStatRuleTableEntry 5 }

gslbStatRuleResponse OBJECT-TYPE
    SYNTAX Counter32
    MAX-ACCESS read-only
    STATUS current
    DESCRIPTION
        "The number of times response is used."
    ::= { gslbStatRuleTableEntry 6 }

gslbStatRuleGeographical OBJECT-TYPE
    SYNTAX Counter32
    MAX-ACCESS read-only
    STATUS current
    DESCRIPTION
        "The number of times geographical is used."
    ::= { gslbStatRuleTableEntry 7 }

gslbStatRuleNetwork OBJECT-TYPE
    SYNTAX Counter32
    MAX-ACCESS read-only
    STATUS current
    DESCRIPTION
        "The number of times network is used."
    ::= { gslbStatRuleTableEntry 8 }

gslbStatRuleRandom OBJECT-TYPE
    SYNTAX Counter32
    MAX-ACCESS read-only
    STATUS current
    DESCRIPTION
        "The number of times random is used."
    ::= { gslbStatRuleTableEntry 9 }

gslbStatRuleAvailability OBJECT-TYPE
    SYNTAX Counter32
    MAX-ACCESS read-only
    STATUS current
    DESCRIPTION
        "The number of times availability is used."
    ::= { gslbStatRuleTableEntry 10 }

gslbStatRuleQos OBJECT-TYPE
    SYNTAX Counter32
    MAX-ACCESS read-only
    STATUS current
    DESCRIPTION
        "The number of times qos is used."
    ::= { gslbStatRuleTableEntry 11 }

gslbStatRulePersistence OBJECT-TYPE
    SYNTAX Counter32
    MAX-ACCESS read-only
    STATUS current
    DESCRIPTION
        "The number of times persistence is used."
    ::= { gslbStatRuleTableEntry 12 }

gslbStatRuleLocal OBJECT-TYPE
    SYNTAX Counter32
    MAX-ACCESS read-only
    STATUS current
    DESCRIPTION
        "The number of times local is used."
    ::= { gslbStatRuleTableEntry 13 }

gslbStatRuleAlways OBJECT-TYPE
    SYNTAX Counter32
    MAX-ACCESS read-only
    STATUS current
    DESCRIPTION
        "The number of times always is used."
    ::= { gslbStatRuleTableEntry 14 }

gslbStatRuleRemote OBJECT-TYPE
    SYNTAX Counter32
    MAX-ACCESS read-only
    STATUS current
    DESCRIPTION
        "The number of times remote is used."
    ::= { gslbStatRuleTableEntry 15 }

gslbStatRuleTotal OBJECT-TYPE
    SYNTAX Counter32
    MAX-ACCESS read-only
    STATUS current
    DESCRIPTION
        "The number of times all the metrics are used."
    ::= { gslbStatRuleTableEntry 16 }

gslbStatRulePhash OBJECT-TYPE
    SYNTAX Counter32
    MAX-ACCESS read-only
    STATUS current
    DESCRIPTION
        "The number of times phash is used."
    ::= { gslbStatRuleTableEntry 17 }

gslbStatRuleAbsLeastconns OBJECT-TYPE
    SYNTAX Counter32
    MAX-ACCESS read-only
    STATUS current
    DESCRIPTION
        "The number of times absolute leastconns is used."
    ::= { gslbStatRuleTableEntry 19 }

-- Global SLB Geographical Statistics

gslbStatGeo OBJECT IDENTIFIER ::= { gslbStats 8 }

gslbStatGeoNA OBJECT-TYPE
    SYNTAX Counter32
    MAX-ACCESS read-only
    STATUS current
    DESCRIPTION
        "The number of times North America is selected.
         Note:This mib is not supported for VX instance of Virtualization."
    ::= { gslbStatGeo 1 }

gslbStatGeoSA OBJECT-TYPE
    SYNTAX Counter32
    MAX-ACCESS read-only
    STATUS current
    DESCRIPTION
        "The number of times South America is selected.
         Note:This mib is not supported for VX instance of Virtualization."
    ::= { gslbStatGeo 2 }

gslbStatGeoEU OBJECT-TYPE
    SYNTAX Counter32
    MAX-ACCESS read-only
    STATUS current
    DESCRIPTION
        "The number of times Europe is selected.
         Note:This mib is not supported for VX instance of Virtualization."
    ::= { gslbStatGeo 3 }

gslbStatGeoCA OBJECT-TYPE
    SYNTAX Counter32
    MAX-ACCESS read-only
    STATUS current
    DESCRIPTION
        "The number of times Caribbean is selected.
         Note:This mib is not supported for VX instance of Virtualization."
    ::= { gslbStatGeo 4 }

gslbStatGeoPR OBJECT-TYPE
    SYNTAX Counter32
    MAX-ACCESS read-only
    STATUS current
    DESCRIPTION
        "The number of times Pacific Rim is selected.
         Note:This mib is not supported for VX instance of Virtualization."
    ::= { gslbStatGeo 5 }

gslbStatGeoSS OBJECT-TYPE
    SYNTAX Counter32
    MAX-ACCESS read-only
    STATUS current
    DESCRIPTION
        "The number of times Sub-Sahara is selected.
         Note:This mib is not supported for VX instance of Virtualization."
    ::= { gslbStatGeo 6 }

gslbStatGeoJP OBJECT-TYPE
    SYNTAX Counter32
    MAX-ACCESS read-only
    STATUS current
    DESCRIPTION
        "The number of times Japan is selected.
         Note:This mib is not supported for VX instance of Virtualization."
    ::= { gslbStatGeo 7 }

gslbStatGeoTotal OBJECT-TYPE
    SYNTAX Counter32
    MAX-ACCESS read-only
    STATUS current
    DESCRIPTION
        "The number of times any of the regions are selected.
         Note:This mib is not supported for VX instance of Virtualization."
    ::= { gslbStatGeo 8 }

gslbStatGeoAF OBJECT-TYPE
    SYNTAX Counter32
    MAX-ACCESS read-only
    STATUS current
    DESCRIPTION
        "The number of times Africa is selected.
         Note:This mib is not supported for VX instance of Virtualization."
    ::= { gslbStatGeo 9 }

-- Global SLB DNS Persistence Cache Statistics

gslbStatPers OBJECT IDENTIFIER ::= { gslbStats 9 }

gslbStatPersCurrent OBJECT-TYPE
    SYNTAX Counter32
    MAX-ACCESS read-only
    STATUS current
    DESCRIPTION
        "The current number of entries in the DNS persistence cache.
         Note:This mib is not supported for VX instance of Virtualization."
    ::= { gslbStatPers 1 }

gslbStatPersHiwat OBJECT-TYPE
    SYNTAX Counter32
    MAX-ACCESS read-only
    STATUS current
    DESCRIPTION
        "The highest number of entries recorded in the DNS persistence cache.
         Note:This mib is not supported for VX instance of Virtualization."
    ::= { gslbStatPers 2 }

gslbStatPersMax OBJECT-TYPE
    SYNTAX Counter32
    MAX-ACCESS read-only
    STATUS current
    DESCRIPTION
        "The maximum number of entries supported in the DNS persistence cache.
         Note:This mib is not supported for VX instance of Virtualization."
    ::= { gslbStatPers 3 }

-- Global SLB DNSSEC Statistics per zone

gslbStatDnsSecTable OBJECT-TYPE
    SYNTAX SEQUENCE OF GslbStatDnsSecTableEntry
    MAX-ACCESS not-accessible
    STATUS current
    DESCRIPTION
        "The Global SLB DNS statistics table.
         Note:This mib is not supported for VX instance of Virtualization."
    ::= { gslbStats 13 }

gslbStatDnsSecTableEntry OBJECT-TYPE
    SYNTAX GslbStatDnsSecTableEntry
    MAX-ACCESS not-accessible
    STATUS current
    DESCRIPTION
        "A row in the Global SLB DNS statistics table."
    INDEX { gslbStatDnsIdx }
    ::= { gslbStatDnsSecTable 1 }

GslbStatDnsSecTableEntry ::=     SEQUENCE {
    gslbStatDnsIdx                   DisplayString,
    gslbStatDnsTotalRequest          Counter32,
    gslbStatDnsDnssecTotalRequest    Counter32,
    gslbStatDnsDnssecRequestPercent  Counter32,
    gslbStatDnsRequestPerSec         Counter32,
    gslbStatDnsDnssecRequestPerSec   Counter32,
    gslbStatDnsTcpRequest            Counter32,
    gslbStatDnsUdpRequest            Counter32,
    gslbStatDnsInvalidRequest        Counter32,
    gslbStatDnsNsecRecordAns         Counter32
    }

gslbStatDnsIdx OBJECT-TYPE
    SYNTAX DisplayString
    MAX-ACCESS read-only
    STATUS current
    DESCRIPTION
        "The DNS ID that identifies the DNS."
    ::= { gslbStatDnsSecTableEntry 1 }

gslbStatDnsTotalRequest OBJECT-TYPE
    SYNTAX Counter32
    MAX-ACCESS read-only
    STATUS current
    DESCRIPTION
        "The number of total DNS requests since boot time."
    ::= { gslbStatDnsSecTableEntry 2 }

gslbStatDnsDnssecTotalRequest OBJECT-TYPE
    SYNTAX Counter32
    MAX-ACCESS read-only
    STATUS current
    DESCRIPTION
        "The number of total DNSSEC requests since boot time."
    ::= { gslbStatDnsSecTableEntry 3 }

gslbStatDnsDnssecRequestPercent OBJECT-TYPE
    SYNTAX Counter32
    MAX-ACCESS read-only
    STATUS current
    DESCRIPTION
        "The number of total DNSSEC out of Total DNS in percent."
    ::= { gslbStatDnsSecTableEntry 4 }

gslbStatDnsRequestPerSec OBJECT-TYPE
    SYNTAX Counter32
    MAX-ACCESS read-only
    STATUS current
    DESCRIPTION
        "The number of DNS request per seconds (CPS)."
    ::= { gslbStatDnsSecTableEntry 5 }

gslbStatDnsDnssecRequestPerSec OBJECT-TYPE
    SYNTAX Counter32
    MAX-ACCESS read-only
    STATUS current
    DESCRIPTION
        "The number of total DNSSEC request per seconds (CPS)."
    ::= { gslbStatDnsSecTableEntry 6 }

gslbStatDnsTcpRequest OBJECT-TYPE
    SYNTAX Counter32
    MAX-ACCESS read-only
    STATUS current
    DESCRIPTION
        "The number of total TCP DNS requests."
    ::= { gslbStatDnsSecTableEntry 7 }

gslbStatDnsUdpRequest OBJECT-TYPE
    SYNTAX Counter32
    MAX-ACCESS read-only
    STATUS current
    DESCRIPTION
        "The number of total UDP DNS requests."
    ::= { gslbStatDnsSecTableEntry 8 }

gslbStatDnsInvalidRequest OBJECT-TYPE
    SYNTAX Counter32
    MAX-ACCESS read-only
    STATUS current
    DESCRIPTION
        "The number of invalid DNS requests."
    ::= { gslbStatDnsSecTableEntry 9 }

gslbStatDnsNsecRecordAns OBJECT-TYPE
    SYNTAX Counter32
    MAX-ACCESS read-only
    STATUS current
    DESCRIPTION
        "The number of total NSEC records answer since boot time."
    ::= { gslbStatDnsSecTableEntry 10 }


-- Global SLB DNSSEC Total Statistics For All Zones

gslbStatDnsSecAll OBJECT IDENTIFIER ::= { gslbStats 14 }

gslbStatDnsDomainPerseErrorsAll OBJECT-TYPE
    SYNTAX Counter32
    MAX-ACCESS read-only
    STATUS current
    DESCRIPTION
        "The number of total domain name parse errors for all zones.
         Note:This mib is not supported for VX instance of Virtualization."
    ::= { gslbStatDnsSecAll 1 }

gslbStatDnsSecCurrentRequestAll OBJECT-TYPE
    SYNTAX Counter32
    MAX-ACCESS read-only
    STATUS current
    DESCRIPTION
        "The number of current DNSSEC requests being processed for all zones.
         Note:This mib is not supported for VX instance of Virtualization."
    ::= { gslbStatDnsSecAll 2 }

gslbStatDnsCurrentRequestAll OBJECT-TYPE
    SYNTAX Counter32
    MAX-ACCESS read-only
    STATUS current
    DESCRIPTION
        "The number of current DNS requests being processed for all zones.
         Note:This mib is not supported for VX instance of Virtualization."
    ::= { gslbStatDnsSecAll 3 }

gslbStatDnsTotalRequestAll OBJECT-TYPE
    SYNTAX Counter32
    MAX-ACCESS read-only
    STATUS current
    DESCRIPTION
        "The number of total DNS requests since boot time for all zones.
         Note:This mib is not supported for VX instance of Virtualization."
    ::= { gslbStatDnsSecAll 4 }

gslbStatDnsSecTotalRequestAll OBJECT-TYPE
    SYNTAX Counter32
    MAX-ACCESS read-only
    STATUS current
    DESCRIPTION
        "The number of total DNSSEC requests since boot time for all zones.
         Note:This mib is not supported for VX instance of Virtualization."
    ::= { gslbStatDnsSecAll 5 }

gslbStatDnsSecRequestPercentAll OBJECT-TYPE
    SYNTAX Counter32
    MAX-ACCESS read-only
    STATUS current
    DESCRIPTION
        "The number of total DNSSEC out of Total DNS in percent for all zones.
         Note:This mib is not supported for VX instance of Virtualization."
    ::= { gslbStatDnsSecAll 6 }

gslbStatDnsRequestPerSecAll OBJECT-TYPE
    SYNTAX Counter32
    MAX-ACCESS read-only
    STATUS current
    DESCRIPTION
        "The number of DNS request per seconds (CPS) for all zones.
         Note:This mib is not supported for VX instance of Virtualization."
    ::= { gslbStatDnsSecAll 7 }

gslbStatDnsSecRequestPerSecAll OBJECT-TYPE
    SYNTAX Counter32
    MAX-ACCESS read-only
    STATUS current
    DESCRIPTION
        "The number of total DNSSEC request per seconds (CPS) for all zones.
         Note:This mib is not supported for VX instance of Virtualization."
    ::= { gslbStatDnsSecAll 8 }

gslbStatDnsTcpRequestAll OBJECT-TYPE
    SYNTAX Counter32
    MAX-ACCESS read-only
    STATUS current
    DESCRIPTION
        "The number of total TCP DNS requests for all zones.
         Note:This mib is not supported for VX instance of Virtualization."
    ::= { gslbStatDnsSecAll 9 }

gslbStatDnsUdpRequestAll OBJECT-TYPE
    SYNTAX Counter32
    MAX-ACCESS read-only
    STATUS current
    DESCRIPTION
        "The number of total UDP DNS requests for all zones.
         Note:This mib is not supported for VX instance of Virtualization."
    ::= { gslbStatDnsSecAll 10 }

gslbStatDnsInvalidRequestAll OBJECT-TYPE
    SYNTAX Counter32
    MAX-ACCESS read-only
    STATUS current
    DESCRIPTION
        "The number of invalid DNS requests for all zones.
         Note:This mib is not supported for VX instance of Virtualization."
    ::= { gslbStatDnsSecAll 11 }

gslbStatDnsNsecRecordAnsAll OBJECT-TYPE
    SYNTAX Counter32
    MAX-ACCESS read-only
    STATUS current
    DESCRIPTION
        "The number of total NSEC records answer since boot time for all zones.
         Note:This mib is not supported for VX instance of Virtualization."
    ::= { gslbStatDnsSecAll 12 }

-- FTP Passive SLB/NAT Statistics

ftpSlbStatTotal  OBJECT-TYPE
    SYNTAX  Counter32
    MAX-ACCESS  read-only
    STATUS  current
    DESCRIPTION
        "The number of times the switch receives both active and passive
         FTP connections.
         Note:This mib is not supported for VX instance of Virtualization."
    ::= { ftpStats 1 }

ftpNatStatTotal  OBJECT-TYPE
    SYNTAX  Counter32
    MAX-ACCESS  read-only
    STATUS  current
    DESCRIPTION
	"The number of times the switch receives the 'port' command from 
         the client.
         Note:This mib is not supported for VX instance of Virtualization."
    ::= { ftpStats 2 } 

ftpStatActiveNatIndex  OBJECT-TYPE
    SYNTAX  Counter32
    MAX-ACCESS  read-only
    STATUS  current
    DESCRIPTION
	"The number of times the switch creates a new index due to 'port'
         command from the client.
         Note:This mib is not supported for VX instance of Virtualization."
    ::= { ftpStats 3 } 

ftpStatNatAckSeqDiff  OBJECT-TYPE
    SYNTAX  Counter32
    MAX-ACCESS  read-only
    STATUS  current
    DESCRIPTION
 	"The difference in the numbers of ACK and SEQ that the switch needs 
         for packet adjustment.
         Note:This mib is not supported for VX instance of Virtualization."
    ::= { ftpStats 4 } 

ftpStatSlbParseIndex  OBJECT-TYPE
    SYNTAX  Counter32
    MAX-ACCESS  read-only
    STATUS  current
    DESCRIPTION
	"The number of times the switch creates a new index in response to the
         'pasv' command from the client.
          Note:This mib is not supported for VX instance of Virtualization."
    ::= { ftpStats 5 } 

ftpStatSlbParseAckSeqDiff  OBJECT-TYPE
    SYNTAX  Counter32
    MAX-ACCESS  read-only
    STATUS  current
    DESCRIPTION
 	"The difference in the numbers of ACK and SEQ that the switch needs 
         for FTP SLB parsing.
         Note:This mib is not supported for VX instance of Virtualization." 
    ::= { ftpStats 6 } 

ftpStatModeSwitchError OBJECT-TYPE
    SYNTAX  Counter32
    MAX-ACCESS  read-only
    STATUS  current
    DESCRIPTION
	"The number of times the switch is not able to switch modes from
         active to passive and vice versa.
         Note:This mib is not supported for VX instance of Virtualization."
    ::= { ftpStats 7 } 

radiusAcctReqsStats     OBJECT IDENTIFIER ::= { wapStats 1 }
tpcpAddSessReqsStats    OBJECT IDENTIFIER ::= { wapStats 2 }
tpcpDeleteSessReqsStats OBJECT IDENTIFIER ::= { wapStats 3 }

radiusAcctReqs OBJECT-TYPE 
    SYNTAX  Counter32 
    MAX-ACCESS  read-only
    STATUS  current 
    DESCRIPTION 
        "Radius Account Request.
         Note:This mib is not supported for VX instance of Virtualization."
    ::= { radiusAcctReqsStats 1 }

radiusAcctWrapReqs OBJECT-TYPE 
    SYNTAX  Counter32 
    MAX-ACCESS  read-only
    STATUS  current 
    DESCRIPTION 
        "Radius Account Wrap Request.
         Note:This mib is not supported for VX instance of Virtualization."
    ::= { radiusAcctReqsStats 2 }

radiusAcctStartReqs OBJECT-TYPE 
    SYNTAX  Counter32 
    MAX-ACCESS  read-only
    STATUS  current 
    DESCRIPTION 
        "Radius Account Start Request.
         Note:This mib is not supported for VX instance of Virtualization."
    ::= { radiusAcctReqsStats 3 }

radiusAcctUpdateReqs OBJECT-TYPE 
    SYNTAX  Counter32 
    MAX-ACCESS  read-only
    STATUS  current 
    DESCRIPTION 
        "Radius Account Update Request.
         Note:This mib is not supported for VX instance of Virtualization."
    ::= { radiusAcctReqsStats 4 }

radiusAcctStopReqs OBJECT-TYPE 
    SYNTAX  Counter32 
    MAX-ACCESS  read-only
    STATUS  current 
    DESCRIPTION 
        "Radius Account stop Request.
         Note:This mib is not supported for VX instance of Virtualization."
    ::= { radiusAcctReqsStats 5 }

radiusAcctBadReqs OBJECT-TYPE 
    SYNTAX  Counter32 
    MAX-ACCESS  read-only
    STATUS  current 
    DESCRIPTION 
        "Radius Account Bad Request.
         Note:This mib is not supported for VX instance of Virtualization."
    ::= { radiusAcctReqsStats 6 }

radiusAcctAddSessionReqs OBJECT-TYPE 
    SYNTAX  Counter32 
    MAX-ACCESS  read-only
    STATUS  current 
    DESCRIPTION 
        "Radius Account add session Request.
         Note:This mib is not supported for VX instance of Virtualization."
    ::= { radiusAcctReqsStats 7 }

radiusAcctDeleteSessionReqs OBJECT-TYPE 
    SYNTAX  Counter32 
    MAX-ACCESS  read-only
    STATUS  current 
    DESCRIPTION 
        "Radius Account delete session Request.
         Note:This mib is not supported for VX instance of Virtualization."
    ::= { radiusAcctReqsStats 8 }

radiusAcctReqFailsSPDead OBJECT-TYPE 
    SYNTAX  Counter32 
    MAX-ACCESS  read-only
    STATUS  current 
    DESCRIPTION 
        "Radius Account request fails SP Dead.
         Note:This mib is not supported for VX instance of Virtualization."
    ::= { radiusAcctReqsStats 10 }

radiusAcctReqFailsDMAFails OBJECT-TYPE 
    SYNTAX  Counter32 
    MAX-ACCESS  read-only
    STATUS  current 
    DESCRIPTION 
        "Radius Account request fails DMA fails.
         Note:This mib is not supported for VX instance of Virtualization."
    ::= { radiusAcctReqsStats 11 }

radiusAcctReqWithFramedIp OBJECT-TYPE 
    SYNTAX  Counter32 
    MAX-ACCESS  read-only
    STATUS  current 
    DESCRIPTION 
        "Radius Account request containing the FRAMED_IP field.
         Note:This mib is not supported for VX instance of Virtualization."
    ::= { radiusAcctReqsStats 12 }

radiusAcctReqWithoutFramedIp OBJECT-TYPE 
    SYNTAX  Counter32 
    MAX-ACCESS  read-only
    STATUS  current 
    DESCRIPTION 
        "Radius Account request not containing the FRAMED_IP field.
         Note:This mib is not supported for VX instance of Virtualization."
    ::= { radiusAcctReqsStats 13 }

tpcpAddSessReqs OBJECT-TYPE 
    SYNTAX  Counter32 
    MAX-ACCESS  read-only
    STATUS  current 
    DESCRIPTION 
        "WAP add Session requests.
         Note:This mib is not supported for VX instance of Virtualization."
    ::= { tpcpAddSessReqsStats 1 }

tpcpAddSessReqsFailsSPDead OBJECT-TYPE 
    SYNTAX  Counter32 
    MAX-ACCESS  read-only
    STATUS  current 
    DESCRIPTION 
        "WAP add Session Fails as the SP is dead.
         Note:This mib is not supported for VX instance of Virtualization."
    ::= { tpcpAddSessReqsStats 3 }

tpcpDeleteSessReqs OBJECT-TYPE 
    SYNTAX  Counter32 
    MAX-ACCESS  read-only
    STATUS  current 
    DESCRIPTION 
        "TPCP Delete Session Requests.
         Note:This mib is not supported for VX instance of Virtualization." 
    ::= { tpcpDeleteSessReqsStats 1 }

tpcpDeleteSessReqsFailsSPDead OBJECT-TYPE 
    SYNTAX  Counter32 
    MAX-ACCESS  read-only
    STATUS current 
    DESCRIPTION 
        "TPCP Delete Session Fails as the SP is dead.
         Note:This mib is not supported for VX instance of Virtualization."
    ::= { tpcpDeleteSessReqsStats 3 }

wapRequestToWrongSP OBJECT-TYPE 
    SYNTAX  Counter32 
    MAX-ACCESS  read-only
    STATUS  current 
    DESCRIPTION 
        "The  WAP delete Session Entries sent to wrong SP.
         Note:This mib is not supported for VX instance of Virtualization."
    ::= { wapStats 4 }

-- RTSP Statistics

rtspStatControlConns OBJECT-TYPE 
    SYNTAX  Counter32
    MAX-ACCESS  read-only
    STATUS  current 
    DESCRIPTION 
        "Total number of active RTSP control connections.
         Note:This mib is not supported for VX instance of Virtualization."
    ::= { rtspStats 1 }

rtspStatUDPStreams OBJECT-TYPE 
    SYNTAX  Counter32
    MAX-ACCESS  read-only
    STATUS  current 
    DESCRIPTION 
        "Total number of active UDP streams.
         Note:This mib is not supported for VX instance of Virtualization."
    ::= { rtspStats 2 }

rtspStatRedirects OBJECT-TYPE 
    SYNTAX  Counter32
    MAX-ACCESS  read-only
    STATUS  current 
    DESCRIPTION 
        "Total number of switch redirects.
         Note:This mib is not supported for VX instance of Virtualization."
    ::= { rtspStats 3 }

rtspStatConnDenied OBJECT-TYPE 
    SYNTAX  Counter32
    MAX-ACCESS  read-only
    STATUS  current 
    DESCRIPTION 
        "Total connections denied due to RTSP connection limit.
         Note:This mib is not supported for VX instance of Virtualization."
    ::= { rtspStats 4 }

rtspStatAllocFails OBJECT-TYPE 
    SYNTAX  Counter32
    MAX-ACCESS  read-only
    STATUS  current 
    DESCRIPTION 
        "Total cases of heap memory allocation failures.
         Note:This mib is not supported for VX instance of Virtualization."
    ::= { rtspStats 5 }

rtspStatBufferAllocs OBJECT-TYPE 
    SYNTAX  Gauge32
    MAX-ACCESS  read-only
    STATUS  current 
    DESCRIPTION 
        "The total number of buffer allocations used.
         Note:This mib is not supported for VX instance of Virtualization."
    ::= { rtspStats 6 }

-- TCP Rate Limiting Statistics
tcpLimitStatHoldDowns OBJECT-TYPE 
    SYNTAX  Counter32
    MAX-ACCESS  read-only
    STATUS  current 
    DESCRIPTION 
        "Total number of client hold downs triggered.
         Note:This mib is not supported for VX instance of Virtualization."
    ::= { tcpLimitStats 1 }

tcpLimitStatClientEntries OBJECT-TYPE 
    SYNTAX  Gauge32
    MAX-ACCESS  read-only
    STATUS  current 
    DESCRIPTION 
        "Current number of TCP rate limiting per-client state entries.
         Note:This mib is not supported for VX instance of Virtualization."
    ::= { tcpLimitStats 2 }
    
udpLimitStatHoldDowns OBJECT-TYPE 
    SYNTAX  Counter32
    MAX-ACCESS  read-only
    STATUS  current 
    DESCRIPTION 
        "Total number of UDP client hold downs triggered.
         Note:This mib is not supported for VX instance of Virtualization."
    ::= { tcpLimitStats 3 }
    
icmpLimitStatHoldDowns OBJECT-TYPE 
    SYNTAX  Counter32
    MAX-ACCESS  read-only
    STATUS  current 
    DESCRIPTION 
        "Total number of ICMP client hold downs triggered.
         Note:This mib is not supported for VX instance of Virtualization."
    ::= { tcpLimitStats 4 }

udpLimitStatClientEntries OBJECT-TYPE 
    SYNTAX  Counter32
    MAX-ACCESS  read-only
    STATUS  current 
    DESCRIPTION 
        "Current number of UDP rate limiting per-client state entries.
         Note:This mib is not supported for VX instance of Virtualization."
    ::= { tcpLimitStats 5 }
    
icmpLimitStatClientEntries OBJECT-TYPE 
    SYNTAX  Counter32
    MAX-ACCESS  read-only
    STATUS  current 
    DESCRIPTION 
        "Current number of ICMP rate limiting per-client state entries.
         Note:This mib is not supported for VX instance of Virtualization."
    ::= { tcpLimitStats 6 }    
    
-- DNS SLB Statistics

dnsSlbStatTCPQueries OBJECT-TYPE 
    SYNTAX  Counter32
    MAX-ACCESS  read-only
    STATUS  current 
    DESCRIPTION 
        "Total number of TCP DNS queries.
         Note:This mib is not supported for VX instance of Virtualization."
    ::= { dnsSlbStats 1 }

dnsSlbStatUDPQueries OBJECT-TYPE 
    SYNTAX  Counter32
    MAX-ACCESS  read-only
    STATUS  current 
    DESCRIPTION 
        "Total number of UDP DNS queries.
         Note:This mib is not supported for VX instance of Virtualization."
    ::= { dnsSlbStats 2 }

dnsSlbStatInvalidQueries OBJECT-TYPE 
    SYNTAX  Counter32
    MAX-ACCESS  read-only
    STATUS  current 
    DESCRIPTION 
        "Total number of invalid DNS queries.
         Note:This mib is not supported for VX instance of Virtualization."
    ::= { dnsSlbStats 3 }

dnsSlbStatMultipleQueries OBJECT-TYPE 
    SYNTAX  Counter32
    MAX-ACCESS  read-only
    STATUS  current 
    DESCRIPTION 
        "Total number of multiple DNS queries.
         Note:This mib is not supported for VX instance of Virtualization."
    ::= { dnsSlbStats 4 }

dnsSlbStatDnameParseErrors OBJECT-TYPE 
    SYNTAX  Counter32
    MAX-ACCESS  read-only
    STATUS  current 
    DESCRIPTION 
        "Total number of domain name parse errors.
         Note:This mib is not supported for VX instance of Virtualization."
    ::= { dnsSlbStats 5 }

dnsSlbStatFailedMatches OBJECT-TYPE 
    SYNTAX  Counter32
    MAX-ACCESS  read-only
    STATUS  current 
    DESCRIPTION 
        "Total number of failed real server name matches.
         Note:This mib is not supported for VX instance of Virtualization."
    ::= { dnsSlbStats 6 }

dnsSlbStatInternalErrors OBJECT-TYPE 
    SYNTAX  Counter32
    MAX-ACCESS  read-only
    STATUS  current 
    DESCRIPTION 
        "Total number of DNS parsing internal errors.
         Note:This mib is not supported for VX instance of Virtualization."
    ::= { dnsSlbStats 7 }

slbStatsClear OBJECT-TYPE
    SYNTAX INTEGER {
	ok(1),
	clear(2),
        unsupported(2147483647)
	}
    MAX-ACCESS read-write
    STATUS current
    DESCRIPTION
        "This is an action object to clear the non-operational SLB statistics. 
         ok(1) is returned when read.
         Note:This mib is not supported for VX instance of Virtualization."
    ::= { layer4Stats 15 }


slbStatsPeerClearConfirm OBJECT-TYPE
    SYNTAX INTEGER {
        yes(1),
        no(2),
        unsupported(2147483647)
        }
    MAX-ACCESS read-write
    STATUS current
    DESCRIPTION
        "This is an action object to clear SLB statistics on HA peer when all SLB statistics 
	 are cleared. Default action is 'no' - SLB stats not cleared on HA peer device.
         Note:This mib is not supported for VX instance of Virtualization."
    ::= { layer4Stats 44 }

slbSfoSessMirrorStatus OBJECT-TYPE
    SYNTAX INTEGER {
        enabled(1),
        disabled(2),
        unsupported(2147483647)
        }
    MAX-ACCESS read-only
    STATUS current
    DESCRIPTION
        "This is an action object to check the status of SFO session mirror.
         Note:This mib is not supported for VX instance of Virtualization."
    ::= { layer4Stats 45 }

slbSecondsFromLastStatsClear OBJECT-TYPE
    SYNTAX  Counter32
    MAX-ACCESS  read-only
    STATUS current
    DESCRIPTION
        "Seconds passed from last statistics slb clear.
         Note:This mib is not supported for VX instance of Virtualization."
    ::= { layer4Stats 33 }
    
slbStatAuxSessTable OBJECT-TYPE
    SYNTAX  SEQUENCE OF SlbStatAuxSessEntry
    MAX-ACCESS  not-accessible
    STATUS  current
    DESCRIPTION
        "The auxiliary session table statistics.
         Note:This mib is not supported for VX instance of Virtualization."
    ::= { layer4Stats 17 }

slbStatAuxSessEntry OBJECT-TYPE
    SYNTAX  SlbStatAuxSessEntry
    MAX-ACCESS  not-accessible
    STATUS  current
    DESCRIPTION
        "The statistics of a particular auxiliary session table entry."
    INDEX   { slbStatAuxSessIndex }
    ::= { slbStatAuxSessTable 1 }

SlbStatAuxSessEntry ::= SEQUENCE {
    slbStatAuxSessIndex               Integer32,
    slbStatAuxSessCurConn             Gauge32,
    slbStatAuxSessMaxConn             Integer32,
    slbStatAuxSessAllocFails          Counter32
    }

slbStatAuxSessIndex OBJECT-TYPE
    SYNTAX  Integer32
    MAX-ACCESS  read-only
    STATUS  current
    DESCRIPTION
        "The auxiliary session table number." 
    ::= { slbStatAuxSessEntry 1 }

slbStatAuxSessCurConn OBJECT-TYPE 
    SYNTAX  Gauge32
    MAX-ACCESS  read-only
    STATUS  current 
    DESCRIPTION 
        "The number of connections in this auxiliary sessions table."
    ::= { slbStatAuxSessEntry 2 }

slbStatAuxSessMaxConn OBJECT-TYPE 
    SYNTAX  Integer32 
    MAX-ACCESS  read-only
    STATUS  current 
    DESCRIPTION 
        "The maximum number of connections handled by this auxiliary session 
         table."
    ::= { slbStatAuxSessEntry 3 }

slbStatAuxSessAllocFails OBJECT-TYPE 
    SYNTAX  Counter32 
    MAX-ACCESS  read-only
    STATUS  current 
    DESCRIPTION 
        "The total number of allocation failures for this auxiliary session 
         table."
    ::= { slbStatAuxSessEntry 4 }

-- SSL SLB Statistics

sslSlbStatSessIdAllocFails OBJECT-TYPE 
    SYNTAX  Counter32
    MAX-ACCESS  read-only
    STATUS  current 
    DESCRIPTION 
        "The number of times allocation of a session table entry failed when
         attempting to store a SessionId in the table.
         Note:This mib is not supported for VX instance of Virtualization."
    ::= { sslSlbStats 1 }

sslSlbStatCurSessions OBJECT-TYPE 
    SYNTAX  Gauge32
    MAX-ACCESS  read-only
    STATUS  current 
    DESCRIPTION 
        "The current number of different TCP sessions using SSL service.
         Note:This mib is not supported for VX instance of Virtualization."
    ::= { sslSlbStats 2 }

sslSlbStatTotalSessions OBJECT-TYPE 
    SYNTAX  Counter32
    MAX-ACCESS  read-only
    STATUS  current 
    DESCRIPTION 
        "The total number of different TCP sessions using SSL service.
         Note:This mib is not supported for VX instance of Virtualization."
    ::= { sslSlbStats 3 }

sslSlbStatHighestSessions OBJECT-TYPE 
    SYNTAX  Counter32
    MAX-ACCESS  read-only
    STATUS  current 
    DESCRIPTION 
        "The high water mark of current sessions of different TCP sessions 
         using SSL service.
         Note:This mib is not supported for VX instance of Virtualization."
    ::= { sslSlbStats 4 }

sslSlbStatUniqCurSessions OBJECT-TYPE 
    SYNTAX  Gauge32
    MAX-ACCESS  read-only
    STATUS  current 
    DESCRIPTION 
        "The current number of unique SSL sessions seen on the switch.
         Note:This mib is not supported for VX instance of Virtualization."
    ::= { sslSlbStats 5 }

sslSlbStatUniqTotalSessions OBJECT-TYPE 
    SYNTAX  Counter32
    MAX-ACCESS  read-only
    STATUS  current 
    DESCRIPTION 
        "The total number of unique SSL sessions seen on the switch.
         Note:This mib is not supported for VX instance of Virtualization."
    ::= { sslSlbStats 6 }

sslSlbStatUniqHighestSessions OBJECT-TYPE 
    SYNTAX  Counter32
    MAX-ACCESS  read-only
    STATUS  current 
    DESCRIPTION 
        "The high water mark of unique SSL sessions seen on the switch.
         Note:This mib is not supported for VX instance of Virtualization."
    ::= { sslSlbStats 7 }

sslSlbStatPersistPortCurSessions OBJECT-TYPE 
    SYNTAX  Gauge32
    MAX-ACCESS  read-only
    STATUS  current 
    DESCRIPTION 
        "The current number of SessionIds maintained on SP 4, to allow for 
         persistence across different client ports.
         Note:This mib is not supported for VX instance of Virtualization."
    ::= { sslSlbStats 8 }

sslSlbStatPersistPortTotalSessions OBJECT-TYPE 
    SYNTAX  Counter32
    MAX-ACCESS  read-only
    STATUS  current 
    DESCRIPTION 
        "The total number of SessionIds maintained on SP 4, to allow for 
         persistence across different client ports.
         Note:This mib is not supported for VX instance of Virtualization."
    ::= { sslSlbStats 9 }

sslSlbStatPersistPortHighestSessions OBJECT-TYPE 
    SYNTAX  Counter32
    MAX-ACCESS  read-only
    STATUS  current 
    DESCRIPTION 
        "The high water mask of SessionIds maintained on SP 4, to allow for 
         persistence across different client ports.
         Note:This mib is not supported for VX instance of Virtualization."
    ::= { sslSlbStats 10 }


-- SLB Virtual Service Statistics Table

slbStatVirtServiceTable OBJECT-TYPE
    SYNTAX  SEQUENCE OF SlbStatVirtServiceEntry
    MAX-ACCESS  not-accessible
    STATUS  current
    DESCRIPTION
        "The virtual service statistics table.
         Note:This mib is not supported for VX instance of Virtualization."
    ::= { layer4Stats 18 }

slbStatVirtServiceEntry OBJECT-TYPE
    SYNTAX  SlbStatVirtServiceEntry
    MAX-ACCESS  not-accessible
    STATUS  current
    DESCRIPTION
        "The statistics of a particular virtual service."
    INDEX   { slbStatVirtServerIndex, slbStatVirtServiceIndex, slbStatRealServerIndex }
    ::= { slbStatVirtServiceTable 1 }

SlbStatVirtServiceEntry ::= SEQUENCE {
    slbStatVirtServerIndex                 Integer32,
    slbStatVirtServiceIndex                Integer32,
    slbStatRealServerIndex                 Integer32,
    slbStatVirtServiceCurrSessions         Gauge32,
    slbStatVirtServiceTotalSessions        Counter32,
    slbStatVirtServiceHighestSessions      Counter32,
    slbStatVirtServiceHCOctetsLow32        Counter32,
    slbStatVirtServiceHCOctetsHigh32       Counter32,
    slbStatVirtServiceHCOctets             Counter64
    }
    
slbStatVirtServerIndex OBJECT-TYPE
    SYNTAX  Integer32
    MAX-ACCESS  read-only
    STATUS  current
    DESCRIPTION
        "The virtual server number that identifies the service." 
    ::= { slbStatVirtServiceEntry 1 }
    
slbStatVirtServiceIndex OBJECT-TYPE
    SYNTAX  Integer32
    MAX-ACCESS  read-only
    STATUS  current
    DESCRIPTION
        "The virtual service number that identifies the service." 
    ::= { slbStatVirtServiceEntry 2 }
    
slbStatRealServerIndex OBJECT-TYPE
    SYNTAX  Integer32
    MAX-ACCESS  read-only
    STATUS  current
    DESCRIPTION
        "The real server index." 
    ::= { slbStatVirtServiceEntry 3 }
    
slbStatVirtServiceCurrSessions OBJECT-TYPE 
    SYNTAX  Gauge32
    MAX-ACCESS  read-only
    STATUS  current 
    DESCRIPTION 
        "The number of sessions that are currently handled by the 
         virtual service."
    ::= { slbStatVirtServiceEntry 4 }
    
slbStatVirtServiceTotalSessions OBJECT-TYPE 
    SYNTAX  Counter32 
    MAX-ACCESS  read-only
    STATUS  current 
    DESCRIPTION 
        "The total number of sessions that are handled by the virtual service."
    ::= { slbStatVirtServiceEntry 5}

slbStatVirtServiceHighestSessions OBJECT-TYPE 
    SYNTAX  Counter32 
    MAX-ACCESS  read-only
    STATUS  current 
    DESCRIPTION 
        "The highest sessions that have been handled by the virtual service."
    ::= { slbStatVirtServiceEntry 6}

slbStatVirtServiceHCOctetsLow32 OBJECT-TYPE
    SYNTAX  Counter32
    MAX-ACCESS  read-only
    STATUS  current
    DESCRIPTION
        "The lower 32 bit value of octets received and transmitted out
         of the virtual service."
    ::= { slbStatVirtServiceEntry 7}

slbStatVirtServiceHCOctetsHigh32 OBJECT-TYPE
    SYNTAX  Counter32
    MAX-ACCESS  read-only
    STATUS  current
    DESCRIPTION
        "The higher 32 bit value of octets received and transmitted out
         of the virtual service."
    ::= { slbStatVirtServiceEntry 8}

slbStatVirtServiceHCOctets OBJECT-TYPE
    SYNTAX  Counter64
    MAX-ACCESS  read-only
    STATUS  current
    DESCRIPTION
        "The total octets received and transmitted by the virtual service."
    ::= { slbStatVirtServiceEntry 9}

slbEnhStatVirtServiceTable OBJECT-TYPE
    SYNTAX  SEQUENCE OF SlbEnhStatVirtServiceEntry
    MAX-ACCESS  not-accessible
    STATUS  current
    DESCRIPTION
        "The virtual service statistics table.
         Note:This mib is not supported for VX instance of Virtualization."
    ::= { layer4Stats 19 }

slbEnhStatVirtServiceEntry OBJECT-TYPE
    SYNTAX  SlbEnhStatVirtServiceEntry
    MAX-ACCESS  not-accessible
    STATUS  current
    DESCRIPTION
        "The statistics of a particular virtual service."
    INDEX   { slbEnhStatVirtServerIndex, slbEnhStatVirtServiceIndex, slbEnhStatRealServerIndex }
    ::= { slbEnhStatVirtServiceTable 1 }

SlbEnhStatVirtServiceEntry ::= SEQUENCE {
    slbEnhStatVirtServerIndex                 DisplayString,
    slbEnhStatVirtServiceIndex                Integer32,
    slbEnhStatRealServerIndex                 DisplayString,
    slbEnhStatVirtServiceCurrSessions         Gauge32,
    slbEnhStatVirtServiceTotalSessions        Counter32,
    slbEnhStatVirtServiceHighestSessions      Counter32,
    slbEnhStatVirtServiceHCOctetsLow32        Counter32,
    slbEnhStatVirtServiceHCOctetsHigh32       Counter32,
    slbEnhStatVirtServiceHCOctets             Counter64,
    slbEnhStatVirtServiceRealStatus           Integer32,
    slbEnhStatVirtServiceHcReason             DisplayString,
    slbEnhStatVirtServiceRSTSessions          Counter32,
    slbEnhStatVirtServiceClientRtt            DisplayString,
    slbEnhStatVirtServiceServerRtt            DisplayString
    }

slbEnhStatVirtServerIndex OBJECT-TYPE
    SYNTAX  DisplayString (SIZE(1..255))
    MAX-ACCESS  read-only
    STATUS  current
    DESCRIPTION
        "The virtual server number that identifies the service."
    ::= { slbEnhStatVirtServiceEntry 1 }

slbEnhStatVirtServiceIndex OBJECT-TYPE
    SYNTAX  Integer32
    MAX-ACCESS  read-only
    STATUS  current
    DESCRIPTION
        "The virtual service number that identifies the service."
    ::= { slbEnhStatVirtServiceEntry 2 }

slbEnhStatRealServerIndex OBJECT-TYPE
    SYNTAX  DisplayString (SIZE(1..255))
    MAX-ACCESS  read-only
    STATUS  current
    DESCRIPTION
        "The real server index."
    ::= { slbEnhStatVirtServiceEntry 3 }

slbEnhStatVirtServiceCurrSessions OBJECT-TYPE
    SYNTAX  Gauge32
    MAX-ACCESS  read-only
    STATUS  current
    DESCRIPTION
        "The number of sessions that are currently handled by the
         virtual service."
    ::= { slbEnhStatVirtServiceEntry 4 }

slbEnhStatVirtServiceTotalSessions OBJECT-TYPE
    SYNTAX  Counter32
    MAX-ACCESS  read-only
    STATUS  current
    DESCRIPTION
        "The total number of sessions that are handled by the virtual service."
    ::= { slbEnhStatVirtServiceEntry 5}

slbEnhStatVirtServiceHighestSessions OBJECT-TYPE
    SYNTAX  Counter32
    MAX-ACCESS  read-only
    STATUS  current
    DESCRIPTION
        "The highest sessions that have been handled by the virtual service."
    ::= { slbEnhStatVirtServiceEntry 6}

slbEnhStatVirtServiceHCOctetsLow32 OBJECT-TYPE
    SYNTAX  Counter32
    MAX-ACCESS  read-only
    STATUS  current
    DESCRIPTION
        "The lower 32 bit value of octets received and transmitted out
         of the virtual service."
    ::= { slbEnhStatVirtServiceEntry 7}

slbEnhStatVirtServiceHCOctetsHigh32 OBJECT-TYPE
    SYNTAX  Counter32
    MAX-ACCESS  read-only
    STATUS  current
    DESCRIPTION
        "The higher 32 bit value of octets received and transmitted out
         of the virtual service."
    ::= { slbEnhStatVirtServiceEntry 8}

slbEnhStatVirtServiceHCOctets OBJECT-TYPE
    SYNTAX  Counter64
    MAX-ACCESS  read-only
    STATUS  current
    DESCRIPTION
        "The total octets received and transmitted by the virtual service."
    ::= { slbEnhStatVirtServiceEntry 9}
	
slbEnhStatVirtServiceRealStatus OBJECT-TYPE
    SYNTAX  Integer32
    MAX-ACCESS  read-only
    STATUS  current
    DESCRIPTION
        "The real server status. (0)Up, (1)Down, (2)Admin-Down, 
				 (3)Warning, (4)Shutdown, (5)Error"
    ::= { slbEnhStatVirtServiceEntry 10 }

slbEnhStatVirtServiceHcReason OBJECT-TYPE
    SYNTAX  DisplayString (SIZE(1..128))
    MAX-ACCESS  read-only
    STATUS  current
    DESCRIPTION
        "Service health check failure reason."
    ::= { slbEnhStatVirtServiceEntry 11 }

slbEnhStatVirtServiceRSTSessions OBJECT-TYPE
    SYNTAX  Counter32
    MAX-ACCESS  read-only
    STATUS  current
    DESCRIPTION
    "The total number of RST sessions that are handled by the virtual service."
    ::= { slbEnhStatVirtServiceEntry 12}

slbEnhStatVirtServiceClientRtt OBJECT-TYPE
    SYNTAX  DisplayString (SIZE(1..255))
    MAX-ACCESS  read-only
    STATUS  current
    DESCRIPTION
    "The average ClientRTT in ms during the past collection interval."
    ::= { slbEnhStatVirtServiceEntry 13 }

slbEnhStatVirtServiceServerRtt OBJECT-TYPE
    SYNTAX  DisplayString (SIZE(1..255))
    MAX-ACCESS  read-only
    STATUS  current
    DESCRIPTION
    "The average ServerRTT in ms during the past collection interval."
    ::= { slbEnhStatVirtServiceEntry 14 }

-- SIP statistics
sipTotalClientParseErrors OBJECT-TYPE 
    SYNTAX  Counter32 
    MAX-ACCESS  read-only
    STATUS  current 
    DESCRIPTION 
        "Total number of SIP Client parse Errors.
         Note:This mib is not supported for VX instance of Virtualization."
    ::= { sipStats 1 }

sipTotalServerParseErrors OBJECT-TYPE 
    SYNTAX  Counter32 
    MAX-ACCESS  read-only
    STATUS  current 
    DESCRIPTION 
        "Total number of SIP Server parse Errors.
         Note:This mib is not supported for VX instance of Virtualization."
    ::= { sipStats 2 }

sipTotalUnknownMethodReq OBJECT-TYPE 
    SYNTAX  Counter32 
    MAX-ACCESS  read-only
    STATUS  current 
    DESCRIPTION 
        "Total number of SIP unknown method requests.
         Note:This mib is not supported for VX instance of Virtualization."
    ::= { sipStats 3 }

sipTotalIncompleteMsgs OBJECT-TYPE 
    SYNTAX  Counter32 
    MAX-ACCESS  read-only
    STATUS  current 
    DESCRIPTION 
        "Total number of SIP Incomplete messages.
         Note:This mib is not supported for VX instance of Virtualization."
    ::= { sipStats 4 }

sipTotalSdpNatPackets OBJECT-TYPE
    SYNTAX  Counter32
    MAX-ACCESS  read-only
    STATUS  current
    DESCRIPTION
        "Total number of SDP NAT packets.
         Note:This mib is not supported for VX instance of Virtualization."
    ::= { sipStats 5 }


-- SLB WLM Statistics Table


wlmStats          OBJECT IDENTIFIER ::= { layer4Stats  21 }

slbStatWlmTable OBJECT-TYPE
    SYNTAX  SEQUENCE OF SlbStatWlmEntry
    MAX-ACCESS  not-accessible
    STATUS  current
    DESCRIPTION
        "The WLM statistics table.
         Note:This mib is not supported for VX instance of Virtualization."
    ::= { wlmStats 1 }

slbStatWlmEntry OBJECT-TYPE
    SYNTAX  SlbStatWlmEntry
    MAX-ACCESS  not-accessible
    STATUS  current
    DESCRIPTION
        "The statistics of a particular work load manager."
    INDEX   { slbStatWlmIndex }
    ::= { slbStatWlmTable 1 }

SlbStatWlmEntry ::= SEQUENCE {
    slbStatWlmIndex                   Integer32, 
    slbStatWlmRegReq                  Counter32,
    slbStatWlmRegRep                  Counter32,
    slbStatWlmRegRepErr               Counter32,
    slbStatWlmDeregReq                Counter32,
    slbStatWlmDeregRep                Counter32,
    slbStatWlmDeregRepErr             Counter32,
    slbStatWlmLbStateReq              Counter32,
    slbStatWlmLbStateRep              Counter32,
    slbStatWlmLbStateRepErr           Counter32,
    slbStatWlmMembStateReq            Counter32,
    slbStatWlmMembStateRep            Counter32,
    slbStatWlmMembStateRepErr         Counter32,
    slbStatWlmWtMsgRecv               Counter32,
    slbStatWlmWtMsgParErr             Counter32,
    slbStatWlmTotInvalidLb            Counter32,
    slbStatWlmTotInvalidGrp           Counter32,
    slbStatWlmTotInvalidRealSer       Counter32,
    slbStatWlmMsgInvalidSASPHeader    Counter32,
    slbStatWlmMsgParseErr             Counter32,
    slbStatWlmMsgUnsupMsgType         Counter32
    }

slbStatWlmIndex OBJECT-TYPE
    SYNTAX Integer32
    MAX-ACCESS  read-only
    STATUS  current
    DESCRIPTION
       "The work load manager number." 
    ::= { slbStatWlmEntry 1 }

slbStatWlmRegReq OBJECT-TYPE
    SYNTAX  Counter32
    MAX-ACCESS  read-only
    STATUS  current
    DESCRIPTION
        "Total number of registration request messages sent by the switch."
    ::= { slbStatWlmEntry 2 }

slbStatWlmRegRep OBJECT-TYPE
    SYNTAX  Counter32
    MAX-ACCESS  read-only
    STATUS  current
    DESCRIPTION
        "Total number of registration replies received from the GWM."
    ::= { slbStatWlmEntry 3 }

slbStatWlmRegRepErr OBJECT-TYPE
    SYNTAX  Counter32
    MAX-ACCESS  read-only
    STATUS  current
    DESCRIPTION
        "Total number of registration replies received where the return 
         code indicates an error."
    ::= { slbStatWlmEntry 4 }
slbStatWlmDeregReq OBJECT-TYPE
    SYNTAX  Counter32
    MAX-ACCESS  read-only
    STATUS  current
    DESCRIPTION
        "Total number of deregistration request messages sent by the switch."
    ::= { slbStatWlmEntry 5 }

slbStatWlmDeregRep OBJECT-TYPE
    SYNTAX  Counter32
    MAX-ACCESS  read-only
    STATUS  current
    DESCRIPTION
        "Total number of deregistration replies received from the GWM."
    ::= { slbStatWlmEntry 6 }

slbStatWlmDeregRepErr OBJECT-TYPE
    SYNTAX  Counter32
    MAX-ACCESS  read-only
    STATUS  current
    DESCRIPTION
        "Total number of deregistration replies received where the return code flag
         set indicating an error in processing of the deregistration request."
    ::= { slbStatWlmEntry 7 }

slbStatWlmLbStateReq OBJECT-TYPE
    SYNTAX  Counter32
    MAX-ACCESS  read-only
    STATUS  current
    DESCRIPTION
        "Total number of set LB state  request messages sent by the switch."
    ::= { slbStatWlmEntry 8 }

slbStatWlmLbStateRep OBJECT-TYPE
    SYNTAX  Counter32
    MAX-ACCESS  read-only
    STATUS  current
    DESCRIPTION
        "Total number of set LB state replies received from the GWM."
    ::= { slbStatWlmEntry 9 }

slbStatWlmLbStateRepErr OBJECT-TYPE
    SYNTAX  Counter32
    MAX-ACCESS  read-only
    STATUS  current
    DESCRIPTION
        "Total number of set LB state replies received where the return code code 
         flag set indicating an error in processing of the set LB state request."
    ::= { slbStatWlmEntry 10 }

slbStatWlmMembStateReq OBJECT-TYPE
    SYNTAX  Counter32
    MAX-ACCESS  read-only
    STATUS  current
    DESCRIPTION
        "Total number of set member state  request messages sent by the switch."
    ::= { slbStatWlmEntry 11 }

slbStatWlmMembStateRep OBJECT-TYPE
    SYNTAX  Counter32
    MAX-ACCESS  read-only
    STATUS  current
    DESCRIPTION
        "Total number of set member state  replies received from the GWM."
    ::= { slbStatWlmEntry 12 }

slbStatWlmMembStateRepErr OBJECT-TYPE
    SYNTAX  Counter32
    MAX-ACCESS  read-only
    STATUS  current
    DESCRIPTION
        "Total number of set member state replies received where the return 
         code code flag set indicating an error in processing of the set
	 member state request."
    ::= { slbStatWlmEntry 13 }

slbStatWlmWtMsgRecv OBJECT-TYPE
    SYNTAX  Counter32
    MAX-ACCESS  read-only
    STATUS  current
    DESCRIPTION
        "Total number of weight updates received from the GWM."
    ::= { slbStatWlmEntry 14 }

slbStatWlmWtMsgParErr OBJECT-TYPE
    SYNTAX  Counter32
    MAX-ACCESS  read-only
    STATUS  current
    DESCRIPTION
        "Total number of errorsencountered during parsing of the send weights message."
    ::= { slbStatWlmEntry 15 }

slbStatWlmTotInvalidLb  OBJECT-TYPE
    SYNTAX  Counter32
    MAX-ACCESS  read-only
    STATUS  current
    DESCRIPTION
        "This counter is incremented when the LB name in send weights message 
         does not match the switch LB name."
    ::= { slbStatWlmEntry 16 }

slbStatWlmTotInvalidGrp  OBJECT-TYPE
    SYNTAX  Counter32
    MAX-ACCESS  read-only
    STATUS  current
    DESCRIPTION
        "This counter is incremented when the group name in send weights message 
         does not match with any of the groups configured on the switch."
    ::= { slbStatWlmEntry 17 }

slbStatWlmTotInvalidRealSer  OBJECT-TYPE
    SYNTAX  Counter32
    MAX-ACCESS  read-only
    STATUS  current
    DESCRIPTION
        "This counter is incremented when the real server name in send weights message
         does not match with any of the reals configured on the switch."
    ::= { slbStatWlmEntry 18 }

slbStatWlmMsgInvalidSASPHeader  OBJECT-TYPE
    SYNTAX  Counter32
    MAX-ACCESS  read-only
    STATUS  current
    DESCRIPTION
        "Total number of messages received from the GWM with invalid headers."
    ::= { slbStatWlmEntry 19 }

slbStatWlmMsgParseErr  OBJECT-TYPE
    SYNTAX  Counter32
    MAX-ACCESS  read-only
    STATUS  current
    DESCRIPTION
        "Total number of parse errors."
    ::= { slbStatWlmEntry 20 }

slbStatWlmMsgUnsupMsgType  OBJECT-TYPE
    SYNTAX  Counter32
    MAX-ACCESS  read-only
    STATUS  current
    DESCRIPTION
        "Total messages received where the message type is not supported by the switch."
    ::= { slbStatWlmEntry 21 }



sessMirrorTotalCreateSessionMsgRx OBJECT-TYPE
    SYNTAX  Counter32
    MAX-ACCESS  read-only
    STATUS  current
    DESCRIPTION
        "Total number of create session messages received.
         Note:This mib is not supported for VX instance of Virtualization."
    ::= { sessMirrorStats 1 }

sessMirrorTotalCreateSessionMsgTx OBJECT-TYPE
    SYNTAX  Counter32
    MAX-ACCESS  read-only
    STATUS  current
    DESCRIPTION
        "Total number of create session messages transmitted.
         Note:This mib is not supported for VX instance of Virtualization."
    ::= { sessMirrorStats 2 }

sessMirrorTotalCreateDataSessionMsgRx OBJECT-TYPE
    SYNTAX  Counter32
    MAX-ACCESS  read-only
    STATUS  current
    DESCRIPTION
        "Total number of create data session messages received.
         Note:This mib is not supported for VX instance of Virtualization."
    ::= { sessMirrorStats 3 }

sessMirrorTotalCreateDataSessionMsgTx OBJECT-TYPE
    SYNTAX  Counter32
    MAX-ACCESS  read-only
    STATUS  current
    DESCRIPTION
        "Total number of create data session messages transmitted.
         Note:This mib is not supported for VX instance of Virtualization."
    ::= { sessMirrorStats 4 }

sessMirrorTotalUpdateSessionMsgRx OBJECT-TYPE
    SYNTAX  Counter32
    MAX-ACCESS  read-only
    STATUS  current
    DESCRIPTION
        "Total number of update session messages received.
         Note:This mib is not supported for VX instance of Virtualization."
    ::= { sessMirrorStats 5 }

sessMirrorTotalUpdateSessionMsgTx OBJECT-TYPE
    SYNTAX  Counter32
    MAX-ACCESS  read-only
    STATUS  current
    DESCRIPTION
        "Total number of update session messages transmitted.
         Note:This mib is not supported for VX instance of Virtualization."
    ::= { sessMirrorStats 6 }

sessMirrorTotalUpdateDataSessionMsgRx OBJECT-TYPE
    SYNTAX  Counter32
    MAX-ACCESS  read-only
    STATUS  current
    DESCRIPTION
        "Total number of update data session messages received.
         Note:This mib is not supported for VX instance of Virtualization."
    ::= { sessMirrorStats 7 }

sessMirrorTotalUpdateDataSessionMsgTx OBJECT-TYPE
    SYNTAX  Counter32
    MAX-ACCESS  read-only
    STATUS  current
    DESCRIPTION
        "Total number of update data session messages transmitted.
         Note:This mib is not supported for VX instance of Virtualization."
    ::= { sessMirrorStats 8 }

sessMirrorTotalDeleteSessionMsgRx OBJECT-TYPE
    SYNTAX  Counter32
    MAX-ACCESS  read-only
    STATUS  current
    DESCRIPTION
        "Total number of delete session messages received.
         Note:This mib is not supported for VX instance of Virtualization."
    ::= { sessMirrorStats 9 }

sessMirrorTotalDeleteSessionMsgTx OBJECT-TYPE
    SYNTAX  Counter32
    MAX-ACCESS  read-only
    STATUS  current
    DESCRIPTION
        "Total number of delete session messages transmitted.
         Note:This mib is not supported for VX instance of Virtualization."
    ::= { sessMirrorStats 10 }

sessMirrorTotalDeleteDataSessionMsgRx OBJECT-TYPE
    SYNTAX  Counter32
    MAX-ACCESS  read-only
    STATUS  current
    DESCRIPTION
        "Total number of delete data session messages received.
         Note:This mib is not supported for VX instance of Virtualization."
    ::= { sessMirrorStats 11 }

sessMirrorTotalDeleteDataSessionMsgTx OBJECT-TYPE
    SYNTAX  Counter32
    MAX-ACCESS  read-only
    STATUS  current
    DESCRIPTION
        "Total number of delete data session messages transmitted.
         Note:This mib is not supported for VX instance of Virtualization."
    ::= { sessMirrorStats 12 }

sessMirrorTotalSessionsCreated OBJECT-TYPE
    SYNTAX  Counter32
    MAX-ACCESS  read-only
    STATUS  current
    DESCRIPTION
        "Total number of sessions created.
         Note:This mib is not supported for VX instance of Virtualization."
    ::= { sessMirrorStats 13 }

sessMirrorTotalDataSessionsCreated OBJECT-TYPE
    SYNTAX  Counter32
    MAX-ACCESS  read-only
    STATUS  current
    DESCRIPTION
        "Total number of data sessions created.
         Note:This mib is not supported for VX instance of Virtualization."
    ::= { sessMirrorStats 14 }

sessMirrorTotalSessionsUpdated OBJECT-TYPE
    SYNTAX  Counter32
    MAX-ACCESS  read-only
    STATUS  current
    DESCRIPTION
        "Total number of sessions updated.
         Note:This mib is not supported for VX instance of Virtualization."
    ::= { sessMirrorStats 15 }

sessMirrorTotalDataSessionsUpdated OBJECT-TYPE
    SYNTAX  Counter32
    MAX-ACCESS  read-only
    STATUS  current
    DESCRIPTION
        "Total number of data sessions updated.
         Note:This mib is not supported for VX instance of Virtualization."
    ::= { sessMirrorStats 16 }

sessMirrorTotalSessionsDeleted OBJECT-TYPE
    SYNTAX  Counter32
    MAX-ACCESS  read-only
    STATUS  current
    DESCRIPTION
        "Total number of sessions deleted.
         Note:This mib is not supported for VX instance of Virtualization."
    ::= { sessMirrorStats 17 }

sessMirrorTotalDataSessionsDeleted OBJECT-TYPE
    SYNTAX  Counter32
    MAX-ACCESS  read-only
    STATUS  current
    DESCRIPTION
        "Total number of data sessions deleted.
         Note:This mib is not supported for VX instance of Virtualization."
    ::= { sessMirrorStats 18 }

sessMirrorSessionTableFullErr OBJECT-TYPE
    SYNTAX  Counter32
    MAX-ACCESS  read-only
    STATUS  current
    DESCRIPTION
        "Error indicates session table full.
         Note:This mib is not supported for VX instance of Virtualization."
    ::= { sessMirrorStats 19 }

sessMirrorNoPortErr OBJECT-TYPE
    SYNTAX  Counter32
    MAX-ACCESS  read-only
    STATUS  current
    DESCRIPTION
        "Error indicates unavailable port.
         Note:This mib is not supported for VX instance of Virtualization."
    ::= { sessMirrorStats 20 }

sessMirrorSessionPresentErr OBJECT-TYPE
    SYNTAX  Counter32
    MAX-ACCESS  read-only
    STATUS  current
    DESCRIPTION
        "Error indicates session already present.
         Note:This mib is not supported for VX instance of Virtualization."
    ::= { sessMirrorStats 21 }

sessMirrorSessionNotFoundErr OBJECT-TYPE
    SYNTAX  Counter32
    MAX-ACCESS  read-only
    STATUS  current
    DESCRIPTION
        "Error indicates session not found.
         Note:This mib is not supported for VX instance of Virtualization."
    ::= { sessMirrorStats 22 }

sessMirrorCtrlSessionNotFoundErr OBJECT-TYPE
    SYNTAX  Counter32
    MAX-ACCESS  read-only
    STATUS  current
    DESCRIPTION
        "Error indicates control session not found.
         Note:This mib is not supported for VX instance of Virtualization."
    ::= { sessMirrorStats 23 }


-- Real Server Information Table

slbRealServerInfoTable OBJECT-TYPE
    SYNTAX  SEQUENCE OF SlbRealServerInfoEntry
    MAX-ACCESS  not-accessible
    STATUS  current
    DESCRIPTION
        "The table of real server run-time information.
         Note:This mib is not supported for VX instance of Virtualization."
    ::= { layer4Info 1 }

slbRealServerInfoEntry OBJECT-TYPE
    SYNTAX  SlbRealServerInfoEntry
    MAX-ACCESS  not-accessible
    STATUS  current
    DESCRIPTION
        "A row in the real server information table."
    INDEX   { slbRealServerInfoIndex }
    ::= { slbRealServerInfoTable 1 }
 
SlbRealServerInfoEntry ::= SEQUENCE {
    slbRealServerInfoIndex           Integer32,
    slbRealServerInfoIpAddr          IpAddress,
    slbRealServerMacAddr             PhysAddress,
    slbRealServerInfoSwitchPort      Integer32,
    slbRealServerInfoHealthLayer     INTEGER,
    slbRealServerInfoOverflow        INTEGER,
    slbRealServerInfoState           INTEGER,
    slbRealServerInfoVlan            Integer32,
    slbRealServerInfoHealth          DisplayString
    }

slbRealServerInfoIndex OBJECT-TYPE
    SYNTAX  Integer32
    MAX-ACCESS  read-only
    STATUS  current
    DESCRIPTION
        "The real server index" 
    ::= { slbRealServerInfoEntry 1 }

slbRealServerInfoIpAddr OBJECT-TYPE
    SYNTAX  IpAddress
    MAX-ACCESS  read-only
    STATUS  current
    DESCRIPTION
        "IP address of the real server." 
    ::= { slbRealServerInfoEntry 2 }

slbRealServerMacAddr OBJECT-TYPE
    SYNTAX  PhysAddress
    MAX-ACCESS  read-only
    STATUS  current
    DESCRIPTION
        "The MAC address of the real server." 
    ::= { slbRealServerInfoEntry 3 }

slbRealServerInfoSwitchPort OBJECT-TYPE
    SYNTAX  Integer32
    MAX-ACCESS  read-only
    STATUS  current
    DESCRIPTION
        "The switch port that the real server is connected to." 
    ::= { slbRealServerInfoEntry 4 }

slbRealServerInfoHealthLayer  OBJECT-TYPE
    SYNTAX  INTEGER { 
        layer1(1), 
        layer3(3),
        layer4(4),
        unsupported(2147483647)
        } 
    MAX-ACCESS  read-only
    STATUS  current
    DESCRIPTION
        "The OSI layer at which the real server functionality is verified."
    ::= { slbRealServerInfoEntry 5 }

slbRealServerInfoOverflow OBJECT-TYPE
    SYNTAX  INTEGER {
	overflow(1),
        no-overflow(2),
        unsupported(2147483647)
        } 
    MAX-ACCESS  read-only
    STATUS  current
    DESCRIPTION
        "The overflow state of the real server." 
    ::= { slbRealServerInfoEntry 6 }

slbRealServerInfoState OBJECT-TYPE
    SYNTAX  INTEGER {
        running(2),
        failed(3),
        disabled(4),
        unsupported(2147483647)
        } 
    MAX-ACCESS  read-only
    STATUS  current
    DESCRIPTION
        "The state of the real server."
    ::= { slbRealServerInfoEntry 7 }

slbRealServerInfoVlan OBJECT-TYPE
    SYNTAX  Integer32
    MAX-ACCESS  read-only
    STATUS  current
    DESCRIPTION
        "The VLAN that the real server belongs to." 
    ::= { slbRealServerInfoEntry 8 }

slbRealServerInfoHealth OBJECT-TYPE
    SYNTAX DisplayString (SIZE(0..128))
    MAX-ACCESS read-only
    STATUS current
    DESCRIPTION
        "The health check id configured for the real server."
    ::= { slbRealServerInfoEntry 9 }

-- Real Server Rport Table
slbRealServerRportInfoTable OBJECT-TYPE
    SYNTAX  SEQUENCE OF SlbRealServerRportInfoEntry
    MAX-ACCESS  not-accessible
    STATUS  current
    DESCRIPTION
        "The table of real server rport run-time information.
         Note:This mib is not supported for VX instance of Virtualization."
    ::= { layer4Info 3 }

slbRealServerRportInfoEntry OBJECT-TYPE
    SYNTAX  SlbRealServerRportInfoEntry
    MAX-ACCESS  not-accessible
    STATUS  current
    DESCRIPTION
        "A row in the real server rport information table."
    INDEX   { slbRealServerRportRealIndex, slbRealServerRportServIndex  }
    ::= { slbRealServerRportInfoTable 1 }
 
SlbRealServerRportInfoEntry ::= SEQUENCE {
    slbRealServerRportRealIndex           Integer32,
    slbRealServerRportServIndex           Integer32,
    slbRealServerRportInfoRport           Integer32,
    slbRealServerRportInfoState           INTEGER,
    slbRealServerRportInfoGroup           INTEGER,
    slbRealServerRportInfoRespTime        Integer32,
    slbRealServerRportInfoFailReason      DisplayString
    }

slbRealServerRportRealIndex OBJECT-TYPE
    SYNTAX  Integer32
    MAX-ACCESS  read-only
    STATUS  current
    DESCRIPTION
        "The real server index" 
    ::= { slbRealServerRportInfoEntry 1 }

slbRealServerRportServIndex OBJECT-TYPE
    SYNTAX  Integer32
    MAX-ACCESS  read-only
    STATUS  current
    DESCRIPTION
        "The real server service index" 
    ::= { slbRealServerRportInfoEntry 2 }

slbRealServerRportInfoRport OBJECT-TYPE
    SYNTAX  Integer32
    MAX-ACCESS  read-only
    STATUS  current
    DESCRIPTION
        "The real server real port number" 
    ::= { slbRealServerRportInfoEntry 3 }

slbRealServerRportInfoState OBJECT-TYPE
    SYNTAX  INTEGER {
        up(1),
        down(2)
        ,slowstart(3),
        unsupported(2147483647)
        } 
    MAX-ACCESS  read-only
    STATUS  current
    DESCRIPTION
        "The state of the real server port."
    ::= { slbRealServerRportInfoEntry 4 }

slbRealServerRportInfoGroup OBJECT-TYPE
    SYNTAX  INTEGER
    MAX-ACCESS  read-only
    STATUS  current 
    DESCRIPTION
        "The real server group number."
    ::= { slbRealServerRportInfoEntry 5 }

slbRealServerRportInfoRespTime OBJECT-TYPE
    SYNTAX  Integer32
    MAX-ACCESS  read-only
    STATUS  current
    DESCRIPTION
        "The response time of the real server health check."
    ::= { slbRealServerRportInfoEntry 6 }

slbRealServerRportInfoFailReason OBJECT-TYPE
    SYNTAX DisplayString (SIZE(0..128))
    MAX-ACCESS read-only
    STATUS current
    DESCRIPTION
        "The reason for health check fail."
    ::= { slbRealServerRportInfoEntry 7 }	

-- Virtual Server Service Information Table

slbVirtServicesInfoTable OBJECT-TYPE
    SYNTAX  SEQUENCE OF SlbVirtServicesInfoEntry
    MAX-ACCESS  not-accessible
    STATUS  current
    DESCRIPTION
        "The table of virtual server services run-time information.
         Note:This mib is not supported for VX instance of Virtualization."
    ::= { layer4Info 4 }

slbVirtServicesInfoEntry OBJECT-TYPE
    SYNTAX  SlbVirtServicesInfoEntry
    MAX-ACCESS  not-accessible
    STATUS  current
    DESCRIPTION
        "A row in the virtual service information table."
    INDEX   { slbVirtServicesInfoVirtServIndex, slbVirtServicesInfoSvcIndex, 
              slbVirtServicesInfoRealServIndex }
    ::= { slbVirtServicesInfoTable 1 }
 
SlbVirtServicesInfoEntry ::= SEQUENCE {
    slbVirtServicesInfoVirtServIndex   Integer32,
    slbVirtServicesInfoSvcIndex        Integer32,
    slbVirtServicesInfoRealServIndex   Integer32,
    slbVirtServicesInfoVport           Integer32,
    slbVirtServicesInfoRport           Integer32,
    slbVirtServicesInfoState           INTEGER,
    slbVirtServicesInfoResponseTime    Integer32,
    slbVirtServicesInfoWeight          Integer32,
    slbVirtServicesInfoCfgRealHealth   DisplayString,
    slbVirtServicesInfoRtRealHealth    DisplayString,
    slbVirtServicesInfoStateFailReason DisplayString,
    slbVirtServicesInfoRealLogexp      DisplayString
    }

slbVirtServicesInfoVirtServIndex OBJECT-TYPE
    SYNTAX  Integer32
    MAX-ACCESS  read-only
    STATUS  current
    DESCRIPTION
        "The virtual server index." 
    ::= { slbVirtServicesInfoEntry 1 }

slbVirtServicesInfoSvcIndex OBJECT-TYPE
    SYNTAX  Integer32
    MAX-ACCESS  read-only
    STATUS  current
    DESCRIPTION
        "The virtual service index." 
    ::= { slbVirtServicesInfoEntry 2 }

slbVirtServicesInfoRealServIndex OBJECT-TYPE
    SYNTAX  Integer32
    MAX-ACCESS  read-only
    STATUS  current
    DESCRIPTION
        "The real server index." 
    ::= { slbVirtServicesInfoEntry 3 }

slbVirtServicesInfoVport OBJECT-TYPE
    SYNTAX  Integer32
    MAX-ACCESS  read-only
    STATUS  current
    DESCRIPTION
        "The layer 4 virtual port number for the service." 
    ::= { slbVirtServicesInfoEntry 4 }

slbVirtServicesInfoRport OBJECT-TYPE
    SYNTAX  Integer32
    MAX-ACCESS  read-only
    STATUS  current
    DESCRIPTION
        "The layer 4 real port number for the service." 
    ::= { slbVirtServicesInfoEntry 5 }

slbVirtServicesInfoState OBJECT-TYPE
    SYNTAX  INTEGER {
        blocked(1),
        running(2),
        failed(3),
        disabled(4),
        slowstart(5),
        overflow(6),
	noinstance(7),
        unsupported(2147483647)
	}
    MAX-ACCESS  read-only
    STATUS  current
    DESCRIPTION
        "The state of the real server for this virtual service." 
    ::= { slbVirtServicesInfoEntry 6 }

slbVirtServicesInfoResponseTime OBJECT-TYPE
    SYNTAX  Integer32
    MAX-ACCESS  read-only
    STATUS  current
    DESCRIPTION
        "The health check response time for the real server for this 
         virtual service." 
    ::= { slbVirtServicesInfoEntry 7 }

slbVirtServicesInfoWeight OBJECT-TYPE
    SYNTAX  Integer32
    MAX-ACCESS  read-only
    STATUS  current
    DESCRIPTION
        "The real server weight." 
    ::= { slbVirtServicesInfoEntry 8 }

slbVirtServicesInfoCfgRealHealth OBJECT-TYPE
    SYNTAX DisplayString (SIZE(0..128))
    MAX-ACCESS read-only
    STATUS current
    DESCRIPTION
        "The configured health check for this real server."
    ::= { slbVirtServicesInfoEntry 9 }

slbVirtServicesInfoRtRealHealth OBJECT-TYPE
    SYNTAX DisplayString (SIZE(0..128))
    MAX-ACCESS read-only
    STATUS current
    DESCRIPTION
        "The runtime health check for ths real server."
    ::= { slbVirtServicesInfoEntry 10 }	

slbVirtServicesInfoStateFailReason OBJECT-TYPE
    SYNTAX DisplayString (SIZE(0..128))
    MAX-ACCESS read-only
    STATUS current
    DESCRIPTION
        "The reason for health check fail."
    ::= { slbVirtServicesInfoEntry 11 }	

slbVirtServicesInfoRealLogexp OBJECT-TYPE
    SYNTAX DisplayString (SIZE(0..128))
    MAX-ACCESS read-only
    STATUS current
    DESCRIPTION
        "The logical expression for this real server."
    ::= { slbVirtServicesInfoEntry 12 }	

slbEnhVirtServicesInfoTable OBJECT-TYPE
    SYNTAX  SEQUENCE OF SlbEnhVirtServicesInfoEntry
    MAX-ACCESS  not-accessible
    STATUS  current
    DESCRIPTION
        "The table of virtual server services run-time information.
         Note:This mib is not supported for VX instance of Virtualization."
    ::= { layer4Info 18 }

slbEnhVirtServicesInfoEntry OBJECT-TYPE
    SYNTAX  SlbEnhVirtServicesInfoEntry
    MAX-ACCESS  not-accessible
    STATUS  current
    DESCRIPTION
        "A row in the virtual service information table."
    INDEX   { slbEnhVirtServicesInfoVirtServIndex, slbEnhVirtServicesInfoSvcIndex,
              slbEnhVirtServicesInfoRealServIndex }
    ::= { slbEnhVirtServicesInfoTable 1 }

SlbEnhVirtServicesInfoEntry ::= SEQUENCE {
    slbEnhVirtServicesInfoVirtServIndex   DisplayString,
    slbEnhVirtServicesInfoSvcIndex        Integer32,
    slbEnhVirtServicesInfoRealServIndex   DisplayString,
    slbEnhVirtServicesInfoVport           Integer32,
    slbEnhVirtServicesInfoRport           Integer32,
    slbEnhVirtServicesInfoState           INTEGER,
    slbEnhVirtServicesInfoResponseTime    Integer32,
    slbEnhVirtServicesInfoWeight          Integer32,
    slbEnhVirtServicesInfoCfgRealHealth   DisplayString,
    slbEnhVirtServicesInfoRtRealHealth    DisplayString,
    slbEnhVirtServicesInfoStateFailReason DisplayString,
    slbEnhVirtServicesInfoRealLogexp      DisplayString
    }

slbEnhVirtServicesInfoVirtServIndex OBJECT-TYPE
    SYNTAX DisplayString (SIZE(1..255))
    MAX-ACCESS  read-only
    STATUS  current
    DESCRIPTION
        "The virtual server index."
    ::= { slbEnhVirtServicesInfoEntry 1 }

slbEnhVirtServicesInfoSvcIndex OBJECT-TYPE
    SYNTAX  Integer32
    MAX-ACCESS  read-only
    STATUS  current
    DESCRIPTION
        "The virtual service index."
    ::= { slbEnhVirtServicesInfoEntry 2 }

slbEnhVirtServicesInfoRealServIndex OBJECT-TYPE
    SYNTAX DisplayString (SIZE(1..255))
    MAX-ACCESS  read-only
    STATUS  current
    DESCRIPTION
        "The real server index."
    ::= { slbEnhVirtServicesInfoEntry 3 }

slbEnhVirtServicesInfoVport OBJECT-TYPE
    SYNTAX  Integer32
    MAX-ACCESS  read-only
    STATUS  current
    DESCRIPTION
        "The layer 4 virtual port number for the service."
    ::= { slbEnhVirtServicesInfoEntry 4 }

slbEnhVirtServicesInfoRport OBJECT-TYPE
    SYNTAX  Integer32
    MAX-ACCESS  read-only
    STATUS  current
    DESCRIPTION
        "The layer 4 real port number for the service."
    ::= { slbEnhVirtServicesInfoEntry 5 }

slbEnhVirtServicesInfoState OBJECT-TYPE
    SYNTAX  INTEGER {
        blocked(1),
        running(2),
        failed(3),
        disabled(4),
        slowstart(5),
        overflow(6),
        noinstance(7),
        unsupported(2147483647)
        }
    MAX-ACCESS  read-only
    STATUS  current
    DESCRIPTION
        "The state of the real server for this virtual service."
    ::= { slbEnhVirtServicesInfoEntry 6 }

slbEnhVirtServicesInfoResponseTime OBJECT-TYPE
    SYNTAX  Integer32
    MAX-ACCESS  read-only
    STATUS  current
    DESCRIPTION
        "The health check response time for the real server for this
         virtual service."
    ::= { slbEnhVirtServicesInfoEntry 7 }

slbEnhVirtServicesInfoWeight OBJECT-TYPE
    SYNTAX  Integer32
    MAX-ACCESS  read-only
    STATUS  current
    DESCRIPTION
        "The real server weight."
    ::= { slbEnhVirtServicesInfoEntry 8 }

slbEnhVirtServicesInfoCfgRealHealth OBJECT-TYPE
    SYNTAX DisplayString (SIZE(0..128))
    MAX-ACCESS read-only
    STATUS current
    DESCRIPTION
        "The configured health check for this real server."
    ::= { slbEnhVirtServicesInfoEntry 9 }

slbEnhVirtServicesInfoRtRealHealth OBJECT-TYPE
    SYNTAX DisplayString (SIZE(0..128))
    MAX-ACCESS read-only
    STATUS current
    DESCRIPTION
        "The runtime health check for ths real server."
    ::= { slbEnhVirtServicesInfoEntry 10 }

slbEnhVirtServicesInfoStateFailReason OBJECT-TYPE
    SYNTAX DisplayString (SIZE(0..128))
    MAX-ACCESS read-only
    STATUS current
    DESCRIPTION
        "The reason for health check fail."
    ::= { slbEnhVirtServicesInfoEntry 11 }

slbEnhVirtServicesInfoRealLogexp OBJECT-TYPE
    SYNTAX DisplayString (SIZE(0..128))
    MAX-ACCESS read-only
    STATUS current
    DESCRIPTION
        "The logical expression for this real server."
    ::= { slbEnhVirtServicesInfoEntry 12 }

-- Virtual Server Service Information Table

slbEnhVirtSpecificServicesInfoTable OBJECT-TYPE
    SYNTAX  SEQUENCE OF SlbEnhVirtSpecificServicesInfoEntry
    MAX-ACCESS  not-accessible
    STATUS  current
    DESCRIPTION
        "The table of specific virtual service information.
         Note:This mib is not supported for VX instance of Virtualization."
    ::= { layer4Info 21 }

slbEnhVirtSpecificServicesInfoEntry OBJECT-TYPE
    SYNTAX  SlbEnhVirtSpecificServicesInfoEntry
    MAX-ACCESS  not-accessible
    STATUS  current
    DESCRIPTION
        "A row in the virtual service information table."
    INDEX   { slbEnhVirtSpecificServicesInfoVirtServIndex, slbEnhVirtSpecificServicesInfoSvcIndex }
    ::= { slbEnhVirtSpecificServicesInfoTable 1 }

SlbEnhVirtSpecificServicesInfoEntry ::= SEQUENCE {
    slbEnhVirtSpecificServicesInfoVirtServIndex   DisplayString,
    slbEnhVirtSpecificServicesInfoSvcIndex        Integer32,
    slbEnhVirtSpecificServicesInfoStatus          INTEGER
    }

slbEnhVirtSpecificServicesInfoVirtServIndex OBJECT-TYPE
    SYNTAX DisplayString (SIZE(1..255))
    MAX-ACCESS  read-only
    STATUS  current
    DESCRIPTION
        "The virtual server index."
    ::= { slbEnhVirtSpecificServicesInfoEntry 1 }

slbEnhVirtSpecificServicesInfoSvcIndex OBJECT-TYPE
    SYNTAX  Integer32
    MAX-ACCESS  read-only
    STATUS  current
    DESCRIPTION
        "The virtual service index."
    ::= { slbEnhVirtSpecificServicesInfoEntry 2 }

slbEnhVirtSpecificServicesInfoStatus OBJECT-TYPE
    SYNTAX  INTEGER {
        up(0),
        down(1),
        admindown(2),
        warning(3),
        shudown(4),
        unsupported(2147483647)
        }
    MAX-ACCESS  read-only
    STATUS  current
    DESCRIPTION
        "The status of the specific virtual service."
    ::= { slbEnhVirtSpecificServicesInfoEntry 3 }

--Sync Peer Cluster Info Start.

clusterInfo    OBJECT IDENTIFIER ::= { layer4Info 22 }

slbClusterInfoPeerTable OBJECT-TYPE
    SYNTAX SEQUENCE OF SlbClusterInfoPeerEntry
    MAX-ACCESS not-accessible
    STATUS current
    DESCRIPTION
        "The information of slb cluster.
         Note:This mib is not supported for VX instance of Virtualization."
    ::= { clusterInfo 1 }

slbClusterInfoPeerEntry OBJECT-TYPE
    SYNTAX SlbClusterInfoPeerEntry
    MAX-ACCESS not-accessible
    STATUS current
    DESCRIPTION
        "Information about Cluster Sync Peer Switch
         Note:This mib is not supported for VX instance of Virtualization."
    INDEX { slbClusterInfoPeerIndex }
    ::= { slbClusterInfoPeerTable 1 }

SlbClusterInfoPeerEntry ::= SEQUENCE {  
    slbClusterInfoPeerIndex                  Integer32,
    slbClusterInfoPeerIpAddr                 IpAddress,
    slbClusterInfoPeerKeepAliveSent          Integer32,
    slbClusterInfoPeerKeepAliveReceived      Integer32,
    slbClusterInfoPeerKeepAliveLastReceived  Integer32
    }

slbClusterInfoPeerIndex OBJECT-TYPE
    SYNTAX Integer32
    MAX-ACCESS read-only
    STATUS current
    DESCRIPTION
        "The index for cluster sync peer switchs."
    ::= { slbClusterInfoPeerEntry 1 }

slbClusterInfoPeerIpAddr OBJECT-TYPE
    SYNTAX IpAddress
    MAX-ACCESS read-only
    STATUS current
    DESCRIPTION
        "The IP address of the cluster sync peer switch."
    ::= { slbClusterInfoPeerEntry 2 }

slbClusterInfoPeerKeepAliveSent OBJECT-TYPE
    SYNTAX Integer32
    MAX-ACCESS read-only
    STATUS current
    DESCRIPTION
        "Total Keep Alives Sent"
    ::= { slbClusterInfoPeerEntry 3 }

slbClusterInfoPeerKeepAliveReceived OBJECT-TYPE
    SYNTAX Integer32
    MAX-ACCESS read-only
    STATUS current
    DESCRIPTION
        "Total Keep Alives Sent"
    ::= { slbClusterInfoPeerEntry 4 }

slbClusterInfoPeerKeepAliveLastReceived OBJECT-TYPE
    SYNTAX Integer32
    MAX-ACCESS read-only
    STATUS current
    DESCRIPTION
        "Total Keep Alives Sent"
    ::= { slbClusterInfoPeerEntry 5 }

--Sync Peer Cluster info End

-- slb session table info
slbSessionInfo        OBJECT IDENTIFIER ::= { layer4Info 5 }

slbSessionInfoState OBJECT-TYPE
    SYNTAX  INTEGER {
	start(1), 
        idle(2),
        inprogress(3),
	complete(4),
        unsupported(2147483647)
	}
    MAX-ACCESS  read-write
    STATUS  current
    DESCRIPTION
 	"When this object is read the current state is returned.
         idle(2) indicates that there is no session binding table request
         in progress.
	 When a read on this object returns inprogress(3) indicates that
	 a session binding table retrieval request is in progress.
         Setting the value to start(1), will start a new session table 
         retrieval operation based on the filtering criteria.
         complete(4) indicates that the session table has been retrieved.
         Once the slbSessionInfoTable is read the state should be set back to 
         'idle' which frees the session table buffer and others can issue a 
         request command via SNMP.
         Note:This mib is not supported for VX instance of Virtualization."
	
    ::= { slbSessionInfo 1 }

slbSessionInfoType OBJECT-TYPE
    SYNTAX  INTEGER {
	all(1),
	cip(2),
	cport(3),
	dip(4),
	dport(5),
	pip(6),
	pport(7),
	filter(8),
	flag(9),
	port(10),
	real(11),
        unsupported(2147483647)
	}
    MAX-ACCESS  read-write
    STATUS  current
    DESCRIPTION
        "This identifies the filtering criteria for the 
         session binding table request. 
	 all(1)   : Show all session entries
	 cip(2)   : Show all session entries with source IP address
         cport(3) : Show all session entries with source port
         dip(4)   : Show all session entries with destination IP address
         dport(5) : Show all session entries with destination port
         pip(6)   : Show all session entries with proxy IP address
         pport(7) : Show all session entries with proxy port
         filter(8): Show all session entries with matching filter
         flag(9)  : Show all session entries with matching flag
         port(10) : Show all session entries with ingress port
         real(11) : Show all session entries with real IP address.
         Note:This mib is not supported for VX instance of Virtualization."
    ::= { slbSessionInfo 2 }

slbSessionInfoIpAddr OBJECT-TYPE
    SYNTAX  IpAddress
    MAX-ACCESS  read-write
    STATUS  current
    DESCRIPTION
        "IP address of the requested filtering criteria 
	 0.0.0.0 if the filtering criteria is not  to match
         session entries with the same IP address.
         Note:This mib is not supported for VX instance of Virtualization."
    ::= { slbSessionInfo 3 }

slbSessionInfoFilterId OBJECT-TYPE
    SYNTAX  Integer32
    MAX-ACCESS  read-write
    STATUS  current
    DESCRIPTION
         "This field indicates that the session is created by filtering
          code as a result of the IP header keys matching the filtering
          criteria. 0 if slbSessionInfoFilterID is not the matching criteria.
          Note:This mib is not supported for VX instance of Virtualization."
    ::= { slbSessionInfo 4 }

slbSessionInfoPortId OBJECT-TYPE
    SYNTAX  Integer32
    MAX-ACCESS  read-write
    STATUS  current
    DESCRIPTION
        "The <port number> if the filtering criteria is (port) to
         match all session entries with the matching ingress port 
         or this represents the <real port> if the requested filtering
         criteria is to match session entries with (pport) proxy port, 
         (cport) source port, (dport) destination port,  
         This entry is 0 if the filtering criteria is not to match
         session entries with the same port.
         Note:This mib is not supported for VX instance of Virtualization."
    ::= { slbSessionInfo 5 }

slbSessionInfoFlag OBJECT-TYPE
    SYNTAX  INTEGER {
	eFlag(1),
	lFlag(2),
	nFlag(3),
	pFlag(4),
	sFlag(5),
	tFlag(6),
	uFlag(7),
	wFlag(8),
	ruFlag(9),
	riFlag(10),
	viFlag(11),
	vrFlag(12),
	vsFlag(13),
        vmFlag(14),
	vdFlag(15),
	none(20),
        unsupported(2147483647)
	}
    MAX-ACCESS  read-write
    STATUS  current
    DESCRIPTION
        "If the filtering criteria is flag select one of e|l|n|p|s|t|u|w(Flag)
         none(20) is selected if flag is not the fitering criteria.

         eFlag: Indicates the session is in use and will be aged out if no
                traffic is received within session timeout value.

         lFlag: Indicates the session is a link load balance session.

         nFlag: Indicates the session only translates the destination
                MAC when forwarding client traffic to the real server.

         pFlag: Indicates the session is a persistent session and is not to
                be aged out. Fields (6), (7) and (8) are not shown for
                persistent session.

         sFlag: Indicates the session is a persistent session and the
                application is SSL or Cookie Pbind.

         tFlag: Indicates the session is TCP rate limiting per-client entry.

         uFlag: Indicates the session is L7 delay binding and switch is
                trying to open TCP connection to real server.

         wFlag: Indicates the session only translates the destination
                MAC when forwarding layer 7 WCR traffic to the real server.

         ruFlag: Indicates the session is a UDP rate limiting per-client entry.

         riFlag: Indicates the session is a ICMP rate limiting per-client 
                 entry.

         viFlag: Indicates the session is a SIP INVITE session.

         vrFlag: Indicates the session is a SIP REGISTER session.

         vsFlag: Indicates the session is a SIP SUBSCRIBE session.

         vmFlag: Indicates the session is a SIP MESSAGE session.

         vdFlag: Indicates the session is a SIP NAT data session.
         Note:This mib is not supported for VX instance of Virtualization."

    ::= { slbSessionInfo 6 }

slbSessionInfoStringFormatFlag OBJECT-TYPE
    SYNTAX  INTEGER {
	formatted(1),
	none(2),
        unsupported(2147483647)
	}
    MAX-ACCESS  read-write
    STATUS  current
    DESCRIPTION
        "The flag which determines if the session table entries
         have to be formatted or (none) indicates no formatting to be done.
         Note:This mib is not supported for VX instance of Virtualization." 
    ::= { slbSessionInfo 7 }

slbSessionInfoMaxSessDump OBJECT-TYPE
    SYNTAX  Integer32 
    MAX-ACCESS  read-only
    STATUS  current
    DESCRIPTION
    "The maximum number of sessions that can exist at any given time.
     Note:This mib is not supported for VX instance of Virtualization."
    ::= { slbSessionInfo 9 }

slbSessionInfoTable OBJECT-TYPE
    SYNTAX SEQUENCE OF SlbSessionInfoEntry
    MAX-ACCESS not-accessible
    STATUS current
    DESCRIPTION
        "The table of SLB session entries.
         Note:This mib is not supported for VX instance of Virtualization."
    ::= { slbSessionInfo 8 }

slbSessionInfoEntry OBJECT-TYPE
    SYNTAX SlbSessionInfoEntry
    MAX-ACCESS not-accessible
    STATUS current
    DESCRIPTION
        "Information about SLB sessions."
    INDEX { slbSessionInfoSpIndex, slbSessionInfoIndex }
    ::= { slbSessionInfoTable 1 }
 
SlbSessionInfoEntry ::= SEQUENCE {
    slbSessionInfoSpIndex                    Integer32,
    slbSessionInfoIndex                      Integer32,
    slbSessionInfoString            	     OCTET STRING
    }

slbSessionInfoSpIndex OBJECT-TYPE
    SYNTAX  Integer32
    MAX-ACCESS  read-only
    STATUS  current
    DESCRIPTION
        "The SP which created the session." 
    ::= { slbSessionInfoEntry 1 }

slbSessionInfoIndex OBJECT-TYPE
    SYNTAX  Integer32
    MAX-ACCESS  read-only
    STATUS  current
    DESCRIPTION
        "The index to the slbSessionInfoTable." 
    ::= { slbSessionInfoEntry 2 }

slbSessionInfoString OBJECT-TYPE
    SYNTAX OCTET STRING
    MAX-ACCESS read-only
    STATUS current
    DESCRIPTION
        "The string representing the SLB session entries in the formatted case:
	 The fields, (1)-(13), associated with a session, as identified in the
	 example below are described in the following.

3, 01: 1.1.1.1 4586, 2.2.2.1 http -> 3567 3.3.3.1 http age 6 f:10 ELNPSRtUW c:#
(1) (2) (3)     (4)  (5)      (6)     (7)   (8)    (9)  (10)  (11)  (12) (13)

3, 01: 1.1.1.1 4586, 2.2.2.1 http ->
(1) (2) (3)     (4)  (5)      (6)
       1.1.1.2 3567 3.3.3.1 http age 6 f:10 ELNPSRtUW c:#
        (7a)     (7)   (8)    (9) (10)  (11)  (12) (13)

------------------------------------------------------------------
(1) SP number:
    This field indicates which SP created the session.

(2) Ingress port:
    This field shows the physical port# of the client traffic that
    entered to the switch.

(3) Source IP address:
    This field contains the source IP address from client IP packet.

(4) Source port:                          
    This field identifies the TCP/UDP source port from client packet.

(5) Destination IP address:
    This is the destination IP address from client TCP/UDP packet.

    For load balancing, this address is the virtual IP address.
    For filtering redirect, this address is the destination server's address.

(6) Destination port:
    This field identifies the TCP/UDP destination port from client packet.

(7a)Proxy IP address:                     
    This field contains the proxy IP address substituted by the switch.

(7) Proxy port:                           
    This field identifies the TCP/UDP source port substituted by the switch.

    The switch does this substitution when Direct Access Mode is enabled or
    Proxy is enabled.

(8) Real server IP address:               
    For load balancing, this field contains the IP address of the real
    server that the switch selects to forward client packet to.
    If the switch does not find live server, this field is the
    same as destination IP address(5).

    e.g. 3,01: 1.1.1.1 1040, 2.2.2.1 http -> 3.3.3.1 http age 10
         3,01: 1.1.1.1 1040, 2.2.2.1 http -> 2.2.2.1 http age 10

    For filtering, this field also shows the real server IP address. No
    address is shown if the filter action is Allow, Deny or NAT.
    It will show ALLOW, DENY or NAT instead.

    e.g. 3,01: 1.1.1.1 1040, 2.2.2.1 http -> 3.3.3.1 http age 10 f:11
         3,01: 1.1.1.1 1040, 2.2.2.1 http ALLOW age 10 f:22

(9) Server port:                          
    For load balancing, this field is the same as destination port(6)
    except for the RTSP UDP session. For RTSP UDP session, this server
    port is obtained from client-server negotiation.

    e.g. 3,01: 1.1.1.1 1040, 2.2.2.1 http -> 3.3.3.1 http age 10
         3,01: 1.1.1.1 6970, 2.2.2.1 rtsp -> 3.3.3.1 21220 age 10 P

    For filtering, this field is the filtering application port.
    It is for internal use only. This field can be urlwcr, wcr,
    idslb, linkslb or nonat.
    e.g. 3,01: 1.1.1.1 1040, 2.2.2.1 http -> 3.3.3.1 urlwcr age 4 f:123
         2,07: 1.1.1.1 1706, 2.2.2.1 http -> 192.168.4.10 linklb age 8 f:10 E

(10) Age:
    This is the session timeout value. If no packet is received within
    the value specified, the session is freed.
    e.g. age 10    - The session is aged out in 10 minutes.
         age < 160 - The session is aged out in 160 minutes. This <
                     indicates that slowage is used(user configures
                     /cfg/slb/adv/slowage)

(11) Filter number:                       
     This field indicates that the session is created by filtering
     code as a result of the IP header keys matching the filtering
     criteria.

(12) Flag:
     E: Indicates the session is in use and will be aged out if no
        traffic is received within session timeout value.

     L: Indicates the session is a link load balance session.

     N: Indicates the session only translates the destination
        MAC when forwarding client traffic to the real server.

     P: Indicates the session is a persistent session and is not to
        be aged out. Fields (6), (7) and (8) are not shown for
        persistent session.

     S: Indicates the session is a persistent session and the
        application is SSL or Cookie Pbind.

     Rt: Indicates the session is TCP rate limiting per-client entry.

     Ru: Indicates the session is UDP rate limiting per-client entry.

     Ri: Indicates the session is ICMP rate limiting per-client entry.

     U: Indicates the session is L7 delay binding and switch is
        trying to open TCP connection to real server.

     W: Indicates the session only translates the destination
        MAC when forwarding layer 7 WCR traffic to the real server.

(13) Persistent session user count:
     This counter indicates the number of client sessions created
     associated with this persistent session."
    ::= { slbSessionInfoEntry 3 }



-- fastview

slbCurAcclCfgFastViewOnOff OBJECT-TYPE
   SYNTAX  INTEGER {
       on(1),
       off(2),
       unsupported(2147483647)
       }
   MAX-ACCESS  read-only
   STATUS  current
   DESCRIPTION
       "Globally ON or OFF of fastview.
        Note:This mib is not supported for VX instance of Virtualization."
   ::= { fastview 1}

slbNewAcclCfgFastViewOnOff OBJECT-TYPE
   SYNTAX  INTEGER {
       on(1),
       off(2),
       unsupported(2147483647)
       }
   MAX-ACCESS  read-write
   STATUS  current
   DESCRIPTION
       "Globally ON or OFF of fastview.
        Note:This mib is not supported for VX instance of Virtualization."
   ::= { fastview 2}

slbCurAcclCfgFastWaTable OBJECT-TYPE
    SYNTAX  SEQUENCE OF SlbCurAcclCfgFastWaEntry
    MAX-ACCESS  not-accessible
    STATUS  current
    DESCRIPTION
        "The table for configuring fastview web application.
         Note:This mib is not supported for VX instance of Virtualization."
    ::= { fastview 3 }

slbCurAcclCfgFastWaEntry OBJECT-TYPE
    SYNTAX  SlbCurAcclCfgFastWaEntry
    MAX-ACCESS  not-accessible
    STATUS  current
    DESCRIPTION
        "A row in the fastview web application table."
    INDEX   { slbCurAcclCfgFastWaNameIdIndex }
    ::= { slbCurAcclCfgFastWaTable 1 }

SlbCurAcclCfgFastWaEntry ::= SEQUENCE {
    slbCurAcclCfgFastWaNameIdIndex          DisplayString,
    slbCurAcclCfgFastWaAdminStatus          INTEGER,
    slbCurAcclCfgFastWaDummy                INTEGER,
    slbCurAcclCfgFastWaName                 DisplayString
    }

slbCurAcclCfgFastWaNameIdIndex OBJECT-TYPE
    SYNTAX   DisplayString (SIZE (0..31))
    MAX-ACCESS  read-only
    STATUS  current
    DESCRIPTION
        "The fastview web application ID(key id) as an index."
    ::= { slbCurAcclCfgFastWaEntry 1 }

slbCurAcclCfgFastWaAdminStatus OBJECT-TYPE
    SYNTAX  INTEGER {
        enabled(1),
        disabled(2),
        unsupported(2147483647)
        }
    MAX-ACCESS  read-only
    STATUS  current
    DESCRIPTION
        "Status (enable/disable) of fastview web application."
    ::= { slbCurAcclCfgFastWaEntry 2 }

slbCurAcclCfgFastWaDummy OBJECT-TYPE
    SYNTAX  INTEGER {
        enabled(1),
        disabled(2),
        unsupported(2147483647)
        }
    MAX-ACCESS  read-only
    STATUS  current
    DESCRIPTION
        "Dummy field to maintain offsets between cur and new."
    ::= { slbCurAcclCfgFastWaEntry 3 }

slbCurAcclCfgFastWaName OBJECT-TYPE
    SYNTAX   DisplayString (SIZE (0..31))
    MAX-ACCESS  read-only
    STATUS  current
    DESCRIPTION
        "Web application name."
    ::= { slbCurAcclCfgFastWaEntry 4 }

slbNewAcclCfgFastWaTable OBJECT-TYPE
    SYNTAX  SEQUENCE OF SlbNewAcclCfgFastWaEntry
    MAX-ACCESS  not-accessible
    STATUS  current
    DESCRIPTION
        "The table for configuring fastview web application.
         Note:This mib is not supported for VX instance of Virtualization."
    ::= { fastview 4 }

slbNewAcclCfgFastWaEntry OBJECT-TYPE
    SYNTAX  SlbNewAcclCfgFastWaEntry
    MAX-ACCESS  not-accessible
    STATUS  current
    DESCRIPTION
        "A row in the fastview web application table."
    INDEX   { slbNewAcclCfgFastWaNameIdIndex }
    ::= { slbNewAcclCfgFastWaTable 1 }

SlbNewAcclCfgFastWaEntry ::= SEQUENCE {
    slbNewAcclCfgFastWaNameIdIndex          DisplayString,
    slbNewAcclCfgFastWaAdminStatus          INTEGER,
    slbNewAcclCfgFastWaDelete               INTEGER,
    slbNewAcclCfgFastWaName                 DisplayString,
    slbNewAcclCfgFastWaCopy                 DisplayString
    }

slbNewAcclCfgFastWaNameIdIndex OBJECT-TYPE
    SYNTAX   DisplayString (SIZE (0..31))
    MAX-ACCESS  read-only
    STATUS  current
    DESCRIPTION
        "The fastview web application ID(key id) as an index, length of the string should be 32 characters."
    ::= { slbNewAcclCfgFastWaEntry 1 }

slbNewAcclCfgFastWaAdminStatus OBJECT-TYPE
    SYNTAX  INTEGER {
        enabled(1),
        disabled(2),
        unsupported(2147483647)
        }
    MAX-ACCESS  read-create
    STATUS  current
    DESCRIPTION
        "Enable or disable fastview web application."
    ::= { slbNewAcclCfgFastWaEntry 2 }

slbNewAcclCfgFastWaDelete OBJECT-TYPE
    SYNTAX  INTEGER {
        other(1),
        delete(2),
        unsupported(2147483647)
        }
    MAX-ACCESS  read-create
    STATUS  current
    DESCRIPTION
        "Delete fastview web application."
    ::= { slbNewAcclCfgFastWaEntry 3 }

slbNewAcclCfgFastWaName OBJECT-TYPE
    SYNTAX   DisplayString (SIZE (0..31))
    MAX-ACCESS  read-create
    STATUS  current
    DESCRIPTION
        "Web application name."
    ::= { slbNewAcclCfgFastWaEntry 4 }

slbNewAcclCfgFastWaCopy OBJECT-TYPE
    SYNTAX   DisplayString (SIZE (0..31))
    MAX-ACCESS  read-create
    STATUS  current
    DESCRIPTION
        "Web application name."
    ::= { slbNewAcclCfgFastWaEntry 5 }

slbCurAcclCfgFastViewSupported OBJECT-TYPE
   SYNTAX  INTEGER {
       true(1),
       false(2),
       unsupported(2147483647)
       }
   MAX-ACCESS  read-only
   STATUS  current
   DESCRIPTION
       "Is fastview supported for platform.
        Note:This mib is not supported for VX instance of Virtualization."
   ::= { fastview 5 }

slbNewAcclCfgClusterTable OBJECT-TYPE
    SYNTAX  SEQUENCE OF SlbNewAcclCfgClusterEntry
    MAX-ACCESS  not-accessible
    STATUS  current
    DESCRIPTION
        "The table for configuring fastview cluster policy.
         Note:This mib is not supported for VX instance of Virtualization."
    ::= { fastview 6 }

slbNewAcclCfgClusterEntry OBJECT-TYPE
    SYNTAX  SlbNewAcclCfgClusterEntry
    MAX-ACCESS  not-accessible
    STATUS  current
    DESCRIPTION
        "A row in the fastview cluster table."
    INDEX   { slbNewAcclCfgClusterVirtId, slbNewAcclCfgClusterServiceVport }
    ::= { slbNewAcclCfgClusterTable 1 }

SlbNewAcclCfgClusterEntry ::= SEQUENCE {
    slbNewAcclCfgClusterVirtId                   DisplayString,
    slbNewAcclCfgClusterServiceVport             Integer32,
    slbNewAcclCfgClusterAdminStatus              INTEGER,
    slbNewAcclCfgClusterPeerVIP1                 IpAddress,
    slbNewAcclCfgClusterPeerVIP2                 IpAddress,
    slbNewAcclCfgClusterPeerVIP3                 IpAddress,
    slbNewAcclCfgClusterPeerVIP4                 IpAddress,
    slbNewAcclCfgClusterPeerVIP5                 IpAddress,
    slbNewAcclCfgClusterDelete                   INTEGER
    }

slbNewAcclCfgClusterVirtId OBJECT-TYPE
    SYNTAX   DisplayString (SIZE (0..255))
    MAX-ACCESS  read-only
    STATUS  current
    DESCRIPTION
        ""
    ::= { slbNewAcclCfgClusterEntry 1 }

slbNewAcclCfgClusterServiceVport OBJECT-TYPE
    SYNTAX  Integer32
    MAX-ACCESS  read-only
    STATUS  current
    DESCRIPTION
        "The layer 4 virtual port number for the service."
    ::= { slbNewAcclCfgClusterEntry 2 }

slbNewAcclCfgClusterAdminStatus OBJECT-TYPE
    SYNTAX  INTEGER {
        enabled(1),
        disabled(2),
        unsupported(2147483647)
        }
    MAX-ACCESS  read-create
    STATUS  current
    DESCRIPTION
        "Enable or disable fastview cluster."
    ::= { slbNewAcclCfgClusterEntry 3 }

slbNewAcclCfgClusterPeerVIP1 OBJECT-TYPE
    SYNTAX  IpAddress
    MAX-ACCESS  read-create
    STATUS  current
    DESCRIPTION
        "IP address of the peer vip 1."
    ::= { slbNewAcclCfgClusterEntry 4 }

slbNewAcclCfgClusterPeerVIP2 OBJECT-TYPE
    SYNTAX  IpAddress
    MAX-ACCESS  read-create
    STATUS  current
    DESCRIPTION
        "IP address of the peer vip 2."
    ::= { slbNewAcclCfgClusterEntry 5 }

slbNewAcclCfgClusterPeerVIP3 OBJECT-TYPE
    SYNTAX  IpAddress
    MAX-ACCESS  read-create
    STATUS  current
    DESCRIPTION
        "IP address of the peer vip 3."
    ::= { slbNewAcclCfgClusterEntry 6 }

slbNewAcclCfgClusterPeerVIP4 OBJECT-TYPE
    SYNTAX  IpAddress
    MAX-ACCESS  read-create
    STATUS  current
    DESCRIPTION
        "IP address of the peer vip 4."
    ::= { slbNewAcclCfgClusterEntry 7 }

slbNewAcclCfgClusterPeerVIP5 OBJECT-TYPE
    SYNTAX  IpAddress
    MAX-ACCESS  read-create
    STATUS  current
    DESCRIPTION
        "IP address of the peer vip 5."
    ::= { slbNewAcclCfgClusterEntry 8 }

slbNewAcclCfgClusterDelete OBJECT-TYPE
    SYNTAX  INTEGER {
        other(1),
        delete(2),
        unsupported(2147483647)
        }
    MAX-ACCESS  read-create
    STATUS  current
    DESCRIPTION
        "Delete fastview web application."
    ::= { slbNewAcclCfgClusterEntry 9 }

slbCurAcclCfgClusterTable OBJECT-TYPE
    SYNTAX  SEQUENCE OF SlbCurAcclCfgClusterEntry
    MAX-ACCESS  not-accessible
    STATUS  current
    DESCRIPTION
        "The table for configuring fastview non affinity policy.
         Note:This mib is not supported for VX instance of Virtualization."
    ::= { fastview 7 }

slbCurAcclCfgClusterEntry OBJECT-TYPE
    SYNTAX  SlbCurAcclCfgClusterEntry
    MAX-ACCESS  not-accessible
    STATUS  current
    DESCRIPTION
        "A row in the fastview non affinity table."
    INDEX   { slbCurAcclCfgClusterVirtId, slbCurAcclCfgClusterServiceVport }
    ::= { slbCurAcclCfgClusterTable 1 }

SlbCurAcclCfgClusterEntry ::= SEQUENCE {
    slbCurAcclCfgClusterVirtId                   DisplayString,
    slbCurAcclCfgClusterServiceVport             Integer32,
    slbCurAcclCfgClusterAdminStatus              INTEGER,
    slbCurAcclCfgClusterPeerVIP1                 IpAddress,
    slbCurAcclCfgClusterPeerVIP2                 IpAddress,
    slbCurAcclCfgClusterPeerVIP3                 IpAddress,
    slbCurAcclCfgClusterPeerVIP4                 IpAddress,
    slbCurAcclCfgClusterPeerVIP5                 IpAddress
    }

slbCurAcclCfgClusterVirtId OBJECT-TYPE
    SYNTAX   DisplayString (SIZE (0..255))
    MAX-ACCESS  read-only
    STATUS  current
    DESCRIPTION
        ""
    ::= { slbCurAcclCfgClusterEntry 1 }

slbCurAcclCfgClusterServiceVport OBJECT-TYPE
    SYNTAX  Integer32
    MAX-ACCESS  read-only
    STATUS  current
    DESCRIPTION
        "The layer 4 virtual port number for the service."
    ::= { slbCurAcclCfgClusterEntry 2 }
	
slbCurAcclCfgClusterAdminStatus OBJECT-TYPE
    SYNTAX  INTEGER {
        enabled(1),
        disabled(2),
        unsupported(2147483647)
        }
    MAX-ACCESS  read-only
    STATUS  current
    DESCRIPTION
        "Enable or disable fastview cluster."
    ::= { slbCurAcclCfgClusterEntry 3 }

slbCurAcclCfgClusterPeerVIP1 OBJECT-TYPE
    SYNTAX  IpAddress
    MAX-ACCESS  read-only
    STATUS  current
    DESCRIPTION
        "IP address of the peer vip 1."
    ::= { slbCurAcclCfgClusterEntry 4 }

slbCurAcclCfgClusterPeerVIP2 OBJECT-TYPE
    SYNTAX  IpAddress
    MAX-ACCESS  read-only
    STATUS  current
    DESCRIPTION
        "IP address of the peer vip 2."
    ::= { slbCurAcclCfgClusterEntry 5 }

slbCurAcclCfgClusterPeerVIP3 OBJECT-TYPE
    SYNTAX  IpAddress
    MAX-ACCESS  read-only
    STATUS  current
    DESCRIPTION
        "IP address of the peer vip 3."
    ::= { slbCurAcclCfgClusterEntry 6 }

slbCurAcclCfgClusterPeerVIP4 OBJECT-TYPE
    SYNTAX  IpAddress
    MAX-ACCESS  read-only
    STATUS  current
    DESCRIPTION
        "IP address of the peer vip 4."
    ::= { slbCurAcclCfgClusterEntry 7 }

slbCurAcclCfgClusterPeerVIP5 OBJECT-TYPE
    SYNTAX  IpAddress
    MAX-ACCESS  read-only
    STATUS  current
    DESCRIPTION
        "IP address of the peer vip 5."
    ::= { slbCurAcclCfgClusterEntry 8 }

-- Global SLB Information

gslbInfo         OBJECT IDENTIFIER ::= { layer4Info 6 }

-- Global SLB Remote Real Server Information

gslbInfoRemRealServerTable OBJECT-TYPE
    SYNTAX SEQUENCE OF GslbInfoRemRealServerEntry
    MAX-ACCESS not-accessible
    STATUS current
    DESCRIPTION
        "The Global SLB virtual server information table.
         Note:This mib is not supported for VX instance of Virtualization."
    ::= { gslbInfo 1 }

gslbInfoRemRealServerEntry OBJECT-TYPE
    SYNTAX GslbInfoRemRealServerEntry
    MAX-ACCESS not-accessible
    STATUS current
    DESCRIPTION
        "A row in the Global SLB remote real server information table."
    INDEX { gslbInfoRemRealServerIdx }
    ::= { gslbInfoRemRealServerTable 1 }

GslbInfoRemRealServerEntry ::=     SEQUENCE {
    gslbInfoRemRealServerIdx            Integer32,
    gslbInfoRemRealServerIpAddr         IpAddress,
    gslbInfoRemRealServerName           DisplayString,
    gslbInfoRemRealServerState          INTEGER
    }
    
gslbInfoRemRealServerIdx OBJECT-TYPE
    SYNTAX Integer32
    MAX-ACCESS read-only
    STATUS current
    DESCRIPTION
        "The remote real server number that identifies the remote real server."
    ::= { gslbInfoRemRealServerEntry 1 }

gslbInfoRemRealServerIpAddr OBJECT-TYPE
    SYNTAX IpAddress
    MAX-ACCESS read-only
    STATUS current
    DESCRIPTION
        "IP address of the remote real server."
    ::= { gslbInfoRemRealServerEntry 2 }

gslbInfoRemRealServerName OBJECT-TYPE
    SYNTAX DisplayString (SIZE(0..255))
    MAX-ACCESS read-only
    STATUS current
    DESCRIPTION
        "The name of the remote real server."
    ::= { gslbInfoRemRealServerEntry 3 }

gslbInfoRemRealServerState OBJECT-TYPE
    SYNTAX INTEGER {
        running(2),
        failed(3),
        disabled(4),
        unsupported(2147483647)
        }
    MAX-ACCESS read-only
    STATUS current
    DESCRIPTION
        "The state of the remote real server."
    ::= { gslbInfoRemRealServerEntry 4 }

-- Global SLB Virtual Server Information

gslbInfoRemEnhRealServerTable OBJECT-TYPE
    SYNTAX SEQUENCE OF GslbInfoRemEnhRealServerEntry
    MAX-ACCESS not-accessible
    STATUS current
    DESCRIPTION
        "The Global SLB virtual server information table.
         Note:This mib is not supported for VX instance of Virtualization."
    ::= { gslbInfo 6 }

gslbInfoRemEnhRealServerEntry OBJECT-TYPE
    SYNTAX GslbInfoRemEnhRealServerEntry
    MAX-ACCESS not-accessible
    STATUS current
    DESCRIPTION
        "A row in the Global SLB remote real server information table."
    INDEX { gslbInfoRemEnhRealServerIdx }
    ::= { gslbInfoRemEnhRealServerTable 1 }

GslbInfoRemEnhRealServerEntry ::=     SEQUENCE {
    gslbInfoRemEnhRealServerIdx            DisplayString,
    gslbInfoRemEnhRealServerIpAddr         IpAddress,
    gslbInfoRemEnhRealServerName           DisplayString,
    gslbInfoRemEnhRealServerState          INTEGER
    }

gslbInfoRemEnhRealServerIdx OBJECT-TYPE
    SYNTAX DisplayString (SIZE(1..255))
    MAX-ACCESS read-only
    STATUS current
    DESCRIPTION
        "The remote real server id that identifies the remote real server."
    ::= { gslbInfoRemEnhRealServerEntry 1 }

gslbInfoRemEnhRealServerIpAddr OBJECT-TYPE
    SYNTAX IpAddress
    MAX-ACCESS read-only
    STATUS current
    DESCRIPTION
        "IP address of the remote real server."
    ::= { gslbInfoRemEnhRealServerEntry 2 }

gslbInfoRemEnhRealServerName OBJECT-TYPE
    SYNTAX DisplayString (SIZE(0..255))
    MAX-ACCESS read-only
    STATUS current
    DESCRIPTION
        "The name of the remote real server."
    ::= { gslbInfoRemEnhRealServerEntry 3 }

gslbInfoRemEnhRealServerState OBJECT-TYPE
    SYNTAX INTEGER {
        running(2),
        failed(3),
        disabled(4),
        unsupported(2147483647)
        }
    MAX-ACCESS read-only
    STATUS current
    DESCRIPTION
        "The state of the remote real server."
    ::= { gslbInfoRemEnhRealServerEntry 4 }

gslbInfoVirtServerTable OBJECT-TYPE
    SYNTAX SEQUENCE OF GslbInfoVirtServerEntry
    MAX-ACCESS not-accessible
    STATUS current
    DESCRIPTION
        "The Global SLB virtual server information table.
         Note:This mib is not supported for VX instance of Virtualization."
    ::= { gslbInfo 2 }

gslbInfoVirtServerEntry OBJECT-TYPE
    SYNTAX GslbInfoVirtServerEntry
    MAX-ACCESS not-accessible
    STATUS current
    DESCRIPTION
        "A row in the Global SLB virtual server information table."
    INDEX { gslbInfoVirtServerIdx, gslbInfoVirtServerServiceIdx,
            gslbInfoVirtServerRserverIdx }
    ::= { gslbInfoVirtServerTable 1 }

GslbInfoVirtServerEntry ::=     SEQUENCE {
    gslbInfoVirtServerIdx            Integer32,
    gslbInfoVirtServerServiceIdx     Integer32,
    gslbInfoVirtServerRserverIdx     Integer32,
    gslbInfoVirtServerDname          DisplayString,
    gslbInfoVirtServerVirtPort       Integer32,
    gslbInfoVirtServerIpAddress      IpAddress,
    gslbInfoVirtServerResponse       Integer32,
    gslbInfoVirtServerSessAvail      Integer32,
    gslbInfoVirtServerSessCur        Integer32,
    gslbInfoVirtServerSessMax        Integer32,
    gslbInfoVirtServerSessUtil       INTEGER,
    gslbInfoVirtServerCpuUtil        INTEGER,
    gslbInfoVirtServerRemSite        Integer32,
    gslbInfoVirtServerWeight         INTEGER,
    gslbInfoVirtServerAvail          INTEGER,
    gslbInfoVirtServerRegion         INTEGER
    }

gslbInfoVirtServerIdx OBJECT-TYPE
    SYNTAX Integer32
    MAX-ACCESS read-only
    STATUS current
    DESCRIPTION
        "The virtual server number that identifies the virtual server."
    ::= { gslbInfoVirtServerEntry 1 }

gslbInfoVirtServerServiceIdx OBJECT-TYPE
    SYNTAX Integer32
    MAX-ACCESS read-only
    STATUS current
    DESCRIPTION
        "The virtual server service number that identifies the virtual service."
    ::= { gslbInfoVirtServerEntry 2 }

gslbInfoVirtServerRserverIdx OBJECT-TYPE
    SYNTAX Integer32
    MAX-ACCESS read-only
    STATUS current
    DESCRIPTION
        "The real server number that identifies a remote real server.
         An index of 0 indicates virtual server."
    ::= { gslbInfoVirtServerEntry 3 }

gslbInfoVirtServerDname OBJECT-TYPE
    SYNTAX DisplayString (SIZE(0..64))
    MAX-ACCESS read-only
    STATUS current
    DESCRIPTION
        "The domain name of the virtual server and remote real server."
    ::= { gslbInfoVirtServerEntry 4 }

gslbInfoVirtServerVirtPort OBJECT-TYPE
    SYNTAX Integer32
    MAX-ACCESS read-only
    STATUS current
    DESCRIPTION
        "The service port of the virtual server and remote real server."
    ::= { gslbInfoVirtServerEntry 5 }

gslbInfoVirtServerIpAddress OBJECT-TYPE
    SYNTAX IpAddress
    MAX-ACCESS read-only
    STATUS current
    DESCRIPTION
        "The IP address of the virtual server or remote real server."
    ::= { gslbInfoVirtServerEntry 6 }

gslbInfoVirtServerResponse OBJECT-TYPE
    SYNTAX Integer32
    MAX-ACCESS read-only
    STATUS current
    DESCRIPTION
        "The health check response time of the virtual server or remote real server."
    ::= { gslbInfoVirtServerEntry 7 }

gslbInfoVirtServerSessAvail OBJECT-TYPE
    SYNTAX Integer32
    MAX-ACCESS read-only
    STATUS current
    DESCRIPTION
        "The available sessions of the virtual server or remote real server."
    ::= { gslbInfoVirtServerEntry 8 }

gslbInfoVirtServerSessCur OBJECT-TYPE
    SYNTAX Integer32
    MAX-ACCESS read-only
    STATUS current
    DESCRIPTION
        "The current sessions of the virtual server or remote real server."
    ::= { gslbInfoVirtServerEntry 9 }

gslbInfoVirtServerSessMax OBJECT-TYPE
    SYNTAX Integer32
    MAX-ACCESS read-only
    STATUS current
    DESCRIPTION
        "The maximum sessions supported by the virtual server or remote real server."
    ::= { gslbInfoVirtServerEntry 10 }

gslbInfoVirtServerSessUtil OBJECT-TYPE
    SYNTAX INTEGER(1..100)
    MAX-ACCESS read-only
    STATUS current
    DESCRIPTION
        "The sessions utilization (current/max) of the virtual server or remote real server."
    ::= { gslbInfoVirtServerEntry 11 }

gslbInfoVirtServerCpuUtil OBJECT-TYPE
    SYNTAX INTEGER(1..100)
    MAX-ACCESS read-only
    STATUS current
    DESCRIPTION
        "The CPU utilization of the virtual server or remote real server."
    ::= { gslbInfoVirtServerEntry 12 }

gslbInfoVirtServerRemSite OBJECT-TYPE
    SYNTAX Integer32
    MAX-ACCESS read-only
    STATUS current
    DESCRIPTION
        "The remote site of the remote real server. For virtual server, the remote site is 0."
    ::= { gslbInfoVirtServerEntry 13 }

gslbInfoVirtServerWeight OBJECT-TYPE
    SYNTAX INTEGER(1..48)
    MAX-ACCESS read-only
    STATUS current
    DESCRIPTION
        "The weight of the virtual server or remote real server."
    ::= { gslbInfoVirtServerEntry 14 }

gslbInfoVirtServerAvail OBJECT-TYPE
    SYNTAX INTEGER(1..48)
    MAX-ACCESS read-only
    STATUS current
    DESCRIPTION
        "The availability of the virtual server or remote real server."
    ::= { gslbInfoVirtServerEntry 15 }

gslbInfoVirtServerRegion OBJECT-TYPE
    SYNTAX INTEGER {
        unknown(0),
        northamerica(1),
        southamerica(2),
        europe(3),
        caribbean(4),
        pacificrim(5),
        subsahara(6),
        japan(7),
        caribbeansubsahara(8),
	africa(9),
        unsupported(2147483647)
        }
    MAX-ACCESS read-only
    STATUS current
    DESCRIPTION
        "The region of the virtual server or remote real server."
    ::= { gslbInfoVirtServerEntry 16 }

-- Global SLB Remote Site Information

gslbInfoRemSiteTable OBJECT-TYPE
    SYNTAX SEQUENCE OF GslbInfoRemSiteEntry
    MAX-ACCESS not-accessible
    STATUS current
    DESCRIPTION
        "The Global SLB remote site information table.
         Note:This mib is not supported for VX instance of Virtualization."
    ::= { gslbInfo 3 }

gslbInfoRemSiteEntry OBJECT-TYPE
    SYNTAX GslbInfoRemSiteEntry
    MAX-ACCESS not-accessible
    STATUS current
    DESCRIPTION
        "A row in the Global SLB remote site information table."
    INDEX { gslbInfoRemSiteIdx }
    ::= { gslbInfoRemSiteTable 1 }

GslbInfoRemSiteEntry ::=     SEQUENCE {
    gslbInfoRemSiteIdx            Integer32,
    gslbInfoRemSitePrimaryIp      IpAddress,
    gslbInfoRemSiteSecondaryIp    IpAddress,
    gslbInfoRemSiteName           DisplayString,
    gslbInfoRemSiteState          INTEGER
    }

gslbInfoRemSiteIdx OBJECT-TYPE
    SYNTAX Integer32
    MAX-ACCESS read-only
    STATUS current
    DESCRIPTION
        "The remote site number that identifies the remote site."
    ::= { gslbInfoRemSiteEntry 1 }

gslbInfoRemSitePrimaryIp OBJECT-TYPE
    SYNTAX IpAddress
    MAX-ACCESS read-only
    STATUS current
    DESCRIPTION
        "The primary IP address of the remote site."
    ::= { gslbInfoRemSiteEntry 2 }

gslbInfoRemSiteSecondaryIp OBJECT-TYPE
    SYNTAX IpAddress
    MAX-ACCESS read-only
    STATUS current
    DESCRIPTION
        "The secondary IP address of the remote site."
    ::= { gslbInfoRemSiteEntry 3 }

gslbInfoRemSiteName OBJECT-TYPE
    SYNTAX DisplayString (SIZE(0..31))
    MAX-ACCESS read-only
    STATUS current
    DESCRIPTION
        "The name of the remote site."
    ::= { gslbInfoRemSiteEntry 4 }

gslbInfoRemSiteState OBJECT-TYPE
    SYNTAX INTEGER {
        running(2),
        failed(3),
        disabled(4),
        unsupported(2147483647)
        }
    MAX-ACCESS read-only
    STATUS current
    DESCRIPTION
        "The state of the remote site."
    ::= { gslbInfoRemSiteEntry 5 }

gslbInfoDnsSec        OBJECT IDENTIFIER ::= { gslbInfo 4 }

gslbInfoDnsSecKey     OBJECT IDENTIFIER ::= { gslbInfoDnsSec 2 }

gslbInfoDnsSecKeyTable OBJECT-TYPE
    SYNTAX  SEQUENCE OF GslbInfoDnsSecKeyEntry
    MAX-ACCESS  not-accessible
    STATUS  current
    DESCRIPTION
        "Note:This mib is not supported for VX instance of Virtualization."
    ::= { gslbInfoDnsSecKey 1 }

gslbInfoDnsSecKeyEntry OBJECT-TYPE
    SYNTAX  GslbInfoDnsSecKeyEntry
    MAX-ACCESS  not-accessible
    STATUS  current
    DESCRIPTION
        "."
    INDEX   { gslbInfoDnsSecKeyID }
    ::= { gslbInfoDnsSecKeyTable 1 }

GslbInfoDnsSecKeyEntry ::= SEQUENCE {
    gslbInfoDnsSecKeyID                DisplayString,
    gslbInfoDnsSecKeyStatus            INTEGER
    }

gslbInfoDnsSecKeyID OBJECT-TYPE
    SYNTAX   DisplayString (SIZE(0..32))
    MAX-ACCESS  read-only
    STATUS  current
    DESCRIPTION
        "DNS Sec Table Key."
    ::= { gslbInfoDnsSecKeyEntry  1 }

gslbInfoDnsSecKeyStatus OBJECT-TYPE
    SYNTAX INTEGER {
    initRollProess(1), 
    newKeyCreated(2),
	newZskKeyDeployed(3),
	oldKeyRemoval(4),
	retrDsFromParent(5),
	newKskKeyDeployed(6),
	waitDsChangeOnParent(7),
	rolloverNotRunning(8),
	invalid(9),
	expired(10),
        unsupported(2147483647)
        }
    MAX-ACCESS  read-only
    STATUS  current
    DESCRIPTION
        "Key status."
    ::= { gslbInfoDnsSecKeyEntry 4 }

-- Global SLB Virtual Server Information

gslbInfoEnhVirtServerTable OBJECT-TYPE
    SYNTAX SEQUENCE OF GslbInfoEnhVirtServerEntry
    MAX-ACCESS not-accessible
    STATUS current
    DESCRIPTION
        "The Global SLB virtual server information table.
         Note:This mib is not supported for VX instance of Virtualization."
    ::= { gslbInfo 5 }

gslbInfoEnhVirtServerEntry OBJECT-TYPE
    SYNTAX GslbInfoEnhVirtServerEntry
    MAX-ACCESS not-accessible
    STATUS current
    DESCRIPTION
        "A row in the Global SLB virtual server information table."
    INDEX { gslbInfoEnhVirtServerIdx, gslbInfoEnhVirtServerServiceIdx,
            gslbInfoEnhVirtServerRserverIdx }
    ::= { gslbInfoEnhVirtServerTable 1 }

GslbInfoEnhVirtServerEntry ::=     SEQUENCE {
    gslbInfoEnhVirtServerIdx            DisplayString,
    gslbInfoEnhVirtServerServiceIdx     Integer32,
    gslbInfoEnhVirtServerRserverIdx     DisplayString,
    gslbInfoEnhVirtServerDname          DisplayString,
    gslbInfoEnhVirtServerVirtPort       Integer32,
    gslbInfoEnhVirtServerIpAddress      IpAddress,
    gslbInfoEnhVirtServerResponse       Integer32,
    gslbInfoEnhVirtServerSessAvail      Integer32,
    gslbInfoEnhVirtServerSessCur        Integer32,
    gslbInfoEnhVirtServerSessMax        Integer32,
    gslbInfoEnhVirtServerSessUtil       INTEGER,
    gslbInfoEnhVirtServerCpuUtil        INTEGER,
    gslbInfoEnhVirtServerRemSite        Integer32,
    gslbInfoEnhVirtServerWeight         INTEGER,
    gslbInfoEnhVirtServerAvail          INTEGER,
    gslbInfoEnhVirtServerRegion         INTEGER
    }

gslbInfoEnhVirtServerIdx OBJECT-TYPE
    SYNTAX DisplayString (SIZE(1..255))
    MAX-ACCESS read-only
    STATUS current
    DESCRIPTION
        "The virtual server number that identifies the virtual server."
    ::= { gslbInfoEnhVirtServerEntry 1 }

gslbInfoEnhVirtServerServiceIdx OBJECT-TYPE
    SYNTAX Integer32
    MAX-ACCESS read-only
    STATUS current
    DESCRIPTION
        "The virtual server service number that identifies the virtual service."
    ::= { gslbInfoEnhVirtServerEntry 2 }

gslbInfoEnhVirtServerRserverIdx OBJECT-TYPE
    SYNTAX DisplayString (SIZE(1..255))
    MAX-ACCESS read-only
    STATUS current
    DESCRIPTION
        "The real server number that identifies a remote real server.
         An index of 0 indicates virtual server."
    ::= { gslbInfoEnhVirtServerEntry 3 }

gslbInfoEnhVirtServerDname OBJECT-TYPE
    SYNTAX DisplayString (SIZE(0..64))
    MAX-ACCESS read-only
    STATUS current
    DESCRIPTION
        "The domain name of the virtual server and remote real server."
    ::= { gslbInfoEnhVirtServerEntry 4 }

gslbInfoEnhVirtServerVirtPort OBJECT-TYPE
    SYNTAX Integer32
    MAX-ACCESS read-only
    STATUS current
    DESCRIPTION
        "The service port of the virtual server and remote real server."
    ::= { gslbInfoEnhVirtServerEntry 5 }

gslbInfoEnhVirtServerIpAddress OBJECT-TYPE
    SYNTAX IpAddress
    MAX-ACCESS read-only
    STATUS current
    DESCRIPTION
        "The IP address of the virtual server or remote real server."
    ::= { gslbInfoEnhVirtServerEntry 6 }

gslbInfoEnhVirtServerResponse OBJECT-TYPE
    SYNTAX Integer32
    MAX-ACCESS read-only
    STATUS current
    DESCRIPTION
        "The health check response time of the virtual server or remote real server."
    ::= { gslbInfoEnhVirtServerEntry 7 }

gslbInfoEnhVirtServerSessAvail OBJECT-TYPE
    SYNTAX Integer32
    MAX-ACCESS read-only
    STATUS current
    DESCRIPTION
        "The available sessions of the virtual server or remote real server."
    ::= { gslbInfoEnhVirtServerEntry 8 }

gslbInfoEnhVirtServerSessCur OBJECT-TYPE
    SYNTAX Integer32
    MAX-ACCESS read-only
    STATUS current
    DESCRIPTION
        "The current sessions of the virtual server or remote real server."
    ::= { gslbInfoEnhVirtServerEntry 9 }

gslbInfoEnhVirtServerSessMax OBJECT-TYPE
    SYNTAX Integer32
    MAX-ACCESS read-only
    STATUS current
    DESCRIPTION
        "The maximum sessions supported by the virtual server or remote real server."
    ::= { gslbInfoEnhVirtServerEntry 10 }

gslbInfoEnhVirtServerSessUtil OBJECT-TYPE
    SYNTAX INTEGER(1..100)
    MAX-ACCESS read-only
    STATUS current
    DESCRIPTION
        "The sessions utilization (current/max) of the virtual server or remote real server."
    ::= { gslbInfoEnhVirtServerEntry 11 }

gslbInfoEnhVirtServerCpuUtil OBJECT-TYPE
    SYNTAX INTEGER(1..100)
    MAX-ACCESS read-only
    STATUS current
    DESCRIPTION
        "The CPU utilization of the virtual server or remote real server."
    ::= { gslbInfoEnhVirtServerEntry 12 }

gslbInfoEnhVirtServerRemSite OBJECT-TYPE
    SYNTAX Integer32
    MAX-ACCESS read-only
    STATUS current
    DESCRIPTION
        "The remote site of the remote real server. For virtual server, the remote site is 0."
    ::= { gslbInfoEnhVirtServerEntry 13 }

gslbInfoEnhVirtServerWeight OBJECT-TYPE
    SYNTAX INTEGER(1..48)
    MAX-ACCESS read-only
    STATUS current
    DESCRIPTION
        "The weight of the virtual server or remote real server."
    ::= { gslbInfoEnhVirtServerEntry 14 }

gslbInfoEnhVirtServerAvail OBJECT-TYPE
    SYNTAX INTEGER(1..48)
    MAX-ACCESS read-only
    STATUS current
    DESCRIPTION
        "The availability of the virtual server or remote real server."
    ::= { gslbInfoEnhVirtServerEntry 15 }

gslbInfoEnhVirtServerRegion OBJECT-TYPE
    SYNTAX INTEGER {
        unknown(0),
        northamerica(1),
        southamerica(2),
        europe(3),
        caribbean(4),
        pacificrim(5),
        subsahara(6),
        japan(7),
        caribbeansubsahara(8),
        africa(9),
        unsupported(2147483647)
        }
    MAX-ACCESS read-only
    STATUS current
    DESCRIPTION
        "The region of the virtual server or remote real server."
    ::= { gslbInfoEnhVirtServerEntry 16 }


-- wlm Information

wlmInfo         OBJECT IDENTIFIER ::= { layer4Info 7 }

slbWlmInfoTable OBJECT-TYPE
    SYNTAX SEQUENCE OF SlbWlmInfoEntry
    MAX-ACCESS not-accessible
    STATUS current
    DESCRIPTION
        "The table of workload manager run-time information.
         Note:This mib is not supported for VX instance of Virtualization."
    ::= { wlmInfo 1 }

slbWlmInfoEntry OBJECT-TYPE
    SYNTAX SlbWlmInfoEntry
    MAX-ACCESS not-accessible
    STATUS current
    DESCRIPTION
        "A row in the workload manager information table."
    INDEX { slbWlmInfoIndex }
    ::= { slbWlmInfoTable 1 }

SlbWlmInfoEntry ::= SEQUENCE {
    slbWlmInfoIndex           Integer32,
    slbWlmInfoIpAddr          IpAddress,
    slbWlmInfoPort            INTEGER,
    slbWlmInfoState           INTEGER 
     }

slbWlmInfoIndex OBJECT-TYPE
    SYNTAX  Integer32
    MAX-ACCESS  read-only
    STATUS  current
    DESCRIPTION
        "The workload manager index."
    ::= { slbWlmInfoEntry 1 }

slbWlmInfoIpAddr OBJECT-TYPE
    SYNTAX  IpAddress
    MAX-ACCESS  read-only
    STATUS  current
    DESCRIPTION
        "IP address of the workload manager."
    ::= { slbWlmInfoEntry 2 }

slbWlmInfoPort OBJECT-TYPE
    SYNTAX  INTEGER (0..65534)
    MAX-ACCESS  read-only
    STATUS  current
    DESCRIPTION
        "The port number of the workload manager."
    ::= { slbWlmInfoEntry 3 }

slbWlmInfoState OBJECT-TYPE
    SYNTAX  INTEGER  { connected(1), notconnected(2)}
    MAX-ACCESS  read-only
    STATUS  current
    DESCRIPTION
        "The state of the workload manager."
    ::= { slbWlmInfoEntry 4 }


slbPortInfo         OBJECT IDENTIFIER ::= { layer4Info 8 }

slbPortInfoTable OBJECT-TYPE
    SYNTAX SEQUENCE OF SlbPortInfoEntry
    MAX-ACCESS not-accessible
    STATUS current
    DESCRIPTION
        "The table of port information.
         Note:This mib is not supported for VX instance of Virtualization."
    ::= { slbPortInfo 1 }

slbPortInfoEntry OBJECT-TYPE
    SYNTAX SlbPortInfoEntry
    MAX-ACCESS not-accessible
    STATUS current
    DESCRIPTION
        "A row in the port information table."
    INDEX { slbPortInfoIndex }
    ::= { slbPortInfoTable 1 }

SlbPortInfoEntry ::= SEQUENCE {
    slbPortInfoIndex           Integer32,
    slbPortClientState         INTEGER,
    slbPortSerState            INTEGER,
    slbPortFltState            INTEGER,
    slbPortRTSState            INTEGER,
    slbPortHotStandbyState     INTEGER,
    slbPortInterSWState        INTEGER,
    slbPortProxyState          INTEGER,
    slbPortIdSlbState          INTEGER,
    slbPortSymantecState       INTEGER,
    slbPortFitersAdded         OCTET STRING 
    }

slbPortInfoIndex OBJECT-TYPE
    SYNTAX Integer32
    MAX-ACCESS read-only
    STATUS current
    DESCRIPTION
        "Index of slb port."
    ::= { slbPortInfoEntry 1 }

slbPortClientState OBJECT-TYPE
    SYNTAX INTEGER {
        enabled(1),
        disabled(2),
        unsupported(2147483647)
        }
    MAX-ACCESS read-only
    STATUS current
    DESCRIPTION
        "Client state on the slb port."
    ::= { slbPortInfoEntry 2 }

slbPortSerState OBJECT-TYPE
    SYNTAX INTEGER {
        enabled(1),
        disabled(2),
        unsupported(2147483647)
        }
    MAX-ACCESS read-only
    STATUS current
    DESCRIPTION
        "Server state on the slb port."
    ::= { slbPortInfoEntry 3 }

slbPortFltState OBJECT-TYPE
    SYNTAX  INTEGER {
        enabled(1),
        disabled(2),
        unsupported(2147483647)
        } 
    MAX-ACCESS read-only
    STATUS current
    DESCRIPTION
        " Filter state on the slb port ."
    ::= { slbPortInfoEntry 4 }

slbPortRTSState OBJECT-TYPE
    SYNTAX INTEGER {
        enabled(1),
        disabled(2),
        unsupported(2147483647)
        }
    MAX-ACCESS read-only
    STATUS current
    DESCRIPTION
        "RTS processing state on the slb port."
    ::= { slbPortInfoEntry 5 }

slbPortHotStandbyState  OBJECT-TYPE
    SYNTAX INTEGER {
        enabled(1),
        disabled(2),
        unsupported(2147483647)
        }
    MAX-ACCESS read-only
    STATUS current
    DESCRIPTION
        "Hot standby state on the slb port."
    ::= { slbPortInfoEntry 6 }

slbPortInterSWState OBJECT-TYPE
    SYNTAX INTEGER {
        enabled(1),
        disabled(2),
        unsupported(2147483647)
        }
    MAX-ACCESS read-only
    STATUS current
    DESCRIPTION
        "Inter-switch processing state on the slb port."
    ::= { slbPortInfoEntry 7 }            

slbPortProxyState  OBJECT-TYPE
    SYNTAX INTEGER {
        enabled(1),
        disabled(2),
        unsupported(2147483647)
        }
    MAX-ACCESS read-only
    STATUS current
    DESCRIPTION
        "Proxy state on the slb port."
    ::= { slbPortInfoEntry 8 }

slbPortIdSlbState  OBJECT-TYPE
    SYNTAX INTEGER {
        enabled(1),
        disabled(2),
        unsupported(2147483647)
        }
    MAX-ACCESS read-only
    STATUS current
    DESCRIPTION
        "Intrusion detection server load balancing state on the slb port."
    ::= { slbPortInfoEntry 9 }

slbPortSymantecState  OBJECT-TYPE
    SYNTAX INTEGER {
        enabled(1),
        disabled(2),
        unsupported(2147483647)
        }
    MAX-ACCESS read-only
    STATUS current
    DESCRIPTION
        " Symantec Processing state on the slb port."
    ::= { slbPortInfoEntry 10 }

slbPortFitersAdded   OBJECT-TYPE
    SYNTAX  OCTET STRING (SIZE(0..256))
    MAX-ACCESS read-only
    STATUS current
    DESCRIPTION
        "The filtering rules applied to the port.  The filtering rules are
         presented in bitmap format.

         in receiving order:

             OCTET 1  OCTET 2  .....
             xxxxxxxx xxxxxxxx .....
             ||    || |_ filter 9
             ||    ||
             ||    ||___ filter 8
             ||    |____ filter 7
             ||      .    .   .
             ||_________ filter 2
             |__________ filter 1 

         where x : 1 - The represented filter rule applied to the port
                   0 - The represented filter rule not applied to the port."
    ::= { slbPortInfoEntry 11 }


synAttackInfo         OBJECT IDENTIFIER ::= { layer4Info 9 }

synAtkState OBJECT-TYPE
    SYNTAX INTEGER { on(1), off(2) }
    MAX-ACCESS read-only
    STATUS current
    DESCRIPTION
        "State of the Syn Attack, represents whether it is running or not.
         Note:This mib is not supported for VX instance of Virtualization."
    ::= { synAttackInfo 1}

synAtkInterval OBJECT-TYPE
    SYNTAX Integer32
    MAX-ACCESS read-only
    STATUS current
    DESCRIPTION
        "Specifies interval period of syn attack inspection in seconds,
         it returns 0 if synAtk is OFF.
         Note:This mib is not supported for VX instance of Virtualization."
    ::= { synAttackInfo 2}

synAtkThreshhold OBJECT-TYPE
    SYNTAX Integer32
    MAX-ACCESS read-only
    STATUS current
    DESCRIPTION
        "Specifies threshold of syn attack alram, it returns 0
         if synAtk is OFF.
         Note:This mib is not supported for VX instance of Virtualization."
    ::= { synAttackInfo 3}

synAtkWarningFired OBJECT-TYPE
    SYNTAX Integer32
    MAX-ACCESS read-only
    STATUS current
    DESCRIPTION
        "Specifies number of times syn attack warnings fired.
         Note:This mib is not supported for VX instance of Virtualization."
    ::= { synAttackInfo 4}

synAtkResponseInterval OBJECT-TYPE
    SYNTAX Integer32
    MAX-ACCESS read-only
    STATUS current
    DESCRIPTION
        "Specifies interval period of syn cookie generation in milliseconds,
         it returns 0 if synAtk is OFF.
         Note:This mib is not supported for VX instance of Virtualization."
    ::= { synAttackInfo 5}

synAtkOnOff OBJECT-TYPE
    SYNTAX INTEGER { on(1), off(2) }
    MAX-ACCESS read-only
    STATUS current
    DESCRIPTION
        "Globaly set SYN Protection ON/FF.
         Note:This mib is not supported for VX instance of Virtualization."
    ::= { synAttackInfo 6}


slbFreeVirtualServerIndexInfo OBJECT-TYPE
    SYNTAX  INTEGER
    MAX-ACCESS  read-only
    STATUS  current
    DESCRIPTION
        "Retrieve the next virtual server index.
         Note:This mib is not supported for VX instance of Virtualization."
    ::= { layer4Info 10 }

slbFreeRealGroupIndexInfo OBJECT-TYPE
    SYNTAX  INTEGER
    MAX-ACCESS  read-only
    STATUS  current
    DESCRIPTION
        "Retrieve the next server group index.
         Note:This mib is not supported for VX instance of Virtualization."
    ::= { layer4Info 11 }

slbFreeRealServerIndexInfo OBJECT-TYPE
    SYNTAX  INTEGER
    MAX-ACCESS  read-only
    STATUS  current
    DESCRIPTION
        "Retrieve the next real server index.
         Note:This mib is not supported for VX instance of Virtualization."
    ::= { layer4Info 12 }

	-- Real Server Information Enhanced Table

slbEnhRealServerInfoTable OBJECT-TYPE
    SYNTAX  SEQUENCE OF SlbEnhRealServerInfoEntry
    MAX-ACCESS  not-accessible
    STATUS  current
    DESCRIPTION
        "The table of real server run-time information.
         Note:This mib is not supported for VX instance of Virtualization."
    ::= { layer4Info 13 }

slbEnhRealServerInfoEntry OBJECT-TYPE
    SYNTAX  SlbEnhRealServerInfoEntry
    MAX-ACCESS  not-accessible
    STATUS  current
    DESCRIPTION
        "A row in the real server information table."
    INDEX   { slbEnhRealServerInfoIndex }
    ::= { slbEnhRealServerInfoTable 1 }

SlbEnhRealServerInfoEntry ::= SEQUENCE {
    slbEnhRealServerInfoIndex           DisplayString,
    slbEnhRealServerInfoIpAddr          IpAddress,
    slbEnhRealServerMacAddr             PhysAddress,
    slbEnhRealServerInfoSwitchPort      Integer32,
    slbEnhRealServerInfoHealthLayer     INTEGER,
    slbEnhRealServerInfoOverflow        INTEGER,
    slbEnhRealServerInfoState           INTEGER,
    slbEnhRealServerInfoVlan            Integer32,
    slbEnhRealServerInfoHealth          DisplayString,
    slbEnhRealServerInfoUpTime          DisplayString,
    slbEnhRealServerInfoDownTime        DisplayString,
    slbEnhRealServerInfoLastFailureTime DisplayString
}

slbEnhRealServerInfoIndex OBJECT-TYPE
    SYNTAX  DisplayString (SIZE(1..255))
    MAX-ACCESS  read-only
    STATUS  current
    DESCRIPTION
        "The real server index" 
::= { slbEnhRealServerInfoEntry 1 }

slbEnhRealServerInfoIpAddr OBJECT-TYPE
    SYNTAX  IpAddress
    MAX-ACCESS  read-only
    STATUS  current
    DESCRIPTION
        "IP address of the real server." 
    ::= { slbEnhRealServerInfoEntry 2 }

slbEnhRealServerMacAddr OBJECT-TYPE
    SYNTAX  PhysAddress
    MAX-ACCESS  read-only
    STATUS  current
    DESCRIPTION
        "The MAC address of the real server." 
    ::= { slbEnhRealServerInfoEntry 3 }

slbEnhRealServerInfoSwitchPort OBJECT-TYPE
    SYNTAX  Integer32
    MAX-ACCESS  read-only
    STATUS  current
    DESCRIPTION
        "The switch port that the real server is connected to." 
    ::= { slbEnhRealServerInfoEntry 4 }

slbEnhRealServerInfoHealthLayer  OBJECT-TYPE
    SYNTAX  INTEGER { 
        layer1(1), 
        layer3(3),
        layer4(4),
        unsupported(2147483647)
    } 
    MAX-ACCESS  read-only
    STATUS  current
    DESCRIPTION
        "The OSI layer at which the real server functionality is verified."
    ::= { slbEnhRealServerInfoEntry 5 }

slbEnhRealServerInfoOverflow OBJECT-TYPE
    SYNTAX  INTEGER {
        overflow(1),
        no-overflow(2),
        unsupported(2147483647)
    } 
    MAX-ACCESS  read-only
    STATUS  current
    DESCRIPTION
        "The overflow state of the real server." 
    ::= { slbEnhRealServerInfoEntry 6 }

slbEnhRealServerInfoState OBJECT-TYPE
    SYNTAX  INTEGER {
        running(2),
        failed(3),
        disabled(4),
        unsupported(2147483647)
    } 
    MAX-ACCESS  read-only
    STATUS  current
    DESCRIPTION
        "The state of the real server."
    ::= { slbEnhRealServerInfoEntry 7 }

slbEnhRealServerInfoVlan OBJECT-TYPE
    SYNTAX  Integer32
    MAX-ACCESS  read-only
    STATUS  current
    DESCRIPTION
        "The VLAN that the real server belongs to." 
    ::= { slbEnhRealServerInfoEntry 8 }

slbEnhRealServerInfoHealth OBJECT-TYPE
    SYNTAX DisplayString (SIZE(0..128))
    MAX-ACCESS read-only
    STATUS current
    DESCRIPTION
        "The health check id configured for the real server."
    ::= { slbEnhRealServerInfoEntry 9 }

slbEnhRealServerInfoUpTime OBJECT-TYPE
    SYNTAX  DisplayString (SIZE(0..127))
    MAX-ACCESS  read-only
    STATUS  current
    DESCRIPTION
        "The total up time of the real server."
    ::= { slbEnhRealServerInfoEntry 10 }

slbEnhRealServerInfoDownTime OBJECT-TYPE
    SYNTAX  DisplayString (SIZE(0..127))
    MAX-ACCESS  read-only
    STATUS  current
    DESCRIPTION
        "The total down time of the real server."
    ::= { slbEnhRealServerInfoEntry 11 }

slbEnhRealServerInfoLastFailureTime OBJECT-TYPE
    SYNTAX  DisplayString (SIZE(0..127))
    MAX-ACCESS  read-only
    STATUS  current
    DESCRIPTION
        "The time-stamp when the last failure of the real server occured."
    ::= { slbEnhRealServerInfoEntry 12 }

-- Real Server Rport Table
slbEnhRealServerRportInfoTable OBJECT-TYPE
    SYNTAX  SEQUENCE OF SlbEnhRealServerRportInfoEntry
    MAX-ACCESS  not-accessible
    STATUS  current
    DESCRIPTION
        "The table of real server rport run-time information.
         Note:This mib is not supported for VX instance of Virtualization."
    ::= { layer4Info 14 }

slbEnhRealServerRportInfoEntry OBJECT-TYPE
    SYNTAX  SlbEnhRealServerRportInfoEntry
    MAX-ACCESS  not-accessible
    STATUS  current
    DESCRIPTION
        "A row in the real server rport information table."
    INDEX   { slbEnhRealServerRportRealIndex, slbEnhRealServerRportServIndex  }
    ::= { slbEnhRealServerRportInfoTable 1 }

SlbEnhRealServerRportInfoEntry ::= SEQUENCE {
    slbEnhRealServerRportRealIndex           DisplayString,
    slbEnhRealServerRportServIndex           Integer32,
    slbEnhRealServerRportInfoRport           Integer32,
    slbEnhRealServerRportInfoState           INTEGER,
    slbEnhRealServerRportInfoGroup           DisplayString,
    slbEnhRealServerRportInfoRespTime        Integer32,
    slbEnhRealServerRportInfoFailReason      DisplayString
}

slbEnhRealServerRportRealIndex OBJECT-TYPE
    SYNTAX  DisplayString (SIZE(1..255))
    MAX-ACCESS  read-only
    STATUS  current
    DESCRIPTION
        "The real server index" 
    ::= { slbEnhRealServerRportInfoEntry 1 }

slbEnhRealServerRportServIndex OBJECT-TYPE
    SYNTAX  Integer32
    MAX-ACCESS  read-only
    STATUS  current
    DESCRIPTION
        "The real server service index" 
    ::= { slbEnhRealServerRportInfoEntry 2 }

slbEnhRealServerRportInfoRport OBJECT-TYPE
    SYNTAX  Integer32
    MAX-ACCESS  read-only
    STATUS  current
    DESCRIPTION
        "The real server real port number" 
    ::= { slbEnhRealServerRportInfoEntry 3 }

slbEnhRealServerRportInfoState OBJECT-TYPE
    SYNTAX  INTEGER {
        up(1),
        down(2)
       ,slowstart(3),
        unsupported(2147483647)
    } 
    MAX-ACCESS  read-only
    STATUS  current
    DESCRIPTION
        "The state of the real server port."
::= { slbEnhRealServerRportInfoEntry 4 }

slbEnhRealServerRportInfoGroup OBJECT-TYPE
    SYNTAX  DisplayString (SIZE(1..255))
    MAX-ACCESS  read-only
    STATUS  current 
    DESCRIPTION
        "The real server group number."
::= { slbEnhRealServerRportInfoEntry 5 }

slbEnhRealServerRportInfoRespTime OBJECT-TYPE
    SYNTAX  Integer32
    MAX-ACCESS  read-only
    STATUS  current
    DESCRIPTION
        "The response time of the real server health check."
    ::= { slbEnhRealServerRportInfoEntry 6 }

slbEnhRealServerRportInfoFailReason OBJECT-TYPE
    SYNTAX DisplayString (SIZE(0..128))
    MAX-ACCESS read-only
    STATUS current
    DESCRIPTION
        "The reason for health check fail."
    ::= { slbEnhRealServerRportInfoEntry 7 }

-- Operation Commands

slbOperRealServerTable OBJECT-TYPE
    SYNTAX  SEQUENCE OF SlbOperRealServerEntry
    MAX-ACCESS  not-accessible
    STATUS  current
    DESCRIPTION
        "The table of real servers.
         Note:This mib is not supported for VX instance of Virtualization."
    ::= { layer4Oper 1 }

slbOperRealServerEntry OBJECT-TYPE
    SYNTAX  SlbOperRealServerEntry
    MAX-ACCESS  not-accessible
    STATUS  current
    DESCRIPTION
        "A row in the slbOperRealServerTable "
    INDEX   { slbOperRealServerIndex }
    ::= { slbOperRealServerTable 1 }

SlbOperRealServerEntry ::= SEQUENCE {
    slbOperRealServerIndex              Integer32,
    slbOperRealServerStatus             INTEGER
    }

slbOperRealServerIndex OBJECT-TYPE
    SYNTAX  Integer32
    MAX-ACCESS  read-only
    STATUS  current
    DESCRIPTION
        "The index for the  real server." 
    ::= { slbOperRealServerEntry 1 }

slbOperRealServerStatus OBJECT-TYPE
    SYNTAX  INTEGER {
	enable(1),
	disable(2),
	cookiepersistent(3),
	fastage(4),
	cookiepersistentfastage(5),
        unsupported(2147483647)
	}
    MAX-ACCESS  read-write
    STATUS  current
    DESCRIPTION
        "This an action object which is used to temporarily enable/disable a
         real server. The real server will be returned to its configured
         operational mode when the switch is reset. Setting the value to 
         'cookiepersistant' allows cookie persistent HTTP 1.0 sessions
         when the real server is offline.'fastage' option is for removing the
         existing sessions. And 'cookiepersistentfastage' allows cookie
         persistent sessions and remove the existing sessions when real server is offline."
    ::= { slbOperRealServerEntry 2 }

slbOperClearSessionTable OBJECT-TYPE
    SYNTAX  INTEGER {
	ok(1),
	clear(2),
        unsupported(2147483647)
	}
    MAX-ACCESS  read-write
    STATUS  current
    DESCRIPTION
        "This is an action object to clear session binding table.
         ok(1) is returned when read.
         Note:This mib is not supported for VX instance of Virtualization."
    ::= { layer4Oper 2 }

slbOperConfigSync OBJECT-TYPE
    SYNTAX  INTEGER {
	ok(1),
	sync(2),
        unsupported(2147483647)
	}
    MAX-ACCESS  read-write
    STATUS  current
    DESCRIPTION
        "When set to a value of 'sync(2)' it synchronizes the SLB, filter
         and VRRP configuration on a peer switch. To take effect, peers must
         be configured on the switches and the administrator password on the
         switches must be identical. 
         'ok(1)' is returned when the object is read.
         Note:This mib is not supported for VX instance of Virtualization."
    ::= { layer4Oper 3 }

-- Global SLB Operations

gslbOper         OBJECT IDENTIFIER ::= { layer4Oper 4 }

gslbOperQuery    OBJECT IDENTIFIER ::= { gslbOper 1 }
gslbOperAdd      OBJECT IDENTIFIER ::= { gslbOper 2 }
gslbOperRemove OBJECT-TYPE
    SYNTAX  INTEGER {
        ok(1),
        remove(2),
        unsupported(2147483647)
        }
    MAX-ACCESS  read-write
    STATUS  current
    DESCRIPTION
        "This is an action object to Remove all entries
         from Global SLB DNS persistence cache.
         ok(1) is returned when read.
         Note:This mib is not supported for VX instance of Virtualization."
    ::= { gslbOper 3 }

gslbOperAvPersis OBJECT IDENTIFIER ::= { gslbOper 4 }

gslbOperClear OBJECT-TYPE
    SYNTAX  INTEGER {
        ok(1),
        clear(2),
        unsupported(2147483647)
        }
    MAX-ACCESS  read-write
    STATUS  current
    DESCRIPTION
        "This is an action object when we set to a value of(2)
         it clear the client cache of dynamic entries.
         ok(1) is returned when read.
         Note:This mib is not supported for VX instance of Virtualization."
    ::= { gslbOper 5 }

gslbOperDnsSec OBJECT IDENTIFIER ::= { gslbOper 6 }

gslbOperDnsSecTable OBJECT-TYPE
    SYNTAX  SEQUENCE OF GslbOperDnsSecEntry
    MAX-ACCESS  not-accessible
    STATUS  current
    DESCRIPTION
        "Note:This mib is not supported for VX instance of Virtualization."
    ::= { gslbOperDnsSec 1 }

gslbOperDnsSecEntry OBJECT-TYPE
    SYNTAX  GslbOperDnsSecEntry
    MAX-ACCESS  not-accessible
    STATUS  current
    DESCRIPTION
        "."
    INDEX   { gslbOperDnsSecKeyID }
    ::= { gslbOperDnsSecTable 1 }

GslbOperDnsSecEntry ::= SEQUENCE {
    gslbOperDnsSecKeyID                 DisplayString,
    gslbOperDnsSecEmergencyRollover     INTEGER,
    gslbOperDnsSecImmediateRollover     INTEGER
    }

gslbOperDnsSecKeyID OBJECT-TYPE
    SYNTAX   DisplayString (SIZE(0..32))
    MAX-ACCESS  read-only
    STATUS  current
    DESCRIPTION
        "DNS Sec Table Key."
    ::= { gslbOperDnsSecEntry  1 }

gslbOperDnsSecEmergencyRollover OBJECT-TYPE
    SYNTAX  INTEGER {
        other(1),
        rollover(2),
        unsupported(2147483647)
        }
    MAX-ACCESS  read-write
    STATUS  current
    DESCRIPTION
        "By setting the value to rollover(2), DNSSEC emergency rollover procedure of a key will be Performed."
    ::= { gslbOperDnsSecEntry 2 }

gslbOperDnsSecImmediateRollover OBJECT-TYPE
    SYNTAX  INTEGER {
        other(1),
        rollover(2),
        unsupported(2147483647)
        }
    MAX-ACCESS  read-write
    STATUS  current
    DESCRIPTION
        "By setting the value to rollover(2), DNSSEC immediate rollover procedure of a key will be Performed."
    ::= { gslbOperDnsSecEntry 3 }


gslbOperQueryDomain OBJECT-TYPE
    SYNTAX  DisplayString
    MAX-ACCESS  read-write
    STATUS  current
    DESCRIPTION
        "Domain to query Global SLB selection.
         Note:This mib is not supported for VX instance of Virtualization."
    ::= { gslbOperQuery 1 }

gslbOperQuerySrcIp OBJECT-TYPE
    SYNTAX IpAddress
    MAX-ACCESS  read-write
    STATUS  current
    DESCRIPTION
        "Source Ip Address to query Global SLB selection.
         Note:This mib is not supported for VX instance of Virtualization."
    ::= { gslbOperQuery 2 }

gslbOperSendQuery OBJECT-TYPE
    SYNTAX  INTEGER {
    ok(1),
    query(2),
    unsupported(2147483647)
    }
    MAX-ACCESS  read-write
    STATUS  current
    DESCRIPTION
        "Query Global SLB selection.When set to a value of Query(2)
         it sends Global SLB selection query.Ok(1) is returned when
         this object is read.
         Note:This mib is not supported for VX instance of Virtualization."
    ::= { gslbOperQuery 3 }

gslbOperQuerySrcIpV6 OBJECT-TYPE
   SYNTAX DisplayString (SIZE(0..40))
    MAX-ACCESS  read-write
    STATUS  current
    DESCRIPTION
    "  Source Ip V6 Address to query Global SLB selection.
       Address should be 4-byte hexadecimal colon notation. Valid IPv6 address should be in
       any of the following forms xxxx:xxxx:xxxx:xxxx:xxxx:xxxx:xxxx:xxxx or xxxx::xxxx:xxxx:xxxx:xxxx or ::xxxx.
       Note:This mib is not supported for VX instance of Virtualization."
   ::= { gslbOperQuery 4 }

gslbOperQuerySrcIpVer OBJECT-TYPE
    SYNTAX  INTEGER{
        ipv4(1),
        ipv6(2),
        unsupported(2147483647)
        }
    MAX-ACCESS  read-only
    STATUS  current
    DESCRIPTION
        "Source Ip Version to query Global SLB selection.
         Note:This mib is not supported for VX instance of Virtualization."
    ::= { gslbOperQuery 5 }

gslbOperQueryType OBJECT-TYPE
    SYNTAX  INTEGER{
        a(1),
        aaaa(2),
        unsupported(2147483647)
        }
    MAX-ACCESS  read-write
    STATUS  current
    DESCRIPTION
        "Global SLB selection Query Type.
         Note:This mib is not supported for VX instance of Virtualization."
    ::= { gslbOperQuery 6 }

gslbOperAddDomain OBJECT-TYPE
    SYNTAX  DisplayString
    MAX-ACCESS  read-write
    STATUS  current
    DESCRIPTION
        "Domain to be added into Global SLB DNS Presistence cache.
         Note:This mib is not supported for VX instance of Virtualization."
    ::= { gslbOperAdd 1 }

gslbOperAddSrcIp OBJECT-TYPE
    SYNTAX IpAddress
    MAX-ACCESS  read-write
    STATUS  current
    DESCRIPTION
        "Source Ip Address to be added into Global SLB DNS
         Persistence cache.
         Note:This mib is not supported for VX instance of Virtualization."
    ::= { gslbOperAdd 2 }

gslbOperAddServerIp OBJECT-TYPE
    SYNTAX  IpAddress
    MAX-ACCESS  read-write
    STATUS  current
    DESCRIPTION
        "Server Ip Address to be added into Global SLB DNS
         Persistence cache.
         Note:This mib is not supported for VX instance of Virtualization."
    ::= { gslbOperAdd 3 }

gslbOperAddEntry OBJECT-TYPE
    SYNTAX  INTEGER {
        ok(1),
        add(2),
        unsupported(2147483647)
        }
    MAX-ACCESS  read-write
    STATUS  current
    DESCRIPTION
        "Add entry to Global SLB DNS persistence cache.
         When set to a value of add(2) Entry will be added into
         Global SLB DNS persistence cache.
         Ok(1) is returned when object is read.
         Note:This mib is not supported for VX instance of Virtualization."
    ::= { gslbOperAdd 4 }

gslbOperAddSrcIp6 OBJECT-TYPE
    SYNTAX   DisplayString (SIZE(0..40))
    MAX-ACCESS  read-write
    STATUS  current
    DESCRIPTION
        "Source Ip Address to be added into Global SLB DNS
         Persistence cache.
	 Address should be 4-byte hexadecimal colon notation.
         Valid IPv6 address should be in any of the following forms
           xxxx:xxxx:xxxx:xxxx:xxxx:xxxx:xxxx:xxxx or
           xxxx::xxxx:xxxx:xxxx:xxxx or ::xxxx.
         Note:This mib is not supported for VX instance of Virtualization."
    ::= { gslbOperAdd 5 }

gslbOperAddServerIp6 OBJECT-TYPE
    SYNTAX   DisplayString (SIZE(0..40))
    MAX-ACCESS  read-write
    STATUS  current
    DESCRIPTION
        "Server IPV6 Address to be added into Global SLB DNS
         Persistence cache.
	 Address should be 4-byte hexadecimal colon notation.
         Valid IPv6 address should be in any of the following forms
           xxxx:xxxx:xxxx:xxxx:xxxx:xxxx:xxxx:xxxx or
           xxxx::xxxx:xxxx:xxxx:xxxx or ::xxxx
         Note:This mib is not supported for VX instance of Virtualization."
    ::= { gslbOperAdd 6 }

gslbOperAddNetIpMask OBJECT-TYPE
    SYNTAX IpAddress
    MAX-ACCESS  read-write
    STATUS  current
    DESCRIPTION
    "Mask for Masking Source Ip Address to be added into Global
    SLB DNS Persistence cache.
    Note:This mib is not supported for VX instance of Virtualization."
    ::= { gslbOperAdd 7 }

gslbOperAddIpv6Prefix OBJECT-TYPE
    SYNTAX INTEGER (0..128)
    MAX-ACCESS  read-write
    STATUS  current
    DESCRIPTION
        "source IPv6 prefix for DNS persistence cache.
         Note:This mib is not supported for VX instance of Virtualization."
    ::= { gslbOperAdd 8 }

gslbOperAvPersisVirtNum OBJECT-TYPE
    SYNTAX  INTEGER (1..1024)
    MAX-ACCESS read-write
    STATUS  current
    DESCRIPTION
      "Enter Virtual Server Number for which GSLB
       availability persistence should be enabled/disabled.
       Note:This mib is not supported for VX instance of Virtualization."
    ::= { gslbOperAvPersis 1 }

gslbOperAvPersisState OBJECT-TYPE
    SYNTAX  INTEGER {
    enabled(1),
    disabled(2)
    }
    MAX-ACCESS  read-write
    STATUS  current
    DESCRIPTION
      "Enable or Disable GSLB availability persistence.
       Note:This mib is not supported for VX instance of Virtualization."
    ::= { gslbOperAvPersis 2 }

gslbOperAvpersistence OBJECT-TYPE
    SYNTAX  INTEGER {
    ok(1),
    config(2),
    unsupported(2147483647)
    }
    MAX-ACCESS  read-write
    STATUS  current
    DESCRIPTION
      "When we set to a value of 2(config),it enable/disable 
       GSLB availability persistence for configures virtual server.
       Ok(1) is returned when this object is read.
       Note:This mib is not supported for VX instance of Virtualization."
    ::= { gslbOperAvPersis 3 }


slbOperGroupRealServerTable OBJECT-TYPE
    SYNTAX  SEQUENCE OF SlbOperGroupRealServerEntry
    MAX-ACCESS  not-accessible
    STATUS  current
    DESCRIPTION
        "The table of real server per group.
         Note:This mib is not supported for VX instance of Virtualization."
    ::= { layer4Oper 5 }

slbOperGroupRealServerEntry OBJECT-TYPE
    SYNTAX  SlbOperGroupRealServerEntry
    MAX-ACCESS  not-accessible
    STATUS  current
    DESCRIPTION
        "A row in the Real server group table."
    INDEX   { slbOperRealServGroupIndex, slbOperGroupRealServIndex}
    ::= { slbOperGroupRealServerTable 1 }

SlbOperGroupRealServerEntry ::= SEQUENCE {
    slbOperRealServGroupIndex        Integer32,
    slbOperGroupRealServIndex        Integer32,
    slbOperGroupRealServerState      INTEGER,
    slbOperGroupRealServerStatus      INTEGER
    }

slbOperRealServGroupIndex OBJECT-TYPE
    SYNTAX  Integer32
    MAX-ACCESS  read-only
    STATUS  current
    DESCRIPTION
        "The real server group index." 
    ::= { slbOperGroupRealServerEntry 1 }

slbOperGroupRealServIndex OBJECT-TYPE
    SYNTAX  Integer32
    MAX-ACCESS  read-only
    STATUS  current
    DESCRIPTION
        "The real server index." 
    ::= { slbOperGroupRealServerEntry 2 }

slbOperGroupRealServerState OBJECT-TYPE
    SYNTAX  INTEGER {
	enable(1),
	disable(2),
        unsupported(2147483647)
	}
    MAX-ACCESS  read-write
    STATUS  current
    DESCRIPTION
        "This an action object which is used to temporarily enable/disable a
         real server in group. The real server will be returned to its configured
         operational mode when the switch is reset."
    ::= { slbOperGroupRealServerEntry 3 }

slbOperGroupRealServerStatus OBJECT-TYPE
    SYNTAX  INTEGER {
	enable(1),
	disable(2),
        unsupported(2147483647)
	}
    MAX-ACCESS  read-only
    STATUS  current
    DESCRIPTION
        "This an action object which is used to temporarily enable/disable a
         real server in group. The real server will be returned to its configured
         operational mode when the switch is reset."
    ::= { slbOperGroupRealServerEntry 4 }

slbOperSessionDel OBJECT IDENTIFIER ::= { layer4Oper 6 }

slbOperSessionDelSrcIp OBJECT-TYPE
    SYNTAX  IpAddress
    MAX-ACCESS  read-write
    STATUS  current
    DESCRIPTION
            "Session Source IP Address to be deleted.
             Note:This mib is not supported for VX instance of Virtualization."
    ::= { slbOperSessionDel 1}

slbOperSessionDelSrcPort OBJECT-TYPE
    SYNTAX  INTEGER (0..65534)
    MAX-ACCESS  read-write
    STATUS  current
    DESCRIPTION
            "Session Source Port to be deleted.
             Note:This mib is not supported for VX instance of Virtualization."
    ::= { slbOperSessionDel 2}

slbOperSessionDelDestIp OBJECT-TYPE
    SYNTAX  IpAddress
    MAX-ACCESS  read-write
    STATUS  current
    DESCRIPTION
            "Session Destination IP Address to be deleted.
             Note:This mib is not supported for VX instance of Virtualization."
    ::= { slbOperSessionDel 3 }
slbOperSessionDelDestPort OBJECT-TYPE
    SYNTAX  INTEGER (0..65534)
    MAX-ACCESS  read-write
    STATUS  current
    DESCRIPTION
            "Session Destination Port to be deleted.
             Note:This mib is not supported for VX instance of Virtualization."
    ::= { slbOperSessionDel 4 }

slbOperSessionDelTransType OBJECT-TYPE
    SYNTAX  INTEGER {
        tcp(1),
        udp(2),
        unsupported(2147483647)
        }
    MAX-ACCESS  read-write
    STATUS  current
    DESCRIPTION
             "Set a flag indicating whether Transport Type
              is TCP or UDP.
              Note:This mib is not supported for VX instance of Virtualization."
    ::= { slbOperSessionDel 5 }

slbOperSessionDelete OBJECT-TYPE
    SYNTAX  INTEGER {
        ok(1),
        delete(2),
        unsupported(2147483647)
        }
    MAX-ACCESS  read-write
    STATUS  current
    DESCRIPTION
        "This is an action object to delete session table entry.
         when set to a value of delete(2) it deletes session 
         table entry. Ok(1) is returned when object is read.
         Note:This mib is not supported for VX instance of Virtualization."
    ::= { slbOperSessionDel 6 }


slbOperHttpCachePurgeTable OBJECT-TYPE
    SYNTAX  SEQUENCE OF SlbOperHttpCachePurgeEntry
    MAX-ACCESS  not-accessible
    STATUS  current
    DESCRIPTION
        "The table of services per server.
         Note:This mib is not supported for VX instance of Virtualization."
    ::= {layer4Oper 7 }

slbOperHttpCachePurgeEntry OBJECT-TYPE
    SYNTAX SlbOperHttpCachePurgeEntry
    MAX-ACCESS  not-accessible
    STATUS  current
    DESCRIPTION
        "A row in the http cache purge service table."
    INDEX   { slbOperHttpCachePurgeServerIndex, slbOperHttpCachePurgeServiceIndex}
    ::= { slbOperHttpCachePurgeTable 1 }

SlbOperHttpCachePurgeEntry ::= SEQUENCE {
    slbOperHttpCachePurgeServerIndex   Integer32,
    slbOperHttpCachePurgeServiceIndex  Integer32,
    slbOperHttpCachePurgeURL           DisplayString 
    }

slbOperHttpCachePurgeServerIndex OBJECT-TYPE
    SYNTAX  Integer32 (1..1024)
    MAX-ACCESS  read-create
    STATUS  current
    DESCRIPTION
        "The Http Cache purge server index."
    ::= { slbOperHttpCachePurgeEntry 1 }

slbOperHttpCachePurgeServiceIndex OBJECT-TYPE
    SYNTAX  Integer32 (10..65534)
    MAX-ACCESS  read-create
    STATUS  current
    DESCRIPTION
        "The Http Cache purge service index."
    ::= { slbOperHttpCachePurgeEntry 2 }

slbOperHttpCachePurgeURL OBJECT-TYPE
    SYNTAX DisplayString 
    MAX-ACCESS  read-create
    STATUS  current
    DESCRIPTION
        "Set object URL or all."
    ::= { slbOperHttpCachePurgeEntry 3 }

ocspCachePurge OBJECT IDENTIFIER ::= { layer4Oper 8 }

slbOperOcspCachePurge OBJECT-TYPE
    SYNTAX DisplayString
    MAX-ACCESS  read-write
    STATUS  current
    DESCRIPTION
        "Client authentication policy id to purge or All.
         Note:This mib is not supported for VX instance of Virtualization."
    ::= { ocspCachePurge 1 }

	-- Real server group operational info 

slbOperEnhGroupRealServerTable OBJECT-TYPE
    SYNTAX  SEQUENCE OF SlbOperEnhGroupRealServerEntry
    MAX-ACCESS  not-accessible
    STATUS  current
    DESCRIPTION
        "The table of real server per group.
         Note:This mib is not supported for VX instance of Virtualization."
    ::= { layer4Oper 9 }

slbOperEnhGroupRealServerEntry OBJECT-TYPE
    SYNTAX  SlbOperEnhGroupRealServerEntry
    MAX-ACCESS  not-accessible
    STATUS  current
    DESCRIPTION
        "A row in the Real server group table."
    INDEX   { slbOperEnhRealServGroupIndex, slbOperEnhGroupRealServIndex}
    ::= { slbOperEnhGroupRealServerTable 1 }

SlbOperEnhGroupRealServerEntry ::= SEQUENCE {
    slbOperEnhRealServGroupIndex        DisplayString,
    slbOperEnhGroupRealServIndex        DisplayString,
    slbOperEnhGroupRealServerState      INTEGER,
    slbOperEnhGroupRealServerStatus     INTEGER,
    slbOperEnhGroupRealServerIP         IpAddress,
    slbOperEnhGroupRealServerDescr      DisplayString,
    slbOperEnhGroupRealServerRuntimeStatus INTEGER
    }

slbOperEnhRealServGroupIndex OBJECT-TYPE
    SYNTAX DisplayString (SIZE(1..255)) 
    MAX-ACCESS  read-only
    STATUS  current
    DESCRIPTION
        "The real server group index."
    ::= { slbOperEnhGroupRealServerEntry 1 }

slbOperEnhGroupRealServIndex OBJECT-TYPE
    SYNTAX DisplayString (SIZE(1..255)) 
    MAX-ACCESS  read-only
    STATUS  current
    DESCRIPTION
        "The real server index."
    ::= { slbOperEnhGroupRealServerEntry 2 }

slbOperEnhGroupRealServerState OBJECT-TYPE
    SYNTAX  INTEGER {
        enable(1),
        disable(2),
	shutdown-connection(3),
	shutdown-persistent-sessions(4),
        unsupported(2147483647)
        }
    MAX-ACCESS  read-write
    STATUS  current
    DESCRIPTION
        "This an action object which is used to temporarily enable/disable a
         real server in group. The real server will be returned to its configured
         operational mode when the switch is reset."
    ::= { slbOperEnhGroupRealServerEntry 3 }

slbOperEnhGroupRealServerStatus OBJECT-TYPE
    SYNTAX  INTEGER {
        enable(1),
        disable(2),
	shutdown-connection(3),
	shutdown-persistent-sessions(4),
        unsupported(2147483647)
        }
    MAX-ACCESS  read-only
    STATUS  current
    DESCRIPTION
        "This an action object which is used to temporarily enable/disable a
         real server in group. The real server will be returned to its configured
         operational mode when the switch is reset."
    ::= { slbOperEnhGroupRealServerEntry 4 }

slbOperEnhGroupRealServerIP OBJECT-TYPE
    SYNTAX  IpAddress
    MAX-ACCESS  read-only
    STATUS  current
    DESCRIPTION
        "IP address of the real server identified by the instance of the
         slbRealServerIndex."
    ::= { slbOperEnhGroupRealServerEntry 5 }

slbOperEnhGroupRealServerDescr OBJECT-TYPE
    SYNTAX DisplayString (SIZE(0..255))
    MAX-ACCESS  read-only
    STATUS  current
    DESCRIPTION
        "Description of the real server identified by the instance of the
           slbRealServerIndex."
    ::= { slbOperEnhGroupRealServerEntry 6 }

slbOperEnhGroupRealServerRuntimeStatus OBJECT-TYPE
    SYNTAX  INTEGER {
        running(1),
        failed(2),
        disabled(3),
        overloaded(4),
        unsupported(2147483647)
    }
    MAX-ACCESS  read-only
    STATUS  current
    DESCRIPTION
        "The current status of a real server in the group."
    ::= { slbOperEnhGroupRealServerEntry 7 }


slbOperEnhHttpCachePurgeTable OBJECT-TYPE
    SYNTAX  SEQUENCE OF SlbOperEnhHttpCachePurgeEntry
    MAX-ACCESS  not-accessible
    STATUS  current
    DESCRIPTION
        "The table of services per server.
         Note:This mib is not supported for VX instance of Virtualization."
    ::= {layer4Oper 11 }

slbOperEnhHttpCachePurgeEntry OBJECT-TYPE
    SYNTAX SlbOperEnhHttpCachePurgeEntry
    MAX-ACCESS  not-accessible
    STATUS  current
    DESCRIPTION
        "A row in the http cache purge service table."
    INDEX   { slbOperEnhHttpCachePurgeServerIndex, slbOperEnhHttpCachePurgeServiceIndex}
    ::= { slbOperEnhHttpCachePurgeTable 1 }

SlbOperEnhHttpCachePurgeEntry ::= SEQUENCE {
    slbOperEnhHttpCachePurgeServerIndex   DisplayString,
    slbOperEnhHttpCachePurgeServiceIndex  Integer32,
    slbOperEnhHttpCachePurgeURL           DisplayString
    }

slbOperEnhHttpCachePurgeServerIndex OBJECT-TYPE
    SYNTAX DisplayString (SIZE(1..255))
    MAX-ACCESS  read-only
    STATUS  current
    DESCRIPTION
        "The Http Cache purge server index."
    ::= { slbOperEnhHttpCachePurgeEntry 1 }

slbOperEnhHttpCachePurgeServiceIndex OBJECT-TYPE
    SYNTAX  Integer32 (10..65534)
    MAX-ACCESS  read-create
    STATUS  current
    DESCRIPTION
        "The Http Cache purge service index."
    ::= { slbOperEnhHttpCachePurgeEntry 2 }

slbOperEnhHttpCachePurgeURL OBJECT-TYPE
    SYNTAX DisplayString
    MAX-ACCESS  read-create
    STATUS  current
    DESCRIPTION
        "Set object URL or all."
    ::= { slbOperEnhHttpCachePurgeEntry 3 }

slbOperEnhRealServerTable OBJECT-TYPE
    SYNTAX  SEQUENCE OF SlbOperEnhRealServerEntry
    MAX-ACCESS  not-accessible
    STATUS  current
    DESCRIPTION
        "The table of real servers.
         Note:This mib is not supported for VX instance of Virtualization."
    ::= { layer4Oper 10 }

slbOperEnhRealServerEntry OBJECT-TYPE
    SYNTAX  SlbOperEnhRealServerEntry
    MAX-ACCESS  not-accessible
    STATUS  current
    DESCRIPTION
        "A row in the slbOperEnhRealServerTable "
    INDEX   { slbOperEnhRealServerIndex }
    ::= { slbOperEnhRealServerTable 1 }

SlbOperEnhRealServerEntry ::= SEQUENCE {
        slbOperEnhRealServerIndex              DisplayString,
        slbOperEnhRealServerStatus             INTEGER
    }

slbOperEnhRealServerIndex OBJECT-TYPE
    SYNTAX  DisplayString (SIZE(1..255))
    MAX-ACCESS  read-only
    STATUS  current
    DESCRIPTION
        "The index for the  real server." 
    ::= { slbOperEnhRealServerEntry 1 }

slbOperEnhRealServerStatus OBJECT-TYPE
    SYNTAX  INTEGER {
        enable(1),
        disable(2),
        cookiepersistent(3),
        fastage(4),
        cookiepersistentfastage(5),
        unsupported(2147483647)
    }
    MAX-ACCESS  read-write
    STATUS  current
    DESCRIPTION
        "This an action object which is used to temporarily enable/disable a
        real server. The real server will be returned to its configured
        operational mode when the switch is reset. Setting the value to 
        'cookiepersistant' allows cookie persistent HTTP 1.0 sessions
        when the real server is offline.'fastage' option is for removing the
        existing sessions. And 'cookiepersistentfastage' allows cookie
        persistent sessions and remove the existing sessions when real server is offline."
    ::= { slbOperEnhRealServerEntry 2 }
 
cdpCachePurge OBJECT IDENTIFIER ::= { layer4Oper 12}

slbOperCdpCachePurge OBJECT-TYPE
    SYNTAX DisplayString
    MAX-ACCESS  read-write
    STATUS  current
    DESCRIPTION
        "Client authentication policy id to purge or All.
         Note:This mib is not supported for VX instance of Virtualization."
    ::= { cdpCachePurge 1 }

slbOperSessionMove OBJECT IDENTIFIER ::= { layer4Oper 13 }

slbOperSessionMoveSrcIp OBJECT-TYPE
    SYNTAX  IpAddress
    MAX-ACCESS  read-write
    STATUS  current
    DESCRIPTION
            "Session Source IP Address.
             Note:This mib is not supported for VX instance of Virtualization."
    ::= { slbOperSessionMove 1}

slbOperSessionMoveVirtId OBJECT-TYPE
    SYNTAX  DisplayString (SIZE(1..255))
    MAX-ACCESS read-write 
    STATUS  current
    DESCRIPTION
        "virtual server ID.
         Note:This mib is not supported for VX instance of Virtualization."
    ::= { slbOperSessionMove  2}

slbOperSessionMoveGroupId OBJECT-TYPE
    SYNTAX  DisplayString (SIZE(1..255))
    MAX-ACCESS  read-write
    STATUS  current
    DESCRIPTION
        "group ID.
         Note:This mib is not supported for VX instance of Virtualization."
    ::= { slbOperSessionMove  3}

slbOperSessionMoveRealId OBJECT-TYPE
    SYNTAX  DisplayString (SIZE(1..255))
    MAX-ACCESS  read-write
    STATUS  current
    DESCRIPTION
        "new real server ID.
         Note:This mib is not supported for VX instance of Virtualization."
    ::= { slbOperSessionMove  4}

slbOperSessionMoveRPort OBJECT-TYPE
    SYNTAX  INTEGER (0..65534)
    MAX-ACCESS  read-write
    STATUS  current
    DESCRIPTION
            "Session Real Port to be updated.
             Note:This mib is not supported for VX instance of Virtualization."
    ::= { slbOperSessionMove 5}

slbOperSessionMoveOper OBJECT-TYPE
    SYNTAX  INTEGER {
        ok(1),
        move(2),
        unsupported(2147483647)
        }
    MAX-ACCESS  read-write
    STATUS  current
    DESCRIPTION
        "This is an action object to move session entry of a 
	 specified client to another server.
         when set to a value of move(2) it update session
         table entry. Ok(1) is returned when object is read.
         Note:This mib is not supported for VX instance of Virtualization."
    ::= { slbOperSessionMove 6 }


slbOperPersSessionDel OBJECT IDENTIFIER ::= { layer4Oper 14 }

slbOperPersSessionDelSessKeyType OBJECT-TYPE
    SYNTAX  INTEGER {
        cookie(1),
        clientip(2),
        sslid(3),
        unsupported(2147483647)
        }
    MAX-ACCESS  read-write
    STATUS  current
    DESCRIPTION
        "Persistent session type.
         Note:This mib is not supported for VX instance of Virtualization."
    ::= { slbOperPersSessionDel  1 }

slbOperPersSessionDelSessKey OBJECT-TYPE
    SYNTAX  DisplayString (SIZE(1..255))
    MAX-ACCESS read-write
    STATUS  current
    DESCRIPTION
            "Persistent Session Key. 
	     Session Type cookie/sslid : Cookie value 
	     Session Type Clientip     : Client IP address,
             Note:This mib is not supported for VX instance of Virtualization."
    ::= { slbOperPersSessionDel  2}

slbOperPersSessionDelVirtId OBJECT-TYPE
    SYNTAX  DisplayString (SIZE(1..255))
    MAX-ACCESS read-write
    STATUS  current
    DESCRIPTION
        "virtual server ID.
         Note:This mib is not supported for VX instance of Virtualization."
    ::= { slbOperPersSessionDel  3}

slbOperPersSessionDelServPort OBJECT-TYPE
    SYNTAX  DisplayString (SIZE(1..255))
    MAX-ACCESS  read-write
    STATUS  current
    DESCRIPTION
        "Persistent session service port. (0-65534) or all.
         Note:This mib is not supported for VX instance of Virtualization."
    ::= { slbOperPersSessionDel  4}

slbOperPersSessionDelRealId OBJECT-TYPE
    SYNTAX  DisplayString (SIZE(1..255))
    MAX-ACCESS  read-write
    STATUS  current
    DESCRIPTION
        "real server ID.
         Note:This mib is not supported for VX instance of Virtualization."
    ::= { slbOperPersSessionDel  5}

slbOperPersSessionDelOper OBJECT-TYPE
    SYNTAX  INTEGER {
        ok(1),
        delete(2),
        unsupported(2147483647)
        }
    MAX-ACCESS  read-write
    STATUS  current
    DESCRIPTION
        "This is an action object to persistent session entry.
         when set to a value of delete(2) it delete persistent 
	session entry. Ok(1) is returned when object is read.
        Note:This mib is not supported for VX instance of Virtualization."
    ::= { slbOperPersSessionDel  6 }

-- Server load balancing - Inbound Link Load Balancing Table

slbCurCfgLinklbState OBJECT-TYPE
    SYNTAX INTEGER {
        enabled(1),
        disabled(2),
        unsupported(2147483647)
        }
    MAX-ACCESS  read-only
    STATUS  current
    DESCRIPTION
        "Enable or disable Inbound Link load balancing.
         Note:This mib is not supported for VX instance of Virtualization."
    ::= { linklbCfg 1 }

slbNewCfgLinklbState OBJECT-TYPE
    SYNTAX INTEGER {
        enabled(1),
        disabled(2),
        unsupported(2147483647)
        }
    MAX-ACCESS  read-write
    STATUS  current
    DESCRIPTION
        "Enable or disable Inbound Link load balancing.
         Note:This mib is not supported for VX instance of Virtualization."
    ::= { linklbCfg 2 }

slbCurCfgLinklbRealGroup OBJECT-TYPE
    SYNTAX  Integer32  
    MAX-ACCESS  read-only
    STATUS  current
    DESCRIPTION
        "The real server group number for Link load balancing.
         Note:This mib is not supported for VX instance of Virtualization."
    ::= { linklbCfg 3 }

slbNewCfgLinklbRealGroup OBJECT-TYPE
    SYNTAX  Integer32  
    MAX-ACCESS  read-write
    STATUS  current
    DESCRIPTION
        "The real server group number for Link load balancing.
         Note:This mib is not supported for VX instance of Virtualization."
    ::= { linklbCfg 4 }

slbCurCfgLinklbTTL OBJECT-TYPE
    SYNTAX  INTEGER (0..65535) 
    MAX-ACCESS  read-only
    STATUS  current
    DESCRIPTION
        "Set Time to Live for DNS resource records.
         Note:This mib is not supported for VX instance of Virtualization."
    ::= { linklbCfg 6 }

slbNewCfgLinklbTTL OBJECT-TYPE
    SYNTAX  INTEGER (0..65535) 
    MAX-ACCESS  read-write
    STATUS  current
    DESCRIPTION
        "Set Time to Live for DNS resource records.
         Note:This mib is not supported for VX instance of Virtualization."
    ::= { linklbCfg 7 }

slbCurCfgLinklbEnhRealGroup OBJECT-TYPE
    SYNTAX  DisplayString (SIZE(1..255)) 
    MAX-ACCESS  read-only
    STATUS  current
    DESCRIPTION
        "The real server group AlphaNumeric ID for Link load balancing.
         Note:This mib is not supported for VX instance of Virtualization."
    ::= { linklbCfg 8 }

slbNewCfgLinklbEnhRealGroup OBJECT-TYPE
    SYNTAX DisplayString (SIZE(1..255)) 
    MAX-ACCESS  read-write
    STATUS  current
    DESCRIPTION
        "The real server group AlphaNumeric ID for Link load balancing.
         Note:This mib is not supported for VX instance of Virtualization."
    ::= { linklbCfg 9 }

slbLinklbDrecord   OBJECT IDENTIFIER ::= { linklbCfg 5 }

slbDrecordTableMaxSize OBJECT-TYPE
    SYNTAX  Integer32 
    MAX-ACCESS  read-only 
    STATUS  current 
    DESCRIPTION 
        "The maximum number of entries in Drecord table.
         Note:This mib is not supported for VX instance of Virtualization."
    ::= { slbLinklbDrecord 1 }

slbCurCfgDrecordTable OBJECT-TYPE
    SYNTAX  SEQUENCE OF SlbCurCfgDrecordEntry
    MAX-ACCESS  not-accessible
    STATUS  current
    DESCRIPTION
        "The table of Domain records for Inbound link load balancing
         in the current configuration block.
         Note:This mib is not supported for VX instance of Virtualization."
    ::= { slbLinklbDrecord 2 }

slbCurCfgDrecordEntry OBJECT-TYPE
    SYNTAX  SlbCurCfgDrecordEntry
    MAX-ACCESS  not-accessible
    STATUS  current
    DESCRIPTION
        "A row in the Domain record table for Inbound Link Load
         balancing."
    INDEX   { slbCurCfgDrecordIndex }
    ::= { slbCurCfgDrecordTable 1 }

SlbCurCfgDrecordEntry ::= SEQUENCE {
    slbCurCfgDrecordIndex            INTEGER,
    slbCurCfgDomainRecordState       INTEGER,
    slbCurCfgDomainRecordName        DisplayString
    }

slbCurCfgDrecordIndex OBJECT-TYPE
    SYNTAX  INTEGER (1..64)
    MAX-ACCESS  read-only
    STATUS  current
    DESCRIPTION
        "The index of the Domain record table." 
    ::= { slbCurCfgDrecordEntry 1 }

slbCurCfgDomainRecordState OBJECT-TYPE
    SYNTAX  INTEGER {
	enabled(1),
	disabled(2),
        unsupported(2147483647)
	}
    MAX-ACCESS  read-only
    STATUS  current
    DESCRIPTION
        "Enable/disable a  domain record."
    ::= { slbCurCfgDrecordEntry 2 }

slbCurCfgDomainRecordName OBJECT-TYPE 
    SYNTAX  DisplayString (SIZE(0..34))
    MAX-ACCESS  read-only
    STATUS  current 
    DESCRIPTION 
        "The name of the domain record."  
    ::= { slbCurCfgDrecordEntry 3 }

slbNewCfgDrecordTable OBJECT-TYPE
    SYNTAX  SEQUENCE OF SlbNewCfgDrecordEntry
    MAX-ACCESS  not-accessible
    STATUS  current
    DESCRIPTION
        "The table of Domain records for Inbound link load balancing
         in the new configuration block.
         Note:This mib is not supported for VX instance of Virtualization."
    ::= { slbLinklbDrecord 3 }

slbNewCfgDrecordEntry OBJECT-TYPE
    SYNTAX  SlbNewCfgDrecordEntry
    MAX-ACCESS  not-accessible
    STATUS  current
    DESCRIPTION
        "A row in the Domain record table for Inbound Link Load
         balancing."
    INDEX   { slbNewCfgDrecordIndex }
    ::= { slbNewCfgDrecordTable 1 }

SlbNewCfgDrecordEntry ::= SEQUENCE {
    slbNewCfgDrecordIndex            INTEGER,
    slbNewCfgDomainRecordState       INTEGER,
    slbNewCfgDomainRecordName        DisplayString,
    slbNewCfgDrecordDelete           INTEGER 
    }

slbNewCfgDrecordIndex OBJECT-TYPE
    SYNTAX  INTEGER (1..64)
    MAX-ACCESS  read-only
    STATUS  current
    DESCRIPTION
        "The index of the Domain record table." 
    ::= { slbNewCfgDrecordEntry 1 }

slbNewCfgDomainRecordState OBJECT-TYPE
    SYNTAX  INTEGER {
	enabled(1),
	disabled(2),
        unsupported(2147483647)
	}
    MAX-ACCESS  read-create
    STATUS  current
    DESCRIPTION
        "Enable/disable a  domain record."
    ::= { slbNewCfgDrecordEntry 2 }

slbNewCfgDomainRecordName OBJECT-TYPE 
    SYNTAX  DisplayString (SIZE(0..64))
    MAX-ACCESS  read-create 
    STATUS  current 
    DESCRIPTION 
        "The name of the domain record."  
    ::= { slbNewCfgDrecordEntry 3 }

slbNewCfgDrecordDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgDrecordEntry 4 }

slbDrecordVirtRealMappingTableMaxSize OBJECT-TYPE
    SYNTAX  Integer32 
    MAX-ACCESS  read-only 
    STATUS  current 
    DESCRIPTION 
        "The maximum number of entries in Drecord Virtual Real server
         mapping Table.
        Note:This mib is not supported for VX instance of Virtualization." 
    ::= { slbLinklbDrecord 4 }

slbCurCfgDrecordVirtRealMappingTable OBJECT-TYPE
    SYNTAX  SEQUENCE OF SlbCurCfgDrecordVirtRealMappingEntry
    MAX-ACCESS  not-accessible
    STATUS  current
    DESCRIPTION
        "The table of Domain records and virtual server and real
         server mappings.
         Note:This mib is not supported for VX instance of Virtualization."
    ::= { slbLinklbDrecord 5 }

slbCurCfgDrecordVirtRealMappingEntry OBJECT-TYPE
    SYNTAX  SlbCurCfgDrecordVirtRealMappingEntry
    MAX-ACCESS  not-accessible
    STATUS  current
    DESCRIPTION
        "A row in the Domain record and virtual/real server mapping table
         for Inbound Link Load balancing."
    INDEX   { slbCurCfgDomainRecordIndex, slbCurCfgEntryIndex}
    ::= { slbCurCfgDrecordVirtRealMappingTable 1 }

SlbCurCfgDrecordVirtRealMappingEntry ::= SEQUENCE {
    slbCurCfgDomainRecordIndex            INTEGER,
    slbCurCfgEntryIndex                   INTEGER,
    slbCurCfgDrecordVirtServer            Integer32,
    slbCurCfgDrecordRealServer            Integer32,
    slbCurCfgDrecordEntryState            INTEGER,
    slbCurCfgDrecordEnhVirtServer         DisplayString,
    slbCurCfgDrecordEnhRealServer         DisplayString 
    }

slbCurCfgDomainRecordIndex OBJECT-TYPE
    SYNTAX  INTEGER (1..64)
    MAX-ACCESS  read-only
    STATUS  current
    DESCRIPTION
        "The number of the domain record." 
    ::= { slbCurCfgDrecordVirtRealMappingEntry 1 }

slbCurCfgEntryIndex OBJECT-TYPE
    SYNTAX  INTEGER (1..8)
    MAX-ACCESS  read-only
    STATUS  current
    DESCRIPTION
        "The number of the entry virtual real server mapping." 
    ::= { slbCurCfgDrecordVirtRealMappingEntry 2 }

slbCurCfgDrecordVirtServer OBJECT-TYPE
    SYNTAX  Integer32 
    MAX-ACCESS  read-only
    STATUS  current
    DESCRIPTION
        "The virtual server number."
    ::= { slbCurCfgDrecordVirtRealMappingEntry 3 }

slbCurCfgDrecordRealServer OBJECT-TYPE
    SYNTAX  Integer32 
    MAX-ACCESS  read-only
    STATUS  current
    DESCRIPTION
        "The Real server number."
    ::= { slbCurCfgDrecordVirtRealMappingEntry 4 }


slbCurCfgDrecordEntryState OBJECT-TYPE
    SYNTAX  INTEGER {
	enabled(1),
	disabled(2),
        unsupported(2147483647)
	}
    MAX-ACCESS  read-only
    STATUS  current
    DESCRIPTION
        "Enable/disable a mapping in this table."
    ::= { slbCurCfgDrecordVirtRealMappingEntry 5 }

slbCurCfgDrecordEnhVirtServer OBJECT-TYPE
    SYNTAX DisplayString (SIZE(1..255)) 
    MAX-ACCESS  read-only
    STATUS  current
    DESCRIPTION
    "The virtual server AlphaNumeric Id."
    ::= { slbCurCfgDrecordVirtRealMappingEntry 6 }

slbCurCfgDrecordEnhRealServer OBJECT-TYPE
    SYNTAX DisplayString (SIZE(1..255)) 
    MAX-ACCESS  read-only
    STATUS  current
    DESCRIPTION
    "The Real server AlphaNumeric Id."
    ::= { slbCurCfgDrecordVirtRealMappingEntry 7 }

slbNewCfgDrecordVirtRealMappingTable OBJECT-TYPE
    SYNTAX  SEQUENCE OF SlbNewCfgDrecordVirtRealMappingEntry
    MAX-ACCESS  not-accessible
    STATUS  current
    DESCRIPTION
        "The table of Domain records and virtual server and real
         server mappings.
         Note:This mib is not supported for VX instance of Virtualization."
    ::= { slbLinklbDrecord 6 }

slbNewCfgDrecordVirtRealMappingEntry OBJECT-TYPE
    SYNTAX  SlbNewCfgDrecordVirtRealMappingEntry
    MAX-ACCESS  not-accessible
    STATUS  current
    DESCRIPTION
        "A row in the Domain record and virtual/real server mapping table
         for Inbound Link Load balancing."
    INDEX   { slbNewCfgDomainRecordIndex, slbNewCfgEntryIndex }
    ::= { slbNewCfgDrecordVirtRealMappingTable 1 }

SlbNewCfgDrecordVirtRealMappingEntry ::= SEQUENCE {
    slbNewCfgDomainRecordIndex            INTEGER,
    slbNewCfgEntryIndex                   INTEGER,
    slbNewCfgDrecordVirtServer            Integer32,
    slbNewCfgDrecordRealServer            Integer32,
    slbNewCfgDrecordEntryState            INTEGER,
    slbNewCfgDrecordEntryDelete           INTEGER,
    slbNewCfgDrecordEnhVirtServer            DisplayString,
    slbNewCfgDrecordEnhRealServer            DisplayString
    }

slbNewCfgDomainRecordIndex OBJECT-TYPE
    SYNTAX  INTEGER (1..64)
    MAX-ACCESS  read-only
    STATUS  current
    DESCRIPTION
        "The number of the domain record." 
    ::= { slbNewCfgDrecordVirtRealMappingEntry 1 }

slbNewCfgEntryIndex OBJECT-TYPE
    SYNTAX  INTEGER (1..8)
    MAX-ACCESS  read-only
    STATUS  current
    DESCRIPTION
        "The number of the virtual real server mapping." 
    ::= { slbNewCfgDrecordVirtRealMappingEntry 2 }

slbNewCfgDrecordVirtServer OBJECT-TYPE
    SYNTAX  Integer32 
    MAX-ACCESS  read-create
    STATUS  current
    DESCRIPTION
        "The virtual server number."
    ::= { slbNewCfgDrecordVirtRealMappingEntry 3 }

slbNewCfgDrecordRealServer OBJECT-TYPE
    SYNTAX  Integer32 
    MAX-ACCESS  read-create
    STATUS  current
    DESCRIPTION
        "The Real server number."
    ::= { slbNewCfgDrecordVirtRealMappingEntry 4 }

slbNewCfgDrecordEntryState OBJECT-TYPE
    SYNTAX  INTEGER {
	enabled(1),
	disabled(2),
        unsupported(2147483647)
	}
    MAX-ACCESS  read-create
    STATUS  current
    DESCRIPTION
        "Enable/disable a mapping in this table."
    ::= { slbNewCfgDrecordVirtRealMappingEntry 5 }

slbNewCfgDrecordEntryDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgDrecordVirtRealMappingEntry 6 }
	
	slbNewCfgDrecordEnhVirtServer OBJECT-TYPE
    SYNTAX DisplayString (SIZE(1..255))
    MAX-ACCESS  read-create
    STATUS  current
    DESCRIPTION
       "The virtual server AlphaNumeric Id."
    ::= { slbNewCfgDrecordVirtRealMappingEntry 7 }

slbNewCfgDrecordEnhRealServer OBJECT-TYPE
    SYNTAX DisplayString (SIZE(1..255))
    MAX-ACCESS  read-create
    STATUS  current
    DESCRIPTION
      "The Real server AlphaNumeric Id."
    ::= { slbNewCfgDrecordVirtRealMappingEntry 8 }


slbCurSslCfgSSLAdminStatus OBJECT-TYPE
    SYNTAX  INTEGER {
        enabled(1),
        disabled(2),
        unsupported(2147483647)
        }
    MAX-ACCESS  read-only
    STATUS  current
    DESCRIPTION
        "Status (enable/disable) of SSL policy.
         Note:This mib is not supported for VX instance of Virtualization."
    ::= { sslCfg 1 }


slbCurSslCfgSSLPolTable OBJECT-TYPE
    SYNTAX  SEQUENCE OF SlbCurSslCfgSSLPolEntry
    MAX-ACCESS  not-accessible
    STATUS  current
    DESCRIPTION
        "The table for configuring ssl  policy.
         Note:This mib is not supported for VX instance of Virtualization."
    ::= { sslPol 5 }

slbCurSslCfgSSLPolEntry OBJECT-TYPE
    SYNTAX  SlbCurSslCfgSSLPolEntry
    MAX-ACCESS  not-accessible
    STATUS  current
    DESCRIPTION
        "A row in the ssl policy table."
    INDEX   { slbCurSslCfgSSLPolNameIdIndex }
    ::= { slbCurSslCfgSSLPolTable 1 }

SlbCurSslCfgSSLPolEntry ::= SEQUENCE {
    slbCurSslCfgSSLPolNameIdIndex             DisplayString,
    slbCurSslCfgSSLPolName                    DisplayString,
    slbCurSslCfgSSLPolPassInfoCipherName      DisplayString,
    slbCurSslCfgSSLPolPassInfoCipherFlag      INTEGER,
    slbCurSslCfgSSLPolPassInfoVersionName     DisplayString,
    slbCurSslCfgSSLPolPassInfoVersionFlag     INTEGER,
    slbCurSslCfgSSLPolPassInfoHeadBitsName    DisplayString,
    slbCurSslCfgSSLPolPassInfoHeadBitsFlag    INTEGER,
    slbCurSslCfgSSLPolPassInfoFrontend        INTEGER,
    slbCurSslCfgSSLPolCipherName              INTEGER,
    slbCurSslCfgSSLPolCipherUserdef           RadwareLongDisplayString,
    slbCurSslCfgSSLPolCipherExpertUserdef     DisplayString,
    slbCurSslCfgSSLPolIntermcaChainName       DisplayString,
    slbCurSslCfgSSLPolIntermcaChainType       DisplayString,
    slbCurSslCfgSSLPolBecipher                INTEGER,
    slbCurSslCfgSSLPolBeCipherUserdef         DisplayString,
    slbCurSslCfgSSLPolBeCipherExpertUserdef   DisplayString,
    slbCurSslCfgSSLPolAuthpol                 DisplayString,
    slbCurSslCfgSSLPolConvuri                 DisplayString,
    slbCurSslCfgSSLPolBessl                   INTEGER,
    slbCurSslCfgSSLPolBEClientCertName        DisplayString,
    slbCurSslCfgSSLPolBETrustedCAcertName     DisplayString,
    slbCurSslCfgSSLPolBETrustedCAcertType     DisplayString,
    slbCurSslCfgSSLPolConvert                 INTEGER,
    slbCurSslCfgSSLPolAdminStatus             INTEGER,
    slbCurSslCfgSSLPolPassInfoComply          INTEGER,
    slbCurSslCfgSSLPolFessl                   INTEGER,
    slbCurSslCfgSSLPolFESslv3Version          INTEGER,
    slbCurSslCfgSSLPolFETls10Version          INTEGER,
    slbCurSslCfgSSLPolFETls11Version          INTEGER,
    slbCurSslCfgSSLPolBESslv3Version          INTEGER,
    slbCurSslCfgSSLPolBETls10Version          INTEGER,
    slbCurSslCfgSSLPolBETls11Version          INTEGER,
    slbCurSslCfgSSLPolFETls12Version          INTEGER,
    slbCurSslCfgSSLPolBETls12Version          INTEGER,
    slbCurSslCfgSSLPolSecreneg                DisplayString,
    slbCurSslCfgSSLPolDHkey                   INTEGER,
    slbCurSslCfgSSLPolBEAuthpol               DisplayString,
    slbCurSslCfgSSLPolHwoffldFeRsa            INTEGER,
    slbCurSslCfgSSLPolHwoffldFeDh             INTEGER,
    slbCurSslCfgSSLPolHwoffldFeEc             INTEGER,
    slbCurSslCfgSSLPolHwoffldFeBulk           INTEGER,
    slbCurSslCfgSSLPolHwoffldFePkey           INTEGER,
    slbCurSslCfgSSLPolHwoffldFeFeatures       INTEGER,
    slbCurSslCfgSSLPolHwoffldBeRsa            INTEGER,
    slbCurSslCfgSSLPolHwoffldBeDh             INTEGER,
    slbCurSslCfgSSLPolHwoffldBeEc             INTEGER,
    slbCurSslCfgSSLPolHwoffldBeBulk           INTEGER,
    slbCurSslCfgSSLPolHwoffldBePkey           INTEGER,
    slbCurSslCfgSSLPolHwoffldBeFeatures       INTEGER,
    slbCurSslCfgSSLPolBesni                   INTEGER,
    slbCurSslCfgSSLPolFETls13Version          INTEGER,
    slbCurSslCfgSSLPolBETls13Version          INTEGER,
    slbCurSslCfgSSLPol0RTTFEData              INTEGER,
    slbCurSslCfgSSLPolFeReuseState            INTEGER,
    slbCurSslCfgSSLPolBeReuseState            INTEGER,
    slbCurSslCfgSSLPolBeReuseSrcMatch         INTEGER,
    slbCurSslCfgSSLPolBeReuseTicket           INTEGER,
    slbCurSslCfgSSLPolFeReuseTicket           INTEGER
    }
slbCurSslCfgSSLPolNameIdIndex OBJECT-TYPE
    SYNTAX   DisplayString
    MAX-ACCESS  read-only
    STATUS  current
    DESCRIPTION
        "The SSL policy name(key id) as an index."
    ::= {slbCurSslCfgSSLPolEntry  1 }

slbCurSslCfgSSLPolName  OBJECT-TYPE
    SYNTAX   DisplayString
    MAX-ACCESS  read-only
    STATUS  current
    DESCRIPTION
        "SSL policy name."
    ::= {slbCurSslCfgSSLPolEntry  2 }

slbCurSslCfgSSLPolPassInfoCipherName OBJECT-TYPE
    SYNTAX DisplayString 
    MAX-ACCESS  read-only
    STATUS  current
    DESCRIPTION
        "The SSL cipher-suite header name."
    ::= {slbCurSslCfgSSLPolEntry  3 }

slbCurSslCfgSSLPolPassInfoCipherFlag OBJECT-TYPE
    SYNTAX  INTEGER 
    MAX-ACCESS  read-only
    STATUS  current
    DESCRIPTION
        "SSL cipher-suite information to backend servers enabled."
    ::= {slbCurSslCfgSSLPolEntry  4 }

slbCurSslCfgSSLPolPassInfoVersionName OBJECT-TYPE
    SYNTAX  DisplayString
    MAX-ACCESS  read-only
    STATUS  current
    DESCRIPTION
        "SSL version header name."
    ::= {slbCurSslCfgSSLPolEntry  5 }

slbCurSslCfgSSLPolPassInfoVersionFlag OBJECT-TYPE
    SYNTAX   INTEGER
    MAX-ACCESS  read-only
    STATUS  current
    DESCRIPTION
        "SSL version information to backend servers enabled."
    ::= {slbCurSslCfgSSLPolEntry  6 }

slbCurSslCfgSSLPolPassInfoHeadBitsName OBJECT-TYPE
    SYNTAX   DisplayString
    MAX-ACCESS  read-only
    STATUS  current
    DESCRIPTION
        "The passive cipher bits information to backend server."
    ::= {slbCurSslCfgSSLPolEntry  7 }


slbCurSslCfgSSLPolPassInfoHeadBitsFlag OBJECT-TYPE
    SYNTAX   INTEGER
    MAX-ACCESS  read-only
    STATUS  current
    DESCRIPTION
        "Cipher bits information to backend servers enabled."
    ::= {slbCurSslCfgSSLPolEntry  8 }


slbCurSslCfgSSLPolPassInfoFrontend OBJECT-TYPE
    SYNTAX   INTEGER
    MAX-ACCESS  read-only
    STATUS  current
    DESCRIPTION
        "Enable/Disable add Front-End-Https: on header."
    ::= {slbCurSslCfgSSLPolEntry  9 }

slbCurSslCfgSSLPolCipherName  OBJECT-TYPE
    SYNTAX  INTEGER 
    MAX-ACCESS  read-only
    STATUS  current
    DESCRIPTION
        "Cipher name for SSL."
    ::= {slbCurSslCfgSSLPolEntry  10 }

slbCurSslCfgSSLPolCipherUserdef  OBJECT-TYPE
    SYNTAX RadwareLongDisplayString (SIZE (0..900))
    MAX-ACCESS  read-only
    STATUS  current
    DESCRIPTION
        "Cipher-suite allowed for SSL."
    ::= {slbCurSslCfgSSLPolEntry  11 }

slbCurSslCfgSSLPolIntermcaChainName  OBJECT-TYPE
    SYNTAX   DisplayString
    MAX-ACCESS  read-only
    STATUS  current
    DESCRIPTION
        "Intermediate CA certificate chain name."
    ::= {slbCurSslCfgSSLPolEntry  12 }

slbCurSslCfgSSLPolIntermcaChainType  OBJECT-TYPE
    SYNTAX   DisplayString
    MAX-ACCESS  read-only
    STATUS  current
    DESCRIPTION
        "Intermediate CA certificate chain type certificate=cert,Group=group,None=empty string."
    ::= {slbCurSslCfgSSLPolEntry  13 }

slbCurSslCfgSSLPolBecipher  OBJECT-TYPE
    SYNTAX  INTEGER{
	low(0),
        medium(1),
        high(2),
	user-defined(3),
	user-defined-expert(4),
        unsupported(2147483647)
        }
    MAX-ACCESS  read-only
    STATUS  current
    DESCRIPTION
        "Allowed cipher-suites in backend SSL [0-low, 1-midium, 2-high, 3-user-defined, 4-user-defined-expert] ."
    ::= {slbCurSslCfgSSLPolEntry  14 }

slbCurSslCfgSSLPolAuthpol  OBJECT-TYPE
    SYNTAX   DisplayString
    MAX-ACCESS  read-only
    STATUS  current
    DESCRIPTION
        "Client authentication policy."
    ::= {slbCurSslCfgSSLPolEntry  15 }

slbCurSslCfgSSLPolConvuri  OBJECT-TYPE
    SYNTAX   DisplayString
    MAX-ACCESS  read-only
    STATUS  current
    DESCRIPTION
        "Host regex for HTTP redirection conversion."
    ::= {slbCurSslCfgSSLPolEntry  16 }

slbCurSslCfgSSLPolBessl  OBJECT-TYPE
    SYNTAX  INTEGER{
        enabled(1),
        disabled(2),
        request(3),
        handshake(4),
        unsupported(2147483647)
        }
    MAX-ACCESS  read-only
    STATUS  current
    DESCRIPTION
        "Enable/Disable backend SSL encryption."
    ::= {slbCurSslCfgSSLPolEntry  17 }

slbCurSslCfgSSLPolConvert  OBJECT-TYPE
    SYNTAX  INTEGER {
        enabled(1),
        disabled(2),
        unsupported(2147483647)
        }
    MAX-ACCESS  read-only
    STATUS  current
    DESCRIPTION
        "Enable/Disable HTTP redirection conversion."
    ::= {slbCurSslCfgSSLPolEntry  18 }

slbCurSslCfgSSLPolAdminStatus OBJECT-TYPE
    SYNTAX  INTEGER {
        enabled(1),
        disabled(2),
        unsupported(2147483647)
        }
    MAX-ACCESS  read-only
    STATUS  current
    DESCRIPTION
        "Enable or disable ssl policy."
    ::= {slbCurSslCfgSSLPolEntry 19 }


slbCurSslCfgSSLPolPassInfoComply OBJECT-TYPE
    SYNTAX   INTEGER
    MAX-ACCESS  read-only
    STATUS  current
    DESCRIPTION
        "Enable/Disable X-SSL header compatible with 2424SSL headers."
    ::= {slbCurSslCfgSSLPolEntry  20 }

slbCurSslCfgSSLPolFessl  OBJECT-TYPE
    SYNTAX  INTEGER{
        enabled(1),
        disabled(2),
        request(3),
        handshake(4),
        unsupported(2147483647)
        }
    MAX-ACCESS  read-only
    STATUS  current
    DESCRIPTION
        "Set frontend SSL encryption mode."
    ::= {slbCurSslCfgSSLPolEntry  21 }

slbCurSslCfgSSLPolFESslv3Version OBJECT-TYPE
    SYNTAX  INTEGER {
        enabled(1),
        disabled(2),
        unsupported(2147483647)
        }
    MAX-ACCESS  read-only
    STATUS  current
    DESCRIPTION
        "Enable or disable frontend sslv3."
    ::= {slbCurSslCfgSSLPolEntry 22 }

slbCurSslCfgSSLPolFETls10Version OBJECT-TYPE
    SYNTAX  INTEGER {
        enabled(1),
        disabled(2),
        unsupported(2147483647)
        }
    MAX-ACCESS  read-only
    STATUS  current
    DESCRIPTION
        "Enable or disable frontend tls1_0."
    ::= {slbCurSslCfgSSLPolEntry 23 }

slbCurSslCfgSSLPolFETls11Version OBJECT-TYPE
    SYNTAX  INTEGER {
        enabled(1),
        disabled(2),
        unsupported(2147483647)
        }
    MAX-ACCESS  read-only
    STATUS  current
    DESCRIPTION
        "Enable or disable frontend tls1_1."
    ::= {slbCurSslCfgSSLPolEntry 24 }

slbCurSslCfgSSLPolBESslv3Version OBJECT-TYPE
    SYNTAX  INTEGER {
        enabled(1),
        disabled(2),
        unsupported(2147483647)
        }
    MAX-ACCESS  read-only
    STATUS  current
    DESCRIPTION
        "Enable or disable backend sslv3."
    ::= {slbCurSslCfgSSLPolEntry 25 }

slbCurSslCfgSSLPolBETls10Version OBJECT-TYPE
    SYNTAX  INTEGER {
        enabled(1),
        disabled(2),
        unsupported(2147483647)
        }
    MAX-ACCESS  read-only
    STATUS  current
    DESCRIPTION
        "Enable or disable backend tls10."
    ::= {slbCurSslCfgSSLPolEntry 26 }

slbCurSslCfgSSLPolBETls11Version OBJECT-TYPE
    SYNTAX  INTEGER {
        enabled(1),
        disabled(2),
        unsupported(2147483647)
        }
    MAX-ACCESS  read-only
    STATUS  current
    DESCRIPTION
        "Enable or disable backend tls11."
    ::= {slbCurSslCfgSSLPolEntry 27 }

slbCurSslCfgSSLPolFETls12Version OBJECT-TYPE
    SYNTAX  INTEGER {
        enabled(1),
        disabled(2),
        unsupported(2147483647)
        }
    MAX-ACCESS  read-only
    STATUS  current
    DESCRIPTION
        "Enable or disable frontend tls1_2."
    ::= {slbCurSslCfgSSLPolEntry 28 }

slbCurSslCfgSSLPolBETls12Version OBJECT-TYPE
    SYNTAX  INTEGER {
        enabled(1),
        disabled(2),
        unsupported(2147483647)
        }
    MAX-ACCESS  read-only
    STATUS  current
    DESCRIPTION
        "Enable or disable backend tls1_2."
    ::= {slbCurSslCfgSSLPolEntry 29 }

slbCurSslCfgSSLPolCipherExpertUserdef OBJECT-TYPE
    SYNTAX  DisplayString
    MAX-ACCESS  read-only
    STATUS  current
    DESCRIPTION
        "Expert-Cipher-suite allowed for SSL."
    ::= {slbCurSslCfgSSLPolEntry  30 }

slbCurSslCfgSSLPolBeCipherUserdef OBJECT-TYPE
    SYNTAX  DisplayString
    MAX-ACCESS  read-only
    STATUS  current
    DESCRIPTION
        "BeCipher-suite allowed for SSL."
    ::= {slbCurSslCfgSSLPolEntry  31 }

slbCurSslCfgSSLPolBeCipherExpertUserdef OBJECT-TYPE
    SYNTAX  DisplayString
    MAX-ACCESS  read-only
    STATUS  current
    DESCRIPTION
        "Expert-BeCipher-suite allowed for SSL."
    ::= {slbCurSslCfgSSLPolEntry  32 }

slbCurSslCfgSSLPolBEClientCertName  OBJECT-TYPE
    SYNTAX   DisplayString
    MAX-ACCESS  read-only
    STATUS  current
    DESCRIPTION
        "Backend client certificate name."
    ::= {slbCurSslCfgSSLPolEntry  33 }

slbCurSslCfgSSLPolBETrustedCAcertName  OBJECT-TYPE
    SYNTAX   DisplayString
    MAX-ACCESS  read-only
    STATUS  current
    DESCRIPTION
        "Backend trusted CA certificate chain name."
    ::= {slbCurSslCfgSSLPolEntry  34 }

slbCurSslCfgSSLPolBETrustedCAcertType  OBJECT-TYPE
    SYNTAX   DisplayString
    MAX-ACCESS  read-only
    STATUS  current
    DESCRIPTION
        "Backend trusted CA certificate chain type certificate=cert,Group=group,None=empty string."
    ::= {slbCurSslCfgSSLPolEntry  35 }

slbCurSslCfgSSLPolSecreneg OBJECT-TYPE
    SYNTAX  DisplayString
    MAX-ACCESS  read-only
    STATUS  current
    DESCRIPTION
        "Secure Renegotiation Frontend and Backend SSL."
    ::= {slbCurSslCfgSSLPolEntry 36 }

slbCurSslCfgSSLPolDHkey OBJECT-TYPE
    SYNTAX INTEGER {
        keySize1024(1),
        keySize2048(2),
        unsupported(2147483647)
	}
    MAX-ACCESS  read-only
    STATUS  current
    DESCRIPTION
        "num of bits in Diffie Helman key."
    ::= {slbCurSslCfgSSLPolEntry 37 }

slbCurSslCfgSSLPolBEAuthpol  OBJECT-TYPE
    SYNTAX   DisplayString
    MAX-ACCESS  read-only
    STATUS  current
    DESCRIPTION
        "backend authentication policy."
    ::= {slbCurSslCfgSSLPolEntry  38 }

slbCurSslCfgSSLPolHwoffldFeRsa OBJECT-TYPE
    SYNTAX  INTEGER {
        enabled(1),
        disabled(2),
        unsupported(2147483647)
        }
    MAX-ACCESS  read-only
    STATUS  current
    DESCRIPTION
        "Disable/Enable HW offload for RSA algorithm."
    ::= {slbCurSslCfgSSLPolEntry 39 }

slbCurSslCfgSSLPolHwoffldFeDh OBJECT-TYPE
    SYNTAX  INTEGER {
        enabled(1),
        disabled(2),
        unsupported(2147483647)
        }
    MAX-ACCESS  read-only
    STATUS  current
    DESCRIPTION
        "Disable/Enable HW offload for DH algorithm."
    ::= {slbCurSslCfgSSLPolEntry 40 }

slbCurSslCfgSSLPolHwoffldFeEc OBJECT-TYPE
    SYNTAX  INTEGER {
        enabled(1),
        disabled(2),
        unsupported(2147483647)
        }
    MAX-ACCESS  read-only
    STATUS  current
    DESCRIPTION
        "Disable/Enable HW offload for EC algorithm."
    ::= {slbCurSslCfgSSLPolEntry 41 }

slbCurSslCfgSSLPolHwoffldFeBulk OBJECT-TYPE
    SYNTAX  INTEGER {
        enabled(1),
        disabled(2),
        unsupported(2147483647)
        }
    MAX-ACCESS  read-only
    STATUS  current
    DESCRIPTION
        "Disable/Enable HW offload for bulk encryption ciphers."
    ::= {slbCurSslCfgSSLPolEntry 42 }

slbCurSslCfgSSLPolHwoffldFePkey OBJECT-TYPE
    SYNTAX  INTEGER {
        enabled(1),
        disabled(2),
        unsupported(2147483647)
        }
    MAX-ACCESS  read-only
    STATUS  current
    DESCRIPTION
        "Disable/Enable HW offload for PKEY functionality."
    ::= {slbCurSslCfgSSLPolEntry 43 }

slbCurSslCfgSSLPolHwoffldFeFeatures OBJECT-TYPE
    SYNTAX  INTEGER {
        enabled(1),
        disabled(2),
        unsupported(2147483647)
        }
    MAX-ACCESS  read-only
    STATUS  current
    DESCRIPTION
        "Disable/Enable HW offload Features."
    ::= {slbCurSslCfgSSLPolEntry 44 }

slbCurSslCfgSSLPolHwoffldBeRsa OBJECT-TYPE
    SYNTAX  INTEGER {
        enabled(1),
        disabled(2),
        unsupported(2147483647)
        }
    MAX-ACCESS  read-only
    STATUS  current
    DESCRIPTION
        "Disable/Enable HW offload for RSA algorithm."
    ::= {slbCurSslCfgSSLPolEntry 45 }

slbCurSslCfgSSLPolHwoffldBeDh OBJECT-TYPE
    SYNTAX  INTEGER {
        enabled(1),
        disabled(2),
        unsupported(2147483647)
        }
    MAX-ACCESS  read-only
    STATUS  current
    DESCRIPTION
        "Disable/Enable HW offload for DH algorithm."
    ::= {slbCurSslCfgSSLPolEntry 46 }

slbCurSslCfgSSLPolHwoffldBeEc OBJECT-TYPE
    SYNTAX  INTEGER {
        enabled(1),
        disabled(2),
        unsupported(2147483647)
        }
    MAX-ACCESS  read-only
    STATUS  current
    DESCRIPTION
        "Disable/Enable HW offload for EC algorithm."
    ::= {slbCurSslCfgSSLPolEntry 47 }

slbCurSslCfgSSLPolHwoffldBeBulk OBJECT-TYPE
    SYNTAX  INTEGER {
        enabled(1),
        disabled(2),
        unsupported(2147483647)
        }
    MAX-ACCESS  read-only
    STATUS  current
    DESCRIPTION
        "Disable/Enable HW offload for bulk encryption ciphers."
    ::= {slbCurSslCfgSSLPolEntry 48 }

slbCurSslCfgSSLPolHwoffldBePkey OBJECT-TYPE
    SYNTAX  INTEGER {
        enabled(1),
        disabled(2),
        unsupported(2147483647)
        }
    MAX-ACCESS  read-only
    STATUS  current
    DESCRIPTION
        "Disable/Enable HW offload for PKEY functionality."
    ::= {slbCurSslCfgSSLPolEntry 49 }

slbCurSslCfgSSLPolHwoffldBeFeatures OBJECT-TYPE
    SYNTAX  INTEGER {
        enabled(1),
        disabled(2),
        unsupported(2147483647)
        }
    MAX-ACCESS  read-only
    STATUS  current
    DESCRIPTION
        "Disable/Enable HW offload Features."
    ::= {slbCurSslCfgSSLPolEntry 50 }

slbCurSslCfgSSLPolBesni  OBJECT-TYPE
    SYNTAX  INTEGER {
        enabled(1),
        disabled(2),
        unsupported(2147483647)
        }
    MAX-ACCESS  read-only
    STATUS  current
    DESCRIPTION
        "Enable/Disable to include SNI."
    ::= {slbCurSslCfgSSLPolEntry  51 }
    
    slbCurSslCfgSSLPolFETls13Version OBJECT-TYPE
    SYNTAX  INTEGER {
        enabled(1),
        disabled(2),
        unsupported(2147483647)
        }
    MAX-ACCESS  read-only
    STATUS  current
    DESCRIPTION
        "Enable or disable frontend tls1_3."
    ::= {slbCurSslCfgSSLPolEntry 52 }

slbCurSslCfgSSLPolBETls13Version OBJECT-TYPE
    SYNTAX  INTEGER {
        enabled(1),
        disabled(2),
        unsupported(2147483647)
        }
    MAX-ACCESS  read-only
    STATUS  current
    DESCRIPTION
        "Enable or disable backend tls1_3."
    ::= {slbCurSslCfgSSLPolEntry 53 }    

slbCurSslCfgSSLPol0RTTFEData OBJECT-TYPE
    SYNTAX  INTEGER (0..131072)
    MAX-ACCESS  read-only
    STATUS  current
    DESCRIPTION
        "Set maximum allowed early data on frontend connection"
    ::= {slbCurSslCfgSSLPolEntry 54 }

slbCurSslCfgSSLPolFeReuseState OBJECT-TYPE
    SYNTAX  INTEGER {
        enabled(1),
        disabled(2),
        inherit(3),
        unsupported(2147483647)
        }
    MAX-ACCESS  read-only
    STATUS  current
    DESCRIPTION
        "Set Frontend SSL reuse state"
    ::= {slbCurSslCfgSSLPolEntry 55 }    

slbCurSslCfgSSLPolBeReuseState OBJECT-TYPE
    SYNTAX  INTEGER {
        enabled(1),
        disabled(2),
        inherit(3),
        unsupported(2147483647)
        }
    MAX-ACCESS  read-only
    STATUS  current
    DESCRIPTION
        "Set Backend SSL reuse state"
    ::= {slbCurSslCfgSSLPolEntry 56 }    

slbCurSslCfgSSLPolBeReuseSrcMatch OBJECT-TYPE
    SYNTAX  INTEGER {
        enabled(1),
        disabled(2),
        unsupported(2147483647)
        }
    MAX-ACCESS  read-only
    STATUS  current
    DESCRIPTION
        "Enable/disable reuse for same client only"
    ::= {slbCurSslCfgSSLPolEntry 57 }    

slbCurSslCfgSSLPolBeReuseTicket OBJECT-TYPE
    SYNTAX  INTEGER {
        enabled(1),
        disabled(2),
        unsupported(2147483647)
        }
    MAX-ACCESS  read-only
    STATUS  current
    DESCRIPTION
        "Enable/disable TLS 1.2 session ticket"
    ::= {slbCurSslCfgSSLPolEntry 58 }

slbCurSslCfgSSLPolFeReuseTicket OBJECT-TYPE
    SYNTAX  INTEGER {
        enabled(1),
        disabled(2),
        unsupported(2147483647)
        }
    MAX-ACCESS  read-only
    STATUS  current
    DESCRIPTION
        "Enable/disable TLS 1.2 session ticket"
    ::= {slbCurSslCfgSSLPolEntry 59 }

slbNewSslCfgSSLAdminStatus OBJECT-TYPE
    SYNTAX  INTEGER {
        enabled(1),
        disabled(2),
        unsupported(2147483647)
        }
    MAX-ACCESS  read-create
    STATUS  current
    DESCRIPTION
        "Status (enable/disable) of SSL policy.
         Note:This mib is not supported for VX instance of Virtualization."
    ::= { sslCfg 2 }


slbNewSslCfgSSLPolTable OBJECT-TYPE
    SYNTAX  SEQUENCE OF SlbNewSslCfgSSLPolEntry
    MAX-ACCESS  not-accessible
    STATUS  current
    DESCRIPTION
        "The table for configuring ssl  policy.
         Note:This mib is not supported for VX instance of Virtualization."
    ::= { sslPol 7 }

slbNewSslCfgSSLPolEntry OBJECT-TYPE
    SYNTAX  SlbNewSslCfgSSLPolEntry
    MAX-ACCESS  not-accessible
    STATUS  current
    DESCRIPTION
        "A row in the ssl policy table."
    INDEX   { slbNewSslCfgSSLPolNameIdIndex }
    ::= { slbNewSslCfgSSLPolTable 1 }

SlbNewSslCfgSSLPolEntry ::= SEQUENCE {
    slbNewSslCfgSSLPolNameIdIndex             DisplayString,
    slbNewSslCfgSSLPolName                    DisplayString,
    slbNewSslCfgSSLPolPassInfoCipherName      DisplayString,
    slbNewSslCfgSSLPolPassInfoCipherFlag      INTEGER,
    slbNewSslCfgSSLPolPassInfoVersionName     DisplayString,
    slbNewSslCfgSSLPolPassInfoVersionFlag     INTEGER,
    slbNewSslCfgSSLPolPassInfoHeadBitsName    DisplayString,
    slbNewSslCfgSSLPolPassInfoHeadBitsFlag    INTEGER,
    slbNewSslCfgSSLPolPassInfoFrontend        INTEGER,
    slbNewSslCfgSSLPolCipherName              INTEGER,
    slbNewSslCfgSSLPolCipherUserdef           RadwareLongDisplayString,
    slbNewSslCfgSSLPolCipherExpertUserdef     DisplayString,
    slbNewSslCfgSSLPolIntermcaChainName       DisplayString,
    slbNewSslCfgSSLPolIntermcaChainType       DisplayString,
    slbNewSslCfgSSLPolBecipher                INTEGER,
    slbNewSslCfgSSLPolBeCipherUserdef         DisplayString,
    slbNewSslCfgSSLPolBeCipherExpertUserdef   DisplayString,
    slbNewSslCfgSSLPolAuthpol                 DisplayString,
    slbNewSslCfgSSLPolConvuri                 DisplayString,
    slbNewSslCfgSSLPolBessl                   INTEGER,
    slbNewSslCfgSSLPolBEClientCertName        DisplayString,
    slbNewSslCfgSSLPolBETrustedCAcertName     DisplayString,
    slbNewSslCfgSSLPolBETrustedCAcertType     DisplayString,
    slbNewSslCfgSSLPolConvert                 INTEGER,
    slbNewSslCfgSSLPolAdminStatus             INTEGER,
    slbNewSslCfgSSLPolDel                     INTEGER,
    slbNewSslCfgSSLPolPassInfoComply          INTEGER,
    slbNewSslCfgSSLPolFessl                   INTEGER,
    slbNewSslCfgSSLPolFESslv3Version          INTEGER,
    slbNewSslCfgSSLPolFETls10Version          INTEGER,
    slbNewSslCfgSSLPolFETls11Version          INTEGER,
    slbNewSslCfgSSLPolBESslv3Version          INTEGER,
    slbNewSslCfgSSLPolBETls10Version          INTEGER,
    slbNewSslCfgSSLPolBETls11Version          INTEGER,
    slbNewSslCfgSSLPolFETls12Version          INTEGER,
    slbNewSslCfgSSLPolBETls12Version          INTEGER,
    slbNewSslCfgSSLPolSecreneg                DisplayString,
    slbNewSslCfgSSLPolDHkey                   INTEGER,
    slbNewSslCfgSSLPolBEAuthpol               DisplayString,
    slbNewSslCfgSSLPolHwoffldFeRsa            INTEGER,
    slbNewSslCfgSSLPolHwoffldFeDh             INTEGER,
    slbNewSslCfgSSLPolHwoffldFeEc             INTEGER,
    slbNewSslCfgSSLPolHwoffldFeBulk           INTEGER,
    slbNewSslCfgSSLPolHwoffldFePkey           INTEGER,
    slbNewSslCfgSSLPolHwoffldFeFeatures       INTEGER,
    slbNewSslCfgSSLPolHwoffldBeRsa            INTEGER,
    slbNewSslCfgSSLPolHwoffldBeDh             INTEGER,
    slbNewSslCfgSSLPolHwoffldBeEc             INTEGER,
    slbNewSslCfgSSLPolHwoffldBeBulk           INTEGER,
    slbNewSslCfgSSLPolHwoffldBePkey           INTEGER,
    slbNewSslCfgSSLPolHwoffldBeFeatures       INTEGER,
    slbNewSslCfgSSLPolBesni                   INTEGER,
    slbNewSslCfgSSLPolFETls13Version          INTEGER,
    slbNewSslCfgSSLPolBETls13Version          INTEGER,
    slbNewSslCfgSSLPol0RTTFEData              INTEGER,
    slbNewSslCfgSSLPolFeReuseState            INTEGER,
    slbNewSslCfgSSLPolBeReuseState            INTEGER,
    slbNewSslCfgSSLPolBeReuseSrcMatch         INTEGER,
    slbNewSslCfgSSLPolBeReuseTicket           INTEGER,
    slbNewSslCfgSSLPolFeReuseTicket           INTEGER
    }

slbNewSslCfgSSLPolNameIdIndex OBJECT-TYPE
    SYNTAX   DisplayString
    MAX-ACCESS  read-create
    STATUS  current
    DESCRIPTION
        "The SSL policy name(key id) as an index."
    ::= {slbNewSslCfgSSLPolEntry  1 }

slbNewSslCfgSSLPolName  OBJECT-TYPE
    SYNTAX   DisplayString
    MAX-ACCESS  read-create
    STATUS  current
    DESCRIPTION
        "SSL policy name,length of the string should be 32 characters."
    ::= {slbNewSslCfgSSLPolEntry  2 }


slbNewSslCfgSSLPolPassInfoCipherName OBJECT-TYPE
    SYNTAX  DisplayString 
    MAX-ACCESS  read-create
    STATUS  current
    DESCRIPTION
        "The SSL cipher-suite header name."
    ::= {slbNewSslCfgSSLPolEntry  3 }

slbNewSslCfgSSLPolPassInfoCipherFlag OBJECT-TYPE
    SYNTAX  INTEGER {
        enabled(1),
        disabled(2),
        unsupported(2147483647)
        }
    MAX-ACCESS  read-create
    STATUS  current
    DESCRIPTION
        "Enable/Disable cipher-suite information to backend servers."
    ::= {slbNewSslCfgSSLPolEntry  4 }

slbNewSslCfgSSLPolPassInfoVersionName OBJECT-TYPE
    SYNTAX  DisplayString
    MAX-ACCESS  read-create
    STATUS  current
    DESCRIPTION
        "SSL version header name."
    ::= {slbNewSslCfgSSLPolEntry  5 }

slbNewSslCfgSSLPolPassInfoVersionFlag OBJECT-TYPE
    SYNTAX  INTEGER {
        enabled(1),
        disabled(2),
        unsupported(2147483647)
        }
    MAX-ACCESS  read-create
    STATUS  current
    DESCRIPTION
        "Enable/Disable  SSL version information to backend servers."
    ::= {slbNewSslCfgSSLPolEntry  6 }


slbNewSslCfgSSLPolPassInfoHeadBitsName OBJECT-TYPE
    SYNTAX  DisplayString 
    MAX-ACCESS  read-create
    STATUS  current
    DESCRIPTION
        "The passive cipher bits information to backend server."
    ::= {slbNewSslCfgSSLPolEntry  7 }


slbNewSslCfgSSLPolPassInfoHeadBitsFlag OBJECT-TYPE
    SYNTAX  INTEGER {
        enabled(1),
        disabled(2),
        unsupported(2147483647)
        }
    MAX-ACCESS  read-create
    STATUS  current
    DESCRIPTION
        "Enable/Disable Cipher bits information to backend servers."
    ::= {slbNewSslCfgSSLPolEntry  8 }


slbNewSslCfgSSLPolPassInfoFrontend OBJECT-TYPE
    SYNTAX  INTEGER {
        enabled(1),
        disabled(2),
        unsupported(2147483647)
        }
    MAX-ACCESS  read-create
    STATUS  current
    DESCRIPTION
        "Enable/Disable add Front-End-Https: on header."
    ::= {slbNewSslCfgSSLPolEntry 9 }


slbNewSslCfgSSLPolCipherName  OBJECT-TYPE
    SYNTAX  INTEGER {
	    rsa(0),
	    all(1),
	    all-non-null-ciphers(2),
	    sslv3(3),
	    tlsv1(4),
	    tlsv1-2(5),
	    export(6),
	    low(7),
	    medium(8),
	    high(9),
	    rsa-rc4-128-md5(10),
	    rsa-rc4-128-sha1(11),
	    rsa-des-sha1(12),
	    rsa-3des-sha1(13),
	    rsa-aes-128-sha1(14),
	    rsa-aes-256-sha1(15),
	    pci-dss-compliance(16),
	    user-defined(17),
	    user-defined-expert(18),
	    main(19),
	    http2(20),
            unsupported(2147483647)
	    }
    MAX-ACCESS  read-create
    STATUS  current
    DESCRIPTION
        "Allowed cipher-suites in frontend SSL."
    ::= {slbNewSslCfgSSLPolEntry  10 }

slbNewSslCfgSSLPolCipherUserdef  OBJECT-TYPE
    SYNTAX  RadwareLongDisplayString (SIZE (0..900))
    MAX-ACCESS  read-create
    STATUS  current
    DESCRIPTION
        "Cipher-suite allowed for SSL."
    ::= {slbNewSslCfgSSLPolEntry  11 }


slbNewSslCfgSSLPolIntermcaChainName  OBJECT-TYPE
    SYNTAX   DisplayString
    MAX-ACCESS  read-create
    STATUS  current
    DESCRIPTION
        "Intermediate CA certificate chain name."
    ::= {slbNewSslCfgSSLPolEntry  12 }

slbNewSslCfgSSLPolIntermcaChainType  OBJECT-TYPE
    SYNTAX   DisplayString
    MAX-ACCESS  read-create
    STATUS  current
    DESCRIPTION
        "Intermediate CA certificate chain type certificate=cert,Group=group,None=empty string."
    ::= {slbNewSslCfgSSLPolEntry  13 }


slbNewSslCfgSSLPolBecipher  OBJECT-TYPE
    SYNTAX INTEGER{
        low(0),
        medium(1),
        high(2),
        user-defined(3),
        user-defined-expert(4),
        main(5),
        unsupported(2147483647)
        }
    MAX-ACCESS  read-create
    STATUS  current
    DESCRIPTION
        "Allowed cipher-suites in backend SSL."
    ::= {slbNewSslCfgSSLPolEntry  14 }

slbNewSslCfgSSLPolAuthpol  OBJECT-TYPE
    SYNTAX   DisplayString
    MAX-ACCESS  read-create
    STATUS  current
    DESCRIPTION
        "Client authentication policy."
    ::= {slbNewSslCfgSSLPolEntry  15 }

slbNewSslCfgSSLPolConvuri  OBJECT-TYPE
    SYNTAX   DisplayString
    MAX-ACCESS  read-create
    STATUS  current
    DESCRIPTION
        "Host regex for HTTP redirection conversion."
    ::= {slbNewSslCfgSSLPolEntry  16 }

slbNewSslCfgSSLPolBessl  OBJECT-TYPE
    SYNTAX  INTEGER{
        enabled(1),
        disabled(2),
        request(3),
        handshake(4),
        unsupported(2147483647)
        }
    MAX-ACCESS  read-create
    STATUS  current
    DESCRIPTION
        "Enable/Disable backend SSL encryption."
    ::= {slbNewSslCfgSSLPolEntry  17 }

slbNewSslCfgSSLPolConvert  OBJECT-TYPE
    SYNTAX  INTEGER{
        enabled(1),
        disabled(2),
        unsupported(2147483647)
        }
    MAX-ACCESS  read-create
    STATUS  current
    DESCRIPTION
        "Enable/Disable HTTP redirection conversion."
    ::= {slbNewSslCfgSSLPolEntry  18 }

slbNewSslCfgSSLPolAdminStatus OBJECT-TYPE
    SYNTAX  INTEGER {
        enabled(1),
        disabled(2),
        unsupported(2147483647)
        }
    MAX-ACCESS  read-create
    STATUS  current
    DESCRIPTION
        "Enable or disable ssl policy."
    ::= {slbNewSslCfgSSLPolEntry 19 }

slbNewSslCfgSSLPolDel  OBJECT-TYPE
    SYNTAX  INTEGER {
        other(1),
        delete(2),
        unsupported(2147483647)
    }
    MAX-ACCESS  read-create
    STATUS  current
    DESCRIPTION
        "Delete SSL policy."
    ::= {slbNewSslCfgSSLPolEntry  20 }


slbNewSslCfgSSLPolPassInfoComply OBJECT-TYPE
    SYNTAX  INTEGER {
        enabled(1),
        disabled(2),
        unsupported(2147483647)
        }
    MAX-ACCESS  read-create
    STATUS  current
    DESCRIPTION
        "Enable/Disable X-SSL header compatible with 2424SSL headers."
    ::= {slbNewSslCfgSSLPolEntry 21 }

slbNewSslCfgSSLPolFessl  OBJECT-TYPE
    SYNTAX  INTEGER{
        enabled(1),
        disabled(2),
        request(3),
        handshake(4),
        unsupported(2147483647)
        }
    MAX-ACCESS  read-create
    STATUS  current
    DESCRIPTION
        "Set frontend SSL encryption mode, default value is enabled."
    ::= {slbNewSslCfgSSLPolEntry  22 }

slbNewSslCfgSSLPolFESslv3Version OBJECT-TYPE
    SYNTAX  INTEGER {
        enabled(1),
        disabled(2),
        unsupported(2147483647)
        }
    MAX-ACCESS  read-create
    STATUS  current
    DESCRIPTION
        "Enable or disable frontend sslv3."
    ::= {slbNewSslCfgSSLPolEntry 23 }

slbNewSslCfgSSLPolFETls10Version OBJECT-TYPE
    SYNTAX  INTEGER {
        enabled(1),
        disabled(2),
        unsupported(2147483647)
        }
    MAX-ACCESS  read-create
    STATUS  current
    DESCRIPTION
        "Enable or disable frontend tls1_0."
    ::= {slbNewSslCfgSSLPolEntry 24 }

slbNewSslCfgSSLPolFETls11Version OBJECT-TYPE
    SYNTAX  INTEGER {
        enabled(1),
        disabled(2),
        unsupported(2147483647)
        }
    MAX-ACCESS  read-create
    STATUS  current
    DESCRIPTION
        "Enable or disable frontend tls1_1."
    ::= {slbNewSslCfgSSLPolEntry 25 }

slbNewSslCfgSSLPolBESslv3Version OBJECT-TYPE
    SYNTAX  INTEGER {
        enabled(1),
        disabled(2),
        unsupported(2147483647)
        }
    MAX-ACCESS  read-create
    STATUS  current
    DESCRIPTION
        "Enable or disable backend sslv3."
    ::= {slbNewSslCfgSSLPolEntry 26 }

slbNewSslCfgSSLPolBETls10Version OBJECT-TYPE
    SYNTAX  INTEGER {
        enabled(1),
        disabled(2),
        unsupported(2147483647)
        }
    MAX-ACCESS  read-create
    STATUS  current
    DESCRIPTION
        "Enable or disable backend tls1_0."
    ::= {slbNewSslCfgSSLPolEntry 27 }

slbNewSslCfgSSLPolBETls11Version OBJECT-TYPE
    SYNTAX  INTEGER {
        enabled(1),
        disabled(2),
        unsupported(2147483647)
        }
    MAX-ACCESS  read-create
    STATUS  current
    DESCRIPTION
        "Enable or disable backend tls1_1."
    ::= {slbNewSslCfgSSLPolEntry 28 }

slbNewSslCfgSSLPolFETls12Version OBJECT-TYPE
    SYNTAX  INTEGER {
        enabled(1),
        disabled(2),
        unsupported(2147483647)
        }
    MAX-ACCESS  read-create
    STATUS  current
    DESCRIPTION
        "Enable or disable frontend tls1_2."
    ::= {slbNewSslCfgSSLPolEntry 29 }

slbNewSslCfgSSLPolBETls12Version OBJECT-TYPE
    SYNTAX  INTEGER {
        enabled(1),
        disabled(2),
        unsupported(2147483647)
        }
    MAX-ACCESS  read-create
    STATUS  current
    DESCRIPTION
        "Enable or disable backend tls1_2."
    ::= {slbNewSslCfgSSLPolEntry 30 }

slbNewSslCfgSSLPolCipherExpertUserdef  OBJECT-TYPE
    SYNTAX  DisplayString(SIZE(0..255))
    MAX-ACCESS  read-create
    STATUS  current
    DESCRIPTION
        "Expert-Cipher-suite allowed for SSL."
    ::= {slbNewSslCfgSSLPolEntry  31 }

slbNewSslCfgSSLPolBeCipherUserdef OBJECT-TYPE
    SYNTAX  DisplayString
    MAX-ACCESS  read-create
    STATUS  current
    DESCRIPTION
        "BeCipher-suite allowed for SSL."
    ::= {slbNewSslCfgSSLPolEntry  32 }

slbNewSslCfgSSLPolBeCipherExpertUserdef OBJECT-TYPE
    SYNTAX  DisplayString
    MAX-ACCESS  read-create
    STATUS  current
    DESCRIPTION
        "Expert-BeCipher-suite allowed for SSL."
    ::= {slbNewSslCfgSSLPolEntry  33 }

slbNewSslCfgSSLPolBEClientCertName  OBJECT-TYPE
    SYNTAX   DisplayString
    MAX-ACCESS  read-create
    STATUS  current
    DESCRIPTION
        "Backend client certificate name."
    ::= {slbNewSslCfgSSLPolEntry  34 }

slbNewSslCfgSSLPolBETrustedCAcertName  OBJECT-TYPE
    SYNTAX   DisplayString
    MAX-ACCESS  read-create
    STATUS  current
    DESCRIPTION
        "Backend trusted CA certificate chain name."
    ::= {slbNewSslCfgSSLPolEntry  35 }

slbNewSslCfgSSLPolBETrustedCAcertType  OBJECT-TYPE
    SYNTAX   DisplayString
    MAX-ACCESS  read-create
    STATUS  current
    DESCRIPTION
        "Backend trusted CA certificate chain type certificate=cert,Group=group,None=empty string."
    ::= {slbNewSslCfgSSLPolEntry  36 }

slbNewSslCfgSSLPolSecreneg OBJECT-TYPE
    SYNTAX  DisplayString
    MAX-ACCESS  read-create
    STATUS  current
    DESCRIPTION
        "Secure Renegotiation Frontend and Backend SSL."
    ::= {slbNewSslCfgSSLPolEntry 37 }

slbNewSslCfgSSLPolDHkey OBJECT-TYPE
    SYNTAX INTEGER {
        keySize1024(1),
        keySize2048(2),
        unsupported(2147483647)
	}
    MAX-ACCESS  read-create
    STATUS  current
    DESCRIPTION
        "num of bits in Diffie Helman key."
    ::= {slbNewSslCfgSSLPolEntry 38 }

slbNewSslCfgSSLPolBEAuthpol  OBJECT-TYPE
    SYNTAX   DisplayString
    MAX-ACCESS  read-create
    STATUS  current
    DESCRIPTION
        "Backend authentication policy."
    ::= {slbNewSslCfgSSLPolEntry  39 }

slbNewSslCfgSSLPolHwoffldFeRsa OBJECT-TYPE
    SYNTAX  INTEGER {
        enabled(1),
        disabled(2),
        unsupported(2147483647)
        }
    MAX-ACCESS  read-create
    STATUS  current
    DESCRIPTION
        "Disable/Enable HW offload for RSA algorithm."
    ::= {slbNewSslCfgSSLPolEntry 40 }
    
slbNewSslCfgSSLPolHwoffldFeDh OBJECT-TYPE
    SYNTAX  INTEGER {
        enabled(1),
        disabled(2),
        unsupported(2147483647)
        }
    MAX-ACCESS  read-create
    STATUS  current
    DESCRIPTION
        "Disable/Enable HW offload for DH algorithm."
    ::= {slbNewSslCfgSSLPolEntry 41 }
    
slbNewSslCfgSSLPolHwoffldFeEc OBJECT-TYPE
    SYNTAX  INTEGER {
        enabled(1),
        disabled(2),
        unsupported(2147483647)
        }
    MAX-ACCESS  read-create
    STATUS  current
    DESCRIPTION
        "Disable/Enable HW offload for EC algorithm."
    ::= {slbNewSslCfgSSLPolEntry 42 }
    
slbNewSslCfgSSLPolHwoffldFeBulk OBJECT-TYPE
    SYNTAX  INTEGER {
        enabled(1),
        disabled(2),
        unsupported(2147483647)
        }
    MAX-ACCESS  read-create
    STATUS  current
    DESCRIPTION
        "Disable/Enable HW offload for bulk encryption ciphers."
    ::= {slbNewSslCfgSSLPolEntry 43 }
    
slbNewSslCfgSSLPolHwoffldFePkey OBJECT-TYPE
    SYNTAX  INTEGER {
        enabled(1),
        disabled(2),
        unsupported(2147483647)
        }
    MAX-ACCESS  read-create
    STATUS  current
    DESCRIPTION
        "Disable/Enable HW offload for PKEY functionality."
    ::= {slbNewSslCfgSSLPolEntry 44 }
    
slbNewSslCfgSSLPolHwoffldFeFeatures OBJECT-TYPE
    SYNTAX  INTEGER {
        enabled(1),
        disabled(2),
        unsupported(2147483647)
        }
    MAX-ACCESS  read-create
    STATUS  current
    DESCRIPTION
        "Disable/Enable HW offload Features."
    ::= {slbNewSslCfgSSLPolEntry 45 }
    
slbNewSslCfgSSLPolHwoffldBeRsa OBJECT-TYPE
    SYNTAX  INTEGER {
        enabled(1),
        disabled(2),
        unsupported(2147483647)
        }
    MAX-ACCESS  read-create
    STATUS  current
    DESCRIPTION
        "Disable/Enable HW offload for RSA algorithm."
    ::= {slbNewSslCfgSSLPolEntry 46 }
    
slbNewSslCfgSSLPolHwoffldBeDh OBJECT-TYPE
    SYNTAX  INTEGER {
        enabled(1),
        disabled(2),
        unsupported(2147483647)
        }
    MAX-ACCESS  read-create
    STATUS  current
    DESCRIPTION
        "Disable/Enable HW offload for DH algorithm."
    ::= {slbNewSslCfgSSLPolEntry 47 }
    
slbNewSslCfgSSLPolHwoffldBeEc OBJECT-TYPE
    SYNTAX  INTEGER {
        enabled(1),
        disabled(2),
        unsupported(2147483647)
        }
    MAX-ACCESS  read-create
    STATUS  current
    DESCRIPTION
        "Disable/Enable HW offload for EC algorithm."
    ::= {slbNewSslCfgSSLPolEntry 48 }
    
slbNewSslCfgSSLPolHwoffldBeBulk OBJECT-TYPE
    SYNTAX  INTEGER {
        enabled(1),
        disabled(2),
        unsupported(2147483647)
        }
    MAX-ACCESS  read-create
    STATUS  current
    DESCRIPTION
        "Disable/Enable HW offload for bulk encryption ciphers."
    ::= {slbNewSslCfgSSLPolEntry 49 }

slbNewSslCfgSSLPolHwoffldBePkey OBJECT-TYPE
    SYNTAX  INTEGER {
        enabled(1),
        disabled(2),
        unsupported(2147483647)
        }
    MAX-ACCESS  read-create
    STATUS  current
    DESCRIPTION
        "Disable/Enable HW offload for PKEY functionality."
    ::= {slbNewSslCfgSSLPolEntry 50 }
    
slbNewSslCfgSSLPolHwoffldBeFeatures OBJECT-TYPE
    SYNTAX  INTEGER {
        enabled(1),
        disabled(2),
        unsupported(2147483647)
        }
    MAX-ACCESS  read-create
    STATUS  current
    DESCRIPTION
        "Disable/Enable HW offload Features."
    ::= {slbNewSslCfgSSLPolEntry 51 }

slbNewSslCfgSSLPolBesni  OBJECT-TYPE
    SYNTAX  INTEGER{
        enabled(1),
        disabled(2),
        unsupported(2147483647)
        }
    MAX-ACCESS  read-create
    STATUS  current
    DESCRIPTION
        "Enable/Disable to include SNI."
    ::= {slbNewSslCfgSSLPolEntry  52 }
    
slbNewSslCfgSSLPolFETls13Version OBJECT-TYPE
    SYNTAX  INTEGER {
        enabled(1),
        disabled(2),
        unsupported(2147483647)
        }
    MAX-ACCESS  read-create
    STATUS  current
    DESCRIPTION
        "Enable or disable frontend tls1_3."
    ::= {slbNewSslCfgSSLPolEntry 53 }

slbNewSslCfgSSLPolBETls13Version OBJECT-TYPE
    SYNTAX  INTEGER {
        enabled(1),
        disabled(2),
        unsupported(2147483647)
        }
    MAX-ACCESS  read-create
    STATUS  current
    DESCRIPTION
        "Enable or disable backend tls1_3."
    ::= {slbNewSslCfgSSLPolEntry 54 }   
    
slbNewSslCfgSSLPol0RTTFEData OBJECT-TYPE
    SYNTAX  INTEGER (0..131072)
    MAX-ACCESS  read-create
    STATUS  current
    DESCRIPTION
        "Set maximum allowed early data on frontend connection"
    ::= {slbNewSslCfgSSLPolEntry 55 }

slbNewSslCfgSSLPolFeReuseState OBJECT-TYPE
    SYNTAX  INTEGER {
        enabled(1),
        disabled(2),
        inherit(3),
        unsupported(2147483647)
        }
    MAX-ACCESS  read-create
    STATUS  current
    DESCRIPTION
        "Set Frontend SSL reuse state"
    ::= {slbNewSslCfgSSLPolEntry 56 }    

slbNewSslCfgSSLPolBeReuseState OBJECT-TYPE
    SYNTAX  INTEGER {
        enabled(1),
        disabled(2),
        inherit(3),
        unsupported(2147483647)
        }
    MAX-ACCESS  read-create
    STATUS  current
    DESCRIPTION
        "Set Backend SSL reuse state"
    ::= {slbNewSslCfgSSLPolEntry 57 }    

slbNewSslCfgSSLPolBeReuseSrcMatch OBJECT-TYPE
    SYNTAX  INTEGER {
        enabled(1),
        disabled(2),
        unsupported(2147483647)
        }
    MAX-ACCESS  read-create
    STATUS  current
    DESCRIPTION
        "Enable/disable reuse for same client only"
    ::= {slbNewSslCfgSSLPolEntry 58 }    

slbNewSslCfgSSLPolBeReuseTicket OBJECT-TYPE
    SYNTAX  INTEGER {
        enabled(1),
        disabled(2),
        unsupported(2147483647)
        }
    MAX-ACCESS  read-create
    STATUS  current
    DESCRIPTION
        "Enable/disable TLS 1.2 session ticket"
    ::= {slbNewSslCfgSSLPolEntry 59 }

slbNewSslCfgSSLPolFeReuseTicket OBJECT-TYPE
    SYNTAX  INTEGER {
        enabled(1),
        disabled(2),
        unsupported(2147483647)
        }
    MAX-ACCESS  read-create
    STATUS  current
    DESCRIPTION
        "Enable/disable TLS 1.2 session ticket"
    ::= {slbNewSslCfgSSLPolEntry 60 }

slbCurSslCfgAuthPolTable OBJECT-TYPE
    SYNTAX  SEQUENCE OF SlbCurSslCfgAuthPolEntry
    MAX-ACCESS  not-accessible
    STATUS  current
    DESCRIPTION
        "The table for configuring Client Authentication  policy.
         Note:This mib is not supported for VX instance of Virtualization."
    ::= { authPol 1 }

slbCurSslCfgAuthPolEntry OBJECT-TYPE
    SYNTAX  SlbCurSslCfgAuthPolEntry
    MAX-ACCESS  not-accessible
    STATUS  current
    DESCRIPTION
        "A row in the Client Authentication policy table."
    INDEX   { slbCurSslCfgAuthPolNameIdIndex }
    ::= { slbCurSslCfgAuthPolTable 1 }

SlbCurSslCfgAuthPolEntry ::= SEQUENCE {
    slbCurSslCfgAuthPolNameIdIndex           DisplayString,
    slbCurSslCfgAuthPolName                  DisplayString,
    slbCurSslCfgAuthPolValidityMethod        INTEGER,
    slbCurSslCfgAuthPolValidityStaturi       DisplayString,
    slbCurSslCfgAuthPolValidityUriprior      INTEGER,
    slbCurSslCfgAuthPolValidityCachtime      INTEGER,
    slbCurSslCfgAuthPolValidityTimedev       INTEGER,
    slbCurSslCfgAuthPolValidityAlgorthmName  DisplayString,
    slbCurSslCfgAuthPolValidityVchain        INTEGER,
    slbCurSslCfgAuthPolValiditySecure        INTEGER,
    slbCurSslCfgAuthPolPassinfoVersionName   DisplayString,
    slbCurSslCfgAuthPolPassinfoVersionFlag   INTEGER,
    slbCurSslCfgAuthPolPassinfoSerialName    DisplayString,
    slbCurSslCfgAuthPolPassinfoSerialFlag    INTEGER,
    slbCurSslCfgAuthPolPassinfoAlgoName      DisplayString,
    slbCurSslCfgAuthPolPassinfoAlgoFlag      INTEGER,
    slbCurSslCfgAuthPolPassinfoIssuerName    DisplayString,
    slbCurSslCfgAuthPolPassinfoIssuerFlag    INTEGER,
    slbCurSslCfgAuthPolPassinfoNbeforeName   DisplayString,
    slbCurSslCfgAuthPolPassinfoNbeforeFlag   INTEGER,
    slbCurSslCfgAuthPolPassinfoNafterName    DisplayString,
    slbCurSslCfgAuthPolPassinfoNafterFlag    INTEGER,
    slbCurSslCfgAuthPolPassinfoSubjectName   DisplayString,
    slbCurSslCfgAuthPolPassinfoSubjectFlag   INTEGER,
    slbCurSslCfgAuthPolPassinfoKeytypeName   DisplayString,
    slbCurSslCfgAuthPolPassinfoKeytypeFlag   INTEGER,
    slbCurSslCfgAuthPolPassinfoMd5Name       DisplayString,
    slbCurSslCfgAuthPolPassinfoMd5Flag       INTEGER,
    slbCurSslCfgAuthPolPassinfoCertName      DisplayString,
    slbCurSslCfgAuthPolPassinfoCertFormat    INTEGER,
    slbCurSslCfgAuthPolPassinfoCertFlag      INTEGER,
    slbCurSslCfgAuthPolPassinfoCharset       INTEGER,
    slbCurSslCfgAuthPolTrustcaChainName      DisplayString,
    slbCurSslCfgAuthPolTrustcaChainType      DisplayString,
    slbCurSslCfgAuthPolCadepth               INTEGER,
    slbCurSslCfgAuthPolCaverify              INTEGER,
    slbCurSslCfgAuthPolFailurl               DisplayString,
    slbCurSslCfgAuthPolAdminStatus           INTEGER,
    slbCurSslCfgAuthPolPassinfoComp2424      INTEGER,
    slbCurSslCfgAuthPolValidityCrlFile       DisplayString,
    slbCurSslCfgAuthPolValidityCdpGroup      DisplayString,
    slbCurSslCfgAuthPolValidityCdpGracetime  INTEGER,
    slbCurSslCfgAuthPolValidityCdpInterval   INTEGER,
    slbCurSslCfgAuthPolValidityCdpPreference INTEGER,
    slbCurSslCfgAuthPolClientcaReqChainName  DisplayString,
    slbCurSslCfgAuthPolClientcaReqChainType  DisplayString,
    slbCurSslCfgAuthPolType                  INTEGER,
    slbCurSslCfgAuthPolSerCertExp            INTEGER,
    slbCurSslCfgAuthPolSerCertMis            INTEGER,
    slbCurSslCfgAuthPolSerCertUntrust        INTEGER,
    slbCurSslCfgAuthPolIssuerNamesOrder      INTEGER,
    slbCurSslCfgAuthPolSubjectNamesOrder     INTEGER,
    slbCurSslCfgAuthPolValidityOcspMode      INTEGER,
    slbCurSslCfgAuthPolValidityStaplinguri   DisplayString,
    slbCurSslCfgAuthPolValidityStaplingUriprior      INTEGER,
    slbCurSslCfgAuthPolValidityStatSecUri       DisplayString,
    slbCurSslCfgAuthPolValidityStaplingSecUri   DisplayString,
    slbCurSslCfgAuthPolValidityOcspRetries   INTEGER
    }

slbCurSslCfgAuthPolNameIdIndex  OBJECT-TYPE
    SYNTAX   DisplayString (SIZE(0..128))
    MAX-ACCESS  read-only
    STATUS  current
    DESCRIPTION
        "The Auth policy name(key id) as an index."
    ::= {slbCurSslCfgAuthPolEntry  1 }


slbCurSslCfgAuthPolName  OBJECT-TYPE
    SYNTAX   DisplayString (SIZE(0..128))
    MAX-ACCESS  read-only
    STATUS  current
    DESCRIPTION
        "Auth policy name."
    ::= {slbCurSslCfgAuthPolEntry  2 }

slbCurSslCfgAuthPolValidityMethod OBJECT-TYPE
    SYNTAX  INTEGER 
    MAX-ACCESS  read-only
    STATUS  current
    DESCRIPTION
        "Certificate validation check method."
    ::= {slbCurSslCfgAuthPolEntry  3 }

slbCurSslCfgAuthPolValidityStaturi OBJECT-TYPE
    SYNTAX   DisplayString (SIZE(0..255))
    MAX-ACCESS  read-only
    STATUS  current
    DESCRIPTION
        "Static URI for OCSP validation requests."
    ::= {slbCurSslCfgAuthPolEntry  4 }

slbCurSslCfgAuthPolValidityUriprior OBJECT-TYPE
    SYNTAX  INTEGER {
        clientcert(1),
        staticuri(2),
        unsupported(2147483647)
        }
    MAX-ACCESS  read-only
    STATUS  current
    DESCRIPTION
        "OCSP URI priority."
    ::= {slbCurSslCfgAuthPolEntry  5 }

slbCurSslCfgAuthPolValidityCachtime OBJECT-TYPE
    SYNTAX  INTEGER
    MAX-ACCESS  read-only
    STATUS  current
    DESCRIPTION
        "OCSP response cache time."
    ::= {slbCurSslCfgAuthPolEntry  6 }

slbCurSslCfgAuthPolValidityTimedev OBJECT-TYPE
    SYNTAX INTEGER
    MAX-ACCESS  read-only
    STATUS  current
    DESCRIPTION
        "OCSP response time deviation."
    ::= {slbCurSslCfgAuthPolEntry  7 }

slbCurSslCfgAuthPolValidityAlgorthmName OBJECT-TYPE
    SYNTAX   DisplayString (SIZE(0..32))
    MAX-ACCESS  read-only
    STATUS  current
    DESCRIPTION
        "Allowed signing algorithm for the OCSP response[all, md5, sha1, sha256, sha384, sha512]."
    ::= {slbCurSslCfgAuthPolEntry  8 }


slbCurSslCfgAuthPolValidityVchain OBJECT-TYPE
    SYNTAX  INTEGER {
        enabled(1),
        disabled(2),
        unsupported(2147483647)
        }
    MAX-ACCESS  read-only
    STATUS  current
    DESCRIPTION
        "Enable/Disable validating every CA certificate in the CA chain."
    ::= {slbCurSslCfgAuthPolEntry  9 }

slbCurSslCfgAuthPolValiditySecure OBJECT-TYPE
    SYNTAX  INTEGER {
        enabled(1),
        disabled(2),
        unsupported(2147483647)
        }
    MAX-ACCESS  read-only
    STATUS  current
    DESCRIPTION
        "Enable/Disable secure OCSP response by sending random nonce."
    ::= {slbCurSslCfgAuthPolEntry  10 }

slbCurSslCfgAuthPolPassinfoVersionName OBJECT-TYPE
    SYNTAX   DisplayString (SIZE(0..255))
    MAX-ACCESS  read-only
    STATUS  current
    DESCRIPTION
        "Certificate version header."
    ::= {slbCurSslCfgAuthPolEntry  11 }

slbCurSslCfgAuthPolPassinfoVersionFlag OBJECT-TYPE
    SYNTAX  INTEGER
    MAX-ACCESS  read-only
    STATUS  current
    DESCRIPTION
        "Pass certificate version information to backend server."
    ::= {slbCurSslCfgAuthPolEntry  12 }

slbCurSslCfgAuthPolPassinfoSerialName OBJECT-TYPE
    SYNTAX   DisplayString (SIZE(0..255))
    MAX-ACCESS  read-only
    STATUS  current
    DESCRIPTION
        "Certificate serial-number header ."
    ::= {slbCurSslCfgAuthPolEntry  13 }

slbCurSslCfgAuthPolPassinfoSerialFlag OBJECT-TYPE
    SYNTAX  INTEGER 
    MAX-ACCESS  read-only
    STATUS  current
    DESCRIPTION
        "Pass certificate serial-number to backend server."
    ::= {slbCurSslCfgAuthPolEntry  14 }

slbCurSslCfgAuthPolPassinfoAlgoName OBJECT-TYPE
    SYNTAX   DisplayString (SIZE(0..255))
    MAX-ACCESS  read-only
    STATUS  current
    DESCRIPTION
        "Certificate signature algorithm header name."
    ::= {slbCurSslCfgAuthPolEntry  15 }

slbCurSslCfgAuthPolPassinfoAlgoFlag OBJECT-TYPE
    SYNTAX  INTEGER 
    MAX-ACCESS  read-only
    STATUS  current
    DESCRIPTION
        "Pass certificate Signature Algorithm to backend server"
    ::= {slbCurSslCfgAuthPolEntry  16 }

slbCurSslCfgAuthPolPassinfoIssuerName OBJECT-TYPE
    SYNTAX   DisplayString (SIZE(0..255))
    MAX-ACCESS  read-only
    STATUS  current
    DESCRIPTION
        "Certificate issuer header."
    ::= {slbCurSslCfgAuthPolEntry  17 }

slbCurSslCfgAuthPolPassinfoIssuerFlag OBJECT-TYPE
    SYNTAX  INTEGER 
    MAX-ACCESS  read-only
    STATUS  current
    DESCRIPTION
        "Pass certificate issuer information to backend server"
    ::= {slbCurSslCfgAuthPolEntry  18 }

slbCurSslCfgAuthPolPassinfoNbeforeName OBJECT-TYPE
    SYNTAX   DisplayString (SIZE(0..255))
    MAX-ACCESS  read-only
    STATUS  current
    DESCRIPTION
        "Certificate 'Not Before Validity Dates' header."
    ::= {slbCurSslCfgAuthPolEntry  19 }

slbCurSslCfgAuthPolPassinfoNbeforeFlag OBJECT-TYPE
    SYNTAX  INTEGER 
    MAX-ACCESS  read-only
    STATUS  current
    DESCRIPTION
        "Pass certificate 'Not Before' Validity Date to backend server"
    ::= {slbCurSslCfgAuthPolEntry  20 }

slbCurSslCfgAuthPolPassinfoNafterName OBJECT-TYPE
    SYNTAX DisplayString (SIZE(0..255))
    MAX-ACCESS  read-only
    STATUS  current
    DESCRIPTION
        "Certificate 'Not After Validity Dates' header."
    ::= {slbCurSslCfgAuthPolEntry  21 }

slbCurSslCfgAuthPolPassinfoNafterFlag OBJECT-TYPE
    SYNTAX  INTEGER 
    MAX-ACCESS  read-only
    STATUS  current
    DESCRIPTION
        "Pass certificate 'Not After' Validity Date to backend server"
    ::= {slbCurSslCfgAuthPolEntry  22 }

slbCurSslCfgAuthPolPassinfoSubjectName OBJECT-TYPE
    SYNTAX   DisplayString (SIZE(0..255))
    MAX-ACCESS  read-only
    STATUS  current
    DESCRIPTION
        "Certificate subject header name."
    ::= {slbCurSslCfgAuthPolEntry  23 }

slbCurSslCfgAuthPolPassinfoSubjectFlag OBJECT-TYPE
    SYNTAX  INTEGER
    MAX-ACCESS  read-only
    STATUS  current
    DESCRIPTION
        "Pass certificate subject to backend server"
    ::= {slbCurSslCfgAuthPolEntry  24 }

slbCurSslCfgAuthPolPassinfoKeytypeName OBJECT-TYPE
    SYNTAX   DisplayString (SIZE(0..255))
    MAX-ACCESS  read-only
    STATUS  current
    DESCRIPTION
        "Certificate Public Key Type header."
    ::= {slbCurSslCfgAuthPolEntry  25 }

slbCurSslCfgAuthPolPassinfoKeytypeFlag OBJECT-TYPE
    SYNTAX  INTEGER 
    MAX-ACCESS  read-only
    STATUS  current
    DESCRIPTION
        "Pass certificate Public Key Type information to backend servers"
    ::= {slbCurSslCfgAuthPolEntry  26 }

slbCurSslCfgAuthPolPassinfoMd5Name OBJECT-TYPE
    SYNTAX   DisplayString (SIZE(0..255))
    MAX-ACCESS  read-only
    STATUS  current
    DESCRIPTION
        "Certificate MD5 Hash header."
    ::= {slbCurSslCfgAuthPolEntry  27 }

slbCurSslCfgAuthPolPassinfoMd5Flag OBJECT-TYPE
    SYNTAX  INTEGER 
    MAX-ACCESS  read-only
    STATUS  current
    DESCRIPTION
        "Pass certificate MD5 Hash information to backend servers"
    ::= {slbCurSslCfgAuthPolEntry  28 }

slbCurSslCfgAuthPolPassinfoCertName OBJECT-TYPE
    SYNTAX   DisplayString (SIZE(0..255))
    MAX-ACCESS  read-only
    STATUS  current
    DESCRIPTION
        "Certificate header."
    ::= {slbCurSslCfgAuthPolEntry  29 }

slbCurSslCfgAuthPolPassinfoCertFormat OBJECT-TYPE
    SYNTAX  INTEGER 
    MAX-ACCESS  read-only
    STATUS  current
    DESCRIPTION
        "Certificate Header Lines Format."
    ::= {slbCurSslCfgAuthPolEntry  30 }

slbCurSslCfgAuthPolPassinfoCertFlag OBJECT-TYPE
    SYNTAX  INTEGER
    MAX-ACCESS  read-only
    STATUS  current
    DESCRIPTION
        "Pass certificate information to backend servers"
    ::= {slbCurSslCfgAuthPolEntry  31 }

slbCurSslCfgAuthPolPassinfoCharset OBJECT-TYPE
    SYNTAX  INTEGER  
    MAX-ACCESS  read-only
    STATUS  current
    DESCRIPTION
        "Set the character set to be used for information."
    ::= {slbCurSslCfgAuthPolEntry  32 }

slbCurSslCfgAuthPolTrustcaChainName OBJECT-TYPE
    SYNTAX   DisplayString (SIZE(0..128))
    MAX-ACCESS  read-only
    STATUS  current
    DESCRIPTION
        "Trusted client's CA certificate."
    ::= {slbCurSslCfgAuthPolEntry  33 }

slbCurSslCfgAuthPolTrustcaChainType OBJECT-TYPE
    SYNTAX   DisplayString (SIZE(0..6))
    MAX-ACCESS  read-only
    STATUS  current
    DESCRIPTION
        "Tusted client's CA certificate type certificate=cert,Group=group,None=empty string."
    ::= {slbCurSslCfgAuthPolEntry  34 }

slbCurSslCfgAuthPolCadepth OBJECT-TYPE
    SYNTAX  INTEGER
    MAX-ACCESS  read-only
    STATUS  current
    DESCRIPTION
        "Maximum depth to search the trusted CA in the CA certificate."
    ::= {slbCurSslCfgAuthPolEntry  35 }

slbCurSslCfgAuthPolCaverify OBJECT-TYPE
    SYNTAX  INTEGER
    MAX-ACCESS  read-only
    STATUS  current
    DESCRIPTION
        "Certificate's CA verification level."
    ::= {slbCurSslCfgAuthPolEntry  36 }

slbCurSslCfgAuthPolFailurl OBJECT-TYPE
    SYNTAX   DisplayString (SIZE(0..255))
    MAX-ACCESS  read-only
    STATUS  current
    DESCRIPTION
        "URL for redirection when client authentication fails"
    ::= {slbCurSslCfgAuthPolEntry  37 }

slbCurSslCfgAuthPolAdminStatus  OBJECT-TYPE
    SYNTAX  INTEGER {
        enabled(1),
        disabled(2),
        unsupported(2147483647)
        }
    MAX-ACCESS  read-only
    STATUS  current
    DESCRIPTION
        "Enable or disable Auth policy."
    ::= {slbCurSslCfgAuthPolEntry  38}

slbCurSslCfgAuthPolPassinfoComp2424 OBJECT-TYPE
    SYNTAX  INTEGER{
        enabled(1),
        disabled(2),
        unsupported(2147483647)
        }
    MAX-ACCESS  read-only
    STATUS  current
    DESCRIPTION
        "Enable/Disable the 2424SSL Headers Compliance Mode."
    ::= {slbCurSslCfgAuthPolEntry  39 }
slbCurSslCfgAuthPolValidityCrlFile OBJECT-TYPE
    SYNTAX   DisplayString (SIZE(0..255))
    MAX-ACCESS  read-only
    STATUS  current
    DESCRIPTION
        "File Name for CRL validation requests."
    ::= {slbCurSslCfgAuthPolEntry  40 }

slbCurSslCfgAuthPolValidityCdpGroup OBJECT-TYPE
    SYNTAX   DisplayString (SIZE(0..255))
    MAX-ACCESS  read-only
    STATUS  current
    DESCRIPTION
        "Group for CDP validation requests."
    ::= {slbCurSslCfgAuthPolEntry  41 }    

slbCurSslCfgAuthPolValidityCdpGracetime OBJECT-TYPE
    SYNTAX  INTEGER (0..100000)
    MAX-ACCESS  read-only
    STATUS  current
    DESCRIPTION
        "CDP General grace time."
    ::= {slbCurSslCfgAuthPolEntry  42 }
    
slbCurSslCfgAuthPolValidityCdpInterval OBJECT-TYPE
    SYNTAX  INTEGER (0..720000)
    MAX-ACCESS  read-only
    STATUS  current
    DESCRIPTION
        "CDP update interval."
    ::= {slbCurSslCfgAuthPolEntry  43 }

slbCurSslCfgAuthPolValidityCdpPreference OBJECT-TYPE
    SYNTAX  INTEGER {
        embedded(1),
        userdefined(2),
        unsupported(2147483647)
        }
    MAX-ACCESS  read-only
    STATUS  current
    DESCRIPTION
        "CDP preference."
    ::= {slbCurSslCfgAuthPolEntry  44 }

slbCurSslCfgAuthPolClientcaReqChainName OBJECT-TYPE
    SYNTAX   DisplayString (SIZE(0..128))
    MAX-ACCESS  read-only
    STATUS  current
    DESCRIPTION
        "Client CA for Request certificate or group name."
    ::= {slbCurSslCfgAuthPolEntry  45 }

slbCurSslCfgAuthPolClientcaReqChainType OBJECT-TYPE
    SYNTAX   DisplayString (SIZE(0..8))
    MAX-ACCESS  read-only
    STATUS  current
    DESCRIPTION
        "Client CA for Request type Certificate=cert,Group=group,None=none,Default=default."
    ::= {slbCurSslCfgAuthPolEntry  46 }

slbCurSslCfgAuthPolType OBJECT-TYPE
    SYNTAX  INTEGER
    MAX-ACCESS  read-only
    STATUS  current
    DESCRIPTION
        "Authentication policy type (frontend/backend)."
    ::= {slbCurSslCfgAuthPolEntry  47 }

slbCurSslCfgAuthPolSerCertExp OBJECT-TYPE
    SYNTAX  INTEGER
    MAX-ACCESS  read-only
    STATUS  current
    DESCRIPTION
        "Authentication policy action on expired cert (ignore/reject)."
    ::= {slbCurSslCfgAuthPolEntry  48 }

slbCurSslCfgAuthPolSerCertMis OBJECT-TYPE
    SYNTAX  INTEGER
    MAX-ACCESS  read-only
    STATUS  current
    DESCRIPTION
        "Authentication policy action on mismatch (ignore/reject)."
    ::= {slbCurSslCfgAuthPolEntry  49 }

slbCurSslCfgAuthPolSerCertUntrust OBJECT-TYPE
    SYNTAX  INTEGER
    MAX-ACCESS  read-only
    STATUS  current
    DESCRIPTION
        "Authentication policy action on untrusted (ignore/reject)."
    ::= {slbCurSslCfgAuthPolEntry  50 }
slbCurSslCfgAuthPolIssuerNamesOrder OBJECT-TYPE
    SYNTAX  INTEGER
    MAX-ACCESS  read-only
    STATUS  current
    DESCRIPTION
        "Set the order in which the issuer names will be passed"
    ::= {slbCurSslCfgAuthPolEntry  51 }

slbCurSslCfgAuthPolSubjectNamesOrder OBJECT-TYPE
    SYNTAX  INTEGER 
    MAX-ACCESS  read-only
    STATUS  current
    DESCRIPTION
        "Set the order in which the subject names will be passed"
    ::= {slbCurSslCfgAuthPolEntry  52 }

slbCurSslCfgAuthPolValidityOcspMode OBJECT-TYPE
    SYNTAX INTEGER {
    ocsp(0),
    stapling(1),
    both(2),
    unsupported(2147483647)
    }
    MAX-ACCESS  read-only
    STATUS  current
    DESCRIPTION
        "OCSP mode."
    ::= {slbCurSslCfgAuthPolEntry  53 }

slbCurSslCfgAuthPolValidityStaplinguri OBJECT-TYPE
    SYNTAX   DisplayString (SIZE(0..255))
    MAX-ACCESS  read-only
    STATUS  current
    DESCRIPTION
        "Static URI for OCSP Stapling validation requests."
    ::= {slbCurSslCfgAuthPolEntry  54 }

slbCurSslCfgAuthPolValidityStaplingUriprior OBJECT-TYPE
    SYNTAX  INTEGER {
        clientcert(1),
        staticuri(2),
        unsupported(2147483647)
        }
    MAX-ACCESS  read-only
    STATUS  current
    DESCRIPTION
        "OCSP Stapling URI priority."
    ::= {slbCurSslCfgAuthPolEntry  56 }

slbCurSslCfgAuthPolValidityStatSecUri OBJECT-TYPE
    SYNTAX   DisplayString (SIZE(0..255))
    MAX-ACCESS  read-only
    STATUS  current
    DESCRIPTION
        "Static Secondary URI for OCSP validation requests."
    ::= {slbCurSslCfgAuthPolEntry  57 }

slbCurSslCfgAuthPolValidityStaplingSecUri OBJECT-TYPE
    SYNTAX   DisplayString (SIZE(0..255))
    MAX-ACCESS  read-only
    STATUS  current
    DESCRIPTION
        "Static Secondary URI for OCSP Stapling validation requests."
    ::= {slbCurSslCfgAuthPolEntry  58 }

slbCurSslCfgAuthPolValidityOcspRetries OBJECT-TYPE
    SYNTAX  INTEGER (1..5)
    MAX-ACCESS  read-only
    STATUS  current
    DESCRIPTION
        "Number of retries reaching the OCSP server."
    ::= {slbCurSslCfgAuthPolEntry  59 }

    
slbNewSslCfgAuthPolTable OBJECT-TYPE
    SYNTAX  SEQUENCE OF SlbNewSslCfgAuthPolEntry
    MAX-ACCESS  not-accessible
    STATUS  current
    DESCRIPTION
        "The table for configuring Client Authentication  policy.
         Note:This mib is not supported for VX instance of Virtualization."
    ::= { authPol 3 }

slbNewSslCfgAuthPolEntry OBJECT-TYPE
    SYNTAX  SlbNewSslCfgAuthPolEntry 
    MAX-ACCESS  not-accessible
    STATUS  current
    DESCRIPTION
        "A row in the Client Authentication policy table."
    INDEX   { slbNewSslCfgAuthPolNameIdIndex }
    ::= { slbNewSslCfgAuthPolTable 1 }

SlbNewSslCfgAuthPolEntry ::= SEQUENCE {
    slbNewSslCfgAuthPolNameIdIndex           DisplayString,
    slbNewSslCfgAuthPolName                  DisplayString,
    slbNewSslCfgAuthPolValidityMethod        INTEGER,
    slbNewSslCfgAuthPolValidityStaturi       DisplayString,
    slbNewSslCfgAuthPolValidityUriprior      INTEGER,
    slbNewSslCfgAuthPolValidityCachtime      INTEGER,
    slbNewSslCfgAuthPolValidityTimedev       INTEGER,
    slbNewSslCfgAuthPolValidityAlgorthmName  DisplayString,
    slbNewSslCfgAuthPolValidityVchain        INTEGER,
    slbNewSslCfgAuthPolValiditySecure        INTEGER,
    slbNewSslCfgAuthPolPassinfoVersionName   DisplayString,
    slbNewSslCfgAuthPolPassinfoVersionFlag   INTEGER,
    slbNewSslCfgAuthPolPassinfoSerialName    DisplayString,
    slbNewSslCfgAuthPolPassinfoSerialFlag    INTEGER,
    slbNewSslCfgAuthPolPassinfoAlgoName      DisplayString,
    slbNewSslCfgAuthPolPassinfoAlgoFlag      INTEGER,
    slbNewSslCfgAuthPolPassinfoIssuerName    DisplayString,
    slbNewSslCfgAuthPolPassinfoIssuerFlag    INTEGER,
    slbNewSslCfgAuthPolPassinfoNbeforeName   DisplayString,
    slbNewSslCfgAuthPolPassinfoNbeforeFlag   INTEGER,
    slbNewSslCfgAuthPolPassinfoNafterName    DisplayString,
    slbNewSslCfgAuthPolPassinfoNafterFlag    INTEGER,
    slbNewSslCfgAuthPolPassinfoSubjectName   DisplayString,
    slbNewSslCfgAuthPolPassinfoSubjectFlag   INTEGER,
    slbNewSslCfgAuthPolPassinfoKeytypeName   DisplayString,
    slbNewSslCfgAuthPolPassinfoKeytypeFlag   INTEGER,
    slbNewSslCfgAuthPolPassinfoMd5Name       DisplayString,
    slbNewSslCfgAuthPolPassinfoMd5Flag       INTEGER,
    slbNewSslCfgAuthPolPassinfoCertName      DisplayString,
    slbNewSslCfgAuthPolPassinfoCertFormat    INTEGER,
    slbNewSslCfgAuthPolPassinfoCertFlag      INTEGER,
    slbNewSslCfgAuthPolPassinfoCharset       INTEGER,
    slbNewSslCfgAuthPolTrustcaChainName      DisplayString,
    slbNewSslCfgAuthPolTrustcaChainType      DisplayString,
    slbNewSslCfgAuthPolCadepth               INTEGER,
    slbNewSslCfgAuthPolCaverify              INTEGER,
    slbNewSslCfgAuthPolFailurl               DisplayString,
    slbNewSslCfgAuthPolAdminStatus           INTEGER,
    slbNewSslCfgAuthPolDelete                INTEGER, 
    slbNewSslCfgAuthPolPassinfoComp2424      INTEGER,
    slbNewSslCfgAuthPolValidityCrlFile       DisplayString,
    slbNewSslCfgAuthPolValidityCdpGroup      DisplayString,
    slbNewSslCfgAuthPolValidityCdpGracetime  INTEGER,
    slbNewSslCfgAuthPolValidityCdpInterval   INTEGER,
    slbNewSslCfgAuthPolValidityCdpPreference INTEGER,
    slbNewSslCfgAuthPolClientcaReqChainName  DisplayString,
    slbNewSslCfgAuthPolClientcaReqChainType  DisplayString,
    slbNewSslCfgAuthPolType                  INTEGER,
    slbNewSslCfgAuthPolSerCertExp            INTEGER,
    slbNewSslCfgAuthPolSerCertMis            INTEGER,
    slbNewSslCfgAuthPolSerCertUntrust        INTEGER,
    slbNewSslCfgAuthPolIssuerNamesOrder      INTEGER,
    slbNewSslCfgAuthPolSubjectNamesOrder     INTEGER,
    slbNewSslCfgAuthPolValidityOcspMode      INTEGER,
    slbNewSslCfgAuthPolValidityStaplinguri   DisplayString,
    slbNewSslCfgAuthPolValidityStaplingUriprior      INTEGER,
    slbNewSslCfgAuthPolValidityStatSecUri   DisplayString,
    slbNewSslCfgAuthPolValidityStaplingSecUri   DisplayString,
    slbNewSslCfgAuthPolValidityOcspRetries     INTEGER
    }

slbNewSslCfgAuthPolNameIdIndex  OBJECT-TYPE
    SYNTAX   DisplayString (SIZE(0..128))
    MAX-ACCESS  read-only
    STATUS  current
    DESCRIPTION
        "The Auth policy name(key id) as an index."
    ::= {slbNewSslCfgAuthPolEntry  1 }

slbNewSslCfgAuthPolName  OBJECT-TYPE
    SYNTAX   DisplayString (SIZE(0..128))
    MAX-ACCESS  read-create
    STATUS  current
    DESCRIPTION
        "Auth policy name."
    ::= {slbNewSslCfgAuthPolEntry  2 }

slbNewSslCfgAuthPolValidityMethod OBJECT-TYPE
    SYNTAX INTEGER 
    MAX-ACCESS  read-create
    STATUS  current
    DESCRIPTION
        "Certificate validation check method."
    ::= {slbNewSslCfgAuthPolEntry  3 }

slbNewSslCfgAuthPolValidityStaturi OBJECT-TYPE
    SYNTAX   DisplayString (SIZE(0..255))
    MAX-ACCESS  read-create
    STATUS  current
    DESCRIPTION
        "Static URI for OCSP validation requests."
    ::= {slbNewSslCfgAuthPolEntry  4 }

slbNewSslCfgAuthPolValidityUriprior OBJECT-TYPE
    SYNTAX  INTEGER {
        clientcert(1),
        staticuri(2),
        unsupported(2147483647)
        }
    MAX-ACCESS  read-create
    STATUS  current
    DESCRIPTION
        "OCSP URI priority."
    ::= {slbNewSslCfgAuthPolEntry  5 }

slbNewSslCfgAuthPolValidityCachtime OBJECT-TYPE
    SYNTAX  INTEGER (0..180000)
    MAX-ACCESS  read-create
    STATUS  current
    DESCRIPTION
        "OCSP response cache time."
    ::= {slbNewSslCfgAuthPolEntry  6 }

slbNewSslCfgAuthPolValidityTimedev OBJECT-TYPE
    SYNTAX  INTEGER (0..2678400)
    MAX-ACCESS  read-create
    STATUS  current
    DESCRIPTION
        "OCSP response time deviation."
    ::= {slbNewSslCfgAuthPolEntry  7 }

slbNewSslCfgAuthPolValidityAlgorthmName OBJECT-TYPE
    SYNTAX   DisplayString (SIZE(0..32))
    MAX-ACCESS  read-create
    STATUS  current
    DESCRIPTION
        "Allowed signing algorithm for the OCSP response [all, md5, sha1, sha256, sha384, sha512]."
    ::= {slbNewSslCfgAuthPolEntry  8 }

slbNewSslCfgAuthPolValidityVchain OBJECT-TYPE
    SYNTAX  INTEGER {
        enabled(1),
        disabled(2),
        unsupported(2147483647)
        }
    MAX-ACCESS  read-create
    STATUS  current
    DESCRIPTION
        "Enable/Disable validating every CA certificate in the CA chain."
    ::= {slbNewSslCfgAuthPolEntry  9 }

slbNewSslCfgAuthPolValiditySecure OBJECT-TYPE
    SYNTAX  INTEGER {
        enabled(1),
        disabled(2),
        unsupported(2147483647)
        }
    MAX-ACCESS  read-create
    STATUS  current
    DESCRIPTION
        "Enable/Disable secure OCSP response by sending random nonce."
    ::= {slbNewSslCfgAuthPolEntry  10 }

slbNewSslCfgAuthPolPassinfoVersionName OBJECT-TYPE
    SYNTAX   DisplayString (SIZE(0..255))
    MAX-ACCESS  read-create
    STATUS  current
    DESCRIPTION
        "Certificate version header."
    ::= {slbNewSslCfgAuthPolEntry  11 }

slbNewSslCfgAuthPolPassinfoVersionFlag OBJECT-TYPE
    SYNTAX  INTEGER {
        enabled(1),
        disabled(2),
        unsupported(2147483647)
        }
    MAX-ACCESS  read-create
    STATUS  current
    DESCRIPTION
         "Pass certificate version information to backend server."
    ::= {slbNewSslCfgAuthPolEntry  12 }


slbNewSslCfgAuthPolPassinfoSerialName OBJECT-TYPE
    SYNTAX   DisplayString (SIZE(0..255))
    MAX-ACCESS  read-create
    STATUS  current
    DESCRIPTION
        "Certificate serial-number header."
    ::= {slbNewSslCfgAuthPolEntry  13 }

slbNewSslCfgAuthPolPassinfoSerialFlag OBJECT-TYPE
    SYNTAX  INTEGER {
        enabled(1),
        disabled(2),
        unsupported(2147483647)
        }
    MAX-ACCESS  read-create
    STATUS  current
    DESCRIPTION
        "Pass certificate serial-number to backend server"
    ::= {slbNewSslCfgAuthPolEntry  14 }

slbNewSslCfgAuthPolPassinfoAlgoName OBJECT-TYPE
    SYNTAX   DisplayString (SIZE(0..255))
    MAX-ACCESS  read-create
    STATUS  current
    DESCRIPTION
        "Certificate signature algorithm header name."
    ::= {slbNewSslCfgAuthPolEntry  15 }

slbNewSslCfgAuthPolPassinfoAlgoFlag OBJECT-TYPE
    SYNTAX  INTEGER {
        enabled(1),
        disabled(2),
        unsupported(2147483647)
        }
    MAX-ACCESS  read-create
    STATUS  current
    DESCRIPTION
        "Pass certificate Signature Algorithm to backend server"
    ::= {slbNewSslCfgAuthPolEntry  16 }

slbNewSslCfgAuthPolPassinfoIssuerName OBJECT-TYPE
    SYNTAX   DisplayString (SIZE(0..255))
    MAX-ACCESS  read-create
    STATUS  current
    DESCRIPTION
        "Certificate issuer header."
    ::= {slbNewSslCfgAuthPolEntry  17 }

slbNewSslCfgAuthPolPassinfoIssuerFlag OBJECT-TYPE
    SYNTAX  INTEGER {
        enabled(1),
        disabled(2),
        unsupported(2147483647)
        }
    MAX-ACCESS  read-create
    STATUS  current
    DESCRIPTION
        "Pass certificate issuer information to backend server"
    ::= {slbNewSslCfgAuthPolEntry  18 }

slbNewSslCfgAuthPolPassinfoNbeforeName OBJECT-TYPE
    SYNTAX   DisplayString (SIZE(0..255))
    MAX-ACCESS  read-create
    STATUS  current
    DESCRIPTION
        "Certificate 'Not Before Validity Dates' header."
    ::= {slbNewSslCfgAuthPolEntry  19 }

slbNewSslCfgAuthPolPassinfoNbeforeFlag OBJECT-TYPE
    SYNTAX  INTEGER {
        enabled(1),
        disabled(2),
        unsupported(2147483647)
        }
    MAX-ACCESS  read-create
    STATUS  current
    DESCRIPTION
        "Pass certificate 'Not Before' Validity Date to backend server"
    ::= {slbNewSslCfgAuthPolEntry  20 }

slbNewSslCfgAuthPolPassinfoNafterName OBJECT-TYPE
    SYNTAX   DisplayString (SIZE(0..255))
    MAX-ACCESS  read-create
    STATUS  current
    DESCRIPTION
        "Certificate 'Not After Validity Dates' header."
    ::= {slbNewSslCfgAuthPolEntry  21 }

slbNewSslCfgAuthPolPassinfoNafterFlag OBJECT-TYPE
    SYNTAX  INTEGER {
        enabled(1),
        disabled(2),
        unsupported(2147483647)
        }
    MAX-ACCESS  read-create
    STATUS  current
    DESCRIPTION
        "Pass certificate 'Not After' Validity Date to backend server"
    ::= {slbNewSslCfgAuthPolEntry  22 }

slbNewSslCfgAuthPolPassinfoSubjectName OBJECT-TYPE
    SYNTAX   DisplayString (SIZE(0..255))
    MAX-ACCESS  read-create
    STATUS  current
    DESCRIPTION
        "Certificate subject header name."
    ::= {slbNewSslCfgAuthPolEntry  23 }

slbNewSslCfgAuthPolPassinfoSubjectFlag OBJECT-TYPE
    SYNTAX  INTEGER {
        enabled(1),
        disabled(2),
        unsupported(2147483647)
        }
    MAX-ACCESS  read-create
    STATUS  current
    DESCRIPTION
        "Pass certificate subject to backend server"
    ::= {slbNewSslCfgAuthPolEntry  24 }


slbNewSslCfgAuthPolPassinfoKeytypeName OBJECT-TYPE
    SYNTAX   DisplayString (SIZE(0..255))
    MAX-ACCESS  read-create
    STATUS  current
    DESCRIPTION
        "Certificate Public Key Type header."
    ::= {slbNewSslCfgAuthPolEntry  25 }

slbNewSslCfgAuthPolPassinfoKeytypeFlag OBJECT-TYPE
    SYNTAX  INTEGER {
        enabled(1),
        disabled(2),
        unsupported(2147483647)
        }
    MAX-ACCESS  read-create
    STATUS  current
    DESCRIPTION
        "Pass certificate Public Key Type information to backend servers"
    ::= {slbNewSslCfgAuthPolEntry  26 }

slbNewSslCfgAuthPolPassinfoMd5Name OBJECT-TYPE
    SYNTAX   DisplayString (SIZE(0..255))
    MAX-ACCESS  read-create
    STATUS  current
    DESCRIPTION
        "Certificate MD5 Hash header."
    ::= {slbNewSslCfgAuthPolEntry  27 }

slbNewSslCfgAuthPolPassinfoMd5Flag OBJECT-TYPE
    SYNTAX  INTEGER {
        enabled(1),
        disabled(2),
        unsupported(2147483647)
        }
    MAX-ACCESS  read-create
    STATUS  current
    DESCRIPTION
        "Pass certificate MD5 Hash information to backend servers"
    ::= {slbNewSslCfgAuthPolEntry  28 }

slbNewSslCfgAuthPolPassinfoCertName OBJECT-TYPE
    SYNTAX   DisplayString (SIZE(0..255))
    MAX-ACCESS  read-create
    STATUS  current
    DESCRIPTION
        "Certificate header."
    ::= {slbNewSslCfgAuthPolEntry  29 }

slbNewSslCfgAuthPolPassinfoCertFormat OBJECT-TYPE
    SYNTAX INTEGER 
    MAX-ACCESS  read-create
    STATUS  current
    DESCRIPTION
        "Certificate Header Lines Format."
    ::= {slbNewSslCfgAuthPolEntry  30 }

slbNewSslCfgAuthPolPassinfoCertFlag OBJECT-TYPE
    SYNTAX  INTEGER {
        enabled(1),
        disabled(2),
        unsupported(2147483647)
        }
    MAX-ACCESS  read-create
    STATUS  current
    DESCRIPTION
        "Pass certificate information to backend servers"
    ::= {slbNewSslCfgAuthPolEntry  31 }

slbNewSslCfgAuthPolPassinfoCharset OBJECT-TYPE
    SYNTAX  INTEGER
    MAX-ACCESS  read-create
    STATUS  current
    DESCRIPTION
        "Set the character set to be used for information."
    ::= {slbNewSslCfgAuthPolEntry  32 }

slbNewSslCfgAuthPolTrustcaChainName OBJECT-TYPE
    SYNTAX  DisplayString (SIZE(0..128))
    MAX-ACCESS  read-create
    STATUS  current
    DESCRIPTION
        "Trusted client's CA certificate name."
    ::= {slbNewSslCfgAuthPolEntry  33 }

slbNewSslCfgAuthPolTrustcaChainType OBJECT-TYPE
    SYNTAX  DisplayString (SIZE(0..6))
    MAX-ACCESS  read-create
    STATUS  current
    DESCRIPTION
        "Trusted client's CA certificate type certificate=cert,Group=group,None=empty string."
    ::= {slbNewSslCfgAuthPolEntry  34 }

slbNewSslCfgAuthPolCadepth OBJECT-TYPE
    SYNTAX  INTEGER
    MAX-ACCESS  read-create
    STATUS  current
    DESCRIPTION
        "Maximum depth to search the trusted CA in the CA certificate."
    ::= {slbNewSslCfgAuthPolEntry  35 }

slbNewSslCfgAuthPolCaverify OBJECT-TYPE
    SYNTAX  INTEGER 
    MAX-ACCESS  read-create
    STATUS  current
    DESCRIPTION
        "Certificate's CA verification level."
    ::= {slbNewSslCfgAuthPolEntry  36 }

slbNewSslCfgAuthPolFailurl OBJECT-TYPE
    SYNTAX   DisplayString (SIZE(0..255))
    MAX-ACCESS  read-create
    STATUS  current
    DESCRIPTION
        "URL for redirection when client authentication fails"
    ::= {slbNewSslCfgAuthPolEntry  37 }

slbNewSslCfgAuthPolAdminStatus  OBJECT-TYPE
    SYNTAX  INTEGER {
        enabled(1),
        disabled(2),
        unsupported(2147483647)
        }
    MAX-ACCESS  read-create
    STATUS  current
    DESCRIPTION
        "Enable or disable Auth policy."
    ::= {slbNewSslCfgAuthPolEntry  38}

slbNewSslCfgAuthPolDelete OBJECT-TYPE
    SYNTAX  INTEGER {
        other(1),
        delete(2),
        unsupported(2147483647)
    }
    MAX-ACCESS  read-create
    STATUS  current
    DESCRIPTION
        "Delete Client Authentication Policy."
    ::= {slbNewSslCfgAuthPolEntry  39 }


slbNewSslCfgAuthPolPassinfoComp2424 OBJECT-TYPE
    SYNTAX  INTEGER{
        enabled(1),
        disabled(2),
        unsupported(2147483647)
        }
    MAX-ACCESS  read-create
    STATUS  current
    DESCRIPTION
        "Enable/Disable the 2424SSL Headers Compliance Mode."
    ::= {slbNewSslCfgAuthPolEntry  40 }
slbNewSslCfgAuthPolValidityCrlFile OBJECT-TYPE
    SYNTAX   DisplayString (SIZE(0..255))
    MAX-ACCESS  read-create
    STATUS  current
    DESCRIPTION
        "File Name for CRL validation requests."
    ::= {slbNewSslCfgAuthPolEntry  41 }

slbNewSslCfgAuthPolValidityCdpGroup OBJECT-TYPE
    SYNTAX   DisplayString (SIZE(0..255))
    MAX-ACCESS  read-create
    STATUS  current
    DESCRIPTION
        "Group for CDP validation requests."
    ::= {slbNewSslCfgAuthPolEntry  42 }    

slbNewSslCfgAuthPolValidityCdpGracetime OBJECT-TYPE
    SYNTAX  INTEGER (0..100000)
    MAX-ACCESS  read-create
    STATUS  current
    DESCRIPTION
        "CDP General grace time."
    ::= {slbNewSslCfgAuthPolEntry  43 }
    
slbNewSslCfgAuthPolValidityCdpInterval OBJECT-TYPE
    SYNTAX  INTEGER (0..720000)
    MAX-ACCESS  read-create
    STATUS  current
    DESCRIPTION
        "CDP update interval."
    ::= {slbNewSslCfgAuthPolEntry  44 }

slbNewSslCfgAuthPolValidityCdpPreference OBJECT-TYPE
    SYNTAX  INTEGER {
        embedded(1),
        userdefined(2),
        unsupported(2147483647)
        }
    MAX-ACCESS  read-create
    STATUS  current
    DESCRIPTION
        "CDP preference."
    ::= {slbNewSslCfgAuthPolEntry  45 }

slbNewSslCfgAuthPolClientcaReqChainName OBJECT-TYPE
    SYNTAX  DisplayString (SIZE(0..128))
    MAX-ACCESS  read-create
    STATUS  current
    DESCRIPTION
        "Client CA for Request certificate or group name."
    ::= {slbNewSslCfgAuthPolEntry  46 }

slbNewSslCfgAuthPolClientcaReqChainType OBJECT-TYPE
    SYNTAX  DisplayString (SIZE(0..8))
    MAX-ACCESS  read-create
    STATUS  current
    DESCRIPTION
        "Client CA for Request type Certificate=cert,Group=group,None=none,Default=default."
    ::= {slbNewSslCfgAuthPolEntry  47 }

slbNewSslCfgAuthPolType OBJECT-TYPE
    SYNTAX  INTEGER {
        frontend(1),
        backend(2),
        unsupported(2147483647)
        }
    MAX-ACCESS  read-create
    STATUS  current
    DESCRIPTION
        "Authentication policy type (frontend/backend)."
    ::= {slbNewSslCfgAuthPolEntry  48 }

slbNewSslCfgAuthPolSerCertExp OBJECT-TYPE
    SYNTAX  INTEGER {
        ignore(1),
        reject(2),
        unsupported(2147483647)
        }
    MAX-ACCESS  read-create
    STATUS  current
    DESCRIPTION
        "Authentication policy action on expired cert (ignore/reject)."
    ::= {slbNewSslCfgAuthPolEntry  49 }

slbNewSslCfgAuthPolSerCertMis OBJECT-TYPE
    SYNTAX  INTEGER {
        ignore(1),
        reject(2),
        unsupported(2147483647)
        }
    MAX-ACCESS  read-create
    STATUS  current
    DESCRIPTION
        "Authentication policy action on mismatch (ignore/reject)."
    ::= {slbNewSslCfgAuthPolEntry  50 }

slbNewSslCfgAuthPolSerCertUntrust OBJECT-TYPE
    SYNTAX  INTEGER {
        ignore(1),
        reject(2),
        unsupported(2147483647)
        }
    MAX-ACCESS  read-create
    STATUS  current
    DESCRIPTION
        "Authentication policy action on untrusted (ignore/reject)."
    ::= {slbNewSslCfgAuthPolEntry  51 }

slbNewSslCfgAuthPolIssuerNamesOrder OBJECT-TYPE
    SYNTAX  INTEGER {
        regular(0),
        reverse(1),
        unsupported(2147483647)
        }
    MAX-ACCESS  read-create
    STATUS  current
    DESCRIPTION
        "Set the order in which the issuer names will be passed"
    ::= {slbNewSslCfgAuthPolEntry  52 }

slbNewSslCfgAuthPolSubjectNamesOrder OBJECT-TYPE
    SYNTAX  INTEGER {
        regular(0),
        reverse(1),
        unsupported(2147483647)
        }
    MAX-ACCESS  read-create
    STATUS  current
    DESCRIPTION
        "Set the order in which the subject names will be passed"
    ::= {slbNewSslCfgAuthPolEntry  53 }

slbNewSslCfgAuthPolValidityOcspMode OBJECT-TYPE
    SYNTAX INTEGER {
    ocsp(0),
    stapling(1),
    both(2),
    unsupported(2147483647)
    }
    MAX-ACCESS  read-create
    STATUS  current
    DESCRIPTION
        "OCSP mode."
    ::= {slbNewSslCfgAuthPolEntry  54 }

slbNewSslCfgAuthPolValidityStaplinguri OBJECT-TYPE
    SYNTAX   DisplayString (SIZE(0..255))
    MAX-ACCESS  read-create
    STATUS  current
    DESCRIPTION
        "Static URI for OCSP Stapling validation requests."
    ::= {slbNewSslCfgAuthPolEntry  55 }

slbNewSslCfgAuthPolValidityStaplingUriprior OBJECT-TYPE
    SYNTAX  INTEGER {
        clientcert(1),
        staticuri(2),
        unsupported(2147483647)
        }
    MAX-ACCESS  read-create
    STATUS  current
    DESCRIPTION
        "OCSP Stapling URI priority."
    ::= {slbNewSslCfgAuthPolEntry  56 }

slbNewSslCfgAuthPolValidityStatSecUri OBJECT-TYPE
    SYNTAX   DisplayString (SIZE(0..255))
    MAX-ACCESS  read-create
    STATUS  current
    DESCRIPTION
        "Static secondary URI for OCSP validation requests."
    ::= {slbNewSslCfgAuthPolEntry  57 }

slbNewSslCfgAuthPolValidityStaplingSecUri OBJECT-TYPE
    SYNTAX   DisplayString (SIZE(0..255))
    MAX-ACCESS  read-create
    STATUS  current
    DESCRIPTION
        "Static secondary URI for OCSP Stapling validation requests."
    ::= {slbNewSslCfgAuthPolEntry  58 }
    
slbNewSslCfgAuthPolValidityOcspRetries OBJECT-TYPE
    SYNTAX  INTEGER (1..5)
    MAX-ACCESS  read-create
    STATUS  current
    DESCRIPTION
        "Number of retries reaching the OCSP server."
    ::= {slbNewSslCfgAuthPolEntry  59 }
    
    
slbNewSslCfgAuthPolTable2 OBJECT-TYPE
    SYNTAX  SEQUENCE OF SlbNewSslCfgAuthPolTable2Entry
    MAX-ACCESS  not-accessible
    STATUS  current
    DESCRIPTION
        "The table for configuring Client Authentication  policy.
         Note:This mib is not supported for VX instance of Virtualization."
    ::= { authPol 4 }

slbNewSslCfgAuthPolTable2Entry OBJECT-TYPE
    SYNTAX  SlbNewSslCfgAuthPolTable2Entry 
    MAX-ACCESS  not-accessible
    STATUS  current
    DESCRIPTION
        "A row in the Client Authentication policy table."
    INDEX   { slbNewSslCfgAuthPolTable2NameIdIndex }
    ::= { slbNewSslCfgAuthPolTable2 1 }

SlbNewSslCfgAuthPolTable2Entry ::= SEQUENCE {
    slbNewSslCfgAuthPolTable2NameIdIndex           DisplayString,
    slbNewSslCfgAuthPolTable2PassinfoSerialName    DisplayString,
    slbNewSslCfgAuthPolTable2PassinfoSerialFlag    INTEGER,
    slbNewSslCfgAuthPolTable2PassinfoAlgoName      DisplayString,
    slbNewSslCfgAuthPolTable2PassinfoAlgoFlag      INTEGER,
    slbNewSslCfgAuthPolTable2PassinfoIssuerName    DisplayString,
    slbNewSslCfgAuthPolTable2PassinfoIssuerFlag    INTEGER

}


slbNewSslCfgAuthPolTable2NameIdIndex  OBJECT-TYPE
    SYNTAX   DisplayString
    MAX-ACCESS  read-only
    STATUS  current
    DESCRIPTION
        "The Auth policy name(key id) as an index.
         Note:This mib is not supported for VX instance of Virtualization."
    ::= {slbNewSslCfgAuthPolTable2Entry  1 }


slbNewSslCfgAuthPolTable2PassinfoSerialName OBJECT-TYPE
    SYNTAX   DisplayString (SIZE(0..255))
    MAX-ACCESS  read-create
    STATUS  current
    DESCRIPTION
        "Certificate serial-number header."
    ::= {slbNewSslCfgAuthPolTable2Entry  2 }

slbNewSslCfgAuthPolTable2PassinfoSerialFlag OBJECT-TYPE
    SYNTAX  INTEGER {
        enabled(1),
        disabled(2),
        unsupported(2147483647)
        }
    MAX-ACCESS  read-create
    STATUS  current
    DESCRIPTION
        "Pass certificate serial-number to backend server"
    ::= {slbNewSslCfgAuthPolTable2Entry  3 }

slbNewSslCfgAuthPolTable2PassinfoAlgoName OBJECT-TYPE
    SYNTAX   DisplayString (SIZE(0..255))
    MAX-ACCESS  read-create
    STATUS  current
    DESCRIPTION
        "Certificate signature algorithm header name."
    ::= {slbNewSslCfgAuthPolTable2Entry  4 }

slbNewSslCfgAuthPolTable2PassinfoAlgoFlag OBJECT-TYPE
    SYNTAX  INTEGER {
        enabled(1),
        disabled(2),
        unsupported(2147483647)
        }
    MAX-ACCESS  read-create
    STATUS  current
    DESCRIPTION
        "Pass certificate Signature Algorithm to backend server"
    ::= {slbNewSslCfgAuthPolTable2Entry  5 }

slbNewSslCfgAuthPolTable2PassinfoIssuerName OBJECT-TYPE
    SYNTAX   DisplayString (SIZE(0..255))
    MAX-ACCESS  read-create
    STATUS  current
    DESCRIPTION
        "Certificate issuer header."
    ::= {slbNewSslCfgAuthPolTable2Entry  6 }

slbNewSslCfgAuthPolTable2PassinfoIssuerFlag OBJECT-TYPE
    SYNTAX  INTEGER {
        enabled(1),
        disabled(2),
        unsupported(2147483647)
        }
    MAX-ACCESS  read-create
    STATUS  current
    DESCRIPTION
        "Pass certificate issuer information to backend server"
    ::= {slbNewSslCfgAuthPolTable2Entry  7 }


slbNewSslCfgAuthPolTable3 OBJECT-TYPE
    SYNTAX  SEQUENCE OF SlbNewSslCfgAuthPolTable3Entry
    MAX-ACCESS  not-accessible
    STATUS  current
    DESCRIPTION
        "The table for configuring Client Authentication  policy.
         Note:This mib is not supported for VX instance of Virtualization."
    ::= { authPol 5 }

slbNewSslCfgAuthPolTable3Entry OBJECT-TYPE
    SYNTAX  SlbNewSslCfgAuthPolTable3Entry 
    MAX-ACCESS  not-accessible
    STATUS  current
    DESCRIPTION
        "A row in the Client Authentication policy table."
    INDEX   { slbNewSslCfgAuthPolTable3NameIdIndex }
    ::= { slbNewSslCfgAuthPolTable3 1 }

SlbNewSslCfgAuthPolTable3Entry ::= SEQUENCE {
    slbNewSslCfgAuthPolTable3NameIdIndex           DisplayString,
    slbNewSslCfgAuthPolTable3PassinfoNbeforeName   DisplayString,
    slbNewSslCfgAuthPolTable3PassinfoNbeforeFlag   INTEGER,
    slbNewSslCfgAuthPolTable3PassinfoNafterName    DisplayString,
    slbNewSslCfgAuthPolTable3PassinfoNafterFlag    INTEGER,
    slbNewSslCfgAuthPolTable3PassinfoSubjectName   DisplayString,
    slbNewSslCfgAuthPolTable3PassinfoSubjectFlag   INTEGER
}


slbNewSslCfgAuthPolTable3NameIdIndex  OBJECT-TYPE
    SYNTAX   DisplayString
    MAX-ACCESS  read-only
    STATUS  current
    DESCRIPTION
        "The Auth policy name(key id) as an index."
    ::= {slbNewSslCfgAuthPolTable3Entry  1 }

slbNewSslCfgAuthPolTable3PassinfoNbeforeName OBJECT-TYPE
    SYNTAX   DisplayString (SIZE(0..255))
    MAX-ACCESS  read-create
    STATUS  current
    DESCRIPTION
        "Certificate 'Not Before Validity Dates' header."
    ::= {slbNewSslCfgAuthPolTable3Entry  2 }

slbNewSslCfgAuthPolTable3PassinfoNbeforeFlag OBJECT-TYPE
    SYNTAX  INTEGER {
        enabled(1),
        disabled(2),
        unsupported(2147483647)
        }
    MAX-ACCESS  read-create
    STATUS  current
    DESCRIPTION
        "Pass certificate 'Not Before' Validity Date to backend server"
    ::= {slbNewSslCfgAuthPolTable3Entry  3 }

slbNewSslCfgAuthPolTable3PassinfoNafterName OBJECT-TYPE
    SYNTAX   DisplayString (SIZE(0..255))
    MAX-ACCESS  read-create
    STATUS  current
    DESCRIPTION
        "Certificate 'Not After Validity Dates' header."
    ::= {slbNewSslCfgAuthPolTable3Entry  4 }

slbNewSslCfgAuthPolTable3PassinfoNafterFlag OBJECT-TYPE
    SYNTAX  INTEGER {
        enabled(1),
        disabled(2),
        unsupported(2147483647)
        }
    MAX-ACCESS  read-create
    STATUS  current
    DESCRIPTION
        "Pass certificate 'Not After' Validity Date to backend server"
    ::= {slbNewSslCfgAuthPolTable3Entry  5 }

slbNewSslCfgAuthPolTable3PassinfoSubjectName OBJECT-TYPE
    SYNTAX   DisplayString (SIZE(0..255))
    MAX-ACCESS  read-create
    STATUS  current
    DESCRIPTION
        "Certificate subject header name."
    ::= {slbNewSslCfgAuthPolTable3Entry  6 }

slbNewSslCfgAuthPolTable3PassinfoSubjectFlag OBJECT-TYPE
    SYNTAX  INTEGER {
        enabled(1),
        disabled(2),
        unsupported(2147483647)
        }
    MAX-ACCESS  read-create
    STATUS  current
    DESCRIPTION
        "Pass certificate subject to backend server"
    ::= {slbNewSslCfgAuthPolTable3Entry  7 }


slbNewSslCfgAuthPolTable4 OBJECT-TYPE
    SYNTAX  SEQUENCE OF SlbNewSslCfgAuthPolTable4Entry
    MAX-ACCESS  not-accessible
    STATUS  current
    DESCRIPTION
        "The table for configuring Client Authentication  policy.
         Note:This mib is not supported for VX instance of Virtualization."
    ::= { authPol 6 }

slbNewSslCfgAuthPolTable4Entry OBJECT-TYPE
    SYNTAX  SlbNewSslCfgAuthPolTable4Entry 
    MAX-ACCESS  not-accessible
    STATUS  current
    DESCRIPTION
        "A row in the Client Authentication policy table."
    INDEX   { slbNewSslCfgAuthPolTable4NameIdIndex }
    ::= { slbNewSslCfgAuthPolTable4 1 }

SlbNewSslCfgAuthPolTable4Entry ::= SEQUENCE {
    slbNewSslCfgAuthPolTable4NameIdIndex           DisplayString,
    slbNewSslCfgAuthPolTable4PassinfoKeytypeName   DisplayString,
    slbNewSslCfgAuthPolTable4PassinfoKeytypeFlag   INTEGER,
    slbNewSslCfgAuthPolTable4PassinfoMd5Name       DisplayString,
    slbNewSslCfgAuthPolTable4PassinfoMd5Flag       INTEGER,
    slbNewSslCfgAuthPolTable4PassinfoCertName      DisplayString,
    slbNewSslCfgAuthPolTable4PassinfoCertFormat    INTEGER,
    slbNewSslCfgAuthPolTable4PassinfoCertFlag      INTEGER,
    slbNewSslCfgAuthPolTable4PassinfoCharset       INTEGER,
    slbNewSslCfgAuthPolTable4TrustcaChainName      DisplayString,
    slbNewSslCfgAuthPolTable4TrustcaChainType      DisplayString,
    slbNewSslCfgAuthPolTable4ClientcaReqChainName  DisplayString,
    slbNewSslCfgAuthPolTable4ClientcaReqChainType  DisplayString

}


slbNewSslCfgAuthPolTable4NameIdIndex  OBJECT-TYPE
    SYNTAX   DisplayString
    MAX-ACCESS  read-only
    STATUS  current
    DESCRIPTION
        "The Auth policy name(key id) as an index."
    ::= {slbNewSslCfgAuthPolTable4Entry  1 }

slbNewSslCfgAuthPolTable4PassinfoKeytypeName OBJECT-TYPE
    SYNTAX   DisplayString (SIZE(0..255))
    MAX-ACCESS  read-create
    STATUS  current
    DESCRIPTION
        "Certificate Public Key Type header."
    ::= {slbNewSslCfgAuthPolTable4Entry  2 }

slbNewSslCfgAuthPolTable4PassinfoKeytypeFlag OBJECT-TYPE
    SYNTAX  INTEGER {
        enabled(1),
        disabled(2),
        unsupported(2147483647)
        }
    MAX-ACCESS  read-create
    STATUS  current
    DESCRIPTION
        "Pass certificate Public Key Type information to backend servers"
    ::= {slbNewSslCfgAuthPolTable4Entry  3 }

slbNewSslCfgAuthPolTable4PassinfoMd5Name OBJECT-TYPE
    SYNTAX   DisplayString (SIZE(0..255))
    MAX-ACCESS  read-create
    STATUS  current
    DESCRIPTION
        "Certificate MD5 Hash header."
    ::= {slbNewSslCfgAuthPolTable4Entry  4 }

slbNewSslCfgAuthPolTable4PassinfoMd5Flag OBJECT-TYPE
    SYNTAX  INTEGER {
        enabled(1),
        disabled(2),
        unsupported(2147483647)
        }
    MAX-ACCESS  read-create
    STATUS  current
    DESCRIPTION
        "Pass certificate MD5 Hash information to backend servers"
    ::= {slbNewSslCfgAuthPolTable4Entry  5 }

slbNewSslCfgAuthPolTable4PassinfoCertName OBJECT-TYPE
    SYNTAX   DisplayString (SIZE(0..255))
    MAX-ACCESS  read-create
    STATUS  current
    DESCRIPTION
        "Certificate header."
    ::= {slbNewSslCfgAuthPolTable4Entry  6 }

slbNewSslCfgAuthPolTable4PassinfoCertFormat OBJECT-TYPE
    SYNTAX INTEGER 
    MAX-ACCESS  read-create
    STATUS  current
    DESCRIPTION
        "Certificate Header Lines Format."
    ::= {slbNewSslCfgAuthPolTable4Entry  7 }

slbNewSslCfgAuthPolTable4PassinfoCertFlag OBJECT-TYPE
    SYNTAX  INTEGER {
        enabled(1),
        disabled(2),
        unsupported(2147483647)
        }
    MAX-ACCESS  read-create
    STATUS  current
    DESCRIPTION
        "Pass certificate information to backend servers"
    ::= {slbNewSslCfgAuthPolTable4Entry  8 }

slbNewSslCfgAuthPolTable4PassinfoCharset OBJECT-TYPE
    SYNTAX  INTEGER
    MAX-ACCESS  read-create
    STATUS  current
    DESCRIPTION
        "Set the character set to be used for information."
    ::= {slbNewSslCfgAuthPolTable4Entry  9 }

slbNewSslCfgAuthPolTable4TrustcaChainName OBJECT-TYPE
    SYNTAX  DisplayString (SIZE(0..128))
    MAX-ACCESS  read-create
    STATUS  current
    DESCRIPTION
        "Trusted client's CA certificate name."
    ::= {slbNewSslCfgAuthPolTable4Entry  10 }

slbNewSslCfgAuthPolTable4TrustcaChainType OBJECT-TYPE
    SYNTAX  DisplayString (SIZE(0..6))
    MAX-ACCESS  read-create
    STATUS  current
    DESCRIPTION
        "Trusted client's CA certificate type certificate=cert,Group=group,None=empty string."
    ::= {slbNewSslCfgAuthPolTable4Entry  11 }

slbNewSslCfgAuthPolTable4ClientcaReqChainName OBJECT-TYPE
    SYNTAX  DisplayString (SIZE(0..128))
    MAX-ACCESS  read-create
    STATUS  current
    DESCRIPTION
        "Client CA for Request certificate or group name."
    ::= {slbNewSslCfgAuthPolTable4Entry  12 }

slbNewSslCfgAuthPolTable4ClientcaReqChainType OBJECT-TYPE
    SYNTAX  DisplayString (SIZE(0..8))
    MAX-ACCESS  read-create
    STATUS  current
    DESCRIPTION
        "Client CA for Request type certificate=cert,Group=group,None=none,Default=default."
    ::= {slbNewSslCfgAuthPolTable4Entry  13 }

slbNewSslCfgAuthPolTable5 OBJECT-TYPE
    SYNTAX  SEQUENCE OF SlbNewSslCfgAuthPolTable5Entry
    MAX-ACCESS  not-accessible
    STATUS  current
    DESCRIPTION
        "The table for configuring Client Authentication  policy.
         Note:This mib is not supported for VX instance of Virtualization."
    ::= { authPol 7 }

slbNewSslCfgAuthPolTable5Entry OBJECT-TYPE
    SYNTAX  SlbNewSslCfgAuthPolTable5Entry 
    MAX-ACCESS  not-accessible
    STATUS  current
    DESCRIPTION
        "A row in the Client Authentication policy table."
    INDEX   { slbNewSslCfgAuthPolTable5NameIdIndex }
    ::= { slbNewSslCfgAuthPolTable5 1 }

SlbNewSslCfgAuthPolTable5Entry ::= SEQUENCE {
    slbNewSslCfgAuthPolTable5NameIdIndex           DisplayString,
    slbNewSslCfgAuthPolTable5Cadepth               INTEGER,
    slbNewSslCfgAuthPolTable5Caverify              INTEGER,
    slbNewSslCfgAuthPolTable5Failurl               DisplayString,
    slbNewSslCfgAuthPolTable5AdminStatus           INTEGER,
    slbNewSslCfgAuthPolTable5Delete                INTEGER, 
    slbNewSslCfgAuthPolTable5PassinfoComp2424      INTEGER

}


slbNewSslCfgAuthPolTable5NameIdIndex  OBJECT-TYPE
    SYNTAX   DisplayString
    MAX-ACCESS  read-only
    STATUS  current
    DESCRIPTION
        "The Auth policy name(key id) as an index."
    ::= {slbNewSslCfgAuthPolTable5Entry  1 }


slbNewSslCfgAuthPolTable5Cadepth OBJECT-TYPE
    SYNTAX  INTEGER (1..9)
    MAX-ACCESS  read-create
    STATUS  current
    DESCRIPTION
        "Maximum depth to search the trusted CA in the CA certificate."
    ::= {slbNewSslCfgAuthPolTable5Entry  2 }

slbNewSslCfgAuthPolTable5Caverify OBJECT-TYPE
    SYNTAX  INTEGER 
    MAX-ACCESS  read-create
    STATUS  current
    DESCRIPTION
        "Certificate's CA verification level."
    ::= {slbNewSslCfgAuthPolTable5Entry  3 }

slbNewSslCfgAuthPolTable5Failurl OBJECT-TYPE
    SYNTAX   DisplayString (SIZE(0..255))
    MAX-ACCESS  read-create
    STATUS  current
    DESCRIPTION
        "URL for redirection when client authentication fails"
    ::= {slbNewSslCfgAuthPolTable5Entry  4 }

slbNewSslCfgAuthPolTable5AdminStatus  OBJECT-TYPE
    SYNTAX  INTEGER {
        enabled(1),
        disabled(2),
        unsupported(2147483647)
        }
    MAX-ACCESS  read-create
    STATUS  current
    DESCRIPTION
        "Enable or disable Auth policy."
    ::= {slbNewSslCfgAuthPolTable5Entry  5}

slbNewSslCfgAuthPolTable5Delete OBJECT-TYPE
    SYNTAX  INTEGER {
        other(1),
        delete(2),
        unsupported(2147483647)
    }
    MAX-ACCESS  read-create
    STATUS  current
    DESCRIPTION
        "Delete Client Authentication Policy."
    ::= {slbNewSslCfgAuthPolTable5Entry  6 }


slbNewSslCfgAuthPolTable5PassinfoComp2424 OBJECT-TYPE
    SYNTAX  INTEGER {
        enabled(1),
        disabled(2),
        unsupported(2147483647)
        }
    MAX-ACCESS  read-create
    STATUS  current
    DESCRIPTION
        "Enable/Disable the 2424SSL Headers Compliance Mode."
    ::= {slbNewSslCfgAuthPolTable5Entry  8 }



-- Certificate Repository
slbCurSslCfgCertsTable OBJECT-TYPE
    SYNTAX  SEQUENCE OF SlbCurSslCfgCertsEntry
    MAX-ACCESS  not-accessible
    STATUS  current
    DESCRIPTION
        "Note:This mib is not supported for VX instance of Virtualization."
    ::= { certs 1 }

slbCurSslCfgCertsEntry OBJECT-TYPE
    SYNTAX  SlbCurSslCfgCertsEntry 
    MAX-ACCESS  not-accessible
    STATUS  current
    DESCRIPTION
        "Note:This mib is not supported for VX instance of Virtualization."
    INDEX   { slbCurSslCfgCertsID, slbCurSslCfgCertsType }
    ::= { slbCurSslCfgCertsTable 1 }

SlbCurSslCfgCertsEntry ::= SEQUENCE {
    slbCurSslCfgCertsID                    DisplayString,
    slbCurSslCfgCertsType                  INTEGER,
    slbCurSslCfgCertsName                  DisplayString,
    slbCurSslCfgCertsKeySize               INTEGER,
    slbCurSslCfgCertsExpirty               DisplayString,
    slbCurSslCfgCertsCommonName            DisplayString,
    slbCurSslCfgCertsHashAlgo              INTEGER,
    slbCurSslCfgCertsCountryName           DisplayString,
    slbCurSslCfgCertsPrpvinceName          DisplayString,
    slbCurSslCfgCertsLocalityName          DisplayString,
    slbCurSslCfgCertsOrganizationName      DisplayString,
    slbCurSslCfgCertsOrganizationUnitName  DisplayString,
    slbCurSslCfgCertsEMail                 DisplayString,
    slbCurSslCfgCertsValidityPeriod        INTEGER,
    slbCurSslCfgCertsStatus                INTEGER,
    slbCurSslCfgCertsGenerate              INTEGER,
    slbCurSslCfgCertsKeyType               INTEGER,
    slbCurSslCfgCertsKeySizeEc             INTEGER,
    slbCurSslCfgCurveNameEc                INTEGER,
    slbCurSslCfgCertsKeySizeCommon         INTEGER,
    slbCurSslCfgCertsIntermcaChainName      DisplayString,
    slbCurSslCfgCertsIntermcaChainType      DisplayString,
    slbCurSslCfgCertsSerial               DisplayString,
    slbCurSslCfgCertsSubjectAltName       RadwareLongDisplayString
    }

slbCurSslCfgCertsID OBJECT-TYPE
    SYNTAX   DisplayString (SIZE(0..128))
    MAX-ACCESS  read-only
    STATUS  current
    DESCRIPTION
        "Certificate id."
    ::= { slbCurSslCfgCertsEntry  1 }

slbCurSslCfgCertsType  OBJECT-TYPE
    SYNTAX  INTEGER {
                     key(1),
                     certificateRequest(2),
                     serverCertificate(3),
                     trustedCertificate(4),
                     intermediateCertificate(5),
                     crl(6),
                     unsupported(2147483647)
                    }
    MAX-ACCESS  read-only
    STATUS  current
    DESCRIPTION
        "Certificate type."
    ::= { slbCurSslCfgCertsEntry  2 }

slbCurSslCfgCertsName  OBJECT-TYPE
    SYNTAX  DisplayString (SIZE(0..32))
    MAX-ACCESS  read-only
    STATUS  current
    DESCRIPTION
        "Certificate name."
    ::= { slbCurSslCfgCertsEntry  3 }

slbCurSslCfgCertsKeySize  OBJECT-TYPE
    SYNTAX  INTEGER {
                     ks512(1),
                     ks1024(2),
                     ks2048(3),
                     ks4096(4),
                     unknown(6),
                     unsupported(2147483647)
                    }
    MAX-ACCESS  read-only
    STATUS  current
    DESCRIPTION
        "Certificate key size."
    ::= { slbCurSslCfgCertsEntry  4 }

slbCurSslCfgCertsExpirty  OBJECT-TYPE
    SYNTAX  DisplayString
    MAX-ACCESS  read-only
    STATUS  current
    DESCRIPTION
        "Certificate expirty."
    ::= { slbCurSslCfgCertsEntry  5 }

slbCurSslCfgCertsCommonName  OBJECT-TYPE
    SYNTAX  DisplayString (SIZE(0..64))
    MAX-ACCESS  read-only
    STATUS  current
    DESCRIPTION
        "Certificate common name."
    ::= { slbCurSslCfgCertsEntry  6 }

slbCurSslCfgCertsHashAlgo  OBJECT-TYPE
    SYNTAX  INTEGER {
                     md5(1),
                     sha1(2),
                     sha256(3),
                     sha384(4),
                     sha512(5),
                     unknown(6),
                     unsupported(2147483647)
                    }
    MAX-ACCESS  read-only
    STATUS  current
    DESCRIPTION
        "Certificate hash algorithm."
    ::= { slbCurSslCfgCertsEntry  7 }

slbCurSslCfgCertsCountryName  OBJECT-TYPE
    SYNTAX  DisplayString (SIZE (2))
    MAX-ACCESS  read-only
    STATUS  current
    DESCRIPTION
        "Certificate country name."
    ::= { slbCurSslCfgCertsEntry  8 }

slbCurSslCfgCertsPrpvinceName  OBJECT-TYPE
    SYNTAX  DisplayString (SIZE(0..128))
    MAX-ACCESS  read-only
    STATUS  current
    DESCRIPTION
        "Certificate province name."
    ::= { slbCurSslCfgCertsEntry  9 }

slbCurSslCfgCertsLocalityName  OBJECT-TYPE
    SYNTAX  DisplayString (SIZE(0..128))
    MAX-ACCESS  read-only
    STATUS  current
    DESCRIPTION
        "Certificate locality name."
    ::= { slbCurSslCfgCertsEntry  10 }

slbCurSslCfgCertsOrganizationName  OBJECT-TYPE
    SYNTAX  DisplayString (SIZE(0..64))
    MAX-ACCESS  read-only
    STATUS  current
    DESCRIPTION
        "Certificate organization name."
    ::= { slbCurSslCfgCertsEntry  11 }

slbCurSslCfgCertsOrganizationUnitName  OBJECT-TYPE
    SYNTAX  DisplayString (SIZE(0..64))
    MAX-ACCESS  read-only
    STATUS  current
    DESCRIPTION
        "Certificate organization unit name."
    ::= { slbCurSslCfgCertsEntry  12 }

slbCurSslCfgCertsEMail  OBJECT-TYPE
    SYNTAX  DisplayString (SIZE(0..128))
    MAX-ACCESS  read-only
    STATUS  current
    DESCRIPTION
        "Email address."
    ::= { slbCurSslCfgCertsEntry  13 }

slbCurSslCfgCertsValidityPeriod  OBJECT-TYPE
    SYNTAX  INTEGER  (1..3650)
    MAX-ACCESS  read-only
    STATUS  current
    DESCRIPTION
        "Certificate Validity period."
    ::= { slbCurSslCfgCertsEntry  14 }

slbCurSslCfgCertsStatus OBJECT-TYPE
    SYNTAX  INTEGER {
        generated(1),
        notGenerated(2),
        unsupported(2147483647)
    }
    MAX-ACCESS  read-only
    STATUS  current
    DESCRIPTION
        "Shows if the current certificate is generated."
    ::= { slbCurSslCfgCertsEntry 15 }

slbCurSslCfgCertsGenerate OBJECT-TYPE
    SYNTAX  INTEGER {
        other(1),
        generate(2),
        idle(3),
        inprogress(4),
        generated(5),
        notGenerated(6),
        unsupported(2147483647)
        }
    MAX-ACCESS  read-only
    STATUS  current
    DESCRIPTION
        "When this object is read the current state is returned.
         Setting the value to generate(2),the Certificate will be generated.
         idle(3) indicates that there is no Certificate generate is in progess.
         generated(5) indicates that the last certificate generate operation is completed.
         If the generate is successful this variable will return the state
         'generated' else it will return 'notGenerated'. In case of failure('notGenerated')
         we should set this variable back to 'idle' state so others can issue the generate
         command via SNMP."
    ::= { slbCurSslCfgCertsEntry 16 }

slbCurSslCfgCertsKeyType  OBJECT-TYPE
    SYNTAX  INTEGER {
                     rsa(1),
                     ec(2),
                     unknown(6),
                     unsupported(2147483647)
                    }
    MAX-ACCESS  read-only
    STATUS  current
    DESCRIPTION
        "Algorithm to generate the key."
    ::= { slbCurSslCfgCertsEntry  17 }

slbCurSslCfgCertsKeySizeEc  OBJECT-TYPE
    SYNTAX  INTEGER {
                     ks0(0),
                     ks192(1),
                     ks224(2),
                     ks256(3),
                     ks384(4),
                     ks521(5),
                     unknown(6),
                     unsupported(2147483647)
                    }
    MAX-ACCESS  read-only
    STATUS  current
    DESCRIPTION
        "EC key size."
    ::= { slbCurSslCfgCertsEntry  18 }

slbCurSslCfgCurveNameEc OBJECT-TYPE
    SYNTAX  INTEGER {
secp112r1(1),
secp112r2(2),
secp128r1(3),
secp128r2(4),
secp160k1(5),
secp160r1(6),
secp160r2(7),
secp192k1(8),
secp224k1(9),
secp224r1(10),
secp256k1(11),
secp384r1(12),
secp521r1(13),
prime192v1(14),
prime192v2(15),
prime192v3(16),
prime239v1(17),
prime239v2(18),
prime239v3(19),
prime256v1(20),
sect113r1(21),
sect113r2(22),
sect131r1(23),
sect131r2(24),
sect163k1(25),
sect163r1(26),
sect163r2(27),
sect193r1(28),
sect193r2(29),
sect233k1(30),
sect233r1(31),
sect239k1(32),
sect283k1(33),
sect283r1(34),
sect409k1(35),
sect409r1(36),
sect571k1(37),
sect571r1(38),
c2pnb163v1(39),
c2pnb163v2(40),
c2pnb163v3(41),
c2pnb176v1(42),
c2tnb191v1(43),
c2tnb191v2(44),
c2tnb191v3(45),
c2pnb208w1(46),
c2tnb239v1(47),
c2tnb239v2(48),
c2tnb239v3(49),
c2pnb272w1(50),
c2pnb304w1(51),
c2tnb359v1(52),
c2pnb368w1(53),
c2tnb431r1(54),
wtls1(55),
wtls3(56),
wtls4(57),
wtls5(58),
wtls6(59),
wtls7(60),
wtls8(61),
wtls9(62),
wtls10(63),
wtls11(64),
wtls12(65),
unknown(0),
unsupported(2147483647)
                    }
    MAX-ACCESS  read-only
      STATUS  current
      DESCRIPTION
          "EC curve name."
      ::= { slbCurSslCfgCertsEntry 19 }

slbCurSslCfgCertsKeySizeCommon  OBJECT-TYPE
    SYNTAX  INTEGER  (0..4096)
    MAX-ACCESS  read-only
    STATUS  current
    DESCRIPTION
        "Current config Read-Only Key size common for both RSA and EC"
    ::= { slbCurSslCfgCertsEntry  20 }

slbCurSslCfgCertsIntermcaChainName  OBJECT-TYPE
    SYNTAX   DisplayString
    MAX-ACCESS  read-only
    STATUS  current
    DESCRIPTION
        "Intermediate CA certificate chain name."
    ::= {slbCurSslCfgCertsEntry  21 }

slbCurSslCfgCertsIntermcaChainType  OBJECT-TYPE
    SYNTAX   DisplayString
    MAX-ACCESS  read-only
    STATUS  current
    DESCRIPTION
        "Intermediate CA certificate chain type certificate=cert,Group=group,None=empty string."
    ::= {slbCurSslCfgCertsEntry  22 }

slbCurSslCfgCertsSerial  OBJECT-TYPE
    SYNTAX  DisplayString (SIZE(0..64))
    MAX-ACCESS  read-only
    STATUS  current
    DESCRIPTION
        "SSL certificate serial number"
    ::= { slbCurSslCfgCertsEntry  23 }

slbCurSslCfgCertsSubjectAltName  OBJECT-TYPE
    SYNTAX   RadwareLongDisplayString (SIZE (0..1024))
    MAX-ACCESS  read-only
    STATUS  current
    DESCRIPTION
        "Subject Alternative Name extension, format allowed <DNS:test.com>, <IP:1.1.1.1>, <email:test@mail.com>"
    ::= {slbCurSslCfgCertsEntry  24 }

slbNewSslCfgCertsTable OBJECT-TYPE
    SYNTAX  SEQUENCE OF SlbNewSslCfgCertsEntry
    MAX-ACCESS  not-accessible
    STATUS  current
    DESCRIPTION
        "Note:This mib is not supported for VX instance of Virtualization."
    ::= { certs 2 }

slbNewSslCfgCertsEntry OBJECT-TYPE
    SYNTAX  SlbNewSslCfgCertsEntry 
    MAX-ACCESS  not-accessible
    STATUS  current
    DESCRIPTION
        "."
    INDEX   { slbNewSslCfgCertsID, slbNewSslCfgCertsType }
    ::= { slbNewSslCfgCertsTable 1 }

SlbNewSslCfgCertsEntry ::= SEQUENCE {
    slbNewSslCfgCertsID                    DisplayString,
    slbNewSslCfgCertsType                  INTEGER,
    slbNewSslCfgCertsName                  DisplayString,
    slbNewSslCfgCertsKeySize               INTEGER,
    slbNewSslCfgCertsExpirty               DisplayString,
    slbNewSslCfgCertsCommonName            DisplayString,
    slbNewSslCfgCertsHashAlgo              INTEGER,
    slbNewSslCfgCertsCountryName           DisplayString,
    slbNewSslCfgCertsPrpvinceName          DisplayString,
    slbNewSslCfgCertsLocalityName          DisplayString,
    slbNewSslCfgCertsOrganizationName      DisplayString,
    slbNewSslCfgCertsOrganizationUnitName  DisplayString,
    slbNewSslCfgCertsEMail                 DisplayString,
    slbNewSslCfgCertsValidityPeriod        INTEGER,
    slbNewSslCfgCertsDelete                INTEGER,
    slbNewSslCfgCertsGenerate              INTEGER,
    slbNewSslCfgCertsStatus                INTEGER,
    slbNewSslCfgCertsKeyType               INTEGER,
    slbNewSslCfgCertsKeySizeEc             INTEGER,
    slbNewSslCfgCurveNameEc                INTEGER,
    slbNewSslCfgCertsKeySizeCommon         INTEGER,
    slbNewSslCfgCertsIntermcaChainName      DisplayString,
    slbNewSslCfgCertsIntermcaChainType      DisplayString,
    slbNewSslCfgCertsSerial               DisplayString,
    slbNewSslCfgCertsSubjectAltName       RadwareLongDisplayString
    }

slbNewSslCfgCertsID OBJECT-TYPE
    SYNTAX   DisplayString (SIZE(0..128))
    MAX-ACCESS  read-only
    STATUS  current
    DESCRIPTION
        "Certificate id."
    ::= { slbNewSslCfgCertsEntry  1 }
slbNewSslCfgCertsType  OBJECT-TYPE
    SYNTAX  INTEGER {
                     key(1),
                     certificateRequest(2),
                     serverCertificate(3),
                     trustedCertificate(4),
                     intermediateCertificate(5),
                     crl(6),
                     unsupported(2147483647)
                     }
    MAX-ACCESS  read-only
    STATUS  current
    DESCRIPTION
        "Certificate type."
    ::= { slbNewSslCfgCertsEntry  2 }

slbNewSslCfgCertsName  OBJECT-TYPE
    SYNTAX  DisplayString (SIZE(0..32))
    MAX-ACCESS  read-write
      STATUS  current
      DESCRIPTION
          "Certificate Name."
      ::= { slbNewSslCfgCertsEntry  3 }

slbNewSslCfgCertsKeySize  OBJECT-TYPE
    SYNTAX  INTEGER {
                     ks512(1),
                     ks1024(2),
                     ks2048(3),
                     ks4096(4),
                     unknown(6),
                     unsupported(2147483647)
                    }
    MAX-ACCESS  read-create
      STATUS  current
      DESCRIPTION
          "Certificate key size."
      ::= { slbNewSslCfgCertsEntry  4 }

slbNewSslCfgCertsExpirty  OBJECT-TYPE
    SYNTAX  DisplayString
    MAX-ACCESS  read-only
      STATUS  current
      DESCRIPTION
          "Certificate expiry."
      ::= { slbNewSslCfgCertsEntry  5 }

slbNewSslCfgCertsCommonName  OBJECT-TYPE
    SYNTAX  DisplayString (SIZE(0..64))
      MAX-ACCESS  read-create
      STATUS  current
      DESCRIPTION
          "Certificate common nane."
      ::= { slbNewSslCfgCertsEntry  6 }

slbNewSslCfgCertsHashAlgo  OBJECT-TYPE
    SYNTAX  INTEGER {
                     md5(1),
                     sha1(2),
                     sha256(3),
                     sha384(4),
                     sha512(5),
                     unknown(6),
                     unsupported(2147483647)
                    }
    MAX-ACCESS  read-create
    STATUS  current
    DESCRIPTION
        "Certificate hash algorithm."
    ::= { slbNewSslCfgCertsEntry  7 }

slbNewSslCfgCertsCountryName  OBJECT-TYPE
    SYNTAX  DisplayString (SIZE (2))
    MAX-ACCESS  read-create
    STATUS  current
    DESCRIPTION
        "Certificate country name."
    ::= { slbNewSslCfgCertsEntry  8 }

slbNewSslCfgCertsPrpvinceName  OBJECT-TYPE
    SYNTAX  DisplayString (SIZE(0..128))
    MAX-ACCESS  read-create
    STATUS  current
    DESCRIPTION
        "Certificate province name."
    ::= { slbNewSslCfgCertsEntry  9 }

slbNewSslCfgCertsLocalityName  OBJECT-TYPE
    SYNTAX  DisplayString (SIZE(0..128))
    MAX-ACCESS  read-create
    STATUS  current
    DESCRIPTION
        "Certificate locality name."
    ::= { slbNewSslCfgCertsEntry  10 }

slbNewSslCfgCertsOrganizationName  OBJECT-TYPE
    SYNTAX  DisplayString (SIZE(0..64))
    MAX-ACCESS  read-create
    STATUS  current
    DESCRIPTION
        "Certificate organization name."
    ::= { slbNewSslCfgCertsEntry  11 }

slbNewSslCfgCertsOrganizationUnitName  OBJECT-TYPE
    SYNTAX  DisplayString (SIZE(0..64))
    MAX-ACCESS  read-create
    STATUS  current
    DESCRIPTION
        "Certificate organization unit name."
    ::= { slbNewSslCfgCertsEntry  12 }

slbNewSslCfgCertsEMail  OBJECT-TYPE
    SYNTAX  DisplayString (SIZE(0..128))
    MAX-ACCESS  read-create
    STATUS  current
    DESCRIPTION
        "Email address."
    ::= { slbNewSslCfgCertsEntry  13 }

slbNewSslCfgCertsValidityPeriod  OBJECT-TYPE
    SYNTAX  INTEGER  (1..3650)
    MAX-ACCESS  read-create
    STATUS  current
    DESCRIPTION
        "Certificate validity period."
    ::= { slbNewSslCfgCertsEntry  14 }

slbNewSslCfgCertsDelete OBJECT-TYPE
    SYNTAX  INTEGER {
        other(1),
        delete(2),
        unsupported(2147483647)
        }
    MAX-ACCESS  read-write
    STATUS  current
    DESCRIPTION
        "Delete certificate."
    ::= { slbNewSslCfgCertsEntry 15 }

slbNewSslCfgCertsGenerate OBJECT-TYPE
    SYNTAX  INTEGER {
        other(1),
        generate(2),
        idle(3),
        inprogress(4),
        generated(5),
        notGenerated(6),
        unsupported(2147483647)
        }
    MAX-ACCESS  read-write
    STATUS  current
    DESCRIPTION
        "When this object is read the current state is returned.
         Setting the value to generate(2),the Certificate will be generated.
         idle(3) indicates that there is no Certificate generate is in progess.
         generated(5) indicates that the last certificate generate operation is completed.
         If the generate is successful this variable will return the state
         'generated' else it will return 'notGenerated'. In case of failure('notGenerated')
         we should set this variable back to 'idle' state so others can issue the generate
         command via SNMP."
    ::= { slbNewSslCfgCertsEntry 16 }

slbNewSslCfgCertsStatus OBJECT-TYPE
    SYNTAX  INTEGER {
        generated(1),
            notGenerated(2),
            inProgress(3),
            unsupported(2147483647)
    }
    MAX-ACCESS  read-only
    STATUS  current
    DESCRIPTION
        "Shows if the current certificate is generated."
    ::= { slbNewSslCfgCertsEntry 17 }

slbNewSslCfgCertsKeyType OBJECT-TYPE
    SYNTAX  INTEGER {
                     rsa(1),
                     ec(2),
                     unknown(6),
                     unsupported(2147483647)
                    }     
    MAX-ACCESS  read-create
    STATUS  current
    DESCRIPTION
        "Algorithm to generate the key."
    ::= { slbNewSslCfgCertsEntry 18 }

slbNewSslCfgCertsKeySizeEc  OBJECT-TYPE
    SYNTAX  INTEGER {
                     ks0(0),
                     ks192(1),
                     ks224(2),
                     ks256(3),
                     ks384(4),
                     ks521(5),
                     unknown(6),
                     unsupported(2147483647)
                    }
    MAX-ACCESS  read-create
      STATUS  current
      DESCRIPTION
          "EC key size."
      ::= { slbNewSslCfgCertsEntry  19 }

slbNewSslCfgCurveNameEc OBJECT-TYPE
    SYNTAX  INTEGER {
secp112r1(1),
secp112r2(2),
secp128r1(3),
secp128r2(4),
secp160k1(5),
secp160r1(6),
secp160r2(7),
secp192k1(8),
secp224k1(9),
secp224r1(10),
secp256k1(11),
secp384r1(12),
secp521r1(13),
prime192v1(14),
prime192v2(15),
prime192v3(16),
prime239v1(17),
prime239v2(18),
prime239v3(19),
prime256v1(20),
sect113r1(21),
sect113r2(22),
sect131r1(23),
sect131r2(24),
sect163k1(25),
sect163r1(26),
sect163r2(27),
sect193r1(28),
sect193r2(29),
sect233k1(30),
sect233r1(31),
sect239k1(32),
sect283k1(33),
sect283r1(34),
sect409k1(35),
sect409r1(36),
sect571k1(37),
sect571r1(38),
c2pnb163v1(39),
c2pnb163v2(40),
c2pnb163v3(41),
c2pnb176v1(42),
c2tnb191v1(43),
c2tnb191v2(44),
c2tnb191v3(45),
c2pnb208w1(46),
c2tnb239v1(47),
c2tnb239v2(48),
c2tnb239v3(49),
c2pnb272w1(50),
c2pnb304w1(51),
c2tnb359v1(52),
c2pnb368w1(53),
c2tnb431r1(54),
wtls1(55),
wtls3(56),
wtls4(57),
wtls5(58),
wtls6(59),
wtls7(60),
wtls8(61),
wtls9(62),
wtls10(63),
wtls11(64),
wtls12(65),
                     unknown(0),
unsupported(2147483647)
                    }     
    MAX-ACCESS  read-create
      STATUS  current
      DESCRIPTION
          "EC curve name."   
      ::= { slbNewSslCfgCertsEntry 20 } 

slbNewSslCfgCertsKeySizeCommon  OBJECT-TYPE
    SYNTAX  INTEGER  (0..4096)
    MAX-ACCESS  read-only
    STATUS  current
    DESCRIPTION
        "New config Read-Only Key size common for both RSA and EC"
    ::= { slbNewSslCfgCertsEntry  21 }

slbNewSslCfgCertsIntermcaChainName  OBJECT-TYPE
    SYNTAX   DisplayString
    MAX-ACCESS  read-write
    STATUS  current
    DESCRIPTION
        "Intermediate CA certificate chain name."
    ::= {slbNewSslCfgCertsEntry  22 }

slbNewSslCfgCertsIntermcaChainType  OBJECT-TYPE
    SYNTAX   DisplayString
    MAX-ACCESS  read-write
    STATUS  current
    DESCRIPTION
        "Intermediate CA certificate chain type certificate=cert,Group=group,None=empty string."
    ::= {slbNewSslCfgCertsEntry  23 }


slbNewSslCfgCertsSerial OBJECT-TYPE
    SYNTAX  DisplayString (SIZE(0..64))
    MAX-ACCESS  read-only
      STATUS  current
      DESCRIPTION
          "SSL certificate serial number"
      ::= { slbNewSslCfgCertsEntry  24 }

slbNewSslCfgCertsSubjectAltName  OBJECT-TYPE
    SYNTAX   RadwareLongDisplayString (SIZE (0..1024))
    MAX-ACCESS  read-create
    STATUS  current
    DESCRIPTION
        "Subject Alternative Name extension, format allowed <DNS:test.com>, <IP:1.1.1.1>, <email:test@mail.com>"
    ::= {slbNewSslCfgCertsEntry  25 }


slbSslCfgCertsDefaults  OBJECT IDENTIFIER ::= { certs 3 }

slbCurSslCfgCertsDefaultsCountryName OBJECT-TYPE
    SYNTAX  DisplayString (SIZE (2))
    MAX-ACCESS  read-only
    STATUS  current
    DESCRIPTION
        "SSL certificate Country Name in 2 letter code.
         Note:This mib is not supported for VX instance of Virtualization."
    ::= { slbSslCfgCertsDefaults 1 }

slbNewSslCfgCertsDefaultsCountryName OBJECT-TYPE
    SYNTAX  DisplayString (SIZE (2))
    MAX-ACCESS  read-write
    STATUS  current
    DESCRIPTION
        "SSL certificate Country Name in 2 letter code.
         Note:This mib is not supported for VX instance of Virtualization."
    ::= { slbSslCfgCertsDefaults 2 }

slbCurSslCfgCertsDefaultsProvinceName OBJECT-TYPE
    SYNTAX  DisplayString (SIZE(0..149))
    MAX-ACCESS  read-only
    STATUS  current
    DESCRIPTION
        "SSL Certificate State or Province Name.
         Note:This mib is not supported for VX instance of Virtualization."
    ::= { slbSslCfgCertsDefaults 3 }

slbNewSslCfgCertsDefaultsProvinceName OBJECT-TYPE
    SYNTAX  DisplayString (SIZE(0..149))
    MAX-ACCESS  read-write
    STATUS  current
    DESCRIPTION
        "SSL Certificate State or Province Name.
         Note:This mib is not supported for VX instance of Virtualization."
    ::= { slbSslCfgCertsDefaults 4 }

slbCurSslCfgCertsDefaultsLocallyName OBJECT-TYPE
    SYNTAX  DisplayString (SIZE(0..149))
    MAX-ACCESS  read-only
    STATUS  current
    DESCRIPTION
        "SSL certificate locality name (e.g. city).
         Note:This mib is not supported for VX instance of Virtualization."
    ::= { slbSslCfgCertsDefaults 5 }

slbNewSslCfgCertsDefaultsLocallyName OBJECT-TYPE
    SYNTAX  DisplayString (SIZE(0..149))
    MAX-ACCESS  read-write
    STATUS  current
    DESCRIPTION
        "SSL certificate locality name (e.g. city).
         Note:This mib is not supported for VX instance of Virtualization."
    ::= { slbSslCfgCertsDefaults 6 }

slbCurSslCfgCertsDefaultsOrganizationName OBJECT-TYPE
    SYNTAX  DisplayString (SIZE(0..85))
    MAX-ACCESS  read-only
    STATUS  current
    DESCRIPTION
        "SSL certificate Organization Name (e.g. company).
         Note:This mib is not supported for VX instance of Virtualization."
    ::= { slbSslCfgCertsDefaults 7 }

slbNewSslCfgCertsDefaultsOrganizationName OBJECT-TYPE
    SYNTAX  DisplayString (SIZE(0..85))
    MAX-ACCESS  read-write
    STATUS  current
    DESCRIPTION
        "SSL certificate Organization Name (e.g. company).
         Note:This mib is not supported for VX instance of Virtualization."
    ::= { slbSslCfgCertsDefaults 8 }

slbCurSslCfgCertsDefaultsOrganizationUnitName OBJECT-TYPE
    SYNTAX  DisplayString (SIZE(0..85))
    MAX-ACCESS  read-only
    STATUS  current
    DESCRIPTION
        "SSL certificate Organizational Unit Name (e.g. accounting).
         Note:This mib is not supported for VX instance of Virtualization."
    ::= { slbSslCfgCertsDefaults 9 }

slbNewSslCfgCertsDefaultsOrganizationUnitName OBJECT-TYPE
    SYNTAX  DisplayString (SIZE(0..85))
    MAX-ACCESS  read-write
    STATUS  current
    DESCRIPTION
        "SSL certificate Organizational Unit Name (e.g. accounting).
         Note:This mib is not supported for VX instance of Virtualization."
    ::= { slbSslCfgCertsDefaults 10 }

slbCurSslCfgCertsDefaultsEMail OBJECT-TYPE
    SYNTAX  DisplayString (SIZE(0..149))
    MAX-ACCESS  read-only
    STATUS  current
    DESCRIPTION
        "SSL certificate Email (e.g. admin@company.com).
         Note:This mib is not supported for VX instance of Virtualization."
    ::= { slbSslCfgCertsDefaults 11 }

slbNewSslCfgCertsDefaultsEMail OBJECT-TYPE
    SYNTAX  DisplayString (SIZE(0..149))
    MAX-ACCESS  read-write
    STATUS  current
    DESCRIPTION
        "SSL certificate Email (e.g. admin@company.com).
         Note:This mib is not supported for VX instance of Virtualization."
    ::= { slbSslCfgCertsDefaults 12 }

slbCurSslCfgGroupsTable OBJECT-TYPE
    SYNTAX  SEQUENCE OF SlbCurSslCfgGroupsEntry
    MAX-ACCESS  not-accessible
    STATUS  current
    DESCRIPTION
        "Note:This mib is not supported for VX instance of Virtualization."
    ::= { certs 4 }

slbCurSslCfgGroupsEntry OBJECT-TYPE
    SYNTAX  SlbCurSslCfgGroupsEntry 
    MAX-ACCESS  not-accessible
    STATUS  current
    DESCRIPTION
        "."
    INDEX   { slbCurSslCfgGroupsID }
    ::= { slbCurSslCfgGroupsTable 1 }

SlbCurSslCfgGroupsEntry ::= SEQUENCE {
    slbCurSslCfgGroupsID           DisplayString,
    slbCurSslCfgGroupsName         DisplayString,
    slbCurSslCfgGroupsType         INTEGER,
    slbCurSslCfgGroupsDefaultCert  DisplayString,
    slbCurSslCfgGroupsCertBmap     OCTET STRING,
    slbCurSslCfgGroupsConfigType   INTEGER,
    slbCurSslCfgGroupsChainingMode INTEGER
    }

slbCurSslCfgGroupsID OBJECT-TYPE
    SYNTAX   DisplayString (SIZE(0..128))
    MAX-ACCESS  read-only
    STATUS  current
    DESCRIPTION
        "Certificate group ID."
    ::= { slbCurSslCfgGroupsEntry  1 }

slbCurSslCfgGroupsName  OBJECT-TYPE
    SYNTAX  DisplayString (SIZE(0..32))
    MAX-ACCESS  read-only
      STATUS  current
      DESCRIPTION
          "Certificate group name."
      ::= { slbCurSslCfgGroupsEntry  2 }

slbCurSslCfgGroupsType  OBJECT-TYPE
    SYNTAX  INTEGER {
                     serverCertificate(3),
                     trustedCertificate(4),
                     intermediateCertificate(5),
                     unsupported(2147483647)
                    }
    MAX-ACCESS  read-only
    STATUS  current
    DESCRIPTION
        "Certificate group type."
    ::= { slbCurSslCfgGroupsEntry  3 }

slbCurSslCfgGroupsDefaultCert OBJECT-TYPE
    SYNTAX  DisplayString (SIZE(0..128))
    MAX-ACCESS  read-only
      STATUS  current
      DESCRIPTION
          "Default certificate."
      ::= { slbCurSslCfgGroupsEntry  4 }

slbCurSslCfgGroupsCertBmap OBJECT-TYPE
    SYNTAX  OCTET STRING
    MAX-ACCESS  read-only
    STATUS  current
    DESCRIPTION
         "List of Certificates the group holds - Selected certificates 
         are presented in a bitmap format.
         Receiving order is as:

	 OCTET 1  OCTET 2  .....
	 xxxxxxxx xxxxxxxx .....
	 ||    || |_ Cert 9
	 ||    ||
	 ||    ||___ Cert 4
	 ||    |____ Cert 3
	 ||      .    .   .
	 ||_________ Cert 2
	 |__________ Cert 1

	 where x : 1 - The represented certficate is selected
	 0 - The represented certificate is not selected."
    ::= { slbCurSslCfgGroupsEntry  5 }	 

slbCurSslCfgGroupsConfigType  OBJECT-TYPE
    SYNTAX  INTEGER {
            regular(1),
            read-only(2),
            unsupported(2147483647)
        }
    MAX-ACCESS  read-only
    STATUS  current
    DESCRIPTION
        "Group config type either regular or read-only."
    ::= { slbCurSslCfgGroupsEntry  6 }

slbCurSslCfgGroupsChainingMode  OBJECT-TYPE
    SYNTAX  INTEGER {
                     bySubjectIssuer(0),
                     bySkidAkid(1),
                     unsupported(2147483647)
                    }
    MAX-ACCESS  read-only
    STATUS  current
    DESCRIPTION
        "Chain Mode. By key - 0 or By Group - 1."
    ::= { slbCurSslCfgGroupsEntry  7 }
    
slbNewSslCfgGroupsTable OBJECT-TYPE
    SYNTAX  SEQUENCE OF SlbNewSslCfgGroupsEntry
    MAX-ACCESS  not-accessible
    STATUS  current
    DESCRIPTION
        "Note:This mib is not supported for VX instance of Virtualization."
    ::= { certs 5 }

slbNewSslCfgGroupsEntry OBJECT-TYPE
    SYNTAX  SlbNewSslCfgGroupsEntry 
    MAX-ACCESS  not-accessible
    STATUS  current
    DESCRIPTION
        "."
    INDEX   { slbNewSslCfgGroupsID }
    ::= { slbNewSslCfgGroupsTable 1 }

SlbNewSslCfgGroupsEntry ::= SEQUENCE {
    slbNewSslCfgGroupsID           DisplayString,
    slbNewSslCfgGroupsName         DisplayString,
    slbNewSslCfgGroupsType         INTEGER,
    slbNewSslCfgGroupsDelete       INTEGER,
    slbNewSslCfgGroupsDefaultCert  DisplayString,
    slbNewSslCfgGroupsAddCert      DisplayString,
    slbNewSslCfgGroupsRemCert      DisplayString,
    slbNewSslCfgGroupsCertBmap     OCTET STRING,
    slbNewSslCfgGroupsConfigType   INTEGER,
    slbNewSslCfgGroupsChainingMode INTEGER
    }

slbNewSslCfgGroupsID OBJECT-TYPE
    SYNTAX   DisplayString (SIZE(0..128))
    MAX-ACCESS  read-only
    STATUS  current
    DESCRIPTION
        "Certificate group ID."
    ::= { slbNewSslCfgGroupsEntry  1 }

slbNewSslCfgGroupsName  OBJECT-TYPE
    SYNTAX  DisplayString (SIZE(0..32))
    MAX-ACCESS  read-write
      STATUS  current
      DESCRIPTION
          "Certificate group name."
      ::= { slbNewSslCfgGroupsEntry  2 }

slbNewSslCfgGroupsType  OBJECT-TYPE
    SYNTAX  INTEGER {
                     serverCertificate(3),
                     trustedCertificate(4),
                     intermediateCertificate(5),
                     unsupported(2147483647)
                    }
    MAX-ACCESS  read-write
    STATUS  current
    DESCRIPTION
        "Certificate group type."
    ::= { slbNewSslCfgGroupsEntry  3 }

slbNewSslCfgGroupsDelete OBJECT-TYPE
    SYNTAX  INTEGER {
        other(1),
        delete(2),
        unsupported(2147483647)
        }
    MAX-ACCESS  read-write
    STATUS  current
    DESCRIPTION
        "Delete certificate group."
    ::= { slbNewSslCfgGroupsEntry 4 }

slbNewSslCfgGroupsDefaultCert OBJECT-TYPE
    SYNTAX  DisplayString (SIZE(0..128))
    MAX-ACCESS  read-write 
      STATUS  current
      DESCRIPTION
          "Default certificate."
      ::= { slbNewSslCfgGroupsEntry  5 }

slbNewSslCfgGroupsAddCert  OBJECT-TYPE
    SYNTAX  DisplayString (SIZE(0..128))
    MAX-ACCESS  read-write
    STATUS  current
    DESCRIPTION
        "Add certificate to the group"
    ::= { slbNewSslCfgGroupsEntry  6 }

slbNewSslCfgGroupsRemCert  OBJECT-TYPE
    SYNTAX  DisplayString (SIZE(0..128))
    MAX-ACCESS  read-write
    STATUS  current
    DESCRIPTION
        "Remove certificate from the group"
    ::= { slbNewSslCfgGroupsEntry  7 }	

slbNewSslCfgGroupsCertBmap OBJECT-TYPE
    SYNTAX  OCTET STRING
    MAX-ACCESS  read-only
    STATUS  current
    DESCRIPTION
         "List of Certificates the group holds - Selected certificates 
         are presented in a bitmap format.
         Receiving order is as:

	 OCTET 1  OCTET 2  .....
	 xxxxxxxx xxxxxxxx .....
	 ||    || |_ Cert 9
	 ||    ||
	 ||    ||___ Cert 4
	 ||    |____ Cert 3
	 ||      .    .   .
	 ||_________ Cert 2
	 |__________ Cert 1

	 where x : 1 - The represented certficate is selected
	 0 - The represented certificate is not selected."
    ::= { slbNewSslCfgGroupsEntry  8 }

slbNewSslCfgGroupsConfigType  OBJECT-TYPE
    SYNTAX  INTEGER {
            regular(1),
            read-only(2),
            unsupported(2147483647)
        }
    MAX-ACCESS  read-only
    STATUS  current
    DESCRIPTION
        "Group config type either regular or read-only."
    ::= { slbNewSslCfgGroupsEntry  9 }

slbNewSslCfgGroupsChainingMode  OBJECT-TYPE
    SYNTAX  INTEGER {
                     bySubjectIssuer(0),
                     bySkidAkid(1),
                     unsupported(2147483647)
                    }
    MAX-ACCESS  read-write
    STATUS  current
    DESCRIPTION
        "Chain Mode. By key - 0 or By Group - 1."
    ::= { slbNewSslCfgGroupsEntry  10 }

slbCurSslCfgSSLCdpGrpTable OBJECT-TYPE
    SYNTAX  SEQUENCE OF SlbCurSslCfgSSLCdpGrpEntry
    MAX-ACCESS  not-accessible
    STATUS  current
    DESCRIPTION
        "The table for configuring CDP group.
         Note:This mib is not supported for VX instance of Virtualization."
    ::= { cdpGrp 1 }

slbCurSslCfgSSLCdpGrpEntry OBJECT-TYPE
    SYNTAX  SlbCurSslCfgSSLCdpGrpEntry
    MAX-ACCESS  not-accessible
    STATUS  current
    DESCRIPTION
        "A row in the cdp Group table."
    INDEX   { slbCurSslCfgSSLCdpGroupIdIndex }  
    ::= { slbCurSslCfgSSLCdpGrpTable 1 }

SlbCurSslCfgSSLCdpGrpEntry ::= SEQUENCE {
    slbCurSslCfgSSLCdpGroupIdIndex          DisplayString
    }

slbCurSslCfgSSLCdpGroupIdIndex OBJECT-TYPE
    SYNTAX   DisplayString (SIZE (0..31))
    MAX-ACCESS  read-only 
    STATUS  current
    DESCRIPTION
        "The CDP group (key id) as an index."
    ::= { slbCurSslCfgSSLCdpGrpEntry 1 }

slbNewSslCfgSSLCdpGrpTable OBJECT-TYPE
    SYNTAX  SEQUENCE OF SlbNewSslCfgSSLCdpGrpEntry
    MAX-ACCESS  not-accessible
    STATUS  current
    DESCRIPTION
        "The table for configuring Cdp Group.
         Note:This mib is not supported for VX instance of Virtualization."
    ::= { cdpGrp 2 }

slbNewSslCfgSSLCdpGrpEntry OBJECT-TYPE
    SYNTAX  SlbNewSslCfgSSLCdpGrpEntry
    MAX-ACCESS  not-accessible
    STATUS  current
    DESCRIPTION
        "A row in the CDP Group table."
    INDEX   { slbNewSslCfgCdpGrpIdIndex } ::= { slbNewSslCfgSSLCdpGrpTable 1 }

SlbNewSslCfgSSLCdpGrpEntry ::= SEQUENCE {
    slbNewSslCfgCdpGrpIdIndex          DisplayString,
    slbNewSslCfgCdpGrpDel              INTEGER
    }

slbNewSslCfgCdpGrpIdIndex OBJECT-TYPE
    SYNTAX   DisplayString (SIZE (0..32))
    MAX-ACCESS  read-only
    STATUS  current
    DESCRIPTION
        "The CDP group (key id) as an index."
    ::= { slbNewSslCfgSSLCdpGrpEntry 1 }

slbNewSslCfgCdpGrpDel OBJECT-TYPE
    SYNTAX  INTEGER {
        other(1),
        delete(2),
        unsupported(2147483647)
        }
    MAX-ACCESS  read-create
    STATUS  current
    DESCRIPTION
        "Delete CDP Group."
    ::= { slbNewSslCfgSSLCdpGrpEntry 2 }

slbCurSslCfgSSLCdpEntryTable OBJECT-TYPE
    SYNTAX  SEQUENCE OF SlbCurSslCfgSSLCdpEntry
    MAX-ACCESS  not-accessible
    STATUS  current
    DESCRIPTION
        "The table for configuring CDP Entry.
         Note:This mib is not supported for VX instance of Virtualization."
    ::= { cdpGrp 3 }

slbCurSslCfgSSLCdpEntry OBJECT-TYPE
    SYNTAX  SlbCurSslCfgSSLCdpEntry
    MAX-ACCESS  not-accessible
    STATUS  current
    DESCRIPTION
        "A row in the CDP Entry table."
    INDEX   { slbCurSslCfgSSLCdpGrpIdIndex, slbCurSslCfgSSLCdpEntryIndex }
    ::= { slbCurSslCfgSSLCdpEntryTable 1 }

SlbCurSslCfgSSLCdpEntry ::= SEQUENCE {
    slbCurSslCfgSSLCdpGrpIdIndex           		 DisplayString,
    slbCurSslCfgSSLCdpEntryIndex                 INTEGER,    
    slbCurSslCfgSSLCdpEntryURL                   DisplayString,
	slbCurSslCfgSSLCdpEntryUser                  DisplayString,
	slbCurSslCfgSSLCdpEntryPassword              DisplayString
	
    }

slbCurSslCfgSSLCdpGrpIdIndex OBJECT-TYPE
    SYNTAX   DisplayString (SIZE (0..31))
    MAX-ACCESS  read-only
    STATUS  current
    DESCRIPTION
        "The CDP Group (key id) as an index."
    ::= { slbCurSslCfgSSLCdpEntry 1 }

slbCurSslCfgSSLCdpEntryIndex OBJECT-TYPE
    SYNTAX   INTEGER
    MAX-ACCESS  read-only
    STATUS  current
    DESCRIPTION
        "The Cdp Entry number as an index."
    ::= { slbCurSslCfgSSLCdpEntry 2 }


slbCurSslCfgSSLCdpEntryURL OBJECT-TYPE
    SYNTAX   DisplayString
    MAX-ACCESS  read-only
    STATUS  current
    DESCRIPTION
        "Defines URL of specific object (file/folder) to be download by this rule."
    ::= { slbCurSslCfgSSLCdpEntry 3 }

slbCurSslCfgSSLCdpEntryUser OBJECT-TYPE
    SYNTAX   DisplayString (SIZE (0..31))
    MAX-ACCESS  read-only
    STATUS  current
    DESCRIPTION
        "The Cdp Entry URL User name."
    ::= { slbCurSslCfgSSLCdpEntry 4 }

slbCurSslCfgSSLCdpEntryPassword OBJECT-TYPE
    SYNTAX   DisplayString (SIZE (0..31))
    MAX-ACCESS  read-only
    STATUS  current
    DESCRIPTION
        "The Cdp Entry URL Password."
    ::= { slbCurSslCfgSSLCdpEntry 5 }

slbNewSslCfgSSLCdpEntryTable OBJECT-TYPE
    SYNTAX  SEQUENCE OF SlbNewSslCfgSSLCdpEntry
    MAX-ACCESS  not-accessible
    STATUS  current
    DESCRIPTION
        "The table for configuring CDP Entry.
         Note:This mib is not supported for VX instance of Virtualization."
    ::= { cdpGrp 4 }

slbNewSslCfgSSLCdpEntry OBJECT-TYPE
    SYNTAX  SlbNewSslCfgSSLCdpEntry
    MAX-ACCESS  not-accessible
    STATUS  current
    DESCRIPTION
        "A row in the CDP Entry table."
    INDEX   { slbNewSslCfgSSLCdpGrpIdIndex, slbNewSslCfgSSLCdpEntryIndex }
    ::= { slbNewSslCfgSSLCdpEntryTable 1 }
	     		 
SlbNewSslCfgSSLCdpEntry ::= SEQUENCE {
    slbNewSslCfgSSLCdpGrpIdIndex           	   DisplayString,
    slbNewSslCfgSSLCdpEntryIndex               INTEGER,    
    slbNewSslCfgSSLCdpEntryURL                 DisplayString,
	slbNewSslCfgSSLCdpEntryUser                DisplayString,
	slbNewSslCfgSSLCdpEntryPassword            DisplayString,
	slbNewSslCfgSSLCdpEntryDelete              INTEGER
    }

slbNewSslCfgSSLCdpGrpIdIndex OBJECT-TYPE
    SYNTAX   DisplayString (SIZE (0..31))
    MAX-ACCESS  read-only
    STATUS  current
    DESCRIPTION
        "The CDP Group (key id) as an index."
    ::= { slbNewSslCfgSSLCdpEntry 1 }

slbNewSslCfgSSLCdpEntryIndex OBJECT-TYPE
    SYNTAX   INTEGER
    MAX-ACCESS  read-only
    STATUS  current
    DESCRIPTION
        "The Cdp Entry number as an index."
    ::= { slbNewSslCfgSSLCdpEntry 2 }

slbNewSslCfgSSLCdpEntryURL OBJECT-TYPE
    SYNTAX   DisplayString
    MAX-ACCESS  read-create
    STATUS  current
    DESCRIPTION
        "Defines URL of specific object (file/folder) to be download by this rule."
    ::= { slbNewSslCfgSSLCdpEntry 3 }

slbNewSslCfgSSLCdpEntryUser OBJECT-TYPE
    SYNTAX   DisplayString (SIZE (0..31))
    MAX-ACCESS  read-create
    STATUS  current
    DESCRIPTION
        "The Cdp Entry URL User name."
    ::= { slbNewSslCfgSSLCdpEntry 4 }

slbNewSslCfgSSLCdpEntryPassword OBJECT-TYPE
    SYNTAX   DisplayString (SIZE (0..31))
    MAX-ACCESS  read-create
    STATUS  current
    DESCRIPTION
        "The Cdp Entry URL Password."
    ::= { slbNewSslCfgSSLCdpEntry 5 }

slbNewSslCfgSSLCdpEntryDelete OBJECT-TYPE
    SYNTAX  INTEGER {
        other(1),
        delete(2),
        unsupported(2147483647)
        }
    MAX-ACCESS  read-create
    STATUS  current
    DESCRIPTION
        "By setting the value to delete(2), the entire row is deleted."
    ::= { slbNewSslCfgSSLCdpEntry 6 }
    
slbCurSslCfgSSLInspectKey OBJECT-TYPE
    SYNTAX   DisplayString (SIZE (0..128))
    MAX-ACCESS  read-only
    STATUS  current
    DESCRIPTION
        "The SSL Inspection Key.
         Note:This mib is not supported for VX instance of Virtualization."
    ::= { inspect 1 }

slbNewSslCfgSSLInspectKey OBJECT-TYPE
    SYNTAX   DisplayString (SIZE (0..128))
    MAX-ACCESS  read-write
    STATUS  current
    DESCRIPTION
        "The SSL Inspection Key.
         Note:This mib is not supported for VX instance of Virtualization."
    ::= { inspect 2 }

slbCurSslCfgSSLInspectCacert OBJECT-TYPE
    SYNTAX   DisplayString (SIZE (0..128))
    MAX-ACCESS  read-only
    STATUS  current
    DESCRIPTION
        "The signature CA certificate.
         Note:This mib is not supported for VX instance of Virtualization."
    ::= { inspect 3 }

slbNewSslCfgSSLInspectCacert OBJECT-TYPE
    SYNTAX   DisplayString (SIZE (0..128))
    MAX-ACCESS  read-write
    STATUS  current
    DESCRIPTION
        "The signature CA certificate.
         Note:This mib is not supported for VX instance of Virtualization."
    ::= { inspect 4 }

slbCurSslCfgSSLInspectMemsize OBJECT-TYPE
    SYNTAX  INTEGER (0..1000)
    MAX-ACCESS  read-only
    STATUS  current
    DESCRIPTION
        "The memory size for inspection certificate cache.
         Note:This mib is not supported for VX instance of Virtualization."
    ::= { inspect 5 }

slbNewSslCfgSSLInspectMemsize OBJECT-TYPE
    SYNTAX  INTEGER (0..1000)
    MAX-ACCESS  read-write
    STATUS  current
    DESCRIPTION
        "The memory size for inspection certificate cache.
         Note:This mib is not supported for VX instance of Virtualization."
    ::= { inspect 6 }

slbCurSslCfgSSLInspectDeployment OBJECT-TYPE
    SYNTAX  INTEGER {
       single(1),
       internal(2),
       external(3),
       unsupported(2147483647)
    }
    MAX-ACCESS  read-only
    STATUS  current
    DESCRIPTION
        "SSL inspection deployment type.
         Note:This mib is not supported for VX instance of Virtualization."
    ::= { inspect 7 }

slbNewSslCfgSSLInspectDeployment OBJECT-TYPE
    SYNTAX  INTEGER {
       single(1),
       internal(2),
       external(3),
       unsupported(2147483647)
    }
    MAX-ACCESS  read-write
    STATUS  current
    DESCRIPTION
        "SSL Inspection deployment type.
         Note:This mib is not supported for VX instance of Virtualization."
    ::= { inspect 8 }

slbCurSslCfgSSLInspectFlowTable OBJECT-TYPE
    SYNTAX  SEQUENCE OF SlbCurSslCfgSSLInspectFlowEntry
    MAX-ACCESS  not-accessible
    STATUS  current
    DESCRIPTION
        "The table of SSL Inspection Flow.
         Note:This mib is not supported for VX instance of Virtualization."
    ::= { sslInspectionFlow 1 }

slbCurSslCfgSSLInspectFlowEntry OBJECT-TYPE
    SYNTAX  SlbCurSslCfgSSLInspectFlowEntry
    MAX-ACCESS  not-accessible
    STATUS  current
    DESCRIPTION
        "A row in the flow table."
    INDEX   { slbCurSslCfgSSLInspectFlowIndex, slbCurSslCfgSSLInspectFlowSeGroupIndex }
    ::= { slbCurSslCfgSSLInspectFlowTable 1 }

SlbCurSslCfgSSLInspectFlowEntry ::= SEQUENCE {
    slbCurSslCfgSSLInspectFlowIndex            		Integer32,
	slbCurSslCfgSSLInspectFlowSeGroupIndex         	Integer32,
	slbCurSslCfgSSLInspectFlowSeGroupState		INTEGER,
    slbCurSslCfgSSLInspectFlowSeGroupLocation      	INTEGER,
    slbCurSslCfgSSLInspectFlowSeGroupFallback     	INTEGER,
	slbCurSslCfgSSLInspectFlowSeGroupRedFiltId     	INTEGER,
	slbCurSslCfgSSLInspectFlowGroupID	         	DisplayString
}

slbCurSslCfgSSLInspectFlowIndex OBJECT-TYPE
    SYNTAX  Integer32
    MAX-ACCESS  read-only
    STATUS  current
    DESCRIPTION
        "The number of the flow." 
    ::= { slbCurSslCfgSSLInspectFlowEntry 1 }

slbCurSslCfgSSLInspectFlowSeGroupIndex OBJECT-TYPE 
    SYNTAX  Integer32
    MAX-ACCESS  read-only 
    STATUS  current 
    DESCRIPTION 
        "The Secarity group index. " 
    ::= { slbCurSslCfgSSLInspectFlowEntry 2 }

slbCurSslCfgSSLInspectFlowSeGroupState OBJECT-TYPE
	SYNTAX  INTEGER {
		enabled(2),
		disabled(3),
                unsupported(2147483647)
	}
	MAX-ACCESS  read-only  
	STATUS  current
	DESCRIPTION
		"Enable/disable security group in flow."
	::= { slbCurSslCfgSSLInspectFlowEntry 3 }

slbCurSslCfgSSLInspectFlowSeGroupLocation OBJECT-TYPE
	SYNTAX  INTEGER (1..10)
    MAX-ACCESS  read-only
    STATUS  current
    DESCRIPTION
        "This is the the Group location in the Flow ."
    ::= { slbCurSslCfgSSLInspectFlowEntry 4 }

slbCurSslCfgSSLInspectFlowSeGroupFallback OBJECT-TYPE
    SYNTAX INTEGER {
        none(1),
        continue(2),
		drop(3),
        unsupported(2147483647)
    }
    MAX-ACCESS read-only
    STATUS current
    DESCRIPTION
        "Each security group has it defined fallback action to be
	done in case the group is down. Can be defined as Continue or Drop."   
    ::= { slbCurSslCfgSSLInspectFlowEntry 5 }

slbCurSslCfgSSLInspectFlowSeGroupRedFiltId OBJECT-TYPE
	SYNTAX  INTEGER (0..2048)
    MAX-ACCESS  read-only
    STATUS  current
    DESCRIPTION
        "This is the redirct filter Id ."
    ::= { slbCurSslCfgSSLInspectFlowEntry 6 }


slbCurSslCfgSSLInspectFlowGroupID OBJECT-TYPE
    SYNTAX   DisplayString (SIZE (0..255))
    MAX-ACCESS read-only
    STATUS  current
    DESCRIPTION
        "Group ID of the Security group "
    ::= { slbCurSslCfgSSLInspectFlowEntry 7 }

--New

slbNewSslCfgSSLInspectFlowTable OBJECT-TYPE
    SYNTAX  SEQUENCE OF SlbNewSslCfgSSLInspectFlowEntry
    MAX-ACCESS  not-accessible
    STATUS  current
    DESCRIPTION
        "The table of SSL Inspection Flow.
         Note:This mib is not supported for VX instance of Virtualization."
    ::= { sslInspectionFlow 2 }

slbNewSslCfgSSLInspectFlowEntry OBJECT-TYPE
    SYNTAX  SlbNewSslCfgSSLInspectFlowEntry
    MAX-ACCESS  not-accessible
    STATUS  current
    DESCRIPTION
        "A row in the flow table."
    INDEX   { slbNewSslCfgSSLInspectFlowIndex, slbNewSslCfgSSLInspectFlowSeGroupIndex }
    ::= { slbNewSslCfgSSLInspectFlowTable 1 }

SlbNewSslCfgSSLInspectFlowEntry ::= SEQUENCE {
	slbNewSslCfgSSLInspectFlowIndex            	Integer32,
	slbNewSslCfgSSLInspectFlowSeGroupIndex         	Integer32,
	slbNewSslCfgSSLInspectFlowSeGroupState		INTEGER,
	slbNewSslCfgSSLInspectFlowSeGroupLocation	INTEGER,
	slbNewSslCfgSSLInspectFlowSeGroupFallback	INTEGER,
	slbNewSslCfgSSLInspectFlowSeGroupRedFiltId	INTEGER,
	slbNewSslCfgSSLInspectFlowGroupID	        DisplayString,
	slbNewSslCfgSSLInspectFlowDelete		INTEGER

}

slbNewSslCfgSSLInspectFlowIndex OBJECT-TYPE
    SYNTAX  Integer32
    MAX-ACCESS  read-only
    STATUS  current
    DESCRIPTION
        "The number of the flow." 
    ::= { slbNewSslCfgSSLInspectFlowEntry 1 }
 
slbNewSslCfgSSLInspectFlowSeGroupIndex OBJECT-TYPE 
    SYNTAX  Integer32
    MAX-ACCESS  read-only 
    STATUS  current 
    DESCRIPTION 
        "The The Secarity group index." 
    ::= { slbNewSslCfgSSLInspectFlowEntry 2 }

slbNewSslCfgSSLInspectFlowSeGroupState OBJECT-TYPE
	SYNTAX  INTEGER {
		enabled(2),
		disabled(3),
                unsupported(2147483647)
	}
	MAX-ACCESS  read-create  
	STATUS  current
	DESCRIPTION
		"Enable/disable security group in flow."
	::= { slbNewSslCfgSSLInspectFlowEntry 3 }

slbNewSslCfgSSLInspectFlowSeGroupLocation OBJECT-TYPE
	SYNTAX  INTEGER (1..10)
    MAX-ACCESS  read-create  
    STATUS  current
    DESCRIPTION
        "This is the the Group location in the Flow ."
    ::= { slbNewSslCfgSSLInspectFlowEntry 4 }

slbNewSslCfgSSLInspectFlowSeGroupFallback OBJECT-TYPE
    SYNTAX INTEGER {
        none(1),
        continue(2),
	drop(3),
        unsupported(2147483647)
    }
    MAX-ACCESS  read-create  
    STATUS current
    DESCRIPTION
        "Each security group has it defined fallback action to be
	done in case the group is down. Can be defined as Continue or Drop."   
    ::= { slbNewSslCfgSSLInspectFlowEntry 5 }


slbNewSslCfgSSLInspectFlowSeGroupRedFiltId OBJECT-TYPE
	SYNTAX  INTEGER (0..2048)
    MAX-ACCESS  read-create  
    STATUS  current
    DESCRIPTION
        "This is the redirct filter Id ."
    ::= { slbNewSslCfgSSLInspectFlowEntry 6 }

slbNewSslCfgSSLInspectFlowGroupID OBJECT-TYPE
    SYNTAX   DisplayString (SIZE (0..255))
    MAX-ACCESS  read-create
    STATUS  current
    DESCRIPTION
        "Group ID of the Security group "
    ::= { slbNewSslCfgSSLInspectFlowEntry 7 }

slbNewSslCfgSSLInspectFlowDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { slbNewSslCfgSSLInspectFlowEntry 8 }



-- SSL Inspaction Flow Rule Table

slbNewSslCfgSSLInspectFlowRuleTable  OBJECT-TYPE
    SYNTAX  SEQUENCE OF SlbNewSslCfgSSLInspectFlowRuleEntry 
    MAX-ACCESS  not-accessible
    STATUS  current
    DESCRIPTION
        "The table of SSL Inspection Flow Rule.
         Note:This mib is not supported for VX instance of Virtualization."
    ::= { sslInspectionFlow 3 }
	
slbNewSslCfgSSLInspectFlowRuleEntry  OBJECT-TYPE
    SYNTAX  SlbNewSslCfgSSLInspectFlowRuleEntry 
    MAX-ACCESS  not-accessible
    STATUS  current
    DESCRIPTION
        "Information about a particular Rule in the Flow."
    INDEX   { slbNewSslCfgSSLInspectFlowRuleIndex  }
    ::= { slbNewSslCfgSSLInspectFlowRuleTable 1 }

SlbNewSslCfgSSLInspectFlowRuleEntry ::= SEQUENCE {
	slbNewSslCfgSSLInspectFlowRuleIndex      			Integer32,
	slbNewSslCfgSSLInspectFlowRuleProxyType            	INTEGER,
	slbNewSslCfgSSLInspectFlowRuleInspectHttp			INTEGER,
	slbNewSslCfgSSLInspectFlowRuleHttpsPort      		INTEGER,
	slbNewSslCfgSSLInspectFlowRuleHttpsDecryptPort     	INTEGER,
	slbNewSslCfgSSLInspectFlowRuleHttpPort      		INTEGER,
	slbNewSslCfgSSLInspectFlowRuleIngressPort  			DisplayString,
	slbNewSslCfgSSLInspectFlowRuleEgressPort  			DisplayString,
	slbNewSslCfgSSLInspectFlowRuleAddIngressPort      	Integer32,
	slbNewSslCfgSSLInspectFlowRuleAddEgressPort      	Integer32,
	slbNewSslCfgSSLInspectFlowRuleRemIngressPort      	Integer32,
	slbNewSslCfgSSLInspectFlowRuleRemEgressPort      	Integer32,
	slbNewSslCfgSSLInspectFlowRuleOutboundAction		INTEGER,
	slbNewSslCfgSSLInspectFlowRuleFloatId				DisplayString,
	slbNewSslCfgSSLInspectFlowRuleOutboundFilterHttps	INTEGER,
	slbNewSslCfgSSLInspectFlowRuleOutboundFilterHttp	INTEGER,
	slbNewSslCfgSSLInspectFlowRuleBackendFilterHttps	INTEGER,
	slbNewSslCfgSSLInspectFlowRuleBackendFilterHttp		INTEGER,
	slbNewSslCfgSSLInspectFlowRuleNetworkAddr			IpAddress,
	slbNewSslCfgSSLInspectFlowRuleGWAddr				IpAddress,
	slbNewSslCfgSSLInspectFlowRuleNATAddr				IpAddress,
	slbNewSslCfgSSLInspectFlowRuleWanLinkGrID			DisplayString,
	slbNewSslCfgSSLInspectFlowRuleDelete				INTEGER,
	slbNewSslCfgSSLInspectFlowRuleNATMASKAddr			IpAddress,
        slbNewSslCfgSSLInspectFlowRuleSrcPortPreserve               INTEGER,
        slbNewSslCfgSSLInspectFlowRuleServerAuthPol             DisplayString
}

slbNewSslCfgSSLInspectFlowRuleIndex OBJECT-TYPE
    SYNTAX  Integer32 
    MAX-ACCESS  read-only
    STATUS  current
    DESCRIPTION
        "The number of the flow." 
    ::= { slbNewSslCfgSSLInspectFlowRuleEntry 1 }

	
slbNewSslCfgSSLInspectFlowRuleProxyType OBJECT-TYPE
    SYNTAX  INTEGER{
        transparent(1),
        expicit(2),
        unsupported(2147483647)
    }
    MAX-ACCESS  read-create
    STATUS  current
    DESCRIPTION
        "The type of Proxy if 1 so transparent, if 2 so expicit ."
    ::= { slbNewSslCfgSSLInspectFlowRuleEntry 2 }

	
slbNewSslCfgSSLInspectFlowRuleInspectHttp OBJECT-TYPE
    SYNTAX  INTEGER{
        true(1),
        false(2),
        unsupported(2147483647)
    }
    MAX-ACCESS  read-create
    STATUS  current
    DESCRIPTION
        "Flag For inspect HTTP , value 1 is to Inspect value 2 not to Inspect."
    ::= { slbNewSslCfgSSLInspectFlowRuleEntry 3 }

slbNewSslCfgSSLInspectFlowRuleHttpsPort OBJECT-TYPE
    SYNTAX  INTEGER (0..65534)
    MAX-ACCESS  read-create
    STATUS  current
    DESCRIPTION
        "HTTPS Port Number"
    ::= { slbNewSslCfgSSLInspectFlowRuleEntry 4 }

slbNewSslCfgSSLInspectFlowRuleHttpsDecryptPort OBJECT-TYPE
    SYNTAX  INTEGER (0..65534)
    MAX-ACCESS  read-create
    STATUS  current
    DESCRIPTION
        "HTTPS Decrypt Port Number"
    ::= { slbNewSslCfgSSLInspectFlowRuleEntry 5 }
	
slbNewSslCfgSSLInspectFlowRuleHttpPort OBJECT-TYPE
    SYNTAX  INTEGER (0..65534)
    MAX-ACCESS  read-create
    STATUS  current
    DESCRIPTION
        "HTTP Port Number"
    ::= { slbNewSslCfgSSLInspectFlowRuleEntry 6 }

slbNewSslCfgSSLInspectFlowRuleIngressPort OBJECT-TYPE
    SYNTAX DisplayString (SIZE(0..40))
    MAX-ACCESS  read-only
    STATUS  current
    DESCRIPTION
        "Ingress Port Number 
	Using the following format: xx, xx"
    ::= { slbNewSslCfgSSLInspectFlowRuleEntry 7 }

slbNewSslCfgSSLInspectFlowRuleEgressPort OBJECT-TYPE
    SYNTAX DisplayString (SIZE(0..40))
    MAX-ACCESS  read-only
    STATUS  current
    DESCRIPTION
        "Egress Port Number 
	Using the following format: xx, xx"
    ::= { slbNewSslCfgSSLInspectFlowRuleEntry 8 }


slbNewSslCfgSSLInspectFlowRuleAddIngressPort OBJECT-TYPE
    SYNTAX  Integer32
    MAX-ACCESS  read-create
    STATUS  current
    DESCRIPTION
        "Ingress Port Number"
    ::= { slbNewSslCfgSSLInspectFlowRuleEntry 9 }

slbNewSslCfgSSLInspectFlowRuleAddEgressPort OBJECT-TYPE
    SYNTAX  Integer32
    MAX-ACCESS  read-create
    STATUS  current
    DESCRIPTION
        "Egress Port Number"
    ::= { slbNewSslCfgSSLInspectFlowRuleEntry 10 }

slbNewSslCfgSSLInspectFlowRuleRemIngressPort OBJECT-TYPE
    SYNTAX  Integer32
    MAX-ACCESS  read-create
    STATUS  current
    DESCRIPTION
        "Ingress Port Number"
    ::= { slbNewSslCfgSSLInspectFlowRuleEntry 11 }

slbNewSslCfgSSLInspectFlowRuleRemEgressPort OBJECT-TYPE
    SYNTAX  Integer32
    MAX-ACCESS  read-create
    STATUS  current
    DESCRIPTION
        "Egress Port Number"
    ::= { slbNewSslCfgSSLInspectFlowRuleEntry 12 }



slbNewSslCfgSSLInspectFlowRuleOutboundAction OBJECT-TYPE
    SYNTAX  INTEGER{
        forward(1),
        nat(2),
		llb(3),
        unsupported(2147483647)
    }
    MAX-ACCESS  read-create
    STATUS  current
    DESCRIPTION
        "The Outbound action if 1 so forward if 2 so nat if 3 llb ."
    ::= { slbNewSslCfgSSLInspectFlowRuleEntry 13 }


slbNewSslCfgSSLInspectFlowRuleFloatId OBJECT-TYPE
    SYNTAX DisplayString (SIZE(1..32))
    MAX-ACCESS  read-create
    STATUS  current
    DESCRIPTION
        "The floating IP number in alphanumeric ID."
    ::= { slbNewSslCfgSSLInspectFlowRuleEntry 14 }

slbNewSslCfgSSLInspectFlowRuleOutboundFilterHttps OBJECT-TYPE
    SYNTAX  INTEGER (1..2048)
    MAX-ACCESS  read-create
    STATUS  current
    DESCRIPTION
        "Outband fillter https Id"
    ::= { slbNewSslCfgSSLInspectFlowRuleEntry 15 }

slbNewSslCfgSSLInspectFlowRuleOutboundFilterHttp OBJECT-TYPE
    SYNTAX  INTEGER (1..2048)
    MAX-ACCESS  read-create
    STATUS  current
    DESCRIPTION
        "Outband fillter http Id"
    ::= { slbNewSslCfgSSLInspectFlowRuleEntry 16 }

slbNewSslCfgSSLInspectFlowRuleBackendFilterHttps OBJECT-TYPE
    SYNTAX  INTEGER (0..2048)
    MAX-ACCESS  read-create
    STATUS  current
    DESCRIPTION
        "Backend fillter https Id"
    ::= { slbNewSslCfgSSLInspectFlowRuleEntry 17 }

slbNewSslCfgSSLInspectFlowRuleBackendFilterHttp OBJECT-TYPE
    SYNTAX  INTEGER (0..2048)
    MAX-ACCESS  read-create
    STATUS  current
    DESCRIPTION
        "Backend fillter http Id"
    ::= { slbNewSslCfgSSLInspectFlowRuleEntry 18 }



slbNewSslCfgSSLInspectFlowRuleNetworkAddr OBJECT-TYPE
    SYNTAX IpAddress
    MAX-ACCESS  read-create
    STATUS  current
    DESCRIPTION
        "Network address for interanl interfaces"
    ::= { slbNewSslCfgSSLInspectFlowRuleEntry 19 }
    
slbNewSslCfgSSLInspectFlowRuleGWAddr OBJECT-TYPE
    SYNTAX IpAddress
    MAX-ACCESS  read-create
    STATUS  current
    DESCRIPTION
        "Gateway address"
    ::= { slbNewSslCfgSSLInspectFlowRuleEntry 20 }
    
slbNewSslCfgSSLInspectFlowRuleNATAddr OBJECT-TYPE
    SYNTAX IpAddress
    MAX-ACCESS  read-create
    STATUS  current
    DESCRIPTION
        "NAT address"
    ::= { slbNewSslCfgSSLInspectFlowRuleEntry 21 }
    
slbNewSslCfgSSLInspectFlowRuleWanLinkGrID OBJECT-TYPE  
    SYNTAX DisplayString (SIZE(1..255))
    MAX-ACCESS  read-create
    STATUS  current
    DESCRIPTION
        "The WAN Link Group ID."
    ::= { slbNewSslCfgSSLInspectFlowRuleEntry 22 }
    
slbNewSslCfgSSLInspectFlowRuleDelete OBJECT-TYPE  
    SYNTAX INTEGER {
        other(1),
        delete(2),
        unsupported(2147483647)
        }
    MAX-ACCESS  read-create
    STATUS  current
    DESCRIPTION
        "By setting the value to delete(2), the entire row is
         deleted."
    ::= { slbNewSslCfgSSLInspectFlowRuleEntry 23 }

slbNewSslCfgSSLInspectFlowRuleNATMASKAddr OBJECT-TYPE
    SYNTAX IpAddress
    MAX-ACCESS  read-create
    STATUS  current
    DESCRIPTION
        "NAT Mask address"
    ::= { slbNewSslCfgSSLInspectFlowRuleEntry 24 }
    
slbNewSslCfgSSLInspectFlowRuleSrcPortPreserve OBJECT-TYPE
    SYNTAX  INTEGER {
        enabled(1),
        disabled(2),
        unsupported(2147483647)
    }
    MAX-ACCESS  read-create
    STATUS  current
    DESCRIPTION
        "Enable or disable ssl inspection source port preservation."
    ::= { slbNewSslCfgSSLInspectFlowRuleEntry 25 }

slbNewSslCfgSSLInspectFlowRuleServerAuthPol OBJECT-TYPE
    SYNTAX DisplayString (SIZE(1..128))
    MAX-ACCESS  read-create
    STATUS  current
    DESCRIPTION
        "Server Authentication Policy"
    ::= { slbNewSslCfgSSLInspectFlowRuleEntry 26 }

-- Current 


slbCurSslCfgSSLInspectFlowRuleTable  OBJECT-TYPE
    SYNTAX  SEQUENCE OF SlbCurSslCfgSSLInspectFlowRuleEntry 
    MAX-ACCESS  not-accessible
    STATUS  current
    DESCRIPTION
        "The table of SSL Inspection Flow Rule.
         Note:This mib is not supported for VX instance of Virtualization."
    ::= { sslInspectionFlow 4 }
	
slbCurSslCfgSSLInspectFlowRuleEntry  OBJECT-TYPE
    SYNTAX  SlbCurSslCfgSSLInspectFlowRuleEntry 
    MAX-ACCESS  not-accessible
    STATUS  current
    DESCRIPTION
        "Information about a particular Rule in the Flow."
    INDEX   { slbCurSslCfgSSLInspectFlowRuleIndex  }
    ::= { slbCurSslCfgSSLInspectFlowRuleTable 1 }

SlbCurSslCfgSSLInspectFlowRuleEntry ::= SEQUENCE {
    slbCurSslCfgSSLInspectFlowRuleIndex      			Integer32,
    slbCurSslCfgSSLInspectFlowRuleProxyType            	INTEGER,
	slbCurSslCfgSSLInspectFlowRuleInspectHttp			INTEGER,
	slbCurSslCfgSSLInspectFlowRuleHttpsPort      		INTEGER,
	slbCurSslCfgSSLInspectFlowRuleHttpsDecryptPort     	INTEGER,
	slbCurSslCfgSSLInspectFlowRuleHttpPort      		INTEGER,
	slbCurSslCfgSSLInspectFlowRuleIngressPort      		DisplayString,
	slbCurSslCfgSSLInspectFlowRuleEgressPort      		DisplayString,
	slbCurSslCfgSSLInspectFlowRuleOutboundAction		INTEGER,
	slbCurSslCfgSSLInspectFlowRuleFloatId				DisplayString,
	slbCurSslCfgSSLInspectFlowRuleOutboundFilterHttps	INTEGER,
	slbCurSslCfgSSLInspectFlowRuleOutboundFilterHttp	INTEGER,
	slbCurSslCfgSSLInspectFlowRuleBackendFilterHttps	INTEGER,
	slbCurSslCfgSSLInspectFlowRuleBackendFilterHttp		INTEGER,
	slbCurSslCfgSSLInspectFlowRuleNetworkAddr			IpAddress,
	slbCurSslCfgSSLInspectFlowRuleGWAddr				IpAddress,
	slbCurSslCfgSSLInspectFlowRuleWanLinkGrID           DisplayString,
	slbCurSslCfgSSLInspectFlowRuleNATAddr				IpAddress,
	slbCurSslCfgSSLInspectFlowRuleNATMASKAddr				IpAddress,
        slbCurSslCfgSSLInspectFlowRuleSrcPortPreserve            INTEGER,
        slbCurSslCfgSSLInspectFlowRuleServerAuthPol             DisplayString

}

slbCurSslCfgSSLInspectFlowRuleIndex OBJECT-TYPE
    SYNTAX  Integer32 
    MAX-ACCESS  read-only
    STATUS  current
    DESCRIPTION
        "The number of the flow." 
    ::= { slbCurSslCfgSSLInspectFlowRuleEntry 1 }


	
slbCurSslCfgSSLInspectFlowRuleProxyType OBJECT-TYPE
    SYNTAX  INTEGER{
        transparent(1),
        expicit(2),
        unsupported(2147483647)
    }
    MAX-ACCESS  read-only
    STATUS  current
    DESCRIPTION
        "The type of Proxy if 1 so transparent, if 2 so expicit ."
    ::= { slbCurSslCfgSSLInspectFlowRuleEntry 2 }
	

	
slbCurSslCfgSSLInspectFlowRuleInspectHttp OBJECT-TYPE
    SYNTAX  INTEGER{
        true(1),
        false(2),
        unsupported(2147483647)
    }
    MAX-ACCESS  read-only
    STATUS  current
    DESCRIPTION
        "Flag For inspect HTTP , value 1 is to Inspect value 2 not to Inspect."
    ::= { slbCurSslCfgSSLInspectFlowRuleEntry 3 }

slbCurSslCfgSSLInspectFlowRuleHttpsPort OBJECT-TYPE
    SYNTAX  INTEGER (0..65534)
    MAX-ACCESS  read-only
    STATUS  current
    DESCRIPTION
        "HTTPS Port Number"
    ::= { slbCurSslCfgSSLInspectFlowRuleEntry 4 }

slbCurSslCfgSSLInspectFlowRuleHttpsDecryptPort OBJECT-TYPE
    SYNTAX  INTEGER (0..65534)
    MAX-ACCESS  read-only
    STATUS  current
    DESCRIPTION
        "HTTPS Decrypt Port Number"
    ::= { slbCurSslCfgSSLInspectFlowRuleEntry 5 }
	
slbCurSslCfgSSLInspectFlowRuleHttpPort OBJECT-TYPE
    SYNTAX  INTEGER (0..65534)
    MAX-ACCESS  read-only
    STATUS  current
    DESCRIPTION
        "HTTP Port Number"
    ::= { slbCurSslCfgSSLInspectFlowRuleEntry 6 }

slbCurSslCfgSSLInspectFlowRuleIngressPort OBJECT-TYPE
    SYNTAX DisplayString (SIZE(0..40))
    MAX-ACCESS  read-only
    STATUS  current
    DESCRIPTION
        "Ingress Ports Number"
    ::= { slbCurSslCfgSSLInspectFlowRuleEntry 7 }

slbCurSslCfgSSLInspectFlowRuleEgressPort OBJECT-TYPE
    SYNTAX DisplayString (SIZE(0..40))
    MAX-ACCESS  read-only
    STATUS  current
    DESCRIPTION
        "Egress Ports Number"
    ::= { slbCurSslCfgSSLInspectFlowRuleEntry 8 }

slbCurSslCfgSSLInspectFlowRuleOutboundAction OBJECT-TYPE
    SYNTAX  INTEGER{
        forward(1),
        nat(2),
		llb(3),
        unsupported(2147483647)
    }
    MAX-ACCESS  read-only
    STATUS  current
    DESCRIPTION
        "The Outbound action if 1 so forward if 2 so nat if 3 llb ."
    ::= { slbCurSslCfgSSLInspectFlowRuleEntry 9 }


slbCurSslCfgSSLInspectFlowRuleFloatId OBJECT-TYPE
    SYNTAX DisplayString (SIZE(1..32))
    MAX-ACCESS  read-only
    STATUS  current
    DESCRIPTION
        "The floating IP number in alphanumeric ID."
    ::= { slbCurSslCfgSSLInspectFlowRuleEntry 10 }

slbCurSslCfgSSLInspectFlowRuleOutboundFilterHttps OBJECT-TYPE
    SYNTAX  INTEGER (1..2048)
    MAX-ACCESS  read-only
    STATUS  current
    DESCRIPTION
        "Outband fillter https Id"
    ::= { slbCurSslCfgSSLInspectFlowRuleEntry 11 }

slbCurSslCfgSSLInspectFlowRuleOutboundFilterHttp OBJECT-TYPE
    SYNTAX  INTEGER (1..2048)
    MAX-ACCESS  read-only
    STATUS  current
    DESCRIPTION
        "Outband fillter http Id"
    ::= { slbCurSslCfgSSLInspectFlowRuleEntry 12 }

slbCurSslCfgSSLInspectFlowRuleBackendFilterHttps OBJECT-TYPE
    SYNTAX  INTEGER (0..2048)
    MAX-ACCESS  read-only
    STATUS  current
    DESCRIPTION
        "Backend fillter https Id"
    ::= { slbCurSslCfgSSLInspectFlowRuleEntry 13 }

slbCurSslCfgSSLInspectFlowRuleBackendFilterHttp OBJECT-TYPE
    SYNTAX  INTEGER (0..2048)
    MAX-ACCESS  read-only
    STATUS  current
    DESCRIPTION
        "Backend fillter http Id"
    ::= { slbCurSslCfgSSLInspectFlowRuleEntry 14 }


slbCurSslCfgSSLInspectFlowRuleNetworkAddr OBJECT-TYPE
    SYNTAX IpAddress
    MAX-ACCESS  read-only
    STATUS  current
    DESCRIPTION
        "Network address for interanl interfaces"
    ::= { slbCurSslCfgSSLInspectFlowRuleEntry 15 }
    
slbCurSslCfgSSLInspectFlowRuleGWAddr OBJECT-TYPE
    SYNTAX IpAddress
    MAX-ACCESS  read-only
    STATUS  current
    DESCRIPTION
        "Gateway address"
    ::= { slbCurSslCfgSSLInspectFlowRuleEntry 16 }
    
slbCurSslCfgSSLInspectFlowRuleNATAddr OBJECT-TYPE
    SYNTAX IpAddress
    MAX-ACCESS  read-only
    STATUS  current
    DESCRIPTION
        "NAT address"
    ::= { slbCurSslCfgSSLInspectFlowRuleEntry 17 }

slbCurSslCfgSSLInspectFlowRuleWanLinkGrID OBJECT-TYPE
    SYNTAX DisplayString (SIZE(1..255))
    MAX-ACCESS  read-only
    STATUS  current
    DESCRIPTION
        "The WAN Link Group ID."
    ::= { slbCurSslCfgSSLInspectFlowRuleEntry 18 }

slbCurSslCfgSSLInspectFlowRuleNATMASKAddr OBJECT-TYPE
    SYNTAX IpAddress
    MAX-ACCESS  read-only
    STATUS  current
    DESCRIPTION
        "NAT MASK address"
    ::= { slbCurSslCfgSSLInspectFlowRuleEntry 19 }

slbCurSslCfgSSLInspectFlowRuleSrcPortPreserve  OBJECT-TYPE
    SYNTAX  INTEGER {
        enabled(1),
        disabled(2),
        unsupported(2147483647)
    }
    MAX-ACCESS  read-only
    STATUS  current
    DESCRIPTION
        "SSL Inspection source port preservation either enable or disable."
    ::= {slbCurSslCfgSSLInspectFlowRuleEntry 20 }

slbCurSslCfgSSLInspectFlowRuleServerAuthPol OBJECT-TYPE
    SYNTAX DisplayString (SIZE(1..128))
    MAX-ACCESS  read-only
    STATUS  current
    DESCRIPTION
        "Server Authentication Policy"
    ::= { slbCurSslCfgSSLInspectFlowRuleEntry 21 }

-- flow inspection criteria  

--Current

slbCurSslCfgSSLInspectFlowCriteriaTable OBJECT-TYPE
    SYNTAX SEQUENCE OF SlbCurSslCfgSSLInspectFlowCriteriaEntry
    MAX-ACCESS not-accessible
    STATUS current
    DESCRIPTION
        "The table of SSL Inspection Flow Criteria.
         Note:This mib is not supported for VX instance of Virtualization."
    ::= { sslInspectionFlow 5 }

slbCurSslCfgSSLInspectFlowCriteriaTableEntry OBJECT-TYPE
    SYNTAX SlbCurSslCfgSSLInspectFlowCriteriaEntry
    MAX-ACCESS not-accessible
    STATUS current
    DESCRIPTION
        "Information about a particular Criteria in the Flow."
    INDEX { slbCurSslCfgSSLInspectFlowCriteriaIndex , slbCurSslCfgSSLInspectFlowCriteriaRuleId}
    ::= { slbCurSslCfgSSLInspectFlowCriteriaTable 1 }

SlbCurSslCfgSSLInspectFlowCriteriaEntry ::= SEQUENCE {
		slbCurSslCfgSSLInspectFlowCriteriaIndex         Integer32,
		slbCurSslCfgSSLInspectFlowCriteriaRuleId   		DisplayString,
		slbCurSslCfgSSLInspectFlowCriteriaHttpsFilter	INTEGER,
		slbCurSslCfgSSLInspectFlowCriteriaAction		INTEGER,
		slbCurSslCfgSSLInspectFlowCriteriaContMatch		INTEGER,
		slbCurSslCfgSSLInspectFlowCriteriaHttpFilter	INTEGER,
		slbCurSslCfgSSLInspectFlowCriteriaReportState	INTEGER,
		slbCurSslCfgSSLInspectFlowCriteriaDataclss	DisplayString
    }


slbCurSslCfgSSLInspectFlowCriteriaIndex  OBJECT-TYPE
    SYNTAX Integer32
    MAX-ACCESS read-only
    STATUS current
    DESCRIPTION
        "The number of the flow."
    ::= { slbCurSslCfgSSLInspectFlowCriteriaTableEntry 1 }


slbCurSslCfgSSLInspectFlowCriteriaRuleId  OBJECT-TYPE
    SYNTAX DisplayString  ( SIZE ( 1 .. 32 ) )
    MAX-ACCESS read-only
    STATUS current
    DESCRIPTION
        "The Inspect flow Criteria name id  ."
    ::= { slbCurSslCfgSSLInspectFlowCriteriaTableEntry 2 }


slbCurSslCfgSSLInspectFlowCriteriaHttpsFilter OBJECT-TYPE
    SYNTAX  INTEGER (1..2048)
    MAX-ACCESS  read-only
    STATUS  current
    DESCRIPTION
        "The Inspect flow Criteria Https filter id."
    ::= { slbCurSslCfgSSLInspectFlowCriteriaTableEntry 3 }


slbCurSslCfgSSLInspectFlowCriteriaHttpFilter OBJECT-TYPE
    SYNTAX  INTEGER (1..2048)
    MAX-ACCESS  read-only
    STATUS  current
    DESCRIPTION
        "The Inspect flow Criteria Http filter id."
    ::= { slbCurSslCfgSSLInspectFlowCriteriaTableEntry 4 }

slbCurSslCfgSSLInspectFlowCriteriaAction OBJECT-TYPE
    SYNTAX  INTEGER{
        inspect(1),
        bypass(2),
        unsupported(2147483647)
    }
    MAX-ACCESS read-only
    STATUS  current
    DESCRIPTION
        "The type of action if 1 so inspect, if 2 so bypass ."
    ::= { slbCurSslCfgSSLInspectFlowCriteriaTableEntry 5 }
    
slbCurSslCfgSSLInspectFlowCriteriaContMatch OBJECT-TYPE
    SYNTAX  INTEGER{
    	none(1),
        urlcategories(2),
        hostnamelist(3),
        unsupported(2147483647)
    }
    MAX-ACCESS read-only
    STATUS  current
    DESCRIPTION
        "Configures whether URL filtering or a content class is attached to the filter ."
    ::= { slbCurSslCfgSSLInspectFlowCriteriaTableEntry 6 }

slbCurSslCfgSSLInspectFlowCriteriaReportState OBJECT-TYPE
    SYNTAX  INTEGER{
        enabled(1),
        disabled(0),
        unsupported(2147483647)
    }
    MAX-ACCESS read-only
    STATUS  current
    DESCRIPTION
        "report state ena or disable ."
    ::= { slbCurSslCfgSSLInspectFlowCriteriaTableEntry 7 }

slbCurSslCfgSSLInspectFlowCriteriaDataclss OBJECT-TYPE
    SYNTAX DisplayString  ( SIZE ( 1 .. 32 ) )
    MAX-ACCESS read-only
    STATUS current
    DESCRIPTION
    "The Inspect flow Criteria dataclass."
    ::= { slbCurSslCfgSSLInspectFlowCriteriaTableEntry 8 }

--New

slbNewSslCfgSSLInspectFlowCriteriaTable OBJECT-TYPE
    SYNTAX SEQUENCE OF SlbNewSslCfgSSLInspectFlowCriteriaEntry
    MAX-ACCESS not-accessible
    STATUS current
    DESCRIPTION
        "The table of SSL Inspection Flow Criteria.
         Note:This mib is not supported for VX instance of Virtualization."
    ::= { sslInspectionFlow 6 }

slbNewSslCfgSSLInspectFlowCriteriaTableEntry OBJECT-TYPE
    SYNTAX SlbNewSslCfgSSLInspectFlowCriteriaEntry
    MAX-ACCESS not-accessible
    STATUS current
    DESCRIPTION
        "Information about a particular Criteria in the Flow."
    INDEX { slbNewSslCfgSSLInspectFlowCriteriaIndex , slbNewSslCfgSSLInspectFlowCriteriaRuleId}
    ::= { slbNewSslCfgSSLInspectFlowCriteriaTable 1 }

SlbNewSslCfgSSLInspectFlowCriteriaEntry ::= SEQUENCE {
		slbNewSslCfgSSLInspectFlowCriteriaIndex         Integer32,
		slbNewSslCfgSSLInspectFlowCriteriaRuleId   		DisplayString,
		slbNewSslCfgSSLInspectFlowCriteriaHttpsFilter	INTEGER,
		slbNewSslCfgSSLInspectFlowCriteriaHttpFilter	INTEGER,
		slbNewSslCfgSSLInspectFlowCriteriaAction		INTEGER,
		slbNewSslCfgSSLInspectFlowCriteriaContMatch     INTEGER,
		slbNewSslCfgSSLInspectFlowCriteriaDelete		INTEGER,
		slbNewSslCfgSSLInspectFlowCriteriaReportState	INTEGER,
                slbNewSslCfgSSLInspectFlowCriteriaDataclss      DisplayString
    }


slbNewSslCfgSSLInspectFlowCriteriaIndex  OBJECT-TYPE
    SYNTAX Integer32
    MAX-ACCESS  read-create
    STATUS current
    DESCRIPTION
        "The number of the flow."
    ::= { slbNewSslCfgSSLInspectFlowCriteriaTableEntry 1 }


slbNewSslCfgSSLInspectFlowCriteriaRuleId  OBJECT-TYPE
    SYNTAX DisplayString  ( SIZE ( 1 .. 32 ) )
    MAX-ACCESS  read-create 
	STATUS current
    DESCRIPTION
        "The Inspect flow Criteria name id  ."
    ::= { slbNewSslCfgSSLInspectFlowCriteriaTableEntry 2 }


slbNewSslCfgSSLInspectFlowCriteriaHttpsFilter OBJECT-TYPE
    SYNTAX  INTEGER (0..2048)
    MAX-ACCESS  read-create 
    STATUS  current
    DESCRIPTION
        "The Inspect flow Criteria Https filter id."
    ::= { slbNewSslCfgSSLInspectFlowCriteriaTableEntry 3 }


slbNewSslCfgSSLInspectFlowCriteriaHttpFilter OBJECT-TYPE
    SYNTAX  INTEGER (0..2048)
    MAX-ACCESS  read-create 
    STATUS  current
    DESCRIPTION
        "The Inspect flow Criteria Http filter id."
    ::= { slbNewSslCfgSSLInspectFlowCriteriaTableEntry 4 }


slbNewSslCfgSSLInspectFlowCriteriaAction OBJECT-TYPE
    SYNTAX  INTEGER{
        inspect(1),
        bypass(2),
        unsupported(2147483647)
    }
    MAX-ACCESS  read-create
    STATUS  current
    DESCRIPTION
        "The type of action if 1 so inspect, if 2 so bypass ."
    ::= { slbNewSslCfgSSLInspectFlowCriteriaTableEntry 5 }

slbNewSslCfgSSLInspectFlowCriteriaContMatch OBJECT-TYPE
    SYNTAX  INTEGER{
    	none(1),
        urlcategories(2),
        hostnamelist(3),
        unsupported(2147483647)
    }
    MAX-ACCESS read-create
    STATUS  current
    DESCRIPTION
        "Configures whether URL filtering or a content class is attached to the filter ."
    ::= { slbNewSslCfgSSLInspectFlowCriteriaTableEntry 6 }


slbNewSslCfgSSLInspectFlowCriteriaDelete OBJECT-TYPE
    SYNTAX INTEGER {
        other(1),
        delete(2),
        unsupported(2147483647)
        }
    MAX-ACCESS  read-create
    STATUS  current
    DESCRIPTION
        "By setting the value to delete(2), the entire row is
         deleted."
    ::= { slbNewSslCfgSSLInspectFlowCriteriaTableEntry 7 }

slbNewSslCfgSSLInspectFlowCriteriaReportState OBJECT-TYPE
    SYNTAX  INTEGER{
        enabled(1),
       disabled(0),
       unsupported(2147483647)
    }
    MAX-ACCESS  read-create
    STATUS  current
    DESCRIPTION
        "report ena or disable."
    ::= { slbNewSslCfgSSLInspectFlowCriteriaTableEntry 8 }


slbNewSslCfgSSLInspectFlowCriteriaDataclss OBJECT-TYPE
    SYNTAX DisplayString  ( SIZE ( 1 .. 32 ) )
    MAX-ACCESS read-create
    STATUS current
    DESCRIPTION
    "Configure data class for the Inspect flow Criteria."
    ::= { slbNewSslCfgSSLInspectFlowCriteriaTableEntry 9 }

slbCurSslCfgHwOffld OBJECT-TYPE
    SYNTAX INTEGER {
        enabled(1),
        disabled(2),
        unsupported(2147483647)
    }
    MAX-ACCESS  read-only
    STATUS  current
    DESCRIPTION
        "Enable/disable HW SSL offloading (if available),
         Note:This mib is not supported for VX instance of Virtualization."
    ::= { sslAdvCfg 1 }

slbNewSslCfgHwOffld OBJECT-TYPE
    SYNTAX INTEGER {
        enabled(1),
        disabled(2),
        unsupported(2147483647)
    }
    MAX-ACCESS  read-write
    STATUS  current
    DESCRIPTION
        "Enable/disable HW SSL offloading (if available),
         Note:This mib is not supported for VX instance of Virtualization."
    ::= { sslAdvCfg 2 }


slbCurSslCfgOcspCacheSize OBJECT-TYPE
    SYNTAX INTEGER 

    MAX-ACCESS  read-only
    STATUS  current
    DESCRIPTION
        "OCSP cache size,
         Note:This mib is not supported for VX instance of Virtualization."
    ::= { sslAdvCfg 5 }

slbNewSslCfgOcspCacheSize OBJECT-TYPE
    SYNTAX INTEGER 
    MAX-ACCESS  read-write
    STATUS  current
    DESCRIPTION
        "OCSP cache size,
         Note:This mib is not supported for VX instance of Virtualization."
    ::= { sslAdvCfg 6 }

sslBereuseCfg         OBJECT IDENTIFIER ::= { sslAdvCfg 3 }

slbCurSslBereuseEna OBJECT-TYPE
    SYNTAX INTEGER {
        enabled(1),
        disabled(2),
        unsupported(2147483647)
    }
    MAX-ACCESS  read-only
    STATUS  current
    DESCRIPTION
        "Enable/disable Backend SSL Session reuse,
         Note:This mib is not supported for VX instance of Virtualization."
    ::= { sslBereuseCfg 1 }

slbCurSslBereuseSrcmtch OBJECT-TYPE
    SYNTAX INTEGER {
        enabled(1),
        disabled(2),
        unsupported(2147483647)
    }
    MAX-ACCESS  read-only
    STATUS  current
    DESCRIPTION
        "Enable/disable reuse for same client only.
         Note:This mib is not supported for VX instance of Virtualization."
    ::= { sslBereuseCfg 2 }

slbCurSslBereuseAging OBJECT-TYPE
    SYNTAX INTEGER (1..86400)
    MAX-ACCESS  read-only
    STATUS  current
    DESCRIPTION
        "Aging of SSL session reuse cache entries (Seconds).
         Note:This mib is not supported for VX instance of Virtualization."
    ::= { sslBereuseCfg 3 }

slbNewSslBereuseEna OBJECT-TYPE
    SYNTAX INTEGER {
        enabled(1),
        disabled(2),
        unsupported(2147483647)
    }
    MAX-ACCESS  read-write
    STATUS  current
    DESCRIPTION
        "Enable/disable Backend SSL Session reuse.
         Note:This mib is not supported for VX instance of Virtualization."
    ::= { sslBereuseCfg 4 }

slbNewSslBereuseSrcmtch OBJECT-TYPE
    SYNTAX INTEGER {
        enabled(1),
        disabled(2),
        unsupported(2147483647)
    }
    MAX-ACCESS  read-write
    STATUS  current
    DESCRIPTION
        "Enable/disable reuse for same client only.
         Note:This mib is not supported for VX instance of Virtualization."
    ::= { sslBereuseCfg 5 }

slbNewSslBereuseAging OBJECT-TYPE
    SYNTAX INTEGER (1..86400)
    MAX-ACCESS  read-write
    STATUS  current
    DESCRIPTION
        "Aging of SSL session reuse cache entries (Seconds).
         Note:This mib is not supported for VX instance of Virtualization."
    ::= { sslBereuseCfg 6 }

slbCurSslBeReuseCacheSize OBJECT-TYPE
    SYNTAX INTEGER
    MAX-ACCESS  read-only
    STATUS  current
    DESCRIPTION
        "Set BE SSL reuse cache size.
         Note:This mib is not supported for VX instance of Virtualization."
    ::= { sslBereuseCfg 7 }

slbNewSslBeReuseCacheSize OBJECT-TYPE
    SYNTAX INTEGER
    MAX-ACCESS  read-write
    STATUS  current
    DESCRIPTION
        "Set BE SSL reuse cache size.
         Note:This mib is not supported for VX instance of Virtualization."
    ::= { sslBereuseCfg 8 }

slbCurSslBereuseTicket OBJECT-TYPE
    SYNTAX INTEGER {
        enabled(1),
        disabled(2),
        unsupported(2147483647)
    }
    MAX-ACCESS  read-only
    STATUS  current
    DESCRIPTION
        "Enable/disable TLS 1.2 session ticket.
         Note:This mib is not supported for VX instance of Virtualization."
    ::= { sslBereuseCfg 9 }

slbNewSslBereuseTicket OBJECT-TYPE
    SYNTAX INTEGER {
        enabled(1),
        disabled(2),
        unsupported(2147483647)
    }
    MAX-ACCESS  read-write
    STATUS  current
    DESCRIPTION
        "Enable/disable TLS 1.2 session ticket.
         Note:This mib is not supported for VX instance of Virtualization."
    ::= { sslBereuseCfg 10 }

sslFereuseCfg         OBJECT IDENTIFIER ::= { sslAdvCfg 4 }

slbCurSslFereuseEna OBJECT-TYPE
    SYNTAX INTEGER {
        enabled(1),
        disabled(2),
        unsupported(2147483647)
    }
    MAX-ACCESS  read-only
    STATUS  current
    DESCRIPTION
        "Enable/disable Frontend SSL Session reuse,
         Note:This mib is not supported for VX instance of Virtualization."
    ::= { sslFereuseCfg 1 }

slbCurSslFereuseAging OBJECT-TYPE
    SYNTAX INTEGER (1..86400)
    MAX-ACCESS  read-only
    STATUS  current
    DESCRIPTION
        "Aging of FE SSL session reuse cache entries (Seconds),
         Note:This mib is not supported for VX instance of Virtualization."
    ::= { sslFereuseCfg 2 }

slbNewSslFereuseEna OBJECT-TYPE
    SYNTAX INTEGER {
        enabled(1),
        disabled(2),
        unsupported(2147483647)
    }
    MAX-ACCESS  read-write
    STATUS  current
    DESCRIPTION
        "Enable/disable Frontend SSL Session reuse,
         Note:This mib is not supported for VX instance of Virtualization."
    ::= { sslFereuseCfg 3 }

slbNewSslFereuseAging OBJECT-TYPE
    SYNTAX INTEGER (1..86400)
    MAX-ACCESS  read-write
    STATUS  current
    DESCRIPTION
        "Aging of FE SSL session reuse cache entries (Seconds),
         Note:This mib is not supported for VX instance of Virtualization."
    ::= { sslFereuseCfg 4 }

slbCurSslFereuseTcktSize OBJECT-TYPE
    SYNTAX INTEGER (10000..100000000)
    MAX-ACCESS  read-only
    STATUS  current
    DESCRIPTION
        "Set session ticket table size for 0-RTT,
         Note:This mib is not supported for VX instance of Virtualization."
    ::= { sslFereuseCfg 5 }

slbNewSslFereuseTcktSize OBJECT-TYPE
    SYNTAX INTEGER (10000..100000000)
    MAX-ACCESS  read-write
    STATUS  current
    DESCRIPTION
        "Set session ticket table size for 0-RTT,
         Note:This mib is not supported for VX instance of Virtualization."
    ::= { sslFereuseCfg 6 }

slbCurSslFeReuseCacheSize OBJECT-TYPE
    SYNTAX INTEGER
    MAX-ACCESS  read-only
    STATUS  current
    DESCRIPTION
        "Set FE SSL reuse cache size.
         Note:This mib is not supported for VX instance of Virtualization."
    ::= { sslFereuseCfg 7 }

slbNewSslFeReuseCacheSize OBJECT-TYPE
    SYNTAX INTEGER
    MAX-ACCESS  read-write
    STATUS  current
    DESCRIPTION
        "Set FE SSL reuse cache size.
         Note:This mib is not supported for VX instance of Virtualization."
    ::= { sslFereuseCfg 8 }

slbCurSslFeReuseTicketKeyRollInt OBJECT-TYPE
    SYNTAX INTEGER
    MAX-ACCESS  read-only
    STATUS  current
    DESCRIPTION
        "Set Ticket Key roll interval in minutes,
         Note:This mib is not supported for VX instance of Virtualization."
    ::= { sslFereuseCfg 9 }

slbNewSslFeReuseTicketKeyRollInt OBJECT-TYPE
    SYNTAX INTEGER (1..10080)
    MAX-ACCESS  read-write
    STATUS  current
    DESCRIPTION
        "Set Ticket Key roll interval in minutes,
         Note:This mib is not supported for VX instance of Virtualization."
    ::= { sslFereuseCfg 10 }

slbCurSslFeReuseTicketKeyGraceTime OBJECT-TYPE
    SYNTAX INTEGER
    MAX-ACCESS  read-only
    STATUS  current
    DESCRIPTION
        "Set Ticket Key grace time in seconds,
         Note:This mib is not supported for VX instance of Virtualization."
    ::= { sslFereuseCfg 11 }

slbNewSslFeReuseTicketKeyGraceTime OBJECT-TYPE
    SYNTAX INTEGER (1..3600)
    MAX-ACCESS  read-write
    STATUS  current
    DESCRIPTION
        "Set Ticket Key grace time in seconds,
         Note:This mib is not supported for VX instance of Virtualization."
    ::= { sslFereuseCfg 12 }

slbCurSslFeReuseTicket OBJECT-TYPE
    SYNTAX INTEGER {
        enabled(1),
        disabled(2),
        unsupported(2147483647)
    }
    MAX-ACCESS  read-only
    STATUS  current
    DESCRIPTION
        "Enable/disable TLS 1.2 session ticket,
         Note:This mib is not supported for VX instance of Virtualization."
    ::= { sslFereuseCfg 13 }

slbNewSslFeReuseTicket OBJECT-TYPE
    SYNTAX INTEGER {
        enabled(1),
        disabled(2),
        unsupported(2147483647)
    }
    MAX-ACCESS  read-write
    STATUS  current
    DESCRIPTION
        "Enable/disable TLS 1.2 session ticket,
         Note:This mib is not supported for VX instance of Virtualization."
    ::= { sslFereuseCfg 14 }

-- Service Mapping Real Port Table 

slbSmtportTableMaxSize OBJECT-TYPE
    SYNTAX  Integer32 
    MAX-ACCESS  read-only 
    STATUS  current 
    DESCRIPTION 
        "The maximum number of entries in service mapping real port table.
         Note:This mib is not supported for VX instance of Virtualization." 
    ::= { smtportCfg 1 }

slbCurCfgSmtportTable OBJECT-TYPE
    SYNTAX  SEQUENCE OF SlbCurCfgSmtportEntry 
    MAX-ACCESS  not-accessible
    STATUS  current
    DESCRIPTION
        "The service mapping real port table.
         Note:This mib is not supported for VX instance of Virtualization."
    ::= { smtportCfg 2 }

slbCurCfgSmtportEntry OBJECT-TYPE
    SYNTAX  SlbCurCfgSmtportEntry
    MAX-ACCESS  not-accessible
    STATUS  current
    DESCRIPTION
        "A row in the service mapping real port table."
    INDEX   { slbCurCfgSmtportIndex }
    ::= { slbCurCfgSmtportTable 1 }

SlbCurCfgSmtportEntry ::= SEQUENCE {
    slbCurCfgSmtportIndex          Integer32,
    slbCurCfgSmtportNum            INTEGER
    }

slbCurCfgSmtportIndex OBJECT-TYPE 
    SYNTAX  Integer32 
    MAX-ACCESS  read-only 
    STATUS  current 
    DESCRIPTION 
        "The service mapping real port index." 
    ::= { slbCurCfgSmtportEntry 1 }

slbCurCfgSmtportNum OBJECT-TYPE  
    SYNTAX  INTEGER (2..65534)
    MAX-ACCESS  read-only  
    STATUS  current  
    DESCRIPTION 
        "The service mapping real port number."  
    ::= { slbCurCfgSmtportEntry 2 } 

slbNewCfgSmtportTable OBJECT-TYPE
    SYNTAX  SEQUENCE OF SlbNewCfgSmtportEntry 
    MAX-ACCESS  not-accessible
    STATUS  current
    DESCRIPTION
        "The table of real server service ports.
         Note:This mib is not supported for VX instance of Virtualization."
    ::= { smtportCfg 3 }

slbNewCfgSmtportEntry OBJECT-TYPE
    SYNTAX  SlbNewCfgSmtportEntry
    MAX-ACCESS  not-accessible
    STATUS  current
    DESCRIPTION
        "A row in the service mapping real port table."
    INDEX   { slbNewCfgSmtportIndex }
    ::= { slbNewCfgSmtportTable 1 }

SlbNewCfgSmtportEntry ::= SEQUENCE {
    slbNewCfgSmtportIndex          Integer32,
    slbNewCfgSmtportNum            INTEGER,
    slbNewCfgSmtportDelete         INTEGER
    }

slbNewCfgSmtportIndex OBJECT-TYPE 
    SYNTAX  Integer32 
    MAX-ACCESS  read-only 
    STATUS  current 
    DESCRIPTION 
        "The service mapping real port index" 
    ::= { slbNewCfgSmtportEntry 1 }

slbNewCfgSmtportNum OBJECT-TYPE  
    SYNTAX  INTEGER (2..65534)
    MAX-ACCESS  read-create  
    STATUS  current  
    DESCRIPTION 
        "The service mapping real port number."  
    ::= { slbNewCfgSmtportEntry 2 } 

slbNewCfgSmtportDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { slbNewCfgSmtportEntry 3 }

slbSmtportTableAvaibleIndex OBJECT-TYPE
    SYNTAX  Integer32
    MAX-ACCESS  read-only
    STATUS  current
    DESCRIPTION
        "The first free real port index of the Service Mapping Table. Value 0 will be returned
         when all 16 real ports are configured.
         Note:This mib is not supported for VX instance of Virtualization."
    ::= { smtportCfg 4 }


slbWlmTableMaxSize OBJECT-TYPE
    SYNTAX Integer32 
    MAX-ACCESS read-only 
    STATUS current 
    DESCRIPTION 
        "The maximum number of entries in Workload Manager table.
         Note:This mib is not supported for VX instance of Virtualization."
    ::= { wlmCfg 1 }

slbCurCfgWlmTable OBJECT-TYPE
    SYNTAX SEQUENCE OF SlbCurCfgWlmEntry
    MAX-ACCESS not-accessible
    STATUS current
    DESCRIPTION
        "The table of Workload Managers configuration.
         Note:This mib is not supported for VX instance of Virtualization."
    ::= { wlmCfg 2 }

slbCurCfgWlmEntry OBJECT-TYPE
    SYNTAX SlbCurCfgWlmEntry
    MAX-ACCESS not-accessible
    STATUS current
    DESCRIPTION
        "Information about a particular Workload Manager configuration."
    INDEX { slbCurCfgWlmIndex }
    ::= { slbCurCfgWlmTable 1 }
 
SlbCurCfgWlmEntry ::= SEQUENCE {
    slbCurCfgWlmIndex           Integer32,
    slbCurCfgWlmIpAddr          IpAddress,
    slbCurCfgWlmPort            INTEGER,
    slbCurCfgWlmGroups          DisplayString,
    slbCurCfgWlmState           INTEGER
    }

slbCurCfgWlmIndex OBJECT-TYPE
    SYNTAX  Integer32
    MAX-ACCESS  read-only
    STATUS  current
    DESCRIPTION
        "The Workload Manager number" 
    ::= { slbCurCfgWlmEntry 1 }

slbCurCfgWlmIpAddr OBJECT-TYPE
    SYNTAX  IpAddress
    MAX-ACCESS  read-only
    STATUS  current
    DESCRIPTION
        "IP address of the Workload Manager."
    ::= { slbCurCfgWlmEntry 2 }

slbCurCfgWlmPort OBJECT-TYPE
    SYNTAX  INTEGER (0..65534)
    MAX-ACCESS  read-only
    STATUS  current
    DESCRIPTION
        "The port number for the Workload Manager." 
    ::= { slbCurCfgWlmEntry 3 }

slbCurCfgWlmGroups OBJECT-TYPE
    SYNTAX DisplayString  ( SIZE ( 0 .. 255  ) ) 
    MAX-ACCESS read-only
    STATUS current
    DESCRIPTION 
        "The group number for the Workload Manager."
    ::= { slbCurCfgWlmEntry 4 }

slbCurCfgWlmState OBJECT-TYPE
    SYNTAX INTEGER {
        enabled(1),
        disabled(2),
        unsupported(2147483647)
    }
    MAX-ACCESS read-only
    STATUS current
    DESCRIPTION
        "Connection state of the Workload Manager."
    ::= { slbCurCfgWlmEntry 5 }

slbNewCfgWlmTable OBJECT-TYPE
    SYNTAX SEQUENCE OF SlbNewCfgWlmEntry
    MAX-ACCESS not-accessible
    STATUS current
    DESCRIPTION
        "The table of Workload Managers configuration.
         Note:This mib is not supported for VX instance of Virtualization."
    ::= { wlmCfg 3 }

slbNewCfgWlmEntry OBJECT-TYPE
    SYNTAX SlbNewCfgWlmEntry
    MAX-ACCESS not-accessible
    STATUS current
    DESCRIPTION
        "Information about a particular Workload Manager configuration."
    INDEX { slbNewCfgWlmIndex }
    ::= { slbNewCfgWlmTable 1 }
 
SlbNewCfgWlmEntry ::= SEQUENCE {
    slbNewCfgWlmIndex           Integer32,
    slbNewCfgWlmIpAddr          IpAddress,
    slbNewCfgWlmPort            INTEGER,
    slbNewCfgWlmDelete          INTEGER,
    slbNewCfgWlmGroups          DisplayString,
    slbNewCfgWlmState           INTEGER
    }

slbNewCfgWlmIndex OBJECT-TYPE
    SYNTAX  Integer32
    MAX-ACCESS  read-only
    STATUS  current
    DESCRIPTION
        "The Workload Manager number" 
    ::= { slbNewCfgWlmEntry 1 }

slbNewCfgWlmIpAddr OBJECT-TYPE
    SYNTAX  IpAddress
    MAX-ACCESS  read-create
    STATUS  current
    DESCRIPTION
        "IP address of the Workload Manager."
    ::= { slbNewCfgWlmEntry 2 }

slbNewCfgWlmPort OBJECT-TYPE
    SYNTAX  INTEGER (0..65534)
    MAX-ACCESS  read-create
    STATUS  current
    DESCRIPTION
        "The port number for the Workload Manager." 
    ::= { slbNewCfgWlmEntry 3 }

slbNewCfgWlmDelete OBJECT-TYPE
    SYNTAX  INTEGER {
        other(1),
        delete(2),
        unsupported(2147483647)
        }
    MAX-ACCESS  read-create
    STATUS  current
    DESCRIPTION
        "By setting the value to delete(2), the entire row is deleted."
    ::= { slbNewCfgWlmEntry 4 }

slbNewCfgWlmGroups OBJECT-TYPE
    SYNTAX DisplayString  ( SIZE ( 0 .. 255  ) )
    MAX-ACCESS read-only
    STATUS current
    DESCRIPTION
        "The group number for the Workload Manager."
    ::= { slbNewCfgWlmEntry 5 }

slbNewCfgWlmState OBJECT-TYPE
    SYNTAX INTEGER {
        enabled(1),
            disabled(2),
        unsupported(2147483647)
    }
    MAX-ACCESS read-only
    STATUS current
    DESCRIPTION
        "Connection state of the Workload Manager."
    ::= { slbNewCfgWlmEntry 6 }


slbCurAcclCfgCachememcache OBJECT-TYPE
   SYNTAX  INTEGER (1..50)
   MAX-ACCESS  read-only
   STATUS  current
   DESCRIPTION
       "Maximum percentage of Alteon RAM to be allocate for caching.
        Note:This mib is not supported for VX instance of Virtualization."
   ::= { caching 1}

slbNewAcclCfgCachememcache OBJECT-TYPE
   SYNTAX  INTEGER (1..50)
   MAX-ACCESS  read-write
   STATUS  current
   DESCRIPTION
       "Defines the maximum percentage of Alteon RAM to be allocate for caching.
        Note:This mib is not supported for VX instance of Virtualization."
   ::= { caching 2}

slbCurAcclCfgCacheOnOff OBJECT-TYPE
   SYNTAX  INTEGER {
       on(1),
       off(2),
       unsupported(2147483647)
       }
   MAX-ACCESS  read-only
   STATUS  current
   DESCRIPTION
       "Globally ON or OFF of caching.
        Note:This mib is not supported for VX instance of Virtualization."
   ::= { caching 3}

slbNewAcclCfgCacheOnOff OBJECT-TYPE
   SYNTAX  INTEGER {
       on(1),
       off(2),
       unsupported(2147483647)
       }
   MAX-ACCESS  read-write
   STATUS  current
   DESCRIPTION
       "Globally ON or OFF of caching.
        Note:This mib is not supported for VX instance of Virtualization."
   ::= { caching 4}

slbCurAcclCfgCachePolTable OBJECT-TYPE
    SYNTAX  SEQUENCE OF SlbCurAcclCfgCachePolEntry
    MAX-ACCESS  not-accessible
    STATUS  current
    DESCRIPTION
        "The table for configuring caching policy.
         Note:This mib is not supported for VX instance of Virtualization."
    ::= { caching 5 }

slbCurAcclCfgCachePolEntry OBJECT-TYPE
    SYNTAX  SlbCurAcclCfgCachePolEntry
    MAX-ACCESS  not-accessible
    STATUS  current
    DESCRIPTION
        "A row in the caching policy table."
    INDEX   { slbCurAcclCfgCachePolNameIdIndex }
    ::= { slbCurAcclCfgCachePolTable 1 }

SlbCurAcclCfgCachePolEntry ::= SEQUENCE {
    slbCurAcclCfgCachePolNameIdIndex          DisplayString,
    slbCurAcclCfgCachePolName                 DisplayString,
    slbCurAcclCfgCachePolExpireTime           INTEGER,
    slbCurAcclCfgCachePolMinSize              INTEGER,
    slbCurAcclCfgCachePolMaxSize              INTEGER,
    slbCurAcclCfgCachePolURLList              DisplayString,
    slbCurAcclCfgCachePolStore                INTEGER,
    slbCurAcclCfgCachePolServe                INTEGER,
    slbCurAcclCfgCachePolQuery                INTEGER,
    slbCurAcclCfgCachePolBrowser              INTEGER,
    slbCurAcclCfgCachePolAdminStatus          INTEGER,
    slbCurAcclCfgCachePolDummy                INTEGER,
    slbCurAcclCfgCachePolCombineCSS           INTEGER,
    slbCurAcclCfgCachePolCombineJS            INTEGER,
    slbCurAcclCfgCachePolDynamicCache         INTEGER,
    slbCurAcclCfgCachePolInlineCSS            INTEGER,
    slbCurAcclCfgCachePolInlineJS             INTEGER,
    slbCurAcclCfgCachePolImageDim             INTEGER,
    slbCurAcclCfgCachePolRemoveCmnt           INTEGER,
    slbCurAcclCfgCachePolRemoveWS             INTEGER,
    slbCurAcclCfgCachePolTrimURL              INTEGER,
    slbCurAcclCfgCachePolOptList              DisplayString
    }

slbCurAcclCfgCachePolNameIdIndex OBJECT-TYPE
    SYNTAX   DisplayString (SIZE (0..32))
    MAX-ACCESS  read-only
    STATUS  current
    DESCRIPTION
        "The caching policy ID(key id) as an index."
    ::= { slbCurAcclCfgCachePolEntry 1 }

slbCurAcclCfgCachePolName OBJECT-TYPE
    SYNTAX   DisplayString (SIZE (0..32))
    MAX-ACCESS  read-only
    STATUS  current
    DESCRIPTION
        "Cache policy name."
    ::= { slbCurAcclCfgCachePolEntry 2 }

slbCurAcclCfgCachePolExpireTime OBJECT-TYPE
    SYNTAX  INTEGER 
    MAX-ACCESS  read-only
    STATUS  current
    DESCRIPTION
        "Maximum expiration time in seconds."
    ::= { slbCurAcclCfgCachePolEntry 3 }

slbCurAcclCfgCachePolMinSize OBJECT-TYPE
    SYNTAX  INTEGER 
    MAX-ACCESS  read-only
    STATUS  current
    DESCRIPTION
        "Minimum Object size to be stored in bytes."
    ::= { slbCurAcclCfgCachePolEntry 4 }

slbCurAcclCfgCachePolMaxSize OBJECT-TYPE
    SYNTAX  INTEGER
    MAX-ACCESS  read-only
    STATUS  current
    DESCRIPTION
        "Maximum Object size to be stored in bytes." 
    ::= { slbCurAcclCfgCachePolEntry 5 }

slbCurAcclCfgCachePolURLList OBJECT-TYPE
    SYNTAX   DisplayString (SIZE (0..32))
    MAX-ACCESS  read-only
    STATUS  current
    DESCRIPTION
        "URL list which is associated with this policy."
    ::= { slbCurAcclCfgCachePolEntry 6 }

slbCurAcclCfgCachePolStore OBJECT-TYPE
    SYNTAX  INTEGER {
        srvrhdr(1),
        cacheall(2),
        unsupported(2147483647)
        }
    MAX-ACCESS  read-only
    STATUS  current
    DESCRIPTION
        "Caching behavior for storing new objects in cache."
    ::= { slbCurAcclCfgCachePolEntry 7 }

slbCurAcclCfgCachePolServe OBJECT-TYPE
    SYNTAX  INTEGER {
        clnthdr(1),
        refresh(2),
        cache(3),
        unsupported(2147483647)
        }
    MAX-ACCESS  read-only
    STATUS  current
    DESCRIPTION
        "Cache behavior when serving clients with objects."
    ::= { slbCurAcclCfgCachePolEntry 8 }

slbCurAcclCfgCachePolQuery OBJECT-TYPE
    SYNTAX  INTEGER {
        consider(1),
        ignore(2),
        unsupported(2147483647)
        }
    MAX-ACCESS  read-only
    STATUS  current
    DESCRIPTION
        "Specifies whether query parameters added to object URL should be considered when storing/serving object from cache."
    ::= { slbCurAcclCfgCachePolEntry 9 }

slbCurAcclCfgCachePolBrowser OBJECT-TYPE
    SYNTAX  INTEGER {
        enabled(1),
        disabled(2),
        unsupported(2147483647)
        }
    MAX-ACCESS  read-only
    STATUS  current
    DESCRIPTION
        "Optimize browser cache."
    ::= { slbCurAcclCfgCachePolEntry 10 }

slbCurAcclCfgCachePolAdminStatus OBJECT-TYPE
    SYNTAX  INTEGER {
        enabled(1),
        disabled(2),
        unsupported(2147483647)
        }
    MAX-ACCESS  read-only
    STATUS  current
    DESCRIPTION
        "Status (enable/disable) of caching policy."
    ::= { slbCurAcclCfgCachePolEntry 11 }

slbCurAcclCfgCachePolDummy OBJECT-TYPE
    SYNTAX  INTEGER {
        enabled(1),
        disabled(2),
        unsupported(2147483647)
        }
    MAX-ACCESS  read-only
    STATUS  current
    DESCRIPTION
        "Dummy field to maintain offsets between cur and new."
    ::= { slbCurAcclCfgCachePolEntry 12 }

slbCurAcclCfgCachePolCombineCSS OBJECT-TYPE
    SYNTAX  INTEGER {
        enabled(1),
        disabled(2),
        unsupported(2147483647)
        }
    MAX-ACCESS  read-only
    STATUS  current
    DESCRIPTION
        "Combine CSS files."
    ::= { slbCurAcclCfgCachePolEntry 13 }

slbCurAcclCfgCachePolCombineJS OBJECT-TYPE
    SYNTAX  INTEGER {
        enabled(1),
        disabled(2),
        unsupported(2147483647)
        }
    MAX-ACCESS  read-only
    STATUS  current
    DESCRIPTION
        "Combine JavaScript files."
    ::= { slbCurAcclCfgCachePolEntry 14 }

slbCurAcclCfgCachePolDynamicCache OBJECT-TYPE
    SYNTAX  INTEGER {
        enabled(1),
        disabled(2),
        unsupported(2147483647)
        }
    MAX-ACCESS  read-only
    STATUS  current
    DESCRIPTION
        "Enhance broswer cache."
    ::= { slbCurAcclCfgCachePolEntry 15 }

slbCurAcclCfgCachePolInlineCSS OBJECT-TYPE
    SYNTAX  INTEGER {
        enabled(1),
        disabled(2),
        unsupported(2147483647)
        }
    MAX-ACCESS  read-only
    STATUS  current
    DESCRIPTION
        "Inline small CSS files."
    ::= { slbCurAcclCfgCachePolEntry 16 }

slbCurAcclCfgCachePolInlineJS OBJECT-TYPE
    SYNTAX  INTEGER {
        enabled(1),
        disabled(2),
        unsupported(2147483647)
        }
    MAX-ACCESS  read-only
    STATUS  current
    DESCRIPTION
        "Inline small JavaScript files."
    ::= { slbCurAcclCfgCachePolEntry 17 }

slbCurAcclCfgCachePolImageDim OBJECT-TYPE
    SYNTAX  INTEGER {
        enabled(1),
        disabled(2),
        unsupported(2147483647)
        }
    MAX-ACCESS  read-only
    STATUS  current
    DESCRIPTION
        "Update image dimensions in html."
    ::= { slbCurAcclCfgCachePolEntry 18 }

slbCurAcclCfgCachePolRemoveCmnt OBJECT-TYPE
    SYNTAX  INTEGER {
        enabled(1),
        disabled(2),
        unsupported(2147483647)
        }
    MAX-ACCESS  read-only
    STATUS  current
    DESCRIPTION
        "Remove comments from html."
    ::= { slbCurAcclCfgCachePolEntry 19 }

slbCurAcclCfgCachePolRemoveWS OBJECT-TYPE
    SYNTAX  INTEGER {
        enabled(1),
        disabled(2),
        unsupported(2147483647)
        }
    MAX-ACCESS  read-only
    STATUS  current
    DESCRIPTION
        "Remove unnecessary whitespace from html code."
    ::= { slbCurAcclCfgCachePolEntry 20 }

slbCurAcclCfgCachePolTrimURL OBJECT-TYPE
    SYNTAX  INTEGER {
        enabled(1),
        disabled(2),
        unsupported(2147483647)
        }
    MAX-ACCESS  read-only
    STATUS  current
    DESCRIPTION
        "Trim absolute URLs in html."
    ::= { slbCurAcclCfgCachePolEntry 21 }

slbCurAcclCfgCachePolOptList OBJECT-TYPE
    SYNTAX   DisplayString (SIZE (0..32))
    MAX-ACCESS  read-only
    STATUS  current
    DESCRIPTION
        "Optimization exception list which is associated with this policy."
    ::= { slbCurAcclCfgCachePolEntry 22 }

slbNewAcclCfgCachePolTable OBJECT-TYPE
    SYNTAX  SEQUENCE OF SlbNewAcclCfgCachePolEntry
    MAX-ACCESS  not-accessible
    STATUS  current
    DESCRIPTION
        "The table for configuring caching policy.
         Note:This mib is not supported for VX instance of Virtualization."
    ::= { caching 6 }

slbNewAcclCfgCachePolEntry OBJECT-TYPE
    SYNTAX  SlbNewAcclCfgCachePolEntry
    MAX-ACCESS  not-accessible
    STATUS  current
    DESCRIPTION
        "A row in the caching policy table."
    INDEX   { slbNewAcclCfgCachePolNameIdIndex }
    ::= { slbNewAcclCfgCachePolTable 1 }

SlbNewAcclCfgCachePolEntry ::= SEQUENCE {
    slbNewAcclCfgCachePolNameIdIndex          DisplayString,
    slbNewAcclCfgCachePolName                 DisplayString,
    slbNewAcclCfgCachePolExpireTime           INTEGER,
    slbNewAcclCfgCachePolMinSize              INTEGER,
    slbNewAcclCfgCachePolMaxSize              INTEGER,
    slbNewAcclCfgCachePolURLList              DisplayString,
    slbNewAcclCfgCachePolStore                INTEGER,
    slbNewAcclCfgCachePolServe                INTEGER,
    slbNewAcclCfgCachePolQuery                INTEGER,
    slbNewAcclCfgCachePolBrowser              INTEGER,
    slbNewAcclCfgCachePolAdminStatus          INTEGER,
    slbNewAcclCfgCachePolDelete               INTEGER,
    slbNewAcclCfgCachePolCombineCSS           INTEGER,
    slbNewAcclCfgCachePolCombineJS            INTEGER,
    slbNewAcclCfgCachePolDynamicCache         INTEGER,
    slbNewAcclCfgCachePolInlineCSS            INTEGER,
    slbNewAcclCfgCachePolInlineJS             INTEGER,
    slbNewAcclCfgCachePolImageDim             INTEGER,
    slbNewAcclCfgCachePolRemoveCmnt           INTEGER,
    slbNewAcclCfgCachePolRemoveWS             INTEGER,
    slbNewAcclCfgCachePolTrimURL              INTEGER,
    slbNewAcclCfgCachePolOptList              DisplayString
    }

slbNewAcclCfgCachePolNameIdIndex OBJECT-TYPE
    SYNTAX   DisplayString (SIZE (0..32))
    MAX-ACCESS  read-only
    STATUS  current
    DESCRIPTION
        "The caching policy ID(key id) as an index, length of the string should be 32 characters."
    ::= { slbNewAcclCfgCachePolEntry 1 }

slbNewAcclCfgCachePolName OBJECT-TYPE
    SYNTAX   DisplayString (SIZE (0..32))
    MAX-ACCESS  read-create
    STATUS  current
    DESCRIPTION
        "Cache policy name, length of the string should be 32 characters."
    ::= { slbNewAcclCfgCachePolEntry 2 }

slbNewAcclCfgCachePolExpireTime OBJECT-TYPE
    SYNTAX  INTEGER
    MAX-ACCESS  read-create
    STATUS  current
    DESCRIPTION
        "Set maximum expiration time, Range is 60- 43,200,000 seconds (~500 days)."
    ::= { slbNewAcclCfgCachePolEntry 3 }

slbNewAcclCfgCachePolMinSize OBJECT-TYPE
    SYNTAX  INTEGER
    MAX-ACCESS  read-create
    STATUS  current
    DESCRIPTION
        "Minimum Object size to be stored [Bytes], Values: 1-65536."
    ::= { slbNewAcclCfgCachePolEntry 4 }

slbNewAcclCfgCachePolMaxSize OBJECT-TYPE
    SYNTAX  INTEGER
    MAX-ACCESS  read-create
    STATUS  current
    DESCRIPTION
        "Maximum Object size to be stored [Bytes], Values: 1-512000000."
    ::= { slbNewAcclCfgCachePolEntry 5 }

slbNewAcclCfgCachePolURLList OBJECT-TYPE
    SYNTAX   DisplayString (SIZE (0..32))
    MAX-ACCESS  read-create
    STATUS  current
    DESCRIPTION
        "URL list to be associated with this policy, Values: 1-32 character string."
    ::= { slbNewAcclCfgCachePolEntry 6 }

slbNewAcclCfgCachePolStore OBJECT-TYPE
    SYNTAX  INTEGER {
        srvrhdr(1),
        cacheall(2),
        unsupported(2147483647)
        }
    MAX-ACCESS  read-create
    STATUS  current
    DESCRIPTION
        "Define caching behavior for storing New objects in cache."
    ::= { slbNewAcclCfgCachePolEntry 7 }

slbNewAcclCfgCachePolServe OBJECT-TYPE
    SYNTAX  INTEGER {
        clnthdr(1),
        refresh(2),
        cache(3),
        unsupported(2147483647)
        }
    MAX-ACCESS  read-create
    STATUS  current
    DESCRIPTION
        "Define cache behavior when serving clients with objects."
    ::= { slbNewAcclCfgCachePolEntry 8 }

slbNewAcclCfgCachePolQuery OBJECT-TYPE
    SYNTAX  INTEGER {
        consider(1),
        ignore(2),
        unsupported(2147483647)
        }
    MAX-ACCESS  read-create
    STATUS  current
    DESCRIPTION
        "Specifies whether query parameters added to object URL should be considered when storing/serving object from cache."
    ::= { slbNewAcclCfgCachePolEntry 9 }

slbNewAcclCfgCachePolBrowser OBJECT-TYPE
    SYNTAX  INTEGER {
        enabled(1),
        disabled(2),
        unsupported(2147483647)
        }
    MAX-ACCESS  read-create
    STATUS  current
    DESCRIPTION
        "Optimize browser cache."
    ::= { slbNewAcclCfgCachePolEntry 10 }

slbNewAcclCfgCachePolAdminStatus OBJECT-TYPE
    SYNTAX  INTEGER {
        enabled(1),
        disabled(2),
        unsupported(2147483647)
        }
    MAX-ACCESS  read-create
    STATUS  current
    DESCRIPTION
        "Enable or disable caching policy."
    ::= { slbNewAcclCfgCachePolEntry 11 }

slbNewAcclCfgCachePolDelete OBJECT-TYPE
    SYNTAX  INTEGER {
        other(1),
        delete(2),
        unsupported(2147483647)
        }
    MAX-ACCESS  read-create
    STATUS  current
    DESCRIPTION
        "Delete Caching policy."
    ::= { slbNewAcclCfgCachePolEntry 12 }

slbNewAcclCfgCachePolCombineCSS OBJECT-TYPE
    SYNTAX  INTEGER {
        enabled(1),
        disabled(2),
        unsupported(2147483647)
        }
    MAX-ACCESS  read-create
    STATUS  current
    DESCRIPTION
        "Combine CSS files."
    ::= { slbNewAcclCfgCachePolEntry 13 }

slbNewAcclCfgCachePolCombineJS OBJECT-TYPE
    SYNTAX  INTEGER {
        enabled(1),
        disabled(2),
        unsupported(2147483647)
        }
    MAX-ACCESS  read-create
    STATUS  current
    DESCRIPTION
        "Combine JavaScript files."
    ::= { slbNewAcclCfgCachePolEntry 14 }

slbNewAcclCfgCachePolDynamicCache OBJECT-TYPE
    SYNTAX  INTEGER {
        enabled(1),
        disabled(2),
        unsupported(2147483647)
        }
    MAX-ACCESS  read-create
    STATUS  current
    DESCRIPTION
        "Enhance broswer cache."
    ::= { slbNewAcclCfgCachePolEntry 15 }

slbNewAcclCfgCachePolInlineCSS OBJECT-TYPE
    SYNTAX  INTEGER {
        enabled(1),
        disabled(2),
        unsupported(2147483647)
        }
    MAX-ACCESS  read-create
    STATUS  current
    DESCRIPTION
        "Inline small CSS files."
    ::= { slbNewAcclCfgCachePolEntry 16 }

slbNewAcclCfgCachePolInlineJS OBJECT-TYPE
    SYNTAX  INTEGER {
        enabled(1),
        disabled(2),
        unsupported(2147483647)
        }
    MAX-ACCESS  read-create
    STATUS  current
    DESCRIPTION
        "Inline small JavaScript files."
    ::= { slbNewAcclCfgCachePolEntry 17 }

slbNewAcclCfgCachePolImageDim OBJECT-TYPE
    SYNTAX  INTEGER {
        enabled(1),
        disabled(2),
        unsupported(2147483647)
        }
    MAX-ACCESS  read-create
    STATUS  current
    DESCRIPTION
        "Update image dimensions in html."
    ::= { slbNewAcclCfgCachePolEntry 18 }

slbNewAcclCfgCachePolRemoveCmnt OBJECT-TYPE
    SYNTAX  INTEGER {
        enabled(1),
        disabled(2),
        unsupported(2147483647)
        }
    MAX-ACCESS  read-create
    STATUS  current
    DESCRIPTION
        "Remove comments from html."
    ::= { slbNewAcclCfgCachePolEntry 19 }

slbNewAcclCfgCachePolRemoveWS OBJECT-TYPE
    SYNTAX  INTEGER {
        enabled(1),
        disabled(2),
        unsupported(2147483647)
        }
    MAX-ACCESS  read-create
    STATUS  current
    DESCRIPTION
        "Remove unnecessary whitespace from html code."
    ::= { slbNewAcclCfgCachePolEntry 20 }

slbNewAcclCfgCachePolTrimURL OBJECT-TYPE
    SYNTAX  INTEGER {
        enabled(1),
        disabled(2),
        unsupported(2147483647)
        }
    MAX-ACCESS  read-create
    STATUS  current
    DESCRIPTION
        "Trim absolute URLs in html."
    ::= { slbNewAcclCfgCachePolEntry 21 }

slbNewAcclCfgCachePolOptList OBJECT-TYPE
    SYNTAX   DisplayString (SIZE (0..32))
    MAX-ACCESS  read-create
    STATUS  current
    DESCRIPTION
        "Optimization exception list to be associated with this policy, Values: 1-32 character string."
    ::= { slbNewAcclCfgCachePolEntry 22 }

slbCurAcclCfgCacheUrlListTable OBJECT-TYPE
    SYNTAX  SEQUENCE OF SlbCurAcclCfgCacheUrlListEntry
    MAX-ACCESS  not-accessible
    STATUS  current
    DESCRIPTION
        "The table for configuring caching URL LIST.
         Note:This mib is not supported for VX instance of Virtualization."
    ::= { caching 7 }

slbCurAcclCfgCacheUrlListEntry OBJECT-TYPE
    SYNTAX  SlbCurAcclCfgCacheUrlListEntry
    MAX-ACCESS  not-accessible
    STATUS  current
    DESCRIPTION
        "A row in the caching URL LIST table."
    INDEX   { slbCurAcclCfgCacheUrlListIdIndex }
    ::= { slbCurAcclCfgCacheUrlListTable 1 }

SlbCurAcclCfgCacheUrlListEntry ::= SEQUENCE {
    slbCurAcclCfgCacheUrlListIdIndex          DisplayString,
    slbCurAcclCfgCacheUrlListName             DisplayString,
    slbCurAcclCfgCacheUrlListAdminStatus          INTEGER
    }

slbCurAcclCfgCacheUrlListIdIndex OBJECT-TYPE
    SYNTAX   DisplayString (SIZE (0..32))
    MAX-ACCESS  read-only
    STATUS  current
    DESCRIPTION
        "The caching policy URL LIST (key id) as an index."
    ::= { slbCurAcclCfgCacheUrlListEntry 1 }

slbCurAcclCfgCacheUrlListName OBJECT-TYPE
    SYNTAX   DisplayString (SIZE (0..32))
    MAX-ACCESS  read-only
    STATUS  current
    DESCRIPTION
        "Cache URL LIST name."
    ::= { slbCurAcclCfgCacheUrlListEntry 2 }

slbCurAcclCfgCacheUrlListAdminStatus OBJECT-TYPE
    SYNTAX  INTEGER {
        enabled(1),
        disabled(2),
        unsupported(2147483647)
        }
    MAX-ACCESS  read-only
    STATUS  current
    DESCRIPTION
        "Status (enable/disable) of caching URL LIST."
    ::= { slbCurAcclCfgCacheUrlListEntry 3 }

slbNewAcclCfgCacheUrlListTable OBJECT-TYPE
    SYNTAX  SEQUENCE OF SlbNewAcclCfgCacheUrlListEntry
    MAX-ACCESS  not-accessible
    STATUS  current
    DESCRIPTION
        "The table for configuring caching URL LIST.
         Note:This mib is not supported for VX instance of Virtualization."
    ::= { caching 8 }

slbNewAcclCfgCacheUrlListEntry OBJECT-TYPE
    SYNTAX  SlbNewAcclCfgCacheUrlListEntry
    MAX-ACCESS  not-accessible
    STATUS  current
    DESCRIPTION
        "A row in the caching URL LIST table."
    INDEX   { slbNewAcclCfgCacheUrlListIdIndex }
    ::= { slbNewAcclCfgCacheUrlListTable 1 }

SlbNewAcclCfgCacheUrlListEntry ::= SEQUENCE {
    slbNewAcclCfgCacheUrlListIdIndex          DisplayString,
    slbNewAcclCfgCacheUrlListName             DisplayString,
    slbNewAcclCfgCacheUrlListAdminStatus      INTEGER,
    slbNewAcclCfgCacheUrlListDel              INTEGER,
    slbNewAcclCfgCacheUrlListCopy             DisplayString
    }

slbNewAcclCfgCacheUrlListIdIndex OBJECT-TYPE
    SYNTAX   DisplayString (SIZE (0..32))
    MAX-ACCESS  read-only
    STATUS  current
    DESCRIPTION
        "The caching policy URL LIST (key id) as an index."
    ::= { slbNewAcclCfgCacheUrlListEntry 1 }

slbNewAcclCfgCacheUrlListName OBJECT-TYPE
    SYNTAX   DisplayString (SIZE (0..32))
    MAX-ACCESS  read-create
    STATUS  current
    DESCRIPTION
        "Cache URL LIST name."
    ::= { slbNewAcclCfgCacheUrlListEntry 2 }

slbNewAcclCfgCacheUrlListAdminStatus OBJECT-TYPE
    SYNTAX  INTEGER {
        enabled(1),
        disabled(2),
        unsupported(2147483647)
        }
    MAX-ACCESS  read-create
    STATUS  current
    DESCRIPTION
        "Status (enable/disable) of caching URL LIST."
    ::= { slbNewAcclCfgCacheUrlListEntry 3 }

slbNewAcclCfgCacheUrlListDel OBJECT-TYPE
    SYNTAX  INTEGER {
        other(1),
        delete(2),
        unsupported(2147483647)
        }
    MAX-ACCESS  read-create
    STATUS  current
    DESCRIPTION
        "Delete Caching URL list."
    ::= { slbNewAcclCfgCacheUrlListEntry 5 }

slbNewAcclCfgCacheUrlListCopy OBJECT-TYPE
    SYNTAX   DisplayString
    MAX-ACCESS  read-create
    STATUS  current
    DESCRIPTION
        "Duplicating an entire Rule-List by defining the destination Rule-list id."
    ::= { slbNewAcclCfgCacheUrlListEntry 6 }

slbCurAcclCfgCacheUrlRuleTable OBJECT-TYPE
    SYNTAX  SEQUENCE OF SlbCurAcclCfgCacheUrlRuleEntry
    MAX-ACCESS  not-accessible
    STATUS  current
    DESCRIPTION
        "The table for configuring caching URL Rules.
         Note:This mib is not supported for VX instance of Virtualization."
    ::= { caching 9 }

slbCurAcclCfgCacheUrlRuleEntry OBJECT-TYPE
    SYNTAX  SlbCurAcclCfgCacheUrlRuleEntry
    MAX-ACCESS  not-accessible
    STATUS  current
    DESCRIPTION
        "A row in the caching URL Rule table."
    INDEX   { slbCurAcclCfgCacheUrlRuleListIdIndex, slbCurAcclCfgCacheUrlRuleIndex }
    ::= { slbCurAcclCfgCacheUrlRuleTable 1 }

SlbCurAcclCfgCacheUrlRuleEntry ::= SEQUENCE {
    slbCurAcclCfgCacheUrlRuleListIdIndex          DisplayString,
    slbCurAcclCfgCacheUrlRuleIndex                INTEGER,
    slbCurAcclCfgCacheUrlRuleName                 DisplayString,
    slbCurAcclCfgCacheUrlRuleDomainM              INTEGER,
    slbCurAcclCfgCacheUrlRuleDomain               DisplayString,
    slbCurAcclCfgCacheUrlRuleURLm                 INTEGER,
    slbCurAcclCfgCacheUrlRuleURL                  DisplayString,
    slbCurAcclCfgCacheUrlRuleExpire               INTEGER,
    slbCurAcclCfgCacheUrlRuleCache                INTEGER,
    slbCurAcclCfgCacheUrlRuleAdminStatus          INTEGER
    }

slbCurAcclCfgCacheUrlRuleListIdIndex OBJECT-TYPE
    SYNTAX   DisplayString (SIZE (0..32))
    MAX-ACCESS  read-only
    STATUS  current
    DESCRIPTION
        "The caching policy URL LIST (key id) as an index."
    ::= { slbCurAcclCfgCacheUrlRuleEntry 1 }

slbCurAcclCfgCacheUrlRuleIndex OBJECT-TYPE
    SYNTAX   INTEGER
    MAX-ACCESS  read-only
    STATUS  current
    DESCRIPTION
        "The caching URL Rule number as an index."
    ::= { slbCurAcclCfgCacheUrlRuleEntry 2 }

slbCurAcclCfgCacheUrlRuleName OBJECT-TYPE
    SYNTAX   DisplayString (SIZE (0..32))
    MAX-ACCESS  read-only
    STATUS  current
    DESCRIPTION
        "The caching URL Rule name."
    ::= { slbCurAcclCfgCacheUrlRuleEntry 3 }

slbCurAcclCfgCacheUrlRuleDomainM OBJECT-TYPE
    SYNTAX  INTEGER {
        any(1),
        text(2),
        regex(3),
        unsupported(2147483647)
        }
    MAX-ACCESS  read-only
    STATUS  current
    DESCRIPTION
        "Defines whether Domain matching should be evaluated as String, Regex or match, any (default any)."
    ::= { slbCurAcclCfgCacheUrlRuleEntry 4 }

slbCurAcclCfgCacheUrlRuleDomain OBJECT-TYPE
    SYNTAX   DisplayString (SIZE (0..254))
    MAX-ACCESS  read-only
    STATUS  current
    DESCRIPTION
        "Defines the Virtual Host for which this rule applies."
    ::= { slbCurAcclCfgCacheUrlRuleEntry 5 }

slbCurAcclCfgCacheUrlRuleURLm OBJECT-TYPE
    SYNTAX  INTEGER {
        any(1),
        text(2),
        regex(3),
        unsupported(2147483647)
        }
    MAX-ACCESS  read-only
    STATUS  current
    DESCRIPTION
        "Defines whether URL matching should be evaluated as String, Regex or match, any (default any)."
    ::= { slbCurAcclCfgCacheUrlRuleEntry 6 }

slbCurAcclCfgCacheUrlRuleURL OBJECT-TYPE
    SYNTAX   DisplayString 
    MAX-ACCESS  read-only
    STATUS  current
    DESCRIPTION
        "Defines URL of specific object (file/folder) to be matched by this rule."
    ::= { slbCurAcclCfgCacheUrlRuleEntry 7 }

slbCurAcclCfgCacheUrlRuleExpire OBJECT-TYPE
    SYNTAX   INTEGER
    MAX-ACCESS  read-only
    STATUS  current
    DESCRIPTION
        "The Maximum time for the cache object to served from cache (in seconds)."
    ::= { slbCurAcclCfgCacheUrlRuleEntry 8 }

slbCurAcclCfgCacheUrlRuleCache OBJECT-TYPE
    SYNTAX  INTEGER {
        enabled(1),
        disabled(2),
        unsupported(2147483647)
        }
    MAX-ACCESS  read-only
    STATUS  current
    DESCRIPTION
        "Defines if the matched response should be cached or not."
    ::= { slbCurAcclCfgCacheUrlRuleEntry 9 }

slbCurAcclCfgCacheUrlRuleAdminStatus OBJECT-TYPE
    SYNTAX  INTEGER {
        enabled(1),
        disabled(2),
        unsupported(2147483647)
        }
    MAX-ACCESS  read-only
    STATUS  current
    DESCRIPTION
        "Status (enable/disable) of caching URL Rule."
    ::= { slbCurAcclCfgCacheUrlRuleEntry 10 }

slbNewAcclCfgCacheUrlRuleTable OBJECT-TYPE
    SYNTAX  SEQUENCE OF SlbNewAcclCfgCacheUrlRuleEntry
    MAX-ACCESS  not-accessible
    STATUS  current
    DESCRIPTION
        "The table for configuring caching URL Rules.
         Note:This mib is not supported for VX instance of Virtualization."
    ::= { caching 10 }

slbNewAcclCfgCacheUrlRuleEntry OBJECT-TYPE
    SYNTAX  SlbNewAcclCfgCacheUrlRuleEntry
    MAX-ACCESS  not-accessible
    STATUS  current
    DESCRIPTION
        "A row in the caching URL Rule table."
    INDEX   { slbNewAcclCfgCacheUrlRuleListIdIndex, slbNewAcclCfgCacheUrlRuleIndex }
    ::= { slbNewAcclCfgCacheUrlRuleTable 1 }

SlbNewAcclCfgCacheUrlRuleEntry ::= SEQUENCE {
    slbNewAcclCfgCacheUrlRuleListIdIndex          DisplayString,
    slbNewAcclCfgCacheUrlRuleIndex                INTEGER,
    slbNewAcclCfgCacheUrlRuleName                 DisplayString,
    slbNewAcclCfgCacheUrlRuleDomainM              INTEGER,
    slbNewAcclCfgCacheUrlRuleDomain               DisplayString,
    slbNewAcclCfgCacheUrlRuleURLm                 INTEGER,
    slbNewAcclCfgCacheUrlRuleURL                  DisplayString,
    slbNewAcclCfgCacheUrlRuleExpire               INTEGER,
    slbNewAcclCfgCacheUrlRuleCache                INTEGER,
    slbNewAcclCfgCacheUrlRuleAdminStatus          INTEGER,
    slbNewAcclCfgCacheUrlRuleDelete               INTEGER,
    slbNewAcclCfgCacheUrlRuleCopy                 DisplayString 
    }

slbNewAcclCfgCacheUrlRuleListIdIndex OBJECT-TYPE
    SYNTAX   DisplayString (SIZE (0..32))
    MAX-ACCESS  read-only
    STATUS  current
    DESCRIPTION
        "The caching policy URL LIST (key id) as an index."
    ::= { slbNewAcclCfgCacheUrlRuleEntry 1 }

slbNewAcclCfgCacheUrlRuleIndex OBJECT-TYPE
    SYNTAX   INTEGER
    MAX-ACCESS  read-only
    STATUS  current
    DESCRIPTION
        "The caching URL Rule number as an index."
    ::= { slbNewAcclCfgCacheUrlRuleEntry 2 }

slbNewAcclCfgCacheUrlRuleName OBJECT-TYPE
    SYNTAX   DisplayString (SIZE (0..32))
    MAX-ACCESS  read-create
    STATUS  current
    DESCRIPTION
        "The caching URL Rule name."
    ::= { slbNewAcclCfgCacheUrlRuleEntry 3 }

slbNewAcclCfgCacheUrlRuleDomainM OBJECT-TYPE
    SYNTAX  INTEGER {
        any(1),
        text(2),
        regex(3),
        unsupported(2147483647)
        }
    MAX-ACCESS  read-create
    STATUS  current
    DESCRIPTION
        "Defines whether Domain matching should be evaluated as String, Regex or match, any (default any)."
    ::= { slbNewAcclCfgCacheUrlRuleEntry 4 }

slbNewAcclCfgCacheUrlRuleDomain OBJECT-TYPE
    SYNTAX   DisplayString (SIZE (0..254))
    MAX-ACCESS  read-create
    STATUS  current
    DESCRIPTION
        "Defines the Virtual Host for which this rule applies."
    ::= { slbNewAcclCfgCacheUrlRuleEntry 5 }

slbNewAcclCfgCacheUrlRuleURLm OBJECT-TYPE
    SYNTAX  INTEGER {
        any(1),
        text(2),
        regex(3),
        unsupported(2147483647)
        }
    MAX-ACCESS  read-create
    STATUS  current
    DESCRIPTION
        "Defines whether URL matching should be evaluated as String, Regex or match, any (default any)."
    ::= { slbNewAcclCfgCacheUrlRuleEntry 6 }

slbNewAcclCfgCacheUrlRuleURL OBJECT-TYPE
    SYNTAX   DisplayString  
    MAX-ACCESS  read-create
    STATUS  current
    DESCRIPTION
        "Defines URL of specific object (file/folder) to be matched by this rule."
    ::= { slbNewAcclCfgCacheUrlRuleEntry 7 }

slbNewAcclCfgCacheUrlRuleExpire OBJECT-TYPE
    SYNTAX   INTEGER
    MAX-ACCESS  read-create
    STATUS  current
    DESCRIPTION
        "The Maximum time for the cache object to served from cache (in seconds)."
    ::= { slbNewAcclCfgCacheUrlRuleEntry 8 }

slbNewAcclCfgCacheUrlRuleCache OBJECT-TYPE
    SYNTAX  INTEGER {
        enabled(1),
        disabled(2),
        unsupported(2147483647)
        }
    MAX-ACCESS  read-create
    STATUS  current
    DESCRIPTION
        "Defines if the matched response should be cached or not."
    ::= { slbNewAcclCfgCacheUrlRuleEntry 9 }

slbNewAcclCfgCacheUrlRuleAdminStatus OBJECT-TYPE
    SYNTAX  INTEGER {
        enabled(1),
        disabled(2),
        unsupported(2147483647)
        }
    MAX-ACCESS  read-create
    STATUS  current
    DESCRIPTION
        "Status (enable/disable) of caching URL Rule."
    ::= { slbNewAcclCfgCacheUrlRuleEntry 10 }

slbNewAcclCfgCacheUrlRuleDelete OBJECT-TYPE
    SYNTAX  INTEGER {
        other(1),
        delete(2),
        unsupported(2147483647)
        }
    MAX-ACCESS  read-create
    STATUS  current
    DESCRIPTION
        "By setting the value to delete(2), the entire row is deleted."
    ::= { slbNewAcclCfgCacheUrlRuleEntry 11 }

slbNewAcclCfgCacheUrlRuleCopy OBJECT-TYPE
    SYNTAX   DisplayString 
    MAX-ACCESS  read-create
    STATUS  current
    DESCRIPTION
        "Copy rule to another index in the same rule-list. When read,
         zero is returned."
    ::= { slbNewAcclCfgCacheUrlRuleEntry 12 }

-- optimization rules
slbCurAcclCfgOptExcListTable OBJECT-TYPE
    SYNTAX  SEQUENCE OF SlbCurAcclCfgOptExcListEntry
    MAX-ACCESS  not-accessible
    STATUS  current
    DESCRIPTION
        "The table for configuring optimization LIST.
         Note:This mib is not supported for VX instance of Virtualization."
    ::= { caching 11 }

slbCurAcclCfgOptExcListEntry OBJECT-TYPE
    SYNTAX  SlbCurAcclCfgOptExcListEntry
    MAX-ACCESS  not-accessible
    STATUS  current
    DESCRIPTION
        "A row in the optimization LIST table."
    INDEX   { slbCurAcclCfgOptExcListIdIndex }
    ::= { slbCurAcclCfgOptExcListTable 1 }

SlbCurAcclCfgOptExcListEntry ::= SEQUENCE {
    slbCurAcclCfgOptExcListIdIndex          DisplayString,
    slbCurAcclCfgOptExcListName             DisplayString,
    slbCurAcclCfgOptExcListAdminStatus          INTEGER
    }

slbCurAcclCfgOptExcListIdIndex OBJECT-TYPE
    SYNTAX   DisplayString (SIZE (0..32))
    MAX-ACCESS  read-only
    STATUS  current
    DESCRIPTION
        "The optimization LIST (key id) as an index."
    ::= { slbCurAcclCfgOptExcListEntry 1 }

slbCurAcclCfgOptExcListName OBJECT-TYPE
    SYNTAX   DisplayString (SIZE (0..32))
    MAX-ACCESS  read-only
    STATUS  current
    DESCRIPTION
        "Optimization LIST name."
    ::= { slbCurAcclCfgOptExcListEntry 2 }

slbCurAcclCfgOptExcListAdminStatus OBJECT-TYPE
    SYNTAX  INTEGER {
        enabled(1),
        disabled(2),
        unsupported(2147483647)
        }
    MAX-ACCESS  read-only
    STATUS  current
    DESCRIPTION
        "Status (enable/disable) of optimization LIST."
    ::= { slbCurAcclCfgOptExcListEntry 3 }

slbNewAcclCfgOptExcListTable OBJECT-TYPE
    SYNTAX  SEQUENCE OF SlbNewAcclCfgOptExcListEntry
    MAX-ACCESS  not-accessible
    STATUS  current
    DESCRIPTION
        "The table for configuring optimization LIST.
         Note:This mib is not supported for VX instance of Virtualization."
    ::= { caching 12 }

slbNewAcclCfgOptExcListEntry OBJECT-TYPE
    SYNTAX  SlbNewAcclCfgOptExcListEntry
    MAX-ACCESS  not-accessible
    STATUS  current
    DESCRIPTION
        "A row in the optimization LIST table."
    INDEX   { slbNewAcclCfgOptExcListIdIndex }
    ::= { slbNewAcclCfgOptExcListTable 1 }

SlbNewAcclCfgOptExcListEntry ::= SEQUENCE {
    slbNewAcclCfgOptExcListIdIndex          DisplayString,
    slbNewAcclCfgOptExcListName             DisplayString,
    slbNewAcclCfgOptExcListAdminStatus      INTEGER,
    slbNewAcclCfgOptExcListDel              INTEGER,
    slbNewAcclCfgOptExcListCopy             DisplayString
    }

slbNewAcclCfgOptExcListIdIndex OBJECT-TYPE
    SYNTAX   DisplayString (SIZE (0..32))
    MAX-ACCESS  read-only
    STATUS  current
    DESCRIPTION
        "The caching optimization LIST (key id) as an index."
    ::= { slbNewAcclCfgOptExcListEntry 1 }

slbNewAcclCfgOptExcListName OBJECT-TYPE
    SYNTAX   DisplayString (SIZE (0..32))
    MAX-ACCESS  read-create
    STATUS  current
    DESCRIPTION
        "Optimization LIST name."
    ::= { slbNewAcclCfgOptExcListEntry 2 }

slbNewAcclCfgOptExcListAdminStatus OBJECT-TYPE
    SYNTAX  INTEGER {
        enabled(1),
        disabled(2),
        unsupported(2147483647)
        }
    MAX-ACCESS  read-create
    STATUS  current
    DESCRIPTION
        "Status (enable/disable) of optimization LIST."
    ::= { slbNewAcclCfgOptExcListEntry 3 }

slbNewAcclCfgOptExcListDel OBJECT-TYPE
    SYNTAX  INTEGER {
        other(1),
        delete(2),
        unsupported(2147483647)
        }
    MAX-ACCESS  read-create
    STATUS  current
    DESCRIPTION
        "Delete optimization list."
    ::= { slbNewAcclCfgOptExcListEntry 4 }

slbNewAcclCfgOptExcListCopy OBJECT-TYPE
    SYNTAX   DisplayString
    MAX-ACCESS  read-create
    STATUS  current
    DESCRIPTION
        "Duplicating an entire Rule-List by defining the destination Rule-list id."
    ::= { slbNewAcclCfgOptExcListEntry 5 }

slbCurAcclCfgOptExcRuleTable OBJECT-TYPE
    SYNTAX  SEQUENCE OF SlbCurAcclCfgOptExcRuleEntry
    MAX-ACCESS  not-accessible
    STATUS  current
    DESCRIPTION
        "The table for configuring optimization Rules.
         Note:This mib is not supported for VX instance of Virtualization."
    ::= { caching 13 }

slbCurAcclCfgOptExcRuleEntry OBJECT-TYPE
    SYNTAX  SlbCurAcclCfgOptExcRuleEntry
    MAX-ACCESS  not-accessible
    STATUS  current
    DESCRIPTION
        "A row in the optimization Rule table."
    INDEX   { slbCurAcclCfgOptExcRuleListIdIndex, slbCurAcclCfgOptExcRuleIndex }
    ::= { slbCurAcclCfgOptExcRuleTable 1 }

SlbCurAcclCfgOptExcRuleEntry ::= SEQUENCE {
    slbCurAcclCfgOptExcRuleListIdIndex          DisplayString,
    slbCurAcclCfgOptExcRuleIndex                INTEGER,
    slbCurAcclCfgOptExcRuleName                 DisplayString,
    slbCurAcclCfgOptExcRuleResType              INTEGER,
    slbCurAcclCfgOptExcRuleURI                  DisplayString,
    slbCurAcclCfgOptExcRuleCombineCSS           INTEGER,
    slbCurAcclCfgOptExcRuleCombineJS            INTEGER,
    slbCurAcclCfgOptExcRuleDynamicCache         INTEGER,
    slbCurAcclCfgOptExcRuleInlineCSS            INTEGER,
    slbCurAcclCfgOptExcRuleInlineJS             INTEGER,
    slbCurAcclCfgOptExcRuleImageDim             INTEGER,
    slbCurAcclCfgOptExcRuleRemoveComments       INTEGER,
    slbCurAcclCfgOptExcRuleRemoveWS             INTEGER,
    slbCurAcclCfgOptExcRuleTrimURL              INTEGER,
    slbCurAcclCfgOptExcRuleAdminStatus          INTEGER
    }

slbCurAcclCfgOptExcRuleListIdIndex OBJECT-TYPE
    SYNTAX   DisplayString (SIZE (0..32))
    MAX-ACCESS  read-only
    STATUS  current
    DESCRIPTION
        "The optimization rule list (key id) as an index."
    ::= { slbCurAcclCfgOptExcRuleEntry 1 }

slbCurAcclCfgOptExcRuleIndex OBJECT-TYPE
    SYNTAX   INTEGER
    MAX-ACCESS  read-only
    STATUS  current
    DESCRIPTION
        "The optimization Rule number as an index."
    ::= { slbCurAcclCfgOptExcRuleEntry 2 }

slbCurAcclCfgOptExcRuleName OBJECT-TYPE
    SYNTAX   DisplayString (SIZE (0..32))
    MAX-ACCESS  read-only
    STATUS  current
    DESCRIPTION
        "The optimization Rule name."
    ::= { slbCurAcclCfgOptExcRuleEntry 3 }

slbCurAcclCfgOptExcRuleResType OBJECT-TYPE
    SYNTAX  INTEGER {
        html(1),
        js(2),
        css(3),
	image(4),
	other(5),
        unsupported(2147483647)
    }
    MAX-ACCESS  read-only
    STATUS  current
    DESCRIPTION
        "Resource type."
    ::= { slbCurAcclCfgOptExcRuleEntry 4 }

slbCurAcclCfgOptExcRuleURI OBJECT-TYPE
    SYNTAX   DisplayString (SIZE (1..127))
    MAX-ACCESS  read-only
    STATUS  current
    DESCRIPTION
        "URI of the resource for which this rule applies."
    ::= { slbCurAcclCfgOptExcRuleEntry 5 }

slbCurAcclCfgOptExcRuleCombineCSS OBJECT-TYPE
    SYNTAX  INTEGER {
        enabled(1),
        disabled(2),
        unsupported(2147483647)
        }
    MAX-ACCESS  read-only
    STATUS  current
    DESCRIPTION
        "Combine CSS optimization."
    ::= { slbCurAcclCfgOptExcRuleEntry 6 }

slbCurAcclCfgOptExcRuleCombineJS OBJECT-TYPE
    SYNTAX  INTEGER {
        enabled(1),
        disabled(2),
        unsupported(2147483647)
        }
    MAX-ACCESS  read-only
    STATUS  current
    DESCRIPTION
        "Combine JavaScript optimization."
    ::= { slbCurAcclCfgOptExcRuleEntry 7 }

slbCurAcclCfgOptExcRuleDynamicCache OBJECT-TYPE
    SYNTAX  INTEGER {
        enabled(1),
        disabled(2),
        unsupported(2147483647)
        }
    MAX-ACCESS  read-only
    STATUS  current
    DESCRIPTION
        "Dynamic cache optimization."
    ::= { slbCurAcclCfgOptExcRuleEntry 8 }

slbCurAcclCfgOptExcRuleInlineCSS OBJECT-TYPE
    SYNTAX  INTEGER {
        enabled(1),
        disabled(2),
        unsupported(2147483647)
        }
    MAX-ACCESS  read-only
    STATUS  current
    DESCRIPTION
        "Inline CSS optimization."
    ::= { slbCurAcclCfgOptExcRuleEntry 9 }

slbCurAcclCfgOptExcRuleInlineJS OBJECT-TYPE
    SYNTAX  INTEGER {
        enabled(1),
        disabled(2),
        unsupported(2147483647)
        }
    MAX-ACCESS  read-only
    STATUS  current
    DESCRIPTION
        "Inline JavaScript optimization."
    ::= { slbCurAcclCfgOptExcRuleEntry 10 }

slbCurAcclCfgOptExcRuleImageDim OBJECT-TYPE
    SYNTAX  INTEGER {
        enabled(1),
        disabled(2),
        unsupported(2147483647)
        }
    MAX-ACCESS  read-only
    STATUS  current
    DESCRIPTION
        "Image dimensions setting optimization."
    ::= { slbCurAcclCfgOptExcRuleEntry 11 }

slbCurAcclCfgOptExcRuleRemoveComments OBJECT-TYPE
    SYNTAX  INTEGER {
        enabled(1),
        disabled(2),
        unsupported(2147483647)
        }
    MAX-ACCESS  read-only
    STATUS  current
    DESCRIPTION
        "Remove comments optimization."
    ::= { slbCurAcclCfgOptExcRuleEntry 12 }

slbCurAcclCfgOptExcRuleRemoveWS OBJECT-TYPE
    SYNTAX  INTEGER {
        enabled(1),
        disabled(2),
        unsupported(2147483647)
        }
    MAX-ACCESS  read-only
    STATUS  current
    DESCRIPTION
        "Remove whitespace optimization."
    ::= { slbCurAcclCfgOptExcRuleEntry 13 }

slbCurAcclCfgOptExcRuleTrimURL OBJECT-TYPE
    SYNTAX  INTEGER {
        enabled(1),
        disabled(2),
        unsupported(2147483647)
        }
    MAX-ACCESS  read-only
    STATUS  current
    DESCRIPTION
        "Trim URLs optimization."
    ::= { slbCurAcclCfgOptExcRuleEntry 14 }

slbCurAcclCfgOptExcRuleAdminStatus OBJECT-TYPE
    SYNTAX  INTEGER {
        enabled(1),
        disabled(2),
        unsupported(2147483647)
        }
    MAX-ACCESS  read-only
    STATUS  current
    DESCRIPTION
        "Status (enable/disable) of optimization Rule."
    ::= { slbCurAcclCfgOptExcRuleEntry 15 }

slbNewAcclCfgOptExcRuleTable OBJECT-TYPE
    SYNTAX  SEQUENCE OF SlbNewAcclCfgOptExcRuleEntry
    MAX-ACCESS  not-accessible
    STATUS  current
    DESCRIPTION
        "The table for configuring optimization Rules.
         Note:This mib is not supported for VX instance of Virtualization."
    ::= { caching 14 }

slbNewAcclCfgOptExcRuleEntry OBJECT-TYPE
    SYNTAX  SlbNewAcclCfgOptExcRuleEntry
    MAX-ACCESS  not-accessible
    STATUS  current
    DESCRIPTION
        "A row in the optimization Rule table."
    INDEX   { slbNewAcclCfgOptExcRuleListIdIndex, slbNewAcclCfgOptExcRuleIndex }
    ::= { slbNewAcclCfgOptExcRuleTable 1 }

SlbNewAcclCfgOptExcRuleEntry ::= SEQUENCE {
    slbNewAcclCfgOptExcRuleListIdIndex          DisplayString,
    slbNewAcclCfgOptExcRuleIndex                INTEGER,
    slbNewAcclCfgOptExcRuleName                 DisplayString,
    slbNewAcclCfgOptExcRuleResType              INTEGER,
    slbNewAcclCfgOptExcRuleURI                  DisplayString,
    slbNewAcclCfgOptExcRuleCombineCSS           INTEGER,
    slbNewAcclCfgOptExcRuleCombineJS            INTEGER,
    slbNewAcclCfgOptExcRuleDynamicCache         INTEGER,
    slbNewAcclCfgOptExcRuleInlineCSS            INTEGER,
    slbNewAcclCfgOptExcRuleInlineJS             INTEGER,
    slbNewAcclCfgOptExcRuleImageDim             INTEGER,
    slbNewAcclCfgOptExcRuleRemoveComments       INTEGER,
    slbNewAcclCfgOptExcRuleRemoveWS             INTEGER,
    slbNewAcclCfgOptExcRuleTrimURL              INTEGER,
    slbNewAcclCfgOptExcRuleAdminStatus          INTEGER,
    slbNewAcclCfgOptExcRuleDelete               INTEGER,
    slbNewAcclCfgOptExcRuleCopy                 DisplayString 
    }

slbNewAcclCfgOptExcRuleListIdIndex OBJECT-TYPE
    SYNTAX   DisplayString (SIZE (0..32))
    MAX-ACCESS  read-only
    STATUS  current
    DESCRIPTION
        "The optimization rule list (key id) as an index."
    ::= { slbNewAcclCfgOptExcRuleEntry 1 }

slbNewAcclCfgOptExcRuleIndex OBJECT-TYPE
    SYNTAX   INTEGER
    MAX-ACCESS  read-only
    STATUS  current
    DESCRIPTION
        "The optimization Rule number as an index."
    ::= { slbNewAcclCfgOptExcRuleEntry 2 }

slbNewAcclCfgOptExcRuleName OBJECT-TYPE
    SYNTAX   DisplayString (SIZE (0..32))
    MAX-ACCESS  read-create
    STATUS  current
    DESCRIPTION
        "The optimization Rule name."
    ::= { slbNewAcclCfgOptExcRuleEntry 3 }

slbNewAcclCfgOptExcRuleResType OBJECT-TYPE
    SYNTAX  INTEGER {
        html(1),
        js(2),
        css(3),
	image(4),
	other(5),
        unsupported(2147483647)
    }
    MAX-ACCESS  read-create
    STATUS  current
    DESCRIPTION
        "Resource type for the rule."
    ::= { slbNewAcclCfgOptExcRuleEntry 4 }

slbNewAcclCfgOptExcRuleURI OBJECT-TYPE
    SYNTAX   DisplayString (SIZE (1..127))
    MAX-ACCESS  read-create
    STATUS  current
    DESCRIPTION
        "URI of the resource."
    ::= { slbNewAcclCfgOptExcRuleEntry 5 }

slbNewAcclCfgOptExcRuleCombineCSS OBJECT-TYPE
    SYNTAX  INTEGER {
        enabled(1),
        disabled(2),
        unsupported(2147483647)
    }
    MAX-ACCESS  read-create
    STATUS  current
    DESCRIPTION
        "Combine CSS optimization."
    ::= { slbNewAcclCfgOptExcRuleEntry 6 }

slbNewAcclCfgOptExcRuleCombineJS OBJECT-TYPE
    SYNTAX  INTEGER {
        enabled(1),
        disabled(2),
        unsupported(2147483647)
    }
    MAX-ACCESS  read-create
    STATUS  current
    DESCRIPTION
        "Combine JavaScript optimization."
    ::= { slbNewAcclCfgOptExcRuleEntry 7 }

slbNewAcclCfgOptExcRuleDynamicCache OBJECT-TYPE
    SYNTAX  INTEGER {
        enabled(1),
        disabled(2),
        unsupported(2147483647)
    }
    MAX-ACCESS  read-create
    STATUS  current
    DESCRIPTION
        "Dynamic cache optimization."
    ::= { slbNewAcclCfgOptExcRuleEntry 8 }

slbNewAcclCfgOptExcRuleInlineCSS OBJECT-TYPE
    SYNTAX  INTEGER {
        enabled(1),
        disabled(2),
        unsupported(2147483647)
    }
    MAX-ACCESS  read-create
    STATUS  current
    DESCRIPTION
        "Inline CSS optimization."
    ::= { slbNewAcclCfgOptExcRuleEntry 9 }

slbNewAcclCfgOptExcRuleInlineJS OBJECT-TYPE
    SYNTAX  INTEGER {
        enabled(1),
        disabled(2),
        unsupported(2147483647)
    }
    MAX-ACCESS  read-create
    STATUS  current
    DESCRIPTION
        "Inline JavaScript optimization."
    ::= { slbNewAcclCfgOptExcRuleEntry 10 }

slbNewAcclCfgOptExcRuleImageDim OBJECT-TYPE
    SYNTAX  INTEGER {
        enabled(1),
        disabled(2),
        unsupported(2147483647)
    }
    MAX-ACCESS  read-create
    STATUS  current
    DESCRIPTION
        "Image dimensions setting optimization."
    ::= { slbNewAcclCfgOptExcRuleEntry 11 }

slbNewAcclCfgOptExcRuleRemoveComments OBJECT-TYPE
    SYNTAX  INTEGER {
        enabled(1),
        disabled(2),
        unsupported(2147483647)
    }
    MAX-ACCESS  read-create
    STATUS  current
    DESCRIPTION
        "Remove comments optimization."
    ::= { slbNewAcclCfgOptExcRuleEntry 12 }

slbNewAcclCfgOptExcRuleRemoveWS OBJECT-TYPE
    SYNTAX  INTEGER {
        enabled(1),
        disabled(2),
        unsupported(2147483647)
    }
    MAX-ACCESS  read-create
    STATUS  current
    DESCRIPTION
        "Remove whitespace optimization."
    ::= { slbNewAcclCfgOptExcRuleEntry 13 }

slbNewAcclCfgOptExcRuleTrimURL OBJECT-TYPE
    SYNTAX  INTEGER {
        enabled(1),
        disabled(2),
        unsupported(2147483647)
    }
    MAX-ACCESS  read-create
    STATUS  current
    DESCRIPTION
        "Trim URLs optimization."
    ::= { slbNewAcclCfgOptExcRuleEntry 14 }


slbNewAcclCfgOptExcRuleAdminStatus OBJECT-TYPE
    SYNTAX  INTEGER {
        enabled(1),
        disabled(2),
        unsupported(2147483647)
        }
    MAX-ACCESS  read-create
    STATUS  current
    DESCRIPTION
        "Status (enable/disable) of optimization Rule."
    ::= { slbNewAcclCfgOptExcRuleEntry 15 }

slbNewAcclCfgOptExcRuleDelete OBJECT-TYPE
    SYNTAX  INTEGER {
        other(1),
        delete(2),
        unsupported(2147483647)
        }
    MAX-ACCESS  read-create
    STATUS  current
    DESCRIPTION
        "By setting the value to delete(2), the entire row is deleted."
    ::= { slbNewAcclCfgOptExcRuleEntry 16 }

slbNewAcclCfgOptExcRuleCopy OBJECT-TYPE
    SYNTAX   DisplayString 
    MAX-ACCESS  read-create
    STATUS  current
    DESCRIPTION
        "Copy rule to another index in the same rule-list. When read,
         zero is returned."
    ::= { slbNewAcclCfgOptExcRuleEntry 17 }


-- compression

slbCurAcclCfgCompOnOff OBJECT-TYPE
   SYNTAX  INTEGER {
       on(1),
       off(2),
       unsupported(2147483647)
       }
   MAX-ACCESS  read-only
   STATUS  current
   DESCRIPTION
       "Globally ON or OFF of compression.
        Note:This mib is not supported for VX instance of Virtualization."
   ::= { compression 1}

slbNewAcclCfgCompOnOff OBJECT-TYPE
   SYNTAX  INTEGER {
       on(1),
       off(2),
       unsupported(2147483647)
       }
   MAX-ACCESS  read-write
   STATUS  current
   DESCRIPTION
       "Globally ON or OFF of compression.
        Note:This mib is not supported for VX instance of Virtualization."
   ::= { compression 2}

slbCurAcclCfgCompPolTable OBJECT-TYPE
    SYNTAX  SEQUENCE OF SlbCurAcclCfgCompPolEntry
    MAX-ACCESS  not-accessible
    STATUS  current
    DESCRIPTION
        "The table for configuring compression policy.
         Note:This mib is not supported for VX instance of Virtualization."
    ::= { compression 3 }

slbCurAcclCfgCompPolEntry OBJECT-TYPE
    SYNTAX  SlbCurAcclCfgCompPolEntry
    MAX-ACCESS  not-accessible
    STATUS  current
    DESCRIPTION
        "A row in the compression policy table."
    INDEX   { slbCurAcclCfgCompPolNameIdIndex }
    ::= { slbCurAcclCfgCompPolTable 1 }

SlbCurAcclCfgCompPolEntry ::= SEQUENCE {
    slbCurAcclCfgCompPolNameIdIndex          DisplayString,
    slbCurAcclCfgCompPolName                 DisplayString,
    slbCurAcclCfgCompPolAlgrthm              INTEGER,
    slbCurAcclCfgCompPolComplv1              INTEGER,
    slbCurAcclCfgCompPolMinSize              INTEGER,
    slbCurAcclCfgCompPolMaxSize              INTEGER,
    slbCurAcclCfgCompPolURLList              DisplayString,
    slbCurAcclCfgCompPolBrwsList             DisplayString,
    slbCurAcclCfgCompPolPreDefBrwsRuleList   INTEGER,
    slbCurAcclCfgCompPolCompsrv              INTEGER,
    slbCurAcclCfgCompPolAdminStatus          INTEGER
    }

slbCurAcclCfgCompPolNameIdIndex OBJECT-TYPE
    SYNTAX   DisplayString (SIZE (0..32))
    MAX-ACCESS  read-only
    STATUS  current
    DESCRIPTION
        "The compression policy ID(key id) as an index."
    ::= { slbCurAcclCfgCompPolEntry 1 }

slbCurAcclCfgCompPolName OBJECT-TYPE
    SYNTAX   DisplayString (SIZE (0..32))
    MAX-ACCESS  read-only
    STATUS  current
    DESCRIPTION
        "Compression policy name."
    ::= { slbCurAcclCfgCompPolEntry 2 }

slbCurAcclCfgCompPolAlgrthm OBJECT-TYPE
    SYNTAX  INTEGER {
        gzip(1),
        deflate(2),
        unsupported(2147483647)
        }
    MAX-ACCESS  read-only
    STATUS  current
    DESCRIPTION
        "Preferred compression algorithm."
    ::= { slbCurAcclCfgCompPolEntry 3 }

slbCurAcclCfgCompPolComplv1 OBJECT-TYPE
    SYNTAX  INTEGER (1..9)
    MAX-ACCESS  read-only
    STATUS  current
    DESCRIPTION
        "Compression level."
    ::= { slbCurAcclCfgCompPolEntry 4 }

slbCurAcclCfgCompPolMinSize OBJECT-TYPE
    SYNTAX  INTEGER (1..65535)
    MAX-ACCESS  read-only
    STATUS  current
    DESCRIPTION
        "Minimum file size to be compressed [Byte]."
    ::= { slbCurAcclCfgCompPolEntry 5 }

slbCurAcclCfgCompPolMaxSize OBJECT-TYPE
    SYNTAX  INTEGER
    MAX-ACCESS  read-only
    STATUS  current
    DESCRIPTION
        "Maximum file size to be compressed [Byte]."
    ::= { slbCurAcclCfgCompPolEntry 6 }

slbCurAcclCfgCompPolURLList OBJECT-TYPE
    SYNTAX   DisplayString (SIZE (0..32))
    MAX-ACCESS  read-only
    STATUS  current
    DESCRIPTION
        "URL list which is associated with this policy."
    ::= { slbCurAcclCfgCompPolEntry 7 }

slbCurAcclCfgCompPolBrwsList OBJECT-TYPE
    SYNTAX   DisplayString (SIZE (0..32))
    MAX-ACCESS  read-only
    STATUS  current
    DESCRIPTION
        "Browser list which is associated with this policy."
    ::= { slbCurAcclCfgCompPolEntry 8 }

slbCurAcclCfgCompPolPreDefBrwsRuleList OBJECT-TYPE
    SYNTAX  INTEGER {
        enabled(1),
        disabled(2),
        unsupported(2147483647)
        }
    MAX-ACCESS  read-only
    STATUS  current
    DESCRIPTION
        "Enable/Disable predefined browser exceptions rule-list."
    ::= { slbCurAcclCfgCompPolEntry 9 }

slbCurAcclCfgCompPolCompsrv OBJECT-TYPE
    SYNTAX  INTEGER {
        enabled(1),
        disabled(2),
        unsupported(2147483647)
        }
    MAX-ACCESS  read-only
    STATUS  current
    DESCRIPTION
        "Enable/Disable compression by real server."
    ::= { slbCurAcclCfgCompPolEntry 10 }

slbCurAcclCfgCompPolAdminStatus OBJECT-TYPE
    SYNTAX  INTEGER {
        enabled(1),
        disabled(2),
        unsupported(2147483647)
        }
    MAX-ACCESS  read-only
    STATUS  current
    DESCRIPTION
        "Status (enable/disable) of compression policy."
    ::= { slbCurAcclCfgCompPolEntry 11 }

slbNewAcclCfgCompPolTable OBJECT-TYPE
    SYNTAX  SEQUENCE OF SlbNewAcclCfgCompPolEntry
    MAX-ACCESS  not-accessible
    STATUS  current
    DESCRIPTION
        "The table for configuring compression policy.
         Note:This mib is not supported for VX instance of Virtualization."
    ::= { compression 4 }

slbNewAcclCfgCompPolEntry OBJECT-TYPE
    SYNTAX  SlbNewAcclCfgCompPolEntry
    MAX-ACCESS  not-accessible
    STATUS  current
    DESCRIPTION
        "A row in the compression policy table."
    INDEX   { slbNewAcclCfgCompPolNameIdIndex }
    ::= { slbNewAcclCfgCompPolTable 1 }

SlbNewAcclCfgCompPolEntry ::= SEQUENCE {
    slbNewAcclCfgCompPolNameIdIndex          DisplayString,
    slbNewAcclCfgCompPolName                 DisplayString,
    slbNewAcclCfgCompPolAlgrthm              INTEGER,
    slbNewAcclCfgCompPolComplv1              INTEGER,
    slbNewAcclCfgCompPolMinSize              INTEGER,
    slbNewAcclCfgCompPolMaxSize              INTEGER,
    slbNewAcclCfgCompPolURLList              DisplayString,
    slbNewAcclCfgCompPolBrwsList             DisplayString,
    slbNewAcclCfgCompPolPreDefBrwsRuleList   INTEGER,
    slbNewAcclCfgCompPolCompsrv              INTEGER,
    slbNewAcclCfgCompPolAdminStatus          INTEGER,
    slbNewAcclCfgCompPolDelete               INTEGER
    }

slbNewAcclCfgCompPolNameIdIndex OBJECT-TYPE
    SYNTAX   DisplayString (SIZE (0..32))
    MAX-ACCESS  read-only
    STATUS  current
    DESCRIPTION
        "The compression policy ID(key id) as an index."
    ::= { slbNewAcclCfgCompPolEntry 1 }

slbNewAcclCfgCompPolName OBJECT-TYPE
    SYNTAX   DisplayString (SIZE (0..32))
    MAX-ACCESS  read-create
    STATUS  current
    DESCRIPTION
        "Compression policy name."
    ::= { slbNewAcclCfgCompPolEntry 2 }

slbNewAcclCfgCompPolAlgrthm OBJECT-TYPE
    SYNTAX  INTEGER {
        gzip(1),
        deflate(2),
        unsupported(2147483647)
        }
    MAX-ACCESS  read-create
    STATUS  current
    DESCRIPTION
        "Preferred compression algorithm."
    ::= { slbNewAcclCfgCompPolEntry 3 }

slbNewAcclCfgCompPolComplv1 OBJECT-TYPE
    SYNTAX  INTEGER (1..9)
    MAX-ACCESS  read-create
    STATUS  current
    DESCRIPTION
        "Compression level."
    ::= { slbNewAcclCfgCompPolEntry 4 }

slbNewAcclCfgCompPolMinSize OBJECT-TYPE
    SYNTAX  INTEGER (1..65535)
    MAX-ACCESS  read-create
    STATUS  current
    DESCRIPTION
        "Minimum file size to be compressed [Byte]."
    ::= { slbNewAcclCfgCompPolEntry 5 }

slbNewAcclCfgCompPolMaxSize OBJECT-TYPE
    SYNTAX  INTEGER
    MAX-ACCESS  read-create
    STATUS  current
    DESCRIPTION
        "Maximum file size to be compressed [Byte], Values: 1-2000000000, 0-Unlimited "
    ::= { slbNewAcclCfgCompPolEntry 6 }

slbNewAcclCfgCompPolURLList OBJECT-TYPE
    SYNTAX   DisplayString (SIZE (0..32))
    MAX-ACCESS  read-create
    STATUS  current
    DESCRIPTION
        "URL list which is associated with this policy."
    ::= { slbNewAcclCfgCompPolEntry 7 }

slbNewAcclCfgCompPolBrwsList OBJECT-TYPE
    SYNTAX   DisplayString (SIZE (0..32))
    MAX-ACCESS  read-create
    STATUS  current
    DESCRIPTION
        "Browser list which is associated with this policy."
    ::= { slbNewAcclCfgCompPolEntry 8 }

slbNewAcclCfgCompPolPreDefBrwsRuleList OBJECT-TYPE
    SYNTAX  INTEGER {
        enabled(1),
        disabled(2),
        unsupported(2147483647)
        }
    MAX-ACCESS  read-create
    STATUS  current
    DESCRIPTION
        "Enable/Disable predefined browser exceptions rule-list."
    ::= { slbNewAcclCfgCompPolEntry 9 }

slbNewAcclCfgCompPolCompsrv OBJECT-TYPE
    SYNTAX  INTEGER {
        enabled(1),
        disabled(2),
        unsupported(2147483647)
        }
    MAX-ACCESS  read-create
    STATUS  current
    DESCRIPTION
        "Enable/Disable compression by real server."
    ::= { slbNewAcclCfgCompPolEntry 10 }

slbNewAcclCfgCompPolAdminStatus OBJECT-TYPE
    SYNTAX  INTEGER {
        enabled(1),
        disabled(2),
        unsupported(2147483647)
        }
    MAX-ACCESS  read-create
    STATUS  current
    DESCRIPTION
        "Status (enable/disable) of compression policy."
    ::= { slbNewAcclCfgCompPolEntry 11 }

slbNewAcclCfgCompPolDelete OBJECT-TYPE
    SYNTAX  INTEGER {
        other(1),
        delete(2),
        unsupported(2147483647)
        }
    MAX-ACCESS  read-create
    STATUS  current
    DESCRIPTION
        "Delete compression policy."
    ::= { slbNewAcclCfgCompPolEntry 12 }

slbCurAcclCfgCompUrlListTable OBJECT-TYPE
    SYNTAX  SEQUENCE OF SlbCurAcclCfgCompUrlListEntry
    MAX-ACCESS  not-accessible
    STATUS  current
    DESCRIPTION
        "The table for configuring compression URL LIST.
         Note:This mib is not supported for VX instance of Virtualization."
    ::= { compression 5 }

slbCurAcclCfgCompUrlListEntry OBJECT-TYPE
    SYNTAX  SlbCurAcclCfgCompUrlListEntry
    MAX-ACCESS  not-accessible
    STATUS  current
    DESCRIPTION
        "A row in the compression URL LIST table."
    INDEX   { slbCurAcclCfgCompUrlListIdIndex }
    ::= { slbCurAcclCfgCompUrlListTable 1 }

SlbCurAcclCfgCompUrlListEntry ::= SEQUENCE {
    slbCurAcclCfgCompUrlListIdIndex          DisplayString,
    slbCurAcclCfgCompUrlListName             DisplayString,
    slbCurAcclCfgCompUrlListAdminStatus      INTEGER
    }

slbCurAcclCfgCompUrlListIdIndex OBJECT-TYPE
    SYNTAX   DisplayString (SIZE (0..32))
    MAX-ACCESS  read-only
    STATUS  current
    DESCRIPTION
        "The compression policy URL LIST (key id) as an index."
    ::= { slbCurAcclCfgCompUrlListEntry 1 }

slbCurAcclCfgCompUrlListName OBJECT-TYPE
    SYNTAX   DisplayString (SIZE (0..32))
    MAX-ACCESS  read-only
    STATUS  current
    DESCRIPTION
        "Compression URL LIST name."
    ::= { slbCurAcclCfgCompUrlListEntry 2 }

slbCurAcclCfgCompUrlListAdminStatus OBJECT-TYPE
    SYNTAX  INTEGER {
        enabled(1),
        disabled(2),
        unsupported(2147483647)
        }
    MAX-ACCESS  read-only
    STATUS  current
    DESCRIPTION
        "Status (enable/disable) of compression URL LIST."
    ::= { slbCurAcclCfgCompUrlListEntry 3 }


slbNewAcclCfgCompUrlListTable OBJECT-TYPE
    SYNTAX  SEQUENCE OF SlbNewAcclCfgCompUrlListEntry
    MAX-ACCESS  not-accessible
    STATUS  current
    DESCRIPTION
        "The table for configuring compression URL LIST.
         Note:This mib is not supported for VX instance of Virtualization."
    ::= { compression 6 }

slbNewAcclCfgCompUrlListEntry OBJECT-TYPE
    SYNTAX  SlbNewAcclCfgCompUrlListEntry
    MAX-ACCESS  not-accessible
    STATUS  current
    DESCRIPTION
        "A row in the compression URL LIST table."
    INDEX   { slbNewAcclCfgCompUrlListIdIndex }
    ::= { slbNewAcclCfgCompUrlListTable 1 }

SlbNewAcclCfgCompUrlListEntry ::= SEQUENCE {
    slbNewAcclCfgCompUrlListIdIndex          DisplayString,
    slbNewAcclCfgCompUrlListName             DisplayString,
    slbNewAcclCfgCompUrlListAdminStatus      INTEGER,
    slbNewAcclCfgCompUrlListDel              INTEGER,
    slbNewAcclCfgCompUrlListCopy             DisplayString
    }

slbNewAcclCfgCompUrlListIdIndex OBJECT-TYPE
    SYNTAX   DisplayString (SIZE (0..32))
    MAX-ACCESS  read-only
    STATUS  current
    DESCRIPTION
        "The compression policy URL LIST (key id) as an index."
    ::= { slbNewAcclCfgCompUrlListEntry 1 }

slbNewAcclCfgCompUrlListName OBJECT-TYPE
    SYNTAX   DisplayString (SIZE (0..32))
    MAX-ACCESS  read-create
    STATUS  current
    DESCRIPTION
        "Compression URL LIST name."
    ::= { slbNewAcclCfgCompUrlListEntry 2 }

slbNewAcclCfgCompUrlListAdminStatus OBJECT-TYPE
    SYNTAX  INTEGER {
        enabled(1),
        disabled(2),
        unsupported(2147483647)
        }
    MAX-ACCESS  read-create
    STATUS  current
    DESCRIPTION
        "Status (enable/disable) of compression URL LIST."
    ::= { slbNewAcclCfgCompUrlListEntry 3 }

slbNewAcclCfgCompUrlListDel OBJECT-TYPE
    SYNTAX  INTEGER {
        other(1),
        delete(2),
        unsupported(2147483647)
        }
    MAX-ACCESS  read-create
    STATUS  current
    DESCRIPTION
        "Delete Compression URL list."
    ::= { slbNewAcclCfgCompUrlListEntry 4 }

slbNewAcclCfgCompUrlListCopy OBJECT-TYPE
    SYNTAX   DisplayString
    MAX-ACCESS  read-create
    STATUS  current
    DESCRIPTION
        "Duplicating an entire Rule-List by defining the destination Rule-list id."
    ::= { slbNewAcclCfgCompUrlListEntry 5 }

slbCurAcclCfgCompUrlRuleTable OBJECT-TYPE
    SYNTAX  SEQUENCE OF SlbCurAcclCfgCompUrlRuleEntry
    MAX-ACCESS  not-accessible
    STATUS  current
    DESCRIPTION
        "The table for configuring compression URL Rules.
         Note:This mib is not supported for VX instance of Virtualization."
    ::= { compression 7 }

slbCurAcclCfgCompUrlRuleEntry OBJECT-TYPE
    SYNTAX  SlbCurAcclCfgCompUrlRuleEntry
    MAX-ACCESS  not-accessible
    STATUS  current
    DESCRIPTION
        "A row in the compression URL Rule table."
    INDEX   { slbCurAcclCfgCompUrlRuleListIdIndex, slbCurAcclCfgCompUrlRuleIndex }
    ::= { slbCurAcclCfgCompUrlRuleTable 1 }

SlbCurAcclCfgCompUrlRuleEntry ::= SEQUENCE {
    slbCurAcclCfgCompUrlRuleListIdIndex          DisplayString,
    slbCurAcclCfgCompUrlRuleIndex                INTEGER,
    slbCurAcclCfgCompUrlRuleName                 DisplayString,
    slbCurAcclCfgCompUrlRuleDomainM              INTEGER,
    slbCurAcclCfgCompUrlRuleDomain               DisplayString,
    slbCurAcclCfgCompUrlRuleURLm                 INTEGER,
    slbCurAcclCfgCompUrlRuleURL                  DisplayString,
    slbCurAcclCfgCompUrlRuleCompress             INTEGER,
    slbCurAcclCfgCompUrlRuleAdminStatus          INTEGER
    }

slbCurAcclCfgCompUrlRuleListIdIndex OBJECT-TYPE
    SYNTAX   DisplayString (SIZE (0..32))
    MAX-ACCESS  read-only
    STATUS  current
    DESCRIPTION
        "The compression URL LIST (key id) as an index."
    ::= { slbCurAcclCfgCompUrlRuleEntry 1 }

slbCurAcclCfgCompUrlRuleIndex OBJECT-TYPE
    SYNTAX   INTEGER
    MAX-ACCESS  read-only
    STATUS  current
    DESCRIPTION
        "The compression URL Rule number as an index."
    ::= { slbCurAcclCfgCompUrlRuleEntry 2 }

slbCurAcclCfgCompUrlRuleName OBJECT-TYPE
    SYNTAX   DisplayString (SIZE (0..32))
    MAX-ACCESS  read-only
    STATUS  current
    DESCRIPTION
        "The compression URL Rule name."
    ::= { slbCurAcclCfgCompUrlRuleEntry 3 }

slbCurAcclCfgCompUrlRuleDomainM OBJECT-TYPE
    SYNTAX  INTEGER {
        any(1),
        text(2),
        regex(3),
        unsupported(2147483647)
        }
    MAX-ACCESS  read-only
    STATUS  current
    DESCRIPTION
        "Defines whether Domain matching should be evaluated as String, Regex or match, any (default any)."
    ::= { slbCurAcclCfgCompUrlRuleEntry 4 }

slbCurAcclCfgCompUrlRuleDomain OBJECT-TYPE
    SYNTAX   DisplayString (SIZE (0..254))
    MAX-ACCESS  read-only
    STATUS  current
    DESCRIPTION
        "Defines the Virtual Host for which this rule applies."
    ::= { slbCurAcclCfgCompUrlRuleEntry 5 }

slbCurAcclCfgCompUrlRuleURLm OBJECT-TYPE
    SYNTAX  INTEGER {
        any(1),
        text(2),
        regex(3),
        unsupported(2147483647)
        }
    MAX-ACCESS  read-only
    STATUS  current
    DESCRIPTION
        "Defines whether URL matching should be evaluated as String, Regex or match, any (default any)."
    ::= { slbCurAcclCfgCompUrlRuleEntry 6 }

slbCurAcclCfgCompUrlRuleURL OBJECT-TYPE
    SYNTAX   DisplayString
    MAX-ACCESS  read-only
    STATUS  current
    DESCRIPTION
        "Defines URL of specific object (file/folder) to be matched by this rule."
    ::= { slbCurAcclCfgCompUrlRuleEntry 7 }

slbCurAcclCfgCompUrlRuleCompress OBJECT-TYPE
    SYNTAX  INTEGER {
        enabled(1),
        disabled(2),
        unsupported(2147483647)
        }
    MAX-ACCESS  read-only
    STATUS  current
    DESCRIPTION
        "Enable/Disable the compression."
    ::= { slbCurAcclCfgCompUrlRuleEntry 8 }

slbCurAcclCfgCompUrlRuleAdminStatus OBJECT-TYPE
    SYNTAX  INTEGER {
        enabled(1),
        disabled(2),
        unsupported(2147483647)
        }
    MAX-ACCESS  read-only
    STATUS  current
    DESCRIPTION
        "Status (enable/disable) of compression URL Rule."
    ::= { slbCurAcclCfgCompUrlRuleEntry 9 }

slbNewAcclCfgCompUrlRuleTable OBJECT-TYPE
    SYNTAX  SEQUENCE OF SlbNewAcclCfgCompUrlRuleEntry
    MAX-ACCESS  not-accessible
    STATUS  current
    DESCRIPTION
        "The table for configuring compression URL Rules.
         Note:This mib is not supported for VX instance of Virtualization."
    ::= { compression 8 }

slbNewAcclCfgCompUrlRuleEntry OBJECT-TYPE
    SYNTAX  SlbNewAcclCfgCompUrlRuleEntry
    MAX-ACCESS  not-accessible
    STATUS  current
    DESCRIPTION
        "A row in the compression URL Rule table."
    INDEX   { slbNewAcclCfgCompUrlRuleListIdIndex, slbNewAcclCfgCompUrlRuleIndex }
    ::= { slbNewAcclCfgCompUrlRuleTable 1 }

SlbNewAcclCfgCompUrlRuleEntry ::= SEQUENCE {
    slbNewAcclCfgCompUrlRuleListIdIndex          DisplayString,
    slbNewAcclCfgCompUrlRuleIndex                INTEGER,
    slbNewAcclCfgCompUrlRuleName                 DisplayString,
    slbNewAcclCfgCompUrlRuleDomainM              INTEGER,
    slbNewAcclCfgCompUrlRuleDomain               DisplayString,
    slbNewAcclCfgCompUrlRuleURLm                 INTEGER,
    slbNewAcclCfgCompUrlRuleURL                  DisplayString,
    slbNewAcclCfgCompUrlRuleCompress             INTEGER,
    slbNewAcclCfgCompUrlRuleAdminStatus          INTEGER,
    slbNewAcclCfgCompUrlRuleDelete               INTEGER,
    slbNewAcclCfgCompUrlRuleCopy                 DisplayString
    }

slbNewAcclCfgCompUrlRuleListIdIndex OBJECT-TYPE
    SYNTAX   DisplayString (SIZE (0..32))
    MAX-ACCESS  read-only
    STATUS  current
    DESCRIPTION
        "The compression URL LIST (key id) as an index."
    ::= { slbNewAcclCfgCompUrlRuleEntry 1 }

slbNewAcclCfgCompUrlRuleIndex OBJECT-TYPE
    SYNTAX   INTEGER
    MAX-ACCESS  read-only
    STATUS  current
    DESCRIPTION
        "The compression URL Rule number as an index."
    ::= { slbNewAcclCfgCompUrlRuleEntry 2 }

slbNewAcclCfgCompUrlRuleName OBJECT-TYPE
    SYNTAX   DisplayString (SIZE (0..32))
    MAX-ACCESS  read-create
    STATUS  current
    DESCRIPTION
        "The compression URL Rule name."
    ::= { slbNewAcclCfgCompUrlRuleEntry 3 }

slbNewAcclCfgCompUrlRuleDomainM OBJECT-TYPE
    SYNTAX  INTEGER {
        any(1),
        text(2),
        regex(3),
        unsupported(2147483647)
        }
    MAX-ACCESS  read-create
    STATUS  current
    DESCRIPTION
        "Defines whether Domain matching should be evaluated as String, Regex or match, any (default any)."
    ::= { slbNewAcclCfgCompUrlRuleEntry 4 }

slbNewAcclCfgCompUrlRuleDomain OBJECT-TYPE
    SYNTAX   DisplayString (SIZE (0..254))
    MAX-ACCESS  read-create
    STATUS  current
    DESCRIPTION
        "Defines the Virtual Host for which this rule applies."
    ::= { slbNewAcclCfgCompUrlRuleEntry 5 }

slbNewAcclCfgCompUrlRuleURLm OBJECT-TYPE
    SYNTAX  INTEGER {
        any(1),
        text(2),
        regex(3),
        unsupported(2147483647)
        }
    MAX-ACCESS  read-create
    STATUS  current
    DESCRIPTION
        "Defines whether URL matching should be evaluated as String, Regex or match, any (default any)."
    ::= { slbNewAcclCfgCompUrlRuleEntry 6 }

slbNewAcclCfgCompUrlRuleURL OBJECT-TYPE
    SYNTAX   DisplayString
    MAX-ACCESS  read-create
    STATUS  current
    DESCRIPTION
        "Defines URL of specific object (file/folder) to be matched by this rule."
    ::= { slbNewAcclCfgCompUrlRuleEntry 7 }

slbNewAcclCfgCompUrlRuleCompress OBJECT-TYPE
    SYNTAX  INTEGER {
        enabled(1),
        disabled(2),
        unsupported(2147483647)
        }
    MAX-ACCESS  read-create
    STATUS  current
    DESCRIPTION
        "Enable/Disable the compression."
    ::= { slbNewAcclCfgCompUrlRuleEntry 8 }

slbNewAcclCfgCompUrlRuleAdminStatus OBJECT-TYPE
    SYNTAX  INTEGER {
        enabled(1),
        disabled(2),
        unsupported(2147483647)
        }
    MAX-ACCESS  read-create
    STATUS  current
    DESCRIPTION
        "Status (enable/disable) of compression URL Rule."
    ::= { slbNewAcclCfgCompUrlRuleEntry 9 }

slbNewAcclCfgCompUrlRuleDelete OBJECT-TYPE
    SYNTAX  INTEGER {
        other(1),
        delete(2),
        unsupported(2147483647)
        }
    MAX-ACCESS  read-create
    STATUS  current
    DESCRIPTION
        "By setting the value to delete(2), the entire row is deleted."
    ::= { slbNewAcclCfgCompUrlRuleEntry 10 }

slbNewAcclCfgCompUrlRuleCopy OBJECT-TYPE
    SYNTAX   DisplayString
    MAX-ACCESS  read-create
    STATUS  current
    DESCRIPTION
        "Copy rule to another index in the same rule-list."
    ::= { slbNewAcclCfgCompUrlRuleEntry 11 }

slbCurAcclCfgCompBrwsListTable OBJECT-TYPE
    SYNTAX  SEQUENCE OF SlbCurAcclCfgCompBrwsListEntry
    MAX-ACCESS  not-accessible
    STATUS  current
    DESCRIPTION
        "The table for configuring compression browser LIST.
         Note:This mib is not supported for VX instance of Virtualization."
    ::= { compression 9 }

slbCurAcclCfgCompBrwsListEntry OBJECT-TYPE
    SYNTAX  SlbCurAcclCfgCompBrwsListEntry
    MAX-ACCESS  not-accessible
    STATUS  current
    DESCRIPTION
        "A row in the compression browser LIST table."
    INDEX   { slbCurAcclCfgCompBrwsListIdIndex }
    ::= { slbCurAcclCfgCompBrwsListTable 1 }

SlbCurAcclCfgCompBrwsListEntry ::= SEQUENCE {
    slbCurAcclCfgCompBrwsListIdIndex          DisplayString,
    slbCurAcclCfgCompBrwsListName             DisplayString,
    slbCurAcclCfgCompBrwsListAdminStatus      INTEGER
    }

slbCurAcclCfgCompBrwsListIdIndex OBJECT-TYPE
    SYNTAX   DisplayString (SIZE (0..32))
    MAX-ACCESS  read-only
    STATUS  current
    DESCRIPTION
        "The compression policy browser LIST (key id) as an index."
    ::= { slbCurAcclCfgCompBrwsListEntry 1 }

slbCurAcclCfgCompBrwsListName OBJECT-TYPE
    SYNTAX   DisplayString (SIZE (0..32))
    MAX-ACCESS  read-only
    STATUS  current
    DESCRIPTION
        "Compression browser list name."
    ::= { slbCurAcclCfgCompBrwsListEntry 2 }

slbCurAcclCfgCompBrwsListAdminStatus OBJECT-TYPE
    SYNTAX  INTEGER {
        enabled(1),
        disabled(2),
        unsupported(2147483647)
        }
    MAX-ACCESS  read-only
    STATUS  current
    DESCRIPTION
        "Status (enable/disable) of compression browser list."
    ::= { slbCurAcclCfgCompBrwsListEntry 3 }


slbNewAcclCfgCompBrwsListTable OBJECT-TYPE
    SYNTAX  SEQUENCE OF SlbNewAcclCfgCompBrwsListEntry
    MAX-ACCESS  not-accessible
    STATUS  current
    DESCRIPTION
        "The table for configuring compression browser list.
         Note:This mib is not supported for VX instance of Virtualization."
    ::= { compression 10 }

slbNewAcclCfgCompBrwsListEntry OBJECT-TYPE
    SYNTAX  SlbNewAcclCfgCompBrwsListEntry
    MAX-ACCESS  not-accessible
    STATUS  current
    DESCRIPTION
        "A row in the compression browser list table."
    INDEX   { slbNewAcclCfgCompBrwsListIdIndex }
    ::= { slbNewAcclCfgCompBrwsListTable 1 }

SlbNewAcclCfgCompBrwsListEntry ::= SEQUENCE {
    slbNewAcclCfgCompBrwsListIdIndex          DisplayString,
    slbNewAcclCfgCompBrwsListName             DisplayString,
    slbNewAcclCfgCompBrwsListAdminStatus      INTEGER,
    slbNewAcclCfgCompBrwsListDel              INTEGER,
    slbNewAcclCfgCompBrwsListCopy             DisplayString
    }

slbNewAcclCfgCompBrwsListIdIndex OBJECT-TYPE
    SYNTAX   DisplayString (SIZE (0..32))
    MAX-ACCESS  read-only
    STATUS  current
    DESCRIPTION
        "The compression policy browser list (key id) as an index."
    ::= { slbNewAcclCfgCompBrwsListEntry 1 }

slbNewAcclCfgCompBrwsListName OBJECT-TYPE
    SYNTAX   DisplayString (SIZE (0..32))
    MAX-ACCESS  read-create
    STATUS  current
    DESCRIPTION
        "Compression browser list name."
    ::= { slbNewAcclCfgCompBrwsListEntry 2 }

slbNewAcclCfgCompBrwsListAdminStatus OBJECT-TYPE
    SYNTAX  INTEGER {
        enabled(1),
        disabled(2),
        unsupported(2147483647)
        }
    MAX-ACCESS  read-create
    STATUS  current
    DESCRIPTION
        "Status (enable/disable) of compression browser list."
    ::= { slbNewAcclCfgCompBrwsListEntry 3 }

slbNewAcclCfgCompBrwsListDel OBJECT-TYPE
    SYNTAX  INTEGER {
        other(1),
        delete(2),
        unsupported(2147483647)
        }
    MAX-ACCESS  read-create
    STATUS  current
    DESCRIPTION
        "Delete Compression Browser list."
    ::= { slbNewAcclCfgCompBrwsListEntry 4 }

slbNewAcclCfgCompBrwsListCopy OBJECT-TYPE
    SYNTAX   DisplayString
    MAX-ACCESS  read-create
    STATUS  current
    DESCRIPTION
        "Duplicating an entire browser list by defining the destination browser list id."
    ::= { slbNewAcclCfgCompBrwsListEntry 5 }

slbCurAcclCfgCompBrwsRuleTable OBJECT-TYPE
    SYNTAX  SEQUENCE OF SlbCurAcclCfgCompBrwsRuleEntry
    MAX-ACCESS  not-accessible
    STATUS  current
    DESCRIPTION
        "The table for configuring compression browser Rules.
         Note:This mib is not supported for VX instance of Virtualization."
    ::= { compression 11 }

slbCurAcclCfgCompBrwsRuleEntry OBJECT-TYPE
    SYNTAX  SlbCurAcclCfgCompBrwsRuleEntry
    MAX-ACCESS  not-accessible
    STATUS  current
    DESCRIPTION
        "A row in the compression browser Rule table."
    INDEX   { slbCurAcclCfgCompBrwsRuleListIdIndex, slbCurAcclCfgCompBrwsRuleIndex }
    ::= { slbCurAcclCfgCompBrwsRuleTable 1 }

SlbCurAcclCfgCompBrwsRuleEntry ::= SEQUENCE {
    slbCurAcclCfgCompBrwsRuleListIdIndex          DisplayString,
    slbCurAcclCfgCompBrwsRuleIndex                INTEGER,
    slbCurAcclCfgCompBrwsRuleName                 DisplayString,
    slbCurAcclCfgCompBrwsRuleAgentM               INTEGER,
    slbCurAcclCfgCompBrwsRuleAgent                DisplayString,
    slbCurAcclCfgCompBrwsRuleContentM             INTEGER,
    slbCurAcclCfgCompBrwsRuleContent              DisplayString,
    slbCurAcclCfgCompBrwsRuleCompress             INTEGER,
    slbCurAcclCfgCompBrwsRuleAdminStatus          INTEGER
    }

slbCurAcclCfgCompBrwsRuleListIdIndex OBJECT-TYPE
    SYNTAX   DisplayString (SIZE (0..32))
    MAX-ACCESS  read-only
    STATUS  current
    DESCRIPTION
        "The compression browser list (key id) as an index."
    ::= { slbCurAcclCfgCompBrwsRuleEntry 1 }

slbCurAcclCfgCompBrwsRuleIndex OBJECT-TYPE
    SYNTAX   INTEGER
    MAX-ACCESS  read-only
    STATUS  current
    DESCRIPTION
        "The compression browser Rule number as an index."
    ::= { slbCurAcclCfgCompBrwsRuleEntry 2 }

slbCurAcclCfgCompBrwsRuleName OBJECT-TYPE
    SYNTAX   DisplayString (SIZE (0..32))
    MAX-ACCESS  read-only
    STATUS  current
    DESCRIPTION
        "The compression browser Rule name."
    ::= { slbCurAcclCfgCompBrwsRuleEntry 3 }

slbCurAcclCfgCompBrwsRuleAgentM OBJECT-TYPE
    SYNTAX  INTEGER {
        any(1),
        text(2),
        regex(3),
        unsupported(2147483647)
        }
    MAX-ACCESS  read-only
    STATUS  current
    DESCRIPTION
        "Defines whether user agent field should be evaluated as String, Regex or match, any (default any)."
    ::= { slbCurAcclCfgCompBrwsRuleEntry 4 }

slbCurAcclCfgCompBrwsRuleAgent OBJECT-TYPE
    SYNTAX   DisplayString (SIZE (0..255))
    MAX-ACCESS  read-only
    STATUS  current
    DESCRIPTION
        "Defines the User-Agent string for which this rule applies."
    ::= { slbCurAcclCfgCompBrwsRuleEntry 5 }

slbCurAcclCfgCompBrwsRuleContentM OBJECT-TYPE
    SYNTAX  INTEGER {
        any(1),
        text(2),
        regex(3),
        unsupported(2147483647)
        }
    MAX-ACCESS  read-only
    STATUS  current
    DESCRIPTION
        "Defines whether content type should be evaluated as String, Regex or match, any (default any)."
    ::= { slbCurAcclCfgCompBrwsRuleEntry 6 }

slbCurAcclCfgCompBrwsRuleContent OBJECT-TYPE
    SYNTAX   DisplayString
    MAX-ACCESS  read-only
    STATUS  current
    DESCRIPTION
        "Defines the Content-type string for which this rule applies."
    ::= { slbCurAcclCfgCompBrwsRuleEntry 7 }

slbCurAcclCfgCompBrwsRuleCompress OBJECT-TYPE
    SYNTAX  INTEGER {
        enabled(1),
        disabled(2),
        unsupported(2147483647)
        }
    MAX-ACCESS  read-only
    STATUS  current
    DESCRIPTION
        "Enable/Disable the compression. Defines if the matched response should be compressed or not"
    ::= { slbCurAcclCfgCompBrwsRuleEntry 8 }

slbCurAcclCfgCompBrwsRuleAdminStatus OBJECT-TYPE
    SYNTAX  INTEGER {
        enabled(1),
        disabled(2),
        unsupported(2147483647)
        }
    MAX-ACCESS  read-only
    STATUS  current
    DESCRIPTION
        "Status (enable/disable) of compression browser Rule."
    ::= { slbCurAcclCfgCompBrwsRuleEntry 9 }

slbNewAcclCfgCompBrwsRuleTable OBJECT-TYPE
    SYNTAX  SEQUENCE OF SlbNewAcclCfgCompBrwsRuleEntry
    MAX-ACCESS  not-accessible
    STATUS  current
    DESCRIPTION
        "The table for configuring compression browser Rules.
         Note:This mib is not supported for VX instance of Virtualization."
    ::= { compression 12 }

slbNewAcclCfgCompBrwsRuleEntry OBJECT-TYPE
    SYNTAX  SlbNewAcclCfgCompBrwsRuleEntry
    MAX-ACCESS  not-accessible
    STATUS  current
    DESCRIPTION
        "A row in the compression browser Rule table."
    INDEX   { slbNewAcclCfgCompBrwsRuleListIdIndex, slbNewAcclCfgCompBrwsRuleIndex }
    ::= { slbNewAcclCfgCompBrwsRuleTable 1 }

SlbNewAcclCfgCompBrwsRuleEntry ::= SEQUENCE {
    slbNewAcclCfgCompBrwsRuleListIdIndex          DisplayString,
    slbNewAcclCfgCompBrwsRuleIndex                INTEGER,
    slbNewAcclCfgCompBrwsRuleName                 DisplayString,
    slbNewAcclCfgCompBrwsRuleAgentM               INTEGER,
    slbNewAcclCfgCompBrwsRuleAgent                DisplayString,
    slbNewAcclCfgCompBrwsRuleContentM             INTEGER,
    slbNewAcclCfgCompBrwsRuleContent              DisplayString,
    slbNewAcclCfgCompBrwsRuleCompress             INTEGER,
    slbNewAcclCfgCompBrwsRuleAdminStatus          INTEGER,
    slbNewAcclCfgCompBrwsRuleDelete               INTEGER,
    slbNewAcclCfgCompBrwsRuleCopy                 INTEGER
    }

slbNewAcclCfgCompBrwsRuleListIdIndex OBJECT-TYPE
    SYNTAX   DisplayString (SIZE (0..32))
    MAX-ACCESS  read-only
    STATUS  current
    DESCRIPTION
        "The compression browser list (key id) as an index."
    ::= { slbNewAcclCfgCompBrwsRuleEntry 1 }

slbNewAcclCfgCompBrwsRuleIndex OBJECT-TYPE
    SYNTAX   INTEGER
    MAX-ACCESS  read-only
    STATUS  current
    DESCRIPTION
        "The compression browser Rule number as an index."
    ::= { slbNewAcclCfgCompBrwsRuleEntry 2 }

slbNewAcclCfgCompBrwsRuleName OBJECT-TYPE
    SYNTAX   DisplayString (SIZE (0..32))
    MAX-ACCESS  read-create
    STATUS  current
    DESCRIPTION
        "The compression browser Rule name."
    ::= { slbNewAcclCfgCompBrwsRuleEntry 3 }

slbNewAcclCfgCompBrwsRuleAgentM OBJECT-TYPE
    SYNTAX  INTEGER {
        any(1),
        text(2),
        regex(3),
        unsupported(2147483647)
        }
    MAX-ACCESS  read-create
    STATUS  current
    DESCRIPTION
        "Defines whether user agent field should be evaluated as String, Regex or match, any (default any)."
    ::= { slbNewAcclCfgCompBrwsRuleEntry 4 }

slbNewAcclCfgCompBrwsRuleAgent OBJECT-TYPE
    SYNTAX   DisplayString (SIZE (0..255))
    MAX-ACCESS  read-create
    STATUS  current
    DESCRIPTION
        "Defines the User-Agent string for which this rule applies."
    ::= { slbNewAcclCfgCompBrwsRuleEntry 5 }

slbNewAcclCfgCompBrwsRuleContentM OBJECT-TYPE
    SYNTAX  INTEGER {
        any(1),
        text(2),
        regex(3),
        unsupported(2147483647)
        }
    MAX-ACCESS  read-create
    STATUS  current
    DESCRIPTION
        "Defines whether content type should be evaluated as String, Regex or match, any (default any)."
    ::= { slbNewAcclCfgCompBrwsRuleEntry 6 }

slbNewAcclCfgCompBrwsRuleContent OBJECT-TYPE
    SYNTAX   DisplayString
    MAX-ACCESS  read-create
    STATUS  current
    DESCRIPTION
        "Defines the Content-type string for which this rule applies."
    ::= { slbNewAcclCfgCompBrwsRuleEntry 7 }

slbNewAcclCfgCompBrwsRuleCompress OBJECT-TYPE
    SYNTAX  INTEGER {
        enabled(1),
        disabled(2),
        unsupported(2147483647)
        }
    MAX-ACCESS  read-create
    STATUS  current
    DESCRIPTION
        "Enable/Disable the compression. Defines if the matched response should be compressed or not"
    ::= { slbNewAcclCfgCompBrwsRuleEntry 8 }

slbNewAcclCfgCompBrwsRuleAdminStatus OBJECT-TYPE
    SYNTAX  INTEGER {
        enabled(1),
        disabled(2),
        unsupported(2147483647)
        }
    MAX-ACCESS  read-create
    STATUS  current
    DESCRIPTION
        "Status (enable/disable) of compression browser Rule."
    ::= { slbNewAcclCfgCompBrwsRuleEntry 9 }

slbNewAcclCfgCompBrwsRuleDelete OBJECT-TYPE
    SYNTAX  INTEGER {
        other(1),
        delete(2),
        unsupported(2147483647)
        }
    MAX-ACCESS  read-create
    STATUS  current
    DESCRIPTION
        "By setting the value to delete(2), the entire row is deleted."
    ::= { slbNewAcclCfgCompBrwsRuleEntry 10 }

slbNewAcclCfgCompBrwsRuleCopy OBJECT-TYPE
    SYNTAX   INTEGER
    MAX-ACCESS  read-create
    STATUS  current
    DESCRIPTION
        "Copy rule to another index in the same rule-list."
    ::= { slbNewAcclCfgCompBrwsRuleEntry 11 }	

-- icap

slbCurIcapPolTable OBJECT-TYPE
    SYNTAX  SEQUENCE OF SlbCurIcapPolEntry
    MAX-ACCESS  not-accessible
    STATUS  current
    DESCRIPTION
        "The table for configuring icap policy.
         Note:This mib is not supported for VX instance of Virtualization."
    ::= { icapPolCfg 1 }

slbCurIcapPolEntry OBJECT-TYPE
    SYNTAX  SlbCurIcapPolEntry
    MAX-ACCESS  not-accessible
    STATUS  current
    DESCRIPTION
        "A row in the icap policy table.
         Note:This mib is not supported for VX instance of Virtualization."
    INDEX   { slbCurIcapPolNameIdIndex }
    ::= { slbCurIcapPolTable 1 }

SlbCurIcapPolEntry ::= SEQUENCE {
    slbCurIcapPolNameIdIndex           DisplayString,
    slbCurIcapPolName                  DisplayString,
    slbCurIcapPolAdminStatus           INTEGER,
    slbCurIcapPolReqmodStatus          INTEGER,
    slbCurIcapPolReqmodUri             DisplayString,
    slbCurIcapPolReqmodGroup           DisplayString,
    slbCurIcapPolReqmodFallback        INTEGER,
    slbCurIcapPolReqmodPreview         INTEGER,
    slbCurIcapPolReqmodFrom            DisplayString, 
    slbCurIcapPolReqmodHost            DisplayString, 
    slbCurIcapPolReqmodReferer         DisplayString, 
    slbCurIcapPolReqmodAgent           DisplayString,
    slbCurIcapPolReqmodXcipHeader      DisplayString,
    slbCurIcapPolReqmodXcip            INTEGER,
    slbCurIcapPolRespmodStatus         INTEGER,
    slbCurIcapPolRespmodUri            DisplayString,
    slbCurIcapPolRespmodGroup          DisplayString,
    slbCurIcapPolRespmodFallback       INTEGER,
    slbCurIcapPolRespmodPreview        INTEGER,
    slbCurIcapPolRespmodFrom           DisplayString, 
    slbCurIcapPolRespmodHost           DisplayString, 
    slbCurIcapPolRespmodReferer        DisplayString, 
    slbCurIcapPolRespmodAgent          DisplayString,
    slbCurIcapPolRespmodXcip           INTEGER,
    slbCurIcapPolRespmodXcipHeader     DisplayString
    }

slbCurIcapPolNameIdIndex OBJECT-TYPE
    SYNTAX   DisplayString (SIZE (0..32))
    MAX-ACCESS  read-only
    STATUS  current
    DESCRIPTION
        "The Icap policy ID(key id) as an index."
    ::= { slbCurIcapPolEntry 1 }
    
slbCurIcapPolName OBJECT-TYPE
    SYNTAX   DisplayString (SIZE (0..32))
    MAX-ACCESS  read-only
    STATUS  current
    DESCRIPTION
        "Icap policy name."
    ::= { slbCurIcapPolEntry 2 }    

slbCurIcapPolAdminStatus OBJECT-TYPE
    SYNTAX  INTEGER {
        enabled(1),
        disabled(2),
        unsupported(2147483647)
        }
    MAX-ACCESS  read-only
    STATUS  current
    DESCRIPTION
        "Status (enable/disable) of icap policy."
    ::= { slbCurIcapPolEntry 3 }

slbCurIcapPolReqmodStatus OBJECT-TYPE
    SYNTAX  INTEGER {
        enabled(1),
        disabled(2),
        unsupported(2147483647)
        }
    MAX-ACCESS  read-only
    STATUS  current
    DESCRIPTION
        "Status (enable/disable) of icap policy."
    ::= { slbCurIcapPolEntry 31 }

slbCurIcapPolReqmodUri OBJECT-TYPE
    SYNTAX   DisplayString (SIZE (0..255))
    MAX-ACCESS  read-only
    STATUS  current
    DESCRIPTION
        "Icap Uri string."
    ::= { slbCurIcapPolEntry 32 }
       
slbCurIcapPolReqmodGroup OBJECT-TYPE   
    SYNTAX  DisplayString (SIZE (0..255))   
    MAX-ACCESS  read-only   
    STATUS  current   
    DESCRIPTION 
        "The Icap Reqmod  server group number."   
    ::= { slbCurIcapPolEntry 33 } 

slbCurIcapPolReqmodFallback OBJECT-TYPE
    SYNTAX  INTEGER {
        drop(1),
        contFlow(2),
        unsupported(2147483647)
        }
    MAX-ACCESS  read-only
    STATUS  current
    DESCRIPTION
        "Fallback action (group down)."
    ::= { slbCurIcapPolEntry 34 }

slbCurIcapPolReqmodPreview OBJECT-TYPE
    SYNTAX  INTEGER (0..1048576)
    MAX-ACCESS  read-only
    STATUS  current
    DESCRIPTION
        "The maximum preview number in bytes." 
    ::= { slbCurIcapPolEntry 35 }

slbCurIcapPolReqmodFrom OBJECT-TYPE
    SYNTAX   DisplayString (SIZE (0..255))
    MAX-ACCESS  read-only
    STATUS  current
    DESCRIPTION
        "Icap From string."
    ::= { slbCurIcapPolEntry 36 }

slbCurIcapPolReqmodHost OBJECT-TYPE
    SYNTAX   DisplayString (SIZE (0..255))
    MAX-ACCESS  read-only
    STATUS  current
    DESCRIPTION
        "Icap Host string."
    ::= { slbCurIcapPolEntry 37 }

slbCurIcapPolReqmodReferer OBJECT-TYPE
    SYNTAX   DisplayString (SIZE (0..255))
    MAX-ACCESS  read-only
    STATUS  current
    DESCRIPTION
        "Icap Referer string."
    ::= { slbCurIcapPolEntry 38 }

slbCurIcapPolReqmodAgent OBJECT-TYPE
    SYNTAX   DisplayString (SIZE (0..255))
    MAX-ACCESS  read-only
    STATUS  current
    DESCRIPTION
        "Icap User-Agent string."
    ::= { slbCurIcapPolEntry 39 }

slbCurIcapPolReqmodXcip OBJECT-TYPE
    SYNTAX  INTEGER {
        cip(1),
        xff(2),
        disabled(3),
        unsupported(2147483647)
        }
    MAX-ACCESS  read-only
    STATUS  current
    DESCRIPTION
        "Icap X-Client-IP status."
    ::= { slbCurIcapPolEntry 40 }

slbCurIcapPolReqmodXcipHeader OBJECT-TYPE
    SYNTAX   DisplayString (SIZE (0..255))
    MAX-ACCESS  read-only
    STATUS  current
    DESCRIPTION
        "Icap xcip header string."
    ::= { slbCurIcapPolEntry 41 }
    
slbCurIcapPolRespmodStatus OBJECT-TYPE
    SYNTAX  INTEGER {
        enabled(1),
        disabled(2),
        unsupported(2147483647)
        }
    MAX-ACCESS  read-only
    STATUS  current
    DESCRIPTION
        "Status (enable/disable) of icap policy."
    ::= { slbCurIcapPolEntry 61 }
    
slbCurIcapPolRespmodUri OBJECT-TYPE
    SYNTAX   DisplayString (SIZE (0..255))
    MAX-ACCESS  read-only
    STATUS  current
    DESCRIPTION
        "Icap Uri string."
    ::= { slbCurIcapPolEntry 62 }
    
slbCurIcapPolRespmodGroup OBJECT-TYPE   
    SYNTAX  DisplayString (SIZE (0..255))   
    MAX-ACCESS  read-only   
    STATUS  current   
    DESCRIPTION 
        "The Icap Respmod  server group number."   
    ::= { slbCurIcapPolEntry 63 }  

slbCurIcapPolRespmodFallback OBJECT-TYPE
    SYNTAX  INTEGER {
        drop(1),
        contFlow(2),
        unsupported(2147483647)
        }
    MAX-ACCESS  read-only
    STATUS  current
    DESCRIPTION
        "Fallback action (group down)."
    ::= { slbCurIcapPolEntry 64 }

slbCurIcapPolRespmodPreview OBJECT-TYPE
    SYNTAX  INTEGER (0..1048576)
    MAX-ACCESS  read-only
    STATUS  current
    DESCRIPTION
        "The maximum preview number in bytes." 
    ::= { slbCurIcapPolEntry 65 }

slbCurIcapPolRespmodFrom OBJECT-TYPE
    SYNTAX   DisplayString (SIZE (0..255))
    MAX-ACCESS  read-only
    STATUS  current
    DESCRIPTION
        "Icap From string."
    ::= { slbCurIcapPolEntry 66 }


slbCurIcapPolRespmodHost OBJECT-TYPE
    SYNTAX   DisplayString (SIZE (0..255))
    MAX-ACCESS  read-only
    STATUS  current
    DESCRIPTION
        "Icap Host string."
    ::= { slbCurIcapPolEntry 67 }

slbCurIcapPolRespmodReferer OBJECT-TYPE
    SYNTAX   DisplayString (SIZE (0..255))
    MAX-ACCESS  read-only
    STATUS  current
    DESCRIPTION
        "Icap Referer string."
    ::= { slbCurIcapPolEntry 68 }

slbCurIcapPolRespmodAgent OBJECT-TYPE
    SYNTAX   DisplayString (SIZE (0..255))
    MAX-ACCESS  read-only
    STATUS  current
    DESCRIPTION
        "Icap User-Agent string."
    ::= { slbCurIcapPolEntry 69 }

slbCurIcapPolRespmodXcip OBJECT-TYPE
    SYNTAX  INTEGER {
        cip(1),
        xff(2),
        disabled(3),
        unsupported(2147483647)
        }
    MAX-ACCESS  read-only
    STATUS  current
    DESCRIPTION
        "Icap X-Client-IP status."
    ::= { slbCurIcapPolEntry 70 }

slbCurIcapPolRespmodXcipHeader OBJECT-TYPE
    SYNTAX   DisplayString (SIZE (0..255))
    MAX-ACCESS  read-only
    STATUS  current
    DESCRIPTION
        "Icap xcip header string."
    ::= { slbCurIcapPolEntry 71 }
    
-- icap_new

slbNewIcapPolTable OBJECT-TYPE
    SYNTAX  SEQUENCE OF SlbNewIcapPolEntry
    MAX-ACCESS  not-accessible
    STATUS  current
    DESCRIPTION
        "The table for configuring icap policy.
         Note:This mib is not supported for VX instance of Virtualization."
    ::= { icapPolCfg 2 }

slbNewIcapPolEntry OBJECT-TYPE
    SYNTAX  SlbNewIcapPolEntry
    MAX-ACCESS  not-accessible
    STATUS  current
    DESCRIPTION
        "A row in the icap policy table.
         Note:This mib is not supported for VX instance of Virtualization."
    INDEX   { slbNewIcapPolNameIdIndex }
    ::= { slbNewIcapPolTable 1 }

SlbNewIcapPolEntry ::= SEQUENCE {
    slbNewIcapPolNameIdIndex           DisplayString,
    slbNewIcapPolName                  DisplayString,
    slbNewIcapPolAdminStatus           INTEGER,
    slbNewIcapPolDel                   INTEGER,
    slbNewIcapPolReqmodStatus          INTEGER,
    slbNewIcapPolReqmodUri             DisplayString,
    slbNewIcapPolReqmodGroup           DisplayString,
    slbNewIcapPolReqmodFallback        INTEGER,
    slbNewIcapPolReqmodPreview         INTEGER,
    slbNewIcapPolReqmodFrom            DisplayString, 
    slbNewIcapPolReqmodHost            DisplayString, 
    slbNewIcapPolReqmodReferer         DisplayString, 
    slbNewIcapPolReqmodAgent           DisplayString,
    slbNewIcapPolReqmodXcip            INTEGER,
    slbNewIcapPolReqmodXcipHeader      DisplayString,
    slbNewIcapPolRespmodStatus         INTEGER,
    slbNewIcapPolRespmodUri            DisplayString,
    slbNewIcapPolRespmodGroup          DisplayString,
    slbNewIcapPolRespmodFallback       INTEGER,
    slbNewIcapPolRespmodPreview        INTEGER,
    slbNewIcapPolRespmodFrom           DisplayString, 
    slbNewIcapPolRespmodHost           DisplayString, 
    slbNewIcapPolRespmodReferer        DisplayString, 
    slbNewIcapPolRespmodAgent          DisplayString,
    slbNewIcapPolRespmodXcip           INTEGER,
    slbNewIcapPolRespmodXcipHeader     DisplayString
    }

slbNewIcapPolNameIdIndex OBJECT-TYPE
    SYNTAX   DisplayString (SIZE (0..32))
    MAX-ACCESS  read-create
    STATUS  current
    DESCRIPTION
        "The Icap policy ID(key id) as an index."
    ::= { slbNewIcapPolEntry 1 }
    
slbNewIcapPolName OBJECT-TYPE
    SYNTAX   DisplayString (SIZE (0..32))
    MAX-ACCESS  read-create
    STATUS  current
    DESCRIPTION
        "Icap policy name."
    ::= { slbNewIcapPolEntry 2 }    

slbNewIcapPolAdminStatus OBJECT-TYPE
    SYNTAX  INTEGER {
        enabled(1),
        disabled(2),
        unsupported(2147483647)
        }
    MAX-ACCESS  read-create
    STATUS  current
    DESCRIPTION
        "Status (enable/disable) of icap policy."
    ::= { slbNewIcapPolEntry 3 }

slbNewIcapPolDel  OBJECT-TYPE
    SYNTAX  INTEGER {
        other(1),
        delete(2),
        unsupported(2147483647)
    }
    MAX-ACCESS  read-create
    STATUS  current
    DESCRIPTION
        "Delete Icap policy."
    ::= { slbNewIcapPolEntry 4 }

slbNewIcapPolReqmodStatus OBJECT-TYPE
    SYNTAX  INTEGER {
        enabled(1),
        disabled(2),
        unsupported(2147483647)
        }
    MAX-ACCESS  read-create
    STATUS  current
    DESCRIPTION
        "Status (enable/disable) of icap policy."
    ::= { slbNewIcapPolEntry 31 }

slbNewIcapPolReqmodUri OBJECT-TYPE
    SYNTAX   DisplayString (SIZE (0..255))
    MAX-ACCESS  read-create
    STATUS  current
    DESCRIPTION
        "Icap Uri string."
    ::= { slbNewIcapPolEntry 32 }
       
slbNewIcapPolReqmodGroup OBJECT-TYPE   
    SYNTAX  DisplayString (SIZE (0..255))   
    MAX-ACCESS  read-create   
    STATUS  current   
    DESCRIPTION 
        "The Icap Reqmod  server group number."   
    ::= { slbNewIcapPolEntry 33 } 

slbNewIcapPolReqmodFallback OBJECT-TYPE
    SYNTAX  INTEGER {
        drop(1),
        contFlow(2),
        unsupported(2147483647)
        }
    MAX-ACCESS  read-create
    STATUS  current
    DESCRIPTION
        "Fallback action (group down)."
    ::= { slbNewIcapPolEntry 34 }

slbNewIcapPolReqmodPreview OBJECT-TYPE
    SYNTAX  INTEGER (0..1048576)
    MAX-ACCESS  read-create
    STATUS  current
    DESCRIPTION
        "The maximum preview number in bytes." 
    ::= { slbNewIcapPolEntry 35 }

slbNewIcapPolReqmodFrom OBJECT-TYPE
    SYNTAX   DisplayString (SIZE (0..255))
    MAX-ACCESS  read-create
    STATUS  current
    DESCRIPTION
        "Icap From string."
    ::= { slbNewIcapPolEntry 36 }

slbNewIcapPolReqmodHost OBJECT-TYPE
    SYNTAX   DisplayString (SIZE (0..255))
    MAX-ACCESS  read-create
    STATUS  current
    DESCRIPTION
        "Icap Host string."
    ::= { slbNewIcapPolEntry 37 }

slbNewIcapPolReqmodReferer OBJECT-TYPE
    SYNTAX   DisplayString (SIZE (0..255))
    MAX-ACCESS  read-create
    STATUS  current
    DESCRIPTION
        "Icap Referer string."
    ::= { slbNewIcapPolEntry 38 }

slbNewIcapPolReqmodAgent OBJECT-TYPE
    SYNTAX   DisplayString (SIZE (0..255))
    MAX-ACCESS  read-create
    STATUS  current
    DESCRIPTION
        "Icap User-Agent string."
    ::= { slbNewIcapPolEntry 39 }

slbNewIcapPolReqmodXcip OBJECT-TYPE
    SYNTAX  INTEGER {
        cip(1),
        xff(2),
        disabled(3),
        unsupported(2147483647)
        }
    MAX-ACCESS  read-create
    STATUS  current
    DESCRIPTION
        "Icap X-Client-IP status."
    ::= { slbNewIcapPolEntry 40 }

slbNewIcapPolReqmodXcipHeader OBJECT-TYPE
    SYNTAX   DisplayString (SIZE (0..255))
    MAX-ACCESS  read-create
    STATUS  current
    DESCRIPTION
        "Icap xcip header string."
    ::= { slbNewIcapPolEntry 41 }
    
slbNewIcapPolRespmodStatus OBJECT-TYPE
    SYNTAX  INTEGER {
        enabled(1),
        disabled(2),
        unsupported(2147483647)
        }
    MAX-ACCESS  read-create
    STATUS  current
    DESCRIPTION
        "Status (enable/disable) of icap policy."
    ::= { slbNewIcapPolEntry 61 }
    
slbNewIcapPolRespmodUri OBJECT-TYPE
    SYNTAX   DisplayString (SIZE (0..255))
    MAX-ACCESS  read-create
    STATUS  current
    DESCRIPTION
        "Icap Uri string."
    ::= { slbNewIcapPolEntry 62 }
    
slbNewIcapPolRespmodGroup OBJECT-TYPE   
    SYNTAX  DisplayString (SIZE (0..255))   
    MAX-ACCESS  read-create   
    STATUS  current   
    DESCRIPTION 
        "The Icap Respmod  server group number."   
    ::= { slbNewIcapPolEntry 63 }  

slbNewIcapPolRespmodFallback OBJECT-TYPE
    SYNTAX  INTEGER {
        drop(1),
        contFlow(2),
        unsupported(2147483647)
        }
    MAX-ACCESS  read-create
    STATUS  current
    DESCRIPTION
        "Fallback action (group down)."
    ::= { slbNewIcapPolEntry 64 }

slbNewIcapPolRespmodPreview OBJECT-TYPE
    SYNTAX  INTEGER (0..1048576)
    MAX-ACCESS  read-create
    STATUS  current
    DESCRIPTION
        "The maximum preview number in bytes." 
    ::= { slbNewIcapPolEntry 65 }

slbNewIcapPolRespmodFrom OBJECT-TYPE
    SYNTAX   DisplayString (SIZE (0..255))
    MAX-ACCESS  read-create
    STATUS  current
    DESCRIPTION
        "Icap From string."
    ::= { slbNewIcapPolEntry 66 }

slbNewIcapPolRespmodHost OBJECT-TYPE
    SYNTAX   DisplayString (SIZE (0..255))
    MAX-ACCESS  read-create
    STATUS  current
    DESCRIPTION
        "Icap Host string."
    ::= { slbNewIcapPolEntry 67 }

slbNewIcapPolRespmodReferer OBJECT-TYPE
    SYNTAX   DisplayString (SIZE (0..255))
    MAX-ACCESS  read-create
    STATUS  current
    DESCRIPTION
        "Icap Referer string."
    ::= { slbNewIcapPolEntry 68 }

slbNewIcapPolRespmodAgent OBJECT-TYPE
    SYNTAX   DisplayString (SIZE (0..255))
    MAX-ACCESS  read-create
    STATUS  current
    DESCRIPTION
        "Icap User-Agent string."
    ::= { slbNewIcapPolEntry 69 }

slbNewIcapPolRespmodXcip OBJECT-TYPE
    SYNTAX  INTEGER {
        cip(1),
        xff(2),
        disabled(3),
        unsupported(2147483647)
        }
    MAX-ACCESS  read-create
    STATUS  current
    DESCRIPTION
        "Icap X-Client-IP status."
    ::= { slbNewIcapPolEntry 70 }

slbNewIcapPolRespmodXcipHeader OBJECT-TYPE
    SYNTAX   DisplayString (SIZE (0..255))
    MAX-ACCESS  read-create
    STATUS  current
    DESCRIPTION
        "Icap xcip header string."
    ::= { slbNewIcapPolEntry 71 }

-- icap_end

-- http2

slbCurAcclCfgHttp2PolTable OBJECT-TYPE
    SYNTAX  SEQUENCE OF SlbCurAcclCfgHttp2PolEntry
    MAX-ACCESS  not-accessible
    STATUS  current
    DESCRIPTION
        "The table for configuring http2 policy.
         Note:This mib is not supported for VX instance of Virtualization."
    ::= { http2 1 }

slbCurAcclCfgHttp2PolEntry OBJECT-TYPE
    SYNTAX  SlbCurAcclCfgHttp2PolEntry
    MAX-ACCESS  not-accessible
    STATUS  current
    DESCRIPTION
        "A row in the http2 policy table."
    INDEX   { slbCurAcclCfgHttp2PolNameIdIndex }
    ::= { slbCurAcclCfgHttp2PolTable 1 }

SlbCurAcclCfgHttp2PolEntry ::= SEQUENCE {
    slbCurAcclCfgHttp2PolNameIdIndex          DisplayString,
    slbCurAcclCfgHttp2PolName                 DisplayString,
    slbCurAcclCfgHttp2PolAdminStatus          INTEGER,
    slbCurAcclCfgHttp2PolStreams              INTEGER,
    slbCurAcclCfgHttp2PolIdle                 INTEGER,
    slbCurAcclCfgHttp2PolEnaInsert            INTEGER,
    slbCurAcclCfgHttp2PolHeader               DisplayString, 
    slbCurAcclCfgHttp2PolEnaServerPush        INTEGER,
    slbCurAcclCfgHttp2PolHpackSize            DisplayString,
    slbCurAcclCfgHttp2PolBackendStatus        INTEGER,
    slbCurAcclCfgHttp2PolBackendStreams       INTEGER,
    slbCurAcclCfgHttp2PolBackendHpackSize     DisplayString,
    slbCurAcclCfgHttp2PolBackendServerPush    INTEGER
    }

slbCurAcclCfgHttp2PolNameIdIndex OBJECT-TYPE
    SYNTAX   DisplayString (SIZE (0..32))
    MAX-ACCESS  read-only
    STATUS  current
    DESCRIPTION
        "The http2 policy ID(key id) as an index."
    ::= { slbCurAcclCfgHttp2PolEntry 1 }
    
slbCurAcclCfgHttp2PolName OBJECT-TYPE
    SYNTAX   DisplayString (SIZE (0..32))
    MAX-ACCESS  read-only
    STATUS  current
    DESCRIPTION
        "Http2 policy name."
    ::= { slbCurAcclCfgHttp2PolEntry 2 }    

slbCurAcclCfgHttp2PolAdminStatus OBJECT-TYPE
    SYNTAX  INTEGER {
        enabled(1),
        disabled(2),
        unsupported(2147483647)
        }
    MAX-ACCESS  read-only
    STATUS  current
    DESCRIPTION
        "Status (enable/disable) of http2 policy."
    ::= { slbCurAcclCfgHttp2PolEntry 3 }
    
slbCurAcclCfgHttp2PolStreams OBJECT-TYPE
    SYNTAX   INTEGER (0..255)
    MAX-ACCESS  read-only
    STATUS  current
    DESCRIPTION
        "maximum concurrent streams per connection."
    ::= { slbCurAcclCfgHttp2PolEntry 4 }
    
slbCurAcclCfgHttp2PolIdle OBJECT-TYPE
	SYNTAX  INTEGER (0..65534)    
    MAX-ACCESS  read-only
    STATUS  current
    DESCRIPTION
        "Display the number of seconds an HTTP/2 connection is left open idly before it is closed."
    ::= { slbCurAcclCfgHttp2PolEntry 5 }

slbCurAcclCfgHttp2PolEnaInsert OBJECT-TYPE
    SYNTAX  INTEGER {
        enabled(1),
        disabled(2),
        unsupported(2147483647)
        }
    MAX-ACCESS  read-only
    STATUS  current
    DESCRIPTION
        "Status (enable/disable) of insert private http2 header."
    ::= { slbCurAcclCfgHttp2PolEntry 6 }

slbCurAcclCfgHttp2PolHeader OBJECT-TYPE
    SYNTAX   DisplayString (SIZE (0..128))
    MAX-ACCESS  read-only
    STATUS  current
    DESCRIPTION
        "Http2 header string."
    ::= { slbCurAcclCfgHttp2PolEntry 7 }   
                    
slbCurAcclCfgHttp2PolEnaServerPush OBJECT-TYPE
    SYNTAX  INTEGER {
        enabled(1),
        disabled(2),
        unsupported(2147483647)
        }
    MAX-ACCESS  read-only
    STATUS  current
    DESCRIPTION
        "Status (enable/disable) of insert http2 server push."
    ::= { slbCurAcclCfgHttp2PolEntry 8 }
    
slbCurAcclCfgHttp2PolHpackSize OBJECT-TYPE
    SYNTAX   DisplayString (SIZE (0..10))
    MAX-ACCESS  read-only
    STATUS  current
    DESCRIPTION
        "HTTP2 policy HPACK table size (small / medium / large)."
    ::= { slbCurAcclCfgHttp2PolEntry 9 }    

slbCurAcclCfgHttp2PolBackendStatus OBJECT-TYPE
    SYNTAX  INTEGER {
        enabled(1),
        disabled(2),
        unsupported(2147483647)
        }
    MAX-ACCESS  read-only
    STATUS  current
    DESCRIPTION
        "Backend Status (enable/disable) of backend http2."
    ::= { slbCurAcclCfgHttp2PolEntry 11 }

slbCurAcclCfgHttp2PolBackendStreams OBJECT-TYPE
    SYNTAX   INTEGER (0..255)
    MAX-ACCESS  read-only
    STATUS  current
    DESCRIPTION
        "maximum concurrent streams per backend connection."
    ::= { slbCurAcclCfgHttp2PolEntry 12 }

slbCurAcclCfgHttp2PolBackendHpackSize OBJECT-TYPE
    SYNTAX   DisplayString (SIZE (0..10))
    MAX-ACCESS  read-only
    STATUS  current
    DESCRIPTION
        "HTTP2 policy backend HPACK table size (small / medium / large)."
    ::= { slbCurAcclCfgHttp2PolEntry 13 }   

slbCurAcclCfgHttp2PolBackendServerPush OBJECT-TYPE
    SYNTAX   INTEGER (0..255)
    MAX-ACCESS  read-only
    STATUS  obsolete
    DESCRIPTION
        "maximum concurrent server push streams per backend connection."
    ::= { slbCurAcclCfgHttp2PolEntry 14 }

--HTTP2_new

slbNewAcclCfgHttp2PolTable OBJECT-TYPE
    SYNTAX  SEQUENCE OF SlbNewAcclCfgHttp2PolEntry
    MAX-ACCESS  not-accessible
    STATUS  current
    DESCRIPTION
        "The table for configuring http2 policy.
         Note:This mib is not supported for VX instance of Virtualization."
    ::= { http2 2 }

slbNewAcclCfgHttp2PolEntry OBJECT-TYPE
    SYNTAX  SlbNewAcclCfgHttp2PolEntry
    MAX-ACCESS  not-accessible
    STATUS  current
    DESCRIPTION
        "A row in the http2 policy table."
    INDEX   { slbNewAcclCfgHttp2PolNameIdIndex }
    ::= { slbNewAcclCfgHttp2PolTable 1 }

SlbNewAcclCfgHttp2PolEntry ::= SEQUENCE {
    slbNewAcclCfgHttp2PolNameIdIndex          DisplayString,
    slbNewAcclCfgHttp2PolName                 DisplayString,
    slbNewAcclCfgHttp2PolAdminStatus          INTEGER,
    slbNewAcclCfgHttp2PolStreams              INTEGER,
    slbNewAcclCfgHttp2PolIdle                 INTEGER,
    slbNewAcclCfgHttp2PolEnaInsert            INTEGER,
    slbNewAcclCfgHttp2PolHeader               DisplayString,
    slbNewAcclCfgHttp2PolEnaServerPush        INTEGER,
    slbNewAcclCfgHttp2PolHpackSize            DisplayString,	
    slbNewAcclCfgHttp2PolDelete               INTEGER,
    slbNewAcclCfgHttp2PolBackendStatus        INTEGER,
    slbNewAcclCfgHttp2PolBackendStreams       INTEGER,
    slbNewAcclCfgHttp2PolBackendHpackSize     DisplayString,
    slbNewAcclCfgHttp2PolBackendServerPush    INTEGER
    }

slbNewAcclCfgHttp2PolNameIdIndex OBJECT-TYPE
    SYNTAX   DisplayString (SIZE (0..32))
    MAX-ACCESS  read-only
    STATUS  current
    DESCRIPTION
        "The http2 policy ID(key id) as an index."
    ::= { slbNewAcclCfgHttp2PolEntry 1 }

slbNewAcclCfgHttp2PolName OBJECT-TYPE
    SYNTAX   DisplayString (SIZE (0..32))
    MAX-ACCESS  read-create
    STATUS  current
    DESCRIPTION
        "Http2 policy name."
    ::= { slbNewAcclCfgHttp2PolEntry 2 }
    
slbNewAcclCfgHttp2PolAdminStatus OBJECT-TYPE
    SYNTAX  INTEGER {
        enabled(1),
        disabled(2),
        unsupported(2147483647)
        }
    MAX-ACCESS  read-create
    STATUS  current
    DESCRIPTION
        "Status (enable/disable) of http2 policy."
    ::= { slbNewAcclCfgHttp2PolEntry 3 }
        
slbNewAcclCfgHttp2PolStreams OBJECT-TYPE
    SYNTAX  INTEGER (1..255)
    MAX-ACCESS  read-create
    STATUS  current
    DESCRIPTION
        "Defines the maximum concurrent streams per connection."
    ::= { slbNewAcclCfgHttp2PolEntry 4 }        
               
slbNewAcclCfgHttp2PolIdle OBJECT-TYPE
    SYNTAX  INTEGER (1..65534)
    MAX-ACCESS  read-create
    STATUS  current
    DESCRIPTION
        "Defines the number of seconds an HTTP/2 connection is left open idly before it is closed."
    ::= { slbNewAcclCfgHttp2PolEntry 5 }   

slbNewAcclCfgHttp2PolEnaInsert OBJECT-TYPE
    SYNTAX  INTEGER {
        enabled(1),
        disabled(2),
        unsupported(2147483647)
        }
    MAX-ACCESS  read-create
    STATUS  current
    DESCRIPTION
        "Define (enable/disable) of insert private http2 header."
    ::= { slbNewAcclCfgHttp2PolEntry 6 }

slbNewAcclCfgHttp2PolHeader OBJECT-TYPE
    SYNTAX   DisplayString (SIZE (0..128))
    MAX-ACCESS  read-create
    STATUS  current
    DESCRIPTION
        "Http2 policy header string."
    ::= { slbNewAcclCfgHttp2PolEntry 7 }

slbNewAcclCfgHttp2PolEnaServerPush OBJECT-TYPE
    SYNTAX  INTEGER {
        enabled(1),
        disabled(2),
        unsupported(2147483647)
        }
    MAX-ACCESS  read-create
    STATUS  current
    DESCRIPTION
        "Define (enable/disable) of http2 server push."
    ::= { slbNewAcclCfgHttp2PolEntry 8 }
    
slbNewAcclCfgHttp2PolHpackSize OBJECT-TYPE
    SYNTAX   DisplayString (SIZE (0..10))
    MAX-ACCESS  read-create
    STATUS  current
    DESCRIPTION
        "Set HTTP2 policy HPACK table size (small / medium / large)."
    ::= { slbNewAcclCfgHttp2PolEntry 9 }
                
slbNewAcclCfgHttp2PolDelete OBJECT-TYPE
    SYNTAX  INTEGER {
        other(1),
        delete(2),
        unsupported(2147483647)
        }
    MAX-ACCESS  read-create
    STATUS  current
    DESCRIPTION
        "Delete Http2 policy."
    ::= { slbNewAcclCfgHttp2PolEntry 10 }
                    
slbNewAcclCfgHttp2PolBackendStatus OBJECT-TYPE
    SYNTAX  INTEGER {
        enabled(1),
        disabled(2),
        unsupported(2147483647)
        }
    MAX-ACCESS  read-create
    STATUS  current
    DESCRIPTION
        "Backend Status (enable/disable) of backend http2."
    ::= { slbNewAcclCfgHttp2PolEntry 11 }

slbNewAcclCfgHttp2PolBackendStreams OBJECT-TYPE
    SYNTAX   INTEGER (0..255)
    MAX-ACCESS  read-create
    STATUS  current
    DESCRIPTION
        "maximum concurrent streams per backend connection."
    ::= { slbNewAcclCfgHttp2PolEntry 12 }

slbNewAcclCfgHttp2PolBackendHpackSize OBJECT-TYPE
    SYNTAX   DisplayString (SIZE (0..10))
    MAX-ACCESS  read-create
    STATUS  current
    DESCRIPTION
        "HTTP2 policy backend HPACK table size (small / medium / large)."
    ::= { slbNewAcclCfgHttp2PolEntry 13 }   

slbNewAcclCfgHttp2PolBackendServerPush OBJECT-TYPE
    SYNTAX   INTEGER (0..255)
    MAX-ACCESS  read-create
    STATUS  obsolete
    DESCRIPTION
        "maximum concurrent server push streams per backend connection."
    ::= { slbNewAcclCfgHttp2PolEntry 14 }

-- SLB Cluster Configuration - BEGIN
slbCurCfgClusterRole OBJECT-TYPE
    SYNTAX  INTEGER {
    off(1),
    frontend(2),
    member(3),
    unsupported(2147483647)
    }
    MAX-ACCESS  read-only
    STATUS  current
    DESCRIPTION
        "Current device role in clustering. Default is OFF.
         Note:This mib is not supported on VX instance of Virtualization."
    ::= { slbClusterCfg 1 }

slbNewCfgClusterRole OBJECT-TYPE
    SYNTAX  INTEGER {
    off(1),
    frontend(2),
    member(3),
    unsupported(2147483647)
    }
    MAX-ACCESS  read-write
    STATUS  current
    DESCRIPTION
        "New device role in clustering. Default is OFF.
         Note:This mib is not supported on VX instance of Virtualization."
    ::= { slbClusterCfg 2 }

slbCurCfgClusterFeprimaV4 OBJECT-TYPE
    SYNTAX  IpAddress
    MAX-ACCESS  read-only
    STATUS  current
    DESCRIPTION
        "Current frontend primary IPv4 address to send cluster updates.
         Note:This mib is not supported on VX instance of Virtualization."
    ::= { slbClusterCfg 3 }

slbCurCfgClusterFeprimaV6 OBJECT-TYPE
    SYNTAX DisplayString (SIZE(0..40))
    MAX-ACCESS  read-only
    STATUS  current
    DESCRIPTION
        "Current frontend primary IPv6 address to send cluster updates.
         Note:This mib is not supported on VX instance of Virtualization."
    ::= { slbClusterCfg 4 }

slbNewCfgClusterFeprimaV4 OBJECT-TYPE
    SYNTAX  IpAddress
    MAX-ACCESS  read-write
    STATUS  current
    DESCRIPTION
        "New frontend primary IPv4 address to send cluster updates.
         Note:This mib is not supported on VX instance of Virtualization."
    ::= { slbClusterCfg 5 }

slbNewCfgClusterFeprimaV6 OBJECT-TYPE
    SYNTAX DisplayString (SIZE(0..40))
    MAX-ACCESS  read-write
    STATUS  current
    DESCRIPTION
        "New frontend primary IPv6 address to send cluster updates.
         Note:This mib is not supported on VX instance of Virtualization."
    ::= { slbClusterCfg 6 }

slbCurCfgClusterFeseconV4 OBJECT-TYPE
    SYNTAX  IpAddress
    MAX-ACCESS  read-only
    STATUS  current
    DESCRIPTION
        "Current frontend secondary IPv4 address to send cluster updates.
         Note:This mib is not supported on VX instance of Virtualization."
    ::= { slbClusterCfg 7 }

slbCurCfgClusterFeseconV6 OBJECT-TYPE
    SYNTAX DisplayString (SIZE(0..40))
    MAX-ACCESS  read-only
    STATUS  current
    DESCRIPTION
        "Current frontend secondary IPv6 address to send cluster updates.
         Note:This mib is not supported on VX instance of Virtualization."
    ::= { slbClusterCfg 8 }

slbNewCfgClusterFeseconV4 OBJECT-TYPE
    SYNTAX  IpAddress
    MAX-ACCESS  read-write
    STATUS  current
    DESCRIPTION
        "New frontend secondary IPv4 address to send cluster updates.
         Note:This mib is not supported on VX instance of Virtualization."
    ::= { slbClusterCfg 9 }

slbNewCfgClusterFeseconV6 OBJECT-TYPE
    SYNTAX DisplayString (SIZE(0..40))
    MAX-ACCESS  read-write
    STATUS  current
    DESCRIPTION
        "Current frontend secondary IP address to send cluster updates.
         Note:This mib is not supported on VX instance of Virtualization."
    ::= { slbClusterCfg 10 }

slbCurCfgClusterFeprimaIpVer OBJECT-TYPE
    SYNTAX  INTEGER {
        ipv4(1),
        ipv6(2),
        unsupported(2147483647)
        }
    MAX-ACCESS  read-only
    STATUS  current
    DESCRIPTION
        "Current config frontend primary IP version.
         Note:This mib is not supported on VX instance of Virtualization."
    ::= { slbClusterCfg 11 }

slbNewCfgClusterFeprimaIpVer OBJECT-TYPE
    SYNTAX  INTEGER {
        ipv4(1),
        ipv6(2),
        unsupported(2147483647)
        }
    MAX-ACCESS  read-write
    STATUS  current
    DESCRIPTION
        "New config frontend primary IP version. Setting respective v4 or v6
         address mibs will take care of setting the version. Hence, set to this
         mib is ignored.
         Note:This mib is not supported on VX instance of Virtualization."
    ::= { slbClusterCfg 12 }

slbCurCfgClusterFeseconIpVer OBJECT-TYPE
    SYNTAX  INTEGER {
        ipv4(1),
        ipv6(2),
        unsupported(2147483647)
        }
    MAX-ACCESS  read-only
    STATUS  current
    DESCRIPTION
        "Current config frontend secondary IP version.
         Note:This mib is not supported on VX instance of Virtualization."
    ::= { slbClusterCfg 13 }

slbNewCfgClusterFeseconIpVer OBJECT-TYPE
    SYNTAX  INTEGER {
        ipv4(1),
        ipv6(2),
        unsupported(2147483647)
        }
    MAX-ACCESS  read-write
    STATUS  current
    DESCRIPTION
        "New config frontend secondary IP version. Setting respective v4 or v6
         address mibs will take care of setting the version. Hence, set to this
         mib is ignored.
         Note:This mib is not supported on VX instance of Virtualization."
    ::= { slbClusterCfg 14 }

slbCurCfgClusterFeprima2V4 OBJECT-TYPE
    SYNTAX  IpAddress
    MAX-ACCESS  read-only
    STATUS  current
    DESCRIPTION
        "Current frontend primary IPv4 address to send cluster updates.
         Note:This mib is not supported on VX instance of Virtualization."
    ::= { slbClusterCfg 15 }

slbCurCfgClusterFeprima2V6 OBJECT-TYPE
    SYNTAX DisplayString (SIZE(0..40))
    MAX-ACCESS  read-only
    STATUS  current
    DESCRIPTION
        "Current frontend primary IPv6 address to send cluster updates.
         Note:This mib is not supported on VX instance of Virtualization."
    ::= { slbClusterCfg 16 }

slbNewCfgClusterFeprima2V4 OBJECT-TYPE
    SYNTAX  IpAddress
    MAX-ACCESS  read-write
    STATUS  current
    DESCRIPTION
        "New frontend primary IPv4 address to send cluster updates.
         Note:This mib is not supported on VX instance of Virtualization."
    ::= { slbClusterCfg 17 }

slbNewCfgClusterFeprima2V6 OBJECT-TYPE
    SYNTAX DisplayString (SIZE(0..40))
    MAX-ACCESS  read-write
    STATUS  current
    DESCRIPTION
        "New frontend primary IPv6 address to send cluster updates.
         Note:This mib is not supported on VX instance of Virtualization."
    ::= { slbClusterCfg 18 }

slbCurCfgClusterFesecon2V4 OBJECT-TYPE
    SYNTAX  IpAddress
    MAX-ACCESS  read-only
    STATUS  current
    DESCRIPTION
        "Current frontend secondary IPv4 address to send cluster updates.
         Note:This mib is not supported on VX instance of Virtualization."
    ::= { slbClusterCfg 19 }

slbCurCfgClusterFesecon2V6 OBJECT-TYPE
    SYNTAX DisplayString (SIZE(0..40))
    MAX-ACCESS  read-only
    STATUS  current
    DESCRIPTION
        "Current frontend secondary IPv6 address to send cluster updates.
         Note:This mib is not supported on VX instance of Virtualization."
    ::= { slbClusterCfg 20 }

slbNewCfgClusterFesecon2V4 OBJECT-TYPE
    SYNTAX  IpAddress
    MAX-ACCESS  read-write
    STATUS  current
    DESCRIPTION
        "New frontend secondary IPv4 address to send cluster updates.
         Note:This mib is not supported on VX instance of Virtualization."
    ::= { slbClusterCfg 21 }

slbNewCfgClusterFesecon2V6 OBJECT-TYPE
    SYNTAX DisplayString (SIZE(0..40))
    MAX-ACCESS  read-write
    STATUS  current
    DESCRIPTION
        "Current frontend secondary IP address to send cluster updates.
         Note:This mib is not supported on VX instance of Virtualization."
    ::= { slbClusterCfg 22 }

slbCurCfgClusterFeprima2IpVer OBJECT-TYPE
    SYNTAX  INTEGER {
        ipv4(1),
        ipv6(2),
        unsupported(2147483647)
        }
    MAX-ACCESS  read-only
    STATUS  current
    DESCRIPTION
        "Current config frontend primary IP version.
         Note:This mib is not supported on VX instance of Virtualization."
    ::= { slbClusterCfg 23 }

slbNewCfgClusterFeprima2IpVer OBJECT-TYPE
    SYNTAX  INTEGER {
        ipv4(1),
        ipv6(2),
        unsupported(2147483647)
        }
    MAX-ACCESS  read-write
    STATUS  current
    DESCRIPTION
        "New config frontend primary IP version. Setting respective v4 or v6
         address mibs will take care of setting the version. Hence, set to this
         mib is ignored.
         Note:This mib is not supported on VX instance of Virtualization."
    ::= { slbClusterCfg 24 }

slbCurCfgClusterFesecon2IpVer OBJECT-TYPE
    SYNTAX  INTEGER {
        ipv4(1),
        ipv6(2),
        unsupported(2147483647)
        }
    MAX-ACCESS  read-only
    STATUS  current
    DESCRIPTION
        "Current config frontend secondary IP version.
         Note:This mib is not supported on VX instance of Virtualization."
    ::= { slbClusterCfg 25 }

slbNewCfgClusterFesecon2IpVer OBJECT-TYPE
    SYNTAX  INTEGER {
        ipv4(1),
        ipv6(2),
        unsupported(2147483647)
        }
    MAX-ACCESS  read-write
    STATUS  current
    DESCRIPTION
        "New config frontend secondary IP version. Setting respective v4 or v6
         address mibs will take care of setting the version. Hence, set to this
         mib is ignored.
         Note:This mib is not supported on VX instance of Virtualization."
    ::= { slbClusterCfg 26 }

-- SLB Cluster Configuration - END

trafficEventCurCfgGlobalControl OBJECT-TYPE
    SYNTAX  INTEGER {
    on(1),
    off(2),
    unsupported(2147483647)
    }
    MAX-ACCESS  read-only
    STATUS  current
    DESCRIPTION
        "Current traffic event log policy global role either on or off. Default is off.
         Note:This mib is not supported on VX instance of Virtualization."
    ::= { trafficEventCfg 1 }

trafficEventNewCfgGlobalControl OBJECT-TYPE
    SYNTAX  INTEGER {
    on(1),
    off(2),
    unsupported(2147483647)
    }
    MAX-ACCESS  read-create
    STATUS  current
    DESCRIPTION
        "Set traffic event log policy global role either on or off. Default is off.
         Note:This mib is not supported on VX instance of Virtualization."
    ::= { trafficEventCfg 2 }

slbCurTrafficEventClassesTable OBJECT-TYPE
    SYNTAX  SEQUENCE OF SlbCurTrafficEventClassesEntry
    MAX-ACCESS  not-accessible
    STATUS  current
    DESCRIPTION
        "Current traffic event table.
         Note:This mib is not supported on VX instance of Virtualization."
    ::= { trafficEventCfg 3 }

slbCurTrafficEventClassesEntry OBJECT-TYPE
    SYNTAX  SlbCurTrafficEventClassesEntry
    MAX-ACCESS  not-accessible
    STATUS  current
    DESCRIPTION
        "A row in the traffic event classes table.
         Note:This mib is not supported on VX instance of Virtualization."
    INDEX   { slbCurTrafficEventId }
    ::= { slbCurTrafficEventClassesTable 1 }

SlbCurTrafficEventClassesEntry ::= SEQUENCE {
    slbCurTrafficEventId            DisplayString,
    slbCurTrafficEventName          DisplayString,
    slbCurTrafficEventGroupName     DisplayString,
    slbCurTrafficEventSysPort       INTEGER,
    slbCurTrafficEventSampleRate    INTEGER,
    slbCurTrafficEventEnaDis        INTEGER,
    slbCurTrafficEventHttpTran      INTEGER,
    slbCurTrafficEventPathCorl      INTEGER,
    slbCurTrafficEventSslConn       INTEGER,
    slbCurTrafficEventSslFail       INTEGER,
    slbCurTrafficEventHostByPass    INTEGER,
    slbCurTrafficEventL4Conn        INTEGER,
    slbCurTrafficEventRemoteLogId   DisplayString,
    slbCurTrafficEventUnified       INTEGER,
    slbCurTrafficEventNormalEps     INTEGER,
    slbCurTrafficEventExceptionEps  INTEGER
    }

slbCurTrafficEventId OBJECT-TYPE
    SYNTAX   DisplayString (SIZE (0..128))
    MAX-ACCESS  read-only
    STATUS  current
    DESCRIPTION
        "Traffic event class id."
    ::= { slbCurTrafficEventClassesEntry 1 }

slbCurTrafficEventName OBJECT-TYPE
    SYNTAX   DisplayString (SIZE (0..128))
    MAX-ACCESS  read-only
    STATUS  current
    DESCRIPTION
        "Traffic event class name."
    ::= { slbCurTrafficEventClassesEntry 2 }

slbCurTrafficEventGroupName OBJECT-TYPE
    SYNTAX   DisplayString (SIZE (0..255))
    MAX-ACCESS  read-only
    STATUS  current
    DESCRIPTION
        "Traffic event class attach group name."
    ::= { slbCurTrafficEventClassesEntry 3 }

slbCurTrafficEventSysPort OBJECT-TYPE
    SYNTAX  INTEGER (0..65535)
    MAX-ACCESS  read-only
    STATUS  current
    DESCRIPTION
        "Traffic event log policy syslog server port."
   ::= { slbCurTrafficEventClassesEntry 4 }

slbCurTrafficEventSampleRate OBJECT-TYPE
    SYNTAX  INTEGER (1..100)
    MAX-ACCESS  read-only
    STATUS  current
    DESCRIPTION
        "Traffic event log policy sampling rate."
    ::= { slbCurTrafficEventClassesEntry 5 }

slbCurTrafficEventEnaDis OBJECT-TYPE
    SYNTAX  INTEGER {
        enabled(1),
        disabled(2),
        unsupported(2147483647)
        }
    MAX-ACCESS  read-only
    STATUS  current
    DESCRIPTION
        "Traffic event policy current status as Ena or Dis."
    ::= { slbCurTrafficEventClassesEntry 6 }

slbCurTrafficEventHttpTran OBJECT-TYPE
    SYNTAX  INTEGER {
        enabled(1),
        disabled(2),
        unsupported(2147483647)
        }
    MAX-ACCESS  read-only
    STATUS  current
    DESCRIPTION
        "Traffic event policy http transaction status."
    ::= { slbCurTrafficEventClassesEntry 7 }

slbCurTrafficEventPathCorl OBJECT-TYPE
    SYNTAX  INTEGER {
        disabled(1),
        entry(2),
        exit(3),
        unsupported(2147483647)
        }
    MAX-ACCESS  read-only
    STATUS  current
    DESCRIPTION
        "Traffic event policy http transaction path correlation."
    ::= { slbCurTrafficEventClassesEntry 8 }

slbCurTrafficEventSslConn OBJECT-TYPE
    SYNTAX  INTEGER {
        disabled(1),
        frontend(2),
        backend(3),
        both(4),
        unsupported(2147483647)
        }
    MAX-ACCESS  read-only
    STATUS  current
    DESCRIPTION
        "Traffic event policy ssl connection status."
    ::= { slbCurTrafficEventClassesEntry 9 }

slbCurTrafficEventSslFail OBJECT-TYPE
    SYNTAX  INTEGER {
        disabled(1),
        frontend(2),
        backend(3),
        both(4),
        unsupported(2147483647)
        }
    MAX-ACCESS  read-only
    STATUS  current
    DESCRIPTION
        "Traffic event policy ssl connection fail status."
    ::= { slbCurTrafficEventClassesEntry 10 }

slbCurTrafficEventHostByPass OBJECT-TYPE
    SYNTAX  INTEGER {
        enabled(1),
        disabled(2),
        unsupported(2147483647)
        }
    MAX-ACCESS  read-only
    STATUS  current
    DESCRIPTION
        "Traffic event policy hotbypass current status as Ena or Dis."
    ::= { slbCurTrafficEventClassesEntry 11 }

slbCurTrafficEventL4Conn OBJECT-TYPE
    SYNTAX  INTEGER {
        enabled(1),
        disabled(2),
        unsupported(2147483647)
        }
    MAX-ACCESS  read-only
    STATUS  current
    DESCRIPTION
        "Traffic event policy current status as Ena or Dis."
    ::= { slbCurTrafficEventClassesEntry 12 }

slbCurTrafficEventRemoteLogId OBJECT-TYPE
    SYNTAX   DisplayString (SIZE (0..32))
    MAX-ACCESS  read-only
    STATUS  current
    DESCRIPTION
        "Current Remote logging object."
    ::= { slbCurTrafficEventClassesEntry 13 }

slbCurTrafficEventUnified OBJECT-TYPE
    SYNTAX  INTEGER {
        enabled(1),
        disabled(2),
        unsupported(2147483647)
        }
    MAX-ACCESS  read-only
    STATUS  current
    DESCRIPTION
        "Traffic event policy unified event current status as Ena or Dis."
    ::= { slbCurTrafficEventClassesEntry 14 }
    
slbCurTrafficEventNormalEps OBJECT-TYPE
    SYNTAX  INTEGER (0..1000000)
    MAX-ACCESS  read-only
    STATUS  current
    DESCRIPTION
        "Traffic event log policy normal EPS limit."
    ::= { slbCurTrafficEventClassesEntry 15 }

slbCurTrafficEventExceptionEps OBJECT-TYPE
    SYNTAX  INTEGER (0..1000000)
    MAX-ACCESS  read-only
    STATUS  current
    DESCRIPTION
        "Traffic event log policy exception EPS limit."
    ::= { slbCurTrafficEventClassesEntry 16 }    

slbNewTrafficEventClassesTable OBJECT-TYPE
    SYNTAX  SEQUENCE OF SlbNewTrafficEventClassesEntry
    MAX-ACCESS  not-accessible
    STATUS  current
    DESCRIPTION
        "Current traffic event table.
         Note:This mib is not supported on VX instance of Virtualization."
    ::= { trafficEventCfg 4 }

slbNewTrafficEventClassesEntry OBJECT-TYPE
    SYNTAX  SlbNewTrafficEventClassesEntry
    MAX-ACCESS  not-accessible
    STATUS  current
    DESCRIPTION
        "A row in the traffic event classes table.
         Note:This mib is not supported on VX instance of Virtualization."
    INDEX   { slbNewTrafficEventId }
    ::= { slbNewTrafficEventClassesTable 1 }

SlbNewTrafficEventClassesEntry ::= SEQUENCE {
    slbNewTrafficEventId            DisplayString,
    slbNewTrafficEventName          DisplayString,
    slbNewTrafficEventGroupName     DisplayString,
    slbNewTrafficEventSysPort       INTEGER,
    slbNewTrafficEventSampleRate    INTEGER,
    slbNewTrafficEventEnaDis        INTEGER,
    slbNewTrafficEventHttpTran      INTEGER,
    slbNewTrafficEventPathCorl      INTEGER,
    slbNewTrafficEventSslConn       INTEGER,
    slbNewTrafficEventSslFail       INTEGER,
    slbNewTrafficEventHostByPass    INTEGER,
    slbNewTrafficEventL4Conn        INTEGER,
    slbNewTrafficEventDel           INTEGER,
    slbNewTrafficEventRemoteLogId   DisplayString,
    slbNewTrafficEventUnified       INTEGER,
    slbNewTrafficEventNormalEps     INTEGER,
    slbNewTrafficEventExceptionEps  INTEGER    
    }

slbNewTrafficEventId OBJECT-TYPE
    SYNTAX   DisplayString (SIZE (0..128))
    MAX-ACCESS  read-create
    STATUS  current
    DESCRIPTION
        "Set traffic event class id."
    ::= { slbNewTrafficEventClassesEntry 1 }

slbNewTrafficEventName OBJECT-TYPE
    SYNTAX   DisplayString (SIZE (0..128))
    MAX-ACCESS  read-create
    STATUS  current
    DESCRIPTION
        "Set traffic event class name."
    ::= { slbNewTrafficEventClassesEntry 2 }

slbNewTrafficEventGroupName OBJECT-TYPE
    SYNTAX   DisplayString (SIZE (0..255))
    MAX-ACCESS  read-create
    STATUS  current
    DESCRIPTION
        "Set traffic event group name."
    ::= { slbNewTrafficEventClassesEntry 3 }

slbNewTrafficEventSysPort OBJECT-TYPE
    SYNTAX  INTEGER (0..65535)
    MAX-ACCESS  read-create
    STATUS  current
    DESCRIPTION
        "Set traffic event log policy syslog server port."
   ::= { slbNewTrafficEventClassesEntry 4 }

slbNewTrafficEventSampleRate OBJECT-TYPE
    SYNTAX  INTEGER (1..100)
    MAX-ACCESS  read-create
    STATUS  current
    DESCRIPTION
        "Set traffic event log policy sampling rate."
    ::= { slbNewTrafficEventClassesEntry 5 }

slbNewTrafficEventEnaDis OBJECT-TYPE
    SYNTAX  INTEGER {
        enabled(1),
        disabled(2),
        unsupported(2147483647)
        }
    MAX-ACCESS  read-create
    STATUS  current
    DESCRIPTION
        "Set traffic event policy status either ena or dis."
    ::= { slbNewTrafficEventClassesEntry 6 }

slbNewTrafficEventHttpTran OBJECT-TYPE
    SYNTAX  INTEGER {
        enabled(1),
        disabled(2),
        unsupported(2147483647)
        }
    MAX-ACCESS  read-create
    STATUS  current
    DESCRIPTION
        "Set http transaction status for the traffic event policy."
    ::= { slbNewTrafficEventClassesEntry 7 }

slbNewTrafficEventPathCorl OBJECT-TYPE
    SYNTAX  INTEGER {
        disabled(1),
        entry(2),
        exit(3),
        unsupported(2147483647)
        }
    MAX-ACCESS  read-create
    STATUS  current
    DESCRIPTION
        "Set http transaction path correlation for the traffic event policy."
    ::= { slbNewTrafficEventClassesEntry 8 }

slbNewTrafficEventSslConn OBJECT-TYPE
    SYNTAX  INTEGER {
        disabled(1),
        frontend(2),
        backend(3),
        both(4),
        unsupported(2147483647)
        }
    MAX-ACCESS  read-create
    STATUS  current
    DESCRIPTION
        "Set ssl connection status for traffic event policy."
    ::= { slbNewTrafficEventClassesEntry 9 }

slbNewTrafficEventSslFail OBJECT-TYPE
    SYNTAX  INTEGER {
        disabled(1),
        frontend(2),
        backend(3),
        both(4),
        unsupported(2147483647)
        }
    MAX-ACCESS  read-create
    STATUS  current
    DESCRIPTION
        "Set ssl connection fail status for traffic event policy."
    ::= { slbNewTrafficEventClassesEntry 10 }

slbNewTrafficEventHostByPass OBJECT-TYPE
    SYNTAX  INTEGER {
        enabled(1),
        disabled(2),
        unsupported(2147483647)
        }
    MAX-ACCESS  read-create
    STATUS  current
    DESCRIPTION
        "set hotbypass status either ena or dis for the traffic event policy."
    ::= { slbNewTrafficEventClassesEntry 11 }

slbNewTrafficEventL4Conn OBJECT-TYPE
    SYNTAX  INTEGER {
        enabled(1),
        disabled(2),
        unsupported(2147483647)
        }
    MAX-ACCESS  read-create
    STATUS  current
    DESCRIPTION
        "Set l4 connection status either ena or dis for the traffic event policy."
    ::= { slbNewTrafficEventClassesEntry 12 }

slbNewTrafficEventDel OBJECT-TYPE
    SYNTAX  INTEGER {
        other(1),
        delete(2),
        unsupported(2147483647)
        }
    MAX-ACCESS  read-create
    STATUS  current
    DESCRIPTION
        "By setting the value to delete(2), the entire row is deleted."
    ::= { slbNewTrafficEventClassesEntry 13 }

slbNewTrafficEventRemoteLogId OBJECT-TYPE
    SYNTAX   DisplayString (SIZE (0..32))
    MAX-ACCESS  read-create
    STATUS  current
    DESCRIPTION
        "Set Remote logging object"
    ::= { slbNewTrafficEventClassesEntry 14 }

slbNewTrafficEventUnified OBJECT-TYPE
    SYNTAX  INTEGER {
        enabled(1),
        disabled(2),
        unsupported(2147483647)
        }
    MAX-ACCESS  read-create
    STATUS  current
    DESCRIPTION
        "Set unified event status either ena or dis for the traffic event policy."
    ::= { slbNewTrafficEventClassesEntry 15 }
    
slbNewTrafficEventNormalEps OBJECT-TYPE
    SYNTAX  INTEGER (0..1000000)
    MAX-ACCESS  read-create
    STATUS  current
    DESCRIPTION
        "Set traffic event log policy Normal EPS limit: 1-999999 Events per second limit, disable or 0, Unlimited or 1000000"
    ::= { slbNewTrafficEventClassesEntry 16 }

slbNewTrafficEventExceptionEps OBJECT-TYPE
    SYNTAX  INTEGER (0..1000000)
    MAX-ACCESS  read-create
    STATUS  current
    DESCRIPTION
        "Set traffic event log policy Exception EPS limit: 1-999999 Events per second limit, disable or 0, Unlimited or 1000000"
    ::= { slbNewTrafficEventClassesEntry 17 }
        

 -- NWCLSS

 -- Network classifiers
slbCurNwclssCfgNetworkClassesTable OBJECT-TYPE
    SYNTAX  SEQUENCE OF SlbCurNwclssCfgNetworkClassesEntry
    MAX-ACCESS  not-accessible
    STATUS  current
    DESCRIPTION
        "Current network classes table.
         Note:This mib is not supported for VX instance of Virtualization."
    ::= { nwclssCfg 1 }

slbCurNwclssCfgNetworkClassesEntry OBJECT-TYPE
    SYNTAX  SlbCurNwclssCfgNetworkClassesEntry
    MAX-ACCESS  not-accessible
    STATUS  current
    DESCRIPTION
        "A row in the network classes table."
    INDEX   { slbCurNwclssCfgNetworkClassesId }
    ::= { slbCurNwclssCfgNetworkClassesTable 1 }

SlbCurNwclssCfgNetworkClassesEntry ::= SEQUENCE {
    slbCurNwclssCfgNetworkClassesId          DisplayString,
    slbCurNwclssCfgNetworkClassesName        DisplayString,
    slbCurNwclssCfgNetworkClassesIpVer       INTEGER,
    slbCurNwclssCfgNetworkClassesType    INTEGER
    }

slbCurNwclssCfgNetworkClassesId OBJECT-TYPE
    SYNTAX   DisplayString (SIZE (0..32))
    MAX-ACCESS  read-only
    STATUS  current
    DESCRIPTION
        "Network class id."
    ::= { slbCurNwclssCfgNetworkClassesEntry 1 }

slbCurNwclssCfgNetworkClassesName OBJECT-TYPE
    SYNTAX   DisplayString (SIZE (0..32))
    MAX-ACCESS  read-only
    STATUS  current
    DESCRIPTION
        "Network class name."
    ::= { slbCurNwclssCfgNetworkClassesEntry 2 }

slbCurNwclssCfgNetworkClassesIpVer OBJECT-TYPE
    SYNTAX  INTEGER{
        ipv4(1),
        ipv6(2),
        unsupported(2147483647)
        }
    MAX-ACCESS  read-only
    STATUS  current
    DESCRIPTION
        "The type of IP address."
   ::= { slbCurNwclssCfgNetworkClassesEntry 3 }

slbCurNwclssCfgNetworkClassesType OBJECT-TYPE
    SYNTAX  INTEGER {
        address(1),
        region(2),
        unsupported(2147483647)
        }
    MAX-ACCESS  read-only
    STATUS  current
    DESCRIPTION
        "The network class type should be either 'address' or 'region'."
    ::= { slbCurNwclssCfgNetworkClassesEntry 4 }

slbNewNwclssCfgNetworkClassesTable OBJECT-TYPE
    SYNTAX  SEQUENCE OF SlbNewNwclssCfgNetworkClassesEntry
    MAX-ACCESS  not-accessible
    STATUS  current
    DESCRIPTION
        "New network classes table.
         Note:This mib is not supported for VX instance of Virtualization."
    ::= { nwclssCfg 2 }

slbNewNwclssCfgNetworkClassesEntry OBJECT-TYPE
    SYNTAX  SlbNewNwclssCfgNetworkClassesEntry
    MAX-ACCESS  not-accessible
    STATUS  current
    DESCRIPTION
        "A row in the new network classes table."
    INDEX   { slbNewNwclssCfgNetworkClassesId }
    ::= { slbNewNwclssCfgNetworkClassesTable 1 }

SlbNewNwclssCfgNetworkClassesEntry ::= SEQUENCE {
    slbNewNwclssCfgNetworkClassesId       	DisplayString,
    slbNewNwclssCfgNetworkClassesName     	DisplayString,
    slbNewNwclssCfgNetworkClassesIpVer      INTEGER,
    slbNewNwclssCfgNetworkClassesDel	INTEGER,
    slbNewNwclssCfgNetworkClassesCopy       DisplayString,
    slbNewNwclssCfgNetworkClassesType    INTEGER
    }

slbNewNwclssCfgNetworkClassesId OBJECT-TYPE
    SYNTAX   DisplayString (SIZE (0..32))
    MAX-ACCESS  read-only
    STATUS  current
    DESCRIPTION
        "Network class id."
    ::= { slbNewNwclssCfgNetworkClassesEntry 1 }

slbNewNwclssCfgNetworkClassesName OBJECT-TYPE
    SYNTAX   DisplayString (SIZE (0..32))
    MAX-ACCESS  read-create
    STATUS  current
    DESCRIPTION
        "Network class name."
    ::= { slbNewNwclssCfgNetworkClassesEntry 2 }

slbNewNwclssCfgNetworkClassesIpVer OBJECT-TYPE
    SYNTAX  INTEGER {
        ipv4(1),
        ipv6(2),
        unsupported(2147483647)
        }
    MAX-ACCESS  read-create
    STATUS  current
    DESCRIPTION
        "The type of IP address."
    ::= { slbNewNwclssCfgNetworkClassesEntry 3 }

slbNewNwclssCfgNetworkClassesDel OBJECT-TYPE
    SYNTAX  INTEGER {
        other(1),
        delete(2),
        unsupported(2147483647)
        }
    MAX-ACCESS  read-create
    STATUS  current
    DESCRIPTION
        "By setting the value to delete(2), the entire row is deleted."
    ::= { slbNewNwclssCfgNetworkClassesEntry 4 }

slbNewNwclssCfgNetworkClassesCopy OBJECT-TYPE
    SYNTAX   DisplayString (SIZE (0..32))
    MAX-ACCESS  read-create
    STATUS  current
    DESCRIPTION
        "Duplicating an entire Network class by defining the destination Network class id."
    ::= { slbNewNwclssCfgNetworkClassesEntry 5 }

slbNewNwclssCfgNetworkClassesType OBJECT-TYPE
    SYNTAX  INTEGER {
        address(1),
        region(2),
        unsupported(2147483647)
        }
    MAX-ACCESS  read-create
    STATUS  current
    DESCRIPTION
        "The network class type should be either 'address' or 'region' to be added to the network."
    ::= { slbNewNwclssCfgNetworkClassesEntry 6 }

 -- Network elements
slbCurNwclssCfgNetworkElementsTable OBJECT-TYPE
    SYNTAX  SEQUENCE OF SlbCurNwclssCfgNetworkElementsEntry
    MAX-ACCESS  not-accessible
    STATUS  current
    DESCRIPTION
        "Current network elements table.
         Note:This mib is not supported for VX instance of Virtualization."
    ::= { nwclssCfg 3 }

slbCurNwclssCfgNetworkElementsEntry OBJECT-TYPE
    SYNTAX  SlbCurNwclssCfgNetworkElementsEntry
    MAX-ACCESS  not-accessible
    STATUS  current
    DESCRIPTION
        "A row in the network elements table."
    INDEX   { slbCurNwclssCfgNetworkElementsNcId, slbCurNwclssCfgNetworkElementsId }
    ::= { slbCurNwclssCfgNetworkElementsTable 1 }

SlbCurNwclssCfgNetworkElementsEntry ::= SEQUENCE {
    slbCurNwclssCfgNetworkElementsNcId          DisplayString,
    slbCurNwclssCfgNetworkElementsId		DisplayString,
    slbCurNwclssCfgNetworkElementsNetType    	INTEGER,
    slbCurNwclssCfgNetworkElementsIp      	IpAddress,
    slbCurNwclssCfgNetworkElementsMask    	IpAddress,
    slbCurNwclssCfgNetworkElementsFromIp      	IpAddress,
    slbCurNwclssCfgNetworkElementsToIp      	IpAddress,
    slbCurNwclssCfgNetworkElementsIpv6Addr      DisplayString,
    slbCurNwclssCfgNetworkElementsPrefixLen    	INTEGER,
    slbCurNwclssCfgNetworkElementsFromIpv6Addr  DisplayString,
    slbCurNwclssCfgNetworkElementsToIpv6Addr    DisplayString,
    slbCurNwclssCfgNetworkElementsMatchType     INTEGER,
    slbCurNwclssCfgNetworkElementsRegCont       DisplayString,
    slbCurNwclssCfgNetworkElementsRegCountry    DisplayString,
    slbCurNwclssCfgNetworkElementsRegState      DisplayString,
    slbCurNwclssCfgNetworkTypeAddrOrRegn        INTEGER
    }
 
slbCurNwclssCfgNetworkElementsNcId OBJECT-TYPE
    SYNTAX   DisplayString (SIZE (0..32))
    MAX-ACCESS  read-only
    STATUS  current
    DESCRIPTION
        "Id of network class which owns network element."
    ::= { slbCurNwclssCfgNetworkElementsEntry 1 }

slbCurNwclssCfgNetworkElementsId OBJECT-TYPE
    SYNTAX   DisplayString (SIZE (0..32))
    MAX-ACCESS  read-only
    STATUS  current
    DESCRIPTION
        "Network element id."
    ::= { slbCurNwclssCfgNetworkElementsEntry 2 }

slbCurNwclssCfgNetworkElementsNetType OBJECT-TYPE
    SYNTAX  INTEGER{
        subnet(1),
        range(2),
        unsupported(2147483647)
        }
    MAX-ACCESS  read-only
    STATUS  current
    DESCRIPTION
        "The type of network."
   ::= { slbCurNwclssCfgNetworkElementsEntry 3 }

slbCurNwclssCfgNetworkElementsIp OBJECT-TYPE
    SYNTAX  IpAddress
    MAX-ACCESS  read-only
    STATUS  current
    DESCRIPTION
        "IPv4 address of network element."
    ::= { slbCurNwclssCfgNetworkElementsEntry 4 }

slbCurNwclssCfgNetworkElementsMask OBJECT-TYPE
    SYNTAX  IpAddress
    MAX-ACCESS  read-only
    STATUS  current  
    DESCRIPTION
        "Subnet mask of network element."
    ::= { slbCurNwclssCfgNetworkElementsEntry 5 }

slbCurNwclssCfgNetworkElementsFromIp OBJECT-TYPE
    SYNTAX  IpAddress
    MAX-ACCESS  read-only
    STATUS  current
    DESCRIPTION
        "From IP address of network element."
    ::= { slbCurNwclssCfgNetworkElementsEntry 6 }

slbCurNwclssCfgNetworkElementsToIp OBJECT-TYPE
    SYNTAX  IpAddress
    MAX-ACCESS  read-only
    STATUS  current
    DESCRIPTION
        "To IP address of network element."
    ::= { slbCurNwclssCfgNetworkElementsEntry 7 }

slbCurNwclssCfgNetworkElementsIpv6Addr OBJECT-TYPE
    SYNTAX   DisplayString (SIZE(0..40))
    MAX-ACCESS  read-only
    STATUS  current
    DESCRIPTION
        "The IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 8 }

slbCurNwclssCfgNetworkElementsPrefixLen OBJECT-TYPE
    SYNTAX  INTEGER(1..128) 
    MAX-ACCESS  read-only
    STATUS  current
    DESCRIPTION
        "The prefix length associated with the network IP address ."
    ::= { slbCurNwclssCfgNetworkElementsEntry 9 }

slbCurNwclssCfgNetworkElementsFromIpv6Addr OBJECT-TYPE
    SYNTAX   DisplayString (SIZE(0..40))
    MAX-ACCESS  read-only
    STATUS  current
    DESCRIPTION
        "The from IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 10 }

slbCurNwclssCfgNetworkElementsToIpv6Addr OBJECT-TYPE
    SYNTAX   DisplayString (SIZE(0..40))
    MAX-ACCESS  read-only
    STATUS  current
    DESCRIPTION
        "The to IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 11 }
 
slbCurNwclssCfgNetworkElementsMatchType OBJECT-TYPE
    SYNTAX  INTEGER{
        include(1),
        exclude(2),
        unsupported(2147483647)
        }
    MAX-ACCESS  read-only
    STATUS  current
    DESCRIPTION
        "The match type of network element."
   ::= { slbCurNwclssCfgNetworkElementsEntry 12 }

slbCurNwclssCfgNetworkElementsRegCont OBJECT-TYPE
    SYNTAX   DisplayString (SIZE (0..64))
    MAX-ACCESS  read-only
    STATUS  current
    DESCRIPTION
        "Continent name of the region to be added for network element."
    ::= { slbCurNwclssCfgNetworkElementsEntry 13 }

slbCurNwclssCfgNetworkElementsRegCountry OBJECT-TYPE
    SYNTAX   DisplayString (SIZE (0..64))
    MAX-ACCESS  read-only
    STATUS  current
    DESCRIPTION
        "Country/Geolocation name of the region to be added for network element."
    ::= { slbCurNwclssCfgNetworkElementsEntry 14 }

slbCurNwclssCfgNetworkElementsRegState OBJECT-TYPE
    SYNTAX   DisplayString (SIZE (0..64))
    MAX-ACCESS  read-only
    STATUS  current
    DESCRIPTION
        "State name of the region to be added for network element."
    ::= { slbCurNwclssCfgNetworkElementsEntry 15 }

slbCurNwclssCfgNetworkTypeAddrOrRegn OBJECT-TYPE
    SYNTAX  INTEGER {
        address(1),
        region(2),
        unsupported(2147483647)
        }
    MAX-ACCESS  read-only
    STATUS  current
    DESCRIPTION
        "The network class type should be either 'address' or 'region' from network class."
    ::= { slbCurNwclssCfgNetworkElementsEntry 16 }

slbNewNwclssCfgNetworkElementsTable  OBJECT-TYPE
    SYNTAX  SEQUENCE OF SlbNewNwclssCfgNetworkElementsEntry
    MAX-ACCESS  not-accessible
    STATUS  current
    DESCRIPTION
        "New network elements table.
         Note:This mib is not supported for VX instance of Virtualization."
    ::= { nwclssCfg 4 }

slbNewNwclssCfgNetworkElementsEntry OBJECT-TYPE
    SYNTAX  SlbNewNwclssCfgNetworkElementsEntry
    MAX-ACCESS  not-accessible
    STATUS  current
    DESCRIPTION
        "A row in the new network elements table."
    INDEX   { slbNewNwclssCfgNetworkElementsNcId, slbNewNwclssCfgNetworkElementsId }
    ::= { slbNewNwclssCfgNetworkElementsTable 1 }
 
SlbNewNwclssCfgNetworkElementsEntry ::= SEQUENCE {
    slbNewNwclssCfgNetworkElementsNcId          DisplayString,
    slbNewNwclssCfgNetworkElementsId		DisplayString,
    slbNewNwclssCfgNetworkElementsNetType    	INTEGER,
    slbNewNwclssCfgNetworkElementsIp      	IpAddress,
    slbNewNwclssCfgNetworkElementsMask    	IpAddress,
    slbNewNwclssCfgNetworkElementsFromIp      	IpAddress,
    slbNewNwclssCfgNetworkElementsToIp      	IpAddress,
    slbNewNwclssCfgNetworkElementsIpv6Addr      DisplayString,
    slbNewNwclssCfgNetworkElementsPrefixLen    	INTEGER,
    slbNewNwclssCfgNetworkElementsFromIpv6Addr  DisplayString,
    slbNewNwclssCfgNetworkElementsToIpv6Addr    DisplayString,
    slbNewNwclssCfgNetworkElementsMatchType     INTEGER,
    slbNewNwclssCfgNetworkElementsDel		INTEGER,
    slbNewNwclssCfgNetworkElementsRegCont       DisplayString,
    slbNewNwclssCfgNetworkElementsRegCountry    DisplayString,
    slbNewNwclssCfgNetworkElementsRegState      DisplayString,
    slbNewNwclssCfgNetworkTypeAddrOrRegn        INTEGER
    }

slbNewNwclssCfgNetworkElementsNcId OBJECT-TYPE
    SYNTAX   DisplayString (SIZE (0..32))
    MAX-ACCESS  read-only
    STATUS  current
    DESCRIPTION
        "ID of network class which owns network element."
    ::= { slbNewNwclssCfgNetworkElementsEntry 1 }

slbNewNwclssCfgNetworkElementsId OBJECT-TYPE
    SYNTAX   DisplayString (SIZE (0..32))
    MAX-ACCESS  read-only
    STATUS  current
    DESCRIPTION
        "Network class ID."
    ::= { slbNewNwclssCfgNetworkElementsEntry 2 }

slbNewNwclssCfgNetworkElementsNetType OBJECT-TYPE
    SYNTAX  INTEGER {
        subnet(1),
        range(2),
        unsupported(2147483647)
        }
    MAX-ACCESS  read-create
    STATUS  current
    DESCRIPTION
        "The type of network."
    ::= { slbNewNwclssCfgNetworkElementsEntry 3 }

slbNewNwclssCfgNetworkElementsIp OBJECT-TYPE
    SYNTAX  IpAddress
    MAX-ACCESS  read-create
    STATUS  current
    DESCRIPTION
        "IP address of network element."
    ::= { slbNewNwclssCfgNetworkElementsEntry 4 }

slbNewNwclssCfgNetworkElementsMask OBJECT-TYPE
    SYNTAX  IpAddress
    MAX-ACCESS  read-create
    STATUS  current  
    DESCRIPTION
        "Subnet mask of network element."
    ::= { slbNewNwclssCfgNetworkElementsEntry 5 }

slbNewNwclssCfgNetworkElementsFromIp OBJECT-TYPE
    SYNTAX  IpAddress
    MAX-ACCESS  read-create
    STATUS  current
    DESCRIPTION
        "From IP address of network element."
    ::= { slbNewNwclssCfgNetworkElementsEntry 6 }

slbNewNwclssCfgNetworkElementsToIp OBJECT-TYPE
    SYNTAX  IpAddress
    MAX-ACCESS  read-create
    STATUS  current
    DESCRIPTION
        "To IP address of network element."
    ::= { slbNewNwclssCfgNetworkElementsEntry 7 }

slbNewNwclssCfgNetworkElementsIpv6Addr OBJECT-TYPE
    SYNTAX   DisplayString (SIZE(0..40))
    MAX-ACCESS  read-create
    STATUS  current
    DESCRIPTION
        "The IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 8 }

slbNewNwclssCfgNetworkElementsPrefixLen OBJECT-TYPE
    SYNTAX  INTEGER(1..128) 
    MAX-ACCESS  read-create
    STATUS  current
    DESCRIPTION
        "The prefix length associated with the network IP address ."
    ::= { slbNewNwclssCfgNetworkElementsEntry 9 }

slbNewNwclssCfgNetworkElementsFromIpv6Addr OBJECT-TYPE
    SYNTAX   DisplayString (SIZE(0..40))
    MAX-ACCESS  read-create
    STATUS  current
    DESCRIPTION
        "The from IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 10 }

slbNewNwclssCfgNetworkElementsToIpv6Addr OBJECT-TYPE
    SYNTAX   DisplayString (SIZE(0..40))
    MAX-ACCESS  read-create
    STATUS  current
    DESCRIPTION
        "The to IPv6 address of network element.
	 Address should be 4-byte hexadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 11 }

slbNewNwclssCfgNetworkElementsMatchType OBJECT-TYPE
    SYNTAX  INTEGER{
        include(1),
        exclude(2),
        unsupported(2147483647)
        }
    MAX-ACCESS  read-create
    STATUS  current
    DESCRIPTION
        "The match type of network element."
   ::= { slbNewNwclssCfgNetworkElementsEntry 12 }

slbNewNwclssCfgNetworkElementsDel OBJECT-TYPE
    SYNTAX  INTEGER {
        other(1),
        delete(2),
        unsupported(2147483647)
        }
    MAX-ACCESS  read-create
    STATUS  current
    DESCRIPTION
        "By setting the value to delete(2), the entire row is deleted."
    ::= { slbNewNwclssCfgNetworkElementsEntry 13 }

slbNewNwclssCfgNetworkElementsRegCont OBJECT-TYPE
    SYNTAX   DisplayString (SIZE (0..64))
    MAX-ACCESS  read-create
    STATUS  current
    DESCRIPTION
        "Continent name of the region for network elements."
    ::= { slbNewNwclssCfgNetworkElementsEntry 14 }

slbNewNwclssCfgNetworkElementsRegCountry OBJECT-TYPE
    SYNTAX   DisplayString (SIZE (0..64))
    MAX-ACCESS  read-create
    STATUS  current
    DESCRIPTION
        "Country/Geolocation name of the region for network elements."
    ::= { slbNewNwclssCfgNetworkElementsEntry 15 }

slbNewNwclssCfgNetworkElementsRegState OBJECT-TYPE
    SYNTAX   DisplayString (SIZE (0..64))
    MAX-ACCESS  read-create
    STATUS  current
    DESCRIPTION
        "State name of the region for network elements."
    ::= { slbNewNwclssCfgNetworkElementsEntry 16 }

slbNewNwclssCfgNetworkTypeAddrOrRegn OBJECT-TYPE
    SYNTAX  INTEGER {
        address(1),
        region(2),
        unsupported(2147483647)
        }
    MAX-ACCESS  read-only
    STATUS  current
    DESCRIPTION
        "The network class type should be either 'address' or 'region' from network class."
    ::= { slbNewNwclssCfgNetworkElementsEntry 17 }

	-- NWCLSS END


-- Data Classes Start

slbCurDataclassCfgDataClassesTable OBJECT-TYPE
    SYNTAX  SEQUENCE OF SlbCurDataclassCfgDataClassesEntry
    MAX-ACCESS  not-accessible
    STATUS  current
    DESCRIPTION
        "Current data classes table.
         Note:This mib is not supported for VX instance of Virtualization."
    ::= { dataclassCfg 1 }

slbCurDataclassCfgDataClassesEntry OBJECT-TYPE
    SYNTAX  SlbCurDataclassCfgDataClassesEntry
    MAX-ACCESS  not-accessible
    STATUS  current
    DESCRIPTION
        "A row in the current data classes table."
    INDEX   { slbCurDataclassCfgDataClassesId  }
    ::= { slbCurDataclassCfgDataClassesTable 1 }

SlbCurDataclassCfgDataClassesEntry ::= SEQUENCE {
    slbCurDataclassCfgDataClassesId          DisplayString,
    slbCurDataclassCfgDataClassesDataType    INTEGER,


    slbCurDataclassCfgDataClassesName        DisplayString
    }

slbCurDataclassCfgDataClassesId OBJECT-TYPE
    SYNTAX   DisplayString (SIZE (1..32))
    MAX-ACCESS  read-only
    STATUS  current
    DESCRIPTION
        "Data class id."
    ::= { slbCurDataclassCfgDataClassesEntry 1 }
    
slbCurDataclassCfgDataClassesDataType OBJECT-TYPE
    SYNTAX  INTEGER{
        string(1),
        ip(2),
        unsupported(2147483647)
        }
    MAX-ACCESS  read-only
    STATUS  current
    DESCRIPTION
        "Data class data type."
   ::= { slbCurDataclassCfgDataClassesEntry 2 }

   

slbCurDataclassCfgDataClassesName OBJECT-TYPE
    SYNTAX   DisplayString (SIZE (0..32))
    MAX-ACCESS  read-only
    STATUS  current
    DESCRIPTION
        "Data class name."
    ::= { slbCurDataclassCfgDataClassesEntry 5 }


slbCurDataclassCfgManualEntriesTable OBJECT-TYPE
    SYNTAX  SEQUENCE OF SlbCurDataclassCfgManualEntriesEntry
    MAX-ACCESS  not-accessible
    STATUS  current
    DESCRIPTION
        "Current data class manual entries table.
         Note:This mib is not supported for VX instance of Virtualization."
    ::= { dataclassCfg 2 }

slbCurDataclassCfgManualEntriesEntry OBJECT-TYPE
    SYNTAX  SlbCurDataclassCfgManualEntriesEntry
    MAX-ACCESS  not-accessible
    STATUS  current
    DESCRIPTION
        "A row in the new data class manual entries table."
    INDEX   {slbCurDataclassCfgManualEntriesEntryDcId, slbCurDataclassCfgManualEntriesEntryId}
    ::= { slbCurDataclassCfgManualEntriesTable 1 }

SlbCurDataclassCfgManualEntriesEntry ::= SEQUENCE {
	slbCurDataclassCfgManualEntriesEntryDcId    DisplayString,
	slbCurDataclassCfgManualEntriesEntryId      INTEGER,
    slbCurDataclassCfgManualEntriesEntryKey     RadwareLongDisplayString,
    slbCurDataclassCfgManualEntriesEntryValue	RadwareLongDisplayString
    }
 
slbCurDataclassCfgManualEntriesEntryDcId OBJECT-TYPE
    SYNTAX   DisplayString (SIZE (1..32))
    MAX-ACCESS  read-only
    STATUS  current
    DESCRIPTION
        "Data class ID which the manual entry belongs to."
    ::= { slbCurDataclassCfgManualEntriesEntry 1 }
  
slbCurDataclassCfgManualEntriesEntryId OBJECT-TYPE
    SYNTAX  INTEGER
    MAX-ACCESS  read-only
    STATUS  current
    DESCRIPTION
        "Manual entry Id."
   ::= { slbCurDataclassCfgManualEntriesEntry 2 }
   
 
slbCurDataclassCfgManualEntriesEntryKey OBJECT-TYPE
    SYNTAX   RadwareLongDisplayString (SIZE (1..255))
    MAX-ACCESS  read-only
    STATUS  current
    DESCRIPTION
        "Manual entry key. When configuration type is string there are no limitations.
        When configuration type is ip should be a discrete IPv4/v6 address or subnet."
    ::= { slbCurDataclassCfgManualEntriesEntry 3 }

slbCurDataclassCfgManualEntriesEntryValue OBJECT-TYPE
    SYNTAX   RadwareLongDisplayString (SIZE (0..512))
    MAX-ACCESS  read-only
    STATUS  current
    DESCRIPTION
        "Manual entry value."
    ::= { slbCurDataclassCfgManualEntriesEntry 4 }


slbNewDataclassCfgDataClassesTable OBJECT-TYPE
    SYNTAX  SEQUENCE OF SlbNewDataclassCfgDataClassesEntry
    MAX-ACCESS  not-accessible
    STATUS  current
    DESCRIPTION
        "New data classes table.
         Note:This mib is not supported for VX instance of Virtualization."
    ::= { dataclassCfg 3 }

slbNewDataclassCfgDataClassesEntry OBJECT-TYPE
    SYNTAX  SlbNewDataclassCfgDataClassesEntry
    MAX-ACCESS  not-accessible
    STATUS  current
    DESCRIPTION
        "A row in the current data classes table."
    INDEX   {slbNewDataclassCfgDataClassesId}
    ::= { slbNewDataclassCfgDataClassesTable 1 }

SlbNewDataclassCfgDataClassesEntry ::= SEQUENCE {
    slbNewDataclassCfgDataClassesId       			 DisplayString,
    slbNewDataclassCfgDataClassesDataType   		 INTEGER,


    slbNewDataclassCfgDataClassesName     			 DisplayString,
    slbNewDataclassCfgDataClassesDel			  	 INTEGER,
    slbNewDataclassCfgDataClassesCopy     			 DisplayString
    }

slbNewDataclassCfgDataClassesId OBJECT-TYPE
    SYNTAX   DisplayString (SIZE (1..32))
    MAX-ACCESS  read-only
    STATUS  current
    DESCRIPTION
        "Data class id."
    ::= { slbNewDataclassCfgDataClassesEntry 1 }

slbNewDataclassCfgDataClassesDataType OBJECT-TYPE
    SYNTAX  INTEGER {
        string(1),
        ip(2),
        unsupported(2147483647)
        }
    MAX-ACCESS  read-create
    STATUS  current
    DESCRIPTION
        "Data class data type."
    ::= { slbNewDataclassCfgDataClassesEntry 2 }

   

slbNewDataclassCfgDataClassesName OBJECT-TYPE
    SYNTAX   DisplayString (SIZE (0..32))
    MAX-ACCESS  read-write
    STATUS  current
    DESCRIPTION
        "Data class name."
    ::= { slbNewDataclassCfgDataClassesEntry 5 }

slbNewDataclassCfgDataClassesDel OBJECT-TYPE
    SYNTAX  INTEGER {
        other(1),
        delete(2),
        unsupported(2147483647)
        }
    MAX-ACCESS  read-write
    STATUS  current
    DESCRIPTION
        "By setting the value to delete(2), the entire row is deleted."
    ::= { slbNewDataclassCfgDataClassesEntry 6 }

slbNewDataclassCfgDataClassesCopy OBJECT-TYPE
    SYNTAX   DisplayString (SIZE (1..32))
    MAX-ACCESS  read-write
    STATUS  current
    DESCRIPTION
        "Duplicating an entire Data class by defining the destination Data class id."
    ::= { slbNewDataclassCfgDataClassesEntry 7 }
    
    
slbNewDataclassCfgManualEntriesTable OBJECT-TYPE
    SYNTAX  SEQUENCE OF SlbNewDataclassCfgManualEntriesEntry
    MAX-ACCESS  not-accessible
    STATUS  current
    DESCRIPTION
        "New data class manual entries table.
         Note:This mib is not supported for VX instance of Virtualization."
    ::= { dataclassCfg 4 }


slbNewDataclassCfgManualEntriesEntry OBJECT-TYPE
    SYNTAX  SlbNewDataclassCfgManualEntriesEntry
    MAX-ACCESS  not-accessible
    STATUS  current
    DESCRIPTION
        "A row in the new data class manual entries table."
    INDEX   {slbNewDataclassCfgManualEntriesEntryDcId, slbNewDataclassCfgManualEntriesEntryId}
    ::= { slbNewDataclassCfgManualEntriesTable 1 }

SlbNewDataclassCfgManualEntriesEntry ::= SEQUENCE {
	slbNewDataclassCfgManualEntriesEntryDcId	DisplayString,
	slbNewDataclassCfgManualEntriesEntryId      INTEGER,
    slbNewDataclassCfgManualEntriesEntryKey     RadwareLongDisplayString,
    slbNewDataclassCfgManualEntriesEntryValue	RadwareLongDisplayString,
    slbNewDataclassCfgManualEntriesEntryDel		INTEGER
    }
    
 
slbNewDataclassCfgManualEntriesEntryDcId OBJECT-TYPE
    SYNTAX   DisplayString (SIZE (1..32))
    MAX-ACCESS  read-only
    STATUS  current
    DESCRIPTION
        "Data class ID which the manual entry belongs to."
    ::= { slbNewDataclassCfgManualEntriesEntry 1 }
  
slbNewDataclassCfgManualEntriesEntryId OBJECT-TYPE
    SYNTAX  INTEGER
    MAX-ACCESS  read-only
    STATUS  current
    DESCRIPTION
        "Manual entry Id."
   ::= { slbNewDataclassCfgManualEntriesEntry 2 }
    
 
slbNewDataclassCfgManualEntriesEntryKey OBJECT-TYPE
    SYNTAX   RadwareLongDisplayString (SIZE (1..255))
    MAX-ACCESS  read-create
    STATUS  current
    DESCRIPTION
        "Manual entry key. When configuration type is string there are no limitations.
        When configuration type is ip should be a discrete IPv4/v6 address or subnet."
    ::= { slbNewDataclassCfgManualEntriesEntry 3 }

slbNewDataclassCfgManualEntriesEntryValue OBJECT-TYPE
    SYNTAX   RadwareLongDisplayString (SIZE (0..512))
    MAX-ACCESS  read-write
    STATUS  current
    DESCRIPTION
        "Manual entry value."
    ::= { slbNewDataclassCfgManualEntriesEntry 4 }
    
slbNewDataclassCfgManualEntriesEntryDel OBJECT-TYPE
    SYNTAX  INTEGER {
        other(1),
        delete(2),
        unsupported(2147483647)
        }
    MAX-ACCESS  read-write
    STATUS  current
    DESCRIPTION
        "By setting the value to delete(2), the entire row is deleted."
    ::= { slbNewDataclassCfgManualEntriesEntry 5 }

slbDataclassCfgDataClassesManualEntryCreationId OBJECT-TYPE
    SYNTAX  INTEGER 
    MAX-ACCESS  read-only
    STATUS  current
    DESCRIPTION
        "This Data Class manual entry ID should be used in a SET command with a Data Class ID,
         to create new entries within that Data Class.
         Note:This mib is not supported for VX instance of Virtualization."
    ::= { dataclassCfg 5 }


-- Data Classes End


fastviewStatSummTransactions OBJECT-TYPE
   SYNTAX  Integer32
   MAX-ACCESS  read-only
   STATUS  current 
   DESCRIPTION
       "Number of fastview transactions within the measuring period.
        Note:This mib is not supported for VX instance of Virtualization."
   ::= {fastviewStats 1}

fastviewStatSummPages OBJECT-TYPE
   SYNTAX  Integer32
   MAX-ACCESS  read-only
   STATUS  current 
   DESCRIPTION
       "Number of fastview pages within the measuring period.
        Note:This mib is not supported for VX instance of Virtualization."
   ::= {fastviewStats 2}

fastviewStatSummOptimizedPages OBJECT-TYPE
   SYNTAX  Integer32
   MAX-ACCESS  read-only
   STATUS  current 
   DESCRIPTION
       "Number of fastview optimized pages within the measuring period.
        Note:This mib is not supported for VX instance of Virtualization."
   ::= {fastviewStats 3}

fastviewStatSummLearningPages OBJECT-TYPE
   SYNTAX  Integer32
   MAX-ACCESS  read-only
   STATUS  current 
   DESCRIPTION
       "Number of fastview learning pages within the measuring period.
        Note:This mib is not supported for VX instance of Virtualization."
   ::= {fastviewStats 4}

fastviewStatSummTokensParsed OBJECT-TYPE
   SYNTAX  Integer32
   MAX-ACCESS  read-only
   STATUS  current 
   DESCRIPTION
       "Number of fastview parsed tokens within the measuring period.
        Note:This mib is not supported for VX instance of Virtualization."
   ::= {fastviewStats 5}

fastviewStatSummTokensRewritten OBJECT-TYPE
   SYNTAX  Integer32
   MAX-ACCESS  read-only
   STATUS  current 
   DESCRIPTION
       "Number of fastview rewritten tokens within the measuring period.
        Note:This mib is not supported for VX instance of Virtualization."
   ::= {fastviewStats 6}

fastviewStatSummBytesSavedImgReduction OBJECT-TYPE
   SYNTAX  Integer32
   MAX-ACCESS  read-only
   STATUS  current 
   DESCRIPTION
       "Number of fastview saved bytes with image reduction within the measuring period.
        Note:This mib is not supported for VX instance of Virtualization."
   ::= {fastviewStats 7}

fastviewStatSummBytesBeforeImgReduction OBJECT-TYPE
   SYNTAX  Integer32
   MAX-ACCESS  read-only
   STATUS  current 
   DESCRIPTION
       "Number of fastview bytes before image compression within the measuring period.
        Note:This mib is not supported for VX instance of Virtualization."
   ::= {fastviewStats 8}

fastviewStatSummBytesSavedPercent OBJECT-TYPE
   SYNTAX  Integer32
   MAX-ACCESS  read-only
   STATUS  current 
   DESCRIPTION
       "% of fastview saved bytes with image reduction within the measuring period.
        Note:This mib is not supported for VX instance of Virtualization."
   ::= {fastviewStats 9}

fastviewStatSummRespWithExpiryModified OBJECT-TYPE
   SYNTAX  Integer32
   MAX-ACCESS  read-only
   STATUS  current 
   DESCRIPTION
       "Number of fastview responses with expiry modified within the measuring period.
        Note:This mib is not supported for VX instance of Virtualization."
   ::= {fastviewStats 10}

fastviewStatSummExpiryModifiedPercent OBJECT-TYPE
   SYNTAX  Integer32
   MAX-ACCESS  read-only
   STATUS  current 
   DESCRIPTION
       "% of fastview responses with expiry modified within the measuring period.
        Note:This mib is not supported for VX instance of Virtualization."
   ::= {fastviewStats 11}
   
fastviewStatSummPeakTransactions OBJECT-TYPE
   SYNTAX  Integer32
   MAX-ACCESS  read-only
   STATUS  current 
   DESCRIPTION
       "Peak Number of fastview transactions within the measuring period.
        Note:This mib is not supported for VX instance of Virtualization."
   ::= {fastviewStats 12}

fastviewStatSummPeakPages OBJECT-TYPE
   SYNTAX  Integer32
   MAX-ACCESS  read-only
   STATUS  current 
   DESCRIPTION
       "Peak Number of fastview pages within the measuring period.
        Note:This mib is not supported for VX instance of Virtualization."
   ::= {fastviewStats 13}

fastviewStatSummPeakOptimizedPages OBJECT-TYPE
   SYNTAX  Integer32
   MAX-ACCESS  read-only
   STATUS  current 
   DESCRIPTION
       "Peak Number of fastview optimized pages within the measuring period.
        Note:This mib is not supported for VX instance of Virtualization."
   ::= {fastviewStats 14}

fastviewStatSummPeakLearningPages OBJECT-TYPE
   SYNTAX  Integer32
   MAX-ACCESS  read-only
   STATUS  current 
   DESCRIPTION
       "Peak Number of fastview learning pages within the measuring period.
        Note:This mib is not supported for VX instance of Virtualization."
   ::= {fastviewStats 15}

fastviewStatSummPeakTokensParsed OBJECT-TYPE
   SYNTAX  Integer32
   MAX-ACCESS  read-only
   STATUS  current 
   DESCRIPTION
       "Peak Number of fastview parsed tokens within the measuring period.
        Note:This mib is not supported for VX instance of Virtualization."
   ::= {fastviewStats 16}

fastviewStatSummPeakTokensRewritten OBJECT-TYPE
   SYNTAX  Integer32
   MAX-ACCESS  read-only
   STATUS  current 
   DESCRIPTION
       "Peak Number of fastview rewritten tokens within the measuring period.
        Note:This mib is not supported for VX instance of Virtualization."
   ::= {fastviewStats 17}
   
fastviewStatSummTotTransactions OBJECT-TYPE
   SYNTAX  Integer32
   MAX-ACCESS  read-only
   STATUS  current 
   DESCRIPTION
       "Total Number of fastview transactions within the measuring period.
        Note:This mib is not supported for VX instance of Virtualization."
   ::= {fastviewStats 18}

fastviewStatSummTotPages OBJECT-TYPE
   SYNTAX  Integer32
   MAX-ACCESS  read-only
   STATUS  current 
   DESCRIPTION
       "Total Number of fastview pages within the measuring period.
        Note:This mib is not supported for VX instance of Virtualization."
   ::= {fastviewStats 19}

fastviewStatSummTotOptimizedPages OBJECT-TYPE
   SYNTAX  Integer32
   MAX-ACCESS  read-only
   STATUS  current 
   DESCRIPTION
       "Total Number of fastview optimized pages within the measuring period.
        Note:This mib is not supported for VX instance of Virtualization."
   ::= {fastviewStats 20}

fastviewStatSummTotLearningPages OBJECT-TYPE
   SYNTAX  Integer32
   MAX-ACCESS  read-only
   STATUS  current 
   DESCRIPTION
       "Total Number of fastview learning pages within the measuring period.
        Note:This mib is not supported for VX instance of Virtualization."
   ::= {fastviewStats 21}

fastviewStatSummTotTokensParsed OBJECT-TYPE
   SYNTAX  Integer32
   MAX-ACCESS  read-only
   STATUS  current 
   DESCRIPTION
       "Total Number of fastview parsed tokens within the measuring period.
        Note:This mib is not supported for VX instance of Virtualization."
   ::= {fastviewStats 22}

fastviewStatSummTotTokensRewritten OBJECT-TYPE
   SYNTAX  Integer32
   MAX-ACCESS  read-only
   STATUS  current 
   DESCRIPTION
       "Total Number of fastview rewritten tokens within the measuring period.
        Note:This mib is not supported for VX instance of Virtualization."
   ::= {fastviewStats 23}

fastviewStatSummTotBytesSavedImgReduction OBJECT-TYPE
   SYNTAX  Integer32
   MAX-ACCESS  read-only
   STATUS  current 
   DESCRIPTION
       "Total Number of fastview saved bytes with image reduction within the measuring period.
        Note:This mib is not supported for VX instance of Virtualization."
   ::= {fastviewStats 24}

fastviewStatSummTotBytesBeforeImgReduction OBJECT-TYPE
   SYNTAX  Integer32
   MAX-ACCESS  read-only
   STATUS  current 
   DESCRIPTION
       "Total Number of fastview bytes before image reduction within the measuring period.
        Note:This mib is not supported for VX instance of Virtualization."
   ::= {fastviewStats 25}

fastviewStatSummTotBytesSavedPercent OBJECT-TYPE
   SYNTAX  Integer32
   MAX-ACCESS  read-only
   STATUS  current 
   DESCRIPTION
       "% of fastview saved bytes with image reduction within the measuring period.
        Note:This mib is not supported for VX instance of Virtualization."
   ::= {fastviewStats 26}
   
fastviewStatSummTotRespWithExpiryModified OBJECT-TYPE
   SYNTAX  Integer32
   MAX-ACCESS  read-only
   STATUS  current 
   DESCRIPTION
       "Total Number of fastview responses with expiry modified within the measuring period.
        Note:This mib is not supported for VX instance of Virtualization."
   ::= {fastviewStats 27}

fastviewStatSummTotExpiryModifiedPercent OBJECT-TYPE
   SYNTAX  Integer32
   MAX-ACCESS  read-only
   STATUS  current 
   DESCRIPTION
       "% of fastview responses with expiry modified within the measuring period.
        Note:This mib is not supported for VX instance of Virtualization."
   ::= {fastviewStats 28}
   
fastviewEnhPerServStatsTable OBJECT-TYPE
    SYNTAX SEQUENCE OF FastviewEnhPerServStatsEntry
    MAX-ACCESS not-accessible
    STATUS current
    DESCRIPTION
        "A table for Fastview statistics per virtual service.
         Note:This mib is not supported for VX instance of Virtualization."
   ::= {fastviewStats 29}

fastviewEnhPerServStatsEntry OBJECT-TYPE
    SYNTAX FastviewEnhPerServStatsEntry
    MAX-ACCESS not-accessible
    STATUS  current
    DESCRIPTION
        " The row definition for Fastview statistics per virtual service table."
    INDEX  { fastviewEnhPerServStatsVirtServIndex, fastviewEnhPerServStatsVirtServiceIndex}
    ::= {fastviewEnhPerServStatsTable 1}

FastviewEnhPerServStatsEntry  ::= SEQUENCE {
	fastviewEnhPerServStatsVirtServIndex       DisplayString,
	fastviewEnhPerServStatsVirtServiceIndex    Integer32,
	fastviewEnhPerServStatsVirtServPort        Integer32,
	fastviewEnhPerServStatsWebappId                       DisplayString,
        fastviewEnhPerServStatsTransactions                           Integer32,
        fastviewEnhPerServStatsPages                          Integer32,
        fastviewEnhPerServStatsOptimizedPages                         Integer32,
        fastviewEnhPerServStatsLearningPages                         Integer32,
        fastviewEnhPerServStatsTokensParsed                     Integer32,
        fastviewEnhPerServStatsTokensRewritten                     Integer32,
        fastviewEnhPerServStatsBytesSavedImgReduction                 Integer32,
        fastviewEnhPerServStatsBytesBeforeImgReduction                 Integer32,
        fastviewEnhPerServStatsBytesSavedPercent                 Integer32,
	fastviewEnhPerServStatsRespWithExpiryModified                 Integer32,
	fastviewEnhPerServStatsExpiryModifiedPercent                 Integer32,
        fastviewEnhPerServStatsPeakTransactions                           Integer32,
        fastviewEnhPerServStatsPeakPages                          Integer32,
        fastviewEnhPerServStatsPeakOptimizedPages                         Integer32,
        fastviewEnhPerServStatsPeakLearningPages                         Integer32,
        fastviewEnhPerServStatsPeakTokensParsed                     Integer32,
        fastviewEnhPerServStatsPeakTokensRewritten                     Integer32,
        fastviewEnhPerServStatsTotTransactions                           Integer32,
        fastviewEnhPerServStatsTotPages                          Integer32,
        fastviewEnhPerServStatsTotOptimizedPages                         Integer32,
        fastviewEnhPerServStatsTotLearningPages                         Integer32,
        fastviewEnhPerServStatsTotTokensParsed                     Integer32,
        fastviewEnhPerServStatsTotTokensRewritten                     Integer32,
        fastviewEnhPerServStatsTotBytesSavedImgReduction                 Integer32,
        fastviewEnhPerServStatsTotBytesBeforeImgReduction                 Integer32,
        fastviewEnhPerServStatsTotBytesSavedPercent                 Integer32,
	fastviewEnhPerServStatsTotRespWithExpiryModified                 Integer32,
	fastviewEnhPerServStatsTotExpiryModifiedPercent                 Integer32
}

fastviewEnhPerServStatsVirtServIndex  OBJECT-TYPE
    SYNTAX  DisplayString  ( SIZE ( 1 .. 255  ) )
    MAX-ACCESS  read-only
    STATUS  current
    DESCRIPTION
        "Virtual server Index."
    ::= {fastviewEnhPerServStatsEntry 1}

fastviewEnhPerServStatsVirtServiceIndex  OBJECT-TYPE
    SYNTAX  Integer32
    MAX-ACCESS  read-only
    STATUS  current
    DESCRIPTION
        "Virtual server service index."
    ::= {fastviewEnhPerServStatsEntry 2}

fastviewEnhPerServStatsVirtServPort  OBJECT-TYPE
    SYNTAX  Integer32
    MAX-ACCESS  read-only
    STATUS  current
    DESCRIPTION
        "Virtual server service port number."
    ::= {fastviewEnhPerServStatsEntry 3}

fastviewEnhPerServStatsWebappId  OBJECT-TYPE
   SYNTAX  DisplayString 
   MAX-ACCESS  read-only
   STATUS  current
   DESCRIPTION
       "Fastview webapp identifier associated with the virtual service."
   ::= {fastviewEnhPerServStatsEntry 4}

fastviewEnhPerServStatsTransactions  OBJECT-TYPE
   SYNTAX  Integer32
   MAX-ACCESS  read-only
   STATUS  current
   DESCRIPTION
       "Number of fastview transactions during the measuring period for virtual service."
   ::= {fastviewEnhPerServStatsEntry 5}

fastviewEnhPerServStatsPages  OBJECT-TYPE
   SYNTAX  Integer32
   MAX-ACCESS  read-only
   STATUS  current
   DESCRIPTION
       "Number of pages served by fastview during the measuring period for virtual service."
   ::= {fastviewEnhPerServStatsEntry 6}

fastviewEnhPerServStatsOptimizedPages  OBJECT-TYPE
   SYNTAX  Integer32
   MAX-ACCESS  read-only
   STATUS  current
   DESCRIPTION
       "Number of optimized pages served by fastview during the measuring period for virtual service."
   ::= {fastviewEnhPerServStatsEntry 7}

fastviewEnhPerServStatsLearningPages  OBJECT-TYPE
   SYNTAX  Integer32
   MAX-ACCESS  read-only
   STATUS  current
   DESCRIPTION
       "Number of learning pages served by fastview during the measuring period for virtual service."
   ::= {fastviewEnhPerServStatsEntry 8}

fastviewEnhPerServStatsTokensParsed  OBJECT-TYPE
   SYNTAX  Integer32
   MAX-ACCESS  read-only
   STATUS  current
   DESCRIPTION
       "Number of fastview parsed tokens during the measuring period for virtual service."
   ::= {fastviewEnhPerServStatsEntry 9}

fastviewEnhPerServStatsTokensRewritten  OBJECT-TYPE
   SYNTAX  Integer32
   MAX-ACCESS  read-only
   STATUS  current
   DESCRIPTION
       "Number of fastview rewritten tokens during the measuring period for virtual service."
   ::= {fastviewEnhPerServStatsEntry 10}

fastviewEnhPerServStatsBytesSavedImgReduction  OBJECT-TYPE
   SYNTAX  Integer32
   MAX-ACCESS  read-only
   STATUS  current
   DESCRIPTION
       "Number of fastview bytes saved with image reduction during the measuring period for virtual service."
   ::= {fastviewEnhPerServStatsEntry 11}

fastviewEnhPerServStatsBytesBeforeImgReduction  OBJECT-TYPE
   SYNTAX  Integer32
   MAX-ACCESS  read-only
   STATUS  current
   DESCRIPTION
       "Number of fastview bytes before image reduction during the measuring period for virtual service."
   ::= {fastviewEnhPerServStatsEntry 12}

fastviewEnhPerServStatsBytesSavedPercent  OBJECT-TYPE
   SYNTAX  Integer32
   MAX-ACCESS  read-only
   STATUS  current
   DESCRIPTION
       "% of fastview bytes saved with image reduction during the measuring period for virtual service."
   ::= {fastviewEnhPerServStatsEntry 13}
   
fastviewEnhPerServStatsRespWithExpiryModified  OBJECT-TYPE
   SYNTAX  Integer32
   MAX-ACCESS  read-only
   STATUS  current
   DESCRIPTION
       "Number of responses with expiry modified by fastview during the measuring period for virtual service."
   ::= {fastviewEnhPerServStatsEntry 14}

fastviewEnhPerServStatsExpiryModifiedPercent  OBJECT-TYPE
   SYNTAX  Integer32
   MAX-ACCESS  read-only
   STATUS  current
   DESCRIPTION
       "% of responses with expiry modified by fastview during the measuring period for virtual service."
   ::= {fastviewEnhPerServStatsEntry 15}

fastviewEnhPerServStatsPeakTransactions  OBJECT-TYPE
   SYNTAX  Integer32
   MAX-ACCESS  read-only
   STATUS  current
   DESCRIPTION
       "Peak Number of fastview transactions during the measuring period for virtual service."
   ::= {fastviewEnhPerServStatsEntry 16}

fastviewEnhPerServStatsPeakPages  OBJECT-TYPE
   SYNTAX  Integer32
   MAX-ACCESS  read-only
   STATUS  current
   DESCRIPTION
       "Peak Number of pages served by fastview during the measuring period for virtual service."
   ::= {fastviewEnhPerServStatsEntry 17}

fastviewEnhPerServStatsPeakOptimizedPages  OBJECT-TYPE
   SYNTAX  Integer32
   MAX-ACCESS  read-only
   STATUS  current
   DESCRIPTION
       "Peak Number of optimized pages served by fastview during the measuring period for virtual service."
   ::= {fastviewEnhPerServStatsEntry 18}

fastviewEnhPerServStatsPeakLearningPages  OBJECT-TYPE
   SYNTAX  Integer32
   MAX-ACCESS  read-only
   STATUS  current
   DESCRIPTION
       "Peak Number of learning pages served by fastview during the measuring period for virtual service."
   ::= {fastviewEnhPerServStatsEntry 19}

fastviewEnhPerServStatsPeakTokensParsed  OBJECT-TYPE
   SYNTAX  Integer32
   MAX-ACCESS  read-only
   STATUS  current
   DESCRIPTION
       "Peak Number of fastview parsed tokens during the measuring period for virtual service."
   ::= {fastviewEnhPerServStatsEntry 20}

fastviewEnhPerServStatsPeakTokensRewritten  OBJECT-TYPE
   SYNTAX  Integer32
   MAX-ACCESS  read-only
   STATUS  current
   DESCRIPTION
       "Peak Number of fastview rewritten tokens during the measuring period for virtual service."
   ::= {fastviewEnhPerServStatsEntry 21}
   
fastviewEnhPerServStatsTotTransactions  OBJECT-TYPE
   SYNTAX  Integer32
   MAX-ACCESS  read-only
   STATUS  current
   DESCRIPTION
       "Total Number of fastview transactions during the measuring period for virtual service."
   ::= {fastviewEnhPerServStatsEntry 22}

fastviewEnhPerServStatsTotPages  OBJECT-TYPE
   SYNTAX  Integer32
   MAX-ACCESS  read-only
   STATUS  current
   DESCRIPTION
       "Total Number of pages served by fastview during the measuring period for virtual service."
   ::= {fastviewEnhPerServStatsEntry 23}

fastviewEnhPerServStatsTotOptimizedPages  OBJECT-TYPE
   SYNTAX  Integer32
   MAX-ACCESS  read-only
   STATUS  current
   DESCRIPTION
       "Total Number of optimized pages served by fastview during the measuring period for virtual service."
   ::= {fastviewEnhPerServStatsEntry 24}

fastviewEnhPerServStatsTotLearningPages  OBJECT-TYPE
   SYNTAX  Integer32
   MAX-ACCESS  read-only
   STATUS  current
   DESCRIPTION
       "Total Number of learning pages served by fastview during the measuring period for virtual service."
   ::= {fastviewEnhPerServStatsEntry 25}

fastviewEnhPerServStatsTotTokensParsed  OBJECT-TYPE
   SYNTAX  Integer32
   MAX-ACCESS  read-only
   STATUS  current
   DESCRIPTION
       "Total Number of fastview parsed tokens during the measuring period for virtual service."
   ::= {fastviewEnhPerServStatsEntry 26}

fastviewEnhPerServStatsTotTokensRewritten  OBJECT-TYPE
   SYNTAX  Integer32
   MAX-ACCESS  read-only
   STATUS  current
   DESCRIPTION
       "Total Number of fastview rewritten tokens during the measuring period for virtual service."
   ::= {fastviewEnhPerServStatsEntry 27}

fastviewEnhPerServStatsTotBytesSavedImgReduction  OBJECT-TYPE
   SYNTAX  Integer32
   MAX-ACCESS  read-only
   STATUS  current
   DESCRIPTION
       "Total Number of fastview bytes saved with image reduction during the measuring period for virtual service."
   ::= {fastviewEnhPerServStatsEntry 28}

fastviewEnhPerServStatsTotBytesBeforeImgReduction  OBJECT-TYPE
   SYNTAX  Integer32
   MAX-ACCESS  read-only
   STATUS  current
   DESCRIPTION
       "Total Number of fastview bytes before image reduction during the measuring period for virtual service."
   ::= {fastviewEnhPerServStatsEntry 29}

fastviewEnhPerServStatsTotBytesSavedPercent  OBJECT-TYPE
   SYNTAX  Integer32
   MAX-ACCESS  read-only
   STATUS  current
   DESCRIPTION
       "% of fastview bytes saved with image reduction during the measuring period for virtual service."
   ::= {fastviewEnhPerServStatsEntry 30}

fastviewEnhPerServStatsTotRespWithExpiryModified  OBJECT-TYPE
   SYNTAX  Integer32
   MAX-ACCESS  read-only
   STATUS  current
   DESCRIPTION
       "Total Number of responses with expiry modified by fastview during the measuring period for virtual service."
   ::= {fastviewEnhPerServStatsEntry 31}

fastviewEnhPerServStatsTotExpiryModifiedPercent  OBJECT-TYPE
   SYNTAX  Integer32
   MAX-ACCESS  read-only
   STATUS  current
   DESCRIPTION
       "% of responses with expiry modified by fastview during the measuring period for virtual service."
   ::= {fastviewEnhPerServStatsEntry 32}

fastviewPerContRuleStatsTable OBJECT-TYPE
    SYNTAX SEQUENCE OF FastviewEnhPerContRuleStatsEntry
    MAX-ACCESS not-accessible
    STATUS current
    DESCRIPTION
        "A table for Fastview statistics per content class.
         Note:This mib is not supported for VX instance of Virtualization."
   ::= {fastviewStats 30}

fastviewEnhPerContRuleStatsEntry OBJECT-TYPE
    SYNTAX FastviewEnhPerContRuleStatsEntry
    MAX-ACCESS not-accessible
    STATUS  current
    DESCRIPTION
        " The row definition for Fastview statistics per content class table."
    INDEX  { fastviewEnhPerContRuleStatsVirtServIndex, fastviewEnhPerContRuleStatsVirtServiceIndex, fastviewEnhPerContRuleStatsIndex }
    ::= {fastviewPerContRuleStatsTable 1}

FastviewEnhPerContRuleStatsEntry  ::= SEQUENCE {
	fastviewEnhPerContRuleStatsVirtServIndex       		DisplayString,
	fastviewEnhPerContRuleStatsVirtServiceIndex    		Integer32,
	fastviewEnhPerContRuleStatsIndex			Integer32,
	fastviewEnhPerContRuleStatsName				DisplayString,
	fastviewEnhPerContRuleStatsContClass			DisplayString,
	fastviewEnhPerContRuleStatsWebappId                     DisplayString,
        fastviewEnhPerContRuleStatsTransactions                 Integer32,
        fastviewEnhPerContRuleStatsPages                        Integer32,
        fastviewEnhPerContRuleStatsOptimizedPages               Integer32,
        fastviewEnhPerContRuleStatsLearningPages               Integer32,
        fastviewEnhPerContRuleStatsTokensParsed              Integer32,
        fastviewEnhPerContRuleStatsTokensRewritten              Integer32,
        fastviewEnhPerContRuleStatsBytesSavedImgReduction                 	Integer32,
        fastviewEnhPerContRuleStatsBytesBeforeImgReduction                 	Integer32,
        fastviewEnhPerContRuleStatsBytesSavedPercent                 	Integer32,
	fastviewEnhPerContRuleStatsRespWithExpiryModified  Integer32,
	fastviewEnhPerContRuleStatsExpiryModifiedPercent  Integer32,
        fastviewEnhPerContRuleStatsPeakTransactions                 Integer32,
        fastviewEnhPerContRuleStatsPeakPages                        Integer32,
        fastviewEnhPerContRuleStatsPeakOptimizedPages               Integer32,
        fastviewEnhPerContRuleStatsPeakLearningPages               Integer32,
        fastviewEnhPerContRuleStatsPeakTokensParsed              Integer32,
        fastviewEnhPerContRuleStatsPeakTokensRewritten              Integer32,
        fastviewEnhPerContRuleStatsTotTransactions                 Integer32,
        fastviewEnhPerContRuleStatsTotPages                        Integer32,
        fastviewEnhPerContRuleStatsTotOptimizedPages               Integer32,
        fastviewEnhPerContRuleStatsTotLearningPages               Integer32,
        fastviewEnhPerContRuleStatsTotTokensParsed              Integer32,
        fastviewEnhPerContRuleStatsTotTokensRewritten              Integer32,
        fastviewEnhPerContRuleStatsTotBytesSavedImgReduction                 	Integer32,
        fastviewEnhPerContRuleStatsTotBytesBeforeImgReduction                 	Integer32,
        fastviewEnhPerContRuleStatsTotBytesSavedPercent               	Integer32,
	fastviewEnhPerContRuleStatsTotRespWithExpiryModified  Integer32,
	fastviewEnhPerContRuleStatsTotExpiryModifiedPercent  Integer32
}

fastviewEnhPerContRuleStatsVirtServIndex  OBJECT-TYPE
    SYNTAX  DisplayString  ( SIZE ( 1 .. 255  ) )
    MAX-ACCESS  read-only
    STATUS  current
    DESCRIPTION
        "Virtual server Index."
    ::= {fastviewEnhPerContRuleStatsEntry 1}

fastviewEnhPerContRuleStatsVirtServiceIndex  OBJECT-TYPE
    SYNTAX  Integer32
    MAX-ACCESS  read-only
    STATUS  current
    DESCRIPTION
        "Virtual server service index."
    ::= {fastviewEnhPerContRuleStatsEntry 2}

fastviewEnhPerContRuleStatsIndex  OBJECT-TYPE
    SYNTAX  Integer32
    MAX-ACCESS  read-only
    STATUS  current
    DESCRIPTION
        "Content rule index."
    ::= {fastviewEnhPerContRuleStatsEntry 3}

fastviewEnhPerContRuleStatsName  OBJECT-TYPE
    SYNTAX  DisplayString  ( SIZE ( 1 .. 32  ) )
    MAX-ACCESS  read-only
    STATUS  current
    DESCRIPTION
        "Content rule name."
    ::= {fastviewEnhPerContRuleStatsEntry 4}

fastviewEnhPerContRuleStatsContClass  OBJECT-TYPE
   SYNTAX  DisplayString 
   MAX-ACCESS  read-only
   STATUS  current
   DESCRIPTION
       "Content class associated with the content rule."
   ::= {fastviewEnhPerContRuleStatsEntry 5}

fastviewEnhPerContRuleStatsWebappId  OBJECT-TYPE
   SYNTAX  DisplayString 
   MAX-ACCESS  read-only
   STATUS  current
   DESCRIPTION
       "Fastview webapp identifier associated with the content rule."
   ::= {fastviewEnhPerContRuleStatsEntry 6}

fastviewEnhPerContRuleStatsTransactions  OBJECT-TYPE
   SYNTAX  Integer32
   MAX-ACCESS  read-only
   STATUS  current
   DESCRIPTION
       "Number of fastview transactions during the measuring period for content rule."
   ::= {fastviewEnhPerContRuleStatsEntry 7}

fastviewEnhPerContRuleStatsPages  OBJECT-TYPE
   SYNTAX  Integer32
   MAX-ACCESS  read-only
   STATUS  current
   DESCRIPTION
       "Number of pages served by fastview during the measuring period for content rule."
   ::= {fastviewEnhPerContRuleStatsEntry 8}

fastviewEnhPerContRuleStatsOptimizedPages  OBJECT-TYPE
   SYNTAX  Integer32
   MAX-ACCESS  read-only
   STATUS  current
   DESCRIPTION
       "Number of optimized pages served by fastview during the measuring period for content rule."
   ::= {fastviewEnhPerContRuleStatsEntry 9}

fastviewEnhPerContRuleStatsLearningPages  OBJECT-TYPE
   SYNTAX  Integer32
   MAX-ACCESS  read-only
   STATUS  current
   DESCRIPTION
       "Number of learning pages served by fastview during the measuring period for content rule."
   ::= {fastviewEnhPerContRuleStatsEntry 10}

fastviewEnhPerContRuleStatsTokensParsed  OBJECT-TYPE
   SYNTAX  Integer32
   MAX-ACCESS  read-only
   STATUS  current
   DESCRIPTION
       "Number of fastview parsed tokens during the measuring period for content rule."
   ::= {fastviewEnhPerContRuleStatsEntry 11}

fastviewEnhPerContRuleStatsTokensRewritten  OBJECT-TYPE
   SYNTAX  Integer32
   MAX-ACCESS  read-only
   STATUS  current
   DESCRIPTION
       "Number of fastview rewritten tokens during the measuring period for content rule."
   ::= {fastviewEnhPerContRuleStatsEntry 12}

fastviewEnhPerContRuleStatsBytesSavedImgReduction  OBJECT-TYPE
   SYNTAX  Integer32
   MAX-ACCESS  read-only
   STATUS  current
   DESCRIPTION
       "Number of bytes saved with image reduction by fastview during the measuring period for content rule."
   ::= {fastviewEnhPerContRuleStatsEntry 13}

fastviewEnhPerContRuleStatsBytesBeforeImgReduction  OBJECT-TYPE
   SYNTAX  Integer32
   MAX-ACCESS  read-only
   STATUS  current
   DESCRIPTION
       "Number of bytes before image reduction by fastview during the measuring period for content rule."
   ::= {fastviewEnhPerContRuleStatsEntry 14}

fastviewEnhPerContRuleStatsBytesSavedPercent  OBJECT-TYPE
   SYNTAX  Integer32
   MAX-ACCESS  read-only
   STATUS  current
   DESCRIPTION
       "% of bytes saved with image reduction by fastview during the measuring period for content rule."
   ::= {fastviewEnhPerContRuleStatsEntry 15}

fastviewEnhPerContRuleStatsRespWithExpiryModified  OBJECT-TYPE
   SYNTAX  Integer32
   MAX-ACCESS  read-only
   STATUS  current
   DESCRIPTION
       "Number of responses with expirty modified by fastview during the measuring period for content rule."
   ::= {fastviewEnhPerContRuleStatsEntry 16}

fastviewEnhPerContRuleStatsExpiryModifiedPercent  OBJECT-TYPE
   SYNTAX  Integer32
   MAX-ACCESS  read-only
   STATUS  current
   DESCRIPTION
       "% of responses with expirty modified by fastview during the measuring period for content rule."
   ::= {fastviewEnhPerContRuleStatsEntry 17}

fastviewEnhPerContRuleStatsPeakTransactions  OBJECT-TYPE
   SYNTAX  Integer32
   MAX-ACCESS  read-only
   STATUS  current
   DESCRIPTION
       "Peak Number of fastview transactions during the measuring period for content rule."
   ::= {fastviewEnhPerContRuleStatsEntry 18}

fastviewEnhPerContRuleStatsPeakPages  OBJECT-TYPE
   SYNTAX  Integer32
   MAX-ACCESS  read-only
   STATUS  current
   DESCRIPTION
       "Peak Number of pages served by fastview during the measuring period for content rule."
   ::= {fastviewEnhPerContRuleStatsEntry 19}

fastviewEnhPerContRuleStatsPeakOptimizedPages  OBJECT-TYPE
   SYNTAX  Integer32
   MAX-ACCESS  read-only
   STATUS  current
   DESCRIPTION
       "Peak Number of optimized pages served by fastview during the measuring period for content rule."
   ::= {fastviewEnhPerContRuleStatsEntry 20}

fastviewEnhPerContRuleStatsPeakLearningPages  OBJECT-TYPE
   SYNTAX  Integer32
   MAX-ACCESS  read-only
   STATUS  current
   DESCRIPTION
       "Peak Number of learning pages served by fastview during the measuring period for content rule."
   ::= {fastviewEnhPerContRuleStatsEntry 21}

fastviewEnhPerContRuleStatsPeakTokensParsed  OBJECT-TYPE
   SYNTAX  Integer32
   MAX-ACCESS  read-only
   STATUS  current
   DESCRIPTION
       "Peak Number of fastview parsed tokens during the measuring period for content rule."
   ::= {fastviewEnhPerContRuleStatsEntry 22}   
   
fastviewEnhPerContRuleStatsPeakTokensRewritten  OBJECT-TYPE
   SYNTAX  Integer32
   MAX-ACCESS  read-only
   STATUS  current
   DESCRIPTION
       "Peak Number of fastview rewritten tokens during the measuring period for content rule."
   ::= {fastviewEnhPerContRuleStatsEntry 23}

fastviewEnhPerContRuleStatsTotTransactions  OBJECT-TYPE
   SYNTAX  Integer32
   MAX-ACCESS  read-only
   STATUS  current
   DESCRIPTION
       "Total Number of fastview transactions during the measuring period for content rule."
   ::= {fastviewEnhPerContRuleStatsEntry 24}

fastviewEnhPerContRuleStatsTotPages  OBJECT-TYPE
   SYNTAX  Integer32
   MAX-ACCESS  read-only
   STATUS  current
   DESCRIPTION
       "Total Number of pages served by fastview during the measuring period for content rule."
   ::= {fastviewEnhPerContRuleStatsEntry 25}

fastviewEnhPerContRuleStatsTotOptimizedPages  OBJECT-TYPE
   SYNTAX  Integer32
   MAX-ACCESS  read-only
   STATUS  current
   DESCRIPTION
       "Total Number of optimized pages served by fastview during the measuring period for content rule."
   ::= {fastviewEnhPerContRuleStatsEntry 26}

fastviewEnhPerContRuleStatsTotLearningPages  OBJECT-TYPE
   SYNTAX  Integer32
   MAX-ACCESS  read-only
   STATUS  current
   DESCRIPTION
       "Total Number of learning pages served by fastview during the measuring period for content rule."
   ::= {fastviewEnhPerContRuleStatsEntry 27}

fastviewEnhPerContRuleStatsTotTokensParsed  OBJECT-TYPE
   SYNTAX  Integer32
   MAX-ACCESS  read-only
   STATUS  current
   DESCRIPTION
       "Total Number of fastview parsed tokens during the measuring period for content rule."
   ::= {fastviewEnhPerContRuleStatsEntry 28}

fastviewEnhPerContRuleStatsTotTokensRewritten  OBJECT-TYPE
   SYNTAX  Integer32
   MAX-ACCESS  read-only
   STATUS  current
   DESCRIPTION
       "Total Number of fastview rewritten tokens during the measuring period for content rule."
   ::= {fastviewEnhPerContRuleStatsEntry 29}

fastviewEnhPerContRuleStatsTotBytesSavedImgReduction  OBJECT-TYPE
   SYNTAX  Integer32
   MAX-ACCESS  read-only
   STATUS  current
   DESCRIPTION
       "Total Number of bytes saved with image reduction by fastview during the measuring period for content rule."
   ::= {fastviewEnhPerContRuleStatsEntry 30}

fastviewEnhPerContRuleStatsTotBytesBeforeImgReduction  OBJECT-TYPE
   SYNTAX  Integer32
   MAX-ACCESS  read-only
   STATUS  current
   DESCRIPTION
       "Total Number of bytes before image reduction by fastview during the measuring period for content rule."
   ::= {fastviewEnhPerContRuleStatsEntry 31}

fastviewEnhPerContRuleStatsTotBytesSavedPercent OBJECT-TYPE
   SYNTAX  Integer32
   MAX-ACCESS  read-only
   STATUS  current
   DESCRIPTION
       "% of bytes saved with image reduction by fastview during the measuring period for content rule."
   ::= {fastviewEnhPerContRuleStatsEntry 32}

fastviewEnhPerContRuleStatsTotRespWithExpiryModified  OBJECT-TYPE
   SYNTAX  Integer32
   MAX-ACCESS  read-only
   STATUS  current
   DESCRIPTION
       "Total Number of responses with expirty modified by fastview during the measuring period for content rule."
   ::= {fastviewEnhPerContRuleStatsEntry 33}

fastviewEnhPerContRuleStatsTotExpiryModifiedPercent  OBJECT-TYPE
   SYNTAX  Integer32
   MAX-ACCESS  read-only
   STATUS  current
   DESCRIPTION
       "% of responses with expirty modified by fastview during the measuring period for content rule."
   ::= {fastviewEnhPerContRuleStatsEntry 34}
   
fastviewPerWebAppStatsTable OBJECT-TYPE
    SYNTAX SEQUENCE OF FastviewEnhPerWebAppStatsEntry
    MAX-ACCESS not-accessible
    STATUS current
    DESCRIPTION
        "A table for Fastview statistics per web application.
         Note:This mib is not supported for VX instance of Virtualization."
   ::= {fastviewStats 31}

fastviewEnhPerWebAppStatsEntry OBJECT-TYPE
    SYNTAX FastviewEnhPerWebAppStatsEntry
    MAX-ACCESS not-accessible
    STATUS  current
    DESCRIPTION
        " The row definition for Fastview statistics per web application table."
    INDEX  { fastviewEnhPerWebAppStatsWebappId }
    ::= {fastviewPerWebAppStatsTable 1}

FastviewEnhPerWebAppStatsEntry  ::= SEQUENCE {
	fastviewEnhPerWebAppStatsWebappId                     DisplayString,
        fastviewEnhPerWebAppStatsTransactions                 Integer32,
        fastviewEnhPerWebAppStatsPages                        Integer32,
        fastviewEnhPerWebAppStatsOptimizedPages               Integer32,
        fastviewEnhPerWebAppStatsLearningPages               Integer32,
        fastviewEnhPerWebAppStatsTokensParsed              Integer32,
        fastviewEnhPerWebAppStatsTokensRewritten              Integer32,
        fastviewEnhPerWebAppStatsBytesSavedImgReduction                 	Integer32,
        fastviewEnhPerWebAppStatsBytesBeforeImgReduction                 	Integer32,
        fastviewEnhPerWebAppStatsBytesSavedPercent                 	Integer32,
	fastviewEnhPerWebAppStatsRespWithExpiryModified  Integer32,
	fastviewEnhPerWebAppStatsExpiryModifiedPercent  Integer32,
        fastviewEnhPerWebAppStatsPeakTransactions                 Integer32,
        fastviewEnhPerWebAppStatsPeakPages                        Integer32,
        fastviewEnhPerWebAppStatsPeakOptimizedPages               Integer32,
        fastviewEnhPerWebAppStatsPeakLearningPages               Integer32,
        fastviewEnhPerWebAppStatsPeakTokensParsed              Integer32,
        fastviewEnhPerWebAppStatsPeakTokensRewritten              Integer32,
        fastviewEnhPerWebAppStatsTotTransactions                 Integer32,
        fastviewEnhPerWebAppStatsTotPages                        Integer32,
        fastviewEnhPerWebAppStatsTotOptimizedPages               Integer32,
        fastviewEnhPerWebAppStatsTotLearningPages               Integer32,
        fastviewEnhPerWebAppStatsTotTokensParsed              Integer32,
        fastviewEnhPerWebAppStatsTotTokensRewritten              Integer32,
        fastviewEnhPerWebAppStatsTotBytesSavedImgReduction                 	Integer32,
        fastviewEnhPerWebAppStatsTotBytesBeforeImgReduction                 	Integer32,
        fastviewEnhPerWebAppStatsTotBytesSavedPercent               	Integer32,
	fastviewEnhPerWebAppStatsTotRespWithExpiryModified  Integer32,
	fastviewEnhPerWebAppStatsTotExpiryModifiedPercent  Integer32,
	fastviewEnhPerWebAppStatsCompiledPages  Integer32,
	fastviewEnhPerWebAppStatsPeakCompiledPages  Integer32,
	fastviewEnhPerWebAppStatsTotCompiledPages  Integer32
}

fastviewEnhPerWebAppStatsWebappId  OBJECT-TYPE
   SYNTAX  DisplayString 
   MAX-ACCESS  read-only
   STATUS  current
   DESCRIPTION
       "Fastview webapp identifier index."
   ::= {fastviewEnhPerWebAppStatsEntry 1}

fastviewEnhPerWebAppStatsTransactions  OBJECT-TYPE
   SYNTAX  Integer32
   MAX-ACCESS  read-only
   STATUS  current
   DESCRIPTION
       "Number of fastview transactions during the measuring period for web application."
   ::= {fastviewEnhPerWebAppStatsEntry 2}

fastviewEnhPerWebAppStatsPages  OBJECT-TYPE
   SYNTAX  Integer32
   MAX-ACCESS  read-only
   STATUS  current
   DESCRIPTION
       "Number of pages served by fastview during the measuring period for web application."
   ::= {fastviewEnhPerWebAppStatsEntry 3}

fastviewEnhPerWebAppStatsOptimizedPages  OBJECT-TYPE
   SYNTAX  Integer32
   MAX-ACCESS  read-only
   STATUS  current
   DESCRIPTION
       "Number of optimized pages served by fastview during the measuring period for web application."
   ::= {fastviewEnhPerWebAppStatsEntry 4}

fastviewEnhPerWebAppStatsLearningPages  OBJECT-TYPE
   SYNTAX  Integer32
   MAX-ACCESS  read-only
   STATUS  current
   DESCRIPTION
       "Number of learning pages served by fastview during the measuring period for web application."
   ::= {fastviewEnhPerWebAppStatsEntry 5}

fastviewEnhPerWebAppStatsTokensParsed  OBJECT-TYPE
   SYNTAX  Integer32
   MAX-ACCESS  read-only
   STATUS  current
   DESCRIPTION
       "Number of fastview parsed tokens during the measuring period for web application."
   ::= {fastviewEnhPerWebAppStatsEntry 6}

fastviewEnhPerWebAppStatsTokensRewritten  OBJECT-TYPE
   SYNTAX  Integer32
   MAX-ACCESS  read-only
   STATUS  current
   DESCRIPTION
       "Number of fastview rewritten tokens during the measuring period for web application."
   ::= {fastviewEnhPerWebAppStatsEntry 7}

fastviewEnhPerWebAppStatsBytesSavedImgReduction  OBJECT-TYPE
   SYNTAX  Integer32
   MAX-ACCESS  read-only
   STATUS  current
   DESCRIPTION
       "Number of bytes saved with image reduction by fastview during the measuring period for web application."
   ::= {fastviewEnhPerWebAppStatsEntry 8}

fastviewEnhPerWebAppStatsBytesBeforeImgReduction  OBJECT-TYPE
   SYNTAX  Integer32
   MAX-ACCESS  read-only
   STATUS  current
   DESCRIPTION
       "Number of bytes before image reduction by fastview during the measuring period for web application."
   ::= {fastviewEnhPerWebAppStatsEntry 9}

fastviewEnhPerWebAppStatsBytesSavedPercent  OBJECT-TYPE
   SYNTAX  Integer32
   MAX-ACCESS  read-only
   STATUS  current
   DESCRIPTION
       "% of bytes saved with image reduction by fastview during the measuring period for web application."
   ::= {fastviewEnhPerWebAppStatsEntry 10}

fastviewEnhPerWebAppStatsRespWithExpiryModified  OBJECT-TYPE
   SYNTAX  Integer32
   MAX-ACCESS  read-only
   STATUS  current
   DESCRIPTION
       "Number of responses with expirty modified by fastview during the measuring period for web application."
   ::= {fastviewEnhPerWebAppStatsEntry 11}

fastviewEnhPerWebAppStatsExpiryModifiedPercent  OBJECT-TYPE
   SYNTAX  Integer32
   MAX-ACCESS  read-only
   STATUS  current
   DESCRIPTION
       "% of responses with expirty modified by fastview during the measuring period for web application."
   ::= {fastviewEnhPerWebAppStatsEntry 12}

fastviewEnhPerWebAppStatsPeakTransactions  OBJECT-TYPE
   SYNTAX  Integer32
   MAX-ACCESS  read-only
   STATUS  current
   DESCRIPTION
       "Peak Number of fastview transactions during the measuring period for web application."
   ::= {fastviewEnhPerWebAppStatsEntry 13}

fastviewEnhPerWebAppStatsPeakPages  OBJECT-TYPE
   SYNTAX  Integer32
   MAX-ACCESS  read-only
   STATUS  current
   DESCRIPTION
       "Peak Number of pages served by fastview during the measuring period for web application."
   ::= {fastviewEnhPerWebAppStatsEntry 14}

fastviewEnhPerWebAppStatsPeakOptimizedPages  OBJECT-TYPE
   SYNTAX  Integer32
   MAX-ACCESS  read-only
   STATUS  current
   DESCRIPTION
       "Peak Number of optimized pages served by fastview during the measuring period for web application."
   ::= {fastviewEnhPerWebAppStatsEntry 15}

fastviewEnhPerWebAppStatsPeakLearningPages  OBJECT-TYPE
   SYNTAX  Integer32
   MAX-ACCESS  read-only
   STATUS  current
   DESCRIPTION
       "Peak Number of learning pages served by fastview during the measuring period for web application."
   ::= {fastviewEnhPerWebAppStatsEntry 16}

fastviewEnhPerWebAppStatsPeakTokensParsed  OBJECT-TYPE
   SYNTAX  Integer32
   MAX-ACCESS  read-only
   STATUS  current
   DESCRIPTION
       "Peak Number of fastview parsed tokens during the measuring period for web application."
   ::= {fastviewEnhPerWebAppStatsEntry 17}   
   
fastviewEnhPerWebAppStatsPeakTokensRewritten  OBJECT-TYPE
   SYNTAX  Integer32
   MAX-ACCESS  read-only
   STATUS  current
   DESCRIPTION
       "Peak Number of fastview rewritten tokens during the measuring period for web application."
   ::= {fastviewEnhPerWebAppStatsEntry 18}

fastviewEnhPerWebAppStatsTotTransactions  OBJECT-TYPE
   SYNTAX  Integer32
   MAX-ACCESS  read-only
   STATUS  current
   DESCRIPTION
       "Total Number of fastview transactions during the measuring period for web application."
   ::= {fastviewEnhPerWebAppStatsEntry 19}

fastviewEnhPerWebAppStatsTotPages  OBJECT-TYPE
   SYNTAX  Integer32
   MAX-ACCESS  read-only
   STATUS  current
   DESCRIPTION
       "Total Number of pages served by fastview during the measuring period for web application."
   ::= {fastviewEnhPerWebAppStatsEntry 20}

fastviewEnhPerWebAppStatsTotOptimizedPages  OBJECT-TYPE
   SYNTAX  Integer32
   MAX-ACCESS  read-only
   STATUS  current
   DESCRIPTION
       "Total Number of optimized pages served by fastview during the measuring period for web application."
   ::= {fastviewEnhPerWebAppStatsEntry 21}

fastviewEnhPerWebAppStatsTotLearningPages  OBJECT-TYPE
   SYNTAX  Integer32
   MAX-ACCESS  read-only
   STATUS  current
   DESCRIPTION
       "Total Number of learning pages served by fastview during the measuring period for web application."
   ::= {fastviewEnhPerWebAppStatsEntry 22}

fastviewEnhPerWebAppStatsTotTokensParsed  OBJECT-TYPE
   SYNTAX  Integer32
   MAX-ACCESS  read-only
   STATUS  current
   DESCRIPTION
       "Total Number of fastview parsed tokens during the measuring period for web application."
   ::= {fastviewEnhPerWebAppStatsEntry 23}

fastviewEnhPerWebAppStatsTotTokensRewritten  OBJECT-TYPE
   SYNTAX  Integer32
   MAX-ACCESS  read-only
   STATUS  current
   DESCRIPTION
       "Total Number of fastview rewritten tokens during the measuring period for web application."
   ::= {fastviewEnhPerWebAppStatsEntry 24}

fastviewEnhPerWebAppStatsTotBytesSavedImgReduction  OBJECT-TYPE
   SYNTAX  Integer32
   MAX-ACCESS  read-only
   STATUS  current
   DESCRIPTION
       "Total Number of bytes saved with image reduction by fastview during the measuring period for web application."
   ::= {fastviewEnhPerWebAppStatsEntry 25}

fastviewEnhPerWebAppStatsTotBytesBeforeImgReduction  OBJECT-TYPE
   SYNTAX  Integer32
   MAX-ACCESS  read-only
   STATUS  current
   DESCRIPTION
       "Total Number of bytes before image reduction by fastview during the measuring period for web application."
   ::= {fastviewEnhPerWebAppStatsEntry 26}

fastviewEnhPerWebAppStatsTotBytesSavedPercent OBJECT-TYPE
   SYNTAX  Integer32
   MAX-ACCESS  read-only
   STATUS  current
   DESCRIPTION
       "% of bytes saved with image reduction by fastview during the measuring period for web application."
   ::= {fastviewEnhPerWebAppStatsEntry 27}

fastviewEnhPerWebAppStatsTotRespWithExpiryModified  OBJECT-TYPE
   SYNTAX  Integer32
   MAX-ACCESS  read-only
   STATUS  current
   DESCRIPTION
       "Total Number of responses with expirty modified by fastview during the measuring period for web application."
   ::= {fastviewEnhPerWebAppStatsEntry 28}

fastviewEnhPerWebAppStatsTotExpiryModifiedPercent  OBJECT-TYPE
   SYNTAX  Integer32
   MAX-ACCESS  read-only
   STATUS  current
   DESCRIPTION
       "% of responses with expirty modified by fastview during the measuring period for web application."
   ::= {fastviewEnhPerWebAppStatsEntry 29}

fastviewEnhPerWebAppStatsCompiledPages  OBJECT-TYPE
   SYNTAX  Integer32
   MAX-ACCESS  read-only
   STATUS  current
   DESCRIPTION
       "Number of fastview compiled pages during the measuring period for web application."
   ::= {fastviewEnhPerWebAppStatsEntry 30}

fastviewEnhPerWebAppStatsPeakCompiledPages  OBJECT-TYPE
   SYNTAX  Integer32
   MAX-ACCESS  read-only
   STATUS  current
   DESCRIPTION
       "Peak of fastview compiled pages during the measuring period for web application."
   ::= {fastviewEnhPerWebAppStatsEntry 31}

fastviewEnhPerWebAppStatsTotCompiledPages  OBJECT-TYPE
   SYNTAX  Integer32
   MAX-ACCESS  read-only
   STATUS  current
   DESCRIPTION
       "Total of fastview compiled pages during the measuring period for web application."
   ::= {fastviewEnhPerWebAppStatsEntry 32}

fastviewStatSummCompiledPages OBJECT-TYPE
   SYNTAX  Integer32
   MAX-ACCESS  read-only
   STATUS  current 
   DESCRIPTION
       "Number of fastview pages compiled within the measuring period.
        Note:This mib is not supported for VX instance of Virtualization."
   ::= {fastviewStats 32}

fastviewStatSummPeakCompiledPages OBJECT-TYPE
   SYNTAX  Integer32
   MAX-ACCESS  read-only
   STATUS  current 
   DESCRIPTION
       "Peak of fastview compiled pages within the measuring period.
        Note:This mib is not supported for VX instance of Virtualization."
   ::= {fastviewStats 33}

fastviewStatSummTotCompiledPages OBJECT-TYPE
   SYNTAX  Integer32
   MAX-ACCESS  read-only
   STATUS  current 
   DESCRIPTION
       "Total of fastview compiled pages within the measuring period.
        Note:This mib is not supported for VX instance of Virtualization."
   ::= {fastviewStats 34}

cachStatSummTotObj OBJECT-TYPE
   SYNTAX  Integer32
   MAX-ACCESS  read-only
   STATUS  current 
   DESCRIPTION
       "Number of Objects served by cache within the measuring period.
        Note:This mib is not supported for VX instance of Virtualization."
   ::= {cachStats 1}

cachStatSummHitPerc OBJECT-TYPE
   SYNTAX  Integer32
   MAX-ACCESS  read-only
   STATUS  current 
   DESCRIPTION
       "Percent of HTTP requests served by objects from cache.
        Note:This mib is not supported for VX instance of Virtualization."
   ::= {cachStats 2}

cachStatSummServRate OBJECT-TYPE
   SYNTAX  Integer32
   MAX-ACCESS  read-only
   STATUS  current 
   DESCRIPTION
       "Rate of requests served by cache every second.
        Note:This mib is not supported for VX instance of Virtualization."
   ::= {cachStats 3}

cachStatSummNewCachedObj OBJECT-TYPE
   SYNTAX  Integer32
   MAX-ACCESS  read-only
   STATUS  current  
   DESCRIPTION
       "Amount of new objects cached during the measuring period.
        Note:This mib is not supported for VX instance of Virtualization."
   ::= {cachStats 4}

cachStatPeakNewCachedObj OBJECT-TYPE
   SYNTAX  Integer32
   MAX-ACCESS  read-only
   STATUS  current  
   DESCRIPTION
       "Peak of new objects cached during the measuring period.
        Note:This mib is not supported for VX instance of Virtualization."
   ::= {cachStats 32}

cachStatSummRateNewCachedObj OBJECT-TYPE
   SYNTAX  Integer32
   MAX-ACCESS  read-only
   STATUS  current 
   DESCRIPTION
       "Average number of new objects cached every second.
        Note:This mib is not supported for VX instance of Virtualization."
   ::= {cachStats 5}

cachStatSummNewCachedBytes OBJECT-TYPE
   SYNTAX  Integer32
   MAX-ACCESS  read-only
   STATUS  current 
   DESCRIPTION
       "Amount of new bytes cached during the measuring period.
        Note:This mib is not supported for VX instance of Virtualization."
   ::= {cachStats 6}

cachStatSummRateNewCachedBytes OBJECT-TYPE
   SYNTAX  Integer32
   MAX-ACCESS  read-only
   STATUS  current 
   DESCRIPTION
       "Average number of new bytes cached every second.
        Note:This mib is not supported for VX instance of Virtualization."
   ::= {cachStats 7}

cachStatSummObjSmaller10K OBJECT-TYPE
   SYNTAX  Integer32
   MAX-ACCESS  read-only
   STATUS  current 
   DESCRIPTION
       "Amount of objects cached during last measuring period of size smaller than 10KB.
        Note:This mib is not supported for VX instance of Virtualization."
   ::= {cachStats 8}

cachStatSummObj11KTO50K OBJECT-TYPE
   SYNTAX  Integer32
   MAX-ACCESS  read-only
   STATUS  current 
   DESCRIPTION
       "Amount of objects cached during last measuring period of size between 11KB and 50KB.
        Note:This mib is not supported for VX instance of Virtualization."
   ::= {cachStats 9}

cachStatSummObj51KTO100K OBJECT-TYPE
   SYNTAX  Integer32
   MAX-ACCESS  read-only
   STATUS  current 
   DESCRIPTION
       "Amount of objects cached during last measuring period of size between 51KB and 100KB.
        Note:This mib is not supported for VX instance of Virtualization."
   ::= {cachStats 10}

cachStatSummObj101KTO1M OBJECT-TYPE
   SYNTAX  Integer32
   MAX-ACCESS  read-only
   STATUS  current 
   DESCRIPTION
       "Amount of objects cached during last measuring period of size between 101KB and 1MB.
        Note:This mib is not supported for VX instance of Virtualization."
   ::= {cachStats 11}

cachStatSummObjLarger1M OBJECT-TYPE
   SYNTAX  Integer32
   MAX-ACCESS  read-only
   STATUS  current 
   DESCRIPTION
       "Amount of objects cached during last measuring period of size larger than 1MB.
        Note:This mib is not supported for VX instance of Virtualization."
   ::= {cachStats 12}

cachPerServStatTable OBJECT-TYPE
   SYNTAX SEQUENCE OF CachPerServStatEntry
   MAX-ACCESS not-accessible
   STATUS current 
   DESCRIPTION
       "A table for cache statistics per virtual service.
        Note:This mib is not supported for VX instance of Virtualization."
   ::= {cachStats 13}

cachPerServStatEntry OBJECT-TYPE
   SYNTAX CachPerServStatEntry 
   MAX-ACCESS not-accessible
   STATUS  current 
   DESCRIPTION
       " The row definition for cache statistics per virtual service table."
   INDEX  { cachStatPerServVirtServIndex, cachStatPerServVirtServiceIndex}
   ::= {cachPerServStatTable 1}

CachPerServStatEntry  ::= SEQUENCE {
        cachStatPerServVirtServIndex                    DisplayString,
        cachStatPerServVirtServiceIndex                 Integer32,
        cachStatPerServVirtServPort                     Integer32,	
	cachStatPerServCachePolId                       DisplayString,
        cachStatPerServTotObj                           Integer32,
        cachStatPerServHitPerc                          Integer32,
        cachStatPerServServRate                         Integer32,
        cachStatPerServNewCachedObj                     Integer32,
        cachStatPerServRateNewCachedObj                 Integer32,
        cachStatPerServNewCachedBytes                   Integer32,
        cachStatPerServRateNewCachedBytes               Integer32,
        cachStatPerServObjSmaller10K                    Integer32,
        cachStatPerServObj11KTO50K                      Integer32,
        cachStatPerServObj51KTO100K                     Integer32,
	cachStatPerServObj101KTO1M                      Integer32,
        cachStatPerServObjLarger1M                      Integer32,
        cachStatPerServPeakNewCachedObj                 Integer32
        }
cachStatPerServVirtServIndex  OBJECT-TYPE
    SYNTAX  DisplayString  ( SIZE ( 1 .. 255  ) )
    MAX-ACCESS  read-only
    STATUS  current
    DESCRIPTION
        "Virtual server Index."
   ::= {cachPerServStatEntry 1}

cachStatPerServVirtServiceIndex  OBJECT-TYPE
   SYNTAX  Integer32 
   MAX-ACCESS  read-only
   STATUS  current
   DESCRIPTION
       "Virtual server service index."
   ::= {cachPerServStatEntry 2}

cachStatPerServVirtServPort  OBJECT-TYPE
   SYNTAX  Integer32 
   MAX-ACCESS  read-only
   STATUS  current
   DESCRIPTION
       "Virtual server service port number."
   ::= {cachPerServStatEntry 3}

cachStatPerServCachePolId  OBJECT-TYPE
   SYNTAX  DisplayString 
   MAX-ACCESS  read-only
   STATUS  current
   DESCRIPTION
       "Cache policy identifier associated with the virtual service."
   ::= {cachPerServStatEntry 4}

cachStatPerServTotObj  OBJECT-TYPE
   SYNTAX  Integer32
   MAX-ACCESS  read-only
   STATUS  current
   DESCRIPTION
       "Number of objects served by cache during the measuring period for virtual service."
   ::= {cachPerServStatEntry 5}

cachStatPerServHitPerc  OBJECT-TYPE
   SYNTAX  Integer32
   MAX-ACCESS  read-only
   STATUS  current
   DESCRIPTION
       "Percent of HTTP requests served by objects from cache for virtual service."
   ::= {cachPerServStatEntry 6}

cachStatPerServServRate  OBJECT-TYPE
   SYNTAX  Integer32
   MAX-ACCESS  read-only
   STATUS  current
   DESCRIPTION
       "Rate of requests served by cache every second for virtual service."
   ::= {cachPerServStatEntry 7}

cachStatPerServNewCachedObj  OBJECT-TYPE
   SYNTAX  Integer32
   MAX-ACCESS  read-only
   STATUS  current
   DESCRIPTION
       "Amount of new objects cached during the measuring period for virtual service."
   ::= {cachPerServStatEntry 8}

cachStatPerServPeakNewCachedObj  OBJECT-TYPE
   SYNTAX  Integer32
   MAX-ACCESS  read-only
   STATUS  current
   DESCRIPTION
       "Peak of new objects cached during the measuring period for virtual service."
   ::= {cachPerServStatEntry 17}
   
cachStatPerServRateNewCachedObj  OBJECT-TYPE
   SYNTAX  Integer32
   MAX-ACCESS  read-only
   STATUS  current
   DESCRIPTION
       "Average number of new objects cached every second for virtual service."
   ::= {cachPerServStatEntry 9}

cachStatPerServNewCachedBytes  OBJECT-TYPE
   SYNTAX  Integer32
   MAX-ACCESS  read-only
   STATUS  current
   DESCRIPTION
       "Amount of new bytes cached during the measuring period for virtual service."
   ::= {cachPerServStatEntry 10}

cachStatPerServRateNewCachedBytes  OBJECT-TYPE
   SYNTAX  Integer32
   MAX-ACCESS  read-only
   STATUS  current
   DESCRIPTION
       "Average number of new bytes cached every second for virtual service."
   ::= {cachPerServStatEntry 11}

cachStatPerServObjSmaller10K  OBJECT-TYPE
   SYNTAX  Integer32
   MAX-ACCESS  read-only
   STATUS  current
   DESCRIPTION
       "Amount of objects cached during last measuring period of size smaller than 10KB for virtual service."
   ::= {cachPerServStatEntry 12}

cachStatPerServObj11KTO50K  OBJECT-TYPE
   SYNTAX  Integer32
   MAX-ACCESS  read-only
   STATUS  current
   DESCRIPTION
       "Amount of objects cached during last measuring period of size between 11KB and 50KB for virtual service."
   ::= {cachPerServStatEntry 13}

cachStatPerServObj51KTO100K  OBJECT-TYPE
   SYNTAX  Integer32
   MAX-ACCESS  read-only
   STATUS  current
   DESCRIPTION
       "Amount of objects cached during last measuring period of size between 51KB and 100KB for virtual service."
   ::= {cachPerServStatEntry 14}

cachStatPerServObj101KTO1M  OBJECT-TYPE
   SYNTAX  Integer32
   MAX-ACCESS  read-only
   STATUS  current
   DESCRIPTION
       "Amount of objects cached during last measuring period of size between 101KB and 1MB for virtual service."
   ::= {cachPerServStatEntry 15}

cachStatPerServObjLarger1M  OBJECT-TYPE
   SYNTAX  Integer32
   MAX-ACCESS  read-only
   STATUS  current
   DESCRIPTION
       "Amount of objects cached during last measuring period of size larger than 1MB for virtual service."
   ::= {cachPerServStatEntry 16}

cachPerRuleListStatsTable OBJECT-TYPE
   SYNTAX SEQUENCE OF CachPerRuleListStatsEntry
   MAX-ACCESS not-accessible
   STATUS current 
   DESCRIPTION
       "A table for cache statistics per rule list.
        Note:This mib is not supported for VX instance of Virtualization."
   ::= {cachStats 14}

cachPerRuleListStatsEntry OBJECT-TYPE
   SYNTAX CachPerRuleListStatsEntry 
   MAX-ACCESS not-accessible
   STATUS  current 
   DESCRIPTION
       " The row definition for cache statistics per rule list table."
   INDEX  { cachRuleListId }
   ::= {cachPerRuleListStatsTable 1}

CachPerRuleListStatsEntry  ::= SEQUENCE {
        cachRuleListIndex                   Integer32,
        cachRuleListId                      DisplayString,
        cachRuleListNumOfObjCac             Integer32,
        cachRuleListNumOfBytesCac           Integer32
        }

cachRuleListIndex  OBJECT-TYPE
   SYNTAX  Integer32
   MAX-ACCESS  read-only
   STATUS  current
   DESCRIPTION
       "Cache rule list index."
   ::= {cachPerRuleListStatsEntry 1}

cachRuleListId  OBJECT-TYPE
   SYNTAX  DisplayString
   MAX-ACCESS  read-only
   STATUS  current
   DESCRIPTION
       "Cache rule list identifier."
   ::= {cachPerRuleListStatsEntry 2}

cachRuleListNumOfObjCac OBJECT-TYPE
   SYNTAX  Integer32
   MAX-ACCESS  read-only
   STATUS  current
   DESCRIPTION
       "Number of objects cached by this rule list."
   ::= {cachPerRuleListStatsEntry 3}

cachRuleListNumOfBytesCac  OBJECT-TYPE
   SYNTAX  Integer32
   MAX-ACCESS  read-only
   STATUS  current
   DESCRIPTION
       "Number of bytes cached by this rule list."
   ::= {cachPerRuleListStatsEntry 4}

cachPerRuleStatsTable OBJECT-TYPE
   SYNTAX SEQUENCE OF CachPerRuleStatsEntry
   MAX-ACCESS not-accessible
   STATUS current 
   DESCRIPTION
       "A table for cache statistics per rule.
        Note:This mib is not supported for VX instance of Virtualization."
   ::= {cachStats 15}

cachPerRuleStatsEntry OBJECT-TYPE
   SYNTAX CachPerRuleStatsEntry 
   MAX-ACCESS not-accessible
   STATUS  current 
   DESCRIPTION
       " The row definition for cache statistics per rule table."
   INDEX  { cachRuleRuleListIndex, cachRuleIndex }
   ::= {cachPerRuleStatsTable 1}

CachPerRuleStatsEntry  ::= SEQUENCE {
        cachRuleRuleListIndex               Integer32,
        cachRuleIndex                       Integer32,
        cachRuleRuleListId                  DisplayString,
        cachRuleNumOfObjCac                 Integer32,
        cachRuleNumOfBytesCac               Integer32
        }

cachRuleRuleListIndex  OBJECT-TYPE
   SYNTAX  Integer32 
   MAX-ACCESS  read-only
   STATUS  current
   DESCRIPTION
       "Cache rule rule-list index."
   ::= {cachPerRuleStatsEntry 1}

cachRuleIndex  OBJECT-TYPE
   SYNTAX  Integer32 
   MAX-ACCESS  read-only
   STATUS  current
   DESCRIPTION
       "Cache rule number."
   ::= {cachPerRuleStatsEntry 2}

cachRuleRuleListId  OBJECT-TYPE
   SYNTAX  DisplayString
   MAX-ACCESS  read-only
   STATUS  current
   DESCRIPTION
       "Cache rule rule-list identifier."
   ::= {cachPerRuleStatsEntry 3}

cachRuleNumOfObjCac  OBJECT-TYPE
   SYNTAX  Integer32 
   MAX-ACCESS  read-only
   STATUS  current
   DESCRIPTION
       "Number of objects cached by the rule."
   ::= {cachPerRuleStatsEntry 4}

cachRuleNumOfBytesCac  OBJECT-TYPE
   SYNTAX  Integer32 
   MAX-ACCESS  read-only
   STATUS  current
   DESCRIPTION
       "Number of bytes cached by the rule."
   ::= {cachPerRuleStatsEntry 5}

-- per optimization list/rule stats

cachPerOptListStatsTable OBJECT-TYPE
   SYNTAX SEQUENCE OF CachPerOptListStatsEntry
   MAX-ACCESS not-accessible
   STATUS current 
   DESCRIPTION
       "A table for cache statistics per optimization rule list.
        Note:This mib is not supported for VX instance of Virtualization."
   ::= {cachStats 30}

cachPerOptListStatsEntry OBJECT-TYPE
   SYNTAX CachPerOptListStatsEntry 
   MAX-ACCESS not-accessible
   STATUS  current 
   DESCRIPTION
       " The row definition for cache statistics per optimization rule list table."
   INDEX  { cachOptListId }
   ::= {cachPerOptListStatsTable 1}

CachPerOptListStatsEntry  ::= SEQUENCE {
        cachOptListIndex                   Integer32,
        cachOptListId                      DisplayString,
        cachOptListNumOfHits               Integer32
        }

cachOptListIndex  OBJECT-TYPE
   SYNTAX  Integer32
   MAX-ACCESS  read-only
   STATUS  current
   DESCRIPTION
       "Cache opt rule list index."
   ::= {cachPerOptListStatsEntry 1}

cachOptListId  OBJECT-TYPE
   SYNTAX  DisplayString
   MAX-ACCESS  read-only
   STATUS  current
   DESCRIPTION
       "Cache opt rule list identifier."
   ::= {cachPerOptListStatsEntry 2}

cachOptListNumOfHits OBJECT-TYPE
   SYNTAX  Integer32
   MAX-ACCESS  read-only
   STATUS  current
   DESCRIPTION
       "Number of hits on this rule list."
   ::= {cachPerOptListStatsEntry 3}

cachPerOptRuleStatsTable OBJECT-TYPE
   SYNTAX SEQUENCE OF CachPerOptRuleStatsEntry
   MAX-ACCESS not-accessible
   STATUS current 
   DESCRIPTION
       "A table for optimization statistics per rule.
        Note:This mib is not supported for VX instance of Virtualization."
   ::= {cachStats 31}

cachPerOptRuleStatsEntry OBJECT-TYPE
   SYNTAX CachPerOptRuleStatsEntry 
   MAX-ACCESS not-accessible
   STATUS  current 
   DESCRIPTION
       " The row definition for optimization statistics per rule table."
   INDEX  { cachOptRuleListIndex, cachOptRuleIndex }
   ::= {cachPerOptRuleStatsTable 1}

CachPerOptRuleStatsEntry  ::= SEQUENCE {
        cachOptRuleListIndex                Integer32,
        cachOptRuleIndex                    Integer32,
        cachOptRuleListId                   DisplayString,
        cachOptRuleNumOfHits                Integer32
        }

cachOptRuleListIndex  OBJECT-TYPE
   SYNTAX  Integer32 
   MAX-ACCESS  read-only
   STATUS  current
   DESCRIPTION
       "Optimization rule rule-list index."
   ::= {cachPerOptRuleStatsEntry 1}

cachOptRuleIndex  OBJECT-TYPE
   SYNTAX  Integer32 
   MAX-ACCESS  read-only
   STATUS  current
   DESCRIPTION
       "Optimization rule number."
   ::= {cachPerOptRuleStatsEntry 2}

cachOptRuleListId  OBJECT-TYPE
   SYNTAX  DisplayString
   MAX-ACCESS  read-only
   STATUS  current
   DESCRIPTION
       "Optimization rule rule-list identifier."
   ::= {cachPerOptRuleStatsEntry 3}

cachOptRuleNumOfHits  OBJECT-TYPE
   SYNTAX  Integer32 
   MAX-ACCESS  read-only
   STATUS  current
   DESCRIPTION
       "Number of hits on the rule."
   ::= {cachPerOptRuleStatsEntry 4}

compUnCompressedThrputKB OBJECT-TYPE
   SYNTAX  Integer32
   MAX-ACCESS  read-only
   STATUS  current
   DESCRIPTION
       "Total throughput of compressible object before compression counted during measuring period.
        Note:This mib is not supported for VX instance of Virtualization."
   ::= {compStats 1}

compAvgSizeBefCompKB  OBJECT-TYPE
   SYNTAX  Integer32
   MAX-ACCESS  read-only
   STATUS  current
   DESCRIPTION
       "Average object size before compression.
        Note:This mib is not supported for VX instance of Virtualization."
   ::= {compStats 2}

compCompressedThrputKB OBJECT-TYPE
   SYNTAX  Integer32
   MAX-ACCESS  read-only
   STATUS  current
   DESCRIPTION
       "Total throughput of compressible objects after compression counted during measuring period.
        Note:This mib is not supported for VX instance of Virtualization."
   ::= {compStats 3}

compAvgSizeAftCompKB OBJECT-TYPE
   SYNTAX  Integer32
   MAX-ACCESS  read-only
   STATUS  current
   DESCRIPTION
       "Average object size after compression.
        Note:This mib is not supported for VX instance of Virtualization."
   ::= {compStats 4}

compAvgCompRatio OBJECT-TYPE
   SYNTAX  Integer32
   MAX-ACCESS  read-only
   STATUS  current
   DESCRIPTION
       "Average compression ratio during measuring period.
        Note:This mib is not supported for VX instance of Virtualization."
   ::= {compStats 5}

compThrputCompRatio OBJECT-TYPE
   SYNTAX  Integer32
   MAX-ACCESS  read-only
   STATUS  current
   DESCRIPTION
       "Effective compression ratio out of total traffic.
        Note:This mib is not supported for VX instance of Virtualization."
   ::= {compStats 6}

compBytesSaved OBJECT-TYPE
   SYNTAX  Counter64
   MAX-ACCESS  read-only
   STATUS  current
   DESCRIPTION
       "Bytes saved.
        Note:This mib is not supported for VX instance of Virtualization."
   ::= {compStats 12}

compBytesSavedPeak OBJECT-TYPE
   SYNTAX  Counter64
   MAX-ACCESS  read-only
   STATUS  current
   DESCRIPTION
       "Peak Bytes saved.
        Note:This mib is not supported for VX instance of Virtualization."
   ::= {compStats 13}

compBytesSavedTot OBJECT-TYPE
   SYNTAX  Counter64
   MAX-ACCESS  read-only
   STATUS  current
   DESCRIPTION
       "Total Bytes saved.
        Note:This mib is not supported for VX instance of Virtualization."
   ::= {compStats 14}

compStatPerServTable OBJECT-TYPE
   SYNTAX SEQUENCE OF CompStatPerServEntry
   MAX-ACCESS not-accessible
   STATUS current
   DESCRIPTION
       "A table for compression statistics per virtual service.
        Note:This mib is not supported for VX instance of Virtualization."
   ::= {compStats 7}

compStatPerServEntry OBJECT-TYPE
   SYNTAX CompStatPerServEntry 
   MAX-ACCESS not-accessible
   STATUS  current
   DESCRIPTION
       " The row definition for compression statistics per virtual service table."
   INDEX  { compStatPerServVirtServIndex, compStatPerServVirtServiceIndex}
   ::= {compStatPerServTable 1}

CompStatPerServEntry  ::= SEQUENCE {
        compStatPerServVirtServIndex      DisplayString,
        compStatPerServVirtServiceIndex   Integer32,
	compStatPerServVirtServPort       Integer32,
	compStatPerServCompPolId          DisplayString,
        compStatPerServUnComprTputKb      Integer32,
        compStatPerServComprTputKb        Integer32,
        compStatPerServAvgSizeBefComp     Integer32,
        compStatPerServAvgSizeAftComp     Integer32,
        compStatPerServAvgCompRatio       Integer32,
	compStatPerServThrputCompRatio    Integer32,
	compStatPerServBytesSaved         Counter64,
	compStatPerServBytesSavedPeak     Counter64,
	compStatPerServBytesSavedTot      Counter64
        }

compStatPerServVirtServIndex  OBJECT-TYPE
    SYNTAX  DisplayString  ( SIZE ( 1 .. 255  ) )
    MAX-ACCESS  read-only
    STATUS  current
    DESCRIPTION
        "Virtual server Index."
   ::= {compStatPerServEntry 1}

compStatPerServVirtServiceIndex  OBJECT-TYPE
   SYNTAX  Integer32 
    MAX-ACCESS  read-only
   STATUS  current
   DESCRIPTION
       "Virtual server service index."
   ::= {compStatPerServEntry 2}

compStatPerServVirtServPort  OBJECT-TYPE
   SYNTAX  Integer32 
    MAX-ACCESS  read-only
   STATUS  current
   DESCRIPTION
       "Virtual server service port number."
   ::= {compStatPerServEntry 3}

compStatPerServCompPolId  OBJECT-TYPE
   SYNTAX  DisplayString 
   MAX-ACCESS  read-only
   STATUS  current
   DESCRIPTION
       "Compression policy identifier associated with the virtual service."
   ::= {compStatPerServEntry 4}

compStatPerServUnComprTputKb  OBJECT-TYPE
   SYNTAX  Integer32
   MAX-ACCESS  read-only
   STATUS  current
   DESCRIPTION
       "Total throughput of compressible object before compression counted during measuring period for virtual service."
   ::= {compStatPerServEntry 5}

compStatPerServComprTputKb  OBJECT-TYPE
   SYNTAX  Integer32
   MAX-ACCESS  read-only
   STATUS  current
   DESCRIPTION
       "Total throughput of compressible objects after compression counted during measuring period for virtual service."
   ::= {compStatPerServEntry 6}

compStatPerServAvgSizeBefComp  OBJECT-TYPE
   SYNTAX  Integer32
   MAX-ACCESS  read-only
   STATUS  current
   DESCRIPTION
       "Average object size before compression for virtual service."
   ::= {compStatPerServEntry 7}

compStatPerServAvgSizeAftComp  OBJECT-TYPE
   SYNTAX  Integer32
   MAX-ACCESS  read-only
   STATUS  current
   DESCRIPTION
       "Average object size after compression for virtual service."
   ::= {compStatPerServEntry 8}

compStatPerServAvgCompRatio  OBJECT-TYPE
   SYNTAX  Integer32
   MAX-ACCESS  read-only
   STATUS  current
   DESCRIPTION
       "Average compression ratio during measuring period for virtual service."
   ::= {compStatPerServEntry 9}

compStatPerServThrputCompRatio  OBJECT-TYPE
   SYNTAX  Integer32
   MAX-ACCESS  read-only
   STATUS  current
   DESCRIPTION
       "Effective compression ratio out of total traffic for virtual service."
   ::= {compStatPerServEntry 10}

compStatPerServBytesSaved  OBJECT-TYPE
   SYNTAX  Counter64
   MAX-ACCESS  read-only
   STATUS  current
   DESCRIPTION
       "bytes saved for virtual service."
   ::= {compStatPerServEntry 11}

compStatPerServBytesSavedPeak  OBJECT-TYPE
   SYNTAX  Counter64
   MAX-ACCESS  read-only
   STATUS  current
   DESCRIPTION
       "Peak bytes saved for virtual service."
   ::= {compStatPerServEntry 12}

compStatPerServBytesSavedTot  OBJECT-TYPE
   SYNTAX  Counter64
   MAX-ACCESS  read-only
   STATUS  current
   DESCRIPTION
       "Total bytes saved for virtual service."
   ::= {compStatPerServEntry 13}

compPerBrowRuleListStatsTable OBJECT-TYPE
   SYNTAX SEQUENCE OF CompPerBrowRuleListStatsEntry
   MAX-ACCESS not-accessible
   STATUS current
   DESCRIPTION
       "A table for compression statistics per rule list.
        Note:This mib is not supported for VX instance of Virtualization."
   ::= {compStats 8}

compPerBrowRuleListStatsEntry OBJECT-TYPE
   SYNTAX CompPerBrowRuleListStatsEntry 
   MAX-ACCESS not-accessible
   STATUS  current
   DESCRIPTION
       " The row definition for compression statistics per rule list table."
   INDEX  { compBrowRuleListIndex }
   ::= {compPerBrowRuleListStatsTable 1}

CompPerBrowRuleListStatsEntry  ::= SEQUENCE {
        compBrowRuleListIndex                          Integer32,
        compBrowRuleListId                             DisplayString,
        compBrowRuleListNumOfObj                       Integer32,
        compBrowRuleListSizeBefComp                    Integer32,
        compBrowRuleListSizeAftComp                    Integer32,
        compBrowRuleListCompRatio                      Integer32
        }

compBrowRuleListIndex  OBJECT-TYPE
   SYNTAX  Integer32
   MAX-ACCESS  read-only
   STATUS  current
   DESCRIPTION
       "Compression browsing rule list index."
   ::= {compPerBrowRuleListStatsEntry 1}

compBrowRuleListId  OBJECT-TYPE
   SYNTAX  DisplayString
   MAX-ACCESS  read-only
   STATUS  current
   DESCRIPTION
       "Compression browsing rule list identifier."
   ::= {compPerBrowRuleListStatsEntry 2}

compBrowRuleListNumOfObj  OBJECT-TYPE
   SYNTAX  Integer32
   MAX-ACCESS  read-only
   STATUS  current
   DESCRIPTION
       "Number of objects matched by this rule-list during measuring period."
   ::= {compPerBrowRuleListStatsEntry 3}

compBrowRuleListSizeBefComp  OBJECT-TYPE
   SYNTAX  Integer32
   MAX-ACCESS  read-only
   STATUS  current
   DESCRIPTION
       "Total size of all matched objects by this browser rule-list before compression."
   ::= {compPerBrowRuleListStatsEntry 4}

compBrowRuleListSizeAftComp  OBJECT-TYPE
   SYNTAX  Integer32
   MAX-ACCESS  read-only
   STATUS  current
   DESCRIPTION
       "Total size of all matched objects by this browser rule-list after compression."
   ::= {compPerBrowRuleListStatsEntry 5}

compBrowRuleListCompRatio  OBJECT-TYPE
   SYNTAX  Integer32
   MAX-ACCESS  read-only
   STATUS  current
   DESCRIPTION
       "Compression ratio per rule list."
   ::= {compPerBrowRuleListStatsEntry 6}

compPerBrowRuleStatsTable OBJECT-TYPE
   SYNTAX SEQUENCE OF CompPerBrowRuleStatsEntry
   MAX-ACCESS not-accessible
   STATUS current
   DESCRIPTION
       "A table for compression statistics per browser rule.
        Note:This mib is not supported for VX instance of Virtualization."
   ::= {compStats 9}

compPerBrowRuleStatsEntry OBJECT-TYPE
   SYNTAX CompPerBrowRuleStatsEntry 
   MAX-ACCESS not-accessible
   STATUS  current
   DESCRIPTION
       " The row definition for compression statistics per browser rule."
   INDEX  { compBrowRuleRuleListIndex, compBrowRuleIndex }
   ::= {compPerBrowRuleStatsTable 1}

CompPerBrowRuleStatsEntry  ::= SEQUENCE {
        compBrowRuleRuleListIndex               Integer32,
        compBrowRuleIndex                       Integer32,
        compBrowRuleRuleListId                  DisplayString,
        compBrowRuleNumOfObj                    Integer32,
        compBrowRuleSizeBefComp                 Integer32,
        compBrowRuleSizeAftComp                 Integer32,
        compBrowRuleCompRatio                   Integer32
        }

compBrowRuleRuleListIndex  OBJECT-TYPE
   SYNTAX  Integer32
   MAX-ACCESS  read-only
   STATUS  current
   DESCRIPTION
       "Compression browser rule rule-list index."
   ::= {compPerBrowRuleStatsEntry 1}

compBrowRuleIndex  OBJECT-TYPE
   SYNTAX  Integer32
   MAX-ACCESS  read-only
   STATUS  current
   DESCRIPTION
       "Compression browser rule index."
   ::= {compPerBrowRuleStatsEntry 2}

compBrowRuleRuleListId  OBJECT-TYPE
   SYNTAX  DisplayString
   MAX-ACCESS  read-only
   STATUS  current
   DESCRIPTION
       "Compression browser rule rule-list identifier."
   ::= {compPerBrowRuleStatsEntry 3}

compBrowRuleNumOfObj  OBJECT-TYPE
   SYNTAX  Integer32
   MAX-ACCESS  read-only
   STATUS  current
   DESCRIPTION
       "Number of objects matched by this browser rule during measuring period."
   ::= {compPerBrowRuleStatsEntry 4}

compBrowRuleSizeBefComp  OBJECT-TYPE
   SYNTAX  Integer32
   MAX-ACCESS  read-only
   STATUS  current
   DESCRIPTION
       "Total size of all matched objects for this browser rule before compression."
   ::= {compPerBrowRuleStatsEntry 5}

compBrowRuleSizeAftComp  OBJECT-TYPE
   SYNTAX  Integer32
   MAX-ACCESS  read-only
   STATUS  current
   DESCRIPTION
       "Total size of all matched objects for this browser rule after compression."
   ::= {compPerBrowRuleStatsEntry 6}

compBrowRuleCompRatio  OBJECT-TYPE
   SYNTAX  Integer32
   MAX-ACCESS  read-only
   STATUS  current
   DESCRIPTION
       "Compression ratio per browser rule."
   ::= {compPerBrowRuleStatsEntry 7}

compPerUrlRuleListStatsTable OBJECT-TYPE
   SYNTAX SEQUENCE OF CompPerUrlRuleListStatsEntry 
   MAX-ACCESS not-accessible
   STATUS current
   DESCRIPTION
       "A table for compression statistics per URL Rule list.
        Note:This mib is not supported for VX instance of Virtualization."
   ::= {compStats 10}

compPerUrlRuleListStatsEntry OBJECT-TYPE
   SYNTAX CompPerUrlRuleListStatsEntry
   MAX-ACCESS not-accessible
   STATUS  current
   DESCRIPTION
       " The row definition for this table."
   INDEX  { compUrlRuleListIndex }
   ::= {compPerUrlRuleListStatsTable 1}

CompPerUrlRuleListStatsEntry  ::= SEQUENCE {
        compUrlRuleListIndex                        Integer32,
        compUrlRuleListId                           DisplayString,
        compUrlRuleListNumOfObj                     Integer32,
        compUrlRuleListSizeBefComp                  Integer32,
        compUrlRuleListSizeAftComp                  Integer32,
        compUrlRuleListCompRatio                    Integer32
        }

compUrlRuleListIndex  OBJECT-TYPE
   SYNTAX  Integer32
   MAX-ACCESS  read-only
   STATUS  current
   DESCRIPTION
       "Compression url rule list index."
   ::= {compPerUrlRuleListStatsEntry 1}

compUrlRuleListId  OBJECT-TYPE
   SYNTAX  DisplayString
   MAX-ACCESS  read-only
   STATUS  current
   DESCRIPTION
       "Compression url rule list identifier."
   ::= {compPerUrlRuleListStatsEntry 2}

compUrlRuleListNumOfObj OBJECT-TYPE
   SYNTAX  Integer32
   MAX-ACCESS  read-only
   STATUS  current
   DESCRIPTION
       "Number of objects matched by this url rule list during measuring period."
   ::= {compPerUrlRuleListStatsEntry 3}

compUrlRuleListSizeBefComp  OBJECT-TYPE
   SYNTAX  Integer32
   MAX-ACCESS  read-only
   STATUS  current
   DESCRIPTION
       "Total size of all matched objects for this url rule list before compression."
   ::= {compPerUrlRuleListStatsEntry 4}

compUrlRuleListSizeAftComp  OBJECT-TYPE
   SYNTAX  Integer32
   MAX-ACCESS  read-only
   STATUS  current
   DESCRIPTION
       "Total size of all matched objects this url rule list after compression."
   ::= {compPerUrlRuleListStatsEntry 5}

compUrlRuleListCompRatio  OBJECT-TYPE
   SYNTAX  Integer32
   MAX-ACCESS  read-only
   STATUS  current
   DESCRIPTION
       "Compression ratio for this url rule list."
   ::= {compPerUrlRuleListStatsEntry 6}

compPerUrlRuleStatsTable OBJECT-TYPE
   SYNTAX SEQUENCE OF CompPerUrlRuleStatsEntry 
   MAX-ACCESS not-accessible
   STATUS current
   DESCRIPTION
       "A table for compression statistics per URL Rule.
        Note:This mib is not supported for VX instance of Virtualization."
   ::= {compStats 11}

compPerUrlRuleStatsEntry OBJECT-TYPE
   SYNTAX CompPerUrlRuleStatsEntry
   MAX-ACCESS not-accessible
   STATUS  current
   DESCRIPTION
       " The row definition for this table."
   INDEX  { compUrlRuleRuleListIndex, compUrlRuleIndex }
   ::= {compPerUrlRuleStatsTable 1}

CompPerUrlRuleStatsEntry  ::= SEQUENCE {
        compUrlRuleRuleListIndex               Integer32,
        compUrlRuleIndex                       Integer32,
        compUrlRuleRuleListId                  DisplayString,
        compUrlRuleNumOfObj                    Integer32,
        compUrlRuleSizeBefComp                 Integer32,
        compUrlRuleSizeAftComp                 Integer32,
        compUrlRuleCompRatio                   Integer32
        }

compUrlRuleRuleListIndex  OBJECT-TYPE
   SYNTAX  Integer32
   MAX-ACCESS  read-only
   STATUS  current
   DESCRIPTION
       "Compression url rule rule-list index."
   ::= {compPerUrlRuleStatsEntry 1}

compUrlRuleIndex  OBJECT-TYPE
   SYNTAX  Integer32
   MAX-ACCESS  read-only
   STATUS  current
   DESCRIPTION
       "Compression url rule index."
   ::= {compPerUrlRuleStatsEntry 2}

compUrlRuleRuleListId  OBJECT-TYPE
   SYNTAX  DisplayString
   MAX-ACCESS  read-only
   STATUS  current
   DESCRIPTION
       "Compression url rule rule-list identifier."
   ::= {compPerUrlRuleStatsEntry 3}

compUrlRuleNumOfObj OBJECT-TYPE
   SYNTAX  Integer32
   MAX-ACCESS  read-only
   STATUS  current
   DESCRIPTION
       "Number of objects matched by this url rule during measuring period."
   ::= {compPerUrlRuleStatsEntry 4}

compUrlRuleSizeBefComp  OBJECT-TYPE
   SYNTAX  Integer32
   MAX-ACCESS  read-only
   STATUS  current
   DESCRIPTION
       "Total size of all matched objects for this url rule before compression."
   ::= {compPerUrlRuleStatsEntry 5}

compUrlRuleSizeAftComp  OBJECT-TYPE
   SYNTAX  Integer32
   MAX-ACCESS  read-only
   STATUS  current
   DESCRIPTION
       "Total size of all matched objects for this url rule after compression."
   ::= {compPerUrlRuleStatsEntry 6}

compUrlRuleCompRatio  OBJECT-TYPE
   SYNTAX  Integer32
   MAX-ACCESS  read-only
   STATUS  current
   DESCRIPTION
       "Compression ratio for this url rule."
   ::= {compPerUrlRuleStatsEntry 7}

sslOffNewHandShake OBJECT-TYPE
   SYNTAX  Integer32 
   MAX-ACCESS  read-only
   STATUS  current
   DESCRIPTION
       "Number of new SSL handshakes between clients and AAS per second.
        Note:This mib is not supported for VX instance of Virtualization."
   ::= {sslSlbStats 11}

sslOffReusedHandShake OBJECT-TYPE
   SYNTAX  Integer32 
   MAX-ACCESS  read-only
   STATUS  current
   DESCRIPTION
       "Number of existing SSL handshakes reused by clients to communicate with AAS per second.
        Note:This mib is not supported for VX instance of Virtualization."
   ::= {sslSlbStats 12}

sslOffPerReusedHandShake OBJECT-TYPE
   SYNTAX  Integer32 
   MAX-ACCESS  read-only
   STATUS  current
   DESCRIPTION
       "Percentage of SSL session re-using keys.
        Note:This mib is not supported for VX instance of Virtualization."
   ::= {sslSlbStats 13}

sslOffPercSessUsingSSLv2 OBJECT-TYPE
   SYNTAX  Integer32 
   MAX-ACCESS  read-only
   STATUS  current
   DESCRIPTION
       "Percentage of session using SSLv2 out of all session during measuring period.
        Note:This mib is not supported for VX instance of Virtualization."
   ::= {sslSlbStats 14}

sslOffPercSessUsingSSLv3 OBJECT-TYPE
   SYNTAX  INTEGER
   MAX-ACCESS  read-only
   STATUS  current
   DESCRIPTION
       "Percentage of session using SSLv3 out of all session during measuring period.
        Note:This mib is not supported for VX instance of Virtualization."
   ::= {sslSlbStats 15}

sslOffPercSessUsingTLS OBJECT-TYPE
   SYNTAX  INTEGER
   MAX-ACCESS  read-only
   STATUS  current
   DESCRIPTION
       "Percentage of session using TLS1.0 out of all session during measuring period.
        Note:This mib is not supported for VX instance of Virtualization."
   ::= {sslSlbStats 16}

--Dont remoive this placeholder. Actual definition 500 lines below
--sslOffPerServStatsTable OBJECT-TYPE 
--  SYNTAX SEQUENCE OF SslOffPerServStatsEntry
--   MAX-ACCESS not-accessible
--   STATUS current
--   DESCRIPTION
--       "A table for SSL statistics per virtual service."
--   ::= {sslSlbStats 17}

sslOffPercSessUsingTLS11 OBJECT-TYPE
   SYNTAX  INTEGER
   MAX-ACCESS  read-only
   STATUS  current
   DESCRIPTION
       "Percentage of session using TLS1.1 out of all session during measuring period.
        Note:This mib is not supported for VX instance of Virtualization."
   ::= {sslSlbStats 18}
      
sslOffPercSessUsingTLS12 OBJECT-TYPE
   SYNTAX  INTEGER
   MAX-ACCESS  read-only
   STATUS  current
   DESCRIPTION
       "Percentage of session using TLS1.2 out of all session during measuring period.
        Note:This mib is not supported for VX instance of Virtualization."
   ::= {sslSlbStats 19}

--Dont remoive this placeholder. Actual definition 500 lines below
--sslOffPerEnhServStatsTable OBJECT-TYPE
--   SYNTAX SEQUENCE OF SslOffPerEnhServStatsEntry
--   MAX-ACCESS not-accessible
--   STATUS current
--   DESCRIPTION
--       "A table for SSL statistics per virtual service."
--   ::= {sslSlbStats 20}

sslOffPerRejectedHandShake OBJECT-TYPE
   SYNTAX  Integer32 
   MAX-ACCESS  read-only
   STATUS  current
   DESCRIPTION
       "SSL rejected handshakes session per second.
        Note:This mib is not supported for VX instance of Virtualization."
   ::= {sslSlbStats 21}

--Dont remoive this placeholder. Actual definition 500 lines below
--sslOffPerFilterStatsTable OBJECT-TYPE
--   SYNTAX SEQUENCE OF SslOffPerFilterStatsEntry
--   MAX-ACCESS not-accessible
--   STATUS current
--   DESCRIPTION
--       "A table for SSL statistics per filter."
--   ::= {sslSlbStats 22}
         
sslOffByCipherHandShake  OBJECT-TYPE
    SYNTAX RadwareLongDisplayString (SIZE (0..10000))
    MAX-ACCESS  read-only
    STATUS  current
    DESCRIPTION
        "Session distribution by cipher (in second).
         Note:This mib is not supported for VX instance of Virtualization."
   ::= {sslSlbStats 23}

sslOffPerRejectedCertificates OBJECT-TYPE
   SYNTAX  Integer32 
   MAX-ACCESS  read-only
   STATUS  current
   DESCRIPTION
       "Obsolete Mib!
        Note:This mib is not supported for VX instance of Virtualization."
   ::= {sslSlbStats 25}

sslOffPerIgnoredCertificates OBJECT-TYPE
   SYNTAX  Integer32 
   MAX-ACCESS  read-only
   STATUS  current
   DESCRIPTION
       "Obsolete Mib!
        Note:This mib is not supported for VX instance of Virtualization."
   ::= {sslSlbStats 26}

sslOffPerExpiredCertificates OBJECT-TYPE
   SYNTAX  Integer32 
   MAX-ACCESS  read-only
   STATUS  current
   DESCRIPTION
       "Obsolete Mib!
        Note:This mib is not supported for VX instance of Virtualization."
   ::= {sslSlbStats 27}

sslOffPerUntrustedCertificates OBJECT-TYPE
   SYNTAX  Integer32 
   MAX-ACCESS  read-only
   STATUS  current
   DESCRIPTION
       "Obsolete Mib!
        Note:This mib is not supported for VX instance of Virtualization."
   ::= {sslSlbStats 28}

sslOffPerCertificateHostnameMismatches OBJECT-TYPE
   SYNTAX  Integer32 
   MAX-ACCESS  read-only
   STATUS  current
   DESCRIPTION
       "Obsolete Mib!
        Note:This mib is not supported for VX instance of Virtualization."
   ::= {sslSlbStats 29}

sslDynamicCertCacheHealth OBJECT-TYPE
   SYNTAX   INTEGER 
   MAX-ACCESS  read-only
   STATUS  current
   DESCRIPTION
       "SSL dynamic certificate cache health.
        Note:This mib is not supported for VX instance of Virtualization."
   ::= {sslSlbStats 30}

sslDynamicCertCacheCurrentHitRate OBJECT-TYPE
   SYNTAX   INTEGER 
   MAX-ACCESS  read-only
   STATUS  current
   DESCRIPTION
       "SSL dynamic certificate cache current hit rate.
        Note:This mib is not supported for VX instance of Virtualization."
   ::= {sslSlbStats 31}

sslDynamicCertCacheTotalHitRate OBJECT-TYPE
   SYNTAX   INTEGER 
   MAX-ACCESS  read-only
   STATUS  current
   DESCRIPTION
       "SSL dynamic certificate cache total hit rate.
        Note:This mib is not supported for VX instance of Virtualization."
   ::= {sslSlbStats 32}

sslDynamicCertCacheCurrentCertificates OBJECT-TYPE
   SYNTAX   INTEGER 
   MAX-ACCESS  read-only
   STATUS  current
   DESCRIPTION
       "The number of certificates currently in the dynamic certificate cache.
        Note:This mib is not supported for VX instance of Virtualization."
   ::= {sslSlbStats 33}

sslDynamicCertCacheDeletedCertificates OBJECT-TYPE
   SYNTAX   INTEGER 
   MAX-ACCESS  read-only
   STATUS  current
   DESCRIPTION
       "The number of certificates deleted due to cache threshold or certpurg.
        Note:This mib is not supported for VX instance of Virtualization."
   ::= {sslSlbStats 34}

sslDynamicCertCacheAgedCertificates OBJECT-TYPE
   SYNTAX   INTEGER 
   MAX-ACCESS  read-only
   STATUS  current
   DESCRIPTION
       "The number of certificates deleted due to 24 hours aging limit.
        Note:This mib is not supported for VX instance of Virtualization."
   ::= {sslSlbStats 35}

sslDynamicCertCacheUsage OBJECT-TYPE
   SYNTAX   INTEGER 
   MAX-ACCESS  read-only
   STATUS  current
   DESCRIPTION
       "The precentage of currently used cache.
        Note:This mib is not supported for VX instance of Virtualization."
   ::= {sslSlbStats 36}
   
   sslOffPercSessUsingTLS13 OBJECT-TYPE
   SYNTAX  INTEGER
   MAX-ACCESS  read-only
   STATUS  current
   DESCRIPTION
       "Percentage of session using TLS1.3 out of all session during measuring period.
        Note:This mib is not supported for VX instance of Virtualization."
    ::= {sslSlbStats 37}   

sslOff0RTTReusedHandShake OBJECT-TYPE
   SYNTAX  Integer32 
   MAX-ACCESS  read-only
   STATUS  current
   DESCRIPTION
       "Number of existing SSL handshakes reused by clients to communicate with AAS per second (0-RTT).
        Note:This mib is not supported for VX instance of Virtualization."
   ::= {sslSlbStats 38}

sslOffPer0RTTReusedHandShake OBJECT-TYPE
   SYNTAX  Integer32 
   MAX-ACCESS  read-only
   STATUS  current
   DESCRIPTION
       "Percentage of SSL session re-using keys (0-RTT).
        Note:This mib is not supported for VX instance of Virtualization."
   ::= {sslSlbStats 39}

 sslOff0RTTRejectedHandShake OBJECT-TYPE
   SYNTAX  Integer32
   MAX-ACCESS  read-only
   STATUS  current
   DESCRIPTION
       "Number of rejected SSL handshakes per second (0-RTT).
        Note:This mib is not supported for VX instance of Virtualization."
   ::= {sslSlbStats 40}

sslOff0RTTNonExpiredTicketDeletions OBJECT-TYPE
   SYNTAX  Integer32
   MAX-ACCESS  read-only
   STATUS  current
   DESCRIPTION
       "Number of non-expired ticket deletions percentage per second (0-RTT).
        Note:This mib is not supported for VX instance of Virtualization."
   ::= {sslSlbStats 41}

   sslOffBeNewHandShake OBJECT-TYPE
   SYNTAX  Integer32 
   MAX-ACCESS  read-only
   STATUS  current
   DESCRIPTION
       "Number of new SSL handshakes between servers and AAS per second.
        Note:This mib is not supported for VX instance of Virtualization."
   ::= {sslSlbStats 42}
   
   sslOffBeReusedHandShake OBJECT-TYPE
   SYNTAX  Integer32 
   MAX-ACCESS  read-only
   STATUS  current
   DESCRIPTION
       "Number of existing SSL handshakes reused by servers to communicate with AAS per second.
        Note:This mib is not supported for VX instance of Virtualization."
   ::= {sslSlbStats 43}
   
   sslOffBePerReusedHandShake OBJECT-TYPE
   SYNTAX  Integer32 
   MAX-ACCESS  read-only
   STATUS  current
   DESCRIPTION
       "Percentage of SSL session re-using keys.
        Note:This mib is not supported for VX instance of Virtualization."
   ::= {sslSlbStats 44}
   
   sslOffBePerRejectedHandShake OBJECT-TYPE
   SYNTAX  Integer32 
   MAX-ACCESS  read-only
   STATUS  current
   DESCRIPTION
       "SSL rejected handshakes session per second.
        Note:This mib is not supported for VX instance of Virtualization."
   ::= {sslSlbStats 45}
   
   sslOffBePercSessUsingSSLv3 OBJECT-TYPE
   SYNTAX  INTEGER
   MAX-ACCESS  read-only
   STATUS  current
   DESCRIPTION
       "Percentage of session using SSLv3 out of all session during measuring period.
        Note:This mib is not supported for VX instance of Virtualization."
   ::= {sslSlbStats 46}
   
   sslOffBePercSessUsingTLS OBJECT-TYPE
   SYNTAX  INTEGER
   MAX-ACCESS  read-only
   STATUS  current
   DESCRIPTION
       "Percentage of session using TLS1.0 out of all session during measuring period.
        Note:This mib is not supported for VX instance of Virtualization."
   ::= {sslSlbStats 47}
   
   sslOffBePercSessUsingTLS13 OBJECT-TYPE
   SYNTAX  INTEGER
   MAX-ACCESS  read-only
   STATUS  current
   DESCRIPTION
       "Percentage of session using TLS1.3 out of all session during measuring period.
        Note:This mib is not supported for VX instance of Virtualization."
   ::= {sslSlbStats 48}
   
   sslOffBePercSessUsingTLS11 OBJECT-TYPE
   SYNTAX  INTEGER
   MAX-ACCESS  read-only
   STATUS  current
   DESCRIPTION
       "Percentage of session using TLS1.1 out of all session during measuring period.
        Note:This mib is not supported for VX instance of Virtualization."
   ::= {sslSlbStats 49}
   
   sslOffBePercSessUsingTLS12 OBJECT-TYPE
   SYNTAX  INTEGER
   MAX-ACCESS  read-only
   STATUS  current
   DESCRIPTION
       "Percentage of session using TLS1.2 out of all session during measuring period.
        Note:This mib is not supported for VX instance of Virtualization."
   ::= {sslSlbStats 50}
   
   sslOffNewHandShakeTotal OBJECT-TYPE
   SYNTAX  Integer32 
   MAX-ACCESS  read-only
   STATUS  current
   DESCRIPTION
       "Number of total SSL handshakes between clients and AAS since last reset.
        Note:This mib is not supported for VX instance of Virtualization."
   ::= {sslSlbStats 51}
   
   sslOffBeNewHandShakeTotal OBJECT-TYPE
   SYNTAX  Integer32 
   MAX-ACCESS  read-only
   STATUS  current
   DESCRIPTION
       "Number of total SSL handshakes between servers and AAS since last reset.
        Note:This mib is not supported for VX instance of Virtualization."
   ::= {sslSlbStats 52}
   
   sslOffReusedHandShakeTotal OBJECT-TYPE
   SYNTAX  Integer32 
   MAX-ACCESS  read-only
   STATUS  current
   DESCRIPTION
       "Number of existing SSL handshakes reused by clients to communicate with AAS since last reset.
        Note:This mib is not supported for VX instance of Virtualization."
   ::= {sslSlbStats 53}
   
   sslOffBeReusedHandShakeTotal OBJECT-TYPE
   SYNTAX  Integer32 
   MAX-ACCESS  read-only
   STATUS  current
   DESCRIPTION
       "Number of existing SSL handshakes reused by servers since last reset.
        Note:This mib is not supported for VX instance of Virtualization."
   ::= {sslSlbStats 54}
   
   sslOffPerReusedHandShakeTotal OBJECT-TYPE
   SYNTAX  Integer32 
   MAX-ACCESS  read-only
   STATUS  current
   DESCRIPTION
       "Total number of SSL session re-using keys.
        Note:This mib is not supported for VX instance of Virtualization."
   ::= {sslSlbStats 55}
   
   sslOffBePerReusedHandShakeTotal OBJECT-TYPE
   SYNTAX  Integer32 
   MAX-ACCESS  read-only
   STATUS  current
   DESCRIPTION
       "Total number of SSL session re-using keys.
        Note:This mib is not supported for VX instance of Virtualization."
   ::= {sslSlbStats 56}
   
   sslOffPerRejectedHandShakeTotal OBJECT-TYPE
   SYNTAX  Integer32 
   MAX-ACCESS  read-only
   STATUS  current
   DESCRIPTION
       "SSL rejected handshakes session since last reset.
        Note:This mib is not supported for VX instance of Virtualization."
   ::= {sslSlbStats 57}
   
   sslOffBePerRejectedHandShakeTotal OBJECT-TYPE
   SYNTAX  Integer32 
   MAX-ACCESS  read-only
   STATUS  current
   DESCRIPTION
       "SSL rejected handshakes session since last reset.
        Note:This mib is not supported for VX instance of Virtualization."
   ::= {sslSlbStats 58}
   
   sslOffPercSessUsingSSLv3Total OBJECT-TYPE
   SYNTAX  INTEGER
   MAX-ACCESS  read-only
   STATUS  current
   DESCRIPTION
       "Percentage of session using SSLv3 out of all session since last reset.
        Note:This mib is not supported for VX instance of Virtualization."
   ::= {sslSlbStats 59}
   
   sslOffBePercSessUsingSSLv3Total OBJECT-TYPE
   SYNTAX  INTEGER
   MAX-ACCESS  read-only
   STATUS  current
   DESCRIPTION
       "Percentage of session using SSLv3 out of all session since last reset.
        Note:This mib is not supported for VX instance of Virtualization."
   ::= {sslSlbStats 60}
   
   sslOffPercSessUsingTLSTotal OBJECT-TYPE
   SYNTAX  INTEGER
   MAX-ACCESS  read-only
   STATUS  current
   DESCRIPTION
       "Percentage of session using TLS1.0 out of all session since last reset.
        Note:This mib is not supported for VX instance of Virtualization."
   ::= {sslSlbStats 61}
   
   sslOffBePercSessUsingTLSTotal OBJECT-TYPE
   SYNTAX  INTEGER
   MAX-ACCESS  read-only
   STATUS  current
   DESCRIPTION
       "Percentage of session using TLS1.0 out of all session since last reset.
        Note:This mib is not supported for VX instance of Virtualization."
   ::= {sslSlbStats 62}
   
   sslOffPercSessUsingTLS11Total OBJECT-TYPE
   SYNTAX  INTEGER
   MAX-ACCESS  read-only
   STATUS  current
   DESCRIPTION
       "Percentage of session using TLS1.1 out of all session since last reset.
        Note:This mib is not supported for VX instance of Virtualization."
   ::= {sslSlbStats 63}
   
   sslOffBePercSessUsingTLS11Total OBJECT-TYPE
   SYNTAX  INTEGER
   MAX-ACCESS  read-only
   STATUS  current
   DESCRIPTION
       "Percentage of session using TLS1.1 out of all session since last reset.
        Note:This mib is not supported for VX instance of Virtualization."
   ::= {sslSlbStats 64}
   
   sslOffPercSessUsingTLS12Total OBJECT-TYPE
   SYNTAX  INTEGER
   MAX-ACCESS  read-only
   STATUS  current
   DESCRIPTION
       "Percentage of session using TLS1.2 out of all session since last reset.
        Note:This mib is not supported for VX instance of Virtualization."
   ::= {sslSlbStats 65}
   
   sslOffBePercSessUsingTLS12Total OBJECT-TYPE
   SYNTAX  INTEGER
   MAX-ACCESS  read-only
   STATUS  current
   DESCRIPTION
       "Percentage of session using TLS1.2 out of all session since last reset.
        Note:This mib is not supported for VX instance of Virtualization."
   ::= {sslSlbStats 66}
   
   sslOffPercSessUsingTLS13Total OBJECT-TYPE
   SYNTAX  INTEGER
   MAX-ACCESS  read-only
   STATUS  current
   DESCRIPTION
       "Percentage of session using TLS1.3 out of all session since last reset.
        Note:This mib is not supported for VX instance of Virtualization."
   ::= {sslSlbStats 67}
   
   sslOffBePercSessUsingTLS13Total OBJECT-TYPE
   SYNTAX  INTEGER
   MAX-ACCESS  read-only
   STATUS  current
   DESCRIPTION
       "Percentage of session using TLS1.3 out of all session since last reset.
        Note:This mib is not supported for VX instance of Virtualization."
   ::= {sslSlbStats 68}

sslOff0RTTReusedHandShakeTotal OBJECT-TYPE
   SYNTAX  Integer32
   MAX-ACCESS  read-only
   STATUS  current
   DESCRIPTION
       "Number of existing SSL handshakes reused by clients to communicate with AAS (0-RTT) since last reset.
        Note:This mib is not supported for VX instance of Virtualization."
   ::= {sslSlbStats 69}

sslOffPer0RTTReusedHandShakeTotal OBJECT-TYPE
   SYNTAX  Integer32
   MAX-ACCESS  read-only
   STATUS  current
   DESCRIPTION
       "Percentage of SSL session re-using keys (0-RTT) since last reset.
        Note:This mib is not supported for VX instance of Virtualization."
   ::= {sslSlbStats 70}

sslOff0RTTRejectedHandShakeTotal OBJECT-TYPE
   SYNTAX  Integer32
   MAX-ACCESS  read-only
   STATUS  current
   DESCRIPTION
       "Number of rejected SSL handshakes (0-RTT) since last reset.
        Note:This mib is not supported for VX instance of Virtualization."
   ::= {sslSlbStats 71}

sslOff0RTTNonExpiredTicketDeletionsTotal OBJECT-TYPE
   SYNTAX  Integer32
   MAX-ACCESS  read-only
   STATUS  current
   DESCRIPTION
       "Number of non-expired ticket deletions percentage (0-RTT) since last reset.
        Note:This mib is not supported for VX instance of Virtualization."
   ::= {sslSlbStats 72}

--Dont remove this placeholder. Actual definition is 500 lines below
--sslOffPerFilterCipherHandShakeStatsTable OBJECT-TYPE
--   SYNTAX SEQUENCE OF SslOffPerFilterCipherHandShakeStatsEntry
--   MAX-ACCESS not-accessible
--   STATUS current
--   DESCRIPTION
--       "A table for frontend SSL Cipher hand shake current and total statistics per filter."
--   ::= {sslSlbStats 73}

--Dont remove this placeholder. Actual definition is 500 lines below
--sslBeOffPerFilterCipherHandShakeStatsTable OBJECT-TYPE
--   SYNTAX SEQUENCE OF SslBeOffPerFilterCipherHandShakeStatsEntry
--   MAX-ACCESS not-accessible
--   STATUS current
--   DESCRIPTION
--       "A table for backend SSL Cipher hand shake current and total statistics per filter."
--   ::= {sslSlbStats 74}

--Dont remove this placeholder. Actual definition is 500 lines below
--sslBeOffPerCiphServStatsTable OBJECT-TYPE	
--   SYNTAX SEQUENCE OF SslBeOffPerCiphServStatsEntry	
--   MAX-ACCESS not-accessible	
--   STATUS current	
--   DESCRIPTION	
--       "A table for backend SSL statistics per virtual service."
--   ::= {sslSlbStats 75}

--Dont remove this placeholder. Actual definition is 500 lines below
--sslOffPerFilterRejHsReasonsStatsTable OBJECT-TYPE
--   SYNTAX SEQUENCE OF SslOffPerFilterRejHsReasonsStatsEntry
--   MAX-ACCESS not-accessible
--   STATUS current
--   DESCRIPTION
--       "A table for frontend SSL Rejected hand shake reasons current and total statistics per filter."
--  ::= {sslSlbStats 76}

--Dont remove this placeholder. Actual definition is 500 lines below
--sslBeOffPerFilterRejHsReasonsStatsTable OBJECT-TYPE
--   SYNTAX SEQUENCE OF SslBeOffPerFilterRejHsReasonsStatsEntry
--   MAX-ACCESS not-accessible
--   STATUS current
--   DESCRIPTION
--       "A table for backend SSL Rejected hand shake reasons current and total statistics per filter."
--   ::= {sslSlbStats 77}

--Dont remove this placeholder. Actual definition is 500 lines below
--sslOffPerServRejHsReasonsStatsTable OBJECT-TYPE
--   SYNTAX SEQUENCE OF SslOffPerServRejHsReasonsStatsEntry
--  MAX-ACCESS not-accessible
--   STATUS current
--   DESCRIPTION
--      "A table for frontend SSL Rejected hand shake reasons current and total statistics per service."
--   ::= {sslSlbStats 78}

--Dont remove this placeholder. Actual definition is 500 lines below
--sslBeOffPerServRejHsReasonsStatsTable OBJECT-TYPE
--   SYNTAX SEQUENCE OF SslBeOffPerServRejHsReasonsStatsEntry
--   MAX-ACCESS not-accessible
--   STATUS current
--   DESCRIPTION
--       "A table for backend SSL Rejected hand shake reasons current and total statistics per service."
--   ::= {sslSlbStats 79}
   

sslOffTicketKeysExpiredKeysRate OBJECT-TYPE
   SYNTAX  Integer32
   MAX-ACCESS  read-only
   STATUS  current
   DESCRIPTION
       "Number of expired ticket keys since last reset.
        Note:This mib is not supported for VX instance of Virtualization."
   ::= {sslSlbStats 80}

sslOffTicketKeysUnknownKeysRate OBJECT-TYPE
   SYNTAX  Integer32
   MAX-ACCESS  read-only
   STATUS  current
   DESCRIPTION
       "Number of unknown ticket keys since last reset.
        Note:This mib is not supported for VX instance of Virtualization."
   ::= {sslSlbStats 81}

sslOffTicketKeysExpiredKeysTotal OBJECT-TYPE
   SYNTAX  Integer32
   MAX-ACCESS  read-only
   STATUS  current
   DESCRIPTION
       "Number of expired ticket keys during measuring period.
        Note:This mib is not supported for VX instance of Virtualization."
   ::= {sslSlbStats 82}

sslOffTicketKeysUnknownKeysTotal OBJECT-TYPE
   SYNTAX  Integer32
   MAX-ACCESS  read-only
   STATUS  current
   DESCRIPTION
       "Number of unknown ticket keys during measuring period.
        Note:This mib is not supported for VX instance of Virtualization."
   ::= {sslSlbStats 83}
  
sslFipsTotalSSLContexts OBJECT-TYPE
   SYNTAX Integer32
   MAX-ACCESS read-only
   STATUS current
   DESCRIPTION
       "get the total contexts in the fips card.
        Note:This mib is not supported for VX instance of Virtualization."
   ::= {sslSlbStats 84}

sslFipsAvailableSSLContexts OBJECT-TYPE
   SYNTAX Integer32
   MAX-ACCESS read-only
   STATUS current
   DESCRIPTION
       "get the available contexts in the fips card right now.
        Note:This mib is not supported for VX instance of Virtualization."
   ::= {sslSlbStats 85}

sslOffSessionIdReusedHandShake OBJECT-TYPE
   SYNTAX  Integer32
   MAX-ACCESS  read-only
   STATUS  current
   DESCRIPTION
       "Number of existing SSL handshakes Session Id reused by clients to communicate with AAS per second.
        Note:This mib is not supported for VX instance of Virtualization."
   ::= {sslSlbStats 86}

sslOffPerSessionIdReusedHandShake OBJECT-TYPE
   SYNTAX  Integer32
   MAX-ACCESS  read-only
   STATUS  current
   DESCRIPTION
       "Percentage of SSL session Id re-using keys.
        Note:This mib is not supported for VX instance of Virtualization."
   ::= {sslSlbStats 87}

sslOffBeSessionIdReusedHandShake OBJECT-TYPE
   SYNTAX  Integer32
   MAX-ACCESS  read-only
   STATUS  current
   DESCRIPTION
       "Number of existing SSL handshakes Session Id reused by servers to communicate with AAS per second.
        Note:This mib is not supported for VX instance of Virtualization."
   ::= {sslSlbStats 88}

sslOffBePerSessionIdReusedHandShake OBJECT-TYPE
   SYNTAX  Integer32
   MAX-ACCESS  read-only
   STATUS  current
   DESCRIPTION
       "Percentage of SSL session Id re-using keys.
        Note:This mib is not supported for VX instance of Virtualization."
   ::= {sslSlbStats 89}

sslOffSessionIdReusedHandShakeTotal OBJECT-TYPE
   SYNTAX  Integer32
   MAX-ACCESS  read-only
   STATUS  current
   DESCRIPTION
       "Number of existing SSL handshakes Session Id reused by clients to communicate with AAS since last reset.
        Note:This mib is not supported for VX instance of Virtualization."
   ::= {sslSlbStats 90}

sslOffBeSessionIdReusedHandShakeTotal OBJECT-TYPE
   SYNTAX  Integer32
   MAX-ACCESS  read-only
   STATUS  current
   DESCRIPTION
       "Number of existing SSL handshakes Session Id reused by servers since last reset.
        Note:This mib is not supported for VX instance of Virtualization."
   ::= {sslSlbStats 91}

sslOffPerSessionIdReusedHandShakeTotal OBJECT-TYPE
   SYNTAX  Integer32
   MAX-ACCESS  read-only
   STATUS  current
   DESCRIPTION
       "Total number of SSL session Id re-using keys.
        Note:This mib is not supported for VX instance of Virtualization."
   ::= {sslSlbStats 92}

sslOffBePerSessionIdReusedHandShakeTotal OBJECT-TYPE
   SYNTAX  Integer32
   MAX-ACCESS  read-only
   STATUS  current
   DESCRIPTION
       "Total number of SSL session Id re-using keys.
        Note:This mib is not supported for VX instance of Virtualization."
   ::= {sslSlbStats 93}

sslOffTicketReusedHandShake OBJECT-TYPE
   SYNTAX  Integer32
   MAX-ACCESS  read-only
   STATUS  current
   DESCRIPTION
       "Number of existing SSL handshakes Ticket reused by clients to communicate with AAS per second.
        Note:This mib is not supported for VX instance of Virtualization."
   ::= {sslSlbStats 94}

sslOffPerTicketReusedHandShake OBJECT-TYPE
   SYNTAX  Integer32
   MAX-ACCESS  read-only
   STATUS  current
   DESCRIPTION
       "Percentage of SSL session Ticket re-using keys.
        Note:This mib is not supported for VX instance of Virtualization."
   ::= {sslSlbStats 95}

sslOffBeTicketReusedHandShake OBJECT-TYPE
   SYNTAX  Integer32
   MAX-ACCESS  read-only
   STATUS  current
   DESCRIPTION
       "Number of existing SSL handshakes Ticket reused by servers to communicate with AAS per second.
        Note:This mib is not supported for VX instance of Virtualization."
   ::= {sslSlbStats 96}

sslOffBePerTicketReusedHandShake OBJECT-TYPE
   SYNTAX  Integer32
   MAX-ACCESS  read-only
   STATUS  current
   DESCRIPTION
       "Percentage of SSL session Ticket re-using keys.
        Note:This mib is not supported for VX instance of Virtualization."
   ::= {sslSlbStats 97}

sslOffTicketReusedHandShakeTotal OBJECT-TYPE
   SYNTAX  Integer32
   MAX-ACCESS  read-only
   STATUS  current
   DESCRIPTION
       "Number of existing SSL handshakes Ticket reused by clients to communicate with AAS since last reset.
        Note:This mib is not supported for VX instance of Virtualization."
   ::= {sslSlbStats 98}

sslOffBeTicketReusedHandShakeTotal OBJECT-TYPE
   SYNTAX  Integer32
   MAX-ACCESS  read-only
   STATUS  current
   DESCRIPTION
       "Number of existing SSL handshakes Ticket reused by servers since last reset.
        Note:This mib is not supported for VX instance of Virtualization."
   ::= {sslSlbStats 99}

sslOffPerTicketReusedHandShakeTotal OBJECT-TYPE
   SYNTAX  Integer32
   MAX-ACCESS  read-only
   STATUS  current
   DESCRIPTION
       "Total number of SSL session Ticket re-using keys.
        Note:This mib is not supported for VX instance of Virtualization."
   ::= {sslSlbStats 100}

sslOffBePerTicketReusedHandShakeTotal OBJECT-TYPE
   SYNTAX  Integer32
   MAX-ACCESS  read-only
   STATUS  current
   DESCRIPTION
       "Total number of SSL session Ticket re-using keys.
        Note:This mib is not supported for VX instance of Virtualization."
   ::= {sslSlbStats 101}

sslOffRejectedHsExpiredCerts OBJECT-TYPE
   SYNTAX  Integer32 
   MAX-ACCESS  read-only
   STATUS  current
   DESCRIPTION
       "SSL rejected expired handshakes sessions per second.
        Note:This mib is not supported for VX instance of Virtualization."
   ::= {sslSlbStats 104}

sslOffRejectedHsUntrustedCerts OBJECT-TYPE
   SYNTAX  Integer32 
   MAX-ACCESS  read-only
   STATUS  current
   DESCRIPTION
       "SSL rejected untrusted handshakes sessions per second.
        Note:This mib is not supported for VX instance of Virtualization."
   ::= {sslSlbStats 105}

sslOffRejectedHsHostnameMismatchCerts OBJECT-TYPE
   SYNTAX  Integer32 
   MAX-ACCESS  read-only
   STATUS  current
   DESCRIPTION
       "SSL rejected hostname mismatch handshakes sessions per second.
        Note:This mib is not supported for VX instance of Virtualization."
   ::= {sslSlbStats 106}

sslOffIgnoredCertsExpired OBJECT-TYPE
   SYNTAX  Integer32 
   MAX-ACCESS  read-only
   STATUS  current
   DESCRIPTION
       "SSL ignored expired certs per second.
        Note:This mib is not supported for VX instance of Virtualization."
   ::= {sslSlbStats 107}

sslOffIgnoredCertsUntrusted OBJECT-TYPE
   SYNTAX  Integer32 
   MAX-ACCESS  read-only
   STATUS  current
   DESCRIPTION
       "SSL ignored untrusted certs per second.
        Note:This mib is not supported for VX instance of Virtualization."
   ::= {sslSlbStats 108}
   
sslOffIgnoredCertsHostnameMismatch OBJECT-TYPE
   SYNTAX  Integer32 
   MAX-ACCESS  read-only
   STATUS  current
   DESCRIPTION
       "SSL ignored hostname mismatch handshakes certs per second.
        Note:This mib is not supported for VX instance of Virtualization."
   ::= {sslSlbStats 109}   

sslOffRejectedHsExpiredCertsTotal OBJECT-TYPE
   SYNTAX  Integer32 
   MAX-ACCESS  read-only
   STATUS  current
   DESCRIPTION
       "SSL total rejected expired handshakes sessions per second.
        Note:This mib is not supported for VX instance of Virtualization."
   ::= {sslSlbStats 110}

sslOffRejectedHsUntrustedCertsTotal OBJECT-TYPE
   SYNTAX  Integer32 
   MAX-ACCESS  read-only
   STATUS  current
   DESCRIPTION
       "SSL total rejected untrusted handshakes sessions per second.
        Note:This mib is not supported for VX instance of Virtualization."
   ::= {sslSlbStats 111}

sslOffRejectedHsHostnameMismatchCertsTotal OBJECT-TYPE
   SYNTAX  Integer32 
   MAX-ACCESS  read-only
   STATUS  current
   DESCRIPTION
       "SSL total rejected hostname mismatch handshakes sessions per second.
        Note:This mib is not supported for VX instance of Virtualization."
   ::= {sslSlbStats 112}

sslOffIgnoredCertsExpiredTotal OBJECT-TYPE
   SYNTAX  Integer32 
   MAX-ACCESS  read-only
   STATUS  current
   DESCRIPTION
       "SSL total ignored untrusted certs per second.
        Note:This mib is not supported for VX instance of Virtualization."
   ::= {sslSlbStats 113}

sslOffIgnoredCertsUntrustedTotal OBJECT-TYPE
   SYNTAX  Integer32 
   MAX-ACCESS  read-only
   STATUS  current
   DESCRIPTION
       "SSL total ignored untrusted certs per second.
        Note:This mib is not supported for VX instance of Virtualization."
   ::= {sslSlbStats 114}
   
sslOffIgnoredCertsHostnameMismatchTotal OBJECT-TYPE
   SYNTAX  Integer32 
   MAX-ACCESS  read-only
   STATUS  current
   DESCRIPTION
       "SSL total ignored hostname mismatch handshakes certs per second.
        Note:This mib is not supported for VX instance of Virtualization."
   ::= {sslSlbStats 115}

sslOffPerServStatsTable OBJECT-TYPE
   SYNTAX SEQUENCE OF SslOffPerServStatsEntry
   MAX-ACCESS not-accessible
   STATUS current
   DESCRIPTION
       "A table for SSL statistics per virtual service.
        Note:This mib is not supported for VX instance of Virtualization."
   ::= {sslSlbStats 17}
   
sslOffPerServStatsEntry OBJECT-TYPE
   SYNTAX SslOffPerServStatsEntry
   MAX-ACCESS not-accessible
   STATUS  current
   DESCRIPTION
       " The row definition for SSL statistics per virtual service table."
   INDEX  { sslOffPerServVirtServIndex, sslOffPerServVirtServiceIndex}
   ::= {sslOffPerServStatsTable 1}

SslOffPerServStatsEntry  ::= SEQUENCE {
        sslOffPerServVirtServIndex                  Integer32,
        sslOffPerServVirtServiceIndex               Integer32,
        sslOffPerServVirtServPort                   Integer32,
        sslOffPerServSslPolId                       DisplayString,
        sslOffPerServNewhandShake                   Integer32,
        sslOffPerServReusedhandShake                Integer32,
        sslOffPerServPercReusedhandShake            Integer32,
        sslOffPerServSessUsingSSLv2                 Integer32,
        sslOffPerServSessUsingSSLv3                 Integer32,
        sslOffPerServSessUsingTLS                   Integer32,
        sslOffPerServSessUsingTLS11                 Integer32,
        sslOffPerServSessUsingTLS12                 Integer32,
        sslOffPerServRejectedhandShake              Integer32,
        sslOffPerServByCipherHandShake              RadwareLongDisplayString,
        sslOffPerServRejectedCertificates           Integer32,
        sslOffPerServIgnoredCertificates            Integer32,
        sslOffPerServExpiredCertificates            Integer32,
        sslOffPerServUntrustedCertificates          Integer32,
        sslOffPerServCertificateHostnameMismatches  Integer32,
        sslOffPerServ0RTTReusedhandShake            Integer32,
        sslOffPerServPerc0RTTReusedhandShake        Integer32
        }

sslOffPerServVirtServIndex  OBJECT-TYPE
   SYNTAX  Integer32 
   MAX-ACCESS  read-only
   STATUS  current
   DESCRIPTION
       "Virtual server number."
   ::= {sslOffPerServStatsEntry 1}

sslOffPerServVirtServiceIndex  OBJECT-TYPE
   SYNTAX  Integer32 
   MAX-ACCESS  read-only
   STATUS  current
   DESCRIPTION
       "Virtual server service index."
   ::= {sslOffPerServStatsEntry 2}

sslOffPerServVirtServPort  OBJECT-TYPE
   SYNTAX  Integer32 
   MAX-ACCESS  read-only
   STATUS  current
   DESCRIPTION
       "Virtual server service port number."
   ::= {sslOffPerServStatsEntry 3}

sslOffPerServSslPolId  OBJECT-TYPE
   SYNTAX  DisplayString 
   MAX-ACCESS  read-only
   STATUS  current
   DESCRIPTION
       "SSL policy identifier associated with the virtual service."
   ::= {sslOffPerServStatsEntry 4}

sslOffPerServNewhandShake  OBJECT-TYPE
   SYNTAX  Integer32
   MAX-ACCESS  read-only
   STATUS  current
   DESCRIPTION
       "Number of New SSL handshakes between Clients and AAS per second for this virtual service."
   ::= {sslOffPerServStatsEntry 5}

sslOffPerServReusedhandShake OBJECT-TYPE
   SYNTAX  Integer32
   MAX-ACCESS  read-only
   STATUS  current
   DESCRIPTION
       "Number of existing SSL handshakes re-used by clients to communicate with AAS per second for virtual service."
   ::= {sslOffPerServStatsEntry 6}

sslOffPerServPercReusedhandShake OBJECT-TYPE
   SYNTAX  Integer32
   MAX-ACCESS  read-only
   STATUS  current
   DESCRIPTION
       "Percentage of SSL session re-using keys for virtual service."
   ::= {sslOffPerServStatsEntry 7}

sslOffPerServSessUsingSSLv2  OBJECT-TYPE
   SYNTAX  Integer32
   MAX-ACCESS  read-only
   STATUS  current
   DESCRIPTION
       "Percentage of session using SSLv2 out of all session during measuring period for virtual service."
   ::= {sslOffPerServStatsEntry 8}

sslOffPerServSessUsingSSLv3 OBJECT-TYPE
   SYNTAX  Integer32
   MAX-ACCESS  read-only
   STATUS  current
   DESCRIPTION
       "Percentage of session using SSLv3 out of all session during measuring period for virtual service."
   ::= {sslOffPerServStatsEntry 9}

sslOffPerServSessUsingTLS OBJECT-TYPE
   SYNTAX  Integer32
   MAX-ACCESS  read-only
   STATUS  current
   DESCRIPTION
       "Percentage of session using TLS1.0 out of all session during measuring period for virtual service."
   ::= {sslOffPerServStatsEntry 10}

sslOffPerServSessUsingTLS11 OBJECT-TYPE
   SYNTAX  Integer32
   MAX-ACCESS  read-only
   STATUS  current
   DESCRIPTION
       "Percentage of session using TLS1.1 out of all session during measuring period for virtual service."
   ::= {sslOffPerServStatsEntry 11}

sslOffPerServSessUsingTLS12 OBJECT-TYPE
   SYNTAX  Integer32
   MAX-ACCESS  read-only
   STATUS  current
   DESCRIPTION
       "Percentage of session using TLS1.2 out of all session during measuring period for virtual service."
   ::= {sslOffPerServStatsEntry 12}

sslOffPerServRejectedhandShake  OBJECT-TYPE
   SYNTAX  Integer32
   MAX-ACCESS  read-only
   STATUS  current
   DESCRIPTION
       "Number of rejected SSL handshakes per second for virtual service."
   ::= {sslOffPerServStatsEntry 13}

sslOffPerServByCipherHandShake  OBJECT-TYPE
    SYNTAX RadwareLongDisplayString (SIZE (0..10000))
    MAX-ACCESS  read-only
    STATUS  current
    DESCRIPTION
        "Session distribution by cipher for virtual service (in second)"
   ::= {sslOffPerServStatsEntry 14}

sslOffPerServRejectedCertificates  OBJECT-TYPE
   SYNTAX  Integer32
   MAX-ACCESS  read-only
   STATUS  current
   DESCRIPTION
       "Obsolete Mib!"
   ::= {sslOffPerServStatsEntry 15}

sslOffPerServIgnoredCertificates  OBJECT-TYPE
   SYNTAX  Integer32
   MAX-ACCESS  read-only
   STATUS  current
   DESCRIPTION
       "Obsolete Mib!"
   ::= {sslOffPerServStatsEntry 16}

sslOffPerServExpiredCertificates  OBJECT-TYPE
   SYNTAX  Integer32
   MAX-ACCESS  read-only
   STATUS  current
   DESCRIPTION
       "Obsolete Mib!"
   ::= {sslOffPerServStatsEntry 17}

sslOffPerServUntrustedCertificates  OBJECT-TYPE
   SYNTAX  Integer32
   MAX-ACCESS  read-only
   STATUS  current
   DESCRIPTION
       "Obsolete Mib!"
   ::= {sslOffPerServStatsEntry 18}

sslOffPerServCertificateHostnameMismatches  OBJECT-TYPE
   SYNTAX  Integer32
   MAX-ACCESS  read-only
   STATUS  current
   DESCRIPTION
       "Obsolete Mib!"
   ::= {sslOffPerServStatsEntry 19}
   
sslOffPerServ0RTTReusedhandShake OBJECT-TYPE
   SYNTAX  Integer32
   MAX-ACCESS  read-only
   STATUS  current
   DESCRIPTION
       "Number of existing SSL handshakes re-used by clients to communicate with AAS per second for virtual service (0-RTT)."
   ::= {sslOffPerServStatsEntry 20}

sslOffPerServPerc0RTTReusedhandShake OBJECT-TYPE
   SYNTAX  Integer32
   MAX-ACCESS  read-only
   STATUS  current
   DESCRIPTION
       "Percentage of SSL session re-using keys for virtual service (0-RTT)."
   ::= {sslOffPerServStatsEntry 21}

sslOffPerEnhServStatsTable OBJECT-TYPE
   SYNTAX SEQUENCE OF SslOffPerEnhServStatsEntry
   MAX-ACCESS not-accessible
   STATUS current
   DESCRIPTION
       "A table for SSL statistics per virtual service.
        Note:This mib is not supported for VX instance of Virtualization."
   ::= {sslSlbStats 20}

sslOffPerEnhServStatsEntry OBJECT-TYPE
   SYNTAX SslOffPerEnhServStatsEntry
   MAX-ACCESS not-accessible
   STATUS  current
   DESCRIPTION
       " The row definition for SSL statistics per virtual service table."
   INDEX  { sslOffPerEnhServVirtServIndex, sslOffPerEnhServVirtServiceIndex}
   ::= {sslOffPerEnhServStatsTable 1}

SslOffPerEnhServStatsEntry  ::= SEQUENCE {        
            sslOffPerEnhServVirtServIndex                       DisplayString,               
            sslOffPerEnhServVirtServiceIndex                    Integer32,                   
            sslOffPerEnhServVirtServPort                        Integer32,                   
            sslOffPerEnhServSslPolId                            DisplayString,               
        
            sslOffPerEnhServNewhandShake                        Integer32,                   
            sslOffPerEnhServReusedhandShake                     Integer32,                   
            sslOffPerEnhServPercReusedhandShake                 Integer32,                   
            sslOffPerEnhServSessUsingSSLv2                      Integer32,                   
            sslOffPerEnhServSessUsingSSLv3                      Integer32,                   
            sslOffPerEnhServSessUsingTLS                        Integer32,                   
            sslOffPerEnhServSessUsingTLS11                      Integer32,                   
            sslOffPerEnhServSessUsingTLS12                      Integer32,                   
            sslOffPerEnhServRejectedHandShake                   Integer32,                   
            sslOffPerEnhServByCipherHandShake                   RadwareLongDisplayString,    
            sslOffPerEnhServRejectedCertificates                Integer32,                   
            sslOffPerEnhServIgnoredCertificates                 Integer32,                   
            sslOffPerEnhServExpiredCertificates                 Integer32,                   
            sslOffPerEnhServUntrustedCertificates               Integer32,                   
            sslOffPerEnhServCertificateHostnameMismatches       Integer32,  
            sslOffPerEnhServSessUsingTLS13                      Integer32,    
            sslOffPerEnhServ0RTTReusedhandShake                 Integer32,
            sslOffPerEnhServPerc0RTTReusedhandShake             Integer32,
            sslOffPerEnhServ0RTTRejectedhandShake               Integer32,
            sslOffPerEnhServByRejectedHandShakeReasons          RadwareLongDisplayString,    
        
            sslOffPerEnhServBeNewhandShake                      Integer32,                   
            sslOffPerEnhServBeReusedhandShake                   Integer32,                   
            sslOffPerEnhServBePercReusedhandShake               Integer32,                   
            sslOffPerEnhServBeSessUsingSSLv2                    Integer32,                   
            sslOffPerEnhServBeSessUsingSSLv3                    Integer32,                   
            sslOffPerEnhServBeSessUsingTLS                      Integer32,                   
            sslOffPerEnhServBeSessUsingTLS11                    Integer32,                   
            sslOffPerEnhServBeSessUsingTLS12                    Integer32,                   
            sslOffPerEnhServBeRejectedHandShake                 Integer32,                   
            sslOffPerEnhServBeByCipherHandShake                 RadwareLongDisplayString,    
            sslOffPerEnhServFeRejectedCertificates              Integer32,                   
            sslOffPerEnhServFeIgnoredCertificates               Integer32,                   
            sslOffPerEnhServFeExpiredCertificates               Integer32,                   
            sslOffPerEnhServFeUntrustedCertificates             Integer32,                   
            sslOffPerEnhServFeCertificateHostnameMismatches     Integer32,                   
            sslOffPerEnhServBeSessUsingTLS13                    Integer32,                   
            sslOffPerEnhServBeByRejectedHandShakeReasons        RadwareLongDisplayString,    
        
            sslOffPerEnhServNewhandShakeTotal                   Integer32,                   
            sslOffPerEnhServReusedhandShakeTotal                Integer32,                   
            sslOffPerEnhServPercReusedhandShakeTotal            Integer32,                   
            sslOffPerEnhServSessUsingSSLv2Total                 Integer32,                   
            sslOffPerEnhServSessUsingSSLv3Total                 Integer32,                   
            sslOffPerEnhServSessUsingTLSTotal                   Integer32,                   
            sslOffPerEnhServSessUsingTLS11Total                 Integer32,                   
            sslOffPerEnhServSessUsingTLS12Total                 Integer32,                   
            sslOffPerEnhServRejectedHandShakeTotal              Integer32,                   
            sslOffPerEnhServByCipherHandShakeTotal              RadwareLongDisplayString,    
            sslOffPerEnhServRejectedCertificatesTotal           Integer32,                   
            sslOffPerEnhServIgnoredCertificatesTotal            Integer32,                   
            sslOffPerEnhServExpiredCertificatesTotal            Integer32,                   
            sslOffPerEnhServUntrustedCertificatesTotal          Integer32,                   
            sslOffPerEnhServCertificateHostnameMismatchesTotal  Integer32,                   
            sslOffPerEnhServSessUsingTLS13Total                 Integer32,                   
            sslOffPerEnhServByRejectedHandShakeReasonsTotal     RadwareLongDisplayString,    
        
            sslOffPerEnhServBeNewhandShakeTotal                 Integer32,                   
            sslOffPerEnhServBeReusedhandShakeTotal              Integer32,                   
            sslOffPerEnhServBePercReusedhandShakeTotal          Integer32,                   
            sslOffPerEnhServBeSessUsingSSLv2Total               Integer32,                   
            sslOffPerEnhServBeSessUsingSSLv3Total               Integer32,                   
            sslOffPerEnhServBeSessUsingTLSTotal                 Integer32,                   
            sslOffPerEnhServBeSessUsingTLS11Total               Integer32,                   
            sslOffPerEnhServBeSessUsingTLS12Total               Integer32,                   
            sslOffPerEnhServBeRejectedHandShakeTotal            Integer32,                   
            sslOffPerEnhServBeByCipherHandShakeTotal            RadwareLongDisplayString,    
            sslOffPerEnhServFeRejectedCertificatesTotal         Integer32,                   
            sslOffPerEnhServFeIgnoredCertificatesTotal          Integer32,                   
            sslOffPerEnhServFeExpiredCertificatesTotal          Integer32,                   
            sslOffPerEnhServFeUntrustedCertificatesTotal        Integer32,                   
            sslOffPerEnhServFeCertificateHostnameMismatchesTotal Integer32,                  
            sslOffPerEnhServBeSessUsingTLS13Total               Integer32,                   
            sslOffPerEnhServBeByRejectedHandShakeReasonsTotal   RadwareLongDisplayString,

            sslOffPerEnhServ0RTTReusedhandShakeTotal                 Integer32,
            sslOffPerEnhServPerc0RTTReusedhandShakeTotal             Integer32,
            sslOffPerEnhServ0RTTRejectedhandShakeTotal               Integer32,

            sslOffPerEnhServSessionIdReusedhandShake               Integer32,
            sslOffPerEnhServPercSessionIdReusedhandShake           Integer32,
            sslOffPerEnhServBeSessionIdReusedhandShake             Integer32,
            sslOffPerEnhServBePercSessionIdReusedhandShake         Integer32,
            sslOffPerEnhServSessionIdReusedhandShakeTotal          Integer32,
            sslOffPerEnhServPercSessionIdReusedhandShakeTotal      Integer32,
            sslOffPerEnhServBeSessionIdReusedhandShakeTotal        Integer32,
            sslOffPerEnhServBePercSessionIdReusedhandShakeTotal    Integer32,
            sslOffPerEnhServTicketReusedhandShake                  Integer32,
            sslOffPerEnhServPercTicketReusedhandShake              Integer32,
            sslOffPerEnhServBeTicketReusedhandShake                Integer32,
            sslOffPerEnhServBePercTicketReusedhandShake            Integer32,
            sslOffPerEnhServTicketReusedhandShakeTotal             Integer32,
            sslOffPerEnhServPercTicketReusedhandShakeTotal         Integer32,
            sslOffPerEnhServBeTicketReusedhandShakeTotal           Integer32,
            sslOffPerEnhServBePercTicketReusedhandShakeTotal       Integer32
        }

sslOffPerEnhServVirtServIndex  OBJECT-TYPE
   SYNTAX DisplayString (SIZE(1..255))
   MAX-ACCESS  read-only
   STATUS  current
   DESCRIPTION
       "Virtual server number in alphanumeric."
   ::= {sslOffPerEnhServStatsEntry 1}

sslOffPerEnhServVirtServiceIndex  OBJECT-TYPE
   SYNTAX  Integer32
   MAX-ACCESS  read-only
   STATUS  current
   DESCRIPTION
       "Virtual server service index."
   ::= {sslOffPerEnhServStatsEntry 2}

sslOffPerEnhServVirtServPort  OBJECT-TYPE
   SYNTAX  Integer32
   MAX-ACCESS  read-only
   STATUS  current
   DESCRIPTION
       "Virtual server service port number."
   ::= {sslOffPerEnhServStatsEntry 3}

sslOffPerEnhServSslPolId  OBJECT-TYPE
   SYNTAX  DisplayString
   MAX-ACCESS  read-only
   STATUS  current
   DESCRIPTION
       "SSL policy identifier associated with the virtual service."
   ::= {sslOffPerEnhServStatsEntry 4}

sslOffPerEnhServNewhandShake  OBJECT-TYPE
   SYNTAX  Integer32
   MAX-ACCESS  read-only
   STATUS  current
   DESCRIPTION
       "Number of New SSL handshakes between Clients and AAS per second for this virtual service."
   ::= {sslOffPerEnhServStatsEntry 5}

sslOffPerEnhServReusedhandShake OBJECT-TYPE
   SYNTAX  Integer32
   MAX-ACCESS  read-only
   STATUS  current
   DESCRIPTION
       "Number of existing SSL handshakes re-used by clients to communicate with AAS per second for virtual service."
   ::= {sslOffPerEnhServStatsEntry 6}

sslOffPerEnhServPercReusedhandShake OBJECT-TYPE
   SYNTAX  Integer32
   MAX-ACCESS  read-only
   STATUS  current
   DESCRIPTION
       "Percentage of SSL session re-using keys for virtual service."
   ::= {sslOffPerEnhServStatsEntry 7}

sslOffPerEnhServSessUsingSSLv2  OBJECT-TYPE
   SYNTAX  Integer32
   MAX-ACCESS  read-only
   STATUS  current
   DESCRIPTION
       "Percentage of session using SSLv2 out of all session during measuring period for virtual service."
   ::= {sslOffPerEnhServStatsEntry 8}

sslOffPerEnhServSessUsingSSLv3 OBJECT-TYPE
   SYNTAX  Integer32
   MAX-ACCESS  read-only
   STATUS  current
   DESCRIPTION
       "Percentage of session using SSLv3 out of all session during measuring period for virtual service."
   ::= {sslOffPerEnhServStatsEntry 9}
sslOffPerEnhServSessUsingTLS OBJECT-TYPE
   SYNTAX  Integer32
   MAX-ACCESS  read-only
   STATUS  current
   DESCRIPTION
       "Percentage of session using TLS1.0 out of all session during measuring period for virtual service."
   ::= {sslOffPerEnhServStatsEntry 10}

sslOffPerEnhServSessUsingTLS11 OBJECT-TYPE
   SYNTAX  Integer32
   MAX-ACCESS  read-only
   STATUS  current
   DESCRIPTION
       "Percentage of session using TLS1.1 out of all session during measuring period for virtual service."
   ::= {sslOffPerEnhServStatsEntry 11}

sslOffPerEnhServSessUsingTLS12 OBJECT-TYPE
   SYNTAX  Integer32
   MAX-ACCESS  read-only
   STATUS  current
   DESCRIPTION
       "Percentage of session using TLS1.2 out of all session during measuring period for virtual service."
   ::= {sslOffPerEnhServStatsEntry 12}

sslOffPerEnhServRejectedHandShake OBJECT-TYPE
   SYNTAX  Integer32
   MAX-ACCESS  read-only
   STATUS  current
   DESCRIPTION
       "Number of rejected SSL handshakes per second for virtual service."
   ::= {sslOffPerEnhServStatsEntry 13}

sslOffPerEnhServByCipherHandShake  OBJECT-TYPE
    SYNTAX RadwareLongDisplayString (SIZE (0..10000))
    MAX-ACCESS  read-only
    STATUS  current
    DESCRIPTION
        "Obsolete Mib! please use SslOffPerCiphServStatsTable instead"
   ::= {sslOffPerEnhServStatsEntry 14}

sslOffPerEnhServRejectedCertificates OBJECT-TYPE
   SYNTAX  Integer32
   MAX-ACCESS  read-only
   STATUS  current
   DESCRIPTION
       "Number of rejected SSL certificates per second for virtual service."
   ::= {sslOffPerEnhServStatsEntry 15}

sslOffPerEnhServIgnoredCertificates OBJECT-TYPE
   SYNTAX  Integer32
   MAX-ACCESS  read-only
   STATUS  current
   DESCRIPTION
       "Number of ignored SSL certificates per second for virtual service."
   ::= {sslOffPerEnhServStatsEntry 16}

sslOffPerEnhServExpiredCertificates OBJECT-TYPE
   SYNTAX  Integer32
   MAX-ACCESS  read-only
   STATUS  current
   DESCRIPTION
       "Number of expired SSL certificates per second for virtual service."
   ::= {sslOffPerEnhServStatsEntry 17}

sslOffPerEnhServUntrustedCertificates OBJECT-TYPE
   SYNTAX  Integer32
   MAX-ACCESS  read-only
   STATUS  current
   DESCRIPTION
       "Number of untrusted SSL certificates per second for virtual service."
   ::= {sslOffPerEnhServStatsEntry 18}

sslOffPerEnhServCertificateHostnameMismatches OBJECT-TYPE
   SYNTAX  Integer32
   MAX-ACCESS  read-only
   STATUS  current
   DESCRIPTION
       "Number of SSL certificate hostname mismatches per second for virtual service."
   ::= {sslOffPerEnhServStatsEntry 19}
   
   sslOffPerEnhServSessUsingTLS13 OBJECT-TYPE
   SYNTAX  Integer32
   MAX-ACCESS  read-only
   STATUS  current
   DESCRIPTION
       "Percentage of session using TLS1.3 out of all session during measuring period for virtual service."
   ::= {sslOffPerEnhServStatsEntry 20}
   
 sslOffPerEnhServ0RTTReusedhandShake OBJECT-TYPE
   SYNTAX  Integer32
   MAX-ACCESS  read-only
   STATUS  current
   DESCRIPTION
       "Number of existing SSL handshakes re-used by clients to communicate with AAS per second for virtual service (0-RTT)."
   ::= {sslOffPerEnhServStatsEntry 21}

sslOffPerEnhServPerc0RTTReusedhandShake OBJECT-TYPE
   SYNTAX  Integer32
   MAX-ACCESS  read-only
   STATUS  current
   DESCRIPTION
       "Percentage of SSL session re-using keys for virtual service (0-RTT)."
   ::= {sslOffPerEnhServStatsEntry 22}
  
   sslOffPerEnhServ0RTTRejectedhandShake OBJECT-TYPE
   SYNTAX  Integer32
   MAX-ACCESS  read-only
   STATUS  current
   DESCRIPTION
       "Number of rejected SSL handshakes per second for virtual service (0-RTT)."
   ::= {sslOffPerEnhServStatsEntry 23}
   
sslOffPerEnhServByRejectedHandShakeReasons  OBJECT-TYPE
    SYNTAX RadwareLongDisplayString (SIZE (0..10000))
    MAX-ACCESS  read-only
    STATUS  current
    DESCRIPTION
        "Obsolete Mib! please use SslOffPerServRejHsReasonsStatsTable instead"
   ::= {sslOffPerEnhServStatsEntry 24}
   
   sslOffPerEnhServBeNewhandShake  OBJECT-TYPE
   SYNTAX  Integer32
   MAX-ACCESS  read-only
   STATUS  current
   DESCRIPTION
       "Number of New SSL handshakes between servers and AAS per second for this virtual service."
   ::= {sslOffPerEnhServStatsEntry 25}

sslOffPerEnhServBeReusedhandShake OBJECT-TYPE
   SYNTAX  Integer32
   MAX-ACCESS  read-only
   STATUS  current
   DESCRIPTION
       "Number of existing SSL handshakes re-used by servers to communicate with AAS per second for virtual service."
   ::= {sslOffPerEnhServStatsEntry 26}

sslOffPerEnhServBePercReusedhandShake OBJECT-TYPE
   SYNTAX  Integer32
   MAX-ACCESS  read-only
   STATUS  current
   DESCRIPTION
       "Percentage of SSL session re-using keys for virtual service."
   ::= {sslOffPerEnhServStatsEntry 27}

sslOffPerEnhServBeSessUsingSSLv2  OBJECT-TYPE
   SYNTAX  Integer32
   MAX-ACCESS  read-only
   STATUS  current
   DESCRIPTION
       "Percentage of session using SSLv2 out of all session during measuring period for virtual service."
   ::= {sslOffPerEnhServStatsEntry 28}

sslOffPerEnhServBeSessUsingSSLv3 OBJECT-TYPE
   SYNTAX  Integer32
   MAX-ACCESS  read-only
   STATUS  current
   DESCRIPTION
       "Percentage of session using SSLv3 out of all session during measuring period for virtual service."
   ::= {sslOffPerEnhServStatsEntry 29}
   
sslOffPerEnhServBeSessUsingTLS OBJECT-TYPE
   SYNTAX  Integer32
   MAX-ACCESS  read-only
   STATUS  current
   DESCRIPTION
       "Percentage of session using TLS1.0 out of all session during measuring period for virtual service."
   ::= {sslOffPerEnhServStatsEntry 30}

sslOffPerEnhServBeSessUsingTLS11 OBJECT-TYPE
   SYNTAX  Integer32
   MAX-ACCESS  read-only
   STATUS  current
   DESCRIPTION
       "Percentage of session using TLS1.1 out of all session during measuring period for virtual service."
   ::= {sslOffPerEnhServStatsEntry 31}

sslOffPerEnhServBeSessUsingTLS12 OBJECT-TYPE
   SYNTAX  Integer32
   MAX-ACCESS  read-only
   STATUS  current
   DESCRIPTION
       "Percentage of session using TLS1.2 out of all session during measuring period for virtual service."
   ::= {sslOffPerEnhServStatsEntry 32}

sslOffPerEnhServBeRejectedHandShake OBJECT-TYPE
   SYNTAX  Integer32
   MAX-ACCESS  read-only
   STATUS  current
   DESCRIPTION
       "Number of rejected SSL handshakes per second for virtual service."
   ::= {sslOffPerEnhServStatsEntry 33}

sslOffPerEnhServBeByCipherHandShake  OBJECT-TYPE
    SYNTAX RadwareLongDisplayString (SIZE (0..10000))
    MAX-ACCESS  read-only
    STATUS  current
    DESCRIPTION
        "Obsolete Mib! please use SslBeOffPerCiphServStatsTable instead"
   ::= {sslOffPerEnhServStatsEntry 34}

sslOffPerEnhServFeRejectedCertificates OBJECT-TYPE
   SYNTAX  Integer32
   MAX-ACCESS  read-only
   STATUS  current
   DESCRIPTION
       "Number of rejected SSL certificates per second for virtual service."
   ::= {sslOffPerEnhServStatsEntry 35}

sslOffPerEnhServFeIgnoredCertificates OBJECT-TYPE
   SYNTAX  Integer32
   MAX-ACCESS  read-only
   STATUS  current
   DESCRIPTION
       "Number of ignored SSL certificates per second for virtual service."
   ::= {sslOffPerEnhServStatsEntry 36}

sslOffPerEnhServFeExpiredCertificates OBJECT-TYPE
   SYNTAX  Integer32
   MAX-ACCESS  read-only
   STATUS  current
   DESCRIPTION
       "Number of expired SSL certificates per second for virtual service."
   ::= {sslOffPerEnhServStatsEntry 37}

sslOffPerEnhServFeUntrustedCertificates OBJECT-TYPE
   SYNTAX  Integer32
   MAX-ACCESS  read-only
   STATUS  current
   DESCRIPTION
       "Number of untrusted SSL certificates per second for virtual service."
   ::= {sslOffPerEnhServStatsEntry 38}

sslOffPerEnhServFeCertificateHostnameMismatches OBJECT-TYPE
   SYNTAX  Integer32
   MAX-ACCESS  read-only
   STATUS  current
   DESCRIPTION
       "Number of SSL certificate hostname mismatches per second for virtual service."
   ::= {sslOffPerEnhServStatsEntry 39}
   
   sslOffPerEnhServBeSessUsingTLS13 OBJECT-TYPE
   SYNTAX  Integer32
   MAX-ACCESS  read-only
   STATUS  current
   DESCRIPTION
       "Percentage of session using TLS1.3 out of all session during measuring period for virtual service."
   ::= {sslOffPerEnhServStatsEntry 40}
   
   sslOffPerEnhServNewhandShakeTotal  OBJECT-TYPE
   SYNTAX  Integer32
   MAX-ACCESS  read-only
   STATUS  current
   DESCRIPTION
       "Number of New SSL handshakes between Clients and AAS since last reset for this virtual service."
   ::= {sslOffPerEnhServStatsEntry 41}
   
sslOffPerEnhServBeByRejectedHandShakeReasons  OBJECT-TYPE
    SYNTAX RadwareLongDisplayString (SIZE (0..10000))
    MAX-ACCESS  read-only
    STATUS  current
    DESCRIPTION
        "Obsolete Mib! please use SslBeOffPerServRejHsReasonsStatsTable instead"
   ::= {sslOffPerEnhServStatsEntry 42}

sslOffPerEnhServReusedhandShakeTotal OBJECT-TYPE
   SYNTAX  Integer32
   MAX-ACCESS  read-only
   STATUS  current
   DESCRIPTION
       "Number of existing SSL handshakes re-used by clients to communicate with AAS since last reset for virtual service."
   ::= {sslOffPerEnhServStatsEntry 43}

sslOffPerEnhServPercReusedhandShakeTotal OBJECT-TYPE
   SYNTAX  Integer32
   MAX-ACCESS  read-only
   STATUS  current
   DESCRIPTION
       "Percentage of SSL session re-using keys for virtual service."
   ::= {sslOffPerEnhServStatsEntry 44}

sslOffPerEnhServSessUsingSSLv2Total  OBJECT-TYPE
   SYNTAX  Integer32
   MAX-ACCESS  read-only
   STATUS  current
   DESCRIPTION
       "Percentage of session using SSLv2 out of all session since last reset for virtual service."
   ::= {sslOffPerEnhServStatsEntry 45}

sslOffPerEnhServSessUsingSSLv3Total OBJECT-TYPE
   SYNTAX  Integer32
   MAX-ACCESS  read-only
   STATUS  current
   DESCRIPTION
       "Percentage of session using SSLv3 out of all session since last reset for virtual service."
   ::= {sslOffPerEnhServStatsEntry 46}
   
sslOffPerEnhServSessUsingTLSTotal OBJECT-TYPE
   SYNTAX  Integer32
   MAX-ACCESS  read-only
   STATUS  current
   DESCRIPTION
       "Percentage of session using TLS1.0 out of all session since last reset for virtual service."
   ::= {sslOffPerEnhServStatsEntry 47}

sslOffPerEnhServSessUsingTLS11Total OBJECT-TYPE
   SYNTAX  Integer32
   MAX-ACCESS  read-only
   STATUS  current
   DESCRIPTION
       "Percentage of session using TLS1.1 out of all session since last reset for virtual service."
   ::= {sslOffPerEnhServStatsEntry 48}

sslOffPerEnhServSessUsingTLS12Total OBJECT-TYPE
   SYNTAX  Integer32
   MAX-ACCESS  read-only
   STATUS  current
   DESCRIPTION
       "Percentage of session using TLS1.2 out of all session since last reset for virtual service."
   ::= {sslOffPerEnhServStatsEntry 49}

sslOffPerEnhServRejectedHandShakeTotal OBJECT-TYPE
   SYNTAX  Integer32
   MAX-ACCESS  read-only
   STATUS  current
   DESCRIPTION
       "Number of rejected SSL handshakes since last reset for virtual service."
   ::= {sslOffPerEnhServStatsEntry 50}

sslOffPerEnhServByCipherHandShakeTotal  OBJECT-TYPE
    SYNTAX RadwareLongDisplayString (SIZE (0..10000))
    MAX-ACCESS  read-only
    STATUS  current
    DESCRIPTION
        "Obsolete Mib! please use SslOffPerCiphServStatsTable instead"
   ::= {sslOffPerEnhServStatsEntry 51}

sslOffPerEnhServRejectedCertificatesTotal OBJECT-TYPE
   SYNTAX  Integer32
   MAX-ACCESS  read-only
   STATUS  current
   DESCRIPTION
       "Number of rejected SSL certificates since last reset for virtual service."
   ::= {sslOffPerEnhServStatsEntry 52}

sslOffPerEnhServIgnoredCertificatesTotal OBJECT-TYPE
   SYNTAX  Integer32
   MAX-ACCESS  read-only
   STATUS  current
   DESCRIPTION
       "Number of ignored SSL certificates per second for virtual service."
   ::= {sslOffPerEnhServStatsEntry 53}

sslOffPerEnhServExpiredCertificatesTotal OBJECT-TYPE
   SYNTAX  Integer32
   MAX-ACCESS  read-only
   STATUS  current
   DESCRIPTION
       "Number of expired SSL certificates since last reset for virtual service."
   ::= {sslOffPerEnhServStatsEntry 54}

sslOffPerEnhServUntrustedCertificatesTotal OBJECT-TYPE
   SYNTAX  Integer32
   MAX-ACCESS  read-only
   STATUS  current
   DESCRIPTION
       "Number of untrusted SSL certificates since last reset for virtual service."
   ::= {sslOffPerEnhServStatsEntry 55}

sslOffPerEnhServCertificateHostnameMismatchesTotal OBJECT-TYPE
   SYNTAX  Integer32
   MAX-ACCESS  read-only
   STATUS  current
   DESCRIPTION
       "Number of SSL certificate hostname mismatches since last reset for virtual service."
   ::= {sslOffPerEnhServStatsEntry 56}
   
   sslOffPerEnhServSessUsingTLS13Total OBJECT-TYPE
   SYNTAX  Integer32
   MAX-ACCESS  read-only
   STATUS  current
   DESCRIPTION
       "Percentage of session using TLS1.3 out of all session since last reset for virtual service."
   ::= {sslOffPerEnhServStatsEntry 57}
   
   sslOffPerEnhServBeNewhandShakeTotal  OBJECT-TYPE
   SYNTAX  Integer32
   MAX-ACCESS  read-only
   STATUS  current
   DESCRIPTION
       "Number of New SSL handshakes between servers and AAS since last reset for this virtual service."
   ::= {sslOffPerEnhServStatsEntry 58}

sslOffPerEnhServBeReusedhandShakeTotal OBJECT-TYPE
   SYNTAX  Integer32
   MAX-ACCESS  read-only
   STATUS  current
   DESCRIPTION
       "Number of existing SSL handshakes re-used by servers to communicate with AAS since last reset for virtual service."
   ::= {sslOffPerEnhServStatsEntry 59}
   
sslOffPerEnhServByRejectedHandShakeReasonsTotal OBJECT-TYPE
    SYNTAX RadwareLongDisplayString (SIZE (0..10000))
    MAX-ACCESS  read-only
    STATUS  current
    DESCRIPTION
        "Obsolete Mib! please use SslOffPerServRejHsReasonsStatsTable instead"
   ::= {sslOffPerEnhServStatsEntry 60}

sslOffPerEnhServBePercReusedhandShakeTotal OBJECT-TYPE
   SYNTAX  Integer32
   MAX-ACCESS  read-only
   STATUS  current
   DESCRIPTION
       "Percentage of SSL session re-using keys for virtual service."
   ::= {sslOffPerEnhServStatsEntry 61}

sslOffPerEnhServBeSessUsingSSLv2Total  OBJECT-TYPE
   SYNTAX  Integer32
   MAX-ACCESS  read-only
   STATUS  current
   DESCRIPTION
       "Percentage of session using SSLv2 out of all session since last reset for virtual service."
   ::= {sslOffPerEnhServStatsEntry 62}

sslOffPerEnhServBeSessUsingSSLv3Total OBJECT-TYPE
   SYNTAX  Integer32
   MAX-ACCESS  read-only
   STATUS  current
   DESCRIPTION
       "Percentage of session using SSLv3 out of all session since last reset for virtual service."
   ::= {sslOffPerEnhServStatsEntry 63}
   
sslOffPerEnhServBeSessUsingTLSTotal OBJECT-TYPE
   SYNTAX  Integer32
   MAX-ACCESS  read-only
   STATUS  current
   DESCRIPTION
       "Percentage of session using TLS1.0 out of all session since last reset for virtual service."
   ::= {sslOffPerEnhServStatsEntry 64}

sslOffPerEnhServBeSessUsingTLS11Total OBJECT-TYPE
   SYNTAX  Integer32
   MAX-ACCESS  read-only
   STATUS  current
   DESCRIPTION
       "Percentage of session using TLS1.1 out of all session since last reset for virtual service."
   ::= {sslOffPerEnhServStatsEntry 65}

sslOffPerEnhServBeSessUsingTLS12Total OBJECT-TYPE
   SYNTAX  Integer32
   MAX-ACCESS  read-only
   STATUS  current
   DESCRIPTION
       "Percentage of session using TLS1.2 out of all session since last reset for virtual service."
   ::= {sslOffPerEnhServStatsEntry 66}

sslOffPerEnhServBeRejectedHandShakeTotal OBJECT-TYPE
   SYNTAX  Integer32
   MAX-ACCESS  read-only
   STATUS  current
   DESCRIPTION
       "Number of rejected SSL handshakes since last reset for virtual service."
   ::= {sslOffPerEnhServStatsEntry 67}

sslOffPerEnhServBeByCipherHandShakeTotal  OBJECT-TYPE
    SYNTAX RadwareLongDisplayString (SIZE (0..10000))
    MAX-ACCESS  read-only
    STATUS  current
    DESCRIPTION
        "Obsolete Mib! please use SslBeOffPerCiphServStatsTable instead"
   ::= {sslOffPerEnhServStatsEntry 68}

sslOffPerEnhServFeRejectedCertificatesTotal OBJECT-TYPE
   SYNTAX  Integer32
   MAX-ACCESS  read-only
   STATUS  current
   DESCRIPTION
       "Number of rejected SSL certificates since last reset for virtual service."
   ::= {sslOffPerEnhServStatsEntry 69}

sslOffPerEnhServFeIgnoredCertificatesTotal OBJECT-TYPE
   SYNTAX  Integer32
   MAX-ACCESS  read-only
   STATUS  current
   DESCRIPTION
       "Number of ignored SSL certificates since last reset for virtual service."
   ::= {sslOffPerEnhServStatsEntry 70}

sslOffPerEnhServFeExpiredCertificatesTotal OBJECT-TYPE
   SYNTAX  Integer32
   MAX-ACCESS  read-only
   STATUS  current
   DESCRIPTION
       "Number of expired SSL certificates since last reset for virtual service."
   ::= {sslOffPerEnhServStatsEntry 71}

sslOffPerEnhServFeUntrustedCertificatesTotal OBJECT-TYPE
   SYNTAX  Integer32
   MAX-ACCESS  read-only
   STATUS  current
   DESCRIPTION
       "Number of untrusted SSL certificates since last reset for virtual service."
   ::= {sslOffPerEnhServStatsEntry 72}

sslOffPerEnhServFeCertificateHostnameMismatchesTotal OBJECT-TYPE
   SYNTAX  Integer32
   MAX-ACCESS  read-only
   STATUS  current
   DESCRIPTION
       "Number of SSL certificate hostname mismatches since last reset for virtual service."
   ::= {sslOffPerEnhServStatsEntry 73}
   
   sslOffPerEnhServBeSessUsingTLS13Total OBJECT-TYPE
   SYNTAX  Integer32
   MAX-ACCESS  read-only
   STATUS  current
   DESCRIPTION
       "Percentage of session using TLS1.3 out of all session since last reset for virtual service."
   ::= {sslOffPerEnhServStatsEntry 74}
   
sslOffPerEnhServBeByRejectedHandShakeReasonsTotal OBJECT-TYPE
    SYNTAX RadwareLongDisplayString (SIZE (0..10000))
    MAX-ACCESS  read-only
    STATUS  current
    DESCRIPTION
        "Obsolete Mib! please use SslBeOffPerServRejHsReasonsStatsTable instead"
   ::= {sslOffPerEnhServStatsEntry 75}

sslOffPerEnhServ0RTTReusedhandShakeTotal OBJECT-TYPE
   SYNTAX  Integer32
   MAX-ACCESS  read-only
   STATUS  current
   DESCRIPTION
       "Number of existing SSL handshakes re-used by clients to communicate with AAS for virtual service (0-RTT) since last reset."
   ::= {sslOffPerEnhServStatsEntry 76}

sslOffPerEnhServPerc0RTTReusedhandShakeTotal OBJECT-TYPE
   SYNTAX  Integer32
   MAX-ACCESS  read-only
   STATUS  current
   DESCRIPTION
       "Percentage of SSL session re-using keys for virtual service (0-RTT) since last reset."
   ::= {sslOffPerEnhServStatsEntry 77}

sslOffPerEnhServ0RTTRejectedhandShakeTotal OBJECT-TYPE
   SYNTAX  Integer32
   MAX-ACCESS  read-only
   STATUS  current
   DESCRIPTION
       "Number of rejected SSL handshakes for virtual service (0-RTT) since last reset."
   ::= {sslOffPerEnhServStatsEntry 78}

sslOffPerEnhServSessionIdReusedhandShake OBJECT-TYPE
   SYNTAX  Integer32
   MAX-ACCESS  read-only
   STATUS  current
   DESCRIPTION
       "Number of existing SSL handshakes Session Id re-used by clients to communicate with AAS per second for virtual service."
   ::= {sslOffPerEnhServStatsEntry 79}

sslOffPerEnhServPercSessionIdReusedhandShake OBJECT-TYPE
   SYNTAX  Integer32
   MAX-ACCESS  read-only
   STATUS  current
   DESCRIPTION
       "Percentage of SSL session Id re-using keys for virtual service."
   ::= {sslOffPerEnhServStatsEntry 80}

sslOffPerEnhServBeSessionIdReusedhandShake OBJECT-TYPE
   SYNTAX  Integer32
   MAX-ACCESS  read-only
   STATUS  current
   DESCRIPTION
       "Number of existing SSL handshakes Session Id re-used by servers to communicate with AAS per second for virtual service."
   ::= {sslOffPerEnhServStatsEntry 81}

sslOffPerEnhServBePercSessionIdReusedhandShake OBJECT-TYPE
   SYNTAX  Integer32
   MAX-ACCESS  read-only
   STATUS  current
   DESCRIPTION
       "Percentage of SSL session Id re-using keys for virtual service."
   ::= {sslOffPerEnhServStatsEntry 82}

sslOffPerEnhServSessionIdReusedhandShakeTotal OBJECT-TYPE
   SYNTAX  Integer32
   MAX-ACCESS  read-only
   STATUS  current
   DESCRIPTION
       "Number of existing SSL handshakes Session Id re-used by clients to communicate with AAS since last reset for virtual service."
   ::= {sslOffPerEnhServStatsEntry 83}

sslOffPerEnhServPercSessionIdReusedhandShakeTotal OBJECT-TYPE
   SYNTAX  Integer32
   MAX-ACCESS  read-only
   STATUS  current
   DESCRIPTION
       "Percentage of SSL session Id re-using keys for virtual service."
   ::= {sslOffPerEnhServStatsEntry 84}

sslOffPerEnhServBeSessionIdReusedhandShakeTotal OBJECT-TYPE
   SYNTAX  Integer32
   MAX-ACCESS  read-only
   STATUS  current
   DESCRIPTION
       "Number of existing SSL handshakes Session Id re-used by servers to communicate with AAS since last reset for virtual service."
   ::= {sslOffPerEnhServStatsEntry 85}

sslOffPerEnhServBePercSessionIdReusedhandShakeTotal OBJECT-TYPE
   SYNTAX  Integer32
   MAX-ACCESS  read-only
   STATUS  current
   DESCRIPTION
       "Percentage of SSL session Id re-using keys for virtual service."
   ::= {sslOffPerEnhServStatsEntry 86}

sslOffPerEnhServTicketReusedhandShake OBJECT-TYPE
   SYNTAX  Integer32
   MAX-ACCESS  read-only
   STATUS  current
   DESCRIPTION
       "Number of existing SSL handshakes Ticket re-used by clients to communicate with AAS per second for virtual service."
   ::= {sslOffPerEnhServStatsEntry 87}

sslOffPerEnhServPercTicketReusedhandShake OBJECT-TYPE
   SYNTAX  Integer32
   MAX-ACCESS  read-only
   STATUS  current
   DESCRIPTION
       "Percentage of SSL session Ticket re-using keys for virtual service."
   ::= {sslOffPerEnhServStatsEntry 88}

sslOffPerEnhServBeTicketReusedhandShake OBJECT-TYPE
   SYNTAX  Integer32
   MAX-ACCESS  read-only
   STATUS  current
   DESCRIPTION
       "Number of existing SSL handshakes Ticket re-used by servers to communicate with AAS per second for virtual service."
   ::= {sslOffPerEnhServStatsEntry 89}

sslOffPerEnhServBePercTicketReusedhandShake OBJECT-TYPE
   SYNTAX  Integer32
   MAX-ACCESS  read-only
   STATUS  current
   DESCRIPTION
       "Percentage of SSL session Ticket re-using keys for virtual service."
   ::= {sslOffPerEnhServStatsEntry 90}

sslOffPerEnhServTicketReusedhandShakeTotal OBJECT-TYPE
   SYNTAX  Integer32
   MAX-ACCESS  read-only
   STATUS  current
   DESCRIPTION
       "Number of existing SSL handshakes Ticket re-used by clients to communicate with AAS since last reset for virtual service."
   ::= {sslOffPerEnhServStatsEntry 91}

sslOffPerEnhServPercTicketReusedhandShakeTotal OBJECT-TYPE
   SYNTAX  Integer32
   MAX-ACCESS  read-only
   STATUS  current
   DESCRIPTION
       "Percentage of SSL session Ticket re-using keys for virtual service."
   ::= {sslOffPerEnhServStatsEntry 92}

sslOffPerEnhServBeTicketReusedhandShakeTotal OBJECT-TYPE
   SYNTAX  Integer32
   MAX-ACCESS  read-only
   STATUS  current
   DESCRIPTION
       "Number of existing SSL handshakes Ticket re-used by servers to communicate with AAS since last reset for virtual service."
   ::= {sslOffPerEnhServStatsEntry 93}

sslOffPerEnhServBePercTicketReusedhandShakeTotal OBJECT-TYPE
   SYNTAX  Integer32
   MAX-ACCESS  read-only
   STATUS  current
   DESCRIPTION
       "Percentage of SSL session Ticket re-using keys for virtual service."
   ::= {sslOffPerEnhServStatsEntry 94}

   
sslOffPerFilterStatsTable OBJECT-TYPE
   SYNTAX SEQUENCE OF SslOffPerFilterStatsEntry
   MAX-ACCESS not-accessible
   STATUS current
   DESCRIPTION
       "A table for SSL statistics per filter.
        Note:This mib is not supported for VX instance of Virtualization."
   ::= {sslSlbStats 22}

sslOffPerFilterStatsEntry OBJECT-TYPE
   SYNTAX SslOffPerFilterStatsEntry
   MAX-ACCESS not-accessible
   STATUS  current
   DESCRIPTION
       " The row definition for SSL statistics per filter table."
   INDEX  {sslOffPerFilterId}
   ::= {sslOffPerFilterStatsTable 1}   
   
SslOffPerFilterStatsEntry  ::= SEQUENCE {
            sslOffPerFilterId                                   Integer32,                   
		    sslOffPerFilterNewhandShake                         Integer32,                   
		    sslOffPerFilterReusedhandShake                      Integer32,                   
		    sslOffPerFilterRateReusedhandShake                  Integer32,                 
            sslOffPerFilterSessionIdReusedhandShake             Integer32,
            sslOffPerFilterRateSessionIdReusedhandShake         Integer32,
            sslOffPerFilterTicketReusedhandShake                Integer32,
            sslOffPerFilterRateTicketReusedhandShake            Integer32,  
		    sslOffPerFilterPerSessUsingSSLv3                    Integer32,                   
		    sslOffPerFilterPerSessUsingTLS10                    Integer32,                   
		    sslOffPerFilterPerSessUsingTLS11                    Integer32,                   
		    sslOffPerFilterPerSessUsingTLS12                    Integer32,                   
		    sslOffPerFilterRejectedHandShakes                   Integer32,                   
            sslOffPerFilterHttpToHTTPSRedir                     Integer32,                   
            sslOffPerFilterByCipherHandShake                    RadwareLongDisplayString,    
            sslOffPerFilterRejectedCertificates                 Integer32,                   
            sslOffPerFilterIgnoredCertificates                  Integer32,                   
            sslOffPerFilterExpiredCertificates                  Integer32,                   
            sslOffPerFilterUntrustedCertificates                Integer32,                   
            sslOffPerFilterCertificateHostnameMismatch          Integer32,                   
            sslOffPerFilterPerSessUsingTLS13                    Integer32,                   
            sslOffPerFilter0RTTReusedhandShake                  Integer32,
            sslOffPerFilterRate0RTTReusedhandShake              Integer32,
            sslOffPerFilter0RTTRejectedhandShake                Integer32,
            sslOffPerFilterByRejectedHandShakeReasons           RadwareLongDisplayString,                        
        
            sslOffPerFilterBeNewhandShake                       Integer32,                   
            sslOffPerFilterBeReusedhandShake                    Integer32,                   
            sslOffPerFilterBeRateReusedhandShake                Integer32,                   
            sslOffPerFilterBeSessionIdReusedhandShake           Integer32,
            sslOffPerFilterBeRateSessionIdReusedhandShake       Integer32,
            sslOffPerFilterBeTicketReusedhandShake              Integer32,
            sslOffPerFilterBeRateTicketReusedhandShake          Integer32,
            sslOffPerFilterBePerSessUsingSSLv3                  Integer32,                   
            sslOffPerFilterBePerSessUsingTLS10                  Integer32,                   
            sslOffPerFilterBePerSessUsingTLS11                  Integer32,                   
            sslOffPerFilterBePerSessUsingTLS12                  Integer32,                   
            sslOffPerFilterBeRejectedHandShakes                 Integer32,                   
            sslOffPerFilterBeHttpToHTTPSRedir                   Integer32,                   
            sslOffPerFilterBeByCipherHandShake                  RadwareLongDisplayString,    
            sslOffPerFilterFeRejectedCertificates               Integer32,                   
            sslOffPerFilterFeIgnoredCertificates                Integer32,                   
            sslOffPerFilterFeExpiredCertificates                Integer32,                   
            sslOffPerFilterFeUntrustedCertificates              Integer32,                   
            sslOffPerFilterFeCertificateHostnameMismatch        Integer32,                   
            sslOffPerFilterBePerSessUsingTLS13                  Integer32,                   
            sslOffPerFilterBeByRejectedHandShakeReasons         RadwareLongDisplayString,    
                
            sslOffPerFilterNewhandShakeTotal                    Integer32,                   
            sslOffPerFilterReusedhandShakeTotal                 Integer32,                   
            sslOffPerFilterRateReusedhandShakeTotal             Integer32,                   
            sslOffPerFilterSessionIdReusedhandShakeTotal        Integer32,
            sslOffPerFilterRateSessionIdReusedhandShakeTotal    Integer32,
            sslOffPerFilterTicketReusedhandShakeTotal           Integer32,
            sslOffPerFilterRateTicketReusedhandShakeTotal       Integer32,
            sslOffPerFilterPerSessUsingSSLv3Total               Integer32,                   
            sslOffPerFilterPerSessUsingTLS10Total               Integer32,                   
            sslOffPerFilterPerSessUsingTLS11Total               Integer32,                   
            sslOffPerFilterPerSessUsingTLS12Total               Integer32,                   
            sslOffPerFilterRejectedHandShakesTotal              Integer32,                   
            sslOffPerFilterHttpToHTTPSRedirTotal                Integer32,                   
            sslOffPerFilterByCipherHandShakeTotal               RadwareLongDisplayString,    
            sslOffPerFilterRejectedCertificatesTotal            Integer32,                   
            sslOffPerFilterIgnoredCertificatesTotal             Integer32,                   
            sslOffPerFilterExpiredCertificatesTotal             Integer32,                   
            sslOffPerFilterUntrustedCertificatesTotal           Integer32,                   
            sslOffPerFilterCertificateHostnameMismatchTotal     Integer32,                   
            sslOffPerFilterPerSessUsingTLS13Total               Integer32,                   
            sslOffPerFilterByRejectedHandShakeReasonsTotal      RadwareLongDisplayString,    
          
            sslOffPerFilterBeNewhandShakeTotal                  Integer32,                   
            sslOffPerFilterBeReusedhandShakeTotal               Integer32,                   
            sslOffPerFilterBeRateReusedhandShakeTotal           Integer32,                   
            sslOffPerFilterBeSessionIdReusedhandShakeTotal      Integer32,
            sslOffPerFilterBeRateSessionIdReusedhandShakeTotal  Integer32,
            sslOffPerFilterBeTicketReusedhandShakeTotal         Integer32,
            sslOffPerFilterBeRateTicketReusedhandShakeTotal     Integer32,
            sslOffPerFilterBePerSessUsingSSLv3Total             Integer32,                   
            sslOffPerFilterBePerSessUsingTLS10Total             Integer32,                   
            sslOffPerFilterBePerSessUsingTLS11Total             Integer32,                   
            sslOffPerFilterBePerSessUsingTLS12Total             Integer32,                   
            sslOffPerFilterBeRejectedHandShakesTotal            Integer32,                   
            sslOffPerFilterBeHttpToHTTPSRedirTotal              Integer32,                   
            sslOffPerFilterBeByCipherHandShakeTotal             RadwareLongDisplayString,    
            sslOffPerFilterFeRejectedCertificatesTotal          Integer32,                   
            sslOffPerFilterFeIgnoredCertificatesTotal           Integer32,                   
            sslOffPerFilterFeExpiredCertificatesTotal           Integer32,                   
            sslOffPerFilterFeUntrustedCertificatesTotal         Integer32,                   
            sslOffPerFilterFeCertificateHostnameMismatchTotal   Integer32,                   
            sslOffPerFilterBePerSessUsingTLS13Total             Integer32,                   
            sslOffPerFilterBeByRejectedHandShakeReasonsTotal    RadwareLongDisplayString,

            sslOffPerFilter0RTTReusedhandShakeTotal                  Integer32,
            sslOffPerFilterRate0RTTReusedhandShakeTotal              Integer32,
            sslOffPerFilter0RTTRejectedhandShakeTotal                Integer32
            
           
        }   
		
sslOffPerFilterId  OBJECT-TYPE
   SYNTAX  Integer32 
   MAX-ACCESS  read-only
   STATUS  current
   DESCRIPTION
       "Filter ID."
   ::= {sslOffPerFilterStatsEntry 1}		
   
sslOffPerFilterNewhandShake  OBJECT-TYPE
   SYNTAX  Integer32
   MAX-ACCESS  read-only
   STATUS  current
   DESCRIPTION
       "Number of New SSL handshakes between Clients and AAS per second for this filter."
   ::= {sslOffPerFilterStatsEntry 2} 
   
sslOffPerFilterReusedhandShake  OBJECT-TYPE
   SYNTAX  Integer32
   MAX-ACCESS  read-only
   STATUS  current
   DESCRIPTION
       "Number of Reused SSL handshakes between Clients and AAS per second for this filter."
   ::= {sslOffPerFilterStatsEntry 3}     
   
sslOffPerFilterRateReusedhandShake  OBJECT-TYPE
   SYNTAX  Integer32
   MAX-ACCESS  read-only
   STATUS  current
   DESCRIPTION
       "Number of existing SSL handshakes re-used by clients to communicate with AAS per second for filter."
   ::= {sslOffPerFilterStatsEntry 4} 

sslOffPerFilterPerSessUsingSSLv3  OBJECT-TYPE
   SYNTAX  Integer32
   MAX-ACCESS  read-only
   STATUS  current
   DESCRIPTION
       "Percentage of session using SSLv3 out of all session during measuring period for filter."
   ::= {sslOffPerFilterStatsEntry 5}    
   
sslOffPerFilterPerSessUsingTLS10  OBJECT-TYPE
   SYNTAX  Integer32
   MAX-ACCESS  read-only
   STATUS  current
   DESCRIPTION
       "Percentage of session using TLS1.0 out of all session during measuring period for filter."
   ::= {sslOffPerFilterStatsEntry 6}   

sslOffPerFilterPerSessUsingTLS11  OBJECT-TYPE
   SYNTAX  Integer32
   MAX-ACCESS  read-only
   STATUS  current
   DESCRIPTION
       "Percentage of session using TLS1.1 out of all session during measuring period for filter."
   ::= {sslOffPerFilterStatsEntry 7}    

sslOffPerFilterPerSessUsingTLS12  OBJECT-TYPE
   SYNTAX  Integer32
   MAX-ACCESS  read-only
   STATUS  current
   DESCRIPTION
       "Percentage of session using TLS1.2 out of all session during measuring period for filter."
   ::= {sslOffPerFilterStatsEntry 8}   
   
sslOffPerFilterRejectedHandShakes  OBJECT-TYPE
   SYNTAX  Integer32
   MAX-ACCESS  read-only
   STATUS  current
   DESCRIPTION
       "Number of rejected SSL handshakes per second for filter."
   ::= {sslOffPerFilterStatsEntry 9} 

sslOffPerFilterHttpToHTTPSRedir  OBJECT-TYPE
   SYNTAX  Integer32
   MAX-ACCESS  read-only
   STATUS  current
   DESCRIPTION
       "Number of HTTP redirect location headers updated from HTTP to HTTPS by AAS for filter."
   ::= {sslOffPerFilterStatsEntry 10} 

sslOffPerFilterByCipherHandShake  OBJECT-TYPE
    SYNTAX RadwareLongDisplayString (SIZE (0..10000))
    MAX-ACCESS  read-only
    STATUS  current
    DESCRIPTION
        "Obsolete Mib! please use SslOffPerFilterCipherHandShakeStatsTable instead"
   ::= {sslOffPerFilterStatsEntry 11}

sslOffPerFilterRejectedCertificates  OBJECT-TYPE
   SYNTAX  Integer32
   MAX-ACCESS  read-only
   STATUS  current
   DESCRIPTION
       "Obsolete Mib!"
   ::= {sslOffPerFilterStatsEntry 12} 

sslOffPerFilterIgnoredCertificates  OBJECT-TYPE
   SYNTAX  Integer32
   MAX-ACCESS  read-only
   STATUS  current
   DESCRIPTION
       "Obsolete Mib!"
   ::= {sslOffPerFilterStatsEntry 13} 

sslOffPerFilterExpiredCertificates  OBJECT-TYPE
   SYNTAX  Integer32
   MAX-ACCESS  read-only
   STATUS  current
   DESCRIPTION
       "Obsolete Mib!"
   ::= {sslOffPerFilterStatsEntry 14} 

sslOffPerFilterUntrustedCertificates  OBJECT-TYPE
   SYNTAX  Integer32
   MAX-ACCESS  read-only
   STATUS  current
   DESCRIPTION
       "Obsolete Mib!"
   ::= {sslOffPerFilterStatsEntry 15} 

sslOffPerFilterCertificateHostnameMismatch  OBJECT-TYPE
   SYNTAX  Integer32
   MAX-ACCESS  read-only
   STATUS  current
   DESCRIPTION
       "Obsolete Mib!"
   ::= {sslOffPerFilterStatsEntry 16} 
   
sslOffPerFilterPerSessUsingTLS13  OBJECT-TYPE
   SYNTAX  Integer32
   MAX-ACCESS  read-only
   STATUS  current
   DESCRIPTION
       "Percentage of session using TLS1.3 out of all session during measuring period for filter."
   ::= {sslOffPerFilterStatsEntry 17}   

sslOffPerFilter0RTTReusedhandShake  OBJECT-TYPE
   SYNTAX  Integer32
   MAX-ACCESS  read-only
   STATUS  current
   DESCRIPTION
       "Number of Reused SSL handshakes between Clients and AAS per second for this filter (0-RTT)."
   ::= {sslOffPerFilterStatsEntry 18}

sslOffPerFilterRate0RTTReusedhandShake  OBJECT-TYPE
   SYNTAX  Integer32
   MAX-ACCESS  read-only
   STATUS  current
   DESCRIPTION
       "Number of existing SSL handshakes re-used by clients to communicate with AAS per second for filter (0-RTT)."
   ::= {sslOffPerFilterStatsEntry 19}

sslOffPerFilter0RTTRejectedhandShake  OBJECT-TYPE
   SYNTAX  Integer32
   MAX-ACCESS  read-only
   STATUS  current
   DESCRIPTION
       "Number of rejected SSL handshakes per second for this filter (0-RTT)."
   ::= {sslOffPerFilterStatsEntry 20}
   
sslOffPerFilterByRejectedHandShakeReasons  OBJECT-TYPE
    SYNTAX RadwareLongDisplayString (SIZE (0..10000))
    MAX-ACCESS  read-only
    STATUS  current
    DESCRIPTION
        "Obsolete Mib! please use SslOffPerFilterRejHsReasonsStatsTable instead"
   ::= {sslOffPerFilterStatsEntry 21}   
   
sslOffPerFilterBeNewhandShake  OBJECT-TYPE
   SYNTAX  Integer32
   MAX-ACCESS  read-only
   STATUS  current
   DESCRIPTION
       "Number of New SSL handshakes between Clients and AAS per second for this filter."
   ::= {sslOffPerFilterStatsEntry 22} 
   
sslOffPerFilterBeReusedhandShake  OBJECT-TYPE
   SYNTAX  Integer32
   MAX-ACCESS  read-only
   STATUS  current
   DESCRIPTION
       "Number of Reused SSL handshakes between servers and AAS per second for this filter."
   ::= {sslOffPerFilterStatsEntry 23}     
   
sslOffPerFilterBeRateReusedhandShake  OBJECT-TYPE
   SYNTAX  Integer32
   MAX-ACCESS  read-only
   STATUS  current
   DESCRIPTION
       "Number of existing SSL handshakes re-used by servers to communicate with AAS per second for filter."
   ::= {sslOffPerFilterStatsEntry 24} 

sslOffPerFilterBePerSessUsingSSLv3  OBJECT-TYPE
   SYNTAX  Integer32
   MAX-ACCESS  read-only
   STATUS  current
   DESCRIPTION
       "Percentage of session using SSLv3 out of all session during measuring period for filter."
   ::= {sslOffPerFilterStatsEntry 25}    
   
sslOffPerFilterBePerSessUsingTLS10  OBJECT-TYPE
   SYNTAX  Integer32
   MAX-ACCESS  read-only
   STATUS  current
   DESCRIPTION
       "Percentage of session using TLS1.0 out of all session during measuring period for filter."
   ::= {sslOffPerFilterStatsEntry 26}   

sslOffPerFilterBePerSessUsingTLS11  OBJECT-TYPE
   SYNTAX  Integer32
   MAX-ACCESS  read-only
   STATUS  current
   DESCRIPTION
       "Percentage of session using TLS1.1 out of all session during measuring period for filter."
   ::= {sslOffPerFilterStatsEntry 27}    

sslOffPerFilterBePerSessUsingTLS12  OBJECT-TYPE
   SYNTAX  Integer32
   MAX-ACCESS  read-only
   STATUS  current
   DESCRIPTION
       "Percentage of session using TLS1.2 out of all session during measuring period for filter."
   ::= {sslOffPerFilterStatsEntry 28}   
   
sslOffPerFilterBeRejectedHandShakes  OBJECT-TYPE
   SYNTAX  Integer32
   MAX-ACCESS  read-only
   STATUS  current
   DESCRIPTION
       "Number of rejected SSL handshakes per second for filter."
   ::= {sslOffPerFilterStatsEntry 29} 

sslOffPerFilterBeHttpToHTTPSRedir  OBJECT-TYPE
   SYNTAX  Integer32
   MAX-ACCESS  read-only
   STATUS  current
   DESCRIPTION
       "Number of HTTP redirect location headers updated from HTTP to HTTPS by AAS for filter."
   ::= {sslOffPerFilterStatsEntry 30} 

sslOffPerFilterBeByCipherHandShake  OBJECT-TYPE
    SYNTAX RadwareLongDisplayString (SIZE (0..10000))
    MAX-ACCESS  read-only
    STATUS  current
    DESCRIPTION
        "Obsolete Mib! please use SslBeOffPerFilterCipherHandShakeStatsTable instead"
   ::= {sslOffPerFilterStatsEntry 31}

sslOffPerFilterFeRejectedCertificates  OBJECT-TYPE
   SYNTAX  Integer32
   MAX-ACCESS  read-only
   STATUS  current
   DESCRIPTION
       "Obsolete Mib!"
   ::= {sslOffPerFilterStatsEntry 32} 

sslOffPerFilterFeIgnoredCertificates  OBJECT-TYPE
   SYNTAX  Integer32
   MAX-ACCESS  read-only
   STATUS  current
   DESCRIPTION
       "Obsolete Mib!"
   ::= {sslOffPerFilterStatsEntry 33} 

sslOffPerFilterFeExpiredCertificates  OBJECT-TYPE
   SYNTAX  Integer32
   MAX-ACCESS  read-only
   STATUS  current
   DESCRIPTION
       "Obsolete Mib!"
   ::= {sslOffPerFilterStatsEntry 34} 

sslOffPerFilterFeUntrustedCertificates  OBJECT-TYPE
   SYNTAX  Integer32
   MAX-ACCESS  read-only
   STATUS  current
   DESCRIPTION
       "Obsolete Mib!"
   ::= {sslOffPerFilterStatsEntry 35} 

sslOffPerFilterFeCertificateHostnameMismatch  OBJECT-TYPE
   SYNTAX  Integer32
   MAX-ACCESS  read-only
   STATUS  current
   DESCRIPTION
       "Obsolete Mib!"
   ::= {sslOffPerFilterStatsEntry 36} 
   
sslOffPerFilterBePerSessUsingTLS13  OBJECT-TYPE
   SYNTAX  Integer32
   MAX-ACCESS  read-only
   STATUS  current
   DESCRIPTION
       "Percentage of session using TLS1.3 out of all session during measuring period for filter."
   ::= {sslOffPerFilterStatsEntry 37}   
   
sslOffPerFilterNewhandShakeTotal  OBJECT-TYPE
   SYNTAX  Integer32
   MAX-ACCESS  read-only
   STATUS  current
   DESCRIPTION
       "Number of New SSL handshakes between Clients and AAS since last reset for this filter."
   ::= {sslOffPerFilterStatsEntry 38} 
   
sslOffPerFilterBeByRejectedHandShakeReasons  OBJECT-TYPE
    SYNTAX RadwareLongDisplayString (SIZE (0..10000))
    MAX-ACCESS  read-only
    STATUS  current
    DESCRIPTION
        "Obsolete Mib! please use SslBeOffPerFilterRejHsReasonsStatsTable instead"
   ::= {sslOffPerFilterStatsEntry 39}
   
sslOffPerFilterReusedhandShakeTotal  OBJECT-TYPE
   SYNTAX  Integer32
   MAX-ACCESS  read-only
   STATUS  current
   DESCRIPTION
       "Number of Reused SSL handshakes between Clients and AAS since last reset for this filter."
   ::= {sslOffPerFilterStatsEntry 40}     
   
sslOffPerFilterRateReusedhandShakeTotal  OBJECT-TYPE
   SYNTAX  Integer32
   MAX-ACCESS  read-only
   STATUS  current
   DESCRIPTION
       "Number of existing SSL handshakes re-used by clients to communicate with AAS since last reset for filter."
   ::= {sslOffPerFilterStatsEntry 41} 

sslOffPerFilterPerSessUsingSSLv3Total  OBJECT-TYPE
   SYNTAX  Integer32
   MAX-ACCESS  read-only
   STATUS  current
   DESCRIPTION
       "Percentage of session using SSLv3 out of all session since last reset for filter."
   ::= {sslOffPerFilterStatsEntry 42}    
   
sslOffPerFilterPerSessUsingTLS10Total  OBJECT-TYPE
   SYNTAX  Integer32
   MAX-ACCESS  read-only
   STATUS  current
   DESCRIPTION
       "Percentage of session using TLS1.0 out of all session since last reset for filter."
   ::= {sslOffPerFilterStatsEntry 43}   

sslOffPerFilterPerSessUsingTLS11Total  OBJECT-TYPE
   SYNTAX  Integer32
   MAX-ACCESS  read-only
   STATUS  current
   DESCRIPTION
       "Percentage of session using TLS1.1 out of all session since last reset for filter."
   ::= {sslOffPerFilterStatsEntry 44}    

sslOffPerFilterPerSessUsingTLS12Total  OBJECT-TYPE
   SYNTAX  Integer32
   MAX-ACCESS  read-only
   STATUS  current
   DESCRIPTION
       "Percentage of session using TLS1.2 out of all session since last reset for filter."
   ::= {sslOffPerFilterStatsEntry 45}   
   
sslOffPerFilterRejectedHandShakesTotal  OBJECT-TYPE
   SYNTAX  Integer32
   MAX-ACCESS  read-only
   STATUS  current
   DESCRIPTION
       "Number of rejected SSL handshakes since last reset for filter."
   ::= {sslOffPerFilterStatsEntry 46} 

sslOffPerFilterHttpToHTTPSRedirTotal  OBJECT-TYPE
   SYNTAX  Integer32
   MAX-ACCESS  read-only
   STATUS  current
   DESCRIPTION
       "Number of HTTP redirect location headers updated from HTTP to HTTPS by AAS for filter."
   ::= {sslOffPerFilterStatsEntry 47} 

sslOffPerFilterByCipherHandShakeTotal  OBJECT-TYPE
    SYNTAX RadwareLongDisplayString (SIZE (0..10000))
    MAX-ACCESS  read-only
    STATUS  current
    DESCRIPTION
        "Obsolete Mib! please use SslOffPerFilterCipherHandShakeStatsTable instead"
   ::= {sslOffPerFilterStatsEntry 48}

sslOffPerFilterRejectedCertificatesTotal  OBJECT-TYPE
   SYNTAX  Integer32
   MAX-ACCESS  read-only
   STATUS  current
   DESCRIPTION
       "Obsolete Mib!"
   ::= {sslOffPerFilterStatsEntry 49} 

sslOffPerFilterIgnoredCertificatesTotal  OBJECT-TYPE
   SYNTAX  Integer32
   MAX-ACCESS  read-only
   STATUS  current
   DESCRIPTION
       "Obsolete Mib!"
   ::= {sslOffPerFilterStatsEntry 50} 

sslOffPerFilterExpiredCertificatesTotal  OBJECT-TYPE
   SYNTAX  Integer32
   MAX-ACCESS  read-only
   STATUS  current
   DESCRIPTION
       "Obsolete Mib!"
   ::= {sslOffPerFilterStatsEntry 51} 

sslOffPerFilterUntrustedCertificatesTotal  OBJECT-TYPE
   SYNTAX  Integer32
   MAX-ACCESS  read-only
   STATUS  current
   DESCRIPTION
       "Obsolete Mib!"
   ::= {sslOffPerFilterStatsEntry 52} 

sslOffPerFilterCertificateHostnameMismatchTotal  OBJECT-TYPE
   SYNTAX  Integer32
   MAX-ACCESS  read-only
   STATUS  current
   DESCRIPTION
       "Obsolete Mib!"
   ::= {sslOffPerFilterStatsEntry 53} 
   
sslOffPerFilterPerSessUsingTLS13Total  OBJECT-TYPE
   SYNTAX  Integer32
   MAX-ACCESS  read-only
   STATUS  current
   DESCRIPTION
       "Percentage of session using TLS1.3 out of all session since last reset for filter."
   ::= {sslOffPerFilterStatsEntry 54}   
   
sslOffPerFilterBeNewhandShakeTotal  OBJECT-TYPE
   SYNTAX  Integer32
   MAX-ACCESS  read-only
   STATUS  current
   DESCRIPTION
       "Number of New SSL handshakes between servers and AAS since last reset for this filter."
   ::= {sslOffPerFilterStatsEntry 55} 
   
sslOffPerFilterBeReusedhandShakeTotal  OBJECT-TYPE
   SYNTAX  Integer32
   MAX-ACCESS  read-only
   STATUS  current
   DESCRIPTION
       "Number of Reused SSL handshakes between servers and AAS since last reset for this filter."
   ::= {sslOffPerFilterStatsEntry 56}     
   
sslOffPerFilterByRejectedHandShakeReasonsTotal  OBJECT-TYPE
    SYNTAX RadwareLongDisplayString (SIZE (0..10000))
    MAX-ACCESS  read-only
    STATUS  current
    DESCRIPTION
        "Obsolete Mib! please use SslOffPerFilterRejHsReasonsStatsTable instead"
   ::= {sslOffPerFilterStatsEntry 57}
   
sslOffPerFilterBeRateReusedhandShakeTotal  OBJECT-TYPE
   SYNTAX  Integer32
   MAX-ACCESS  read-only
   STATUS  current
   DESCRIPTION
       "Number of existing SSL handshakes re-used by servers to communicate with AAS since last reset for filter."
   ::= {sslOffPerFilterStatsEntry 58} 

sslOffPerFilterBePerSessUsingSSLv3Total  OBJECT-TYPE
   SYNTAX  Integer32
   MAX-ACCESS  read-only
   STATUS  current
   DESCRIPTION
       "Percentage of session using SSLv3 out of all session since last reset for filter."
   ::= {sslOffPerFilterStatsEntry 59}    
   
sslOffPerFilterBePerSessUsingTLS10Total  OBJECT-TYPE
   SYNTAX  Integer32
   MAX-ACCESS  read-only
   STATUS  current
   DESCRIPTION
       "Percentage of session using TLS1.0 out of all session since last reset for filter."
   ::= {sslOffPerFilterStatsEntry 60}   

sslOffPerFilterBePerSessUsingTLS11Total  OBJECT-TYPE
   SYNTAX  Integer32
   MAX-ACCESS  read-only
   STATUS  current
   DESCRIPTION
       "Percentage of session using TLS1.1 out of all session since last reset for filter."
   ::= {sslOffPerFilterStatsEntry 61}    

sslOffPerFilterBePerSessUsingTLS12Total  OBJECT-TYPE
   SYNTAX  Integer32
   MAX-ACCESS  read-only
   STATUS  current
   DESCRIPTION
       "Percentage of session using TLS1.2 out of all session since last reset for filter."
   ::= {sslOffPerFilterStatsEntry 62}   
   
sslOffPerFilterBeRejectedHandShakesTotal  OBJECT-TYPE
   SYNTAX  Integer32
   MAX-ACCESS  read-only
   STATUS  current
   DESCRIPTION
       "Number of rejected SSL handshakes since last reset for filter."
   ::= {sslOffPerFilterStatsEntry 63} 

sslOffPerFilterBeHttpToHTTPSRedirTotal  OBJECT-TYPE
   SYNTAX  Integer32
   MAX-ACCESS  read-only
   STATUS  current
   DESCRIPTION
       "Number of HTTP redirect location headers updated from HTTP to HTTPS by AAS for filter."
   ::= {sslOffPerFilterStatsEntry 64} 

sslOffPerFilterBeByCipherHandShakeTotal  OBJECT-TYPE
    SYNTAX RadwareLongDisplayString (SIZE (0..10000))
    MAX-ACCESS  read-only
    STATUS  current
    DESCRIPTION
        "Obsolete Mib! please use SslBeOffPerFilterCipherHandShakeStatsTable instead"
   ::= {sslOffPerFilterStatsEntry 65}

sslOffPerFilterFeRejectedCertificatesTotal  OBJECT-TYPE
   SYNTAX  Integer32
   MAX-ACCESS  read-only
   STATUS  current
   DESCRIPTION
       "Obsolete Mib!"
   ::= {sslOffPerFilterStatsEntry 66} 

sslOffPerFilterFeIgnoredCertificatesTotal  OBJECT-TYPE
   SYNTAX  Integer32
   MAX-ACCESS  read-only
   STATUS  current
   DESCRIPTION
       "Obsolete Mib!"
   ::= {sslOffPerFilterStatsEntry 67} 

sslOffPerFilterFeExpiredCertificatesTotal  OBJECT-TYPE
   SYNTAX  Integer32
   MAX-ACCESS  read-only
   STATUS  current
   DESCRIPTION
       "Obsolete Mib!"
   ::= {sslOffPerFilterStatsEntry 68} 

sslOffPerFilterFeUntrustedCertificatesTotal  OBJECT-TYPE
   SYNTAX  Integer32
   MAX-ACCESS  read-only
   STATUS  current
   DESCRIPTION
       "Obsolete Mib!"
   ::= {sslOffPerFilterStatsEntry 69} 

sslOffPerFilterFeCertificateHostnameMismatchTotal  OBJECT-TYPE
   SYNTAX  Integer32
   MAX-ACCESS  read-only
   STATUS  current
   DESCRIPTION
       "Obsolete Mib!"
   ::= {sslOffPerFilterStatsEntry 70} 
   
sslOffPerFilterBePerSessUsingTLS13Total  OBJECT-TYPE
   SYNTAX  Integer32
   MAX-ACCESS  read-only
   STATUS  current
   DESCRIPTION
       "Percentage of session using TLS1.3 out of all session since last reset for filter."
   ::= {sslOffPerFilterStatsEntry 71}
   
sslOffPerFilterBeByRejectedHandShakeReasonsTotal  OBJECT-TYPE
    SYNTAX RadwareLongDisplayString (SIZE (0..10000))
    MAX-ACCESS  read-only
    STATUS  current
    DESCRIPTION
        "Obsolete Mib! please use SslBeOffPerFilterRejHsReasonsStatsTable instead"
   ::= {sslOffPerFilterStatsEntry 72}  

sslOffPerFilter0RTTReusedhandShakeTotal OBJECT-TYPE
   SYNTAX  Integer32
   MAX-ACCESS  read-only
   STATUS  current
   DESCRIPTION
       "Number of existing SSL handshakes re-used by clients to communicate with AAS for filter (0-RTT) since last reset."
   ::= {sslOffPerFilterStatsEntry 73}

sslOffPerFilterRate0RTTReusedhandShakeTotal OBJECT-TYPE
   SYNTAX  Integer32
   MAX-ACCESS  read-only
   STATUS  current
   DESCRIPTION
       "Percentage of SSL session re-using keys for filter (0-RTT) since last reset."
   ::= {sslOffPerFilterStatsEntry 74}

sslOffPerFilter0RTTRejectedhandShakeTotal OBJECT-TYPE
   SYNTAX  Integer32
   MAX-ACCESS  read-only
   STATUS  current
   DESCRIPTION
       "Number of rejected SSL handshakes for filter (0-RTT) since last reset."
   ::= {sslOffPerFilterStatsEntry 75}

sslOffPerFilterSessionIdReusedhandShake  OBJECT-TYPE
   SYNTAX  Integer32
   MAX-ACCESS  read-only
   STATUS  current
   DESCRIPTION
       "Number of Session Id Reused SSL handshakes between Clients and AAS per second for this filter."
   ::= {sslOffPerFilterStatsEntry 76}

sslOffPerFilterRateSessionIdReusedhandShake  OBJECT-TYPE
   SYNTAX  Integer32
   MAX-ACCESS  read-only
   STATUS  current
   DESCRIPTION
       "Number of existing SSL handshakes Session Id re-used by clients to communicate with AAS per second for filter."
   ::= {sslOffPerFilterStatsEntry 77}

sslOffPerFilterBeSessionIdReusedhandShake  OBJECT-TYPE
   SYNTAX  Integer32
   MAX-ACCESS  read-only
   STATUS  current
   DESCRIPTION
       "Number of Session Id Reused SSL handshakes between servers and AAS per second for this filter."
   ::= {sslOffPerFilterStatsEntry 78}

sslOffPerFilterBeRateSessionIdReusedhandShake  OBJECT-TYPE
   SYNTAX  Integer32
   MAX-ACCESS  read-only
   STATUS  current
   DESCRIPTION
       "Number of existing SSL handshakes Session Id re-used by servers to communicate with AAS per second for filter."
   ::= {sslOffPerFilterStatsEntry 79}

sslOffPerFilterSessionIdReusedhandShakeTotal  OBJECT-TYPE
   SYNTAX  Integer32
   MAX-ACCESS  read-only
   STATUS  current
   DESCRIPTION
       "Number of Session Id Reused SSL handshakes between Clients and AAS since last reset for this filter."
   ::= {sslOffPerFilterStatsEntry 80}

sslOffPerFilterRateSessionIdReusedhandShakeTotal  OBJECT-TYPE
   SYNTAX  Integer32
   MAX-ACCESS  read-only
   STATUS  current
   DESCRIPTION
       "Number of existing SSL handshakes Session Id re-used by clients to communicate with AAS since last reset for filter."
   ::= {sslOffPerFilterStatsEntry 81}

   
sslOffPerFilterBeSessionIdReusedhandShakeTotal  OBJECT-TYPE
   SYNTAX  Integer32
   MAX-ACCESS  read-only
   STATUS  current
   DESCRIPTION
       "Number of Session Id Reused SSL handshakes between servers and AAS since last reset for this filter."
   ::= {sslOffPerFilterStatsEntry 82}

sslOffPerFilterBeRateSessionIdReusedhandShakeTotal  OBJECT-TYPE
   SYNTAX  Integer32
   MAX-ACCESS  read-only
   STATUS  current
   DESCRIPTION
       "Number of existing SSL handshakes Session Id re-used by servers to communicate with AAS since last reset for filter."
   ::= {sslOffPerFilterStatsEntry 83}

sslOffPerFilterTicketReusedhandShake  OBJECT-TYPE
   SYNTAX  Integer32
   MAX-ACCESS  read-only
   STATUS  current
   DESCRIPTION
       "Number of Ticket Reused SSL handshakes between Clients and AAS per second for this filter."
   ::= {sslOffPerFilterStatsEntry 84}

sslOffPerFilterRateTicketReusedhandShake  OBJECT-TYPE
   SYNTAX  Integer32
   MAX-ACCESS  read-only
   STATUS  current
   DESCRIPTION
       "Number of existing SSL handshakes Ticket re-used by clients to communicate with AAS per second for filter."
   ::= {sslOffPerFilterStatsEntry 85}

sslOffPerFilterBeTicketReusedhandShake  OBJECT-TYPE
   SYNTAX  Integer32
   MAX-ACCESS  read-only
   STATUS  current
   DESCRIPTION
       "Number of Ticket Reused SSL handshakes between servers and AAS per second for this filter."
   ::= {sslOffPerFilterStatsEntry 86}

sslOffPerFilterBeRateTicketReusedhandShake  OBJECT-TYPE
   SYNTAX  Integer32
   MAX-ACCESS  read-only
   STATUS  current
   DESCRIPTION
       "Number of existing SSL handshakes Ticket re-used by servers to communicate with AAS per second for filter."
   ::= {sslOffPerFilterStatsEntry 87}

sslOffPerFilterTicketReusedhandShakeTotal  OBJECT-TYPE
   SYNTAX  Integer32
   MAX-ACCESS  read-only
   STATUS  current
   DESCRIPTION
       "Number of Ticket Reused SSL handshakes between Clients and AAS since last reset for this filter."
   ::= {sslOffPerFilterStatsEntry 88}

sslOffPerFilterRateTicketReusedhandShakeTotal  OBJECT-TYPE
   SYNTAX  Integer32
   MAX-ACCESS  read-only
   STATUS  current
   DESCRIPTION
       "Number of existing SSL handshakes Ticket re-used by clients to communicate with AAS since last reset for filter."
   ::= {sslOffPerFilterStatsEntry 89}

   
sslOffPerFilterBeTicketReusedhandShakeTotal  OBJECT-TYPE
   SYNTAX  Integer32
   MAX-ACCESS  read-only
   STATUS  current
   DESCRIPTION
       "Number of Ticket Reused SSL handshakes between servers and AAS since last reset for this filter."
   ::= {sslOffPerFilterStatsEntry 90}

sslOffPerFilterBeRateTicketReusedhandShakeTotal  OBJECT-TYPE
   SYNTAX  Integer32
   MAX-ACCESS  read-only
   STATUS  current
   DESCRIPTION
       "Number of existing SSL handshakes Ticket re-used by servers to communicate with AAS since last reset for filter."
   ::= {sslOffPerFilterStatsEntry 91}



sslOffPerFilterCipherHandShakeStatsTable OBJECT-TYPE
   SYNTAX SEQUENCE OF SslOffPerFilterCipherHandShakeStatsEntry
   MAX-ACCESS not-accessible
   STATUS current
   DESCRIPTION
       "A table for frontend SSL Cipher hand shake current and total statistics per filter.
        Note:This mib is not supported for VX instance of Virtualization."
   ::= {sslSlbStats 73}   
   
sslOffPerFilterCipherHandShakeStatsEntry OBJECT-TYPE
   SYNTAX SslOffPerFilterCipherHandShakeStatsEntry
   MAX-ACCESS not-accessible
   STATUS  current
   DESCRIPTION
       " The row definition for SSL statistics per filter table.
         Note:This mib is not supported for VX instance of Virtualization."
   INDEX  {sslOffPerFilterCipherHandShakeFiltId, sslOffPerFilterByCipherHandShakeCipherName}
   ::= {sslOffPerFilterCipherHandShakeStatsTable 1}
   
SslOffPerFilterCipherHandShakeStatsEntry  ::= SEQUENCE {
        sslOffPerFilterCipherHandShakeFiltId                               	Integer32,
	sslOffPerFilterByCipherHandShakeCipherName				DisplayString,			
	sslOffPerFilterByCipherHandShakeCipherHits				Integer32,
	sslOffPerFilterByCipherHandShakeCipherHitsTotal				Integer32
		}
		
sslOffPerFilterCipherHandShakeFiltId  OBJECT-TYPE
   SYNTAX  Integer32 
   MAX-ACCESS  read-only
   STATUS  current
   DESCRIPTION
       "Filter ID."
   ::= {sslOffPerFilterCipherHandShakeStatsEntry 1}		
   
   
sslOffPerFilterByCipherHandShakeCipherName  OBJECT-TYPE
   SYNTAX  DisplayString
   MAX-ACCESS  read-only
   STATUS  current
   DESCRIPTION
       "Cipher index."
   ::= {sslOffPerFilterCipherHandShakeStatsEntry 2}     
   
sslOffPerFilterByCipherHandShakeCipherHits  OBJECT-TYPE
   SYNTAX  Integer32
   MAX-ACCESS  read-only
   STATUS  current
   DESCRIPTION
       "Number of existing SSL handshakes re-used by clients to communicate with AAS per second for filter."
   ::= {sslOffPerFilterCipherHandShakeStatsEntry 3}   

sslOffPerFilterByCipherHandShakeCipherHitsTotal  OBJECT-TYPE
   SYNTAX  Integer32
   MAX-ACCESS  read-only
   STATUS  current
   DESCRIPTION
       "Number of existing SSL handshakes re-used by clients to communicate with AAS per second for filter."
   ::= {sslOffPerFilterCipherHandShakeStatsEntry 4}   

sslBeOffPerFilterCipherHandShakeStatsTable OBJECT-TYPE
   SYNTAX SEQUENCE OF SslBeOffPerFilterCipherHandShakeStatsEntry
   MAX-ACCESS not-accessible
   STATUS current
   DESCRIPTION
       "A table for backend SSL Cipher hand shake current and total statistics per filter.
        Note:This mib is not supported for VX instance of Virtualization."
   ::= {sslSlbStats 74}

sslBeOffPerFilterCipherHandShakeStatsEntry OBJECT-TYPE
   SYNTAX SslBeOffPerFilterCipherHandShakeStatsEntry
   MAX-ACCESS not-accessible
   STATUS  current
   DESCRIPTION
       " The row definition for SSL statistics per filter table."
   INDEX  {sslBeOffPerFilterCipherHandShakeFiltId, sslBeOffPerFilterByCipherHandShakeCipherName}
   ::= {sslBeOffPerFilterCipherHandShakeStatsTable 1}
   
SslBeOffPerFilterCipherHandShakeStatsEntry  ::= SEQUENCE {
        sslBeOffPerFilterCipherHandShakeFiltId                               	Integer32,
	sslBeOffPerFilterByCipherHandShakeCipherName				DisplayString,			
	sslBeOffPerFilterByCipherHandShakeCipherHits				Integer32,
	sslBeOffPerFilterByCipherHandShakeCipherHitsTotal			Integer32
		}
		
sslBeOffPerFilterCipherHandShakeFiltId  OBJECT-TYPE
   SYNTAX  Integer32 
   MAX-ACCESS  read-only
   STATUS  current
   DESCRIPTION
       "Filter ID."
   ::= {sslBeOffPerFilterCipherHandShakeStatsEntry 1}		
   
   
sslBeOffPerFilterByCipherHandShakeCipherName  OBJECT-TYPE
   SYNTAX  DisplayString
   MAX-ACCESS  read-only
   STATUS  current
   DESCRIPTION
       "Cipher index."
   ::= {sslBeOffPerFilterCipherHandShakeStatsEntry 2}     
   
sslBeOffPerFilterByCipherHandShakeCipherHits  OBJECT-TYPE
   SYNTAX  Integer32
   MAX-ACCESS  read-only
   STATUS  current
   DESCRIPTION
       "Number of existing SSL handshakes re-used by AAS to communicate with server per second for filter."
   ::= {sslBeOffPerFilterCipherHandShakeStatsEntry 3}   

sslBeOffPerFilterByCipherHandShakeCipherHitsTotal  OBJECT-TYPE
   SYNTAX  Integer32
   MAX-ACCESS  read-only
   STATUS  current
   DESCRIPTION
       "Number of total SSL handshakes re-used by AAS to communicate with server per second for filter."
   ::= {sslBeOffPerFilterCipherHandShakeStatsEntry 4}   

sslBeOffPerCiphServStatsTable OBJECT-TYPE	
   SYNTAX SEQUENCE OF SslBeOffPerCiphServStatsEntry	
   MAX-ACCESS not-accessible	
   STATUS current	
   DESCRIPTION	
       "A table for backend SSL statistics per virtual service.
        Note:This mib is not supported for VX instance of Virtualization."
   ::= {sslSlbStats 75}

sslBeOffPerCiphServStatsEntry OBJECT-TYPE
   SYNTAX SslBeOffPerCiphServStatsEntry
   MAX-ACCESS not-accessible
   STATUS  current
   DESCRIPTION
       " The row definition for SSL statistics per virtual service table."
   INDEX  { sslBeOffPerCiphServVirtServIndex, sslBeOffPerCiphServVirtServiceIndex, sslBeOffPerCiphServVirtCiphIndex}
   ::= {sslBeOffPerCiphServStatsTable 1}

SslBeOffPerCiphServStatsEntry  ::= SEQUENCE {
        sslBeOffPerCiphServVirtServIndex           DisplayString,
        sslBeOffPerCiphServVirtServiceIndex        Integer32,
        sslBeOffPerCiphServVirtCiphIndex           Integer32,
        sslBeOffPerCiphServCiphName                DisplayString,
        sslBeOffPerCiphServNewhandShake            Integer32,
        sslBeOffPerCiphServVirtServPort            Integer32,
        sslBeOffPerCiphServNewhandShakeTotal       Integer32
        }

sslBeOffPerCiphServVirtServIndex  OBJECT-TYPE
    SYNTAX  DisplayString
    MAX-ACCESS  read-only
    STATUS  current
    DESCRIPTION
        "The virtual server name that identifies the service."
   ::= {sslBeOffPerCiphServStatsEntry 1}

sslBeOffPerCiphServVirtServiceIndex  OBJECT-TYPE
   SYNTAX  Integer32
   MAX-ACCESS  read-only
   STATUS  current
   DESCRIPTION
       "Virtual server service index."
   ::= {sslBeOffPerCiphServStatsEntry 2}

sslBeOffPerCiphServVirtCiphIndex  OBJECT-TYPE
   SYNTAX  Integer32
   MAX-ACCESS  read-only
   STATUS  current
   DESCRIPTION
       "Virtual server service cipher index."
   ::= {sslBeOffPerCiphServStatsEntry 3}

sslBeOffPerCiphServCiphName  OBJECT-TYPE
   SYNTAX  DisplayString
   MAX-ACCESS  read-only
   STATUS  current
   DESCRIPTION
       "Virtual server service cipher name."
   ::= {sslBeOffPerCiphServStatsEntry 4}

sslBeOffPerCiphServNewhandShake  OBJECT-TYPE
   SYNTAX  Integer32
   MAX-ACCESS  read-only
   STATUS  current
   DESCRIPTION
       "Number of New SSL handshakes between AAS and server per second for this virtual service."
   ::= {sslBeOffPerCiphServStatsEntry 5}

sslBeOffPerCiphServVirtServPort  OBJECT-TYPE
   SYNTAX  Integer32
   MAX-ACCESS  read-only
   STATUS  current
   DESCRIPTION
       "Virtual server service port number."
   ::= {sslBeOffPerCiphServStatsEntry 6}
   
sslBeOffPerCiphServNewhandShakeTotal  OBJECT-TYPE
   SYNTAX  Integer32
   MAX-ACCESS  read-only
   STATUS  current
   DESCRIPTION
       "Number of total SSL handshakes between AAS and server per second for this virtual service."
   ::= {sslBeOffPerCiphServStatsEntry 7}

sslOffPerFilterRejHsReasonsStatsTable OBJECT-TYPE
   SYNTAX SEQUENCE OF SslOffPerFilterRejHsReasonsStatsEntry
   MAX-ACCESS not-accessible
   STATUS current
   DESCRIPTION
       "A table for frontend SSL Rejected hand shake reasons current and total statistics per filter.
        Note:This mib is not supported for VX instance of Virtualization."
   ::= {sslSlbStats 76}

sslOffPerFilterRejHsReasonsStatsEntry OBJECT-TYPE
   SYNTAX SslOffPerFilterRejHsReasonsStatsEntry
   MAX-ACCESS not-accessible
   STATUS  current
   DESCRIPTION
       " The row definition for SSL statistics per filter table.
        Note:This mib is not supported for VX instance of Virtualization."
   INDEX  {sslOffPerFilterRejHsReasonsFiltId, sslOffPerFilterRejHsReasonsName}
   ::= {sslOffPerFilterRejHsReasonsStatsTable 1}
   
SslOffPerFilterRejHsReasonsStatsEntry  ::= SEQUENCE {
        sslOffPerFilterRejHsReasonsFiltId                           Integer32,
	sslOffPerFilterRejHsReasonsName				DisplayString,			
	sslOffPerFilterRejHsReasonsHits				Integer32,
	sslOffPerFilterRejHsReasonsHitsTotal			Integer32
		}
		
sslOffPerFilterRejHsReasonsFiltId  OBJECT-TYPE
   SYNTAX  Integer32 
   MAX-ACCESS  read-only
   STATUS  current
   DESCRIPTION
       "Filter ID."
   ::= {sslOffPerFilterRejHsReasonsStatsEntry 1}		
   
   
sslOffPerFilterRejHsReasonsName  OBJECT-TYPE
   SYNTAX  DisplayString
   MAX-ACCESS  read-only
   STATUS  current
   DESCRIPTION
       "Cipher index."
   ::= {sslOffPerFilterRejHsReasonsStatsEntry 2}     
   
sslOffPerFilterRejHsReasonsHits  OBJECT-TYPE
   SYNTAX  Integer32
   MAX-ACCESS  read-only
   STATUS  current
   DESCRIPTION
       "Number of existing SSL handshakes re-used by clients to communicate with AAS per second for filter."
   ::= {sslOffPerFilterRejHsReasonsStatsEntry 3}   

sslOffPerFilterRejHsReasonsHitsTotal  OBJECT-TYPE
   SYNTAX  Integer32
   MAX-ACCESS  read-only
   STATUS  current
   DESCRIPTION
       "Number of existing SSL handshakes re-used by clients to communicate with AAS per second for filter."
   ::= {sslOffPerFilterRejHsReasonsStatsEntry 4}
   
sslBeOffPerFilterRejHsReasonsStatsTable OBJECT-TYPE
   SYNTAX SEQUENCE OF SslBeOffPerFilterRejHsReasonsStatsEntry
   MAX-ACCESS not-accessible
   STATUS current
   DESCRIPTION
       "A table for backend SSL Rejected hand shake reasons current and total statistics per filter.
        Note:This mib is not supported for VX instance of Virtualization."
   ::= {sslSlbStats 77}

sslBeOffPerFilterRejHsReasonsStatsEntry OBJECT-TYPE
   SYNTAX SslBeOffPerFilterRejHsReasonsStatsEntry
   MAX-ACCESS not-accessible
   STATUS  current
   DESCRIPTION
       " The row definition for SSL statistics per filter table.
        Note:This mib is not supported for VX instance of Virtualization."
   INDEX  {sslBeOffPerFilterRejHsReasonsFiltId, sslBeOffPerFilterRejHsReasonsName}
   ::= {sslBeOffPerFilterRejHsReasonsStatsTable 1}
   
SslBeOffPerFilterRejHsReasonsStatsEntry  ::= SEQUENCE {
        sslBeOffPerFilterRejHsReasonsFiltId                           Integer32,
	sslBeOffPerFilterRejHsReasonsName				DisplayString,			
	sslBeOffPerFilterRejHsReasonsHits				Integer32,
	sslBeOffPerFilterRejHsReasonsHitsTotal			Integer32
	}
		
sslBeOffPerFilterRejHsReasonsFiltId  OBJECT-TYPE
   SYNTAX  Integer32 
   MAX-ACCESS  read-only
   STATUS  current
   DESCRIPTION
       "Filter ID."
   ::= {sslBeOffPerFilterRejHsReasonsStatsEntry 1}		
   
   
sslBeOffPerFilterRejHsReasonsName  OBJECT-TYPE
   SYNTAX  DisplayString
   MAX-ACCESS  read-only
   STATUS  current
   DESCRIPTION
       "Cipher index."
   ::= {sslBeOffPerFilterRejHsReasonsStatsEntry 2}     
   
sslBeOffPerFilterRejHsReasonsHits  OBJECT-TYPE
   SYNTAX  Integer32
   MAX-ACCESS  read-only
   STATUS  current
   DESCRIPTION
       "Number of existing SSL handshakes re-used by AAS to communicate with server per second for filter."
   ::= {sslBeOffPerFilterRejHsReasonsStatsEntry 3}   

sslBeOffPerFilterRejHsReasonsHitsTotal  OBJECT-TYPE
   SYNTAX  Integer32
   MAX-ACCESS  read-only
   STATUS  current
   DESCRIPTION
       "Number of total SSL handshakes re-used by AAS to communicate with server per second for filter."
   ::= {sslBeOffPerFilterRejHsReasonsStatsEntry 4}

sslOffPerServRejHsReasonsStatsTable OBJECT-TYPE
   SYNTAX SEQUENCE OF SslOffPerServRejHsReasonsStatsEntry
   MAX-ACCESS not-accessible
   STATUS current
   DESCRIPTION
       "A table for frontend SSL Rejected hand shake reasons current and total statistics per service.
        Note:This mib is not supported for VX instance of Virtualization."
   ::= {sslSlbStats 78}

sslOffPerServRejHsReasonsStatsEntry OBJECT-TYPE
   SYNTAX SslOffPerServRejHsReasonsStatsEntry
   MAX-ACCESS not-accessible
   STATUS  current
   DESCRIPTION
       " The row definition for SSL statistics per virtual service table.
        Note:This mib is not supported for VX instance of Virtualization."
   INDEX  { sslOffPerServRejHsReasonsVirtServIndex, sslOffPerServRejHsReasonsVirtServiceIndex, sslOffPerServRejHsReasonsVirtRejHsIndex}
   ::= {sslOffPerServRejHsReasonsStatsTable 1}

SslOffPerServRejHsReasonsStatsEntry  ::= SEQUENCE {
        sslOffPerServRejHsReasonsVirtServIndex           DisplayString,
        sslOffPerServRejHsReasonsVirtServiceIndex        Integer32,
        sslOffPerServRejHsReasonsVirtRejHsIndex           Integer32,
        sslOffPerServRejHsReasonsRejHsName                DisplayString,
        sslOffPerServRejHsReasonsNewHandShake            Integer32,
        sslOffPerServRejHsReasonsVirtServPort            Integer32,
        sslOffPerServRejHsReasonsNewHandShakeTotal       Integer32
        }

sslOffPerServRejHsReasonsVirtServIndex  OBJECT-TYPE
    SYNTAX  DisplayString
    MAX-ACCESS  read-only
    STATUS  current
    DESCRIPTION
        "The virtual server name that identifies the service."
   ::= {sslOffPerServRejHsReasonsStatsEntry 1}

sslOffPerServRejHsReasonsVirtServiceIndex  OBJECT-TYPE
   SYNTAX  Integer32
   MAX-ACCESS  read-only
   STATUS  current
   DESCRIPTION
       "Virtual server service index."
   ::= {sslOffPerServRejHsReasonsStatsEntry 2}

sslOffPerServRejHsReasonsVirtRejHsIndex  OBJECT-TYPE
   SYNTAX  Integer32
   MAX-ACCESS  read-only
   STATUS  current
   DESCRIPTION
       "Virtual server service rejected handshake reason index."
   ::= {sslOffPerServRejHsReasonsStatsEntry 3}

sslOffPerServRejHsReasonsRejHsName  OBJECT-TYPE
   SYNTAX  DisplayString
   MAX-ACCESS  read-only
   STATUS  current
   DESCRIPTION
       "Virtual server service rejected handshake name."
   ::= {sslOffPerServRejHsReasonsStatsEntry 4}

sslOffPerServRejHsReasonsNewHandShake  OBJECT-TYPE
   SYNTAX  Integer32
   MAX-ACCESS  read-only
   STATUS  current
   DESCRIPTION
       "Number of New SSL rejected handshakes caused due to this reason between Clients and AAS per second for this virtual service."
   ::= {sslOffPerServRejHsReasonsStatsEntry 5}

sslOffPerServRejHsReasonsVirtServPort  OBJECT-TYPE
   SYNTAX  Integer32
   MAX-ACCESS  read-only
   STATUS  current
   DESCRIPTION
       "Virtual server service port number."
   ::= {sslOffPerServRejHsReasonsStatsEntry 6}
   
sslOffPerServRejHsReasonsNewHandShakeTotal  OBJECT-TYPE
   SYNTAX  Integer32
   MAX-ACCESS  read-only
   STATUS  current
   DESCRIPTION
       "Number of Total SSL rejected handshakes caused due to this reason between Clients and AAS per second for this virtual service."
   ::= {sslOffPerServRejHsReasonsStatsEntry 7}

sslBeOffPerServRejHsReasonsStatsTable OBJECT-TYPE
   SYNTAX SEQUENCE OF SslBeOffPerServRejHsReasonsStatsEntry
   MAX-ACCESS not-accessible
   STATUS current
   DESCRIPTION
       "A table for backend SSL Rejected hand shake reasons current and total statistics per service.
        Note:This mib is not supported for VX instance of Virtualization."
   ::= {sslSlbStats 79}

sslBeOffPerServRejHsReasonsStatsEntry OBJECT-TYPE
   SYNTAX SslBeOffPerServRejHsReasonsStatsEntry
   MAX-ACCESS not-accessible
   STATUS  current
   DESCRIPTION
       " The row definition for SSL statistics per virtual service table.
        Note:This mib is not supported for VX instance of Virtualization."
   INDEX  { sslBeOffPerServRejHsReasonsVirtServIndex, sslBeOffPerServRejHsReasonsVirtServiceIndex, sslBeOffPerServRejHsReasonsVirtRejHsIndex}
   ::= {sslBeOffPerServRejHsReasonsStatsTable 1}

SslBeOffPerServRejHsReasonsStatsEntry  ::= SEQUENCE {
        sslBeOffPerServRejHsReasonsVirtServIndex           DisplayString,
        sslBeOffPerServRejHsReasonsVirtServiceIndex        Integer32,
        sslBeOffPerServRejHsReasonsVirtRejHsIndex           Integer32,
        sslBeOffPerServRejHsReasonsRejHsName                DisplayString,
        sslBeOffPerServRejHsReasonsNewHandShake            Integer32,
        sslBeOffPerServRejHsReasonsVirtServPort            Integer32,
        sslBeOffPerServRejHsReasonsNewHandShakeTotal       Integer32
        }

sslBeOffPerServRejHsReasonsVirtServIndex  OBJECT-TYPE
    SYNTAX  DisplayString
    MAX-ACCESS  read-only
    STATUS  current
    DESCRIPTION
        "The virtual server name that identifies the service."
   ::= {sslBeOffPerServRejHsReasonsStatsEntry 1}

sslBeOffPerServRejHsReasonsVirtServiceIndex  OBJECT-TYPE
   SYNTAX  Integer32
   MAX-ACCESS  read-only
   STATUS  current
   DESCRIPTION
       "Virtual server service index."
   ::= {sslBeOffPerServRejHsReasonsStatsEntry 2}

sslBeOffPerServRejHsReasonsVirtRejHsIndex  OBJECT-TYPE
   SYNTAX  Integer32
   MAX-ACCESS  read-only
   STATUS  current
   DESCRIPTION
       "Virtual server service rejected handshake reason index."
   ::= {sslBeOffPerServRejHsReasonsStatsEntry 3}

sslBeOffPerServRejHsReasonsRejHsName  OBJECT-TYPE
   SYNTAX  DisplayString
   MAX-ACCESS  read-only
   STATUS  current
   DESCRIPTION
       "Virtual server service rejected handshake name."
   ::= {sslBeOffPerServRejHsReasonsStatsEntry 4}

sslBeOffPerServRejHsReasonsNewHandShake  OBJECT-TYPE
   SYNTAX  Integer32
   MAX-ACCESS  read-only
   STATUS  current
   DESCRIPTION
       "Number of New SSL rejected handshakes caused due to this reason between AAS and server per second for this virtual service."
   ::= {sslBeOffPerServRejHsReasonsStatsEntry 5}

sslBeOffPerServRejHsReasonsVirtServPort  OBJECT-TYPE
   SYNTAX  Integer32
   MAX-ACCESS  read-only
   STATUS  current
   DESCRIPTION
       "Virtual server service port number."
   ::= {sslBeOffPerServRejHsReasonsStatsEntry 6}
   
sslBeOffPerServRejHsReasonsNewHandShakeTotal  OBJECT-TYPE
   SYNTAX  Integer32
   MAX-ACCESS  read-only
   STATUS  current
   DESCRIPTION
       "Number of Total SSL rejected handshakes caused due to this reason between AAS and server per second for this virtual service."
   ::= {sslBeOffPerServRejHsReasonsStatsEntry 7}


   sslBeOffPerFilterIgnoredCertsReasonsStatsTable OBJECT-TYPE
   SYNTAX SEQUENCE OF SslBeOffPerFilterIgnoredCertsReasonsStatsEntry
   MAX-ACCESS not-accessible
   STATUS current
   DESCRIPTION
       "A table for backend SSL current and total statistics per filter ignored Certs reasons.
        Note:This mib is not supported for VX instance of Virtualization."
   ::= {sslSlbStats 102}

sslBeOffPerFilterIgnoredCertsReasonsStatsEntry OBJECT-TYPE
   SYNTAX SslBeOffPerFilterIgnoredCertsReasonsStatsEntry
   MAX-ACCESS not-accessible
   STATUS  current
   DESCRIPTION
       " The row definition for backend SSL statistics per filter ignored Certs table.
        Note:This mib is not supported for VX instance of Virtualization."
   INDEX  {sslBeOffPerFilterIgnoredCertsReasonsFiltId, sslBeOffPerFilterIgnoredCertsReasonsName}
   ::= {sslBeOffPerFilterIgnoredCertsReasonsStatsTable 1}
   
SslBeOffPerFilterIgnoredCertsReasonsStatsEntry  ::= SEQUENCE {
        sslBeOffPerFilterIgnoredCertsReasonsFiltId                     	Integer32,
	sslBeOffPerFilterIgnoredCertsReasonsName							DisplayString,			
	sslBeOffPerFilterIgnoredCertsReasonsHits							Integer32,
	sslBeOffPerFilterIgnoredCertsReasonsHitsTotal						Integer32
		}
		
sslBeOffPerFilterIgnoredCertsReasonsFiltId  OBJECT-TYPE
   SYNTAX  Integer32
   MAX-ACCESS  read-only
   STATUS  current
   DESCRIPTION
       "Filter backend ignored Certs ID."
   ::= {sslBeOffPerFilterIgnoredCertsReasonsStatsEntry 1}
   
sslBeOffPerFilterIgnoredCertsReasonsName  OBJECT-TYPE
   SYNTAX  DisplayString
   MAX-ACCESS  read-only
   STATUS  current
   DESCRIPTION
       "Filter backend ignored certs name."
   ::= {sslBeOffPerFilterIgnoredCertsReasonsStatsEntry 2}     
   
sslBeOffPerFilterIgnoredCertsReasonsHits  OBJECT-TYPE
   SYNTAX  Integer32
   MAX-ACCESS  read-only
   STATUS  current
   DESCRIPTION
       "Number of hits per second for this backend for this filter ignored certs reason."
   ::= {sslBeOffPerFilterIgnoredCertsReasonsStatsEntry 3}   

sslBeOffPerFilterIgnoredCertsReasonsHitsTotal  OBJECT-TYPE
   SYNTAX  Integer32
   MAX-ACCESS  read-only
   STATUS  current
   DESCRIPTION
       "Number of total hits per second for this backend for this filter ignored certificates reason."
   ::= {sslBeOffPerFilterIgnoredCertsReasonsStatsEntry 4}   
  
sslBeOffPerServIgnoredCertsReasonsStatsTable OBJECT-TYPE
   SYNTAX SEQUENCE OF SslBeOffPerServIgnoredCertsReasonsStatsEntry
   MAX-ACCESS not-accessible
   STATUS current
   DESCRIPTION
       "A table for backend SSL reasons current and total statistics per service ignored certs.
        Note:This mib is not supported for VX instance of Virtualization."
   ::= {sslSlbStats 103}

sslBeOffPerServIgnoredCertsReasonsStatsEntry OBJECT-TYPE
   SYNTAX SslBeOffPerServIgnoredCertsReasonsStatsEntry
   MAX-ACCESS not-accessible
   STATUS  current
   DESCRIPTION
       " The row definition for backend SSL statistics per virtual service table ignored certs.
        Note:This mib is not supported for VX instance of Virtualization."
   INDEX  { sslBeOffPerServIgnoredCertsReasonsVirtServIndex, sslBeOffPerServIgnoredCertsReasonsVirtServiceIndex, sslBeOffPerServIgnoredCertsReasonsIgnoredCertsName}
   ::= {sslBeOffPerServIgnoredCertsReasonsStatsTable 1}

SslBeOffPerServIgnoredCertsReasonsStatsEntry  ::= SEQUENCE {
        sslBeOffPerServIgnoredCertsReasonsVirtServIndex				DisplayString,
        sslBeOffPerServIgnoredCertsReasonsVirtServiceIndex			Integer32,
        sslBeOffPerServIgnoredCertsReasonsIgnoredCertsName			DisplayString,
        sslBeOffPerServIgnoredCertsReasonsHits						Integer32,
		sslBeOffPerServIgnoredCertsReasonsHitsTotal					Integer32
        }

sslBeOffPerServIgnoredCertsReasonsVirtServIndex  OBJECT-TYPE
    SYNTAX  DisplayString
    MAX-ACCESS  read-only
    STATUS  current
    DESCRIPTION
        "The virtual backend server number that identifies the service ignored certs."
   ::= {sslBeOffPerServIgnoredCertsReasonsStatsEntry 1}

sslBeOffPerServIgnoredCertsReasonsVirtServiceIndex  OBJECT-TYPE
   SYNTAX  Integer32
   MAX-ACCESS  read-only
   STATUS  current
   DESCRIPTION
       "Virtual backend server service ignored certs index."
   ::= {sslBeOffPerServIgnoredCertsReasonsStatsEntry 2}

sslBeOffPerServIgnoredCertsReasonsIgnoredCertsName  OBJECT-TYPE
   SYNTAX  DisplayString
   MAX-ACCESS  read-only
   STATUS  current
   DESCRIPTION
       "Virtual backend server service ignored certs reason index."
   ::= {sslBeOffPerServIgnoredCertsReasonsStatsEntry 3}

sslBeOffPerServIgnoredCertsReasonsHits  OBJECT-TYPE
   SYNTAX  Integer32
   MAX-ACCESS  read-only
   STATUS  current
   DESCRIPTION
       "Virtual backend server service ignored certs name."
   ::= {sslBeOffPerServIgnoredCertsReasonsStatsEntry 4}

sslBeOffPerServIgnoredCertsReasonsHitsTotal  OBJECT-TYPE
   SYNTAX  Integer32
   MAX-ACCESS  read-only
   STATUS  current
   DESCRIPTION
       "Number of New backend SSL per second for this virtual service ignored certs ."
   ::= {sslBeOffPerServIgnoredCertsReasonsStatsEntry 5}
   
httpStatSummCliusingKeepAliv  OBJECT-TYPE
   SYNTAX  Integer32
   MAX-ACCESS  read-only
   STATUS  current
   DESCRIPTION
       "Number of clients sending connection: keep-alive.
        Note:This mib is not supported for VX instance of Virtualization."
   ::= {httpStats 1}

httpStatSummHTTP10Per OBJECT-TYPE
   SYNTAX  Integer32
   MAX-ACCESS  read-only
   STATUS  current
   DESCRIPTION
       "Percent of requests done using HTTP 1.0 during the measuring period.
        Note:This mib is not supported for VX instance of Virtualization."
   ::= {httpStats 2}

httpStatSummHTTP11Per  OBJECT-TYPE
   SYNTAX  Integer32
   MAX-ACCESS  read-only
   STATUS  current
   DESCRIPTION
       "Percent of requests done using HTTP 1.1 during measuring period.
        Note:This mib is not supported for VX instance of Virtualization."
   ::= {httpStats 3}

httpStatSummHttpToHttpsRedir  OBJECT-TYPE
   SYNTAX  Integer32
   MAX-ACCESS  read-only
   STATUS  current
   DESCRIPTION
       "Number of HTTP redirect location headers updated from HTTP to HTTPS by AAS.
        Note:This mib is not supported for VX instance of Virtualization."
   ::= {httpStats 4}

httpStatSummAvgNumReqPerConn OBJECT-TYPE
   SYNTAX  Integer32
   MAX-ACCESS  read-only
   STATUS  current
   DESCRIPTION
       "The average number of requests done over each client connection.
        Note:This mib is not supported for VX instance of Virtualization."
   ::= {httpStats 5}

httpStatSummResSmall1Kb  OBJECT-TYPE
   SYNTAX  Integer32
   MAX-ACCESS  read-only
   STATUS  current
   DESCRIPTION
       "Number of responses for which content size reported smaller than 1KB.
        Note:This mib is not supported for VX instance of Virtualization."
   ::= {httpStats 6}

httpStatSummRes1KbTo10Kb  OBJECT-TYPE
   SYNTAX  Integer32
   MAX-ACCESS  read-only
   STATUS  current
   DESCRIPTION
       "Number of responses for which content size reported  between 1KB and 10KB.
        Note:This mib is not supported for VX instance of Virtualization."
   ::= {httpStats 7}

httpStatSummRes11KbTo50Kb  OBJECT-TYPE
   SYNTAX  Integer32
   MAX-ACCESS  read-only
   STATUS  current
   DESCRIPTION
       "Number of responses for which content size reported between 11KB and 50KB.
        Note:This mib is not supported for VX instance of Virtualization."
   ::= {httpStats 8}

httpStatSummRes51KbTo100Kb  OBJECT-TYPE
   SYNTAX  Integer32
   MAX-ACCESS  read-only
   STATUS  current
   DESCRIPTION
       "Number of responses for which content size reported between 51KB and 100KB.
        Note:This mib is not supported for VX instance of Virtualization."
   ::= {httpStats 9}

httpStatSummResLarger100Kb  OBJECT-TYPE
   SYNTAX  Integer32
   MAX-ACCESS  read-only
   STATUS  current
   DESCRIPTION
       "Number of responses for which content size reported larger than 100KB.
        Note:This mib is not supported for VX instance of Virtualization."
   ::= {httpStats 10}

httpTransSummReqCliToAas  OBJECT-TYPE
   SYNTAX  Integer32
   MAX-ACCESS  read-only
   STATUS  current
   DESCRIPTION
       "Number of clients requests from AAS done in the measuring period.
        Note:This mib is not supported for VX instance of Virtualization."
   ::= {httpStats 11}

httpTransSummReqAasToSer  OBJECT-TYPE
   SYNTAX  Integer32
   MAX-ACCESS  read-only
   STATUS  current
   DESCRIPTION
       "Number of AAS requests from servers done in the measuring period.
        Note:This mib is not supported for VX instance of Virtualization."
   ::= {httpStats 12}

httpTransSummResSerToAas  OBJECT-TYPE
   SYNTAX  Integer32
   MAX-ACCESS  read-only
   STATUS  current
   DESCRIPTION
       "Number of servers responses to AAS in the measuring period.
        Note:This mib is not supported for VX instance of Virtualization."
   ::= {httpStats 13}

httpTransSummResAasToCli  OBJECT-TYPE
   SYNTAX  Integer32
   MAX-ACCESS  read-only
   STATUS  current
   DESCRIPTION
       "Number of AAS responses to clients in the measuring period.
        Note:This mib is not supported for VX instance of Virtualization."
   ::= {httpStats 14}

httpTransSummTransRate  OBJECT-TYPE
   SYNTAX  Integer32
   MAX-ACCESS  read-only
   STATUS  current
   DESCRIPTION
       "HTTP transactions per second.
        Note:This mib is not supported for VX instance of Virtualization."
   ::= {httpStats 15}

httpPerServStatsTable OBJECT-TYPE
   SYNTAX SEQUENCE OF HttpPerServStatsEntry
   MAX-ACCESS not-accessible
   STATUS current
   DESCRIPTION
       "A table for HTTP statistics per virtual service.
        Note:This mib is not supported for VX instance of Virtualization."
   ::= {httpStats 16}

httpPerServStatsEntry OBJECT-TYPE
   SYNTAX HttpPerServStatsEntry 
   MAX-ACCESS not-accessible
   STATUS  current
   DESCRIPTION
       " The row definition for HTTP statistics per virtual service table."
   INDEX  { httpPerServStatsVirtServIndex, httpPerServStatsVirtServiceIndex}
   ::= {httpPerServStatsTable 1}

HttpPerServStatsEntry  ::= SEQUENCE {
        httpPerServStatsVirtServIndex       Integer32,
        httpPerServStatsVirtServiceIndex    Integer32,
	httpPerServStatsVirtServPort        Integer32,
        httpPerServStatsCliUseKeepAlive     Integer32,
	httpPerServStatsHttp10VsHttp11Ratio Integer32,
	httpPerServStatsHttpToHTTPSRedir    Integer32,
	httpPerServStatsAvgNumReqPerConn    Integer32,
	httpPerServStatsRespSmall1Kb        Integer32,
	httpPerServStatsResp1KbTo10Kb       Integer32,
        httpPerServStatsResp11KbTo50Kb      Integer32,
	httpPerServStatsResp51KbTo100Kb     Integer32,
	httpPerServStatsRespLarger100Kb     Integer32,
        httpPerServStatsReqCliToAas         Integer32,
        httpPerServStatsReqAasToSer         Integer32,
        httpPerServStatsRespSerToAas        Integer32,
	httpPerServStatsRespAasToCli        Integer32,
	httpPerServStatsTransRate           Integer32
        }

httpPerServStatsVirtServIndex  OBJECT-TYPE
   SYNTAX  Integer32 
   MAX-ACCESS  read-write
   STATUS  current
   DESCRIPTION
       "Virtual server number."
   ::= {httpPerServStatsEntry 1}

httpPerServStatsVirtServiceIndex  OBJECT-TYPE
   SYNTAX  Integer32 
   MAX-ACCESS  read-write
   STATUS  current
   DESCRIPTION
       "Virtual server service index."
   ::= {httpPerServStatsEntry 2}

httpPerServStatsVirtServPort  OBJECT-TYPE
   SYNTAX  Integer32 
   MAX-ACCESS  read-write
   STATUS  current
   DESCRIPTION
       "Virtual server service port number."
   ::= {httpPerServStatsEntry 3}

httpPerServStatsCliUseKeepAlive  OBJECT-TYPE
   SYNTAX  Integer32
   MAX-ACCESS  read-only
   STATUS  current
   DESCRIPTION
       "Number of clients sending Connection: Keep-Alive for virtual service."
   ::= {httpPerServStatsEntry 4}

httpPerServStatsHttp10VsHttp11Ratio  OBJECT-TYPE
   SYNTAX  Integer32
   MAX-ACCESS  read-only
   STATUS  current
   DESCRIPTION
       "Ratio of requests done using HTTP 1.0 and HTTP 1.1 during measuring period for virtual service."
   ::= {httpPerServStatsEntry 5}

httpPerServStatsHttpToHTTPSRedir  OBJECT-TYPE
   SYNTAX  Integer32
   MAX-ACCESS  read-only
   STATUS  current
   DESCRIPTION
       "Number of HTTP redirect location headers updated from HTTP to HTTPS by AAS for virtual service."
   ::= {httpPerServStatsEntry 6}

httpPerServStatsAvgNumReqPerConn OBJECT-TYPE
   SYNTAX  Integer32
   MAX-ACCESS  read-only
   STATUS  current
   DESCRIPTION
       "The average number of requests done over each client connection for virtual service."
   ::= {httpPerServStatsEntry 7}

httpPerServStatsRespSmall1Kb  OBJECT-TYPE
   SYNTAX  Integer32
   MAX-ACCESS  read-only
   STATUS  current
   DESCRIPTION
       "Number of responses for which content size reported smaller than 1KB for virtual service."
   ::= {httpPerServStatsEntry 8}

httpPerServStatsResp1KbTo10Kb  OBJECT-TYPE
   SYNTAX  Integer32
   MAX-ACCESS  read-only
   STATUS  current
   DESCRIPTION
       "Number of responses for which content size reported  between 1KB and 10KB for virtual service."
   ::= {httpPerServStatsEntry 9}

httpPerServStatsResp11KbTo50Kb  OBJECT-TYPE
   SYNTAX  Integer32
   MAX-ACCESS  read-only
   STATUS  current
   DESCRIPTION
       "Number of responses for which content size reported between 11KB and 50KB for virtual service."
   ::= {httpPerServStatsEntry 10}

httpPerServStatsResp51KbTo100Kb  OBJECT-TYPE
   SYNTAX  Integer32
   MAX-ACCESS  read-only
   STATUS  current
   DESCRIPTION
       "Number of responses for which content size reported between 51KB and 100KB for virtual service."
   ::= {httpPerServStatsEntry 11}

httpPerServStatsRespLarger100Kb  OBJECT-TYPE
   SYNTAX  Integer32
   MAX-ACCESS  read-only
   STATUS  current
   DESCRIPTION
       "Number of responses for which content size reported larger than 100KB for virtual service."
   ::= {httpPerServStatsEntry 12}

httpPerServStatsReqCliToAas  OBJECT-TYPE
   SYNTAX  Integer32
   MAX-ACCESS  read-only
   STATUS  current
   DESCRIPTION
       "Number of clients requests from AAS done in the measuring period for virtual service."
   ::= {httpPerServStatsEntry 13}

httpPerServStatsReqAasToSer  OBJECT-TYPE
   SYNTAX  Integer32
   MAX-ACCESS  read-only
   STATUS  current
   DESCRIPTION
       "Number of AAS requests from servers done in the measuring period for virtual service."
   ::= {httpPerServStatsEntry 14}

httpPerServStatsRespSerToAas  OBJECT-TYPE
   SYNTAX  Integer32
   MAX-ACCESS  read-only
   STATUS  current
   DESCRIPTION
       "Number of servers responses to AAS in the measuring period for virtual service."
   ::= {httpPerServStatsEntry 15}

httpPerServStatsRespAasToCli  OBJECT-TYPE
   SYNTAX  Integer32
   MAX-ACCESS  read-only
   STATUS  current
   DESCRIPTION
       "Number of AAS responses to clients in the measuring period for virtual service."
   ::= {httpPerServStatsEntry 16}

httpPerServStatsTransRate  OBJECT-TYPE
   SYNTAX  Integer32
   MAX-ACCESS  read-only
   STATUS  current
   DESCRIPTION
       "Transactions rate for virtual service."
   ::= {httpPerServStatsEntry 17}

httpEnhPerServStatsTable OBJECT-TYPE
    SYNTAX SEQUENCE OF HttpEnhPerServStatsEntry
    MAX-ACCESS not-accessible
    STATUS current
    DESCRIPTION
        "A table for HTTP statistics per virtual service.
         Note:This mib is not supported for VX instance of Virtualization."
    ::= {httpStats 18}

httpEnhPerServStatsEntry OBJECT-TYPE
    SYNTAX HttpEnhPerServStatsEntry
    MAX-ACCESS not-accessible
    STATUS  current
    DESCRIPTION
        " The row definition for HTTP statistics per virtual service table."
    INDEX  { httpEnhPerServStatsVirtServIndex, httpEnhPerServStatsVirtServiceIndex}
    ::= {httpEnhPerServStatsTable 1}

HttpEnhPerServStatsEntry  ::= SEQUENCE {
    httpEnhPerServStatsVirtServIndex       DisplayString,
    httpEnhPerServStatsVirtServiceIndex    Integer32,
    httpEnhPerServStatsVirtServPort        Integer32,
    httpEnhPerServStatsCliUseKeepAlive     Integer32,
    httpEnhPerServStatsHttp10VsHttp11Ratio Integer32,
    httpEnhPerServStatsHttpToHTTPSRedir    Integer32,
    httpEnhPerServStatsAvgNumReqPerConn    Integer32,
    httpEnhPerServStatsRespSmall1Kb        Integer32,
    httpEnhPerServStatsResp1KbTo10Kb       Integer32,
    httpEnhPerServStatsResp11KbTo50Kb      Integer32,
    httpEnhPerServStatsResp51KbTo100Kb     Integer32,
    httpEnhPerServStatsRespLarger100Kb     Integer32,
    httpEnhPerServStatsReqCliToAas         Integer32,
    httpEnhPerServStatsReqAasToSer         Integer32,
    httpEnhPerServStatsRespSerToAas        Integer32,
    httpEnhPerServStatsRespAasToCli        Integer32,
    httpEnhPerServStatsTransRate           Integer32,
	httpPerServStatsHttp20ConnectionCount     Integer32,
	httpPerServStatsHttp11ConnectionCount     Integer32,
	httpPerServStatsHttp10ConnectionCount     Integer32,
	httpPerServStatsHttp20ConnectionPeak      Integer32,
	httpPerServStatsHttp11ConnectionPeak      Integer32,
	httpPerServStatsHttp10ConnectionPeak      Integer32,
	httpPerServStatsHttp20RequestCount        Integer32,
	httpPerServStatsHttp11RequestCount        Integer32,
	httpPerServStatsHttp10RequestCount        Integer32,
	httpPerServStatsBackendProxyConnections     	Integer32,
	httpPerServStatsClientStreams                	Integer32,
	httpPerServStatsPushStreams			Integer32,
	httpPerServStatsCanceledPushStreams		Integer32,
	httpPerServStatsConnectionDurationAvgStr	DisplayString,
	httpPerServStatsHeadersRequestCompRatio		Integer32,
	httpPerServStatsHeadersResponseCompRatio	Integer32,
	httpPerServStatsBigHeaders			Integer32,
	httpPerServStatsAvgEvictionBytes		Integer32,
	httpPerServStatsAvgHpackTableSize		Integer32,
	httpPerServStatsPeakBackendProxyConnections	Integer32,
	httpPerServStatsPeakClientStreams		Integer32,
	httpPerServStatsPeakPushStreams			Integer32,
	httpPerServStatsPeakCanceledPushStreams		Integer32,
	httpPerServStatsPeakConnectionDurationAvgStr	DisplayString,
	httpPerServStatsPeakHeadersRequestCompRatio	Integer32,	
	httpPerServStatsPeakHeadersResponseCompRatio	Integer32,
	httpPerServStatsPeakBigHeaders			Integer32,
	httpPerServStatsPeakAvgEvictionBytes		Integer32,
	httpPerServStatsPeakAvgHpackTableSize		Integer32
}

httpEnhPerServStatsVirtServIndex  OBJECT-TYPE
    SYNTAX  DisplayString  ( SIZE ( 1 .. 255  ) )
    MAX-ACCESS  read-only
    STATUS  current
    DESCRIPTION
        "Virtual server Index."
    ::= {httpEnhPerServStatsEntry 1}

httpEnhPerServStatsVirtServiceIndex  OBJECT-TYPE
    SYNTAX  Integer32
    MAX-ACCESS  read-only
    STATUS  current
    DESCRIPTION
        "Virtual server service index."
    ::= {httpEnhPerServStatsEntry 2}

httpEnhPerServStatsVirtServPort  OBJECT-TYPE
    SYNTAX  Integer32
    MAX-ACCESS  read-only
    STATUS  current
    DESCRIPTION
        "Virtual server service port number."
    ::= {httpEnhPerServStatsEntry 3}

httpEnhPerServStatsCliUseKeepAlive  OBJECT-TYPE
    SYNTAX  Integer32
    MAX-ACCESS  read-only
    STATUS  current
    DESCRIPTION
        "Number of clients sending Connection: Keep-Alive for virtual service."
    ::= {httpEnhPerServStatsEntry 4}

httpEnhPerServStatsHttp10VsHttp11Ratio  OBJECT-TYPE
    SYNTAX  Integer32
    MAX-ACCESS  read-only
    STATUS  current
    DESCRIPTION
        "Ratio of requests done using HTTP 1.0 and HTTP 1.1 during measuring period for virtual service."
    ::= {httpEnhPerServStatsEntry 5}

httpEnhPerServStatsHttpToHTTPSRedir  OBJECT-TYPE
    SYNTAX  Integer32
    MAX-ACCESS  read-only
    STATUS  current
    DESCRIPTION
    "Number of HTTP redirect location headers updated from HTTP to HTTPS by AAS for virtual service."
    ::= {httpEnhPerServStatsEntry 6}

httpEnhPerServStatsAvgNumReqPerConn OBJECT-TYPE
    SYNTAX  Integer32
    MAX-ACCESS  read-only
    STATUS  current
    DESCRIPTION
        "The average number of requests done over each client connection for virtual service."
    ::= {httpEnhPerServStatsEntry 7}

httpEnhPerServStatsRespSmall1Kb  OBJECT-TYPE
    SYNTAX  Integer32
    MAX-ACCESS  read-only
    STATUS  current
    DESCRIPTION
        "Number of responses for which content size reported smaller than 1KB for virtual service."
    ::= {httpEnhPerServStatsEntry 8}

httpEnhPerServStatsResp1KbTo10Kb  OBJECT-TYPE
    SYNTAX  Integer32
    MAX-ACCESS  read-only
    STATUS  current
    DESCRIPTION
        "Number of responses for which content size reported  between 1KB and 10KB for virtual service."
    ::= {httpEnhPerServStatsEntry 9}

httpEnhPerServStatsResp11KbTo50Kb  OBJECT-TYPE
    SYNTAX  Integer32
    MAX-ACCESS  read-only
    STATUS  current
    DESCRIPTION
        "Number of responses for which content size reported between 11KB and 50KB for virtual service."
    ::= {httpEnhPerServStatsEntry 10}

httpEnhPerServStatsResp51KbTo100Kb  OBJECT-TYPE
    SYNTAX  Integer32
    MAX-ACCESS  read-only
    STATUS  current
    DESCRIPTION
        "Number of responses for which content size reported between 51KB and 100KB for virtual service."
    ::= {httpEnhPerServStatsEntry 11}

httpEnhPerServStatsRespLarger100Kb  OBJECT-TYPE
    SYNTAX  Integer32
    MAX-ACCESS  read-only
    STATUS  current
    DESCRIPTION
        "Number of responses for which content size reported larger than 100KB for virtual service."
    ::= {httpEnhPerServStatsEntry 12}

httpEnhPerServStatsReqCliToAas  OBJECT-TYPE
    SYNTAX  Integer32
    MAX-ACCESS  read-only
    STATUS  current
    DESCRIPTION
        "Number of clients requests from AAS done in the measuring period for virtual service."
    ::= {httpEnhPerServStatsEntry 13}

httpEnhPerServStatsReqAasToSer  OBJECT-TYPE
    SYNTAX  Integer32
    MAX-ACCESS  read-only
    STATUS  current
    DESCRIPTION
        "Number of AAS requests from servers done in the measuring period for virtual service."
    ::= {httpEnhPerServStatsEntry 14}

httpEnhPerServStatsRespSerToAas  OBJECT-TYPE
    SYNTAX  Integer32
    MAX-ACCESS  read-only
    STATUS  current
    DESCRIPTION
        "Number of servers responses to AAS in the measuring period for virtual service."
    ::= {httpEnhPerServStatsEntry 15}

httpEnhPerServStatsRespAasToCli  OBJECT-TYPE
    SYNTAX  Integer32
    MAX-ACCESS  read-only
    STATUS  current
    DESCRIPTION
        "Number of AAS responses to clients in the measuring period for virtual service."
    ::= {httpEnhPerServStatsEntry 16}

httpEnhPerServStatsTransRate  OBJECT-TYPE
    SYNTAX  Integer32
    MAX-ACCESS  read-only
    STATUS  current
    DESCRIPTION
        "Transactions rate for virtual service."
    ::= {httpEnhPerServStatsEntry 17}

httpPerServStatsHttp20ConnectionCount	OBJECT-TYPE
   SYNTAX  Integer32
   MAX-ACCESS  read-only
   STATUS  current
   DESCRIPTION
       "HTTP2 connection count."
   ::= {httpEnhPerServStatsEntry 18}

httpPerServStatsHttp11ConnectionCount	OBJECT-TYPE
   SYNTAX  Integer32
   MAX-ACCESS  read-only
   STATUS  current
   DESCRIPTION
       "HTTP 1.1 connection count."
   ::= {httpEnhPerServStatsEntry 19}

httpPerServStatsHttp10ConnectionCount	OBJECT-TYPE
   SYNTAX  Integer32
   MAX-ACCESS  read-only
   STATUS  current
   DESCRIPTION
       "HTTP 1.0 connection count."
   ::= {httpEnhPerServStatsEntry 20}

httpPerServStatsHttp20ConnectionPeak	OBJECT-TYPE
   SYNTAX  Integer32
   MAX-ACCESS  read-only
   STATUS  current
   DESCRIPTION
       "HTTP 2.0 connection count peak."
   ::= {httpEnhPerServStatsEntry 21}

httpPerServStatsHttp11ConnectionPeak	OBJECT-TYPE
   SYNTAX  Integer32
   MAX-ACCESS  read-only
   STATUS  current
   DESCRIPTION
       "HTTP 1.1 connection count peak."
   ::= {httpEnhPerServStatsEntry 22}

httpPerServStatsHttp10ConnectionPeak	OBJECT-TYPE
   SYNTAX  Integer32
   MAX-ACCESS  read-only
   STATUS  current
   DESCRIPTION
       "HTTP 1.0 connection count peak."
   ::= {httpEnhPerServStatsEntry 23}

httpPerServStatsHttp20RequestCount	OBJECT-TYPE
   SYNTAX  Integer32
   MAX-ACCESS  read-only
   STATUS  current
   DESCRIPTION
       "HTTP 2.0 request count."
   ::= {httpEnhPerServStatsEntry 24}

httpPerServStatsHttp11RequestCount	OBJECT-TYPE
   SYNTAX  Integer32
   MAX-ACCESS  read-only
   STATUS  current
   DESCRIPTION
       "HTTP 1.1 request count."
   ::= {httpEnhPerServStatsEntry 25}

httpPerServStatsHttp10RequestCount	OBJECT-TYPE
   SYNTAX  Integer32
   MAX-ACCESS  read-only
   STATUS  current
   DESCRIPTION
       "HTTP 1.0 request count."
   ::= {httpEnhPerServStatsEntry 26}

httpPerServStatsBackendProxyConnections	OBJECT-TYPE
   SYNTAX  Integer32
   MAX-ACCESS  read-only
   STATUS  current
   DESCRIPTION
       "HTTP2 backend proxy connections."
   ::= {httpEnhPerServStatsEntry 27}

httpPerServStatsClientStreams	OBJECT-TYPE
   SYNTAX  Integer32
   MAX-ACCESS  read-only
   STATUS  current
   DESCRIPTION
       "HTTP2 client streams."
   ::= {httpEnhPerServStatsEntry 28}

httpPerServStatsPushStreams	OBJECT-TYPE
   SYNTAX  Integer32
   MAX-ACCESS  read-only
   STATUS  current
   DESCRIPTION
       "HTTP2 PUSH streams."
   ::= {httpEnhPerServStatsEntry 29}

httpPerServStatsCanceledPushStreams	OBJECT-TYPE
   SYNTAX  Integer32
   MAX-ACCESS  read-only
   STATUS  current
   DESCRIPTION
       "HTTP2 cancelled PUSH streams."
   ::= {httpEnhPerServStatsEntry 30}

httpPerServStatsConnectionDurationAvgStr	OBJECT-TYPE
   SYNTAX  DisplayString (SIZE(0..127))
   MAX-ACCESS  read-only
   STATUS  current
   DESCRIPTION
       "HTTP2 average connection duration (seconds)."
   ::= {httpEnhPerServStatsEntry 31}

httpPerServStatsHeadersRequestCompRatio	OBJECT-TYPE
   SYNTAX  Integer32
   MAX-ACCESS  read-only
   STATUS  current
   DESCRIPTION
       "HTTP2 headers request compression ratio."
   ::= {httpEnhPerServStatsEntry 32}

httpPerServStatsHeadersResponseCompRatio	OBJECT-TYPE
   SYNTAX  Integer32
   MAX-ACCESS  read-only
   STATUS  current
   DESCRIPTION
       "HTTP2 headers response compression ratio."
   ::= {httpEnhPerServStatsEntry 33}

httpPerServStatsBigHeaders	OBJECT-TYPE
   SYNTAX  Integer32
   MAX-ACCESS  read-only
   STATUS  current
   DESCRIPTION
       "HTTP2 big headers count."
   ::= {httpEnhPerServStatsEntry 34}

httpPerServStatsAvgEvictionBytes	OBJECT-TYPE
   SYNTAX  Integer32
   MAX-ACCESS  read-only
   STATUS  current
   DESCRIPTION
       "HTTP2 average eviction bytes."
   ::= {httpEnhPerServStatsEntry 35}

httpPerServStatsAvgHpackTableSize	OBJECT-TYPE
   SYNTAX  Integer32
   MAX-ACCESS  read-only
   STATUS  current
   DESCRIPTION
       "HTTP2 average HPACK table size."
   ::= {httpEnhPerServStatsEntry 36}

httpPerServStatsPeakBackendProxyConnections	OBJECT-TYPE
   SYNTAX  Integer32
   MAX-ACCESS  read-only
   STATUS  current
   DESCRIPTION
       "HTTP2 Peak of backend proxy connections."
   ::= {httpEnhPerServStatsEntry 37}

httpPerServStatsPeakClientStreams	OBJECT-TYPE
   SYNTAX  Integer32
   MAX-ACCESS  read-only
   STATUS  current
   DESCRIPTION
       "HTTP2 Peak of client streams."
   ::= {httpEnhPerServStatsEntry 38}

httpPerServStatsPeakPushStreams	OBJECT-TYPE
   SYNTAX  Integer32
   MAX-ACCESS  read-only
   STATUS  current
   DESCRIPTION
       "HTTP2 Peak of PUSH streams."
   ::= {httpEnhPerServStatsEntry 39}

httpPerServStatsPeakCanceledPushStreams	OBJECT-TYPE
   SYNTAX  Integer32
   MAX-ACCESS  read-only
   STATUS  current
   DESCRIPTION
       "HTTP2 Peak of cancelled PUSH streams."
   ::= {httpEnhPerServStatsEntry 40}

httpPerServStatsPeakConnectionDurationAvgStr	OBJECT-TYPE
   SYNTAX  DisplayString (SIZE(0..127))
   MAX-ACCESS  read-only
   STATUS  current
   DESCRIPTION
       "HTTP2 Peak of connection duration average (seconds)."
   ::= {httpEnhPerServStatsEntry 41}

httpPerServStatsPeakHeadersRequestCompRatio	OBJECT-TYPE
   SYNTAX  Integer32
   MAX-ACCESS  read-only
   STATUS  current
   DESCRIPTION
       "HTTP2 Peak of headers request compression ratio."
   ::= {httpEnhPerServStatsEntry 42}

httpPerServStatsPeakHeadersResponseCompRatio	OBJECT-TYPE
   SYNTAX  Integer32
   MAX-ACCESS  read-only
   STATUS  current
   DESCRIPTION
       "HTTP2 Peak of headers response compression ratio."
   ::= {httpEnhPerServStatsEntry 43}

httpPerServStatsPeakBigHeaders	OBJECT-TYPE
   SYNTAX  Integer32
   MAX-ACCESS  read-only
   STATUS  current
   DESCRIPTION
       "HTTP2 Peak of number of big headers."
   ::= {httpEnhPerServStatsEntry 44}

httpPerServStatsPeakAvgEvictionBytes	OBJECT-TYPE
   SYNTAX  Integer32
   MAX-ACCESS  read-only
   STATUS  current
   DESCRIPTION
       "HTTP2 Peak of average eviction in bytes."
   ::= {httpEnhPerServStatsEntry 45}

httpPerServStatsPeakAvgHpackTableSize	OBJECT-TYPE
   SYNTAX  Integer32
   MAX-ACCESS  read-only
   STATUS  current
   DESCRIPTION
       "HTTP2 Peak of average HPACK table size in Kb."
   ::= {httpEnhPerServStatsEntry 46}

httpStatSummHTTP20ConnectionCount  OBJECT-TYPE
   SYNTAX  Integer32
   MAX-ACCESS  read-only
   STATUS  current
   DESCRIPTION
       "HTTP 2.0 connection count.
        Note:This mib is not supported for VX instance of Virtualization."
   ::= {httpStats 19}

httpStatSummHTTP11ConnectionCount  OBJECT-TYPE
   SYNTAX  Integer32
   MAX-ACCESS  read-only
   STATUS  current
   DESCRIPTION
       "HTTP 1.1 connection count.
        Note:This mib is not supported for VX instance of Virtualization."
   ::= {httpStats 20}

httpStatSummHTTP10ConnectionCount  OBJECT-TYPE
   SYNTAX  Integer32
   MAX-ACCESS  read-only
   STATUS  current
   DESCRIPTION
       "HTTP 1.0 connection count.
        Note:This mib is not supported for VX instance of Virtualization."
   ::= {httpStats 21}

httpStatSummHTTP20ConnectionPeak  OBJECT-TYPE
   SYNTAX  Integer32
   MAX-ACCESS  read-only
   STATUS  current
   DESCRIPTION
       "HTTP 2.0 connection count peak.
        Note:This mib is not supported for VX instance of Virtualization."
   ::= {httpStats 22}

httpStatSummHTTP11ConnectionPeak  OBJECT-TYPE
   SYNTAX  Integer32
   MAX-ACCESS  read-only
   STATUS  current
   DESCRIPTION
       "HTTP 1.1 connection count peak.
        Note:This mib is not supported for VX instance of Virtualization."
   ::= {httpStats 23}

httpStatSummHTTP10ConnectionPeak  OBJECT-TYPE
   SYNTAX  Integer32
   MAX-ACCESS  read-only
   STATUS  current
   DESCRIPTION
       "HTTP 1.0 connection count peak.
        Note:This mib is not supported for VX instance of Virtualization."
   ::= {httpStats 24}

httpStatSummHTTP20RequestCount  OBJECT-TYPE
   SYNTAX  Integer32
   MAX-ACCESS  read-only
   STATUS  current
   DESCRIPTION
       "HTTP 2.0 request count.
        Note:This mib is not supported for VX instance of Virtualization."
   ::= {httpStats 25}

httpStatSummHTTP11RequestCount  OBJECT-TYPE
   SYNTAX  Integer32
   MAX-ACCESS  read-only
   STATUS  current
   DESCRIPTION
       "HTTP 1.1 request count.
        Note:This mib is not supported for VX instance of Virtualization."
   ::= {httpStats 26}

httpStatSummHTTP10RequestCount  OBJECT-TYPE
   SYNTAX  Integer32
   MAX-ACCESS  read-only
   STATUS  current
   DESCRIPTION
       "HTTP 1.0 request count.
        Note:This mib is not supported for VX instance of Virtualization."
   ::= {httpStats 27}

connmngStatSummServConn  OBJECT-TYPE
   SYNTAX  Integer32
   MAX-ACCESS  read-only
   STATUS  current
   DESCRIPTION
       "Number of concurrent backend server connections.
        Note:This mib is not supported for VX instance of Virtualization."
   ::= {connmngStats 1}

connmngStatSummCliReq OBJECT-TYPE
   SYNTAX  Integer32
   MAX-ACCESS  read-only
   STATUS  current
   DESCRIPTION
       "Number of client requests passed to AE.
        Note:This mib is not supported for VX instance of Virtualization."
   ::= {connmngStats 2}

connmngStatSummMulRatio OBJECT-TYPE
   SYNTAX  Integer32
   MAX-ACCESS  read-only
   STATUS  current
   DESCRIPTION
       "Connection multiplexing ratio.
        Note:This mib is not supported for VX instance of Virtualization."
   ::= {connmngStats 3}

connmngPerServStatsTable OBJECT-TYPE
   SYNTAX SEQUENCE OF ConnmngPerServStatsEntry
   MAX-ACCESS not-accessible
   STATUS current
   DESCRIPTION
       "A table for connection management statistics per virtual service.
        Note:This mib is not supported for VX instance of Virtualization."
   ::= {connmngStats 4}

connmngPerServStatsEntry OBJECT-TYPE
   SYNTAX ConnmngPerServStatsEntry 
   MAX-ACCESS not-accessible
   STATUS  current
   DESCRIPTION
       " The row definition for connection management statistics per virtual service table."
   INDEX  { connmngPerServStatsVirtServIndex, connmngPerServStatsVirtServiceIndex}
   ::= {connmngPerServStatsTable 1}

ConnmngPerServStatsEntry  ::= SEQUENCE {
        connmngPerServStatsVirtServIndex       Integer32,
        connmngPerServStatsVirtServiceIndex    Integer32,
        connmngPerServStatsVirtServPort        Integer32,          
        connmngPerServStatsServConn            Integer32,
        connmngPerServStatsCliReq              Integer32,
        connmngPerServStatsMulRatio            Integer32
        }

connmngPerServStatsVirtServIndex  OBJECT-TYPE
   SYNTAX  Integer32 
   MAX-ACCESS  read-write
   STATUS  current
   DESCRIPTION
       "Virtual server number."
   ::= {connmngPerServStatsEntry 1}

connmngPerServStatsVirtServiceIndex  OBJECT-TYPE
   SYNTAX  Integer32 
   MAX-ACCESS  read-write
   STATUS  current
   DESCRIPTION
       "Virtual server service index."
   ::= {connmngPerServStatsEntry 2}

connmngPerServStatsVirtServPort  OBJECT-TYPE
   SYNTAX  Integer32 
   MAX-ACCESS  read-write
   STATUS  current
   DESCRIPTION
       "Virtual server service port number."
   ::= {connmngPerServStatsEntry 3}

connmngPerServStatsServConn  OBJECT-TYPE
   SYNTAX  Integer32
   MAX-ACCESS  read-only
   STATUS  current
   DESCRIPTION
       "Number of concurrent backend server connections for virtual service."
   ::= {connmngPerServStatsEntry 4}

connmngPerServStatsCliReq  OBJECT-TYPE
   SYNTAX  Integer32
   MAX-ACCESS  read-only
   STATUS  current
   DESCRIPTION
       "Number of client requests passed to AE for virtual service."
   ::= {connmngPerServStatsEntry 5}

connmngPerServStatsMulRatio  OBJECT-TYPE
   SYNTAX  Integer32
   MAX-ACCESS  read-only
   STATUS  current
   DESCRIPTION
       "Connection multiplexing ratio for virtual service."
   ::= {connmngPerServStatsEntry 6}

connmngEnhPerServStatsTable OBJECT-TYPE
    SYNTAX SEQUENCE OF ConnmngEnhPerServStatsEntry
    MAX-ACCESS not-accessible
    STATUS current
    DESCRIPTION
        "A table for connection management statistics per virtual service.
         Note:This mib is not supported for VX instance of Virtualization."
    ::= {connmngStats 5}

connmngEnhPerServStatsEntry OBJECT-TYPE
    SYNTAX ConnmngEnhPerServStatsEntry
    MAX-ACCESS not-accessible
    STATUS  current
    DESCRIPTION
        " The row definition for connection management statistics per virtual service table."
    INDEX  { connmngEnhPerServStatsVirtServIndex, connmngEnhPerServStatsVirtServiceIndex}
    ::= {connmngEnhPerServStatsTable 1}

ConnmngEnhPerServStatsEntry  ::= SEQUENCE {
    connmngEnhPerServStatsVirtServIndex       DisplayString,
    connmngEnhPerServStatsVirtServiceIndex    Integer32,
    connmngEnhPerServStatsVirtServPort        Integer32,
    connmngEnhPerServStatsServConn            Integer32,
    connmngEnhPerServStatsCliReq              Integer32,
    connmngEnhPerServStatsMulRatio            Integer32
}

connmngEnhPerServStatsVirtServIndex  OBJECT-TYPE
    SYNTAX  DisplayString  ( SIZE ( 1 .. 255  ) ) 
    MAX-ACCESS  read-only
    STATUS  current
    DESCRIPTION
        "Virtual server index."
    ::= {connmngEnhPerServStatsEntry 1}

connmngEnhPerServStatsVirtServiceIndex  OBJECT-TYPE
    SYNTAX  Integer32
    MAX-ACCESS  read-only
    STATUS  current
    DESCRIPTION
        "Virtual server service index."
    ::= {connmngEnhPerServStatsEntry 2}

connmngEnhPerServStatsVirtServPort  OBJECT-TYPE
    SYNTAX  Integer32
    MAX-ACCESS  read-only
    STATUS  current
    DESCRIPTION
        "Virtual server service port number."
    ::= {connmngEnhPerServStatsEntry 3}

connmngEnhPerServStatsServConn  OBJECT-TYPE
    SYNTAX  Integer32
    MAX-ACCESS  read-only
    STATUS  current
    DESCRIPTION
        "Number of concurrent backend server connections for virtual service."
    ::= {connmngEnhPerServStatsEntry 4}

connmngEnhPerServStatsCliReq  OBJECT-TYPE
    SYNTAX  Integer32
    MAX-ACCESS  read-only
    STATUS  current
    DESCRIPTION
        "Number of client requests passed to AX for virtual service."
    ::= {connmngEnhPerServStatsEntry 5}

connmngEnhPerServStatsMulRatio  OBJECT-TYPE
    SYNTAX  Integer32
    MAX-ACCESS  read-only
    STATUS  current
    DESCRIPTION
        "Connection multiplexing ratio for virtual service."
    ::= {connmngEnhPerServStatsEntry 6}

tcpConnmngStatSummServConn  OBJECT-TYPE
   SYNTAX  Integer32
   MAX-ACCESS  read-only
   STATUS  current
   DESCRIPTION
       "Number of concurrent backend server connections.
        Note:This mib is not supported for VX instance of Virtualization."
   ::= {tcpConnmngStats 1}

tcpConnmngStatSummServConnReuse  OBJECT-TYPE
   SYNTAX  Integer32
   MAX-ACCESS  read-only
   STATUS  current
   DESCRIPTION
       "Number of reused backend server connections.
        Note:This mib is not supported for VX instance of Virtualization."
   ::= {tcpConnmngStats 2}

tcpConnmngStatSummCliTrans OBJECT-TYPE
   SYNTAX  Integer32
   MAX-ACCESS  read-only
   STATUS  current
   DESCRIPTION
       "Number of client transactions passed to AX.
        Note:This mib is not supported for VX instance of Virtualization."
   ::= {tcpConnmngStats 3}

tcpConnmngStatSummMulRatio OBJECT-TYPE
   SYNTAX  Integer32
   MAX-ACCESS  read-only
   STATUS  current
   DESCRIPTION
       "Connection multiplexing ratio.
        Note:This mib is not supported for VX instance of Virtualization."
   ::= {tcpConnmngStats 4}

tcpConnmngStatSummTotalServConn  OBJECT-TYPE
   SYNTAX  Counter64
   MAX-ACCESS  read-only
   STATUS  current
   DESCRIPTION
       "Total number of new backend server connections.
        Note:This mib is not supported for VX instance of Virtualization."
   ::= {tcpConnmngStats 5}

tcpConnmngStatSummTotalServConnReuse  OBJECT-TYPE
   SYNTAX  Counter64
   MAX-ACCESS  read-only
   STATUS  current
   DESCRIPTION
       "Total number of reused backend server connections.
        Note:This mib is not supported for VX instance of Virtualization."
   ::= {tcpConnmngStats 6}

tcpConnmngStatSummTotalCliTrans OBJECT-TYPE
   SYNTAX  Counter64
   MAX-ACCESS  read-only
   STATUS  current
   DESCRIPTION
       "Total number of client transactions passed to AE.
        Note:This mib is not supported for VX instance of Virtualization."
   ::= {tcpConnmngStats 7}

tcpConnmngStatSummTotalMulRatio OBJECT-TYPE
   SYNTAX  Integer32
   MAX-ACCESS  read-only
   STATUS  current
   DESCRIPTION
       "Connection multiplexing ratio on total numbers.
        Note:This mib is not supported for VX instance of Virtualization."
   ::= {tcpConnmngStats 8}

tcpConnmngEnhPerServStatsTable OBJECT-TYPE
    SYNTAX SEQUENCE OF TcpConnmngEnhPerServStatsEntry
    MAX-ACCESS not-accessible
    STATUS current
    DESCRIPTION
        "A table for tcp connection management statistics per virtual service.
         Note:This mib is not supported for VX instance of Virtualization."
    ::= {tcpConnmngStats 9}

tcpConnmngEnhPerServStatsEntry OBJECT-TYPE
    SYNTAX TcpConnmngEnhPerServStatsEntry
    MAX-ACCESS not-accessible
    STATUS  current
    DESCRIPTION
        " The row definition for tcp connection management statistics per virtual service table."
    INDEX  { tcpConnmngEnhPerServStatsVirtServIndex, tcpConnmngEnhPerServStatsVirtServiceIndex}
    ::= {tcpConnmngEnhPerServStatsTable 1}

TcpConnmngEnhPerServStatsEntry  ::= SEQUENCE {
    tcpConnmngEnhPerServStatsVirtServIndex       DisplayString,
    tcpConnmngEnhPerServStatsVirtServiceIndex    Integer32,
    tcpConnmngEnhPerServStatsVirtServPort        Integer32,
    tcpConnmngEnhPerServStatsServConn            Integer32,
    tcpConnmngEnhPerServStatsServConnReuse       Integer32,
    tcpConnmngEnhPerServStatsCliTrans            Integer32,
    tcpConnmngEnhPerServStatsMulRatio            Integer32,
    tcpConnmngEnhPerServStatsTotalServConn       Counter64,
    tcpConnmngEnhPerServStatsTotalServConnReuse  Counter64,
    tcpConnmngEnhPerServStatsTotalCliTrans       Counter64,
    tcpConnmngEnhPerServStatsTotalMulRatio       Integer32
}

tcpConnmngEnhPerServStatsVirtServIndex  OBJECT-TYPE
    SYNTAX  DisplayString  ( SIZE ( 1 .. 255  ) )
    MAX-ACCESS  read-only
    STATUS  current
    DESCRIPTION
        "Virtual server index."
    ::= {tcpConnmngEnhPerServStatsEntry 1}

tcpConnmngEnhPerServStatsVirtServiceIndex  OBJECT-TYPE
    SYNTAX  Integer32
    MAX-ACCESS  read-only
    STATUS  current
    DESCRIPTION
        "Virtual server service index."
    ::= {tcpConnmngEnhPerServStatsEntry 2}

tcpConnmngEnhPerServStatsVirtServPort  OBJECT-TYPE
    SYNTAX  Integer32
    MAX-ACCESS  read-only
    STATUS  current
    DESCRIPTION
        "Virtual server service port number."
    ::= {tcpConnmngEnhPerServStatsEntry 3}

tcpConnmngEnhPerServStatsServConn  OBJECT-TYPE
    SYNTAX  Integer32
    MAX-ACCESS  read-only
    STATUS  current
    DESCRIPTION
        "Number of concurrent backend server connections for virtual service."
    ::= {tcpConnmngEnhPerServStatsEntry 4}

tcpConnmngEnhPerServStatsServConnReuse  OBJECT-TYPE
    SYNTAX  Integer32
    MAX-ACCESS  read-only
    STATUS  current
    DESCRIPTION
        "Number of reused backend server connections for virtual service."
    ::= {tcpConnmngEnhPerServStatsEntry 5}

tcpConnmngEnhPerServStatsCliTrans  OBJECT-TYPE
    SYNTAX  Integer32
    MAX-ACCESS  read-only
    STATUS  current
    DESCRIPTION
        "Number of client transactions passed to AX for virtual service."
    ::= {tcpConnmngEnhPerServStatsEntry 6}

tcpConnmngEnhPerServStatsMulRatio  OBJECT-TYPE
    SYNTAX  Integer32
    MAX-ACCESS  read-only
    STATUS  current
    DESCRIPTION
        "Connection multiplexing ratio for virtual service."
    ::= {tcpConnmngEnhPerServStatsEntry 7}

tcpConnmngEnhPerServStatsTotalServConn  OBJECT-TYPE
    SYNTAX  Counter64
    MAX-ACCESS  read-only
    STATUS  current
    DESCRIPTION
        "Total number of new backend server connections for virtual service."
    ::= {tcpConnmngEnhPerServStatsEntry 8}

tcpConnmngEnhPerServStatsTotalServConnReuse  OBJECT-TYPE
    SYNTAX  Counter64
    MAX-ACCESS  read-only
    STATUS  current
    DESCRIPTION
        "Total number of reused backend server connections for virtual service."
    ::= {tcpConnmngEnhPerServStatsEntry 9}

tcpConnmngEnhPerServStatsTotalCliTrans  OBJECT-TYPE
    SYNTAX  Counter64
    MAX-ACCESS  read-only
    STATUS  current
    DESCRIPTION
        "Total number of client transactions passed to AX for virtual service."
    ::= {tcpConnmngEnhPerServStatsEntry 10}

tcpConnmngEnhPerServStatsTotalMulRatio  OBJECT-TYPE
    SYNTAX  Integer32
    MAX-ACCESS  read-only
    STATUS  current
    DESCRIPTION
        "Connection multiplexing ratio on total numbers for virtual service."
    ::= {tcpConnmngEnhPerServStatsEntry 11}

slbSapAslrTableMaxSize OBJECT-TYPE
    SYNTAX  Integer32 
    MAX-ACCESS  read-only 
    STATUS  current 
    DESCRIPTION 
        "The maximum number of entries in SAP ASLR connection management table.
         Note:This mib is not supported on VX instance of Virtualization." 
    ::= { sapCfg 1 }

slbCurCfgSapAslrTable OBJECT-TYPE
    SYNTAX  SEQUENCE OF SlbCurCfgSapAslrEntry 
    MAX-ACCESS  not-accessible
    STATUS  current
    DESCRIPTION
        "The SAP ASLR connection management  table.
         Note:This mib is not supported on VX instance of Virtualization."
    ::= { sapCfg 2 }

slbCurCfgSapAslrEntry OBJECT-TYPE
    SYNTAX  SlbCurCfgSapAslrEntry
    MAX-ACCESS  not-accessible
    STATUS  current
    DESCRIPTION
        "A row in the SAP ASLR connection management table."
    INDEX   { slbCurCfgSapAslrIndex }
    ::= { slbCurCfgSapAslrTable 1 }

SlbCurCfgSapAslrEntry ::= SEQUENCE {
    slbCurCfgSapAslrIndex           Integer32,
    slbCurCfgSapAslrIpAddr          IpAddress,
    slbCurCfgSapAslrIpv6Addr     DisplayString,
    slbCurCfgSapAslrIpVer            INTEGER,
    slbCurCfgSapAslrPortNum      INTEGER,
    slbCurCfgSapAslrVipAddr       IpAddress,
    slbCurCfgSapAslrVipv6Addr   DisplayString,
    slbCurCfgSapAslrVipIpVer      INTEGER,
    slbCurCfgSapAslrInterval        INTEGER,
    slbCurCfgSapAslrState            INTEGER,
    slbCurCfgSapAslrName           DisplayString,
    slbCurCfgSapAslrLastAct        DisplayString,
    slbCurCfgSapAslrAutoConfig  INTEGER,
    slbCurCfgSapAslrSessionInfo INTEGER,
    slbCurCfgSapAslrDelete          INTEGER,
    slbCurCfgSapAslrSignature    DisplayString,
    slbCurCfgSapAslrServCert      DisplayString
    }

slbCurCfgSapAslrIndex OBJECT-TYPE
    SYNTAX  Integer32
    MAX-ACCESS  read-only
    STATUS  current
    DESCRIPTION
        "The Sap Aslr number" 
    ::= { slbCurCfgSapAslrEntry 1 }

slbCurCfgSapAslrIpAddr OBJECT-TYPE
    SYNTAX  IpAddress
    MAX-ACCESS  read-only
    STATUS  current
    DESCRIPTION
        "IP address of the Sap Aslr identified by the instance of the 
         slbCurCfgSapAslrIndex." 
    ::= { slbCurCfgSapAslrEntry 2 }

slbCurCfgSapAslrIpv6Addr OBJECT-TYPE
   SYNTAX DisplayString (SIZE(0..40))
    MAX-ACCESS  read-only
    STATUS  current
    DESCRIPTION
    "  IPV6 address of the Sap Aslr manager identified by the instance of the slbCurCfgSapAslrIndex
       Address should be 4-byte hexadecimal colon notation. Valid IPv6 address should be in
       any of the following forms xxxx:xxxx:xxxx:xxxx:xxxx:xxxx:xxxx:xxxx or xxxx::xxxx:xxxx:xxxx:xxxx or ::xxxx "
   ::= { slbCurCfgSapAslrEntry 3 }


slbCurCfgSapAslrIpVer OBJECT-TYPE
    SYNTAX  INTEGER{
        ipv4(1),
        ipv6(2),
        unsupported(2147483647)
        }
    MAX-ACCESS  read-only
    STATUS  current
    DESCRIPTION
        "The type of IP address."
    ::= { slbCurCfgSapAslrEntry 4  }


slbCurCfgSapAslrPortNum OBJECT-TYPE  
    SYNTAX  INTEGER (2..65534)
    MAX-ACCESS  read-only  
    STATUS  current  
    DESCRIPTION 
        "The Sap Aslr service port number."  
    ::= { slbCurCfgSapAslrEntry 5 } 


slbCurCfgSapAslrVipAddr OBJECT-TYPE
    SYNTAX  IpAddress
    MAX-ACCESS  read-only
    STATUS  current
    DESCRIPTION
        "IP address of the VIP identified by the instance of the 
         slbNewCfgSapAslrIndex." 
    ::= { slbCurCfgSapAslrEntry 6 }

slbCurCfgSapAslrVipv6Addr OBJECT-TYPE
   SYNTAX DisplayString (SIZE(0..40))
    MAX-ACCESS  read-only
    STATUS  current
    DESCRIPTION
    "  IPV6 address of the VIP identified by the instance of the slbNewCfgSapAslrIndex
       Address should be 4-byte hexadecimal colon notation. Valid IPv6 address should be in
       any of the following forms xxxx:xxxx:xxxx:xxxx:xxxx:xxxx:xxxx:xxxx or xxxx::xxxx:xxxx:xxxx:xxxx or ::xxxx "
   ::= { slbCurCfgSapAslrEntry 7 }

slbCurCfgSapAslrVipIpVer OBJECT-TYPE
    SYNTAX  INTEGER{
        ipv4(1),
        ipv6(2),
        unsupported(2147483647)
        }
    MAX-ACCESS  read-only
    STATUS  current
    DESCRIPTION
        "The type of VIP IP address."
    ::= { slbCurCfgSapAslrEntry 8  }

slbCurCfgSapAslrInterval OBJECT-TYPE
    SYNTAX  INTEGER (1..60)
    MAX-ACCESS  read-only
    STATUS  current
    DESCRIPTION
        "Set the Sap Aslr server inspection interval." 
    ::= { slbCurCfgSapAslrEntry 9 }


slbCurCfgSapAslrState OBJECT-TYPE
    SYNTAX  INTEGER {
	enabled(1),
	disabled(2),
        unsupported(2147483647)
	}
    MAX-ACCESS  read-only
    STATUS  current
    DESCRIPTION
        "Enable or disable the Sap Aslr server sampling." 
    ::= { slbCurCfgSapAslrEntry 10 }

slbCurCfgSapAslrName OBJECT-TYPE 
    SYNTAX  DisplayString (SIZE(0..31))
    MAX-ACCESS  read-only 
    STATUS  current 
    DESCRIPTION 
        "The name of the Sap Aslr connection."  
    ::= { slbCurCfgSapAslrEntry 11 }

slbCurCfgSapAslrLastAct OBJECT-TYPE 
    SYNTAX  DisplayString (SIZE(0..31))
    MAX-ACCESS  read-only 
    STATUS  current 
    DESCRIPTION 
        "The Sap Aslr connection last activity time stamp."  
    ::= { slbCurCfgSapAslrEntry 12 }

slbCurCfgSapAslrAutoConfig OBJECT-TYPE
    SYNTAX  INTEGER {
        basic(1),
        full(2),
        unsupported(2147483647)
        }
    MAX-ACCESS  read-create
    STATUS  current
    DESCRIPTION
        "Defines the configuration update process.  
         When set the value to basic (1), the configuration is limited,
	 comparing to full (2)"
    ::= { slbCurCfgSapAslrEntry 13 }

slbCurCfgSapAslrSessionInfo  OBJECT-TYPE
 SYNTAX  INTEGER 
    MAX-ACCESS  read-only
    STATUS  current
    DESCRIPTION
        "Set the Sap Aslr session information.
	When read, zero is returned." 
    ::= { slbCurCfgSapAslrEntry 14 }


slbCurCfgSapAslrDelete OBJECT-TYPE
    SYNTAX  INTEGER {
        other(1),
        delete(2),
        unsupported(2147483647)
        }
    MAX-ACCESS  read-only
    STATUS  current
    DESCRIPTION
        "When set to the value of 2 (delete), the entire row is deleted. 
         When read, other(1) is returned. Setting the value to anything 
         other than 2(delete) has no effect on the state of the row."
    ::= { slbCurCfgSapAslrEntry 15 }



slbCurCfgSapAslrSignature OBJECT-TYPE 
    SYNTAX  DisplayString (SIZE(0..40))
    MAX-ACCESS  read-only 
    STATUS  current 
    DESCRIPTION 
        "The Sap Aslr connection signature."  
    ::= { slbCurCfgSapAslrEntry 16 }

slbCurCfgSapAslrServCert OBJECT-TYPE
    SYNTAX  DisplayString  (SIZE(0..32))
    MAX-ACCESS  read-create
    STATUS  current
    DESCRIPTION
        "Server Certificate name associated with this virtual service."
    ::= { slbCurCfgSapAslrEntry 17 }

slbNewCfgSapAslrTable OBJECT-TYPE
    SYNTAX  SEQUENCE OF SlbNewCfgSapAslrEntry 
    MAX-ACCESS  not-accessible
    STATUS  current
    DESCRIPTION
        "The SAP ASLR connection management  table.
         Note:This mib is not supported on VX instance of Virtualization."
    ::= { sapCfg 3 }

slbNewCfgSapAslrEntry OBJECT-TYPE
    SYNTAX  SlbNewCfgSapAslrEntry
    MAX-ACCESS  not-accessible
    STATUS  current
    DESCRIPTION
        "A row in the SAP ASLR connection management table."
    INDEX   { slbNewCfgSapAslrIndex }
    ::= { slbNewCfgSapAslrTable 1 }

SlbNewCfgSapAslrEntry ::= SEQUENCE {
    slbNewCfgSapAslrIndex           Integer32,
    slbNewCfgSapAslrIpAddr          IpAddress,
    slbNewCfgSapAslrIpv6Addr     DisplayString,
    slbNewCfgSapAslrIpVer            INTEGER,
    slbNewCfgSapAslrPortNum      INTEGER,
    slbNewCfgSapAslrVipAddr       IpAddress,
    slbNewCfgSapAslrVipv6Addr   DisplayString,
    slbNewCfgSapAslrVipIpVer      INTEGER,
    slbNewCfgSapAslrInterval        INTEGER,
    slbNewCfgSapAslrState            INTEGER,
    slbNewCfgSapAslrName           DisplayString,
    slbNewCfgSapAslrLastAct        DisplayString,
    slbNewCfgSapAslrAutoConfig INTEGER,
    slbNewCfgSapAslrSessionInfo  INTEGER,
    slbNewCfgSapAslrDelete           INTEGER,
    slbNewCfgSapAslrSignature     DisplayString,
    slbNewCfgSapAslrServCert       DisplayString
    }

slbNewCfgSapAslrIndex OBJECT-TYPE
    SYNTAX  Integer32
    MAX-ACCESS  read-create
    STATUS  current
    DESCRIPTION
        "The Sap Aslr number" 
    ::= { slbNewCfgSapAslrEntry 1 }

slbNewCfgSapAslrIpAddr OBJECT-TYPE
    SYNTAX  IpAddress
    MAX-ACCESS  read-create
    STATUS  current
    DESCRIPTION
        "IP address of the Sap Aslr identified by the instance of the 
         slbNewCfgSapAslrIndex." 
    ::= { slbNewCfgSapAslrEntry 2 }

slbNewCfgSapAslrIpv6Addr OBJECT-TYPE
   SYNTAX DisplayString (SIZE(0..40))
    MAX-ACCESS  read-create
    STATUS  current
    DESCRIPTION
    "  IPV6 address of the Sap Aslr manager identified by the instance of the slbNewCfgSapAslrIndex
       Address should be 4-byte hexadecimal colon notation. Valid IPv6 address should be in
       any of the following forms xxxx:xxxx:xxxx:xxxx:xxxx:xxxx:xxxx:xxxx or xxxx::xxxx:xxxx:xxxx:xxxx or ::xxxx "
   ::= { slbNewCfgSapAslrEntry 3 }

slbNewCfgSapAslrIpVer OBJECT-TYPE
    SYNTAX  INTEGER{
        ipv4(1),
        ipv6(2),
        unsupported(2147483647)
        }
    MAX-ACCESS  read-create
    STATUS  current
    DESCRIPTION
        "The type of IP address."
    ::= { slbNewCfgSapAslrEntry 4  }

slbNewCfgSapAslrPortNum OBJECT-TYPE  
    SYNTAX  INTEGER (2..65534)
    MAX-ACCESS  read-create 
    STATUS  current  
    DESCRIPTION 
        "The Sap Aslr service port number."  
    ::= { slbNewCfgSapAslrEntry 5 } 

slbNewCfgSapAslrVipAddr OBJECT-TYPE
    SYNTAX  IpAddress
    MAX-ACCESS  read-create
    STATUS  current
    DESCRIPTION
        "IP address of the VIP identified by the instance of the 
         slbNewCfgSapAslrIndex." 
    ::= { slbNewCfgSapAslrEntry 6 }

slbNewCfgSapAslrVipv6Addr OBJECT-TYPE
   SYNTAX DisplayString (SIZE(0..40))
    MAX-ACCESS  read-create
    STATUS  current
    DESCRIPTION
    "  IPV6 address of the VIP identified by the instance of the slbNewCfgSapAslrIndex
       Address should be 4-byte hexadecimal colon notation. Valid IPv6 address should be in
       any of the following forms xxxx:xxxx:xxxx:xxxx:xxxx:xxxx:xxxx:xxxx or xxxx::xxxx:xxxx:xxxx:xxxx or ::xxxx "
   ::= { slbNewCfgSapAslrEntry 7 }


slbNewCfgSapAslrVipIpVer OBJECT-TYPE
    SYNTAX  INTEGER{
        ipv4(1),
        ipv6(2),
        unsupported(2147483647)
        }
    MAX-ACCESS  read-create
    STATUS  current
    DESCRIPTION
        "The type of VIP IP address."
    ::= { slbNewCfgSapAslrEntry 8  }

slbNewCfgSapAslrInterval OBJECT-TYPE
    SYNTAX  INTEGER (4..60)
    MAX-ACCESS  read-create
    STATUS  current
    DESCRIPTION
        "Set the Sap Aslr server inspection interval." 
    ::= { slbNewCfgSapAslrEntry 9 }

slbNewCfgSapAslrState OBJECT-TYPE
    SYNTAX  INTEGER {
	enabled(1),
	disabled(2),
        unsupported(2147483647)
	}
    MAX-ACCESS  read-create
    STATUS  current
    DESCRIPTION
        "Enable or disable the Sap Aslr server sampling." 
    ::= { slbNewCfgSapAslrEntry 10 }

slbNewCfgSapAslrName OBJECT-TYPE 
    SYNTAX  DisplayString (SIZE(0..31))
    MAX-ACCESS  read-create 
    STATUS  current 
    DESCRIPTION 
        "The name of the Sap Aslr connection."  
    ::= { slbNewCfgSapAslrEntry 11 }

slbNewCfgSapAslrLastAct OBJECT-TYPE 
    SYNTAX  DisplayString (SIZE(0..31))
    MAX-ACCESS  read-create 
    STATUS  current 
    DESCRIPTION 
        "The Sap Aslr last activity time stamp."  
    ::= { slbNewCfgSapAslrEntry 12 }

slbNewCfgSapAslrAutoConfig OBJECT-TYPE
    SYNTAX  INTEGER {
        basic(1),
        full(2),
        unsupported(2147483647)
        }
    MAX-ACCESS  read-create
    STATUS  current
    DESCRIPTION
        "Defines the configuration update process.  
         When set the value to basic (1), the configuration is limited,
	 comparing to full (2)"
    ::= { slbNewCfgSapAslrEntry 13 }

slbNewCfgSapAslrSessionInfo  OBJECT-TYPE
 SYNTAX  INTEGER 
    MAX-ACCESS  read-create
    STATUS  current
    DESCRIPTION
        "Set the Sap Aslr session information.
	When read, zero is returned." 
    ::= { slbNewCfgSapAslrEntry 14 }

slbNewCfgSapAslrDelete OBJECT-TYPE
    SYNTAX  INTEGER {
        other(1),
        delete(2),
        unsupported(2147483647)
        }
    MAX-ACCESS  read-create
    STATUS  current
    DESCRIPTION
        "When set to the value of 2 (delete), the entire row is deleted. 
         When read, other(1) is returned. Setting the value to anything 
         other than 2(delete) has no effect on the state of the row."
    ::= { slbNewCfgSapAslrEntry 15 }

slbNewCfgSapAslrSignature OBJECT-TYPE 
    SYNTAX  DisplayString (SIZE(0..40))
    MAX-ACCESS  read-create 
    STATUS  current 
    DESCRIPTION 
        "The Sap Aslr connection signature."  
    ::= { slbNewCfgSapAslrEntry 16 }

slbNewCfgSapAslrServCert OBJECT-TYPE
    SYNTAX  DisplayString  (SIZE(0..32))
    MAX-ACCESS  read-create
    STATUS  current
    DESCRIPTION
        "Server Certificate name associated with this virtual service."
    ::= { slbNewCfgSapAslrEntry 17 }


slbStatSapAslrTable OBJECT-TYPE
    SYNTAX  SEQUENCE OF SlbStatSapAslrEntry
    MAX-ACCESS  not-accessible
    STATUS  current
    DESCRIPTION
        "The sap aslrr statistics table.  This table shows the statistics 
         of sap aslr for a particular vip.
         Note:This mib is not supported on VX instance of Virtualization."
    ::= { sapStats 1 }

slbStatSapAslrEntry OBJECT-TYPE
    SYNTAX  SlbStatSapAslrEntry
    MAX-ACCESS  not-accessible
    STATUS  current
    DESCRIPTION
        "A row in the sap aslr statistics table."
    INDEX  { slbStatSapAslrIndex }
    ::= { slbStatSapAslrTable 1 }
              
SlbStatSapAslrEntry ::= SEQUENCE {
   slbStatSapAslrIndex                    Integer32,
   slbStatSapAslrSampling             Counter32,
   slbStatSapAslrFailure                 Counter32,
   slbStatSapAslrDeviceUpdates  Counter32,
   slbStatSapAslrDeviceFailure     Counter32,
   slbStatSapAslrLastAct                DisplayString
    }

slbStatSapAslrIndex OBJECT-TYPE
    SYNTAX  Integer32
    MAX-ACCESS  read-only
    STATUS  current
    DESCRIPTION
        "The Sap Aslr table index."
    ::= { slbStatSapAslrEntry 1 }

slbStatSapAslrSampling OBJECT-TYPE 
    SYNTAX  Counter32 
    MAX-ACCESS  read-only
    STATUS  current 
    DESCRIPTION 
        "The number of Sap Aslr server lookups." 
    ::= { slbStatSapAslrEntry 2 }

slbStatSapAslrFailure OBJECT-TYPE 
    SYNTAX  Counter32
    MAX-ACCESS  read-only
    STATUS  current 
    DESCRIPTION 
        "The number of Sap Aslr server lookup failures."
    ::= { slbStatSapAslrEntry 3 }

slbStatSapAslrDeviceUpdates OBJECT-TYPE 
    SYNTAX  Counter32 
    MAX-ACCESS  read-only
    STATUS  current 
    DESCRIPTION 
        "The number of Alteon automated configuration updates."
    ::= { slbStatSapAslrEntry 4 }

slbStatSapAslrDeviceFailure OBJECT-TYPE
    SYNTAX  Counter32
    MAX-ACCESS  read-only
    STATUS  current
    DESCRIPTION
        "The number of Alteon automated configuration failure."
    ::= { slbStatSapAslrEntry 5 }

slbStatSapAslrLastAct OBJECT-TYPE
    SYNTAX  DisplayString (SIZE(0..31))
    MAX-ACCESS  read-only
    STATUS  current
    DESCRIPTION
        "The Sap Aslr last activity time stamp."
    ::= { slbStatSapAslrEntry 6 }

--PIP Stats start
slbStatPipTable OBJECT-TYPE
    SYNTAX  SEQUENCE OF SlbStatPipEntry
    MAX-ACCESS  not-accessible
    STATUS  current
    DESCRIPTION
        "The Proxy IP table statistics.
         Note:This mib is not supported on VX instance of Virtualization."
    ::= { pipStats 1 }

slbStatPipEntry OBJECT-TYPE
    SYNTAX  SlbStatPipEntry
    MAX-ACCESS  not-accessible
    STATUS  current
    DESCRIPTION
        "The Proxy IP statistics of a particular table entry."
    INDEX   { slbStatPipIndex }
    ::= { slbStatPipTable 1 }

SlbStatPipEntry ::= SEQUENCE {
    slbStatPipIndex               IpAddress,
    slbStatPipMask               IpAddress,    
    slbStatPipUsed	    Counter32,    
    slbStatPipFailure	    Counter32  
    }
    
slbStatPipIndex OBJECT-TYPE
    SYNTAX  IpAddress
    MAX-ACCESS  read-only
    STATUS  current
    DESCRIPTION
        "The PIP address ." 
    ::= { slbStatPipEntry 1 }    
    
slbStatPipMask OBJECT-TYPE
    SYNTAX  IpAddress
    MAX-ACCESS  read-only
    STATUS  current
    DESCRIPTION
        "The PIP address Mask ." 
    ::= { slbStatPipEntry 2 }    
    
slbStatPipUsed OBJECT-TYPE 
    SYNTAX  Counter32 
    MAX-ACCESS  read-only
    STATUS  current 
    DESCRIPTION 
        "The total number of PIP used counter."
    ::= { slbStatPipEntry 3 }

slbStatPipFailure OBJECT-TYPE 
    SYNTAX  Counter32 
    MAX-ACCESS  read-only
    STATUS  current 
    DESCRIPTION 
        "The total number of PIP Failure counter."
    ::= { slbStatPipEntry 4 }

slbStatPipNwClassTable OBJECT-TYPE
    SYNTAX  SEQUENCE OF SlbStatPipNwClassEntry
    MAX-ACCESS  not-accessible
    STATUS  current
    DESCRIPTION
        "The Proxy IP NwClass table statistics.
         Note:This mib is not supported on VX instance of Virtualization."
    ::= { pipStats 2 }

slbStatPipNwClassEntry OBJECT-TYPE
    SYNTAX  SlbStatPipNwClassEntry
    MAX-ACCESS  not-accessible
    STATUS  current
    DESCRIPTION
        "The Proxy IP NwClass statistics of a particular table entry."
    INDEX   { slbStatPipNwClassId }
    ::= { slbStatPipNwClassTable 1 }

SlbStatPipNwClassEntry ::= SEQUENCE {
    slbStatPipNwClassId               DisplayString,
    slbStatPipNwClassName          DisplayString,
    slbStatPipNwClassUsed	    Counter32,    
    slbStatPipNwClassFailure	    Counter32  
    }
    
slbStatPipNwClassId OBJECT-TYPE
    SYNTAX  DisplayString (SIZE (0..32))
    MAX-ACCESS  read-only
    STATUS  current
    DESCRIPTION
        "The PIP Network class id ." 
    ::= { slbStatPipNwClassEntry 1 }    

slbStatPipNwClassName OBJECT-TYPE
    SYNTAX  DisplayString (SIZE (0..32))
    MAX-ACCESS  read-only
    STATUS  current
    DESCRIPTION
        "The PIP Network class name ." 
    ::= { slbStatPipNwClassEntry 2 }  
    
slbStatPipNwClassUsed OBJECT-TYPE 
    SYNTAX  Counter32 
    MAX-ACCESS  read-only
    STATUS  current 
    DESCRIPTION 
        "The total number of PIP NwClass used counter."
    ::= { slbStatPipNwClassEntry 3 }

slbStatPipNwClassFailure OBJECT-TYPE 
    SYNTAX  Counter32 
    MAX-ACCESS  read-only
    STATUS  current 
    DESCRIPTION 
        "The total number of PIP NwClass Failure counter."
    ::= { slbStatPipNwClassEntry 4 }

slbAppShapeStatsTable OBJECT-TYPE
   SYNTAX SEQUENCE OF SlbAppShapeStatsEntry
   MAX-ACCESS not-accessible
   STATUS current
   DESCRIPTION
       "A table for AppShape statistics.
        Note:This mib is not supported on VX instance of Virtualization."
   ::= {appShapeStats 1}

slbAppShapeStatsEntry OBJECT-TYPE
   SYNTAX SlbAppShapeStatsEntry
   MAX-ACCESS not-accessible
   STATUS  current
   DESCRIPTION
       " The row definition for AppShape statistics."
   INDEX  { slbAppShapeScriptId }
   ::= {slbAppShapeStatsTable 1}

SlbAppShapeStatsEntry  ::= SEQUENCE {
        slbAppShapeScriptId                      DisplayString,
        slbAppShapeEvent                         Integer32,
        slbAppShapeActivations                   Integer32,
        slbAppShapeFailures                      Integer32,
        slbAppShapeAborts                        Integer32,
	slbAppShapeEventAsString		 DisplayString
        }	

slbAppShapeScriptId  OBJECT-TYPE
   SYNTAX  DisplayString
   MAX-ACCESS  read-only
   STATUS  current
   DESCRIPTION
       "AppShape script identifier."
   ::= {slbAppShapeStatsEntry 1}

slbAppShapeEvent  OBJECT-TYPE
   SYNTAX  Integer32
   MAX-ACCESS  read-only
   STATUS  current
   DESCRIPTION
       "AppShape script identifier. 
        0 BIT is for CLIENT_ACCEPTED,
        1 BIT is for CLIENT_DATA,
        2 BIT is for CLIENT_CLOSED,
        3 BIT is for SERVER_CONNECTED,
        4 BIT is for SERVER_DATA,
        5 BIT is for SERVER_CLOSED,
        6 BIT is for HTTP_REQUEST,
        7 BIT is for HTTP_REQUEST_DATA,
        8 BIT is for HTTP_CRULE_MATCH,
        9 BIT is for HTTP_CRULE_NOMATCH,
        10 BIT is for HTTP_RESPONSE,
        11 BIT is for HTTP_CACHE_RESPONSE,
        12 BIT is for HTTP_RESPONSE_CONTINUE,
        13 BIT is for HTTP_RESPONSE_DATA,
        14 BIT is for SIP_REQUEST,
        15 BIT is for SIP_RESPONSE,
        16 BIT is for PERSIST_DOWN,
	17 BIT is for LB_SELECTED,
	18 BIT is for LB_FAILED,
	19 BIT is for NAME_RESOLVED,
	20 BIT is for SESSION_CLOSE.
        If the bit is SET than the event has occurred."
   ::= {slbAppShapeStatsEntry 2}

slbAppShapeActivations OBJECT-TYPE
   SYNTAX  Integer32
   MAX-ACCESS  read-only
   STATUS  current
   DESCRIPTION
       "Number of activations."
   ::= {slbAppShapeStatsEntry 3}

slbAppShapeFailures OBJECT-TYPE
   SYNTAX  Integer32
   MAX-ACCESS  read-only
   STATUS  current
   DESCRIPTION
       "Number of failures."
   ::= {slbAppShapeStatsEntry 4}

slbAppShapeAborts  OBJECT-TYPE
   SYNTAX  Integer32
   MAX-ACCESS  read-only
   STATUS  current
   DESCRIPTION
       "Number of aborts."
   ::= {slbAppShapeStatsEntry 5}

slbAppShapeEventAsString OBJECT-TYPE
   SYNTAX  DisplayString
   MAX-ACCESS  read-only
   STATUS  current
   DESCRIPTION
   "The events that occured - displayed in a string"
   ::= {slbAppShapeStatsEntry 6}



    -- ADVHC Start

SlbAdvhcType ::= INTEGER {
        empty(0),
        arp(1),
    	dhcp(2),
    	dns(3),
    	ftp(4),
    	http(5),
    	imap(6),
    	ldap(7),
    	db(8),
    	nntp(9),
    	icmp(10),
    	pop3(11),
    	radius(12),
    	rtsp(13),
    	sip(14),
    	smtp(15),
    	snmp(16),
    	ssl(17),
    	tcp(18),
    	tftp(19),
    	udp(20),
    	wap(21),
        wts(22),
    	script(23),
    	link(24),
    	logexp(25),
        virtualwire(26),
        dssp(27),
        clusthcfr(28),
        clusthcme(29),
        advvirtualwire(30),
        unsupported(2147483647)
        }

SlbAdvhcEnaDis ::= INTEGER { enabled(1), disabled(2), unsupported(2147483647) }
SlbAdvhcDelete ::= INTEGER { other(1), delete(2), unsupported(2147483647) }
SlbAdvhcIPVer  ::= INTEGER { ipv4(1), ipv6(2), none(3) }

-- Advance Health Check General Params
--------------------------------------

slbAdvhcGeneralTable  OBJECT-TYPE
    SYNTAX  SEQUENCE OF SlbAdvhcGeneralEntry
    MAX-ACCESS  not-accessible
    STATUS  current
    DESCRIPTION
        "Note:This mib is not supported on VX instance of Virtualization."
    ::= { advhcCfg 1 }

slbAdvhcGeneralEntry OBJECT-TYPE
    SYNTAX  SlbAdvhcGeneralEntry
    MAX-ACCESS  not-accessible
    STATUS  current
    DESCRIPTION
        "."
    INDEX   { slbAdvhcGeneralID }
    ::= { slbAdvhcGeneralTable 1 }
 
SlbAdvhcGeneralEntry ::= SEQUENCE {
    slbAdvhcGeneralID       DisplayString,
    slbAdvhcGeneralType     SlbAdvhcType,
    slbAdvhcGeneralName     DisplayString,
    slbAdvhcGeneralDPort    INTEGER,
    slbAdvhcGeneralIPVer    SlbAdvhcIPVer,
    slbAdvhcGeneralHostName DisplayString
    }

slbAdvhcGeneralID OBJECT-TYPE
    SYNTAX   DisplayString (SIZE (0..32))
    MAX-ACCESS  read-only
    STATUS  current
    DESCRIPTION
        "Health check ID."
    ::= { slbAdvhcGeneralEntry 1 }

slbAdvhcGeneralType OBJECT-TYPE
    SYNTAX  SlbAdvhcType
    MAX-ACCESS  read-only
    STATUS  current
    DESCRIPTION
        "Health check type."
    ::= { slbAdvhcGeneralEntry 2 }

slbAdvhcGeneralName OBJECT-TYPE
    SYNTAX   DisplayString (SIZE (0..32))
    MAX-ACCESS  read-only
    STATUS  current
    DESCRIPTION
        "Health check name."
    ::= { slbAdvhcGeneralEntry 3 }

slbAdvhcGeneralDPort OBJECT-TYPE
    SYNTAX  INTEGER (0..65534)
    MAX-ACCESS  read-only
    STATUS  current
    DESCRIPTION
        "Health check destination port."
    ::= { slbAdvhcGeneralEntry 4 }

slbAdvhcGeneralIPVer OBJECT-TYPE
    SYNTAX  SlbAdvhcIPVer
    MAX-ACCESS  read-only
    STATUS  current
    DESCRIPTION
        "Health check IP version."
    ::= { slbAdvhcGeneralEntry 5 }

slbAdvhcGeneralHostName OBJECT-TYPE
    SYNTAX   DisplayString (SIZE (0..128))
    MAX-ACCESS  read-only
    STATUS  current
    DESCRIPTION
        "Health check hostname."
    ::= { slbAdvhcGeneralEntry 6 }


-- Advance Health Check ARP
---------------------------

slbCurAdvhcArpTable  OBJECT-TYPE
    SYNTAX  SEQUENCE OF SlbCurAdvhcArpEntry
    MAX-ACCESS  not-accessible
    STATUS  current
    DESCRIPTION
        "Note:This mib is not supported on VX instance of Virtualization."
    ::= { advhcCfg 3 }

slbCurAdvhcArpEntry OBJECT-TYPE
    SYNTAX  SlbCurAdvhcArpEntry
    MAX-ACCESS  not-accessible
    STATUS  current
    DESCRIPTION
        "."
    INDEX   { slbCurAdvhcArpID }
    ::= { slbCurAdvhcArpTable 1 }

SlbCurAdvhcArpEntry ::= SEQUENCE {
    slbCurAdvhcArpID                DisplayString,
    slbCurAdvhcArpName              DisplayString,
    slbCurAdvhcArpIPVer             SlbAdvhcIPVer,
    slbCurAdvhcArpHostName          DisplayString,
    slbCurAdvhcArpTransparent       SlbAdvhcEnaDis,
    slbCurAdvhcArpInterval          INTEGER,
    slbCurAdvhcArpRetries           INTEGER,
    slbCurAdvhcArpRestoreRetries    INTEGER,
    slbCurAdvhcArpTimeout           INTEGER,
    slbCurAdvhcArpOverflow          INTEGER,
    slbCurAdvhcArpDownInterval      INTEGER,
    slbCurAdvhcArpInvert            SlbAdvhcEnaDis
    }

slbCurAdvhcArpID OBJECT-TYPE
    SYNTAX   DisplayString (SIZE (0..128))
    MAX-ACCESS  read-only
    STATUS  current
    DESCRIPTION
        "ARP Health check id."
    ::= { slbCurAdvhcArpEntry 1 }

slbCurAdvhcArpName OBJECT-TYPE
    SYNTAX   DisplayString (SIZE (0..128))
    MAX-ACCESS  read-only
    STATUS  current
    DESCRIPTION
        "ARP Health check name."
    ::= { slbCurAdvhcArpEntry 2 }

slbCurAdvhcArpIPVer OBJECT-TYPE
    SYNTAX  SlbAdvhcIPVer
    MAX-ACCESS  read-only
    STATUS  current
    DESCRIPTION
        "ARP Health check IP version."
    ::= { slbCurAdvhcArpEntry 3 }

slbCurAdvhcArpHostName OBJECT-TYPE
    SYNTAX   DisplayString (SIZE (0..128))
    MAX-ACCESS  read-only
    STATUS  current
    DESCRIPTION
        "ARP health check hostname."
    ::= { slbCurAdvhcArpEntry 4 }

slbCurAdvhcArpTransparent OBJECT-TYPE
    SYNTAX  SlbAdvhcEnaDis
    MAX-ACCESS  read-only
    STATUS  obsolete
    DESCRIPTION
        "Is ARP health check transparent."
    ::= { slbCurAdvhcArpEntry 5 }

slbCurAdvhcArpInterval OBJECT-TYPE
    SYNTAX  INTEGER (1..600)
    MAX-ACCESS  read-only
    STATUS  current
    DESCRIPTION
        "ARP Health check interval."
    ::= { slbCurAdvhcArpEntry 6 }

slbCurAdvhcArpRetries OBJECT-TYPE
    SYNTAX  INTEGER (1..63)
    MAX-ACCESS  read-only
    STATUS  current
    DESCRIPTION
        "ARP Health check retries before failure counter."
    ::= { slbCurAdvhcArpEntry 7 }

slbCurAdvhcArpRestoreRetries OBJECT-TYPE
    SYNTAX  INTEGER (1..63)
    MAX-ACCESS  read-only
    STATUS  current
    DESCRIPTION
        "ARP Health check retries before marking health check up, counter."
    ::= { slbCurAdvhcArpEntry 8 }

slbCurAdvhcArpTimeout OBJECT-TYPE
    SYNTAX  INTEGER (1..63)
    MAX-ACCESS  read-only
    STATUS  current
    DESCRIPTION
        "ARP Health checheck timeout parameter."
    ::= { slbCurAdvhcArpEntry 9 }

slbCurAdvhcArpOverflow OBJECT-TYPE
    SYNTAX  INTEGER (0..600)
    MAX-ACCESS  read-only
    STATUS  current
    DESCRIPTION
        "ARP Health check overflow parameter."
    ::= { slbCurAdvhcArpEntry 10 }

slbCurAdvhcArpDownInterval OBJECT-TYPE
    SYNTAX  INTEGER (0..600)
    MAX-ACCESS  read-only
    STATUS  current
    DESCRIPTION
        "ARP Health check checks Interval on Down-Time."
    ::= { slbCurAdvhcArpEntry 11 }

slbCurAdvhcArpInvert OBJECT-TYPE
    SYNTAX  SlbAdvhcEnaDis
    MAX-ACCESS  read-only
    STATUS  current
    DESCRIPTION
        "ARP Health check invert flag."
    ::= { slbCurAdvhcArpEntry 12 }


slbNewAdvhcArpTable  OBJECT-TYPE
    SYNTAX  SEQUENCE OF SlbNewAdvhcArpEntry
    MAX-ACCESS  not-accessible
    STATUS  current
    DESCRIPTION
        "Note:This mib is not supported on VX instance of Virtualization."
    ::= { advhcCfg 4 }

slbNewAdvhcArpEntry OBJECT-TYPE
    SYNTAX  SlbNewAdvhcArpEntry
    MAX-ACCESS  not-accessible
    STATUS  current
    DESCRIPTION
        "."
    INDEX   { slbNewAdvhcArpID }
    ::= { slbNewAdvhcArpTable 1 }

SlbNewAdvhcArpEntry ::= SEQUENCE {
    slbNewAdvhcArpID                DisplayString,
    slbNewAdvhcArpName              DisplayString,
    slbNewAdvhcArpIPVer             SlbAdvhcIPVer,
    slbNewAdvhcArpHostName          DisplayString,
    slbNewAdvhcArpTransparent       SlbAdvhcEnaDis,
    slbNewAdvhcArpInterval          INTEGER,
    slbNewAdvhcArpRetries           INTEGER,
    slbNewAdvhcArpRestoreRetries    INTEGER,
    slbNewAdvhcArpTimeout           INTEGER,
    slbNewAdvhcArpOverflow          INTEGER,
    slbNewAdvhcArpDownInterval      INTEGER,
    slbNewAdvhcArpInvert            SlbAdvhcEnaDis,
    slbNewAdvhcArpCopy              DisplayString,
    slbNewAdvhcArpDelete            SlbAdvhcDelete
    }

slbNewAdvhcArpID OBJECT-TYPE
    SYNTAX   DisplayString (SIZE (0..128))
    MAX-ACCESS  read-only
    STATUS  current
    DESCRIPTION
        "ARP Health check id."
    ::= { slbNewAdvhcArpEntry 1 }

slbNewAdvhcArpName OBJECT-TYPE
    SYNTAX   DisplayString (SIZE (0..128))
    MAX-ACCESS  read-write
    STATUS  current
    DESCRIPTION
        "ARP Health check name."
    ::= { slbNewAdvhcArpEntry 2 }

slbNewAdvhcArpIPVer OBJECT-TYPE
    SYNTAX  SlbAdvhcIPVer
    MAX-ACCESS  read-write
    STATUS  current
    DESCRIPTION
        "ARP Health check IP version."
    ::= { slbNewAdvhcArpEntry 3 }

slbNewAdvhcArpHostName OBJECT-TYPE
    SYNTAX   DisplayString (SIZE (0..128))
    MAX-ACCESS  read-write
    STATUS  current
    DESCRIPTION
        "ARP health check hostname."
    ::= { slbNewAdvhcArpEntry 4 }

slbNewAdvhcArpTransparent OBJECT-TYPE
    SYNTAX  SlbAdvhcEnaDis
    MAX-ACCESS  read-write
    STATUS  obsolete
    DESCRIPTION
        "Is ARP health check transparent."
    ::= { slbNewAdvhcArpEntry 5 }

slbNewAdvhcArpInterval OBJECT-TYPE
    SYNTAX  INTEGER (1..600)
    MAX-ACCESS  read-write
    STATUS  current
    DESCRIPTION
        "ARP Health check interval."
    ::= { slbNewAdvhcArpEntry 6 }

slbNewAdvhcArpRetries OBJECT-TYPE
    SYNTAX  INTEGER (1..63)
    MAX-ACCESS  read-write
    STATUS  current
    DESCRIPTION
        "ARP Health check retries before failure counter."
    ::= { slbNewAdvhcArpEntry 7 }

slbNewAdvhcArpRestoreRetries OBJECT-TYPE
    SYNTAX  INTEGER (1..63)
    MAX-ACCESS  read-write
    STATUS  current
    DESCRIPTION
        "ARP Health check retries before marking health check up, counter."
    ::= { slbNewAdvhcArpEntry 8 }

slbNewAdvhcArpTimeout OBJECT-TYPE
    SYNTAX  INTEGER (1..63)
    MAX-ACCESS  read-write
    STATUS  current
    DESCRIPTION
        "ARP Health checheck timeout parameter."
    ::= { slbNewAdvhcArpEntry 9 }

slbNewAdvhcArpOverflow OBJECT-TYPE
    SYNTAX  INTEGER (0..600)
    MAX-ACCESS  read-write
    STATUS  current
    DESCRIPTION
        "ARP Health check overflow parameter."
    ::= { slbNewAdvhcArpEntry 10 }

slbNewAdvhcArpDownInterval OBJECT-TYPE
    SYNTAX  INTEGER (0..600)
    MAX-ACCESS  read-write
    STATUS  current
    DESCRIPTION
        "ARP Health check checks Interval on Down-Time."
    ::= { slbNewAdvhcArpEntry 11 }

slbNewAdvhcArpInvert OBJECT-TYPE
    SYNTAX  SlbAdvhcEnaDis
    MAX-ACCESS  read-write
    STATUS  current
    DESCRIPTION
        "ARP Health check invert flag."
    ::= { slbNewAdvhcArpEntry 12 }

slbNewAdvhcArpCopy OBJECT-TYPE
    SYNTAX   DisplayString (SIZE (0..128))
    MAX-ACCESS  read-write
    STATUS  current
    DESCRIPTION
        "ARP Health check copy indicator."
    ::= { slbNewAdvhcArpEntry 13 }

slbNewAdvhcArpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcArpEntry 14 }


-- Advance Health Check DHCP
----------------------------

slbCurAdvhcDhcpTable  OBJECT-TYPE
    SYNTAX  SEQUENCE OF SlbCurAdvhcDhcpEntry
    MAX-ACCESS  not-accessible
    STATUS  current
    DESCRIPTION
        "Note:This mib is not supported on VX instance of Virtualization."
    ::= { advhcCfg 5 }

slbCurAdvhcDhcpEntry OBJECT-TYPE
    SYNTAX  SlbCurAdvhcDhcpEntry
    MAX-ACCESS  not-accessible
    STATUS  current
    DESCRIPTION
        "."
    INDEX   { slbCurAdvhcDhcpID }
    ::= { slbCurAdvhcDhcpTable 1 }

SlbCurAdvhcDhcpEntry ::= SEQUENCE {
    slbCurAdvhcDhcpID               DisplayString,
    slbCurAdvhcDhcpName             DisplayString,
    slbCurAdvhcDhcpDPort            INTEGER,
    slbCurAdvhcDhcpIPVer            SlbAdvhcIPVer,
    slbCurAdvhcDhcpHostName         DisplayString,
    slbCurAdvhcDhcpTransparent      SlbAdvhcEnaDis,
    slbCurAdvhcDhcpInterval         INTEGER,
    slbCurAdvhcDhcpRetries          INTEGER,
    slbCurAdvhcDhcpRestoreRetries   INTEGER,
    slbCurAdvhcDhcpTimeout          INTEGER,
    slbCurAdvhcDhcpOverflow         INTEGER,
    slbCurAdvhcDhcpDownInterval     INTEGER,
    slbCurAdvhcDhcpInvert           SlbAdvhcEnaDis,
    slbCurAdvhcDhcpDhcpType         INTEGER,
    slbCurAdvhcDhcpSourcePortType   INTEGER,
    slbCurAdvhcDhcpDhcpDuidType     INTEGER,
    slbCurAdvhcDhcpDhcpDuidLLA      PhysAddress,
    slbCurAdvhcDhcpDhcpDuidTime     Unsigned32
    }

slbCurAdvhcDhcpID OBJECT-TYPE
    SYNTAX   DisplayString (SIZE (0..128))
    MAX-ACCESS  read-only
    STATUS  current
    DESCRIPTION
        "DHCP Health check id."
    ::= { slbCurAdvhcDhcpEntry 1 }

slbCurAdvhcDhcpName OBJECT-TYPE
    SYNTAX   DisplayString (SIZE (0..128))
    MAX-ACCESS  read-only
    STATUS  current
    DESCRIPTION
        "DHCP Health check name."
    ::= { slbCurAdvhcDhcpEntry 2 }

slbCurAdvhcDhcpDPort OBJECT-TYPE
    SYNTAX  INTEGER (0..65534)
    MAX-ACCESS  read-only
    STATUS  current
    DESCRIPTION
        "DHCP Health check port."
    ::= { slbCurAdvhcDhcpEntry 3 }

slbCurAdvhcDhcpIPVer OBJECT-TYPE
    SYNTAX  SlbAdvhcIPVer
    MAX-ACCESS  read-only
    STATUS  current
    DESCRIPTION
        "DHCP Health check IP version."
    ::= { slbCurAdvhcDhcpEntry 4 }

slbCurAdvhcDhcpHostName OBJECT-TYPE
    SYNTAX   DisplayString (SIZE (0..128))
    MAX-ACCESS  read-only
    STATUS  current
    DESCRIPTION
        "DHCP Health check destination hostname."
    ::= { slbCurAdvhcDhcpEntry 5 }

slbCurAdvhcDhcpTransparent OBJECT-TYPE
    SYNTAX  SlbAdvhcEnaDis
    MAX-ACCESS  read-only
    STATUS  current
    DESCRIPTION
        "DHCP Health check transparent flag."
    ::= { slbCurAdvhcDhcpEntry 6 }

slbCurAdvhcDhcpInterval OBJECT-TYPE
    SYNTAX  INTEGER (1..600)
    MAX-ACCESS  read-only
    STATUS  current
    DESCRIPTION
        "DHCP Health check interval."
    ::= { slbCurAdvhcDhcpEntry 7 }

slbCurAdvhcDhcpRetries OBJECT-TYPE
    SYNTAX  INTEGER (1..63)
    MAX-ACCESS  read-only
    STATUS  current
    DESCRIPTION
        "DHCP Health check retries counter."
    ::= { slbCurAdvhcDhcpEntry 8 }

slbCurAdvhcDhcpRestoreRetries OBJECT-TYPE
    SYNTAX  INTEGER (1..63)
    MAX-ACCESS  read-only
    STATUS  current
    DESCRIPTION
        "DHCP Health check restore from down state counter."
    ::= { slbCurAdvhcDhcpEntry 9 }

slbCurAdvhcDhcpTimeout OBJECT-TYPE
    SYNTAX  INTEGER (1..63)
    MAX-ACCESS  read-only
    STATUS  current
    DESCRIPTION
        "DHCP Health check timeout period."
    ::= { slbCurAdvhcDhcpEntry 10 }

slbCurAdvhcDhcpOverflow OBJECT-TYPE
    SYNTAX  INTEGER (0..600)
    MAX-ACCESS  read-only
    STATUS  current
    DESCRIPTION
        "DHCP Health check overflow flag."
    ::= { slbCurAdvhcDhcpEntry 11 }

slbCurAdvhcDhcpDownInterval OBJECT-TYPE
    SYNTAX  INTEGER (0..600)
    MAX-ACCESS  read-only
    STATUS  current
    DESCRIPTION
        "DHCP Health check interval in down state."
    ::= { slbCurAdvhcDhcpEntry 12 }

slbCurAdvhcDhcpInvert OBJECT-TYPE
    SYNTAX  SlbAdvhcEnaDis
    MAX-ACCESS  read-only
    STATUS  current
    DESCRIPTION
        "DHCP Health check invert flag."
    ::= { slbCurAdvhcDhcpEntry 13 }

slbCurAdvhcDhcpDhcpType OBJECT-TYPE
    SYNTAX  INTEGER { inherit(1), inform(2), request(3), relay(4), unsupported(2147483647) }
    MAX-ACCESS  read-only
    STATUS  current
    DESCRIPTION
        "DHCP Health check packet type."
    ::= { slbCurAdvhcDhcpEntry 14 }

slbCurAdvhcDhcpSourcePortType OBJECT-TYPE
    SYNTAX  INTEGER { inherit(1), random(2), strict(3), unsupported(2147483647) }
    MAX-ACCESS  read-only
    STATUS  current
    DESCRIPTION
        "DHCP Health check source port selection method."
    ::= { slbCurAdvhcDhcpEntry 15 }

slbCurAdvhcDhcpDhcpDuidType OBJECT-TYPE
    SYNTAX  INTEGER { linklayertime(1), linklayer(3), unsupported(2147483647) }
    MAX-ACCESS  read-only
    STATUS  current
    DESCRIPTION
        "DHCP server's DUID Type. Only 1 and 3 are supported."
    ::= { slbCurAdvhcDhcpEntry 16 }

slbCurAdvhcDhcpDhcpDuidLLA OBJECT-TYPE
    SYNTAX  PhysAddress 
    MAX-ACCESS  read-only
    STATUS  current
    DESCRIPTION
        "DHCP server's Link-Layer address."
    ::= { slbCurAdvhcDhcpEntry 17 }

slbCurAdvhcDhcpDhcpDuidTime OBJECT-TYPE
    SYNTAX  Unsigned32 
    MAX-ACCESS  read-only
    STATUS  current
    DESCRIPTION
        "DHCP server's DUID time, e.g. 500058203."
    ::= { slbCurAdvhcDhcpEntry 18 }

slbNewAdvhcDhcpTable  OBJECT-TYPE
    SYNTAX  SEQUENCE OF SlbNewAdvhcDhcpEntry
    MAX-ACCESS  not-accessible
    STATUS  current
    DESCRIPTION
        "Note:This mib is not supported on VX instance of Virtualization."
    ::= { advhcCfg 6 }

slbNewAdvhcDhcpEntry OBJECT-TYPE
    SYNTAX  SlbNewAdvhcDhcpEntry
    MAX-ACCESS  not-accessible
    STATUS  current
    DESCRIPTION
        "."
    INDEX   { slbNewAdvhcDhcpID }
    ::= { slbNewAdvhcDhcpTable 1 }

SlbNewAdvhcDhcpEntry ::= SEQUENCE {
    slbNewAdvhcDhcpID               DisplayString,
    slbNewAdvhcDhcpName             DisplayString,
    slbNewAdvhcDhcpDPort            INTEGER,
    slbNewAdvhcDhcpIPVer            SlbAdvhcIPVer,
    slbNewAdvhcDhcpHostName         DisplayString,
    slbNewAdvhcDhcpTransparent      SlbAdvhcEnaDis,
    slbNewAdvhcDhcpInterval         INTEGER,
    slbNewAdvhcDhcpRetries          INTEGER,
    slbNewAdvhcDhcpRestoreRetries   INTEGER,
    slbNewAdvhcDhcpTimeout          INTEGER,
    slbNewAdvhcDhcpOverflow         INTEGER,
    slbNewAdvhcDhcpDownInterval     INTEGER,
    slbNewAdvhcDhcpInvert           SlbAdvhcEnaDis,
    slbNewAdvhcDhcpDhcpType         INTEGER,
    slbNewAdvhcDhcpSourcePortType   INTEGER,
    slbNewAdvhcDhcpCopy             DisplayString,
    slbNewAdvhcDhcpDelete           SlbAdvhcDelete,
    slbNewAdvhcDhcpDhcpDuidType     INTEGER,
    slbNewAdvhcDhcpDhcpDuidLLA      PhysAddress,
    slbNewAdvhcDhcpDhcpDuidTime     Unsigned32

    }

slbNewAdvhcDhcpID OBJECT-TYPE
    SYNTAX   DisplayString (SIZE (0..128))
    MAX-ACCESS  read-only
    STATUS  current
    DESCRIPTION
        "DHCP Health check id."
    ::= { slbNewAdvhcDhcpEntry 1 }

slbNewAdvhcDhcpName OBJECT-TYPE
    SYNTAX   DisplayString (SIZE (0..128))
    MAX-ACCESS  read-write
    STATUS  current
    DESCRIPTION
        "DHCP Health check name."
    ::= { slbNewAdvhcDhcpEntry 2 }


slbNewAdvhcDhcpDPort OBJECT-TYPE
    SYNTAX  INTEGER (0..65534)
    MAX-ACCESS  read-write
    STATUS  current
    DESCRIPTION
        "DHCP Health check port."
    ::= { slbNewAdvhcDhcpEntry 3 }

slbNewAdvhcDhcpIPVer OBJECT-TYPE
    SYNTAX  SlbAdvhcIPVer
    MAX-ACCESS  read-write
    STATUS  current
    DESCRIPTION
        "DHCP Health check IP version."
    ::= { slbNewAdvhcDhcpEntry 4 }

slbNewAdvhcDhcpHostName OBJECT-TYPE
    SYNTAX   DisplayString (SIZE (0..128))
    MAX-ACCESS  read-write
    STATUS  current
    DESCRIPTION
        "DHCP Health check destination hostname."
    ::= { slbNewAdvhcDhcpEntry 5 }

slbNewAdvhcDhcpTransparent OBJECT-TYPE
    SYNTAX  SlbAdvhcEnaDis
    MAX-ACCESS  read-write
    STATUS  current
    DESCRIPTION
        "DHCP Health check transparent flag."
    ::= { slbNewAdvhcDhcpEntry 6 }

slbNewAdvhcDhcpInterval OBJECT-TYPE
    SYNTAX  INTEGER (1..600)
    MAX-ACCESS  read-write
    STATUS  current
    DESCRIPTION
        "DHCP Health check interval."
    ::= { slbNewAdvhcDhcpEntry 7 }

slbNewAdvhcDhcpRetries OBJECT-TYPE
    SYNTAX  INTEGER (1..63)
    MAX-ACCESS  read-write
    STATUS  current
    DESCRIPTION
        "DHCP Health check retries counter."
    ::= { slbNewAdvhcDhcpEntry 8 }

slbNewAdvhcDhcpRestoreRetries OBJECT-TYPE
    SYNTAX  INTEGER (1..63)
    MAX-ACCESS  read-write
    STATUS  current
    DESCRIPTION
        "DHCP Health check restore from down state counter."
    ::= { slbNewAdvhcDhcpEntry 9 }

slbNewAdvhcDhcpTimeout OBJECT-TYPE
    SYNTAX  INTEGER (1..63)
    MAX-ACCESS  read-write
    STATUS  current
    DESCRIPTION
        "DHCP Health check timeout period."
    ::= { slbNewAdvhcDhcpEntry 10 }

slbNewAdvhcDhcpOverflow OBJECT-TYPE
    SYNTAX  INTEGER (0..600)
    MAX-ACCESS  read-write
    STATUS  current
    DESCRIPTION
        "DHCP Health check overflow flag."
    ::= { slbNewAdvhcDhcpEntry 11 }

slbNewAdvhcDhcpDownInterval OBJECT-TYPE
    SYNTAX  INTEGER (0..600)
    MAX-ACCESS  read-write
    STATUS  current
    DESCRIPTION
        "DHCP Health check interval in down state."
    ::= { slbNewAdvhcDhcpEntry 12 }

slbNewAdvhcDhcpInvert OBJECT-TYPE
    SYNTAX  SlbAdvhcEnaDis
    MAX-ACCESS  read-write
    STATUS  current
    DESCRIPTION
        "DHCP Health check invert flag."
    ::= { slbNewAdvhcDhcpEntry 13 }

slbNewAdvhcDhcpDhcpType OBJECT-TYPE
    SYNTAX  INTEGER { inherit(1), inform(2), request(3), relay(4), unsupported(2147483647) }
    MAX-ACCESS  read-write
    STATUS  current
    DESCRIPTION
        "DHCP Health check packet type."
    ::= { slbNewAdvhcDhcpEntry 14 }

slbNewAdvhcDhcpSourcePortType OBJECT-TYPE
    SYNTAX  INTEGER { inherit(1), random(2), strict(3), unsupported(2147483647) }
    MAX-ACCESS  read-write
    STATUS  current
    DESCRIPTION
        "DHCP Health check source port selection method."
    ::= { slbNewAdvhcDhcpEntry 15 }

slbNewAdvhcDhcpCopy OBJECT-TYPE
    SYNTAX   DisplayString (SIZE (0..128))
    MAX-ACCESS  read-write
    STATUS  current
    DESCRIPTION
        "Copy DHCP Health check."
    ::= { slbNewAdvhcDhcpEntry 16 }

slbNewAdvhcDhcpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcDhcpEntry 17 }

slbNewAdvhcDhcpDhcpDuidType OBJECT-TYPE
    SYNTAX  INTEGER { linklayertime(1), linklayer(3), unsupported(2147483647) }
    MAX-ACCESS  read-write
    STATUS  current
    DESCRIPTION
        "DHCP server's DUID Type. Only 1 and 3 are supported."
    ::= { slbNewAdvhcDhcpEntry 18 }

slbNewAdvhcDhcpDhcpDuidLLA OBJECT-TYPE
    SYNTAX  PhysAddress 
    MAX-ACCESS  read-write
    STATUS  current
    DESCRIPTION
        "DHCP server's Link-Layer address, e.g. e0:69:95:c8:ca:9d or e06995c8ca9d"
    ::= { slbNewAdvhcDhcpEntry 19 }

slbNewAdvhcDhcpDhcpDuidTime OBJECT-TYPE
    SYNTAX  Unsigned32 
    MAX-ACCESS  read-write
    STATUS  current
    DESCRIPTION
        "DHCP server's DUID time, e.g. 500058203."
    ::= { slbNewAdvhcDhcpEntry 20 }

-- Advance Health Check DNS
---------------------------

slbCurAdvhcDnsTable  OBJECT-TYPE
    SYNTAX  SEQUENCE OF SlbCurAdvhcDnsEntry
    MAX-ACCESS  not-accessible
    STATUS  current
    DESCRIPTION
        "Note:This mib is not supported on VX instance of Virtualization."
    ::= { advhcCfg 7 }

slbCurAdvhcDnsEntry OBJECT-TYPE
    SYNTAX  SlbCurAdvhcDnsEntry
    MAX-ACCESS  not-accessible
    STATUS  current
    DESCRIPTION
        "."
    INDEX   { slbCurAdvhcDnsID }
    ::= { slbCurAdvhcDnsTable 1 }

SlbCurAdvhcDnsEntry ::= SEQUENCE {
    slbCurAdvhcDnsID                DisplayString,
    slbCurAdvhcDnsName              DisplayString,
    slbCurAdvhcDnsDPort             INTEGER,
    slbCurAdvhcDnsIPVer             SlbAdvhcIPVer,
    slbCurAdvhcDnsHostName          DisplayString,
    slbCurAdvhcDnsTransparent       SlbAdvhcEnaDis,
    slbCurAdvhcDnsInterval          INTEGER,
    slbCurAdvhcDnsRetries           INTEGER,
    slbCurAdvhcDnsRestoreRetries    INTEGER,
    slbCurAdvhcDnsTimeout           INTEGER,
    slbCurAdvhcDnsOverflow          INTEGER,
    slbCurAdvhcDnsDownInterval      INTEGER,
    slbCurAdvhcDnsInvert            SlbAdvhcEnaDis,
    slbCurAdvhcDnsDomainName        DisplayString,
    slbCurAdvhcDnsTransport         INTEGER
    }

slbCurAdvhcDnsID OBJECT-TYPE
    SYNTAX   DisplayString (SIZE (0..128))
    MAX-ACCESS  read-only
    STATUS  current
    DESCRIPTION
        "DNS Health check id."
    ::= { slbCurAdvhcDnsEntry 1 }

slbCurAdvhcDnsName OBJECT-TYPE
    SYNTAX   DisplayString (SIZE (0..128))
    MAX-ACCESS  read-only
    STATUS  current
    DESCRIPTION
        "DNS Health check name."
    ::= { slbCurAdvhcDnsEntry 2 }

slbCurAdvhcDnsDPort OBJECT-TYPE
    SYNTAX  INTEGER (0..65534)
    MAX-ACCESS  read-only
    STATUS  current
    DESCRIPTION
        "DNS Health check destination port."
    ::= { slbCurAdvhcDnsEntry 3 }

slbCurAdvhcDnsIPVer OBJECT-TYPE
    SYNTAX  SlbAdvhcIPVer
    MAX-ACCESS  read-only
    STATUS  current
    DESCRIPTION
        "DNS Health check IP version."
    ::= { slbCurAdvhcDnsEntry 4 }

slbCurAdvhcDnsHostName OBJECT-TYPE
    SYNTAX   DisplayString (SIZE (0..128))
    MAX-ACCESS  read-only
    STATUS  current
    DESCRIPTION
        "DNS Health check destination host name."
    ::= { slbCurAdvhcDnsEntry 5 }

slbCurAdvhcDnsTransparent OBJECT-TYPE
    SYNTAX  SlbAdvhcEnaDis
    MAX-ACCESS  read-only
    STATUS  current
    DESCRIPTION
        "DNS Health check transparent flag."
    ::= { slbCurAdvhcDnsEntry 6 }

slbCurAdvhcDnsInterval OBJECT-TYPE
    SYNTAX  INTEGER (1..600)
    MAX-ACCESS  read-only
    STATUS  current
    DESCRIPTION
        "DNS Health check interval."
    ::= { slbCurAdvhcDnsEntry 7 }

slbCurAdvhcDnsRetries OBJECT-TYPE
    SYNTAX  INTEGER (1..63)
    MAX-ACCESS  read-only
    STATUS  current
    DESCRIPTION
        "DNS Health check retries counter."
    ::= { slbCurAdvhcDnsEntry 8 }

slbCurAdvhcDnsRestoreRetries OBJECT-TYPE
    SYNTAX  INTEGER (1..63)
    MAX-ACCESS  read-only
    STATUS  current
    DESCRIPTION
        "DNS Health check restore from down state counter."
    ::= { slbCurAdvhcDnsEntry 9 }

slbCurAdvhcDnsTimeout OBJECT-TYPE
    SYNTAX  INTEGER (1..63)
    MAX-ACCESS  read-only
    STATUS  current
    DESCRIPTION
        "DNS Health check timeout."
    ::= { slbCurAdvhcDnsEntry 10 }

slbCurAdvhcDnsOverflow OBJECT-TYPE
    SYNTAX  INTEGER (0..600)
    MAX-ACCESS  read-only
    STATUS  current
    DESCRIPTION
        "DNS Health check overflow flag."
    ::= { slbCurAdvhcDnsEntry 11 }

slbCurAdvhcDnsDownInterval OBJECT-TYPE
    SYNTAX  INTEGER (0..600)
    MAX-ACCESS  read-only
    STATUS  current
    DESCRIPTION
        "DNS Health check recovery from down state interval."
    ::= { slbCurAdvhcDnsEntry 12 }

slbCurAdvhcDnsInvert OBJECT-TYPE
    SYNTAX  SlbAdvhcEnaDis
    MAX-ACCESS  read-only
    STATUS  current
    DESCRIPTION
        "DNS Health check invert flag."
    ::= { slbCurAdvhcDnsEntry 13 }

slbCurAdvhcDnsDomainName OBJECT-TYPE
    SYNTAX   DisplayString (SIZE (0..63))
    MAX-ACCESS  read-only
    STATUS  current
    DESCRIPTION
        "DNS Health check domain name parameter."
    ::= { slbCurAdvhcDnsEntry 14 }

slbCurAdvhcDnsTransport OBJECT-TYPE
    SYNTAX  INTEGER { tcp(1), udp(2), unsupported(2147483647) }
    MAX-ACCESS  read-only
    STATUS  current
    DESCRIPTION
        "DNS Health check transport layer."
    ::= { slbCurAdvhcDnsEntry 15 }


slbNewAdvhcDnsTable  OBJECT-TYPE
    SYNTAX  SEQUENCE OF SlbNewAdvhcDnsEntry
    MAX-ACCESS  not-accessible
    STATUS  current
    DESCRIPTION
        "Note:This mib is not supported on VX instance of Virtualization."
    ::= { advhcCfg 8 }

slbNewAdvhcDnsEntry OBJECT-TYPE
    SYNTAX  SlbNewAdvhcDnsEntry
    MAX-ACCESS  not-accessible
    STATUS  current
    DESCRIPTION
        "."
    INDEX   { slbNewAdvhcDnsID }
    ::= { slbNewAdvhcDnsTable 1 }

SlbNewAdvhcDnsEntry ::= SEQUENCE {
    slbNewAdvhcDnsID                DisplayString,
    slbNewAdvhcDnsName              DisplayString,
    slbNewAdvhcDnsDPort             INTEGER,
    slbNewAdvhcDnsIPVer             SlbAdvhcIPVer,
    slbNewAdvhcDnsHostName          DisplayString,
    slbNewAdvhcDnsTransparent       SlbAdvhcEnaDis,
    slbNewAdvhcDnsInterval          INTEGER,
    slbNewAdvhcDnsRetries           INTEGER,
    slbNewAdvhcDnsRestoreRetries    INTEGER,
    slbNewAdvhcDnsTimeout           INTEGER,
    slbNewAdvhcDnsOverflow          INTEGER,
    slbNewAdvhcDnsDownInterval      INTEGER,
    slbNewAdvhcDnsInvert            SlbAdvhcEnaDis,
    slbNewAdvhcDnsDomainName        DisplayString,
    slbNewAdvhcDnsTransport         INTEGER,
    slbNewAdvhcDnsCopy              DisplayString,
    slbNewAdvhcDnsDelete            SlbAdvhcDelete
    }

slbNewAdvhcDnsID OBJECT-TYPE
    SYNTAX   DisplayString (SIZE (0..128))
    MAX-ACCESS  read-only
    STATUS  current
    DESCRIPTION
        "DNS Health check id."
    ::= { slbNewAdvhcDnsEntry 1 }

slbNewAdvhcDnsName OBJECT-TYPE
    SYNTAX   DisplayString (SIZE (0..128))
    MAX-ACCESS  read-write
    STATUS  current
    DESCRIPTION
        "DNS Health check name."
    ::= { slbNewAdvhcDnsEntry 2 }

slbNewAdvhcDnsDPort OBJECT-TYPE
    SYNTAX  INTEGER (0..65534)
    MAX-ACCESS  read-write
    STATUS  current
    DESCRIPTION
        "DNS Health check destination port."
    ::= { slbNewAdvhcDnsEntry 3 }

slbNewAdvhcDnsIPVer OBJECT-TYPE
    SYNTAX  SlbAdvhcIPVer
    MAX-ACCESS  read-write
    STATUS  current
    DESCRIPTION
        "DNS Health check IP version."
    ::= { slbNewAdvhcDnsEntry 4 }

slbNewAdvhcDnsHostName OBJECT-TYPE
    SYNTAX   DisplayString (SIZE (0..128))
    MAX-ACCESS  read-write
    STATUS  current
    DESCRIPTION
        "DNS Health check destination host name."
    ::= { slbNewAdvhcDnsEntry 5 }

slbNewAdvhcDnsTransparent OBJECT-TYPE
    SYNTAX  SlbAdvhcEnaDis
    MAX-ACCESS  read-write
    STATUS  current
    DESCRIPTION
        "DNS Health check transparent flag."
    ::= { slbNewAdvhcDnsEntry 6 }

slbNewAdvhcDnsInterval OBJECT-TYPE
    SYNTAX  INTEGER (1..600)
    MAX-ACCESS  read-write
    STATUS  current
    DESCRIPTION
        "DNS Health check interval."
    ::= { slbNewAdvhcDnsEntry 7 }

slbNewAdvhcDnsRetries OBJECT-TYPE
    SYNTAX  INTEGER (1..63)
    MAX-ACCESS  read-write
    STATUS  current
    DESCRIPTION
        "DNS Health check retries counter."
    ::= { slbNewAdvhcDnsEntry 8 }

slbNewAdvhcDnsRestoreRetries OBJECT-TYPE
    SYNTAX  INTEGER (1..63)
    MAX-ACCESS  read-write
    STATUS  current
    DESCRIPTION
        "DNS Health check restore from down state counter."
    ::= { slbNewAdvhcDnsEntry 9 }

slbNewAdvhcDnsTimeout OBJECT-TYPE
    SYNTAX  INTEGER (1..63)
    MAX-ACCESS  read-write
    STATUS  current
    DESCRIPTION
        "DNS Health check timeout."
    ::= { slbNewAdvhcDnsEntry 10 }

slbNewAdvhcDnsOverflow OBJECT-TYPE
    SYNTAX  INTEGER (0..600)
    MAX-ACCESS  read-write
    STATUS  current
    DESCRIPTION
        "DNS Health check overflow flag."
    ::= { slbNewAdvhcDnsEntry 11 }

slbNewAdvhcDnsDownInterval OBJECT-TYPE
    SYNTAX  INTEGER (0..600)
    MAX-ACCESS  read-write
    STATUS  current
    DESCRIPTION
        "DNS Health check recovery from down state interval."
    ::= { slbNewAdvhcDnsEntry 12 }

slbNewAdvhcDnsInvert OBJECT-TYPE
    SYNTAX  SlbAdvhcEnaDis
    MAX-ACCESS  read-write
    STATUS  current
    DESCRIPTION
        "DNS Health check invert flag."
    ::= { slbNewAdvhcDnsEntry 13 }

slbNewAdvhcDnsDomainName OBJECT-TYPE
    SYNTAX   DisplayString (SIZE (0..63))
    MAX-ACCESS  read-write
    STATUS  current
    DESCRIPTION
        "DNS Health check domain name parameter."
    ::= { slbNewAdvhcDnsEntry 14 }

slbNewAdvhcDnsTransport OBJECT-TYPE
    SYNTAX  INTEGER { tcp(1), udp(2), unsupported(2147483647) }
    MAX-ACCESS  read-write
    STATUS  current
    DESCRIPTION
        "DNS Health check transport layer."
    ::= { slbNewAdvhcDnsEntry 15 }

slbNewAdvhcDnsCopy OBJECT-TYPE
    SYNTAX   DisplayString (SIZE (0..128))
    MAX-ACCESS  read-write
    STATUS  current
    DESCRIPTION
        "DNS Health check field to copy object."
    ::= { slbNewAdvhcDnsEntry 16 }

slbNewAdvhcDnsDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcDnsEntry 17 }


-- Advance Health Check FTP
---------------------------

slbCurAdvhcFtpTable  OBJECT-TYPE
    SYNTAX  SEQUENCE OF SlbCurAdvhcFtpEntry
    MAX-ACCESS  not-accessible
    STATUS  current
    DESCRIPTION
        "Note:This mib is not supported on VX instance of Virtualization."
    ::= { advhcCfg 9 }

slbCurAdvhcFtpEntry OBJECT-TYPE
    SYNTAX  SlbCurAdvhcFtpEntry
    MAX-ACCESS  not-accessible
    STATUS  current
    DESCRIPTION
        "."
    INDEX   { slbCurAdvhcFtpID }
    ::= { slbCurAdvhcFtpTable 1 }

SlbCurAdvhcFtpEntry ::= SEQUENCE {
    slbCurAdvhcFtpID                DisplayString,
    slbCurAdvhcFtpName              DisplayString,
    slbCurAdvhcFtpDPort             INTEGER,
    slbCurAdvhcFtpIPVer             SlbAdvhcIPVer,
    slbCurAdvhcFtpHostName          DisplayString,
    slbCurAdvhcFtpTransparent       SlbAdvhcEnaDis,
    slbCurAdvhcFtpInterval          INTEGER,
    slbCurAdvhcFtpRetries           INTEGER,
    slbCurAdvhcFtpRestoreRetries    INTEGER,
    slbCurAdvhcFtpTimeout           INTEGER,
    slbCurAdvhcFtpOverflow          INTEGER,
    slbCurAdvhcFtpDownInterval      INTEGER,
    slbCurAdvhcFtpInvert            SlbAdvhcEnaDis,
    slbCurAdvhcFtpUserName          DisplayString,
    slbCurAdvhcFtpPassword          DisplayString,
    slbCurAdvhcFtpPath              DisplayString
    }

slbCurAdvhcFtpID OBJECT-TYPE
    SYNTAX   DisplayString (SIZE (0..128))
    MAX-ACCESS  read-only
    STATUS  current
    DESCRIPTION
        "FTP Health check id."
    ::= { slbCurAdvhcFtpEntry 1 }

slbCurAdvhcFtpName OBJECT-TYPE
    SYNTAX   DisplayString (SIZE (0..128))
    MAX-ACCESS  read-only
    STATUS  current
    DESCRIPTION
        "FTP Health check name."
    ::= { slbCurAdvhcFtpEntry 2 }

slbCurAdvhcFtpDPort OBJECT-TYPE
    SYNTAX  INTEGER (0..65534)
    MAX-ACCESS  read-only
    STATUS  current
    DESCRIPTION
        "FTP Health check destination port."
    ::= { slbCurAdvhcFtpEntry 3 }

slbCurAdvhcFtpIPVer OBJECT-TYPE
    SYNTAX  SlbAdvhcIPVer
    MAX-ACCESS  read-only
    STATUS  current
    DESCRIPTION
        "FTP Health check destination IP version."
    ::= { slbCurAdvhcFtpEntry 4 }

slbCurAdvhcFtpHostName OBJECT-TYPE
    SYNTAX   DisplayString (SIZE (0..128))
    MAX-ACCESS  read-only
    STATUS  current
    DESCRIPTION
        "FTP Health check destination hostname."
    ::= { slbCurAdvhcFtpEntry 5 }

slbCurAdvhcFtpTransparent OBJECT-TYPE
    SYNTAX  SlbAdvhcEnaDis
    MAX-ACCESS  read-only
    STATUS  current
    DESCRIPTION
        "FTP Health check transparent flag."
    ::= { slbCurAdvhcFtpEntry 6 }

slbCurAdvhcFtpInterval OBJECT-TYPE
    SYNTAX  INTEGER (1..600)
    MAX-ACCESS  read-only
    STATUS  current
    DESCRIPTION
        "FTP Health check interval."
    ::= { slbCurAdvhcFtpEntry 7 }

slbCurAdvhcFtpRetries OBJECT-TYPE
    SYNTAX  INTEGER (1..63)
    MAX-ACCESS  read-only
    STATUS  current
    DESCRIPTION
        "FTP Health check retries counter."
    ::= { slbCurAdvhcFtpEntry 8 }

slbCurAdvhcFtpRestoreRetries OBJECT-TYPE
    SYNTAX  INTEGER (1..63)
    MAX-ACCESS  read-only
    STATUS  current
    DESCRIPTION
        "FTP Health check restore from down state counter."
    ::= { slbCurAdvhcFtpEntry 9 }

slbCurAdvhcFtpTimeout OBJECT-TYPE
    SYNTAX  INTEGER (1..63)
    MAX-ACCESS  read-only
    STATUS  current
    DESCRIPTION
        "FTP Health check timeout period."
    ::= { slbCurAdvhcFtpEntry 10 }

slbCurAdvhcFtpOverflow OBJECT-TYPE
    SYNTAX  INTEGER (0..600)
    MAX-ACCESS  read-only
    STATUS  current
    DESCRIPTION
        "FTP Health check overflow flag."
    ::= { slbCurAdvhcFtpEntry 11 }

slbCurAdvhcFtpDownInterval OBJECT-TYPE
    SYNTAX  INTEGER (0..600)
    MAX-ACCESS  read-only
    STATUS  current
    DESCRIPTION
        "FTP Health check interval in down state."
    ::= { slbCurAdvhcFtpEntry 12 }

slbCurAdvhcFtpInvert OBJECT-TYPE
    SYNTAX  SlbAdvhcEnaDis
    MAX-ACCESS  read-only
    STATUS  current
    DESCRIPTION
        "FTP Health check invert flag."
    ::= { slbCurAdvhcFtpEntry 13 }

slbCurAdvhcFtpUserName OBJECT-TYPE
    SYNTAX   DisplayString (SIZE (0..32))
    MAX-ACCESS  read-only
    STATUS  current
    DESCRIPTION
        "FTP Health check connection user name."
    ::= { slbCurAdvhcFtpEntry 14 }

slbCurAdvhcFtpPassword OBJECT-TYPE
    SYNTAX   DisplayString (SIZE (0..32))
    MAX-ACCESS  read-only
    STATUS  current
    DESCRIPTION
        "FTP Health check connection password."
    ::= { slbCurAdvhcFtpEntry 15 }

slbCurAdvhcFtpPath OBJECT-TYPE
    SYNTAX   DisplayString (SIZE (0..32))
    MAX-ACCESS  read-only
    STATUS  current
    DESCRIPTION
        "FTP Health check file path parameter."
    ::= { slbCurAdvhcFtpEntry 16 }


slbNewAdvhcFtpTable  OBJECT-TYPE
    SYNTAX  SEQUENCE OF SlbNewAdvhcFtpEntry
    MAX-ACCESS  not-accessible
    STATUS  current
    DESCRIPTION
        "Note:This mib is not supported on VX instance of Virtualization."
    ::= { advhcCfg 10 }

slbNewAdvhcFtpEntry OBJECT-TYPE
    SYNTAX  SlbNewAdvhcFtpEntry
    MAX-ACCESS  not-accessible
    STATUS  current
    DESCRIPTION
        "."
    INDEX   { slbNewAdvhcFtpID }
    ::= { slbNewAdvhcFtpTable 1 }

SlbNewAdvhcFtpEntry ::= SEQUENCE {
    slbNewAdvhcFtpID                DisplayString,
    slbNewAdvhcFtpName              DisplayString,
    slbNewAdvhcFtpDPort             INTEGER,
    slbNewAdvhcFtpIPVer             SlbAdvhcIPVer,
    slbNewAdvhcFtpHostName          DisplayString,
    slbNewAdvhcFtpTransparent       SlbAdvhcEnaDis,
    slbNewAdvhcFtpInterval          INTEGER,
    slbNewAdvhcFtpRetries           INTEGER,
    slbNewAdvhcFtpRestoreRetries    INTEGER,
    slbNewAdvhcFtpTimeout           INTEGER,
    slbNewAdvhcFtpOverflow          INTEGER,
    slbNewAdvhcFtpDownInterval      INTEGER,
    slbNewAdvhcFtpInvert            SlbAdvhcEnaDis,
    slbNewAdvhcFtpUserName          DisplayString,
    slbNewAdvhcFtpPassword          DisplayString,
    slbNewAdvhcFtpPath              DisplayString,
    slbNewAdvhcFtpCopy              DisplayString,
    slbNewAdvhcFtpDelete            SlbAdvhcDelete
    }

slbNewAdvhcFtpID OBJECT-TYPE
    SYNTAX   DisplayString (SIZE (0..128))
    MAX-ACCESS  read-only
    STATUS  current
    DESCRIPTION
        "FTP Health check id."
    ::= { slbNewAdvhcFtpEntry 1 }

slbNewAdvhcFtpName OBJECT-TYPE
    SYNTAX   DisplayString (SIZE (0..128))
    MAX-ACCESS  read-write
    STATUS  current
    DESCRIPTION
        "FTP Health check name."
    ::= { slbNewAdvhcFtpEntry 2 }

slbNewAdvhcFtpDPort OBJECT-TYPE
    SYNTAX  INTEGER (0..65534)
    MAX-ACCESS  read-write
    STATUS  current
    DESCRIPTION
        "FTP Health check destination port."
    ::= { slbNewAdvhcFtpEntry 3 }

slbNewAdvhcFtpIPVer OBJECT-TYPE
    SYNTAX  SlbAdvhcIPVer
    MAX-ACCESS  read-write
    STATUS  current
    DESCRIPTION
        "FTP Health check destination IP version."
    ::= { slbNewAdvhcFtpEntry 4 }

slbNewAdvhcFtpHostName OBJECT-TYPE
    SYNTAX   DisplayString (SIZE (0..128))
    MAX-ACCESS  read-write
    STATUS  current
    DESCRIPTION
        "FTP Health check destination hostname."
    ::= { slbNewAdvhcFtpEntry 5 }

slbNewAdvhcFtpTransparent OBJECT-TYPE
    SYNTAX  SlbAdvhcEnaDis
    MAX-ACCESS  read-write
    STATUS  current
    DESCRIPTION
        "FTP Health check transparent flag."
    ::= { slbNewAdvhcFtpEntry 6 }

slbNewAdvhcFtpInterval OBJECT-TYPE
    SYNTAX  INTEGER (1..600)
    MAX-ACCESS  read-write
    STATUS  current
    DESCRIPTION
        "FTP Health check interval."
    ::= { slbNewAdvhcFtpEntry 7 }

slbNewAdvhcFtpRetries OBJECT-TYPE
    SYNTAX  INTEGER (1..63)
    MAX-ACCESS  read-write
    STATUS  current
    DESCRIPTION
        "FTP Health check retries counter."
    ::= { slbNewAdvhcFtpEntry 8 }

slbNewAdvhcFtpRestoreRetries OBJECT-TYPE
    SYNTAX  INTEGER (1..63)
    MAX-ACCESS  read-write
    STATUS  current
    DESCRIPTION
        "FTP Health check restore from down state counter."
    ::= { slbNewAdvhcFtpEntry 9 }

slbNewAdvhcFtpTimeout OBJECT-TYPE
    SYNTAX  INTEGER (1..63)
    MAX-ACCESS  read-write
    STATUS  current
    DESCRIPTION
        "FTP Health check timeout period."
    ::= { slbNewAdvhcFtpEntry 10 }

slbNewAdvhcFtpOverflow OBJECT-TYPE
    SYNTAX  INTEGER (0..600)
    MAX-ACCESS  read-write
    STATUS  current
    DESCRIPTION
        "FTP Health check overflow flag."
    ::= { slbNewAdvhcFtpEntry 11 }

slbNewAdvhcFtpDownInterval OBJECT-TYPE
    SYNTAX  INTEGER (0..600)
    MAX-ACCESS  read-write
    STATUS  current
    DESCRIPTION
        "FTP Health check interval in down state."
    ::= { slbNewAdvhcFtpEntry 12 }

slbNewAdvhcFtpInvert OBJECT-TYPE
    SYNTAX  SlbAdvhcEnaDis
    MAX-ACCESS  read-write
    STATUS  current
    DESCRIPTION
        "FTP Health check invert flag."
    ::= { slbNewAdvhcFtpEntry 13 }

slbNewAdvhcFtpUserName OBJECT-TYPE
    SYNTAX   DisplayString (SIZE (0..32))
    MAX-ACCESS  read-write
    STATUS  current
    DESCRIPTION
        "FTP Health check connection user name."
    ::= { slbNewAdvhcFtpEntry 14 }

slbNewAdvhcFtpPassword OBJECT-TYPE
    SYNTAX   DisplayString (SIZE (0..32))
    MAX-ACCESS  read-write
    STATUS  current
    DESCRIPTION
        "FTP Health check connection password."
    ::= { slbNewAdvhcFtpEntry 15 }

slbNewAdvhcFtpPath OBJECT-TYPE
    SYNTAX   DisplayString (SIZE (0..32))
    MAX-ACCESS  read-write
    STATUS  current
    DESCRIPTION
        "FTP Health check file path parameter."
    ::= { slbNewAdvhcFtpEntry 16 }

slbNewAdvhcFtpCopy OBJECT-TYPE
    SYNTAX   DisplayString (SIZE (0..128))
    MAX-ACCESS  read-write
    STATUS  current
    DESCRIPTION
        "FTP Health check copy flag."
    ::= { slbNewAdvhcFtpEntry 17 }

slbNewAdvhcFtpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcFtpEntry 18 }


-- Advance Health Check HTTP
----------------------------

slbCurAdvhcHttpTable  OBJECT-TYPE
    SYNTAX  SEQUENCE OF SlbCurAdvhcHttpEntry
    MAX-ACCESS  not-accessible
    STATUS  current
    DESCRIPTION
        "Note:This mib is not supported on VX instance of Virtualization."
    ::= { advhcCfg 11 }

slbCurAdvhcHttpEntry OBJECT-TYPE
    SYNTAX  SlbCurAdvhcHttpEntry
    MAX-ACCESS  not-accessible
    STATUS  current
    DESCRIPTION
        "."
    INDEX   { slbCurAdvhcHttpID }
    ::= { slbCurAdvhcHttpTable 1 }

SlbCurAdvhcHttpEntry ::= SEQUENCE {
    slbCurAdvhcHttpID                       DisplayString,
    slbCurAdvhcHttpName                     DisplayString,
    slbCurAdvhcHttpDPort                    INTEGER,
    slbCurAdvhcHttpIPVer                    SlbAdvhcIPVer,
    slbCurAdvhcHttpHostName                 DisplayString,
    slbCurAdvhcHttpTransparent              SlbAdvhcEnaDis,
    slbCurAdvhcHttpInterval                 INTEGER,
    slbCurAdvhcHttpRetries                  INTEGER,
    slbCurAdvhcHttpRestoreRetries           INTEGER,
    slbCurAdvhcHttpTimeout                  INTEGER,
    slbCurAdvhcHttpOverflow                 INTEGER,
    slbCurAdvhcHttpDownInterval             INTEGER,
    slbCurAdvhcHttpInvert                   SlbAdvhcEnaDis,
    slbCurAdvhcHttpHttps                    SlbAdvhcEnaDis,
    slbCurAdvhcHttpHost                     DisplayString,
    slbCurAdvhcHttpPath                     RadwareLongDisplayString,
    slbCurAdvhcHttpMethod                   INTEGER,
    slbCurAdvhcHttpHeaders                  RadwareLongDisplayString,
    slbCurAdvhcHttpBody                     RadwareLongDisplayString,
    slbCurAdvhcHttpAuthLevel                INTEGER,
    slbCurAdvhcHttpUserName                 DisplayString,
    slbCurAdvhcHttpPassword                 DisplayString,
    slbCurAdvhcHttpResponseType             INTEGER,
    slbCurAdvhcHttpOverloadType             INTEGER,
    slbCurAdvhcHttpResponseCode             DisplayString,
    slbCurAdvhcHttpReceiveString            RadwareLongDisplayString,
    slbCurAdvhcHttpResponseCodeOverload     DisplayString,
    slbCurAdvhcHttpOverloadString           RadwareLongDisplayString,
    slbCurAdvhcHttpProxy                    SlbAdvhcEnaDis,
    slbCurAdvhcHttpConnTerm                 INTEGER,
    slbCurAdvhcHttpHttpsCipherName          INTEGER,
    slbCurAdvhcHttpHttpsCipherUserdef       RadwareLongDisplayString,
    slbCurAdvhcHttpHttp2                    SlbAdvhcEnaDis,
    slbCurAdvhcHttpAlways                   SlbAdvhcEnaDis
    }

slbCurAdvhcHttpID OBJECT-TYPE
    SYNTAX   DisplayString (SIZE (0..128))
    MAX-ACCESS  read-only
    STATUS  current
    DESCRIPTION
        "HTTP Health check id."
    ::= { slbCurAdvhcHttpEntry 1 }

slbCurAdvhcHttpName OBJECT-TYPE
    SYNTAX   DisplayString (SIZE (0..128))
    MAX-ACCESS  read-only
    STATUS  current
    DESCRIPTION
        "HTTP Health check name."
    ::= { slbCurAdvhcHttpEntry 2 }

slbCurAdvhcHttpDPort OBJECT-TYPE
    SYNTAX  INTEGER (0..65534)
    MAX-ACCESS  read-only
    STATUS  current
    DESCRIPTION
        "HTTP Health check destination port."
    ::= { slbCurAdvhcHttpEntry 3 }

slbCurAdvhcHttpIPVer OBJECT-TYPE
    SYNTAX  SlbAdvhcIPVer
    MAX-ACCESS  read-only
    STATUS  current
    DESCRIPTION
        "HTTP Health check destination IP version."
    ::= { slbCurAdvhcHttpEntry 4 }

slbCurAdvhcHttpHostName OBJECT-TYPE
    SYNTAX   DisplayString (SIZE (0..128))
    MAX-ACCESS  read-only
    STATUS  current
    DESCRIPTION
        "HTTP Health check destination hostname."
    ::= { slbCurAdvhcHttpEntry 5 }

slbCurAdvhcHttpTransparent OBJECT-TYPE
    SYNTAX  SlbAdvhcEnaDis
    MAX-ACCESS  read-only
    STATUS  current
    DESCRIPTION
        "HTTP Health check transparent flag."
    ::= { slbCurAdvhcHttpEntry 6 }

slbCurAdvhcHttpInterval OBJECT-TYPE
    SYNTAX  INTEGER (1..600)
    MAX-ACCESS  read-only
    STATUS  current
    DESCRIPTION
        "HTTP Health check interval."
    ::= { slbCurAdvhcHttpEntry 7 }

slbCurAdvhcHttpRetries OBJECT-TYPE
    SYNTAX  INTEGER (1..63)
    MAX-ACCESS  read-only
    STATUS  current
    DESCRIPTION
        "HTTP Health check retries counter."
    ::= { slbCurAdvhcHttpEntry 8 }

slbCurAdvhcHttpRestoreRetries OBJECT-TYPE
    SYNTAX  INTEGER (1..63)
    MAX-ACCESS  read-only
    STATUS  current
    DESCRIPTION
        "HTTP Health check retries in down state counter."
    ::= { slbCurAdvhcHttpEntry 9 }

slbCurAdvhcHttpTimeout OBJECT-TYPE
    SYNTAX  INTEGER (1..63)
    MAX-ACCESS  read-only
    STATUS  current
    DESCRIPTION
        "HTTP Health check timeout."
    ::= { slbCurAdvhcHttpEntry 10 }

slbCurAdvhcHttpOverflow OBJECT-TYPE
    SYNTAX  INTEGER (0..600)
    MAX-ACCESS  read-only
    STATUS  current
    DESCRIPTION
        "HTTP Health check overflow flag."
    ::= { slbCurAdvhcHttpEntry 11 }

slbCurAdvhcHttpDownInterval OBJECT-TYPE
    SYNTAX  INTEGER (0..600)
    MAX-ACCESS  read-only
    STATUS  current
    DESCRIPTION 
        "HTTP Health check interval in down state."
    ::= { slbCurAdvhcHttpEntry 12 }

slbCurAdvhcHttpInvert OBJECT-TYPE
    SYNTAX  SlbAdvhcEnaDis
    MAX-ACCESS  read-only
    STATUS  current
    DESCRIPTION
        "HTTP Health check invert flag."
    ::= { slbCurAdvhcHttpEntry 13 }

slbCurAdvhcHttpHttps OBJECT-TYPE
    SYNTAX  SlbAdvhcEnaDis
    MAX-ACCESS  read-only
    STATUS  current
    DESCRIPTION
        "HTTP Health check HTTPS enable/disable flag."
    ::= { slbCurAdvhcHttpEntry 14 }

slbCurAdvhcHttpHost OBJECT-TYPE
    SYNTAX   DisplayString (SIZE (0..128))
    MAX-ACCESS  read-only
    STATUS  current
    DESCRIPTION
        "HTTP Health check host field."
    ::= { slbCurAdvhcHttpEntry 15 }

slbCurAdvhcHttpPath OBJECT-TYPE
    SYNTAX   RadwareLongDisplayString (SIZE (0..256))
    MAX-ACCESS  read-only
    STATUS  current
    DESCRIPTION
        "HTTP Health check path field."
    ::= { slbCurAdvhcHttpEntry 16 }
    
slbCurAdvhcHttpMethod OBJECT-TYPE
    SYNTAX  INTEGER { get(1), post(2), head(3), unsupported(2147483647) }
    MAX-ACCESS  read-only
    STATUS  current
    DESCRIPTION
        "HTTP Health check HTTP method."
    ::= { slbCurAdvhcHttpEntry 17 }

slbCurAdvhcHttpHeaders OBJECT-TYPE
    SYNTAX   RadwareLongDisplayString (SIZE (0..1024))
    MAX-ACCESS  read-only
    STATUS  current
    DESCRIPTION
        "HTTP Health check headers list."
    ::= { slbCurAdvhcHttpEntry 18 }

slbCurAdvhcHttpBody OBJECT-TYPE
    SYNTAX   RadwareLongDisplayString (SIZE (0..1024))
    MAX-ACCESS  read-only
    STATUS  current
    DESCRIPTION
        "HTTP Health check body field."
    ::= { slbCurAdvhcHttpEntry 19 }
    
slbCurAdvhcHttpAuthLevel OBJECT-TYPE
    SYNTAX  INTEGER { none(1), basic(2), ntlm2(3), ntlmssp(4), unsupported(2147483647) }
--    SYNTAX  INTEGER { none(1), basic(2), ntlm2(3) }
    MAX-ACCESS  read-only
    STATUS  current
    DESCRIPTION
        "HTTP Health check authentication method."
    ::= { slbCurAdvhcHttpEntry 20 }

slbCurAdvhcHttpUserName OBJECT-TYPE
    SYNTAX   DisplayString (SIZE (0..32))
    MAX-ACCESS  read-only
    STATUS  current
    DESCRIPTION
        "HTTP Health check user name."
    ::= { slbCurAdvhcHttpEntry 21 }

slbCurAdvhcHttpPassword OBJECT-TYPE
    SYNTAX   DisplayString (SIZE (0..32))
    MAX-ACCESS  read-only
    STATUS  current
    DESCRIPTION
        "HTTP Health check password."
    ::= { slbCurAdvhcHttpEntry 22 }

slbCurAdvhcHttpResponseType OBJECT-TYPE
--    SYNTAX  INTEGER { none(1), incl(2), regex(3) }
    SYNTAX  INTEGER { none(1), incl(2), excl(4), unsupported(2147483647) }
    MAX-ACCESS  read-only
    STATUS  current
    DESCRIPTION
        "HTTP Health check response handling method."
    ::= { slbCurAdvhcHttpEntry 23 }
    
slbCurAdvhcHttpOverloadType OBJECT-TYPE
    SYNTAX  INTEGER { none(1), incl(2), unsupported(2147483647) }
    MAX-ACCESS  read-only
    STATUS  current
    DESCRIPTION
        "overload string is included or not included."
    ::= { slbCurAdvhcHttpEntry 24 }
    
slbCurAdvhcHttpResponseCode OBJECT-TYPE
    SYNTAX   DisplayString (SIZE (0..48))
    MAX-ACCESS  read-only
    STATUS  current
    DESCRIPTION
        "HTTP Health check expected response code."
    ::= { slbCurAdvhcHttpEntry 25 }

slbCurAdvhcHttpReceiveString OBJECT-TYPE
    SYNTAX   RadwareLongDisplayString (SIZE (0..256))
    MAX-ACCESS  read-only
    STATUS  current
    DESCRIPTION
        "HTTP Health check expected response string."
    ::= { slbCurAdvhcHttpEntry 26 }

slbCurAdvhcHttpResponseCodeOverload OBJECT-TYPE
    SYNTAX   DisplayString (SIZE (0..48))
    MAX-ACCESS  read-only
    STATUS  current
    DESCRIPTION
        "HTTP Health check expected code for overflow state."
    ::= { slbCurAdvhcHttpEntry 27 }

slbCurAdvhcHttpOverloadString OBJECT-TYPE
    SYNTAX   RadwareLongDisplayString (SIZE (0..256))
    MAX-ACCESS  read-only
    STATUS  current
    DESCRIPTION
        "expected response for server overload."
    ::= { slbCurAdvhcHttpEntry 28 }

slbCurAdvhcHttpProxy OBJECT-TYPE
    SYNTAX  SlbAdvhcEnaDis
    MAX-ACCESS  read-only
    STATUS  current
    DESCRIPTION
        "Enable/disable HTTP health check proxy request."
    ::= { slbCurAdvhcHttpEntry 29 }
    
slbCurAdvhcHttpConnTerm OBJECT-TYPE
    SYNTAX  INTEGER{
        fin(1),
        rst(2),
        unsupported(2147483647)
        }
    MAX-ACCESS  read-only
    STATUS  current
    DESCRIPTION
        "Connection termination type."
    ::= { slbCurAdvhcHttpEntry 30 }    

slbCurAdvhcHttpHttpsCipherName OBJECT-TYPE
    SYNTAX  INTEGER{
        userDefined(1),
        low(2),
        medium(3),
        high(4),
        unsupported(2147483647)
        }
    MAX-ACCESS  read-only
    STATUS  current
    DESCRIPTION
        "Cipher name for SSL for HTTPS HC Context."
    ::= { slbCurAdvhcHttpEntry 31 }

slbCurAdvhcHttpHttpsCipherUserdef OBJECT-TYPE
    SYNTAX RadwareLongDisplayString (SIZE (0..1024))
    MAX-ACCESS  read-only
    STATUS  current
    DESCRIPTION
        "Cipher-suite allowed for SSL for HTTPS HC Context."
    ::= { slbCurAdvhcHttpEntry 32 }

slbCurAdvhcHttpHttp2 OBJECT-TYPE
    SYNTAX  SlbAdvhcEnaDis
    MAX-ACCESS  read-only
    STATUS  current
    DESCRIPTION
        "HTTP Health check enable/disable HTTP2."
    ::= { slbCurAdvhcHttpEntry 33 }
    
slbCurAdvhcHttpAlways OBJECT-TYPE
    SYNTAX  SlbAdvhcEnaDis
    MAX-ACCESS  read-only
    STATUS  current
    DESCRIPTION
        "This flag determines whether HC is allowed for standalone real."
    ::= { slbCurAdvhcHttpEntry 34 }


slbNewAdvhcHttpTable  OBJECT-TYPE
    SYNTAX  SEQUENCE OF SlbNewAdvhcHttpEntry
    MAX-ACCESS  not-accessible
    STATUS  current
    DESCRIPTION
        "Note:This mib is not supported on VX instance of Virtualization."
    ::= { advhcCfg 12 }

slbNewAdvhcHttpEntry OBJECT-TYPE
    SYNTAX  SlbNewAdvhcHttpEntry
    MAX-ACCESS  not-accessible
    STATUS  current
    DESCRIPTION
        "."
    INDEX   { slbNewAdvhcHttpID }
    ::= { slbNewAdvhcHttpTable 1 }

SlbNewAdvhcHttpEntry ::= SEQUENCE {
    slbNewAdvhcHttpID                       DisplayString,
    slbNewAdvhcHttpName                     DisplayString,
    slbNewAdvhcHttpDPort                    INTEGER,
    slbNewAdvhcHttpIPVer                    SlbAdvhcIPVer,
    slbNewAdvhcHttpHostName                 DisplayString,
    slbNewAdvhcHttpTransparent              SlbAdvhcEnaDis,
    slbNewAdvhcHttpInterval                 INTEGER,
    slbNewAdvhcHttpRetries                  INTEGER,
    slbNewAdvhcHttpRestoreRetries           INTEGER,
    slbNewAdvhcHttpTimeout                  INTEGER,
    slbNewAdvhcHttpOverflow                 INTEGER,
    slbNewAdvhcHttpDownInterval             INTEGER,
    slbNewAdvhcHttpInvert                   SlbAdvhcEnaDis,
    slbNewAdvhcHttpHttps                    SlbAdvhcEnaDis,
    slbNewAdvhcHttpHost                     DisplayString,
    slbNewAdvhcHttpPath                     RadwareLongDisplayString,
    slbNewAdvhcHttpMethod                   INTEGER,
    slbNewAdvhcHttpHeaders                  RadwareLongDisplayString,
    slbNewAdvhcHttpBody                     RadwareLongDisplayString,
    slbNewAdvhcHttpAuthLevel                INTEGER,
    slbNewAdvhcHttpUserName                 DisplayString,
    slbNewAdvhcHttpPassword                 DisplayString,
    slbNewAdvhcHttpResponseType             INTEGER,
    slbNewAdvhcHttpOverloadType             INTEGER,
    slbNewAdvhcHttpResponseCode             DisplayString,
    slbNewAdvhcHttpReceiveString            RadwareLongDisplayString,
    slbNewAdvhcHttpResponseCodeOverload     DisplayString,
    slbNewAdvhcHttpOverloadString           RadwareLongDisplayString,
    slbNewAdvhcHttpCopy                     DisplayString,
    slbNewAdvhcHttpDelete                   SlbAdvhcDelete,
    slbNewAdvhcHttpProxy                    SlbAdvhcEnaDis,
    slbNewAdvhcHttpConnTerm                 INTEGER,
    slbNewAdvhcHttpHttpsCipherName          INTEGER,
    slbNewAdvhcHttpHttpsCipherUserdef       RadwareLongDisplayString,
    slbNewAdvhcHttpHttp2                    SlbAdvhcEnaDis,
    slbNewAdvhcHttpAlways                   SlbAdvhcEnaDis
    }

slbNewAdvhcHttpID OBJECT-TYPE
    SYNTAX   DisplayString (SIZE (0..128))
    MAX-ACCESS  read-only
    STATUS  current
    DESCRIPTION
        "HTTP Health check id."
    ::= { slbNewAdvhcHttpEntry 1 }

slbNewAdvhcHttpName OBJECT-TYPE
    SYNTAX   DisplayString (SIZE (0..128))
    MAX-ACCESS  read-write
    STATUS  current
    DESCRIPTION
        "HTTP Health check name."
    ::= { slbNewAdvhcHttpEntry 2 }


slbNewAdvhcHttpDPort OBJECT-TYPE
    SYNTAX  INTEGER (0..65534)
    MAX-ACCESS  read-write
    STATUS  current
    DESCRIPTION
        "HTTP Health check destination port."
    ::= { slbNewAdvhcHttpEntry 3 }

slbNewAdvhcHttpIPVer OBJECT-TYPE
    SYNTAX  SlbAdvhcIPVer
    MAX-ACCESS  read-write
    STATUS  current
    DESCRIPTION
        "HTTP Health check destination IP version."
    ::= { slbNewAdvhcHttpEntry 4 }

slbNewAdvhcHttpHostName OBJECT-TYPE
    SYNTAX   DisplayString (SIZE (0..128))
    MAX-ACCESS  read-write
    STATUS  current
    DESCRIPTION
        "HTTP Health check destination hostname."
    ::= { slbNewAdvhcHttpEntry 5 }

slbNewAdvhcHttpTransparent OBJECT-TYPE
    SYNTAX  SlbAdvhcEnaDis
    MAX-ACCESS  read-write
    STATUS  current
    DESCRIPTION
        "HTTP Health check transparent flag."
    ::= { slbNewAdvhcHttpEntry 6 }

slbNewAdvhcHttpInterval OBJECT-TYPE
    SYNTAX  INTEGER (1..600)
    MAX-ACCESS  read-write
    STATUS  current
    DESCRIPTION
        "HTTP Health check interval."
    ::= { slbNewAdvhcHttpEntry 7 }

slbNewAdvhcHttpRetries OBJECT-TYPE
    SYNTAX  INTEGER (1..63)
    MAX-ACCESS  read-write
    STATUS  current
    DESCRIPTION
        "HTTP Health check retries counter."
    ::= { slbNewAdvhcHttpEntry 8 }

slbNewAdvhcHttpRestoreRetries OBJECT-TYPE
    SYNTAX  INTEGER (1..63)
    MAX-ACCESS  read-write
    STATUS  current
    DESCRIPTION
        "HTTP Health check retries in down state counter."
    ::= { slbNewAdvhcHttpEntry 9 }

slbNewAdvhcHttpTimeout OBJECT-TYPE
    SYNTAX  INTEGER (1..63)
    MAX-ACCESS  read-write
    STATUS  current
    DESCRIPTION
        "HTTP Health check timeout."
    ::= { slbNewAdvhcHttpEntry 10 }

slbNewAdvhcHttpOverflow OBJECT-TYPE
    SYNTAX  INTEGER (0..600)
    MAX-ACCESS  read-write
    STATUS  current
    DESCRIPTION
        "HTTP Health check overflow flag."
    ::= { slbNewAdvhcHttpEntry 11 }

slbNewAdvhcHttpDownInterval OBJECT-TYPE
    SYNTAX  INTEGER (0..600)
    MAX-ACCESS  read-write
    STATUS  current
    DESCRIPTION
        "HTTP Health check interval in down state."
    ::= { slbNewAdvhcHttpEntry 12 }

slbNewAdvhcHttpInvert OBJECT-TYPE
    SYNTAX  SlbAdvhcEnaDis
    MAX-ACCESS  read-write
    STATUS  current
    DESCRIPTION
        "HTTP Health check invert flag."
    ::= { slbNewAdvhcHttpEntry 13 }

slbNewAdvhcHttpHttps OBJECT-TYPE
    SYNTAX  SlbAdvhcEnaDis
    MAX-ACCESS  read-write
    STATUS  current
    DESCRIPTION
        "HTTP Health check HTTPS enable/disable flag."
    ::= { slbNewAdvhcHttpEntry 14 }

slbNewAdvhcHttpHost OBJECT-TYPE
    SYNTAX   DisplayString (SIZE (0..128))
    MAX-ACCESS  read-write
    STATUS  current
    DESCRIPTION
        "HTTP Health check host field."
    ::= { slbNewAdvhcHttpEntry 15 }

slbNewAdvhcHttpPath OBJECT-TYPE
    SYNTAX   RadwareLongDisplayString (SIZE (0..256))
    MAX-ACCESS  read-write
    STATUS  current
    DESCRIPTION
        "HTTP Health check path field."
    ::= { slbNewAdvhcHttpEntry 16 }
    
slbNewAdvhcHttpMethod OBJECT-TYPE
    SYNTAX  INTEGER { get(1), post(2), head(3), unsupported(2147483647) }
    MAX-ACCESS  read-write
    STATUS  current
    DESCRIPTION
        "HTTP Health check HTTP method."
    ::= { slbNewAdvhcHttpEntry 17 }

slbNewAdvhcHttpHeaders OBJECT-TYPE
    SYNTAX   RadwareLongDisplayString (SIZE (0..1024))
    MAX-ACCESS  read-write
    STATUS  current
    DESCRIPTION
        "HTTP Health check headers list."
    ::= { slbNewAdvhcHttpEntry 18 }

slbNewAdvhcHttpBody OBJECT-TYPE
    SYNTAX   RadwareLongDisplayString (SIZE (0..1024))
    MAX-ACCESS  read-write
    STATUS  current
    DESCRIPTION
        "HTTP Health check body field."
    ::= { slbNewAdvhcHttpEntry 19 }
    
slbNewAdvhcHttpAuthLevel OBJECT-TYPE
    SYNTAX  INTEGER { none(1), basic(2), ntlm2(3), ntlmssp(4), unsupported(2147483647) }
--    SYNTAX  INTEGER { none(1), basic(2), ntlm2(3) }
    MAX-ACCESS  read-write
    STATUS  current
    DESCRIPTION
        "HTTP Health check authentication method."
    ::= { slbNewAdvhcHttpEntry 20 }

slbNewAdvhcHttpUserName OBJECT-TYPE
    SYNTAX   DisplayString (SIZE (0..32))
    MAX-ACCESS  read-write
    STATUS  current
    DESCRIPTION
        "HTTP Health check user name."
    ::= { slbNewAdvhcHttpEntry 21 }

slbNewAdvhcHttpPassword OBJECT-TYPE
    SYNTAX   DisplayString (SIZE (0..32))
    MAX-ACCESS  read-write
    STATUS  current
    DESCRIPTION
        "HTTP Health check password."
    ::= { slbNewAdvhcHttpEntry 22 }

slbNewAdvhcHttpResponseType OBJECT-TYPE
--    SYNTAX  INTEGER { none(1), incl(2), regex(3) }
    SYNTAX  INTEGER { none(1), incl(2), excl(4), unsupported(2147483647) }
    MAX-ACCESS  read-write
    STATUS  current
    DESCRIPTION
        "HTTP Health check response handling method."
    ::= { slbNewAdvhcHttpEntry 23 }
    
slbNewAdvhcHttpOverloadType OBJECT-TYPE
    SYNTAX  INTEGER { none(1), incl(2), unsupported(2147483647) }
    MAX-ACCESS  read-write
    STATUS  current
    DESCRIPTION
        "overload string is included or not included."
    ::= { slbNewAdvhcHttpEntry 24 }
    
slbNewAdvhcHttpResponseCode OBJECT-TYPE
    SYNTAX   DisplayString (SIZE (0..48))
    MAX-ACCESS  read-write
    STATUS  current
    DESCRIPTION
        "HTTP Health check expected response code."
    ::= { slbNewAdvhcHttpEntry 25 }

slbNewAdvhcHttpReceiveString OBJECT-TYPE
    SYNTAX   RadwareLongDisplayString (SIZE (0..256))
    MAX-ACCESS  read-write
    STATUS  current
    DESCRIPTION
        "HTTP Health check expected response string."
    ::= { slbNewAdvhcHttpEntry 26 }

slbNewAdvhcHttpResponseCodeOverload OBJECT-TYPE
    SYNTAX   DisplayString (SIZE (0..48))
    MAX-ACCESS  read-write
    STATUS  current
    DESCRIPTION
        "HTTP Health check expected code for overflow state."
    ::= { slbNewAdvhcHttpEntry 27 }

slbNewAdvhcHttpOverloadString OBJECT-TYPE
    SYNTAX   RadwareLongDisplayString (SIZE (0..256))
    MAX-ACCESS  read-write
    STATUS  current
    DESCRIPTION
        "expected response for server overload."
    ::= { slbNewAdvhcHttpEntry 28 }

slbNewAdvhcHttpCopy OBJECT-TYPE
    SYNTAX   DisplayString (SIZE (0..128))
    MAX-ACCESS  read-write
    STATUS  current
    DESCRIPTION
        "HTTP Health check copy action trigger."
    ::= { slbNewAdvhcHttpEntry 29 }

slbNewAdvhcHttpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcHttpEntry 30 }

slbNewAdvhcHttpProxy OBJECT-TYPE
    SYNTAX  SlbAdvhcEnaDis
    MAX-ACCESS  read-write
    STATUS  current
    DESCRIPTION
        "Enable/disable HTTP health check proxy request."
    ::= { slbNewAdvhcHttpEntry 31 }
    
slbNewAdvhcHttpConnTerm OBJECT-TYPE
    SYNTAX  INTEGER{
        fin(1),
        rst(2),
        unsupported(2147483647)
        }
    MAX-ACCESS  read-write
    STATUS  current
    DESCRIPTION
        "Connection termination type."
    ::= { slbNewAdvhcHttpEntry 32 }    

slbNewAdvhcHttpHttpsCipherName OBJECT-TYPE
    SYNTAX  INTEGER{
        userDefined(1),
        low(2),
        medium(3),
        high(4),
        unsupported(2147483647)
        }
    MAX-ACCESS  read-write
    STATUS  current
    DESCRIPTION
        "Cipher name for SSL for HTTPS HC Context."
    ::= { slbNewAdvhcHttpEntry 33 }

slbNewAdvhcHttpHttpsCipherUserdef OBJECT-TYPE
    SYNTAX RadwareLongDisplayString (SIZE (0..1024))
    MAX-ACCESS  read-write
    STATUS  current
    DESCRIPTION
        "Cipher-suite allowed for SSL for HTTPS HC Context."
    ::= { slbNewAdvhcHttpEntry 34 }

slbNewAdvhcHttpHttp2 OBJECT-TYPE
    SYNTAX  SlbAdvhcEnaDis
    MAX-ACCESS  read-write
    STATUS  current
    DESCRIPTION
        "HTTP Health check HTTP2 flag."
    ::= { slbNewAdvhcHttpEntry 35 }
    
slbNewAdvhcHttpAlways OBJECT-TYPE
    SYNTAX  SlbAdvhcEnaDis
    MAX-ACCESS  read-write
    STATUS  current
    DESCRIPTION
        "This flag determines whether HC is allowed for standalone real."
    ::= { slbNewAdvhcHttpEntry 36 }

-- Advance Health Check IMAP
----------------------------

slbCurAdvhcImapTable  OBJECT-TYPE
    SYNTAX  SEQUENCE OF SlbCurAdvhcImapEntry
    MAX-ACCESS  not-accessible
    STATUS  current
    DESCRIPTION
        "Note:This mib is not supported on VX instance of Virtualization."
    ::= { advhcCfg 13 }

slbCurAdvhcImapEntry OBJECT-TYPE
    SYNTAX  SlbCurAdvhcImapEntry
    MAX-ACCESS  not-accessible
    STATUS  current
    DESCRIPTION
        "."
    INDEX   { slbCurAdvhcImapID }
    ::= { slbCurAdvhcImapTable 1 }

SlbCurAdvhcImapEntry ::= SEQUENCE {
    slbCurAdvhcImapID               DisplayString,
    slbCurAdvhcImapName             DisplayString,
    slbCurAdvhcImapDPort            INTEGER,
    slbCurAdvhcImapIPVer            SlbAdvhcIPVer,
    slbCurAdvhcImapHostName         DisplayString,
    slbCurAdvhcImapTransparent      SlbAdvhcEnaDis,
    slbCurAdvhcImapInterval         INTEGER,
    slbCurAdvhcImapRetries          INTEGER,
    slbCurAdvhcImapRestoreRetries   INTEGER,
    slbCurAdvhcImapTimeout          INTEGER,
    slbCurAdvhcImapOverflow         INTEGER,
    slbCurAdvhcImapDownInterval     INTEGER,
    slbCurAdvhcImapInvert           SlbAdvhcEnaDis,
    slbCurAdvhcImapUserName         DisplayString,
    slbCurAdvhcImapPassword         DisplayString
    }

slbCurAdvhcImapID OBJECT-TYPE
    SYNTAX   DisplayString (SIZE (0..128))
    MAX-ACCESS  read-only
    STATUS  current
    DESCRIPTION
        "IMAP Health check id."
    ::= { slbCurAdvhcImapEntry 1 }

slbCurAdvhcImapName OBJECT-TYPE
    SYNTAX   DisplayString (SIZE (0..128))
    MAX-ACCESS  read-only
    STATUS  current
    DESCRIPTION
        "IMAP Health check name."
    ::= { slbCurAdvhcImapEntry 2 }

slbCurAdvhcImapDPort OBJECT-TYPE
    SYNTAX  INTEGER (0..65534)
    MAX-ACCESS  read-only
    STATUS  current
    DESCRIPTION
        "IMAP Health check destination port."
    ::= { slbCurAdvhcImapEntry 3 }

slbCurAdvhcImapIPVer OBJECT-TYPE
    SYNTAX  SlbAdvhcIPVer
    MAX-ACCESS  read-only
    STATUS  current
    DESCRIPTION
        "IMAP Health check destination IP version."
    ::= { slbCurAdvhcImapEntry 4 }

slbCurAdvhcImapHostName OBJECT-TYPE
    SYNTAX   DisplayString (SIZE (0..128))
    MAX-ACCESS  read-only
    STATUS  current
    DESCRIPTION
        "IMAP Health check destination hostname."
    ::= { slbCurAdvhcImapEntry 5 }

slbCurAdvhcImapTransparent OBJECT-TYPE
    SYNTAX  SlbAdvhcEnaDis
    MAX-ACCESS  read-only
    STATUS  current
    DESCRIPTION
        "IMAP Health check transparent flag."
    ::= { slbCurAdvhcImapEntry 6 }

slbCurAdvhcImapInterval OBJECT-TYPE
    SYNTAX  INTEGER (1..600)
    MAX-ACCESS  read-only
    STATUS  current
    DESCRIPTION
        "IMAP Health check interval."
    ::= { slbCurAdvhcImapEntry 7 }

slbCurAdvhcImapRetries OBJECT-TYPE
    SYNTAX  INTEGER (1..63)
    MAX-ACCESS  read-only
    STATUS  current
    DESCRIPTION
        "IMAP Health check retries counter."
    ::= { slbCurAdvhcImapEntry 8 }

slbCurAdvhcImapRestoreRetries OBJECT-TYPE
    SYNTAX  INTEGER (1..63)
    MAX-ACCESS  read-only
    STATUS  current
    DESCRIPTION
        "IMAP Health check retries from the down state counter."
    ::= { slbCurAdvhcImapEntry 9 }

slbCurAdvhcImapTimeout OBJECT-TYPE
    SYNTAX  INTEGER (1..63)
    MAX-ACCESS  read-only
    STATUS  current
    DESCRIPTION
        "IMAP Health check timeout."
    ::= { slbCurAdvhcImapEntry 10 }

slbCurAdvhcImapOverflow OBJECT-TYPE
    SYNTAX  INTEGER (0..600)
    MAX-ACCESS  read-only
    STATUS  current
    DESCRIPTION
        "IMAP Health check overflow flag."
    ::= { slbCurAdvhcImapEntry 11 }

slbCurAdvhcImapDownInterval OBJECT-TYPE
    SYNTAX  INTEGER (0..600)
    MAX-ACCESS  read-only
    STATUS  current
    DESCRIPTION
        "IMAP Health check interval when in the down state."
    ::= { slbCurAdvhcImapEntry 12 }

slbCurAdvhcImapInvert OBJECT-TYPE
    SYNTAX  SlbAdvhcEnaDis
    MAX-ACCESS  read-only
    STATUS  current
    DESCRIPTION
        "IMAP Health check invert flag."
    ::= { slbCurAdvhcImapEntry 13 }

slbCurAdvhcImapUserName OBJECT-TYPE
    SYNTAX   DisplayString (SIZE (0..32))
    MAX-ACCESS  read-only
    STATUS  current
    DESCRIPTION
        "IMAP Health check username."
    ::= { slbCurAdvhcImapEntry 14 }

slbCurAdvhcImapPassword OBJECT-TYPE
    SYNTAX   DisplayString (SIZE (0..32))
    MAX-ACCESS  read-only
    STATUS  current
    DESCRIPTION
        "IMAP Health check password."
    ::= { slbCurAdvhcImapEntry 15 }


slbNewAdvhcImapTable  OBJECT-TYPE
    SYNTAX  SEQUENCE OF SlbNewAdvhcImapEntry
    MAX-ACCESS  not-accessible
    STATUS  current
    DESCRIPTION
        "Note:This mib is not supported on VX instance of Virtualization."
    ::= { advhcCfg 14 }

slbNewAdvhcImapEntry OBJECT-TYPE
    SYNTAX  SlbNewAdvhcImapEntry
    MAX-ACCESS  not-accessible
    STATUS  current
    DESCRIPTION
        "."
    INDEX   { slbNewAdvhcImapID }
    ::= { slbNewAdvhcImapTable 1 }

SlbNewAdvhcImapEntry ::= SEQUENCE {
    slbNewAdvhcImapID               DisplayString,
    slbNewAdvhcImapName             DisplayString,
    slbNewAdvhcImapDPort            INTEGER,
    slbNewAdvhcImapIPVer            SlbAdvhcIPVer,
    slbNewAdvhcImapHostName         DisplayString,
    slbNewAdvhcImapTransparent      SlbAdvhcEnaDis,
    slbNewAdvhcImapInterval         INTEGER,
    slbNewAdvhcImapRetries          INTEGER,
    slbNewAdvhcImapRestoreRetries   INTEGER,
    slbNewAdvhcImapTimeout          INTEGER,
    slbNewAdvhcImapOverflow         INTEGER,
    slbNewAdvhcImapDownInterval     INTEGER,
    slbNewAdvhcImapInvert           SlbAdvhcEnaDis,
    slbNewAdvhcImapUserName         DisplayString,
    slbNewAdvhcImapPassword         DisplayString,
    slbNewAdvhcImapCopy             DisplayString,
    slbNewAdvhcImapDelete           SlbAdvhcDelete
    }

slbNewAdvhcImapID OBJECT-TYPE
    SYNTAX   DisplayString (SIZE (0..128))
    MAX-ACCESS  read-only
    STATUS  current
    DESCRIPTION
        "IMAP Health check id."
    ::= { slbNewAdvhcImapEntry 1 }

slbNewAdvhcImapName OBJECT-TYPE
    SYNTAX   DisplayString (SIZE (0..128))
    MAX-ACCESS  read-write
    STATUS  current
    DESCRIPTION
        "IMAP Health check name."
    ::= { slbNewAdvhcImapEntry 2 }

slbNewAdvhcImapDPort OBJECT-TYPE
    SYNTAX  INTEGER (0..65534)
    MAX-ACCESS  read-write
    STATUS  current
    DESCRIPTION
        "IMAP Health check destination port."
    ::= { slbNewAdvhcImapEntry 3 }

slbNewAdvhcImapIPVer OBJECT-TYPE
    SYNTAX  SlbAdvhcIPVer
    MAX-ACCESS  read-write
    STATUS  current
    DESCRIPTION
        "IMAP Health check destination IP version."
    ::= { slbNewAdvhcImapEntry 4 }

slbNewAdvhcImapHostName OBJECT-TYPE
    SYNTAX   DisplayString (SIZE (0..128))
    MAX-ACCESS  read-write
    STATUS  current
    DESCRIPTION
        "IMAP Health check destination hostname."
    ::= { slbNewAdvhcImapEntry 5 }

slbNewAdvhcImapTransparent OBJECT-TYPE
    SYNTAX  SlbAdvhcEnaDis
    MAX-ACCESS  read-write
    STATUS  current
    DESCRIPTION
        "IMAP Health check transparent flag."
    ::= { slbNewAdvhcImapEntry 6 }

slbNewAdvhcImapInterval OBJECT-TYPE
    SYNTAX  INTEGER (1..600)
    MAX-ACCESS  read-write
    STATUS  current
    DESCRIPTION
        "IMAP Health check interval."
    ::= { slbNewAdvhcImapEntry 7 }

slbNewAdvhcImapRetries OBJECT-TYPE
    SYNTAX  INTEGER (1..63)
    MAX-ACCESS  read-write
    STATUS  current
    DESCRIPTION
        "IMAP Health check retries counter."
    ::= { slbNewAdvhcImapEntry 8 }

slbNewAdvhcImapRestoreRetries OBJECT-TYPE
    SYNTAX  INTEGER (1..63)
    MAX-ACCESS  read-write
    STATUS  current
    DESCRIPTION
        "IMAP Health check retries from the down state counter."
    ::= { slbNewAdvhcImapEntry 9 }

slbNewAdvhcImapTimeout OBJECT-TYPE
    SYNTAX  INTEGER (1..63)
    MAX-ACCESS  read-write
    STATUS  current
    DESCRIPTION
        "IMAP Health check timeout."
    ::= { slbNewAdvhcImapEntry 10 }

slbNewAdvhcImapOverflow OBJECT-TYPE
    SYNTAX  INTEGER (0..600)
    MAX-ACCESS  read-write
    STATUS  current
    DESCRIPTION
        "IMAP Health check overflow flag."
    ::= { slbNewAdvhcImapEntry 11 }

slbNewAdvhcImapDownInterval OBJECT-TYPE
    SYNTAX  INTEGER (0..600)
    MAX-ACCESS  read-write
    STATUS  current
    DESCRIPTION
        "IMAP Health check interval when in the down state."
    ::= { slbNewAdvhcImapEntry 12 }

slbNewAdvhcImapInvert OBJECT-TYPE
    SYNTAX  SlbAdvhcEnaDis
    MAX-ACCESS  read-write
    STATUS  current
    DESCRIPTION
        "IMAP Health check invert flag."
    ::= { slbNewAdvhcImapEntry 13 }

slbNewAdvhcImapUserName OBJECT-TYPE
    SYNTAX   DisplayString (SIZE (0..32))
    MAX-ACCESS  read-write
    STATUS  current
    DESCRIPTION
        "IMAP Health check username."
    ::= { slbNewAdvhcImapEntry 14 }

slbNewAdvhcImapPassword OBJECT-TYPE
    SYNTAX   DisplayString (SIZE (0..32))
    MAX-ACCESS  read-write
    STATUS  current
    DESCRIPTION
        "IMAP Health check password."
    ::= { slbNewAdvhcImapEntry 15 }

slbNewAdvhcImapCopy OBJECT-TYPE
    SYNTAX   DisplayString (SIZE (0..128))
    MAX-ACCESS  read-write
    STATUS  current
    DESCRIPTION
        "IMAP Health check copy flag."
    ::= { slbNewAdvhcImapEntry 16 }

slbNewAdvhcImapDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcImapEntry 17 }


-- Advance Health Check LDAP
----------------------------

slbCurAdvhcLdapTable  OBJECT-TYPE
    SYNTAX  SEQUENCE OF SlbCurAdvhcLdapEntry
    MAX-ACCESS  not-accessible
    STATUS  current
    DESCRIPTION
        "Note:This mib is not supported on VX instance of Virtualization."
    ::= { advhcCfg 15 }

slbCurAdvhcLdapEntry OBJECT-TYPE
    SYNTAX  SlbCurAdvhcLdapEntry
    MAX-ACCESS  not-accessible
    STATUS  current
    DESCRIPTION
        "."
    INDEX   { slbCurAdvhcLdapID }
    ::= { slbCurAdvhcLdapTable 1 }

SlbCurAdvhcLdapEntry ::= SEQUENCE {
    slbCurAdvhcLdapID               DisplayString,
    slbCurAdvhcLdapName             DisplayString,
    slbCurAdvhcLdapDPort            INTEGER,
    slbCurAdvhcLdapIPVer            SlbAdvhcIPVer,
    slbCurAdvhcLdapHostName         DisplayString,
    slbCurAdvhcLdapTransparent      SlbAdvhcEnaDis,
    slbCurAdvhcLdapInterval         INTEGER,
    slbCurAdvhcLdapRetries          INTEGER,
    slbCurAdvhcLdapRestoreRetries   INTEGER,
    slbCurAdvhcLdapTimeout          INTEGER,
    slbCurAdvhcLdapOverflow         INTEGER,
    slbCurAdvhcLdapDownInterval     INTEGER,
    slbCurAdvhcLdapInvert           SlbAdvhcEnaDis,
    slbCurAdvhcLdapLdaps            SlbAdvhcEnaDis,
    slbCurAdvhcLdapUserName         DisplayString,
    slbCurAdvhcLdapPassword         DisplayString,
    slbCurAdvhcLdapBaseObject       DisplayString,
    slbCurAdvhcLdapBaseFmt          INTEGER  
    }

slbCurAdvhcLdapID OBJECT-TYPE
    SYNTAX   DisplayString (SIZE (0..128))
    MAX-ACCESS  read-only
    STATUS  current
    DESCRIPTION
        "LDAP Health check id."
    ::= { slbCurAdvhcLdapEntry 1 }

slbCurAdvhcLdapName OBJECT-TYPE
    SYNTAX   DisplayString (SIZE (0..128))
    MAX-ACCESS  read-only
    STATUS  current
    DESCRIPTION
        "LDAP Health check name."
    ::= { slbCurAdvhcLdapEntry 2 }

slbCurAdvhcLdapDPort OBJECT-TYPE
    SYNTAX  INTEGER (0..65534)
    MAX-ACCESS  read-only
    STATUS  current
    DESCRIPTION
        "LDAP Health check destination port."
    ::= { slbCurAdvhcLdapEntry 3 }

slbCurAdvhcLdapIPVer OBJECT-TYPE
    SYNTAX  SlbAdvhcIPVer
    MAX-ACCESS  read-only
    STATUS  current
    DESCRIPTION
        "LDAP Health check destination IP version."
    ::= { slbCurAdvhcLdapEntry 4 }

slbCurAdvhcLdapHostName OBJECT-TYPE
    SYNTAX   DisplayString (SIZE (0..128))
    MAX-ACCESS  read-only
    STATUS  current
    DESCRIPTION
        "LDAP Health check destination hostname."
    ::= { slbCurAdvhcLdapEntry 5 }

slbCurAdvhcLdapTransparent OBJECT-TYPE
    SYNTAX  SlbAdvhcEnaDis
    MAX-ACCESS  read-only
    STATUS  current
    DESCRIPTION
        "LDAP Health check transparent flag."
    ::= { slbCurAdvhcLdapEntry 6 }

slbCurAdvhcLdapInterval OBJECT-TYPE
    SYNTAX  INTEGER (1..600)
    MAX-ACCESS  read-only
    STATUS  current
    DESCRIPTION
        "LDAP Health check interval."
    ::= { slbCurAdvhcLdapEntry 7 }

slbCurAdvhcLdapRetries OBJECT-TYPE
    SYNTAX  INTEGER (1..63)
    MAX-ACCESS  read-only
    STATUS  current
    DESCRIPTION
        "LDAP Health check retries counter."
    ::= { slbCurAdvhcLdapEntry 8 }

slbCurAdvhcLdapRestoreRetries OBJECT-TYPE
    SYNTAX  INTEGER (1..63)
    MAX-ACCESS  read-only
    STATUS  current
    DESCRIPTION
        "LDAP Health check restore from down state counter."
    ::= { slbCurAdvhcLdapEntry 9 }

slbCurAdvhcLdapTimeout OBJECT-TYPE
    SYNTAX  INTEGER (1..63)
    MAX-ACCESS  read-only
    STATUS  current
    DESCRIPTION
        "LDAP Health check timeout."
    ::= { slbCurAdvhcLdapEntry 10 }

slbCurAdvhcLdapOverflow OBJECT-TYPE
    SYNTAX  INTEGER (0..600)
    MAX-ACCESS  read-only
    STATUS  current
    DESCRIPTION
        "LDAP Health check overflow flag."
    ::= { slbCurAdvhcLdapEntry 11 }

slbCurAdvhcLdapDownInterval OBJECT-TYPE
    SYNTAX  INTEGER (0..600)
    MAX-ACCESS  read-only
    STATUS  current
    DESCRIPTION
        "LDAP Health check interval in down state."
    ::= { slbCurAdvhcLdapEntry 12 }

slbCurAdvhcLdapInvert OBJECT-TYPE
    SYNTAX  SlbAdvhcEnaDis
    MAX-ACCESS  read-only
    STATUS  current
    DESCRIPTION
        "LDAP Health check invert flag."
    ::= { slbCurAdvhcLdapEntry 13 }

slbCurAdvhcLdapLdaps OBJECT-TYPE
    SYNTAX  SlbAdvhcEnaDis
    MAX-ACCESS  read-only
    STATUS  current
    DESCRIPTION
        "LDAP Health check e/d secure protocol."
    ::= { slbCurAdvhcLdapEntry 14 }

slbCurAdvhcLdapUserName OBJECT-TYPE
    SYNTAX   DisplayString (SIZE (0..32))
    MAX-ACCESS  read-only
    STATUS  current
    DESCRIPTION
        "LDAP Health check user name."
    ::= { slbCurAdvhcLdapEntry 15 }

slbCurAdvhcLdapPassword OBJECT-TYPE
    SYNTAX   DisplayString (SIZE (0..32))
    MAX-ACCESS  read-only
    STATUS  current
    DESCRIPTION
        "LDAP Health check password."
    ::= { slbCurAdvhcLdapEntry 16 }

slbCurAdvhcLdapBaseObject OBJECT-TYPE
    SYNTAX   DisplayString (SIZE (0..255))
    MAX-ACCESS  read-only
    STATUS  current
    DESCRIPTION
        "LDAP Health check base distinguish name."
    ::= { slbCurAdvhcLdapEntry 17 }

slbCurAdvhcLdapBaseFmt OBJECT-TYPE
    SYNTAX  INTEGER {
        fqdn(0),
        ldap(1),
        unsupported(2147483647)
        }
    MAX-ACCESS  read-only
    STATUS  current
    DESCRIPTION
        "LDAP base DN format."
    ::= { slbCurAdvhcLdapEntry 18 }

slbNewAdvhcLdapTable  OBJECT-TYPE
    SYNTAX  SEQUENCE OF SlbNewAdvhcLdapEntry
    MAX-ACCESS  not-accessible
    STATUS  current
    DESCRIPTION
        "Note:This mib is not supported on VX instance of Virtualization."
    ::= { advhcCfg 16 }

slbNewAdvhcLdapEntry OBJECT-TYPE
    SYNTAX  SlbNewAdvhcLdapEntry
    MAX-ACCESS  not-accessible
    STATUS  current
    DESCRIPTION
        "."
    INDEX   { slbNewAdvhcLdapID }
    ::= { slbNewAdvhcLdapTable 1 }

SlbNewAdvhcLdapEntry ::= SEQUENCE {
    slbNewAdvhcLdapID               DisplayString,
    slbNewAdvhcLdapName             DisplayString,
    slbNewAdvhcLdapDPort            INTEGER,
    slbNewAdvhcLdapIPVer            SlbAdvhcIPVer,
    slbNewAdvhcLdapHostName         DisplayString,
    slbNewAdvhcLdapTransparent      SlbAdvhcEnaDis,
    slbNewAdvhcLdapInterval         INTEGER,
    slbNewAdvhcLdapRetries          INTEGER,
    slbNewAdvhcLdapRestoreRetries   INTEGER,
    slbNewAdvhcLdapTimeout          INTEGER,
    slbNewAdvhcLdapOverflow         INTEGER,
    slbNewAdvhcLdapDownInterval     INTEGER,
    slbNewAdvhcLdapInvert           SlbAdvhcEnaDis,
    slbNewAdvhcLdapLdaps            SlbAdvhcEnaDis,
    slbNewAdvhcLdapUserName         DisplayString,
    slbNewAdvhcLdapPassword         DisplayString,
    slbNewAdvhcLdapBaseObject       DisplayString,
    slbNewAdvhcLdapCopy             DisplayString,
    slbNewAdvhcLdapDelete           SlbAdvhcDelete,
    slbNewAdvhcLdapBaseFmt          INTEGER
    }

slbNewAdvhcLdapID OBJECT-TYPE
    SYNTAX   DisplayString (SIZE (0..128))
    MAX-ACCESS  read-only
    STATUS  current
    DESCRIPTION
        "LDAP Health check id."
    ::= { slbNewAdvhcLdapEntry 1 }

slbNewAdvhcLdapName OBJECT-TYPE
    SYNTAX   DisplayString (SIZE (0..128))
    MAX-ACCESS  read-write
    STATUS  current
    DESCRIPTION
        "LDAP Health check name."
    ::= { slbNewAdvhcLdapEntry 2 }

slbNewAdvhcLdapDPort OBJECT-TYPE
    SYNTAX  INTEGER (0..65534)
    MAX-ACCESS  read-write
    STATUS  current
    DESCRIPTION
        "LDAP Health check destination port."
    ::= { slbNewAdvhcLdapEntry 3 }

slbNewAdvhcLdapIPVer OBJECT-TYPE
    SYNTAX  SlbAdvhcIPVer
    MAX-ACCESS  read-write
    STATUS  current
    DESCRIPTION
        "LDAP Health check destination IP version."
    ::= { slbNewAdvhcLdapEntry 4 }

slbNewAdvhcLdapHostName OBJECT-TYPE
    SYNTAX   DisplayString (SIZE (0..128))
    MAX-ACCESS  read-write
    STATUS  current
    DESCRIPTION
        "LDAP Health check destination hostname."
    ::= { slbNewAdvhcLdapEntry 5 }

slbNewAdvhcLdapTransparent OBJECT-TYPE
    SYNTAX  SlbAdvhcEnaDis
    MAX-ACCESS  read-write
    STATUS  current
    DESCRIPTION
        "LDAP Health check transparent flag."
    ::= { slbNewAdvhcLdapEntry 6 }

slbNewAdvhcLdapInterval OBJECT-TYPE
    SYNTAX  INTEGER (1..600)
    MAX-ACCESS  read-write
    STATUS  current
    DESCRIPTION
        "LDAP Health check interval."
    ::= { slbNewAdvhcLdapEntry 7 }

slbNewAdvhcLdapRetries OBJECT-TYPE
    SYNTAX  INTEGER (1..63)
    MAX-ACCESS  read-write
    STATUS  current
    DESCRIPTION
        "LDAP Health check retries counter."
    ::= { slbNewAdvhcLdapEntry 8 }

slbNewAdvhcLdapRestoreRetries OBJECT-TYPE
    SYNTAX  INTEGER (1..63)
    MAX-ACCESS  read-write
    STATUS  current
    DESCRIPTION
        "LDAP Health check restore from down state counter."
    ::= { slbNewAdvhcLdapEntry 9 }

slbNewAdvhcLdapTimeout OBJECT-TYPE
    SYNTAX  INTEGER (1..63)
    MAX-ACCESS  read-write
    STATUS  current
    DESCRIPTION
        "LDAP Health check timeout."
    ::= { slbNewAdvhcLdapEntry 10 }

slbNewAdvhcLdapOverflow OBJECT-TYPE
    SYNTAX  INTEGER (0..600)
    MAX-ACCESS  read-write
    STATUS  current
    DESCRIPTION
        "LDAP Health check overflow flag."
    ::= { slbNewAdvhcLdapEntry 11 }

slbNewAdvhcLdapDownInterval OBJECT-TYPE
    SYNTAX  INTEGER (0..600)
    MAX-ACCESS  read-write
    STATUS  current
    DESCRIPTION
        "LDAP Health check interval in down state."
    ::= { slbNewAdvhcLdapEntry 12 }

slbNewAdvhcLdapInvert OBJECT-TYPE
    SYNTAX  SlbAdvhcEnaDis
    MAX-ACCESS  read-write
    STATUS  current
    DESCRIPTION
        "LDAP Health check invert flag."
    ::= { slbNewAdvhcLdapEntry 13 }

slbNewAdvhcLdapLdaps OBJECT-TYPE
    SYNTAX  SlbAdvhcEnaDis
    MAX-ACCESS  read-write
    STATUS  current
    DESCRIPTION
        "LDAP Health check e/d secure protocol."
    ::= { slbNewAdvhcLdapEntry 14 }

slbNewAdvhcLdapUserName OBJECT-TYPE
    SYNTAX   DisplayString (SIZE (0..32))
    MAX-ACCESS  read-write
    STATUS  current
    DESCRIPTION
        "LDAP Health check user name."
    ::= { slbNewAdvhcLdapEntry 15 }

slbNewAdvhcLdapPassword OBJECT-TYPE
    SYNTAX   DisplayString (SIZE (0..32))
    MAX-ACCESS  read-write
    STATUS  current
    DESCRIPTION
        "LDAP Health check password."
    ::= { slbNewAdvhcLdapEntry 16 }

slbNewAdvhcLdapBaseObject OBJECT-TYPE
    SYNTAX   DisplayString (SIZE (0..255))
    MAX-ACCESS  read-write
    STATUS  current
    DESCRIPTION
        "LDAP Health check base distinguish name."
    ::= { slbNewAdvhcLdapEntry 17 }

slbNewAdvhcLdapCopy OBJECT-TYPE
    SYNTAX   DisplayString (SIZE (0..128))
    MAX-ACCESS  read-write
    STATUS  current
    DESCRIPTION
        "LDAP Health check base distinguish name copy flag."
    ::= { slbNewAdvhcLdapEntry 18 }

slbNewAdvhcLdapDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcLdapEntry 19 }

slbNewAdvhcLdapBaseFmt OBJECT-TYPE
    SYNTAX  INTEGER {
        fqdn(0),
        ldap(1),
        unsupported(2147483647)
        }
    MAX-ACCESS  read-write
    STATUS  current
    DESCRIPTION
        "LDAP base DN format."
    ::= { slbNewAdvhcLdapEntry 20 }

-- Advance Health Check NNTP
----------------------------

slbCurAdvhcNntpTable  OBJECT-TYPE
    SYNTAX  SEQUENCE OF SlbCurAdvhcNntpEntry
    MAX-ACCESS  not-accessible
    STATUS  current
    DESCRIPTION
        "Note:This mib is not supported on VX instance of Virtualization."
    ::= { advhcCfg 17 }

slbCurAdvhcNntpEntry OBJECT-TYPE
    SYNTAX  SlbCurAdvhcNntpEntry
    MAX-ACCESS  not-accessible
    STATUS  current
    DESCRIPTION
        "."
    INDEX   { slbCurAdvhcNntpID }
    ::= { slbCurAdvhcNntpTable 1 }

SlbCurAdvhcNntpEntry ::= SEQUENCE {
    slbCurAdvhcNntpID               DisplayString,
    slbCurAdvhcNntpName             DisplayString,
    slbCurAdvhcNntpDPort            INTEGER,
    slbCurAdvhcNntpIPVer            SlbAdvhcIPVer,
    slbCurAdvhcNntpHostName         DisplayString,
    slbCurAdvhcNntpTransparent      SlbAdvhcEnaDis,
    slbCurAdvhcNntpInterval         INTEGER,
    slbCurAdvhcNntpRetries          INTEGER,
    slbCurAdvhcNntpRestoreRetries   INTEGER,
    slbCurAdvhcNntpTimeout          INTEGER,
    slbCurAdvhcNntpOverflow         INTEGER,
    slbCurAdvhcNntpDownInterval     INTEGER,
    slbCurAdvhcNntpInvert           SlbAdvhcEnaDis,
    slbCurAdvhcNntpNewsgroupName    DisplayString
    }

slbCurAdvhcNntpID OBJECT-TYPE
    SYNTAX   DisplayString (SIZE (0..128))
    MAX-ACCESS  read-only
    STATUS  current
    DESCRIPTION
        "NNTP Health check id."
    ::= { slbCurAdvhcNntpEntry 1 }

slbCurAdvhcNntpName OBJECT-TYPE
    SYNTAX   DisplayString (SIZE (0..128))
    MAX-ACCESS  read-only
    STATUS  current
    DESCRIPTION
        "NNTP Health check name."
    ::= { slbCurAdvhcNntpEntry 2 }

slbCurAdvhcNntpDPort OBJECT-TYPE
    SYNTAX  INTEGER (0..65534)
    MAX-ACCESS  read-only
    STATUS  current
    DESCRIPTION
        "NNTP Health check destination port."
    ::= { slbCurAdvhcNntpEntry 3 }

slbCurAdvhcNntpIPVer OBJECT-TYPE
    SYNTAX  SlbAdvhcIPVer
    MAX-ACCESS  read-only
    STATUS  current
    DESCRIPTION
        "NNTP Health check destination IP version."
    ::= { slbCurAdvhcNntpEntry 4 }

slbCurAdvhcNntpHostName OBJECT-TYPE
    SYNTAX   DisplayString (SIZE (0..128))
    MAX-ACCESS  read-only
    STATUS  current
    DESCRIPTION
        "NNTP Health check destination hostname."
    ::= { slbCurAdvhcNntpEntry 5 }

slbCurAdvhcNntpTransparent OBJECT-TYPE
    SYNTAX  SlbAdvhcEnaDis
    MAX-ACCESS  read-only
    STATUS  current
    DESCRIPTION
        "NNTP Health check transparent flag."
    ::= { slbCurAdvhcNntpEntry 6 }

slbCurAdvhcNntpInterval OBJECT-TYPE
    SYNTAX  INTEGER (1..600)
    MAX-ACCESS  read-only
    STATUS  current
    DESCRIPTION
        "NNTP Health check interval."
    ::= { slbCurAdvhcNntpEntry 7 }

slbCurAdvhcNntpRetries OBJECT-TYPE
    SYNTAX  INTEGER (1..63)
    MAX-ACCESS  read-only
    STATUS  current
    DESCRIPTION
        "NNTP Health check retries counter."
    ::= { slbCurAdvhcNntpEntry 8 }

slbCurAdvhcNntpRestoreRetries OBJECT-TYPE
    SYNTAX  INTEGER (1..63)
    MAX-ACCESS  read-only
    STATUS  current
    DESCRIPTION
        "NNTP Health check restore from down state retries counter."
    ::= { slbCurAdvhcNntpEntry 9 }

slbCurAdvhcNntpTimeout OBJECT-TYPE
    SYNTAX  INTEGER (1..63)
    MAX-ACCESS  read-only
    STATUS  current
    DESCRIPTION
        "NNTP Health check timeout."
    ::= { slbCurAdvhcNntpEntry 10 }

slbCurAdvhcNntpOverflow OBJECT-TYPE
    SYNTAX  INTEGER (0..600)
    MAX-ACCESS  read-only
    STATUS  current
    DESCRIPTION
        "NNTP Health check overflow flag."
    ::= { slbCurAdvhcNntpEntry 11 }

slbCurAdvhcNntpDownInterval OBJECT-TYPE
    SYNTAX  INTEGER (0..600)
    MAX-ACCESS  read-only
    STATUS  current
    DESCRIPTION
        "NNTP Health check interval when in down state."
    ::= { slbCurAdvhcNntpEntry 12 }

slbCurAdvhcNntpInvert OBJECT-TYPE
    SYNTAX  SlbAdvhcEnaDis
    MAX-ACCESS  read-only
    STATUS  current
    DESCRIPTION
        "NNTP Health check invert flag."
    ::= { slbCurAdvhcNntpEntry 13 }

slbCurAdvhcNntpNewsgroupName OBJECT-TYPE
    SYNTAX   DisplayString (SIZE (0..128))
    MAX-ACCESS  read-only
    STATUS  current
    DESCRIPTION
        "NNTP Health check newsgroup name."
    ::= { slbCurAdvhcNntpEntry 14 }


slbNewAdvhcNntpTable  OBJECT-TYPE
    SYNTAX  SEQUENCE OF SlbNewAdvhcNntpEntry
    MAX-ACCESS  not-accessible
    STATUS  current
    DESCRIPTION
        "Note:This mib is not supported on VX instance of Virtualization."
    ::= { advhcCfg 18 }

slbNewAdvhcNntpEntry OBJECT-TYPE
    SYNTAX  SlbNewAdvhcNntpEntry
    MAX-ACCESS  not-accessible
    STATUS  current
    DESCRIPTION
        "."
    INDEX   { slbNewAdvhcNntpID }
    ::= { slbNewAdvhcNntpTable 1 }

SlbNewAdvhcNntpEntry ::= SEQUENCE {
    slbNewAdvhcNntpID               DisplayString,
    slbNewAdvhcNntpName             DisplayString,
    slbNewAdvhcNntpDPort            INTEGER,
    slbNewAdvhcNntpIPVer            SlbAdvhcIPVer,
    slbNewAdvhcNntpHostName         DisplayString,
    slbNewAdvhcNntpTransparent      SlbAdvhcEnaDis,
    slbNewAdvhcNntpInterval         INTEGER,
    slbNewAdvhcNntpRetries          INTEGER,
    slbNewAdvhcNntpRestoreRetries   INTEGER,
    slbNewAdvhcNntpTimeout          INTEGER,
    slbNewAdvhcNntpOverflow         INTEGER,
    slbNewAdvhcNntpDownInterval     INTEGER,
    slbNewAdvhcNntpInvert           SlbAdvhcEnaDis,
    slbNewAdvhcNntpNewsgroupName    DisplayString,
    slbNewAdvhcNntpCopy             DisplayString,
    slbNewAdvhcNntpDelete           SlbAdvhcDelete
    }

slbNewAdvhcNntpID OBJECT-TYPE
    SYNTAX   DisplayString (SIZE (0..128))
    MAX-ACCESS  read-only
    STATUS  current
    DESCRIPTION
        "NNTP Health check id."
    ::= { slbNewAdvhcNntpEntry 1 }

slbNewAdvhcNntpName OBJECT-TYPE
    SYNTAX   DisplayString (SIZE (0..128))
    MAX-ACCESS  read-write
    STATUS  current
    DESCRIPTION
        "NNTP Health check name."
    ::= { slbNewAdvhcNntpEntry 2 }

slbNewAdvhcNntpDPort OBJECT-TYPE
    SYNTAX  INTEGER (0..65534)
    MAX-ACCESS  read-write
    STATUS  current
    DESCRIPTION
        "NNTP Health check destination port."
    ::= { slbNewAdvhcNntpEntry 3 }

slbNewAdvhcNntpIPVer OBJECT-TYPE
    SYNTAX  SlbAdvhcIPVer
    MAX-ACCESS  read-write
    STATUS  current
    DESCRIPTION
        "NNTP Health check destination IP version."
    ::= { slbNewAdvhcNntpEntry 4 }

slbNewAdvhcNntpHostName OBJECT-TYPE
    SYNTAX   DisplayString (SIZE (0..128))
    MAX-ACCESS  read-write
    STATUS  current
    DESCRIPTION
        "NNTP Health check destination hostname."
    ::= { slbNewAdvhcNntpEntry 5 }

slbNewAdvhcNntpTransparent OBJECT-TYPE
    SYNTAX  SlbAdvhcEnaDis
    MAX-ACCESS  read-write
    STATUS  current
    DESCRIPTION
        "NNTP Health check transparent flag."
    ::= { slbNewAdvhcNntpEntry 6 }

slbNewAdvhcNntpInterval OBJECT-TYPE
    SYNTAX  INTEGER (1..600)
    MAX-ACCESS  read-write
    STATUS  current
    DESCRIPTION
        "NNTP Health check interval."
    ::= { slbNewAdvhcNntpEntry 7 }

slbNewAdvhcNntpRetries OBJECT-TYPE
    SYNTAX  INTEGER (1..63)
    MAX-ACCESS  read-write
    STATUS  current
    DESCRIPTION
        "NNTP Health check retries counter."
    ::= { slbNewAdvhcNntpEntry 8 }

slbNewAdvhcNntpRestoreRetries OBJECT-TYPE
    SYNTAX  INTEGER (1..63)
    MAX-ACCESS  read-write
    STATUS  current
    DESCRIPTION
        "NNTP Health check restore from down state retries counter."
    ::= { slbNewAdvhcNntpEntry 9 }

slbNewAdvhcNntpTimeout OBJECT-TYPE
    SYNTAX  INTEGER (1..63)
    MAX-ACCESS  read-write
    STATUS  current
    DESCRIPTION
        "NNTP Health check timeout."
    ::= { slbNewAdvhcNntpEntry 10 }

slbNewAdvhcNntpOverflow OBJECT-TYPE
    SYNTAX  INTEGER (0..600)
    MAX-ACCESS  read-write
    STATUS  current
    DESCRIPTION
        "NNTP Health check overflow flag."
    ::= { slbNewAdvhcNntpEntry 11 }

slbNewAdvhcNntpDownInterval OBJECT-TYPE
    SYNTAX  INTEGER (0..600)
    MAX-ACCESS  read-write
    STATUS  current
    DESCRIPTION
        "NNTP Health check interval when in down state."
    ::= { slbNewAdvhcNntpEntry 12 }

slbNewAdvhcNntpInvert OBJECT-TYPE
    SYNTAX  SlbAdvhcEnaDis
    MAX-ACCESS  read-write
    STATUS  current
    DESCRIPTION
        "NNTP Health check invert flag."
    ::= { slbNewAdvhcNntpEntry 13 }

slbNewAdvhcNntpNewsgroupName OBJECT-TYPE
    SYNTAX   DisplayString (SIZE (0..128))
    MAX-ACCESS  read-write
    STATUS  current
    DESCRIPTION
        "NNTP Health check newsgroup name."
    ::= { slbNewAdvhcNntpEntry 14 }

slbNewAdvhcNntpCopy OBJECT-TYPE
    SYNTAX   DisplayString (SIZE (0..128))
    MAX-ACCESS  read-write
    STATUS  current
    DESCRIPTION
        "NNTP Health check copy flag."
    ::= { slbNewAdvhcNntpEntry 15 }

slbNewAdvhcNntpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcNntpEntry 16 }


-- Advance Health Check POP3
----------------------------

slbCurAdvhcPop3Table  OBJECT-TYPE
    SYNTAX  SEQUENCE OF SlbCurAdvhcPop3Entry
    MAX-ACCESS  not-accessible
    STATUS  current
    DESCRIPTION
        "Note:This mib is not supported on VX instance of Virtualization."
    ::= { advhcCfg 19 }

slbCurAdvhcPop3Entry OBJECT-TYPE
    SYNTAX  SlbCurAdvhcPop3Entry
    MAX-ACCESS  not-accessible
    STATUS  current
    DESCRIPTION
        "."
    INDEX   { slbCurAdvhcPop3ID }
    ::= { slbCurAdvhcPop3Table 1 }

SlbCurAdvhcPop3Entry ::= SEQUENCE {
    slbCurAdvhcPop3ID               DisplayString,
    slbCurAdvhcPop3Name             DisplayString,
    slbCurAdvhcPop3DPort            INTEGER,
    slbCurAdvhcPop3IPVer            SlbAdvhcIPVer,
    slbCurAdvhcPop3HostName         DisplayString,
    slbCurAdvhcPop3Transparent      SlbAdvhcEnaDis,
    slbCurAdvhcPop3Interval         INTEGER,
    slbCurAdvhcPop3Retries          INTEGER,
    slbCurAdvhcPop3RestoreRetries   INTEGER,
    slbCurAdvhcPop3Timeout          INTEGER,
    slbCurAdvhcPop3Overflow         INTEGER,
    slbCurAdvhcPop3DownInterval     INTEGER,
    slbCurAdvhcPop3Invert           SlbAdvhcEnaDis,
    slbCurAdvhcPop3UserName         DisplayString,
    slbCurAdvhcPop3Password         DisplayString
    }

slbCurAdvhcPop3ID OBJECT-TYPE
    SYNTAX   DisplayString (SIZE (0..128))
    MAX-ACCESS  read-only
    STATUS  current
    DESCRIPTION
        "POP3 Health check id."
    ::= { slbCurAdvhcPop3Entry 1 }

slbCurAdvhcPop3Name OBJECT-TYPE
    SYNTAX   DisplayString (SIZE (0..128))
    MAX-ACCESS  read-only
    STATUS  current
    DESCRIPTION
        "POP3 Health check name."
    ::= { slbCurAdvhcPop3Entry 2 }

slbCurAdvhcPop3DPort OBJECT-TYPE
    SYNTAX  INTEGER (0..65534)
    MAX-ACCESS  read-only
    STATUS  current
    DESCRIPTION
        "POP3 Health check destination port."
    ::= { slbCurAdvhcPop3Entry 3 }

slbCurAdvhcPop3IPVer OBJECT-TYPE
    SYNTAX  SlbAdvhcIPVer
    MAX-ACCESS  read-only
    STATUS  current
    DESCRIPTION
        "POP3 Health check destination IP version."
    ::= { slbCurAdvhcPop3Entry 4 }

slbCurAdvhcPop3HostName OBJECT-TYPE
    SYNTAX   DisplayString (SIZE (0..128))
    MAX-ACCESS  read-only
    STATUS  current
    DESCRIPTION
        "POP3 Health check destination hostname."
    ::= { slbCurAdvhcPop3Entry 5 }

slbCurAdvhcPop3Transparent OBJECT-TYPE
    SYNTAX  SlbAdvhcEnaDis
    MAX-ACCESS  read-only
    STATUS  current
    DESCRIPTION
        "POP3 Health check trasnsparent flag."
    ::= { slbCurAdvhcPop3Entry 6 }

slbCurAdvhcPop3Interval OBJECT-TYPE
    SYNTAX  INTEGER (1..600)
    MAX-ACCESS  read-only
    STATUS  current
    DESCRIPTION
        "POP3 Health check interval."
    ::= { slbCurAdvhcPop3Entry 7 }

slbCurAdvhcPop3Retries OBJECT-TYPE
    SYNTAX  INTEGER (1..63)
    MAX-ACCESS  read-only
    STATUS  current
    DESCRIPTION
        "POP3 Health check retries counter."
    ::= { slbCurAdvhcPop3Entry 8 }

slbCurAdvhcPop3RestoreRetries OBJECT-TYPE
    SYNTAX  INTEGER (1..63)
    MAX-ACCESS  read-only
    STATUS  current
    DESCRIPTION
        "POP3 Health check retries counter when in the down state."
    ::= { slbCurAdvhcPop3Entry 9 }

slbCurAdvhcPop3Timeout OBJECT-TYPE
    SYNTAX  INTEGER (1..63)
    MAX-ACCESS  read-only
    STATUS  current
    DESCRIPTION
        "POP3 Health check timeout."
    ::= { slbCurAdvhcPop3Entry 10 }

slbCurAdvhcPop3Overflow OBJECT-TYPE
    SYNTAX  INTEGER (0..600)
    MAX-ACCESS  read-only
    STATUS  current
    DESCRIPTION
        "POP3 Health check overload flag."
    ::= { slbCurAdvhcPop3Entry 11 }

slbCurAdvhcPop3DownInterval OBJECT-TYPE
    SYNTAX  INTEGER (0..600)
    MAX-ACCESS  read-only
    STATUS  current
    DESCRIPTION
        "POP3 Health check interval when in the down state."
    ::= { slbCurAdvhcPop3Entry 12 }

slbCurAdvhcPop3Invert OBJECT-TYPE
    SYNTAX  SlbAdvhcEnaDis
    MAX-ACCESS  read-only
    STATUS  current
    DESCRIPTION
        "POP3 Health check invert flag."
    ::= { slbCurAdvhcPop3Entry 13 }

slbCurAdvhcPop3UserName OBJECT-TYPE
    SYNTAX   DisplayString (SIZE (0..32))
    MAX-ACCESS  read-only
    STATUS  current
    DESCRIPTION
        "POP3 Health check user name."
    ::= { slbCurAdvhcPop3Entry 14 }

slbCurAdvhcPop3Password OBJECT-TYPE
    SYNTAX   DisplayString (SIZE (0..32))
    MAX-ACCESS  read-only
    STATUS  current
    DESCRIPTION
        "POP3 Health check password."
    ::= { slbCurAdvhcPop3Entry 15 }


slbNewAdvhcPop3Table  OBJECT-TYPE
    SYNTAX  SEQUENCE OF SlbNewAdvhcPop3Entry
    MAX-ACCESS  not-accessible
    STATUS  current
    DESCRIPTION
        "Note:This mib is not supported on VX instance of Virtualization."
    ::= { advhcCfg 20 }

slbNewAdvhcPop3Entry OBJECT-TYPE
    SYNTAX  SlbNewAdvhcPop3Entry
    MAX-ACCESS  not-accessible
    STATUS  current
    DESCRIPTION
        "."
    INDEX   { slbNewAdvhcPop3ID }
    ::= { slbNewAdvhcPop3Table 1 }

SlbNewAdvhcPop3Entry ::= SEQUENCE {
    slbNewAdvhcPop3ID               DisplayString,
    slbNewAdvhcPop3Name             DisplayString,
    slbNewAdvhcPop3DPort            INTEGER,
    slbNewAdvhcPop3IPVer            SlbAdvhcIPVer,
    slbNewAdvhcPop3HostName         DisplayString,
    slbNewAdvhcPop3Transparent      SlbAdvhcEnaDis,
    slbNewAdvhcPop3Interval         INTEGER,
    slbNewAdvhcPop3Retries          INTEGER,
    slbNewAdvhcPop3RestoreRetries   INTEGER,
    slbNewAdvhcPop3Timeout          INTEGER,
    slbNewAdvhcPop3Overflow         INTEGER,
    slbNewAdvhcPop3DownInterval     INTEGER,
    slbNewAdvhcPop3Invert           SlbAdvhcEnaDis,
    slbNewAdvhcPop3UserName         DisplayString,
    slbNewAdvhcPop3Password         DisplayString,
    slbNewAdvhcPop3Copy             DisplayString,
    slbNewAdvhcPop3Delete           SlbAdvhcDelete
    }

slbNewAdvhcPop3ID OBJECT-TYPE
    SYNTAX   DisplayString (SIZE (0..128))
    MAX-ACCESS  read-only
    STATUS  current
    DESCRIPTION
        "POP3 Health check id."
    ::= { slbNewAdvhcPop3Entry 1 }

slbNewAdvhcPop3Name OBJECT-TYPE
    SYNTAX   DisplayString (SIZE (0..128))
    MAX-ACCESS  read-write
    STATUS  current
    DESCRIPTION
        "POP3 Health check name."
    ::= { slbNewAdvhcPop3Entry 2 }

slbNewAdvhcPop3DPort OBJECT-TYPE
    SYNTAX  INTEGER (0..65534)
    MAX-ACCESS  read-write
    STATUS  current
    DESCRIPTION
        "POP3 Health check destination port."
    ::= { slbNewAdvhcPop3Entry 3 }

slbNewAdvhcPop3IPVer OBJECT-TYPE
    SYNTAX  SlbAdvhcIPVer
    MAX-ACCESS  read-write
    STATUS  current
    DESCRIPTION
        "POP3 Health check destination IP version."
    ::= { slbNewAdvhcPop3Entry 4 }

slbNewAdvhcPop3HostName OBJECT-TYPE
    SYNTAX   DisplayString (SIZE (0..128))
    MAX-ACCESS  read-write
    STATUS  current
    DESCRIPTION
        "POP3 Health check destination hostname."
    ::= { slbNewAdvhcPop3Entry 5 }

slbNewAdvhcPop3Transparent OBJECT-TYPE
    SYNTAX  SlbAdvhcEnaDis
    MAX-ACCESS  read-write
    STATUS  current
    DESCRIPTION
        "POP3 Health check trasnsparent flag."
    ::= { slbNewAdvhcPop3Entry 6 }

slbNewAdvhcPop3Interval OBJECT-TYPE
    SYNTAX  INTEGER (1..600)
    MAX-ACCESS  read-write
    STATUS  current
    DESCRIPTION
        "POP3 Health check interval."
    ::= { slbNewAdvhcPop3Entry 7 }

slbNewAdvhcPop3Retries OBJECT-TYPE
    SYNTAX  INTEGER (1..63)
    MAX-ACCESS  read-write
    STATUS  current
    DESCRIPTION
        "POP3 Health check retries counter."
    ::= { slbNewAdvhcPop3Entry 8 }

slbNewAdvhcPop3RestoreRetries OBJECT-TYPE
    SYNTAX  INTEGER (1..63)
    MAX-ACCESS  read-write
    STATUS  current
    DESCRIPTION
        "POP3 Health check retries counter when in the down state."
    ::= { slbNewAdvhcPop3Entry 9 }

slbNewAdvhcPop3Timeout OBJECT-TYPE
    SYNTAX  INTEGER (1..63)
    MAX-ACCESS  read-write
    STATUS  current
    DESCRIPTION
        "POP3 Health check timeout."
    ::= { slbNewAdvhcPop3Entry 10 }

slbNewAdvhcPop3Overflow OBJECT-TYPE
    SYNTAX  INTEGER (0..600)
    MAX-ACCESS  read-write
    STATUS  current
    DESCRIPTION
        "POP3 Health check overload flag."
    ::= { slbNewAdvhcPop3Entry 11 }

slbNewAdvhcPop3DownInterval OBJECT-TYPE
    SYNTAX  INTEGER (0..600)
    MAX-ACCESS  read-write
    STATUS  current
    DESCRIPTION
        "POP3 Health check interval when in the down state."
    ::= { slbNewAdvhcPop3Entry 12 }

slbNewAdvhcPop3Invert OBJECT-TYPE
    SYNTAX  SlbAdvhcEnaDis
    MAX-ACCESS  read-write
    STATUS  current
    DESCRIPTION
        "POP3 Health check invert flag."
    ::= { slbNewAdvhcPop3Entry 13 }

slbNewAdvhcPop3UserName OBJECT-TYPE
    SYNTAX   DisplayString (SIZE (0..32))
    MAX-ACCESS  read-write
    STATUS  current
    DESCRIPTION
        "POP3 Health check user name."
    ::= { slbNewAdvhcPop3Entry 14 }

slbNewAdvhcPop3Password OBJECT-TYPE
    SYNTAX   DisplayString (SIZE (0..32))
    MAX-ACCESS  read-write
    STATUS  current
    DESCRIPTION
        "POP3 Health check password."
    ::= { slbNewAdvhcPop3Entry 15 }

slbNewAdvhcPop3Copy OBJECT-TYPE
    SYNTAX   DisplayString (SIZE (0..128))
    MAX-ACCESS  read-write
    STATUS  current
    DESCRIPTION
        "POP3 Health check copy indicator."
    ::= { slbNewAdvhcPop3Entry 16 }

slbNewAdvhcPop3Delete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcPop3Entry 17 }


-- Advance Health Check RADIUS
------------------------------

slbCurAdvhcRadiusTable  OBJECT-TYPE
    SYNTAX  SEQUENCE OF SlbCurAdvhcRadiusEntry
    MAX-ACCESS  not-accessible
    STATUS  current
    DESCRIPTION
        "Note:This mib is not supported on VX instance of Virtualization."
    ::= { advhcCfg 21 }

slbCurAdvhcRadiusEntry OBJECT-TYPE
    SYNTAX  SlbCurAdvhcRadiusEntry
    MAX-ACCESS  not-accessible
    STATUS  current
    DESCRIPTION
        "."
    INDEX   { slbCurAdvhcRadiusID }
    ::= { slbCurAdvhcRadiusTable 1 }

SlbCurAdvhcRadiusEntry ::= SEQUENCE {
    slbCurAdvhcRadiusID             DisplayString,
    slbCurAdvhcRadiusName           DisplayString,
    slbCurAdvhcRadiusDPort          INTEGER,
    slbCurAdvhcRadiusIPVer          SlbAdvhcIPVer,
    slbCurAdvhcRadiusHostName       DisplayString,
    slbCurAdvhcRadiusTransparent    SlbAdvhcEnaDis,
    slbCurAdvhcRadiusInterval       INTEGER,
    slbCurAdvhcRadiusRetries        INTEGER,
    slbCurAdvhcRadiusRestoreRetries INTEGER,
    slbCurAdvhcRadiusTimeout        INTEGER,
    slbCurAdvhcRadiusOverflow       INTEGER,
    slbCurAdvhcRadiusDownInterval   INTEGER,
    slbCurAdvhcRadiusInvert         SlbAdvhcEnaDis,
    slbCurAdvhcRadiusDownType       INTEGER,
    slbCurAdvhcRadiusUserName       DisplayString,
    slbCurAdvhcRadiusPassword       DisplayString,
    slbCurAdvhcRadiusSecret         DisplayString
    }

slbCurAdvhcRadiusID OBJECT-TYPE
    SYNTAX   DisplayString (SIZE (0..128))
    MAX-ACCESS  read-only
    STATUS  current
    DESCRIPTION
        "RADIUS health check id."
    ::= { slbCurAdvhcRadiusEntry 1 }

slbCurAdvhcRadiusName OBJECT-TYPE
    SYNTAX   DisplayString (SIZE (0..128))
    MAX-ACCESS  read-only
    STATUS  current
    DESCRIPTION
        "RADIUS health check name."
    ::= { slbCurAdvhcRadiusEntry 2 }

slbCurAdvhcRadiusDPort OBJECT-TYPE
    SYNTAX  INTEGER (0..65534)
    MAX-ACCESS  read-only
    STATUS  current
    DESCRIPTION
        "RADIUS health check destination port."
    ::= { slbCurAdvhcRadiusEntry 3 }

slbCurAdvhcRadiusIPVer OBJECT-TYPE
    SYNTAX  SlbAdvhcIPVer
    MAX-ACCESS  read-only
    STATUS  current
    DESCRIPTION
        "RADIUS health check destination IP version."
    ::= { slbCurAdvhcRadiusEntry 4 }

slbCurAdvhcRadiusHostName OBJECT-TYPE
    SYNTAX   DisplayString (SIZE (0..128))
    MAX-ACCESS  read-only
    STATUS  current
    DESCRIPTION
        "RADIUS health check destination hostname."
    ::= { slbCurAdvhcRadiusEntry 5 }

slbCurAdvhcRadiusTransparent OBJECT-TYPE
    SYNTAX  SlbAdvhcEnaDis
    MAX-ACCESS  read-only
    STATUS  current
    DESCRIPTION
        "RADIUS health check transparent flag."
    ::= { slbCurAdvhcRadiusEntry 6 }

slbCurAdvhcRadiusInterval OBJECT-TYPE
    SYNTAX  INTEGER (1..600)
    MAX-ACCESS  read-only
    STATUS  current
    DESCRIPTION
        "RADIUS health check interval."
    ::= { slbCurAdvhcRadiusEntry 7 }

slbCurAdvhcRadiusRetries OBJECT-TYPE
    SYNTAX  INTEGER (1..63)
    MAX-ACCESS  read-only
    STATUS  current
    DESCRIPTION
        "RADIUS health check retries counter."
    ::= { slbCurAdvhcRadiusEntry 8 }

slbCurAdvhcRadiusRestoreRetries OBJECT-TYPE
    SYNTAX  INTEGER (1..63)
    MAX-ACCESS  read-only
    STATUS  current
    DESCRIPTION
        "RADIUS health check retries in the down state counter."
    ::= { slbCurAdvhcRadiusEntry 9 }

slbCurAdvhcRadiusTimeout OBJECT-TYPE
    SYNTAX  INTEGER (1..63)
    MAX-ACCESS  read-only
    STATUS  current
    DESCRIPTION
        "RADIUS health check timeout parameter."
    ::= { slbCurAdvhcRadiusEntry 10 }

slbCurAdvhcRadiusOverflow OBJECT-TYPE
    SYNTAX  INTEGER (0..600)
    MAX-ACCESS  read-only
    STATUS  current
    DESCRIPTION
        "RADIUS health check overflow flag."
    ::= { slbCurAdvhcRadiusEntry 11 }

slbCurAdvhcRadiusDownInterval OBJECT-TYPE
    SYNTAX  INTEGER (0..600)
    MAX-ACCESS  read-only
    STATUS  current
    DESCRIPTION
        "RADIUS health check interval in down state."
    ::= { slbCurAdvhcRadiusEntry 12 }

slbCurAdvhcRadiusInvert OBJECT-TYPE
    SYNTAX  SlbAdvhcEnaDis
    MAX-ACCESS  read-only
    STATUS  current
    DESCRIPTION
        "RADIUS health check invert flag."
    ::= { slbCurAdvhcRadiusEntry 13 }

slbCurAdvhcRadiusDownType OBJECT-TYPE
    SYNTAX  INTEGER { accounting(1), authentication(2), any(3), unsupported(2147483647) }
    MAX-ACCESS  read-only
    STATUS  current
    DESCRIPTION
        "RADIUS health check type."
    ::= { slbCurAdvhcRadiusEntry 14 }

slbCurAdvhcRadiusUserName OBJECT-TYPE
    SYNTAX   DisplayString (SIZE (0..32))
    MAX-ACCESS  read-only
    STATUS  current
    DESCRIPTION
        "RADIUS health check user name."
    ::= { slbCurAdvhcRadiusEntry 15 }

slbCurAdvhcRadiusPassword OBJECT-TYPE
    SYNTAX   DisplayString (SIZE (0..32))
    MAX-ACCESS  read-only
    STATUS  current
    DESCRIPTION
        "RADIUS health check password."
    ::= { slbCurAdvhcRadiusEntry 16 }

slbCurAdvhcRadiusSecret OBJECT-TYPE
    SYNTAX   DisplayString (SIZE (0..32))
    MAX-ACCESS  read-only
    STATUS  current
    DESCRIPTION
        "RADIUS health check secret."
    ::= { slbCurAdvhcRadiusEntry 17 }


slbNewAdvhcRadiusTable  OBJECT-TYPE
    SYNTAX  SEQUENCE OF SlbNewAdvhcRadiusEntry
    MAX-ACCESS  not-accessible
    STATUS  current
    DESCRIPTION
        "Note:This mib is not supported on VX instance of Virtualization."
    ::= { advhcCfg 22 }

slbNewAdvhcRadiusEntry OBJECT-TYPE
    SYNTAX  SlbNewAdvhcRadiusEntry
    MAX-ACCESS  not-accessible
    STATUS  current
    DESCRIPTION
        "."
    INDEX   { slbNewAdvhcRadiusID }
    ::= { slbNewAdvhcRadiusTable 1 }

SlbNewAdvhcRadiusEntry ::= SEQUENCE {
    slbNewAdvhcRadiusID             DisplayString,
    slbNewAdvhcRadiusName           DisplayString,
    slbNewAdvhcRadiusDPort          INTEGER,
    slbNewAdvhcRadiusIPVer          SlbAdvhcIPVer,
    slbNewAdvhcRadiusHostName       DisplayString,
    slbNewAdvhcRadiusTransparent    SlbAdvhcEnaDis,
    slbNewAdvhcRadiusInterval       INTEGER,
    slbNewAdvhcRadiusRetries        INTEGER,
    slbNewAdvhcRadiusRestoreRetries INTEGER,
    slbNewAdvhcRadiusTimeout        INTEGER,
    slbNewAdvhcRadiusOverflow       INTEGER,
    slbNewAdvhcRadiusDownInterval   INTEGER,
    slbNewAdvhcRadiusInvert         SlbAdvhcEnaDis,
    slbNewAdvhcRadiusDownType       INTEGER,
    slbNewAdvhcRadiusUserName       DisplayString,
    slbNewAdvhcRadiusPassword       DisplayString,
    slbNewAdvhcRadiusSecret         DisplayString,
    slbNewAdvhcRadiusCopy           DisplayString,
    slbNewAdvhcRadiusDelete         SlbAdvhcDelete
    }

slbNewAdvhcRadiusID OBJECT-TYPE
    SYNTAX   DisplayString (SIZE (0..128))
    MAX-ACCESS  read-only
    STATUS  current
    DESCRIPTION
        "RADIUS health check id."
    ::= { slbNewAdvhcRadiusEntry 1 }

slbNewAdvhcRadiusName OBJECT-TYPE
    SYNTAX   DisplayString (SIZE (0..128))
    MAX-ACCESS  read-write
    STATUS  current
    DESCRIPTION
        "RADIUS health check name."
    ::= { slbNewAdvhcRadiusEntry 2 }

slbNewAdvhcRadiusDPort OBJECT-TYPE
    SYNTAX  INTEGER (0..65534)
    MAX-ACCESS  read-write
    STATUS  current
    DESCRIPTION
        "RADIUS health check destination port."
    ::= { slbNewAdvhcRadiusEntry 3 }

slbNewAdvhcRadiusIPVer OBJECT-TYPE
    SYNTAX  SlbAdvhcIPVer
    MAX-ACCESS  read-write
    STATUS  current
    DESCRIPTION
        "RADIUS health check destination IP version."
    ::= { slbNewAdvhcRadiusEntry 4 }

slbNewAdvhcRadiusHostName OBJECT-TYPE
    SYNTAX   DisplayString (SIZE (0..128))
    MAX-ACCESS  read-write
    STATUS  current
    DESCRIPTION
        "RADIUS health check destination hostname."
    ::= { slbNewAdvhcRadiusEntry 5 }

slbNewAdvhcRadiusTransparent OBJECT-TYPE
    SYNTAX  SlbAdvhcEnaDis
    MAX-ACCESS  read-write
    STATUS  current
    DESCRIPTION
        "RADIUS health check transparent flag."
    ::= { slbNewAdvhcRadiusEntry 6 }

slbNewAdvhcRadiusInterval OBJECT-TYPE
    SYNTAX  INTEGER (1..600)
    MAX-ACCESS  read-write
    STATUS  current
    DESCRIPTION
        "RADIUS health check interval."
    ::= { slbNewAdvhcRadiusEntry 7 }

slbNewAdvhcRadiusRetries OBJECT-TYPE
    SYNTAX  INTEGER (1..63)
    MAX-ACCESS  read-write
    STATUS  current
    DESCRIPTION
        "RADIUS health check retries counter."
    ::= { slbNewAdvhcRadiusEntry 8 }

slbNewAdvhcRadiusRestoreRetries OBJECT-TYPE
    SYNTAX  INTEGER (1..63)
    MAX-ACCESS  read-write
    STATUS  current
    DESCRIPTION
        "RADIUS health check retries in the down state counter."
    ::= { slbNewAdvhcRadiusEntry 9 }

slbNewAdvhcRadiusTimeout OBJECT-TYPE
    SYNTAX  INTEGER (1..63)
    MAX-ACCESS  read-write
    STATUS  current
    DESCRIPTION
        "RADIUS health check timeout parameter."
    ::= { slbNewAdvhcRadiusEntry 10 }

slbNewAdvhcRadiusOverflow OBJECT-TYPE
    SYNTAX  INTEGER (0..600)
    MAX-ACCESS  read-write
    STATUS  current
    DESCRIPTION
        "RADIUS health check overflow flag."
    ::= { slbNewAdvhcRadiusEntry 11 }

slbNewAdvhcRadiusDownInterval OBJECT-TYPE
    SYNTAX  INTEGER (0..600)
    MAX-ACCESS  read-write
    STATUS  current
    DESCRIPTION
        "RADIUS health check interval in down state."
    ::= { slbNewAdvhcRadiusEntry 12 }

slbNewAdvhcRadiusInvert OBJECT-TYPE
    SYNTAX  SlbAdvhcEnaDis
    MAX-ACCESS  read-write
    STATUS  current
    DESCRIPTION
        "RADIUS health check invert flag."
    ::= { slbNewAdvhcRadiusEntry 13 }

slbNewAdvhcRadiusDownType OBJECT-TYPE
    SYNTAX  INTEGER { accounting(1), authentication(2), any(3), unsupported(2147483647) }
    MAX-ACCESS  read-write
    STATUS  current
    DESCRIPTION
        "RADIUS health check type."
    ::= { slbNewAdvhcRadiusEntry 14 }

slbNewAdvhcRadiusUserName OBJECT-TYPE
    SYNTAX   DisplayString (SIZE (0..32))
    MAX-ACCESS  read-write
    STATUS  current
    DESCRIPTION
        "RADIUS health check user name."
    ::= { slbNewAdvhcRadiusEntry 15 }

slbNewAdvhcRadiusPassword OBJECT-TYPE
    SYNTAX   DisplayString (SIZE (0..32))
    MAX-ACCESS  read-write
    STATUS  current
    DESCRIPTION
        "RADIUS health check password."
    ::= { slbNewAdvhcRadiusEntry 16 }

slbNewAdvhcRadiusSecret OBJECT-TYPE
    SYNTAX   DisplayString (SIZE (0..32))
    MAX-ACCESS  read-write
    STATUS  current
    DESCRIPTION
        "RADIUS health check secret."
    ::= { slbNewAdvhcRadiusEntry 17 }

slbNewAdvhcRadiusCopy OBJECT-TYPE
    SYNTAX   DisplayString (SIZE (0..128))
    MAX-ACCESS  read-write
    STATUS  current
    DESCRIPTION
        "RADIUS health check copy indicator."
    ::= { slbNewAdvhcRadiusEntry 18 }

slbNewAdvhcRadiusDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcRadiusEntry 19 }


-- Advance Health Check RTSP
----------------------------

slbCurAdvhcRtspTable  OBJECT-TYPE
    SYNTAX  SEQUENCE OF SlbCurAdvhcRtspEntry
    MAX-ACCESS  not-accessible
    STATUS  current
    DESCRIPTION
        "Note:This mib is not supported on VX instance of Virtualization."
    ::= { advhcCfg 23 }

slbCurAdvhcRtspEntry OBJECT-TYPE
    SYNTAX  SlbCurAdvhcRtspEntry
    MAX-ACCESS  not-accessible
    STATUS  current
    DESCRIPTION
        "."
    INDEX   { slbCurAdvhcRtspID }
    ::= { slbCurAdvhcRtspTable 1 }

SlbCurAdvhcRtspEntry ::= SEQUENCE {
    slbCurAdvhcRtspID               DisplayString,
    slbCurAdvhcRtspName             DisplayString,
    slbCurAdvhcRtspDPort            INTEGER,
    slbCurAdvhcRtspIPVer            SlbAdvhcIPVer,
    slbCurAdvhcRtspHostName         DisplayString,
    slbCurAdvhcRtspTransparent      SlbAdvhcEnaDis,
    slbCurAdvhcRtspInterval         INTEGER,
    slbCurAdvhcRtspRetries          INTEGER,
    slbCurAdvhcRtspRestoreRetries   INTEGER,
    slbCurAdvhcRtspTimeout          INTEGER,
    slbCurAdvhcRtspOverflow         INTEGER,
    slbCurAdvhcRtspDownInterval     INTEGER,
    slbCurAdvhcRtspInvert           SlbAdvhcEnaDis,
    slbCurAdvhcRtspMethod           INTEGER,
    slbCurAdvhcRtspHostname         DisplayString,
    slbCurAdvhcRtspPath             RadwareLongDisplayString,
    slbCurAdvhcRtspResponseCodes    DisplayString
    }

slbCurAdvhcRtspID OBJECT-TYPE
    SYNTAX   DisplayString (SIZE (0..128))
    MAX-ACCESS  read-only
    STATUS  current
    DESCRIPTION
        "RTSP health check id."
    ::= { slbCurAdvhcRtspEntry 1 }

slbCurAdvhcRtspName OBJECT-TYPE
    SYNTAX   DisplayString (SIZE (0..128))
    MAX-ACCESS  read-only
    STATUS  current
    DESCRIPTION
        "RTSP health check name."
    ::= { slbCurAdvhcRtspEntry 2 }

slbCurAdvhcRtspDPort OBJECT-TYPE
    SYNTAX  INTEGER (0..65534)
    MAX-ACCESS  read-only
    STATUS  current
    DESCRIPTION
        "RTSP health check destination port."
    ::= { slbCurAdvhcRtspEntry 3 }

slbCurAdvhcRtspIPVer OBJECT-TYPE
    SYNTAX  SlbAdvhcIPVer
    MAX-ACCESS  read-only
    STATUS  current
    DESCRIPTION
        "RTSP health check destination IP version."
    ::= { slbCurAdvhcRtspEntry 4 }

slbCurAdvhcRtspHostName OBJECT-TYPE
    SYNTAX   DisplayString (SIZE (0..128))
    MAX-ACCESS  read-only
    STATUS  current
    DESCRIPTION
        "RTSP health check destination hostname."
    ::= { slbCurAdvhcRtspEntry 5 }

slbCurAdvhcRtspTransparent OBJECT-TYPE
    SYNTAX  SlbAdvhcEnaDis
    MAX-ACCESS  read-only
    STATUS  current
    DESCRIPTION
        "RTSP health check transparent flag."
    ::= { slbCurAdvhcRtspEntry 6 }

slbCurAdvhcRtspInterval OBJECT-TYPE
    SYNTAX  INTEGER (1..600)
    MAX-ACCESS  read-only
    STATUS  current
    DESCRIPTION
        "RTSP health check interval."
    ::= { slbCurAdvhcRtspEntry 7 }

slbCurAdvhcRtspRetries OBJECT-TYPE
    SYNTAX  INTEGER (1..63)
    MAX-ACCESS  read-only
    STATUS  current
    DESCRIPTION
        "RTSP health check retries counter."
    ::= { slbCurAdvhcRtspEntry 8 }

slbCurAdvhcRtspRestoreRetries OBJECT-TYPE
    SYNTAX  INTEGER (1..63)
    MAX-ACCESS  read-only
    STATUS  current
    DESCRIPTION
        "RTSP health check retries counter in the down state."
    ::= { slbCurAdvhcRtspEntry 9 }

slbCurAdvhcRtspTimeout OBJECT-TYPE
    SYNTAX  INTEGER (1..63)
    MAX-ACCESS  read-only
    STATUS  current
    DESCRIPTION
        "RTSP health check timeout."
    ::= { slbCurAdvhcRtspEntry 10 }

slbCurAdvhcRtspOverflow OBJECT-TYPE
    SYNTAX  INTEGER (0..600)
    MAX-ACCESS  read-only
    STATUS  current
    DESCRIPTION
        "RTSP health check overflow flag."
    ::= { slbCurAdvhcRtspEntry 11 }

slbCurAdvhcRtspDownInterval OBJECT-TYPE
    SYNTAX  INTEGER (0..600)
    MAX-ACCESS  read-only
    STATUS  current
    DESCRIPTION
        "RTSP health check interval when in the down state."
    ::= { slbCurAdvhcRtspEntry 12 }

slbCurAdvhcRtspInvert OBJECT-TYPE
    SYNTAX  SlbAdvhcEnaDis
    MAX-ACCESS  read-only
    STATUS  current
    DESCRIPTION
        "RTSP health check invert flag."
    ::= { slbCurAdvhcRtspEntry 13 }

slbCurAdvhcRtspMethod OBJECT-TYPE
    SYNTAX  INTEGER { options(1), describe(2), inherit(3), unsupported(2147483647) }
    MAX-ACCESS  read-only
    STATUS  current
    DESCRIPTION
        "RTSP health check method."
    ::= { slbCurAdvhcRtspEntry 14 }

slbCurAdvhcRtspHostname OBJECT-TYPE
    SYNTAX   DisplayString (SIZE (0..128))
    MAX-ACCESS  read-only
    STATUS  current
    DESCRIPTION
        "RTSP health check server hostname."
    ::= { slbCurAdvhcRtspEntry 15 }

slbCurAdvhcRtspPath OBJECT-TYPE
    SYNTAX   RadwareLongDisplayString (SIZE (0..256))
    MAX-ACCESS  read-only
    STATUS  current
    DESCRIPTION
        "RTSP health check path."
    ::= { slbCurAdvhcRtspEntry 16 }    
    
slbCurAdvhcRtspResponseCodes OBJECT-TYPE
    SYNTAX   DisplayString (SIZE (0..48))
    MAX-ACCESS  read-only
    STATUS  current
    DESCRIPTION
        "RTSP health check response code."
    ::= { slbCurAdvhcRtspEntry 17 }


slbNewAdvhcRtspTable  OBJECT-TYPE
    SYNTAX  SEQUENCE OF SlbNewAdvhcRtspEntry
    MAX-ACCESS  not-accessible
    STATUS  current
    DESCRIPTION
        "Note:This mib is not supported on VX instance of Virtualization."
    ::= { advhcCfg 24 }

slbNewAdvhcRtspEntry OBJECT-TYPE
    SYNTAX  SlbNewAdvhcRtspEntry
    MAX-ACCESS  not-accessible
    STATUS  current
    DESCRIPTION
        "."
    INDEX   { slbNewAdvhcRtspID }
    ::= { slbNewAdvhcRtspTable 1 }

SlbNewAdvhcRtspEntry ::= SEQUENCE {
    slbNewAdvhcRtspID               DisplayString,
    slbNewAdvhcRtspName             DisplayString,
    slbNewAdvhcRtspDPort            INTEGER,
    slbNewAdvhcRtspIPVer            SlbAdvhcIPVer,
    slbNewAdvhcRtspHostName         DisplayString,
    slbNewAdvhcRtspTransparent      SlbAdvhcEnaDis,
    slbNewAdvhcRtspInterval         INTEGER,
    slbNewAdvhcRtspRetries          INTEGER,
    slbNewAdvhcRtspRestoreRetries   INTEGER,
    slbNewAdvhcRtspTimeout          INTEGER,
    slbNewAdvhcRtspOverflow         INTEGER,
    slbNewAdvhcRtspDownInterval     INTEGER,
    slbNewAdvhcRtspInvert           SlbAdvhcEnaDis,
    slbNewAdvhcRtspMethod           INTEGER,
    slbNewAdvhcRtspHostname         DisplayString,
    slbNewAdvhcRtspPath             RadwareLongDisplayString,
    slbNewAdvhcRtspResponseCodes    DisplayString,
    slbNewAdvhcRtspCopy             DisplayString,
    slbNewAdvhcRtspDelete           SlbAdvhcDelete
    }

slbNewAdvhcRtspID OBJECT-TYPE
    SYNTAX   DisplayString (SIZE (0..128))
    MAX-ACCESS  read-only
    STATUS  current
    DESCRIPTION
        "RTSP health check id."
    ::= { slbNewAdvhcRtspEntry 1 }

slbNewAdvhcRtspName OBJECT-TYPE
    SYNTAX   DisplayString (SIZE (0..128))
    MAX-ACCESS  read-write
    STATUS  current
    DESCRIPTION
        "RTSP health check name."
    ::= { slbNewAdvhcRtspEntry 2 }

slbNewAdvhcRtspDPort OBJECT-TYPE
    SYNTAX  INTEGER (0..65534)
    MAX-ACCESS  read-write
    STATUS  current
    DESCRIPTION
        "RTSP health check destination port."
    ::= { slbNewAdvhcRtspEntry 3 }

slbNewAdvhcRtspIPVer OBJECT-TYPE
    SYNTAX  SlbAdvhcIPVer
    MAX-ACCESS  read-write
    STATUS  current
    DESCRIPTION
        "RTSP health check destination IP version."
    ::= { slbNewAdvhcRtspEntry 4 }

slbNewAdvhcRtspHostName OBJECT-TYPE
    SYNTAX   DisplayString (SIZE (0..128))
    MAX-ACCESS  read-write
    STATUS  current
    DESCRIPTION
        "RTSP health check destination hostname."
    ::= { slbNewAdvhcRtspEntry 5 }

slbNewAdvhcRtspTransparent OBJECT-TYPE
    SYNTAX  SlbAdvhcEnaDis
    MAX-ACCESS  read-write
    STATUS  current
    DESCRIPTION
        "RTSP health check transparent flag."
    ::= { slbNewAdvhcRtspEntry 6 }

slbNewAdvhcRtspInterval OBJECT-TYPE
    SYNTAX  INTEGER (1..600)
    MAX-ACCESS  read-write
    STATUS  current
    DESCRIPTION
        "RTSP health check interval."
    ::= { slbNewAdvhcRtspEntry 7 }

slbNewAdvhcRtspRetries OBJECT-TYPE
    SYNTAX  INTEGER (1..63)
    MAX-ACCESS  read-write
    STATUS  current
    DESCRIPTION
        "RTSP health check retries counter."
    ::= { slbNewAdvhcRtspEntry 8 }

slbNewAdvhcRtspRestoreRetries OBJECT-TYPE
    SYNTAX  INTEGER (1..63)
    MAX-ACCESS  read-write
    STATUS  current
    DESCRIPTION
        "RTSP health check retries counter in the down state."
    ::= { slbNewAdvhcRtspEntry 9 }

slbNewAdvhcRtspTimeout OBJECT-TYPE
    SYNTAX  INTEGER (1..63)
    MAX-ACCESS  read-write
    STATUS  current
    DESCRIPTION
        "RTSP health check timeout."
    ::= { slbNewAdvhcRtspEntry 10 }

slbNewAdvhcRtspOverflow OBJECT-TYPE
    SYNTAX  INTEGER (0..600)
    MAX-ACCESS  read-write
    STATUS  current
    DESCRIPTION
        "RTSP health check overflow flag."
    ::= { slbNewAdvhcRtspEntry 11 }

slbNewAdvhcRtspDownInterval OBJECT-TYPE
    SYNTAX  INTEGER (0..600)
    MAX-ACCESS  read-write
    STATUS  current
    DESCRIPTION
        "RTSP health check interval when in the down state."
    ::= { slbNewAdvhcRtspEntry 12 }

slbNewAdvhcRtspInvert OBJECT-TYPE
    SYNTAX  SlbAdvhcEnaDis
    MAX-ACCESS  read-write
    STATUS  current
    DESCRIPTION
        "RTSP health check invert flag."
    ::= { slbNewAdvhcRtspEntry 13 }

slbNewAdvhcRtspMethod OBJECT-TYPE
    SYNTAX  INTEGER { options(1), describe(2), inherit(3), unsupported(2147483647) }
    MAX-ACCESS  read-write
    STATUS  current
    DESCRIPTION
        "RTSP health check method."
    ::= { slbNewAdvhcRtspEntry 14 }

slbNewAdvhcRtspHostname OBJECT-TYPE
    SYNTAX   DisplayString (SIZE (0..128))
    MAX-ACCESS  read-write
    STATUS  current
    DESCRIPTION
        "RTSP health check server hostname."
    ::= { slbNewAdvhcRtspEntry 15 }

slbNewAdvhcRtspPath OBJECT-TYPE
    SYNTAX   RadwareLongDisplayString (SIZE (0..256))
    MAX-ACCESS  read-write
    STATUS  current
    DESCRIPTION
        "RTSP health check path."
    ::= { slbNewAdvhcRtspEntry 16 }    
    
slbNewAdvhcRtspResponseCodes OBJECT-TYPE
    SYNTAX   DisplayString (SIZE (0..48))
    MAX-ACCESS  read-write
    STATUS  current
    DESCRIPTION
        "RTSP health check response code."
    ::= { slbNewAdvhcRtspEntry 17 }  

slbNewAdvhcRtspCopy OBJECT-TYPE
    SYNTAX   DisplayString (SIZE (0..128))
    MAX-ACCESS  read-write
    STATUS  current
    DESCRIPTION
        "RTSP health check copy flag."
    ::= { slbNewAdvhcRtspEntry 18 }

slbNewAdvhcRtspDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcRtspEntry 19 }


-- Advance Health Check SIP
---------------------------

slbCurAdvhcSipTable  OBJECT-TYPE
    SYNTAX  SEQUENCE OF SlbCurAdvhcSipEntry
    MAX-ACCESS  not-accessible
    STATUS  current
    DESCRIPTION
        "Note:This mib is not supported on VX instance of Virtualization."
    ::= { advhcCfg 25 }

slbCurAdvhcSipEntry OBJECT-TYPE
    SYNTAX  SlbCurAdvhcSipEntry
    MAX-ACCESS  not-accessible
    STATUS  current
    DESCRIPTION
        "."
    INDEX   { slbCurAdvhcSipID }
    ::= { slbCurAdvhcSipTable 1 }

SlbCurAdvhcSipEntry ::= SEQUENCE {
    slbCurAdvhcSipID                DisplayString,
    slbCurAdvhcSipName              DisplayString,
    slbCurAdvhcSipDPort             INTEGER,
    slbCurAdvhcSipIPVer             SlbAdvhcIPVer,
    slbCurAdvhcSipHostName          DisplayString,
    slbCurAdvhcSipTransparent       SlbAdvhcEnaDis,
    slbCurAdvhcSipInterval          INTEGER,
    slbCurAdvhcSipRetries           INTEGER,
    slbCurAdvhcSipRestoreRetries    INTEGER,
    slbCurAdvhcSipTimeout           INTEGER,
    slbCurAdvhcSipOverflow          INTEGER,
    slbCurAdvhcSipDownInterval      INTEGER,
    slbCurAdvhcSipInvert            SlbAdvhcEnaDis,
    slbCurAdvhcSipMethod            INTEGER,
    slbCurAdvhcSipTransport         INTEGER,
    slbCurAdvhcSipRequestUri        RadwareLongDisplayString,
    slbCurAdvhcSipFrom              RadwareLongDisplayString,
    slbCurAdvhcSipResponseCodes     DisplayString
    }

slbCurAdvhcSipID OBJECT-TYPE
    SYNTAX   DisplayString (SIZE (0..128))
    MAX-ACCESS  read-only
    STATUS  current
    DESCRIPTION
        "SIP Health check id."
    ::= { slbCurAdvhcSipEntry 1 }

slbCurAdvhcSipName OBJECT-TYPE
    SYNTAX   DisplayString (SIZE (0..128))
    MAX-ACCESS  read-only
    STATUS  current
    DESCRIPTION
        "SIP Health check name."
    ::= { slbCurAdvhcSipEntry 2 }

slbCurAdvhcSipDPort OBJECT-TYPE
    SYNTAX  INTEGER (0..65534)
    MAX-ACCESS  read-only
    STATUS  current
    DESCRIPTION
        "SIP Health check destination port."
    ::= { slbCurAdvhcSipEntry 3 }

slbCurAdvhcSipIPVer OBJECT-TYPE
    SYNTAX  SlbAdvhcIPVer
    MAX-ACCESS  read-only
    STATUS  current
    DESCRIPTION
        "SIP Health check destination IP version."
    ::= { slbCurAdvhcSipEntry 4 }

slbCurAdvhcSipHostName OBJECT-TYPE
    SYNTAX   DisplayString (SIZE (0..128))
    MAX-ACCESS  read-only
    STATUS  current
    DESCRIPTION
        "SIP Health check destination hostname."
    ::= { slbCurAdvhcSipEntry 5 }

slbCurAdvhcSipTransparent OBJECT-TYPE
    SYNTAX  SlbAdvhcEnaDis
    MAX-ACCESS  read-only
    STATUS  current
    DESCRIPTION
        "SIP Health check transparent flag."
    ::= { slbCurAdvhcSipEntry 6 }

slbCurAdvhcSipInterval OBJECT-TYPE
    SYNTAX  INTEGER (1..600)
    MAX-ACCESS  read-only
    STATUS  current
    DESCRIPTION
        "SIP Health check interval."
    ::= { slbCurAdvhcSipEntry 7 }

slbCurAdvhcSipRetries OBJECT-TYPE
    SYNTAX  INTEGER (1..63)
    MAX-ACCESS  read-only
    STATUS  current
    DESCRIPTION
        "SIP Health check retries counter."
    ::= { slbCurAdvhcSipEntry 8 }

slbCurAdvhcSipRestoreRetries OBJECT-TYPE
    SYNTAX  INTEGER (1..63)
    MAX-ACCESS  read-only
    STATUS  current
    DESCRIPTION
        "SIP Health check retries when in the down state."
    ::= { slbCurAdvhcSipEntry 9 }

slbCurAdvhcSipTimeout OBJECT-TYPE
    SYNTAX  INTEGER (1..63)
    MAX-ACCESS  read-only
    STATUS  current
    DESCRIPTION
        "SIP Health check timeout."
    ::= { slbCurAdvhcSipEntry 10 }

slbCurAdvhcSipOverflow OBJECT-TYPE
    SYNTAX  INTEGER (0..600)
    MAX-ACCESS  read-only
    STATUS  current
    DESCRIPTION
        "SIP Health check overflow flag."
    ::= { slbCurAdvhcSipEntry 11 }

slbCurAdvhcSipDownInterval OBJECT-TYPE
    SYNTAX  INTEGER (0..600)
    MAX-ACCESS  read-only
    STATUS  current
    DESCRIPTION
        "SIP Health check interval when in down state."
    ::= { slbCurAdvhcSipEntry 12 }

slbCurAdvhcSipInvert OBJECT-TYPE
    SYNTAX  SlbAdvhcEnaDis
    MAX-ACCESS  read-only
    STATUS  current
    DESCRIPTION
        "SIP Health check invert flag."
    ::= { slbCurAdvhcSipEntry 13 }

slbCurAdvhcSipMethod OBJECT-TYPE
    SYNTAX  INTEGER { options(1), ping(2), unsupported(2147483647) }
    MAX-ACCESS  read-only
    STATUS  current
    DESCRIPTION
        "SIP Health check method."
    ::= { slbCurAdvhcSipEntry 14 }

slbCurAdvhcSipTransport OBJECT-TYPE
    SYNTAX  INTEGER { udp(1), tcp(2), unsupported(2147483647) }
    MAX-ACCESS  read-only
    STATUS  current
    DESCRIPTION
        "SIP Health check transport."
    ::= { slbCurAdvhcSipEntry 15 }

slbCurAdvhcSipRequestUri OBJECT-TYPE
    SYNTAX   RadwareLongDisplayString (SIZE (0..256))
    MAX-ACCESS  read-only
    STATUS  current
    DESCRIPTION
        "SIP Health check URI."
    ::= { slbCurAdvhcSipEntry 16 }
    
slbCurAdvhcSipFrom OBJECT-TYPE
    SYNTAX   RadwareLongDisplayString (SIZE (0..256))
    MAX-ACCESS  read-only
    STATUS  current
    DESCRIPTION
        "SIP Health check 'from' string."
    ::= { slbCurAdvhcSipEntry 17 }
    
slbCurAdvhcSipResponseCodes OBJECT-TYPE
    SYNTAX   DisplayString (SIZE (0..48))
    MAX-ACCESS  read-only
    STATUS  current
    DESCRIPTION
        "SIP Health check expected response code."
    ::= { slbCurAdvhcSipEntry 18 }    


slbNewAdvhcSipTable  OBJECT-TYPE
    SYNTAX  SEQUENCE OF SlbNewAdvhcSipEntry
    MAX-ACCESS  not-accessible
    STATUS  current
    DESCRIPTION
        "Note:This mib is not supported on VX instance of Virtualization."
    ::= { advhcCfg 26 }

slbNewAdvhcSipEntry OBJECT-TYPE
    SYNTAX  SlbNewAdvhcSipEntry
    MAX-ACCESS  not-accessible
    STATUS  current
    DESCRIPTION
        "."
    INDEX   { slbNewAdvhcSipID }
    ::= { slbNewAdvhcSipTable 1 }

SlbNewAdvhcSipEntry ::= SEQUENCE {
    slbNewAdvhcSipID                DisplayString,
    slbNewAdvhcSipName              DisplayString,
    slbNewAdvhcSipDPort             INTEGER,
    slbNewAdvhcSipIPVer             SlbAdvhcIPVer,
    slbNewAdvhcSipHostName          DisplayString,
    slbNewAdvhcSipTransparent       SlbAdvhcEnaDis,
    slbNewAdvhcSipInterval          INTEGER,
    slbNewAdvhcSipRetries           INTEGER,
    slbNewAdvhcSipRestoreRetries    INTEGER,
    slbNewAdvhcSipTimeout           INTEGER,
    slbNewAdvhcSipOverflow          INTEGER,
    slbNewAdvhcSipDownInterval      INTEGER,
    slbNewAdvhcSipInvert            SlbAdvhcEnaDis,
    slbNewAdvhcSipMethod            INTEGER,
    slbNewAdvhcSipTransport         INTEGER,
    slbNewAdvhcSipRequestUri        RadwareLongDisplayString,
    slbNewAdvhcSipFrom              RadwareLongDisplayString,
    slbNewAdvhcSipResponseCodes     DisplayString,
    slbNewAdvhcSipCopy              DisplayString,
    slbNewAdvhcSipDelete            SlbAdvhcDelete
    }

slbNewAdvhcSipID OBJECT-TYPE
    SYNTAX   DisplayString (SIZE (0..128))
    MAX-ACCESS  read-only
    STATUS  current
    DESCRIPTION
        "SIP Health check id ."
    ::= { slbNewAdvhcSipEntry 1 }

slbNewAdvhcSipName OBJECT-TYPE
    SYNTAX   DisplayString (SIZE (0..128))
    MAX-ACCESS  read-write
    STATUS  current
    DESCRIPTION
        "SIP Health check name."
    ::= { slbNewAdvhcSipEntry 2 }

slbNewAdvhcSipDPort OBJECT-TYPE
    SYNTAX  INTEGER (0..65534)
    MAX-ACCESS  read-write
    STATUS  current
    DESCRIPTION
        "SIP Health check destination port."
    ::= { slbNewAdvhcSipEntry 3 }

slbNewAdvhcSipIPVer OBJECT-TYPE
    SYNTAX  SlbAdvhcIPVer
    MAX-ACCESS  read-write
    STATUS  current
    DESCRIPTION
        "SIP Health check destination IP version."
    ::= { slbNewAdvhcSipEntry 4 }

slbNewAdvhcSipHostName OBJECT-TYPE
    SYNTAX   DisplayString (SIZE (0..128))
    MAX-ACCESS  read-write
    STATUS  current
    DESCRIPTION
        "SIP Health check destination hostname."
    ::= { slbNewAdvhcSipEntry 5 }

slbNewAdvhcSipTransparent OBJECT-TYPE
    SYNTAX  SlbAdvhcEnaDis
    MAX-ACCESS  read-write
    STATUS  current
    DESCRIPTION
        "SIP Health check transparent flag."
    ::= { slbNewAdvhcSipEntry 6 }

slbNewAdvhcSipInterval OBJECT-TYPE
    SYNTAX  INTEGER (1..600)
    MAX-ACCESS  read-write
    STATUS  current
    DESCRIPTION
        "SIP Health check interval."
    ::= { slbNewAdvhcSipEntry 7 }

slbNewAdvhcSipRetries OBJECT-TYPE
    SYNTAX  INTEGER (1..63)
    MAX-ACCESS  read-write
    STATUS  current
    DESCRIPTION
        "SIP Health check retries counter."
    ::= { slbNewAdvhcSipEntry 8 }

slbNewAdvhcSipRestoreRetries OBJECT-TYPE
    SYNTAX  INTEGER (1..63)
    MAX-ACCESS  read-write
    STATUS  current
    DESCRIPTION
        "SIP Health check retries when in the down state."
    ::= { slbNewAdvhcSipEntry 9 }

slbNewAdvhcSipTimeout OBJECT-TYPE
    SYNTAX  INTEGER (1..63)
    MAX-ACCESS  read-write
    STATUS  current
    DESCRIPTION
        "SIP Health check timeout."
    ::= { slbNewAdvhcSipEntry 10 }

slbNewAdvhcSipOverflow OBJECT-TYPE
    SYNTAX  INTEGER (0..600)
    MAX-ACCESS  read-write
    STATUS  current
    DESCRIPTION
        "SIP Health check overflow flag."
    ::= { slbNewAdvhcSipEntry 11 }

slbNewAdvhcSipDownInterval OBJECT-TYPE
    SYNTAX  INTEGER (0..600)
    MAX-ACCESS  read-write
    STATUS  current
    DESCRIPTION
        "SIP Health check interval when in down state."
    ::= { slbNewAdvhcSipEntry 12 }

slbNewAdvhcSipInvert OBJECT-TYPE
    SYNTAX  SlbAdvhcEnaDis
    MAX-ACCESS  read-write
    STATUS  current
    DESCRIPTION
        "SIP Health check invert flag."
    ::= { slbNewAdvhcSipEntry 13 }

slbNewAdvhcSipMethod OBJECT-TYPE
    SYNTAX  INTEGER { options(1), ping(2), unsupported(2147483647) }
    MAX-ACCESS  read-write
    STATUS  current
    DESCRIPTION
        "SIP Health check method."
    ::= { slbNewAdvhcSipEntry 14 }

slbNewAdvhcSipTransport OBJECT-TYPE
    SYNTAX  INTEGER { udp(1), tcp(2), unsupported(2147483647) }
    MAX-ACCESS  read-write
    STATUS  current
    DESCRIPTION
        "SIP Health check transport."
    ::= { slbNewAdvhcSipEntry 15 }

slbNewAdvhcSipRequestUri OBJECT-TYPE
    SYNTAX   RadwareLongDisplayString (SIZE (0..256))
    MAX-ACCESS  read-write
    STATUS  current
    DESCRIPTION
        "SIP Health check URI."
    ::= { slbNewAdvhcSipEntry 16 }
    
slbNewAdvhcSipFrom OBJECT-TYPE
    SYNTAX   RadwareLongDisplayString (SIZE (0..256))
    MAX-ACCESS  read-write
    STATUS  current
    DESCRIPTION
        "SIP Health check 'from' string."
    ::= { slbNewAdvhcSipEntry 17 }
    
slbNewAdvhcSipResponseCodes OBJECT-TYPE
    SYNTAX   DisplayString (SIZE (0..48))
    MAX-ACCESS  read-write
    STATUS  current
    DESCRIPTION
        "SIP Health check expected response code."
    ::= { slbNewAdvhcSipEntry 18 }    


slbNewAdvhcSipCopy OBJECT-TYPE
    SYNTAX   DisplayString (SIZE (0..128))
    MAX-ACCESS  read-write
    STATUS  current
    DESCRIPTION
        "SIP Health check copy flag."
    ::= { slbNewAdvhcSipEntry 19 }

slbNewAdvhcSipDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcSipEntry 20 }


-- Advance Health Check SMTP
----------------------------

slbCurAdvhcSmtpTable  OBJECT-TYPE
    SYNTAX  SEQUENCE OF SlbCurAdvhcSmtpEntry
    MAX-ACCESS  not-accessible
    STATUS  current
    DESCRIPTION
        "Note:This mib is not supported on VX instance of Virtualization."
    ::= { advhcCfg 27 }

slbCurAdvhcSmtpEntry OBJECT-TYPE
    SYNTAX  SlbCurAdvhcSmtpEntry
    MAX-ACCESS  not-accessible
    STATUS  current
    DESCRIPTION
        "."
    INDEX   { slbCurAdvhcSmtpID }
    ::= { slbCurAdvhcSmtpTable 1 }

SlbCurAdvhcSmtpEntry ::= SEQUENCE {
    slbCurAdvhcSmtpID               DisplayString,
    slbCurAdvhcSmtpName             DisplayString,
    slbCurAdvhcSmtpDPort            INTEGER,
    slbCurAdvhcSmtpIPVer            SlbAdvhcIPVer,
    slbCurAdvhcSmtpHostName         DisplayString,
    slbCurAdvhcSmtpTransparent      SlbAdvhcEnaDis,
    slbCurAdvhcSmtpInterval         INTEGER,
    slbCurAdvhcSmtpRetries          INTEGER,
    slbCurAdvhcSmtpRestoreRetries   INTEGER,
    slbCurAdvhcSmtpTimeout          INTEGER,
    slbCurAdvhcSmtpOverflow         INTEGER,
    slbCurAdvhcSmtpDownInterval     INTEGER,
    slbCurAdvhcSmtpInvert           SlbAdvhcEnaDis,
    slbCurAdvhcSmtpUserName         DisplayString
    }

slbCurAdvhcSmtpID OBJECT-TYPE
    SYNTAX   DisplayString (SIZE (0..128))
    MAX-ACCESS  read-only
    STATUS  current
    DESCRIPTION
        "SMTP health check id."
    ::= { slbCurAdvhcSmtpEntry 1 }

slbCurAdvhcSmtpName OBJECT-TYPE
    SYNTAX   DisplayString (SIZE (0..128))
    MAX-ACCESS  read-only
    STATUS  current
    DESCRIPTION
        "SMTP health check name."
    ::= { slbCurAdvhcSmtpEntry 2 }

slbCurAdvhcSmtpDPort OBJECT-TYPE
    SYNTAX  INTEGER (0..65534)
    MAX-ACCESS  read-only
    STATUS  current
    DESCRIPTION
        "SMTP health check destination port."
    ::= { slbCurAdvhcSmtpEntry 3 }

slbCurAdvhcSmtpIPVer OBJECT-TYPE
    SYNTAX  SlbAdvhcIPVer
    MAX-ACCESS  read-only
    STATUS  current
    DESCRIPTION
        "SMTP health check destination IP version."
    ::= { slbCurAdvhcSmtpEntry 4 }

slbCurAdvhcSmtpHostName OBJECT-TYPE
    SYNTAX   DisplayString (SIZE (0..128))
    MAX-ACCESS  read-only
    STATUS  current
    DESCRIPTION
        "SMTP health check destination hostname."
    ::= { slbCurAdvhcSmtpEntry 5 }

slbCurAdvhcSmtpTransparent OBJECT-TYPE
    SYNTAX  SlbAdvhcEnaDis
    MAX-ACCESS  read-only
    STATUS  current
    DESCRIPTION
        "SMTP health check transparent flag."
    ::= { slbCurAdvhcSmtpEntry 6 }

slbCurAdvhcSmtpInterval OBJECT-TYPE
    SYNTAX  INTEGER (1..600)
    MAX-ACCESS  read-only
    STATUS  current
    DESCRIPTION
        "SMTP health check interval."
    ::= { slbCurAdvhcSmtpEntry 7 }

slbCurAdvhcSmtpRetries OBJECT-TYPE
    SYNTAX  INTEGER (1..63)
    MAX-ACCESS  read-only
    STATUS  current
    DESCRIPTION
        "SMTP health check retries counter."
    ::= { slbCurAdvhcSmtpEntry 8 }

slbCurAdvhcSmtpRestoreRetries OBJECT-TYPE
    SYNTAX  INTEGER (1..63)
    MAX-ACCESS  read-only
    STATUS  current
    DESCRIPTION
        "SMTP health check retries when in down state counter."
    ::= { slbCurAdvhcSmtpEntry 9 }

slbCurAdvhcSmtpTimeout OBJECT-TYPE
    SYNTAX  INTEGER (1..63)
    MAX-ACCESS  read-only
    STATUS  current
    DESCRIPTION
        "SMTP health check timeout."
    ::= { slbCurAdvhcSmtpEntry 10 }

slbCurAdvhcSmtpOverflow OBJECT-TYPE
    SYNTAX  INTEGER (0..600)
    MAX-ACCESS  read-only
    STATUS  current
    DESCRIPTION
        "SMTP health check overflow flag."
    ::= { slbCurAdvhcSmtpEntry 11 }

slbCurAdvhcSmtpDownInterval OBJECT-TYPE
    SYNTAX  INTEGER (0..600)
    MAX-ACCESS  read-only
    STATUS  current
    DESCRIPTION
        "SMTP health check interval when in the down state."
    ::= { slbCurAdvhcSmtpEntry 12 }

slbCurAdvhcSmtpInvert OBJECT-TYPE
    SYNTAX  SlbAdvhcEnaDis
    MAX-ACCESS  read-only
    STATUS  current
    DESCRIPTION
        "SMTP health check invert flag."
    ::= { slbCurAdvhcSmtpEntry 13 }

slbCurAdvhcSmtpUserName OBJECT-TYPE
    SYNTAX   DisplayString (SIZE (0..32))
    MAX-ACCESS  read-only
    STATUS  current
    DESCRIPTION
        "SMTP health check username."
    ::= { slbCurAdvhcSmtpEntry 14 }


slbNewAdvhcSmtpTable  OBJECT-TYPE
    SYNTAX  SEQUENCE OF SlbNewAdvhcSmtpEntry
    MAX-ACCESS  not-accessible
    STATUS  current
    DESCRIPTION
        "Note:This mib is not supported on VX instance of Virtualization."
    ::= { advhcCfg 28 }

slbNewAdvhcSmtpEntry OBJECT-TYPE
    SYNTAX  SlbNewAdvhcSmtpEntry
    MAX-ACCESS  not-accessible
    STATUS  current
    DESCRIPTION
        "."
    INDEX   { slbNewAdvhcSmtpID }
    ::= { slbNewAdvhcSmtpTable 1 }

SlbNewAdvhcSmtpEntry ::= SEQUENCE {
    slbNewAdvhcSmtpID               DisplayString,
    slbNewAdvhcSmtpName             DisplayString,
    slbNewAdvhcSmtpDPort            INTEGER,
    slbNewAdvhcSmtpIPVer            SlbAdvhcIPVer,
    slbNewAdvhcSmtpHostName         DisplayString,
    slbNewAdvhcSmtpTransparent      SlbAdvhcEnaDis,
    slbNewAdvhcSmtpInterval         INTEGER,
    slbNewAdvhcSmtpRetries          INTEGER,
    slbNewAdvhcSmtpRestoreRetries   INTEGER,
    slbNewAdvhcSmtpTimeout          INTEGER,
    slbNewAdvhcSmtpOverflow         INTEGER,
    slbNewAdvhcSmtpDownInterval     INTEGER,
    slbNewAdvhcSmtpInvert           SlbAdvhcEnaDis,
    slbNewAdvhcSmtpUserName         DisplayString,
    slbNewAdvhcSmtpCopy             DisplayString,
    slbNewAdvhcSmtpDelete           SlbAdvhcDelete
    }

slbNewAdvhcSmtpID OBJECT-TYPE
    SYNTAX   DisplayString (SIZE (0..128))
    MAX-ACCESS  read-only
    STATUS  current
    DESCRIPTION
        "SMTP health check id."
    ::= { slbNewAdvhcSmtpEntry 1 }

slbNewAdvhcSmtpName OBJECT-TYPE
    SYNTAX   DisplayString (SIZE (0..128))
    MAX-ACCESS  read-write
    STATUS  current
    DESCRIPTION
        "SMTP health check name."
    ::= { slbNewAdvhcSmtpEntry 2 }

slbNewAdvhcSmtpDPort OBJECT-TYPE
    SYNTAX  INTEGER (0..65534)
    MAX-ACCESS  read-write
    STATUS  current
    DESCRIPTION
        "SMTP health check destination port."
    ::= { slbNewAdvhcSmtpEntry 3 }

slbNewAdvhcSmtpIPVer OBJECT-TYPE
    SYNTAX  SlbAdvhcIPVer
    MAX-ACCESS  read-write
    STATUS  current
    DESCRIPTION
        "SMTP health check destination IP version."
    ::= { slbNewAdvhcSmtpEntry 4 }

slbNewAdvhcSmtpHostName OBJECT-TYPE
    SYNTAX   DisplayString (SIZE (0..128))
    MAX-ACCESS  read-write
    STATUS  current
    DESCRIPTION
        "SMTP health check destination hostname."
    ::= { slbNewAdvhcSmtpEntry 5 }

slbNewAdvhcSmtpTransparent OBJECT-TYPE
    SYNTAX  SlbAdvhcEnaDis
    MAX-ACCESS  read-write
    STATUS  current
    DESCRIPTION
        "SMTP health check transparent flag."
    ::= { slbNewAdvhcSmtpEntry 6 }

slbNewAdvhcSmtpInterval OBJECT-TYPE
    SYNTAX  INTEGER (1..600)
    MAX-ACCESS  read-write
    STATUS  current
    DESCRIPTION
        "SMTP health check interval."
    ::= { slbNewAdvhcSmtpEntry 7 }

slbNewAdvhcSmtpRetries OBJECT-TYPE
    SYNTAX  INTEGER (1..63)
    MAX-ACCESS  read-write
    STATUS  current
    DESCRIPTION
        "SMTP health check retries counter."
    ::= { slbNewAdvhcSmtpEntry 8 }

slbNewAdvhcSmtpRestoreRetries OBJECT-TYPE
    SYNTAX  INTEGER (1..63)
    MAX-ACCESS  read-write
    STATUS  current
    DESCRIPTION
        "SMTP health check retries when in down state counter."
    ::= { slbNewAdvhcSmtpEntry 9 }

slbNewAdvhcSmtpTimeout OBJECT-TYPE
    SYNTAX  INTEGER (1..63)
    MAX-ACCESS  read-write
    STATUS  current
    DESCRIPTION
        "SMTP health check timeout."
    ::= { slbNewAdvhcSmtpEntry 10 }

slbNewAdvhcSmtpOverflow OBJECT-TYPE
    SYNTAX  INTEGER (0..600)
    MAX-ACCESS  read-write
    STATUS  current
    DESCRIPTION
        "SMTP health check overflow flag."
    ::= { slbNewAdvhcSmtpEntry 11 }

slbNewAdvhcSmtpDownInterval OBJECT-TYPE
    SYNTAX  INTEGER (0..600)
    MAX-ACCESS  read-write
    STATUS  current
    DESCRIPTION
        "SMTP health check interval when in the down state."
    ::= { slbNewAdvhcSmtpEntry 12 }

slbNewAdvhcSmtpInvert OBJECT-TYPE
    SYNTAX  SlbAdvhcEnaDis
    MAX-ACCESS  read-write
    STATUS  current
    DESCRIPTION
        "SMTP health check invert flag."
    ::= { slbNewAdvhcSmtpEntry 13 }

slbNewAdvhcSmtpUserName OBJECT-TYPE
    SYNTAX   DisplayString (SIZE (0..32))
    MAX-ACCESS  read-write
    STATUS  current
    DESCRIPTION
        "SMTP health check username."
    ::= { slbNewAdvhcSmtpEntry 14 }

slbNewAdvhcSmtpCopy OBJECT-TYPE
    SYNTAX   DisplayString (SIZE (0..128))
    MAX-ACCESS  read-write
    STATUS  current
    DESCRIPTION
        "SMTP health check copy flag."
    ::= { slbNewAdvhcSmtpEntry 16 }

slbNewAdvhcSmtpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcSmtpEntry 17 }


-- Advance Health Check SNMP
----------------------------

slbCurAdvhcSnmpTable  OBJECT-TYPE
    SYNTAX  SEQUENCE OF SlbCurAdvhcSnmpEntry
    MAX-ACCESS  not-accessible
    STATUS  current
    DESCRIPTION
        "Note:This mib is not supported on VX instance of Virtualization."
    ::= { advhcCfg 29 }

slbCurAdvhcSnmpEntry OBJECT-TYPE
    SYNTAX  SlbCurAdvhcSnmpEntry
    MAX-ACCESS  not-accessible
    STATUS  current
    DESCRIPTION
        "."
    INDEX   { slbCurAdvhcSnmpID }
    ::= { slbCurAdvhcSnmpTable 1 }

SlbCurAdvhcSnmpEntry ::= SEQUENCE {
    slbCurAdvhcSnmpID               DisplayString,
    slbCurAdvhcSnmpName             DisplayString,
    slbCurAdvhcSnmpDPort            INTEGER,
    slbCurAdvhcSnmpIPVer            SlbAdvhcIPVer,
    slbCurAdvhcSnmpHostName         DisplayString,
    slbCurAdvhcSnmpTransparent      SlbAdvhcEnaDis,
    slbCurAdvhcSnmpInterval         INTEGER,
    slbCurAdvhcSnmpRetries          INTEGER,
    slbCurAdvhcSnmpRestoreRetries   INTEGER,
    slbCurAdvhcSnmpTimeout          INTEGER,
    slbCurAdvhcSnmpOverflow         INTEGER,
    slbCurAdvhcSnmpDownInterval     INTEGER,
    slbCurAdvhcSnmpInvert           SlbAdvhcEnaDis,
    slbCurAdvhcSnmpOid              OCTET STRING,
    slbCurAdvhcSnmpCommunity        OCTET STRING,
    slbCurAdvhcSnmpType             INTEGER,
    slbCurAdvhcSnmpMinValue         INTEGER,
    slbCurAdvhcSnmpMaxValue         INTEGER,
    slbCurAdvhcSnmpReceiveString    OCTET STRING,
    slbCurAdvhcSnmpReadjustWeight   INTEGER,
    slbCurAdvhcSnmpOverloadMinValue INTEGER,
    slbCurAdvhcSnmpOverloadMaxValue INTEGER,
    slbCurAdvhcSnmpOverloadString   OCTET STRING
    }

slbCurAdvhcSnmpID OBJECT-TYPE
    SYNTAX   DisplayString (SIZE (0..128))
    MAX-ACCESS  read-only
    STATUS  current
    DESCRIPTION
        "SNMP Health check id."
    ::= { slbCurAdvhcSnmpEntry 1 }

slbCurAdvhcSnmpName OBJECT-TYPE
    SYNTAX   DisplayString (SIZE (0..128))
    MAX-ACCESS  read-only
    STATUS  current
    DESCRIPTION
        "SNMP Health check name."
    ::= { slbCurAdvhcSnmpEntry 2 }

slbCurAdvhcSnmpDPort OBJECT-TYPE
    SYNTAX  INTEGER (0..65534)
    MAX-ACCESS  read-only
    STATUS  current
    DESCRIPTION
        "SNMP Health check destination port."
    ::= { slbCurAdvhcSnmpEntry 3 }

slbCurAdvhcSnmpIPVer OBJECT-TYPE
    SYNTAX  SlbAdvhcIPVer
    MAX-ACCESS  read-only
    STATUS  current
    DESCRIPTION
        "SNMP Health check destination IP version."
    ::= { slbCurAdvhcSnmpEntry 4 }

slbCurAdvhcSnmpHostName OBJECT-TYPE
    SYNTAX   DisplayString (SIZE (0..128))
    MAX-ACCESS  read-only
    STATUS  current
    DESCRIPTION
        "SNMP Health check destination hostname."
    ::= { slbCurAdvhcSnmpEntry 5 }

slbCurAdvhcSnmpTransparent OBJECT-TYPE
    SYNTAX  SlbAdvhcEnaDis
    MAX-ACCESS  read-only
    STATUS  current
    DESCRIPTION
        "SNMP Health check transparent flag."
    ::= { slbCurAdvhcSnmpEntry 6 }

slbCurAdvhcSnmpInterval OBJECT-TYPE
    SYNTAX  INTEGER (1..600)
    MAX-ACCESS  read-only
    STATUS  current
    DESCRIPTION
        "SNMP Health check interval."
    ::= { slbCurAdvhcSnmpEntry 7 }

slbCurAdvhcSnmpRetries OBJECT-TYPE
    SYNTAX  INTEGER (1..63)
    MAX-ACCESS  read-only
    STATUS  current
    DESCRIPTION
        "SNMP Health check retries counter."
    ::= { slbCurAdvhcSnmpEntry 8 }

slbCurAdvhcSnmpRestoreRetries OBJECT-TYPE
    SYNTAX  INTEGER (1..63)
    MAX-ACCESS  read-only
    STATUS  current
    DESCRIPTION
        "SNMP Health check retries counter in the down state."
    ::= { slbCurAdvhcSnmpEntry 9 }

slbCurAdvhcSnmpTimeout OBJECT-TYPE
    SYNTAX  INTEGER (1..63)
    MAX-ACCESS  read-only
    STATUS  current
    DESCRIPTION
        "SNMP Health check timeout."
    ::= { slbCurAdvhcSnmpEntry 10 }

slbCurAdvhcSnmpOverflow OBJECT-TYPE
    SYNTAX  INTEGER (0..600)
    MAX-ACCESS  read-only
    STATUS  current
    DESCRIPTION
        "SNMP Health check overflow flag."
    ::= { slbCurAdvhcSnmpEntry 11 }

slbCurAdvhcSnmpDownInterval OBJECT-TYPE
    SYNTAX  INTEGER (0..600)
    MAX-ACCESS  read-only
    STATUS  current
    DESCRIPTION
        "SNMP Health check interval when in the down state."
    ::= { slbCurAdvhcSnmpEntry 12 }

slbCurAdvhcSnmpInvert OBJECT-TYPE
    SYNTAX  SlbAdvhcEnaDis
    MAX-ACCESS  read-only
    STATUS  current
    DESCRIPTION
        "SNMP Health check invert flag."
    ::= { slbCurAdvhcSnmpEntry 13 }

slbCurAdvhcSnmpOid OBJECT-TYPE
    SYNTAX   OCTET STRING (SIZE (0..256))
    MAX-ACCESS  read-only
    STATUS  current
    DESCRIPTION
        "SNMP Health check OID."
    ::= { slbCurAdvhcSnmpEntry 14 }

slbCurAdvhcSnmpCommunity OBJECT-TYPE
    SYNTAX   OCTET STRING (SIZE (0..32))
    MAX-ACCESS  read-only
    STATUS  current
    DESCRIPTION
        "SNMP Health check community string."
    ::= { slbCurAdvhcSnmpEntry 15 }

slbCurAdvhcSnmpType OBJECT-TYPE
    SYNTAX  INTEGER { integer(1), string(2), unsupported(2147483647) }
    MAX-ACCESS  read-only
    STATUS  current
    DESCRIPTION
        "SNMP Health check OID type."
    ::= { slbCurAdvhcSnmpEntry 16 }

slbCurAdvhcSnmpMinValue OBJECT-TYPE
    SYNTAX  INTEGER
    MAX-ACCESS  read-only
    STATUS  current
    DESCRIPTION
        "SNMP Health check OID variable minimum value."
    ::= { slbCurAdvhcSnmpEntry 17 }

slbCurAdvhcSnmpMaxValue OBJECT-TYPE
    SYNTAX  INTEGER
    MAX-ACCESS  read-only
    STATUS  current
    DESCRIPTION
        "SNMP Health check OID maximum value."
    ::= { slbCurAdvhcSnmpEntry 18 }

slbCurAdvhcSnmpReceiveString OBJECT-TYPE
    SYNTAX   OCTET STRING (SIZE (0..64))
    MAX-ACCESS  read-only
    STATUS  current
    DESCRIPTION
        "SNMP Health check receive string."
    ::= { slbCurAdvhcSnmpEntry 19 }

slbCurAdvhcSnmpReadjustWeight OBJECT-TYPE
    SYNTAX  INTEGER {
        enabled(1),
        disabled(2),
        inverted(3),
        unsupported(2147483647)
        }
    MAX-ACCESS  read-only
    STATUS  current
    DESCRIPTION
        "Enabled: value received in SNMP health check response is used as real server weight.
         Disabled: value received in SNMP health check response is not used as real server weight.
         Inverted: value received in SNMP health check response is subtracted from 100 (100 - value) is used as real server weight"
    ::= { slbCurAdvhcSnmpEntry 20 }

slbCurAdvhcSnmpOverloadMinValue OBJECT-TYPE
    SYNTAX  INTEGER
    MAX-ACCESS  read-only
    STATUS  current
    DESCRIPTION
        "."
    ::= { slbCurAdvhcSnmpEntry 21 }

slbCurAdvhcSnmpOverloadMaxValue OBJECT-TYPE
    SYNTAX  INTEGER
    MAX-ACCESS  read-only
    STATUS  current
    DESCRIPTION
        "."
    ::= { slbCurAdvhcSnmpEntry 22 }

slbCurAdvhcSnmpOverloadString OBJECT-TYPE
    SYNTAX   OCTET STRING (SIZE (0..64))
    MAX-ACCESS  read-only
    STATUS  current
    DESCRIPTION
        "."
    ::= { slbCurAdvhcSnmpEntry 23 }

slbNewAdvhcSnmpTable  OBJECT-TYPE
    SYNTAX  SEQUENCE OF SlbNewAdvhcSnmpEntry
    MAX-ACCESS  not-accessible
    STATUS  current
    DESCRIPTION
        "Note:This mib is not supported on VX instance of Virtualization."
    ::= { advhcCfg 30 }

slbNewAdvhcSnmpEntry OBJECT-TYPE
    SYNTAX  SlbNewAdvhcSnmpEntry
    MAX-ACCESS  not-accessible
    STATUS  current
    DESCRIPTION
        "."
    INDEX   { slbNewAdvhcSnmpID }
    ::= { slbNewAdvhcSnmpTable 1 }

SlbNewAdvhcSnmpEntry ::= SEQUENCE {
    slbNewAdvhcSnmpID               DisplayString,
    slbNewAdvhcSnmpName             DisplayString,
    slbNewAdvhcSnmpDPort            INTEGER,
    slbNewAdvhcSnmpIPVer            SlbAdvhcIPVer,
    slbNewAdvhcSnmpHostName         DisplayString,
    slbNewAdvhcSnmpTransparent      SlbAdvhcEnaDis,
    slbNewAdvhcSnmpInterval         INTEGER,
    slbNewAdvhcSnmpRetries          INTEGER,
    slbNewAdvhcSnmpRestoreRetries   INTEGER,
    slbNewAdvhcSnmpTimeout          INTEGER,
    slbNewAdvhcSnmpOverflow         INTEGER,
    slbNewAdvhcSnmpDownInterval     INTEGER,
    slbNewAdvhcSnmpInvert           SlbAdvhcEnaDis,
    slbNewAdvhcSnmpOid              DisplayString,
    slbNewAdvhcSnmpCommunity        DisplayString,
    slbNewAdvhcSnmpType             INTEGER,
    slbNewAdvhcSnmpMinValue         INTEGER,
    slbNewAdvhcSnmpMaxValue         INTEGER,
    slbNewAdvhcSnmpReceiveString    DisplayString,
    slbNewAdvhcSnmpReadjustWeight   INTEGER,
    slbNewAdvhcSnmpOverloadMinValue INTEGER,
    slbNewAdvhcSnmpOverloadMaxValue INTEGER,
    slbNewAdvhcSnmpOverloadString   DisplayString,
    slbNewAdvhcSnmpCopy             DisplayString,
    slbNewAdvhcSnmpDelete           SlbAdvhcDelete
    }

slbNewAdvhcSnmpID OBJECT-TYPE
    SYNTAX   DisplayString (SIZE (0..128))
    MAX-ACCESS  read-only
    STATUS  current
    DESCRIPTION
        "SNMP Health check id."
    ::= { slbNewAdvhcSnmpEntry 1 }

slbNewAdvhcSnmpName OBJECT-TYPE
    SYNTAX   DisplayString (SIZE (0..128))
    MAX-ACCESS  read-write
    STATUS  current
    DESCRIPTION
        "SNMP Health check name."
    ::= { slbNewAdvhcSnmpEntry 2 }

slbNewAdvhcSnmpDPort OBJECT-TYPE
    SYNTAX  INTEGER (0..65534)
    MAX-ACCESS  read-write
    STATUS  current
    DESCRIPTION
        "SNMP Health check destination port."
    ::= { slbNewAdvhcSnmpEntry 3 }

slbNewAdvhcSnmpIPVer OBJECT-TYPE
    SYNTAX  SlbAdvhcIPVer
    MAX-ACCESS  read-write
    STATUS  current
    DESCRIPTION
        "SNMP Health check destination IP version."
    ::= { slbNewAdvhcSnmpEntry 4 }

slbNewAdvhcSnmpHostName OBJECT-TYPE
    SYNTAX   DisplayString (SIZE (0..128))
    MAX-ACCESS  read-write
    STATUS  current
    DESCRIPTION
        "SNMP Health check destination hostname."
    ::= { slbNewAdvhcSnmpEntry 5 }

slbNewAdvhcSnmpTransparent OBJECT-TYPE
    SYNTAX  SlbAdvhcEnaDis
    MAX-ACCESS  read-write
    STATUS  current
    DESCRIPTION
        "SNMP Health check transparent flag."
    ::= { slbNewAdvhcSnmpEntry 6 }

slbNewAdvhcSnmpInterval OBJECT-TYPE
    SYNTAX  INTEGER (1..600)
    MAX-ACCESS  read-write
    STATUS  current
    DESCRIPTION
        "SNMP Health check interval."
    ::= { slbNewAdvhcSnmpEntry 7 }

slbNewAdvhcSnmpRetries OBJECT-TYPE
    SYNTAX  INTEGER (1..63)
    MAX-ACCESS  read-write
    STATUS  current
    DESCRIPTION
        "SNMP Health check retries counter."
    ::= { slbNewAdvhcSnmpEntry 8 }

slbNewAdvhcSnmpRestoreRetries OBJECT-TYPE
    SYNTAX  INTEGER (1..63)
    MAX-ACCESS  read-write
    STATUS  current
    DESCRIPTION
        "SNMP Health check retries counter in the down state."
    ::= { slbNewAdvhcSnmpEntry 9 }

slbNewAdvhcSnmpTimeout OBJECT-TYPE
    SYNTAX  INTEGER (1..63)
    MAX-ACCESS  read-write
    STATUS  current
    DESCRIPTION
        "SNMP Health check timeout."
    ::= { slbNewAdvhcSnmpEntry 10 }

slbNewAdvhcSnmpOverflow OBJECT-TYPE
    SYNTAX  INTEGER (0..600)
    MAX-ACCESS  read-write
    STATUS  current
    DESCRIPTION
        "SNMP Health check overflow flag."
    ::= { slbNewAdvhcSnmpEntry 11 }

slbNewAdvhcSnmpDownInterval OBJECT-TYPE
    SYNTAX  INTEGER (0..600)
    MAX-ACCESS  read-write
    STATUS  current
    DESCRIPTION
        "SNMP Health check interval when in the down state."
    ::= { slbNewAdvhcSnmpEntry 12 }

slbNewAdvhcSnmpInvert OBJECT-TYPE
    SYNTAX  SlbAdvhcEnaDis
    MAX-ACCESS  read-write
    STATUS  current
    DESCRIPTION
        "SNMP Health check invert flag."
    ::= { slbNewAdvhcSnmpEntry 13 }


slbNewAdvhcSnmpOid OBJECT-TYPE
    SYNTAX  DisplayString (SIZE (0..255))
    MAX-ACCESS  read-write
    STATUS  current
    DESCRIPTION
        "SNMP Health check OID."
    ::= { slbNewAdvhcSnmpEntry 14 }

slbNewAdvhcSnmpCommunity OBJECT-TYPE
    SYNTAX   DisplayString (SIZE (0..32))
    MAX-ACCESS  read-write
    STATUS  current
    DESCRIPTION
        "SNMP Health check community string."
    ::= { slbNewAdvhcSnmpEntry 15 }

slbNewAdvhcSnmpType OBJECT-TYPE
    SYNTAX  INTEGER { integer(1), string(2), unsupported(2147483647) }
    MAX-ACCESS  read-write
    STATUS  current
    DESCRIPTION
        "SNMP Health check OID type."
    ::= { slbNewAdvhcSnmpEntry 16 }

slbNewAdvhcSnmpMinValue OBJECT-TYPE
    SYNTAX  INTEGER
    MAX-ACCESS  read-write
    STATUS  current
    DESCRIPTION
        "SNMP Health check OID variable minimum value."
    ::= { slbNewAdvhcSnmpEntry 17 }

slbNewAdvhcSnmpMaxValue OBJECT-TYPE
    SYNTAX  INTEGER
    MAX-ACCESS  read-write
    STATUS  current
    DESCRIPTION
        "SNMP Health check OID maximum value."
    ::= { slbNewAdvhcSnmpEntry 18 }

slbNewAdvhcSnmpReceiveString OBJECT-TYPE
    SYNTAX   DisplayString (SIZE (0..64))
    MAX-ACCESS  read-write
    STATUS  current
    DESCRIPTION
        "SNMP Health check receive string."
    ::= { slbNewAdvhcSnmpEntry 19 }

slbNewAdvhcSnmpReadjustWeight OBJECT-TYPE
    SYNTAX  INTEGER {
        enabled(1),
        disabled(2),
        inverted(3),
        unsupported(2147483647)
        }
    MAX-ACCESS  read-write
    STATUS  current
    DESCRIPTION
        "Enabled: value received in SNMP health check response is used as real server weight.
         Disabled: value received in SNMP health check response is not used as real server weight.
         Inverted: value received in SNMP health check response is subtracted from 100 (100 - value) is used as real server weight"
    ::= { slbNewAdvhcSnmpEntry 20 }

slbNewAdvhcSnmpCopy OBJECT-TYPE
    SYNTAX   DisplayString (SIZE (0..128))
    MAX-ACCESS  read-write
    STATUS  current
    DESCRIPTION
        "SNMP Health check copy indicator."
    ::= { slbNewAdvhcSnmpEntry 21 }

slbNewAdvhcSnmpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcSnmpEntry 22 }


slbNewAdvhcSnmpOverloadMinValue OBJECT-TYPE
    SYNTAX  INTEGER
    MAX-ACCESS  read-write
    STATUS  current
    DESCRIPTION
        "Oveload minimum value."
    ::= { slbNewAdvhcSnmpEntry 23 }

slbNewAdvhcSnmpOverloadMaxValue OBJECT-TYPE
    SYNTAX  INTEGER
    MAX-ACCESS  read-write
    STATUS  current
    DESCRIPTION
        "Oveload maximum value."
    ::= { slbNewAdvhcSnmpEntry 24 }

slbNewAdvhcSnmpOverloadString OBJECT-TYPE
    SYNTAX   DisplayString (SIZE (0..64))
    MAX-ACCESS  read-write
    STATUS  current
    DESCRIPTION
        "expected response for server overload."
    ::= { slbNewAdvhcSnmpEntry 25 }


-- Advance Health Check SSLHello
--------------------------------

slbCurAdvhcSslHelloTable  OBJECT-TYPE
    SYNTAX  SEQUENCE OF SlbCurAdvhcSslHelloEntry
    MAX-ACCESS  not-accessible
    STATUS  current
    DESCRIPTION
        "Note:This mib is not supported on VX instance of Virtualization."
    ::= { advhcCfg 31 }

slbCurAdvhcSslHelloEntry OBJECT-TYPE
    SYNTAX  SlbCurAdvhcSslHelloEntry
    MAX-ACCESS  not-accessible
    STATUS  current
    DESCRIPTION
        "."
    INDEX   { slbCurAdvhcSslHelloID }
    ::= { slbCurAdvhcSslHelloTable 1 }

SlbCurAdvhcSslHelloEntry ::= SEQUENCE {
    slbCurAdvhcSslHelloID               DisplayString,
    slbCurAdvhcSslHelloName             DisplayString,
    slbCurAdvhcSslHelloDPort            INTEGER,
    slbCurAdvhcSslHelloIPVer            SlbAdvhcIPVer,
    slbCurAdvhcSslHelloHostName         DisplayString,
    slbCurAdvhcSslHelloTransparent      SlbAdvhcEnaDis,
    slbCurAdvhcSslHelloInterval         INTEGER,
    slbCurAdvhcSslHelloRetries          INTEGER,
    slbCurAdvhcSslHelloRestoreRetries   INTEGER,
    slbCurAdvhcSslHelloTimeout          INTEGER,
    slbCurAdvhcSslHelloOverflow         INTEGER,
    slbCurAdvhcSslHelloDownInterval     INTEGER,
    slbCurAdvhcSslHelloInvert           SlbAdvhcEnaDis,
    slbCurAdvhcSslHelloSslVersion       INTEGER,
    slbCurAdvhcSslHelloCipherName       INTEGER,
    slbCurAdvhcSslHelloCipherUserdef    RadwareLongDisplayString
    }

slbCurAdvhcSslHelloID OBJECT-TYPE
    SYNTAX   DisplayString (SIZE (0..128))
    MAX-ACCESS  read-only
    STATUS  current
    DESCRIPTION
        "SSL Hello Health check id."
    ::= { slbCurAdvhcSslHelloEntry 1 }

slbCurAdvhcSslHelloName OBJECT-TYPE
    SYNTAX   DisplayString (SIZE (0..128))
    MAX-ACCESS  read-only
    STATUS  current
    DESCRIPTION
        "SSL Hello Health check name."
    ::= { slbCurAdvhcSslHelloEntry 2 }

slbCurAdvhcSslHelloDPort OBJECT-TYPE
    SYNTAX  INTEGER (0..65534)
    MAX-ACCESS  read-only
    STATUS  current
    DESCRIPTION
        "SSL Hello Health check destination port."
    ::= { slbCurAdvhcSslHelloEntry 3 }

slbCurAdvhcSslHelloIPVer OBJECT-TYPE
    SYNTAX  SlbAdvhcIPVer
    MAX-ACCESS  read-only
    STATUS  current
    DESCRIPTION
        "SSL Hello Health check destination IP version."
    ::= { slbCurAdvhcSslHelloEntry 4 }

slbCurAdvhcSslHelloHostName OBJECT-TYPE
    SYNTAX   DisplayString (SIZE (0..128))
    MAX-ACCESS  read-only
    STATUS  current
    DESCRIPTION
        "SSL Hello Health check destination hostname."
    ::= { slbCurAdvhcSslHelloEntry 5 }

slbCurAdvhcSslHelloTransparent OBJECT-TYPE
    SYNTAX  SlbAdvhcEnaDis
    MAX-ACCESS  read-only
    STATUS  current
    DESCRIPTION
        "SSL Hello Health check transparent flag."
    ::= { slbCurAdvhcSslHelloEntry 6 }

slbCurAdvhcSslHelloInterval OBJECT-TYPE
    SYNTAX  INTEGER (1..600)
    MAX-ACCESS  read-only
    STATUS  current
    DESCRIPTION
        "SSL Hello Health check interval."
    ::= { slbCurAdvhcSslHelloEntry 7 }

slbCurAdvhcSslHelloRetries OBJECT-TYPE
    SYNTAX  INTEGER (1..63)
    MAX-ACCESS  read-only
    STATUS  current
    DESCRIPTION
        "SSL Hello Health check retries counter."
    ::= { slbCurAdvhcSslHelloEntry 8 }

slbCurAdvhcSslHelloRestoreRetries OBJECT-TYPE
    SYNTAX  INTEGER (1..63)
    MAX-ACCESS  read-only
    STATUS  current
    DESCRIPTION
        "SSL Hello Health check retries counter."
    ::= { slbCurAdvhcSslHelloEntry 9 }

slbCurAdvhcSslHelloTimeout OBJECT-TYPE
    SYNTAX  INTEGER (1..63)
    MAX-ACCESS  read-only
    STATUS  current
    DESCRIPTION
        "SSL Hello Health check timeout."
    ::= { slbCurAdvhcSslHelloEntry 10 }

slbCurAdvhcSslHelloOverflow OBJECT-TYPE
    SYNTAX  INTEGER (0..600)
    MAX-ACCESS  read-only
    STATUS  current
    DESCRIPTION
        "SSL Hello Health check overflow flag."
    ::= { slbCurAdvhcSslHelloEntry 11 }

slbCurAdvhcSslHelloDownInterval OBJECT-TYPE
    SYNTAX  INTEGER (0..600)
    MAX-ACCESS  read-only
    STATUS  current
    DESCRIPTION
        "SSL Hello Health check interval in the down state."
    ::= { slbCurAdvhcSslHelloEntry 12 }

slbCurAdvhcSslHelloInvert OBJECT-TYPE
    SYNTAX  SlbAdvhcEnaDis
    MAX-ACCESS  read-only
    STATUS  current
    DESCRIPTION
        "SSL Hello Health check invert flag."
    ::= { slbCurAdvhcSslHelloEntry 13 }

slbCurAdvhcSslHelloSslVersion OBJECT-TYPE
    SYNTAX  INTEGER { ver2(2), ver3(3), tls(4), unsupported(2147483647) }
    MAX-ACCESS  read-only
    STATUS  current
    DESCRIPTION
        "SSL Hello Health check SSL version field."
    ::= { slbCurAdvhcSslHelloEntry 14 }

slbCurAdvhcSslHelloCipherName OBJECT-TYPE
    SYNTAX  INTEGER{
        userDefined(1),
        low(2),
        medium(3),
        high(4),
        unsupported(2147483647)
        }
    MAX-ACCESS  read-only
    STATUS  current
    DESCRIPTION
        "Cipher name for SSLHELLO HC Context."
    ::= { slbCurAdvhcSslHelloEntry 15 }

slbCurAdvhcSslHelloCipherUserdef OBJECT-TYPE
    SYNTAX RadwareLongDisplayString (SIZE (0..1024))
    MAX-ACCESS  read-only
    STATUS  current
    DESCRIPTION
        "Cipher-suite allowed for SSLHELLO HC Context."
    ::= { slbCurAdvhcSslHelloEntry 16 }

slbNewAdvhcSslHelloTable  OBJECT-TYPE
    SYNTAX  SEQUENCE OF SlbNewAdvhcSslHelloEntry
    MAX-ACCESS  not-accessible
    STATUS  current
    DESCRIPTION
        "Note:This mib is not supported on VX instance of Virtualization."
    ::= { advhcCfg 32 }

slbNewAdvhcSslHelloEntry OBJECT-TYPE
    SYNTAX  SlbNewAdvhcSslHelloEntry
    MAX-ACCESS  not-accessible
    STATUS  current
    DESCRIPTION
        "."
    INDEX   { slbNewAdvhcSslHelloID }
    ::= { slbNewAdvhcSslHelloTable 1 }

SlbNewAdvhcSslHelloEntry ::= SEQUENCE {
    slbNewAdvhcSslHelloID               DisplayString,
    slbNewAdvhcSslHelloName             DisplayString,
    slbNewAdvhcSslHelloDPort            INTEGER,
    slbNewAdvhcSslHelloIPVer            SlbAdvhcIPVer,
    slbNewAdvhcSslHelloHostName         DisplayString,
    slbNewAdvhcSslHelloTransparent      SlbAdvhcEnaDis,
    slbNewAdvhcSslHelloInterval         INTEGER,
    slbNewAdvhcSslHelloRetries          INTEGER,
    slbNewAdvhcSslHelloRestoreRetries   INTEGER,
    slbNewAdvhcSslHelloTimeout          INTEGER,
    slbNewAdvhcSslHelloOverflow         INTEGER,
    slbNewAdvhcSslHelloDownInterval     INTEGER,
    slbNewAdvhcSslHelloInvert           SlbAdvhcEnaDis,
    slbNewAdvhcSslHelloSslVersion       INTEGER,
    slbNewAdvhcSslHelloCopy             DisplayString,
    slbNewAdvhcSslHelloDelete           SlbAdvhcDelete,
    slbNewAdvhcSslHelloCipherName       INTEGER,
    slbNewAdvhcSslHelloCipherUserdef    RadwareLongDisplayString
    }

slbNewAdvhcSslHelloID OBJECT-TYPE
    SYNTAX   DisplayString (SIZE (0..128))
    MAX-ACCESS  read-only
    STATUS  current
    DESCRIPTION
        "SSL Hello Health check id."
    ::= { slbNewAdvhcSslHelloEntry 1 }

slbNewAdvhcSslHelloName OBJECT-TYPE
    SYNTAX   DisplayString (SIZE (0..128))
    MAX-ACCESS  read-write
    STATUS  current
    DESCRIPTION
        "SSL Hello Health check name."
    ::= { slbNewAdvhcSslHelloEntry 2 }

slbNewAdvhcSslHelloDPort OBJECT-TYPE
    SYNTAX  INTEGER (0..65534)
    MAX-ACCESS  read-write
    STATUS  current
    DESCRIPTION
        "SSL Hello Health check destination port."
    ::= { slbNewAdvhcSslHelloEntry 3 }

slbNewAdvhcSslHelloIPVer OBJECT-TYPE
    SYNTAX  SlbAdvhcIPVer
    MAX-ACCESS  read-write
    STATUS  current
    DESCRIPTION
        "SSL Hello Health check destination IP version."
    ::= { slbNewAdvhcSslHelloEntry 4 }

slbNewAdvhcSslHelloHostName OBJECT-TYPE
    SYNTAX   DisplayString (SIZE (0..128))
    MAX-ACCESS  read-write
    STATUS  current
    DESCRIPTION
        "SSL Hello Health check destination hostname."
    ::= { slbNewAdvhcSslHelloEntry 5 }

slbNewAdvhcSslHelloTransparent OBJECT-TYPE
    SYNTAX  SlbAdvhcEnaDis
    MAX-ACCESS  read-write
    STATUS  current
    DESCRIPTION
        "SSL Hello Health check transparent flag."
    ::= { slbNewAdvhcSslHelloEntry 6 }

slbNewAdvhcSslHelloInterval OBJECT-TYPE
    SYNTAX  INTEGER (1..600)
    MAX-ACCESS  read-write
    STATUS  current
    DESCRIPTION
        "SSL Hello Health check interval."
    ::= { slbNewAdvhcSslHelloEntry 7 }

slbNewAdvhcSslHelloRetries OBJECT-TYPE
    SYNTAX  INTEGER (1..63)
    MAX-ACCESS  read-write
    STATUS  current
    DESCRIPTION
        "SSL Hello Health check retries counter."
    ::= { slbNewAdvhcSslHelloEntry 8 }

slbNewAdvhcSslHelloRestoreRetries OBJECT-TYPE
    SYNTAX  INTEGER (1..63)
    MAX-ACCESS  read-write
    STATUS  current
    DESCRIPTION
        "SSL Hello Health check retries counter."
    ::= { slbNewAdvhcSslHelloEntry 9 }

slbNewAdvhcSslHelloTimeout OBJECT-TYPE
    SYNTAX  INTEGER (1..63)
    MAX-ACCESS  read-write
    STATUS  current
    DESCRIPTION
        "SSL Hello Health check timeout."
    ::= { slbNewAdvhcSslHelloEntry 10 }

slbNewAdvhcSslHelloOverflow OBJECT-TYPE
    SYNTAX  INTEGER (0..600)
    MAX-ACCESS  read-write
    STATUS  current
    DESCRIPTION
        "SSL Hello Health check overflow flag."
    ::= { slbNewAdvhcSslHelloEntry 11 }

slbNewAdvhcSslHelloDownInterval OBJECT-TYPE
    SYNTAX  INTEGER (0..600)
    MAX-ACCESS  read-write
    STATUS  current
    DESCRIPTION
        "SSL Hello Health check interval in the down state."
    ::= { slbNewAdvhcSslHelloEntry 12 }

slbNewAdvhcSslHelloInvert OBJECT-TYPE
    SYNTAX  SlbAdvhcEnaDis
    MAX-ACCESS  read-write
    STATUS  current
    DESCRIPTION
        "SSL Hello Health check invert flag."
    ::= { slbNewAdvhcSslHelloEntry 13 }

slbNewAdvhcSslHelloSslVersion OBJECT-TYPE
    SYNTAX  INTEGER { ver2(2), ver3(3), tls(4), unsupported(2147483647) }
    MAX-ACCESS  read-write
    STATUS  current
    DESCRIPTION
        "SSL Hello Health check SSL version field."
    ::= { slbNewAdvhcSslHelloEntry 14 }

slbNewAdvhcSslHelloCopy OBJECT-TYPE
    SYNTAX   DisplayString (SIZE (0..128))
    MAX-ACCESS  read-write
    STATUS  current
    DESCRIPTION
        "SSL Hello Health check copy indicator."
    ::= { slbNewAdvhcSslHelloEntry 15 }

slbNewAdvhcSslHelloDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcSslHelloEntry 16 }

slbNewAdvhcSslHelloCipherName OBJECT-TYPE
    SYNTAX  INTEGER{
        userDefined(1),
        low(2),
        medium(3),
        high(4),
        unsupported(2147483647)
        }
    MAX-ACCESS  read-write
    STATUS  current
    DESCRIPTION
        "Cipher name for SSLHELLO HC Context."
    ::= { slbNewAdvhcSslHelloEntry 17 }

slbNewAdvhcSslHelloCipherUserdef OBJECT-TYPE
    SYNTAX RadwareLongDisplayString  (SIZE (0..1024))
    MAX-ACCESS  read-write
    STATUS  current
    DESCRIPTION
        "Cipher-suite allowed for SSLHELLO HC Context."
    ::= { slbNewAdvhcSslHelloEntry 18 }

-- Advance Health Check TCP
---------------------------

slbCurAdvhcTcpTable  OBJECT-TYPE
    SYNTAX  SEQUENCE OF SlbCurAdvhcTcpEntry
    MAX-ACCESS  not-accessible
    STATUS  current
    DESCRIPTION
        "Note:This mib is not supported on VX instance of Virtualization."
    ::= { advhcCfg 33 }

slbCurAdvhcTcpEntry OBJECT-TYPE
    SYNTAX  SlbCurAdvhcTcpEntry
    MAX-ACCESS  not-accessible
    STATUS  current
    DESCRIPTION
        "."
    INDEX   { slbCurAdvhcTcpID }
    ::= { slbCurAdvhcTcpTable 1 }

SlbCurAdvhcTcpEntry ::= SEQUENCE {
    slbCurAdvhcTcpID               DisplayString,
    slbCurAdvhcTcpName             DisplayString,
    slbCurAdvhcTcpDPort            INTEGER,
    slbCurAdvhcTcpIPVer            SlbAdvhcIPVer,
    slbCurAdvhcTcpHostName         DisplayString,
    slbCurAdvhcTcpTransparent      SlbAdvhcEnaDis,
    slbCurAdvhcTcpInterval         INTEGER,
    slbCurAdvhcTcpRetries          INTEGER,
    slbCurAdvhcTcpRestoreRetries   INTEGER,
    slbCurAdvhcTcpTimeout          INTEGER,
    slbCurAdvhcTcpOverflow         INTEGER,
    slbCurAdvhcTcpDownInterval     INTEGER,
    slbCurAdvhcTcpInvert           SlbAdvhcEnaDis,
    slbCurAdvhcTcpConnTerm         INTEGER,
    slbCurAdvhcTcpAlways           SlbAdvhcEnaDis
    }

slbCurAdvhcTcpID OBJECT-TYPE
    SYNTAX   DisplayString (SIZE (0..128))
    MAX-ACCESS  read-only
    STATUS  current
    DESCRIPTION
        "TCP Health check id."
    ::= { slbCurAdvhcTcpEntry 1 }

slbCurAdvhcTcpName OBJECT-TYPE
    SYNTAX   DisplayString (SIZE (0..128))
    MAX-ACCESS  read-only
    STATUS  current
    DESCRIPTION
        "TCP Health check name."
    ::= { slbCurAdvhcTcpEntry 2 }

slbCurAdvhcTcpDPort OBJECT-TYPE
    SYNTAX  INTEGER (0..65534)
    MAX-ACCESS  read-only
    STATUS  current
    DESCRIPTION
        "TCP Health check destination port."
    ::= { slbCurAdvhcTcpEntry 3 }

slbCurAdvhcTcpIPVer OBJECT-TYPE
    SYNTAX  SlbAdvhcIPVer
    MAX-ACCESS  read-only
    STATUS  current
    DESCRIPTION
        "TCP Health check destination IP version."
    ::= { slbCurAdvhcTcpEntry 4 }

slbCurAdvhcTcpHostName OBJECT-TYPE
    SYNTAX   DisplayString (SIZE (0..128))
    MAX-ACCESS  read-only
    STATUS  current
    DESCRIPTION
        "TCP Health check destination host name."
    ::= { slbCurAdvhcTcpEntry 5 }

slbCurAdvhcTcpTransparent OBJECT-TYPE
    SYNTAX  SlbAdvhcEnaDis
    MAX-ACCESS  read-only
    STATUS  current
    DESCRIPTION
        "TCP Health check transparent flag."
    ::= { slbCurAdvhcTcpEntry 6 }

slbCurAdvhcTcpInterval OBJECT-TYPE
    SYNTAX  INTEGER (1..600)
    MAX-ACCESS  read-only
    STATUS  current
    DESCRIPTION
        "TCP Health check interval."
    ::= { slbCurAdvhcTcpEntry 7 }

slbCurAdvhcTcpRetries OBJECT-TYPE
    SYNTAX  INTEGER (1..63)
    MAX-ACCESS  read-only
    STATUS  current
    DESCRIPTION
        "TCP Health check retries counter."
    ::= { slbCurAdvhcTcpEntry 8 }

slbCurAdvhcTcpRestoreRetries OBJECT-TYPE
    SYNTAX  INTEGER (1..63)
    MAX-ACCESS  read-only
    STATUS  current
    DESCRIPTION
        "TCP Health check retries counter in the down state."
    ::= { slbCurAdvhcTcpEntry 9 }

slbCurAdvhcTcpTimeout OBJECT-TYPE
    SYNTAX  INTEGER (1..63)
    MAX-ACCESS  read-only
    STATUS  current
    DESCRIPTION
        "TCP Health check timeout."
    ::= { slbCurAdvhcTcpEntry 10 }

slbCurAdvhcTcpOverflow OBJECT-TYPE
    SYNTAX  INTEGER (0..600)
    MAX-ACCESS  read-only
    STATUS  current
    DESCRIPTION
        "TCP Health check overflow flag."
    ::= { slbCurAdvhcTcpEntry 11 }

slbCurAdvhcTcpDownInterval OBJECT-TYPE
    SYNTAX  INTEGER (0..600)
    MAX-ACCESS  read-only
    STATUS  current
    DESCRIPTION
        "TCP Health check interval in the down state."
    ::= { slbCurAdvhcTcpEntry 12 }

slbCurAdvhcTcpInvert OBJECT-TYPE
    SYNTAX  SlbAdvhcEnaDis
    MAX-ACCESS  read-only
    STATUS  current
    DESCRIPTION
        "TCP Health check invert flag."
    ::= { slbCurAdvhcTcpEntry 13 }

slbCurAdvhcTcpConnTerm OBJECT-TYPE
    SYNTAX  INTEGER{
        fin(1),
        rst(2),
        unsupported(2147483647)
        }
    MAX-ACCESS  read-only
    STATUS  current
    DESCRIPTION
        "Connection termination type"
    ::= { slbCurAdvhcTcpEntry 14 }

slbCurAdvhcTcpAlways OBJECT-TYPE
    SYNTAX  SlbAdvhcEnaDis
    MAX-ACCESS  read-only
    STATUS  current
    DESCRIPTION
        "This flag determines whether HC is allowed for standalone real."
    ::= { slbCurAdvhcTcpEntry 15 }

slbNewAdvhcTcpTable  OBJECT-TYPE
    SYNTAX  SEQUENCE OF SlbNewAdvhcTcpEntry
    MAX-ACCESS  not-accessible
    STATUS  current
    DESCRIPTION
        "Note:This mib is not supported on VX instance of Virtualization."
    ::= { advhcCfg 34 }

slbNewAdvhcTcpEntry OBJECT-TYPE
    SYNTAX  SlbNewAdvhcTcpEntry
    MAX-ACCESS  not-accessible
    STATUS  current
    DESCRIPTION
        "."
    INDEX   { slbNewAdvhcTcpID }
    ::= { slbNewAdvhcTcpTable 1 }

SlbNewAdvhcTcpEntry ::= SEQUENCE {
    slbNewAdvhcTcpID               DisplayString,
    slbNewAdvhcTcpName             DisplayString,
    slbNewAdvhcTcpDPort            INTEGER,
    slbNewAdvhcTcpIPVer            SlbAdvhcIPVer,
    slbNewAdvhcTcpHostName         DisplayString,
    slbNewAdvhcTcpTransparent      SlbAdvhcEnaDis,
    slbNewAdvhcTcpInterval         INTEGER,
    slbNewAdvhcTcpRetries          INTEGER,
    slbNewAdvhcTcpRestoreRetries   INTEGER,
    slbNewAdvhcTcpTimeout          INTEGER,
    slbNewAdvhcTcpOverflow         INTEGER,
    slbNewAdvhcTcpDownInterval     INTEGER,
    slbNewAdvhcTcpInvert           SlbAdvhcEnaDis,
    slbNewAdvhcTcpCopy             DisplayString,
    slbNewAdvhcTcpDelete           SlbAdvhcDelete,
    slbNewAdvhcTcpConnTerm         INTEGER,
    slbNewAdvhcTcpAlways           SlbAdvhcEnaDis
    }

slbNewAdvhcTcpID OBJECT-TYPE
    SYNTAX   DisplayString (SIZE (0..128))
    MAX-ACCESS  read-only
    STATUS  current
    DESCRIPTION
        "TCP Health check id."
    ::= { slbNewAdvhcTcpEntry 1 }

slbNewAdvhcTcpName OBJECT-TYPE
    SYNTAX   DisplayString (SIZE (0..128))
    MAX-ACCESS  read-write
    STATUS  current
    DESCRIPTION
        "TCP Health check name."
    ::= { slbNewAdvhcTcpEntry 2 }

slbNewAdvhcTcpDPort OBJECT-TYPE
    SYNTAX  INTEGER (0..65534)
    MAX-ACCESS  read-write
    STATUS  current
    DESCRIPTION
        "TCP Health check destination port."
    ::= { slbNewAdvhcTcpEntry 3 }

slbNewAdvhcTcpIPVer OBJECT-TYPE
    SYNTAX  SlbAdvhcIPVer
    MAX-ACCESS  read-write
    STATUS  current
    DESCRIPTION
        "TCP Health check destination IP version."
    ::= { slbNewAdvhcTcpEntry 4 }

slbNewAdvhcTcpHostName OBJECT-TYPE
    SYNTAX   DisplayString (SIZE (0..128))
    MAX-ACCESS  read-write
    STATUS  current
    DESCRIPTION
        "TCP Health check destination host name."
    ::= { slbNewAdvhcTcpEntry 5 }

slbNewAdvhcTcpTransparent OBJECT-TYPE
    SYNTAX  SlbAdvhcEnaDis
    MAX-ACCESS  read-write
    STATUS  current
    DESCRIPTION
        "TCP Health check transparent flag."
    ::= { slbNewAdvhcTcpEntry 6 }

slbNewAdvhcTcpInterval OBJECT-TYPE
    SYNTAX  INTEGER (1..600)
    MAX-ACCESS  read-write
    STATUS  current
    DESCRIPTION
        "TCP Health check interval."
    ::= { slbNewAdvhcTcpEntry 7 }

slbNewAdvhcTcpRetries OBJECT-TYPE
    SYNTAX  INTEGER (1..63)
    MAX-ACCESS  read-write
    STATUS  current
    DESCRIPTION
        "TCP Health check retries counter."
    ::= { slbNewAdvhcTcpEntry 8 }

slbNewAdvhcTcpRestoreRetries OBJECT-TYPE
    SYNTAX  INTEGER (1..63)
    MAX-ACCESS  read-write
    STATUS  current
    DESCRIPTION
        "TCP Health check retries counter in the down state."
    ::= { slbNewAdvhcTcpEntry 9 }

slbNewAdvhcTcpTimeout OBJECT-TYPE
    SYNTAX  INTEGER (1..63)
    MAX-ACCESS  read-write
    STATUS  current
    DESCRIPTION
        "TCP Health check timeout."
    ::= { slbNewAdvhcTcpEntry 10 }

slbNewAdvhcTcpOverflow OBJECT-TYPE
    SYNTAX  INTEGER (0..600)
    MAX-ACCESS  read-write
    STATUS  current
    DESCRIPTION
        "TCP Health check overflow flag."
    ::= { slbNewAdvhcTcpEntry 11 }

slbNewAdvhcTcpDownInterval OBJECT-TYPE
    SYNTAX  INTEGER (0..600)
    MAX-ACCESS  read-write
    STATUS  current
    DESCRIPTION
        "TCP Health check interval in the down state."
    ::= { slbNewAdvhcTcpEntry 12 }

slbNewAdvhcTcpInvert OBJECT-TYPE
    SYNTAX  SlbAdvhcEnaDis
    MAX-ACCESS  read-write
    STATUS  current
    DESCRIPTION
        "TCP Health check invert flag."
    ::= { slbNewAdvhcTcpEntry 13 }

slbNewAdvhcTcpCopy OBJECT-TYPE
    SYNTAX   DisplayString (SIZE (0..128))
    MAX-ACCESS  read-write
    STATUS  current
    DESCRIPTION
        "TCP Health check copy indicator."
    ::= { slbNewAdvhcTcpEntry 14 }

slbNewAdvhcTcpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcTcpEntry 15 }
    
slbNewAdvhcTcpConnTerm OBJECT-TYPE
   SYNTAX  INTEGER{
        fin(1),
        rst(2),
        unsupported(2147483647)
        }
    MAX-ACCESS  read-write
    STATUS  current
    DESCRIPTION
        "Connection termination type."
    ::= { slbNewAdvhcTcpEntry 16 }

slbNewAdvhcTcpAlways OBJECT-TYPE
    SYNTAX  SlbAdvhcEnaDis
    MAX-ACCESS  read-write
    STATUS  current
    DESCRIPTION
        "This flag determines whether HC is allowed for standalone real."
    ::= { slbNewAdvhcTcpEntry 17 }

-- Advance Health Check TFTP
----------------------------

slbCurAdvhcTftpTable  OBJECT-TYPE
    SYNTAX  SEQUENCE OF SlbCurAdvhcTftpEntry
    MAX-ACCESS  not-accessible
    STATUS  current
    DESCRIPTION
        "Note:This mib is not supported on VX instance of Virtualization."
    ::= { advhcCfg 35 }

slbCurAdvhcTftpEntry OBJECT-TYPE
    SYNTAX  SlbCurAdvhcTftpEntry
    MAX-ACCESS  not-accessible
    STATUS  current
    DESCRIPTION
        "."
    INDEX   { slbCurAdvhcTftpID }
    ::= { slbCurAdvhcTftpTable 1 }

SlbCurAdvhcTftpEntry ::= SEQUENCE {
    slbCurAdvhcTftpID               DisplayString,
    slbCurAdvhcTftpName             DisplayString,
    slbCurAdvhcTftpDPort            INTEGER,
    slbCurAdvhcTftpIPVer            SlbAdvhcIPVer,
    slbCurAdvhcTftpHostName         DisplayString,
    slbCurAdvhcTftpTransparent      SlbAdvhcEnaDis,
    slbCurAdvhcTftpInterval         INTEGER,
    slbCurAdvhcTftpRetries          INTEGER,
    slbCurAdvhcTftpRestoreRetries   INTEGER,
    slbCurAdvhcTftpTimeout          INTEGER,
    slbCurAdvhcTftpOverflow         INTEGER,
    slbCurAdvhcTftpDownInterval     INTEGER,
    slbCurAdvhcTftpInvert           SlbAdvhcEnaDis,
    slbCurAdvhcTftpfileFullPath     RadwareLongDisplayString
    }

slbCurAdvhcTftpID OBJECT-TYPE
    SYNTAX   DisplayString (SIZE (0..128))
    MAX-ACCESS  read-only
    STATUS  current
    DESCRIPTION
        "TFTP Health check id."
    ::= { slbCurAdvhcTftpEntry 1 }

slbCurAdvhcTftpName OBJECT-TYPE
    SYNTAX   DisplayString (SIZE (0..128))
    MAX-ACCESS  read-only
    STATUS  current
    DESCRIPTION
        "TFTP Health check name."
    ::= { slbCurAdvhcTftpEntry 2 }

slbCurAdvhcTftpDPort OBJECT-TYPE
    SYNTAX  INTEGER (0..65534)
    MAX-ACCESS  read-only
    STATUS  current
    DESCRIPTION
        "TFTP Health check destination port."
    ::= { slbCurAdvhcTftpEntry 3 }

slbCurAdvhcTftpIPVer OBJECT-TYPE
    SYNTAX  SlbAdvhcIPVer
    MAX-ACCESS  read-only
    STATUS  current
    DESCRIPTION
        "TFTP Health check destination IP version."
    ::= { slbCurAdvhcTftpEntry 4 }

slbCurAdvhcTftpHostName OBJECT-TYPE
    SYNTAX   DisplayString (SIZE (0..128))
    MAX-ACCESS  read-only
    STATUS  current
    DESCRIPTION
        "TFTP Health check host name."
    ::= { slbCurAdvhcTftpEntry 5 }

slbCurAdvhcTftpTransparent OBJECT-TYPE
    SYNTAX  SlbAdvhcEnaDis
    MAX-ACCESS  read-only
    STATUS  current
    DESCRIPTION
        "TFTP Health check transparent flag."
    ::= { slbCurAdvhcTftpEntry 6 }

slbCurAdvhcTftpInterval OBJECT-TYPE
    SYNTAX  INTEGER (1..600)
    MAX-ACCESS  read-only
    STATUS  current
    DESCRIPTION
        "TFTP Health check interval."
    ::= { slbCurAdvhcTftpEntry 7 }

slbCurAdvhcTftpRetries OBJECT-TYPE
    SYNTAX  INTEGER (1..63)
    MAX-ACCESS  read-only
    STATUS  current
    DESCRIPTION
        "TFTP Health check retries counter."
    ::= { slbCurAdvhcTftpEntry 8 }

slbCurAdvhcTftpRestoreRetries OBJECT-TYPE
    SYNTAX  INTEGER (1..63)
    MAX-ACCESS  read-only
    STATUS  current
    DESCRIPTION
        "TFTP Health check retries counter in the down state."
    ::= { slbCurAdvhcTftpEntry 9 }

slbCurAdvhcTftpTimeout OBJECT-TYPE
    SYNTAX  INTEGER (1..63)
    MAX-ACCESS  read-only
    STATUS  current
    DESCRIPTION
        "TFTP Health check timeout."
    ::= { slbCurAdvhcTftpEntry 10 }

slbCurAdvhcTftpOverflow OBJECT-TYPE
    SYNTAX  INTEGER (0..600)
    MAX-ACCESS  read-only
    STATUS  current
    DESCRIPTION
        "TFTP Health check overflow flag."
    ::= { slbCurAdvhcTftpEntry 11 }

slbCurAdvhcTftpDownInterval OBJECT-TYPE
    SYNTAX  INTEGER (0..600)
    MAX-ACCESS  read-only
    STATUS  current
    DESCRIPTION
        "TFTP Health check interval in the down state."
    ::= { slbCurAdvhcTftpEntry 12 }

slbCurAdvhcTftpInvert OBJECT-TYPE
    SYNTAX  SlbAdvhcEnaDis
    MAX-ACCESS  read-only
    STATUS  current
    DESCRIPTION
        "TFTP Health check invert flag."
    ::= { slbCurAdvhcTftpEntry 13 }

slbCurAdvhcTftpfileFullPath OBJECT-TYPE
    SYNTAX   RadwareLongDisplayString (SIZE (0..256))
    MAX-ACCESS  read-only
    STATUS  current
    DESCRIPTION
        "."
    ::= { slbCurAdvhcTftpEntry 14 }


slbNewAdvhcTftpTable  OBJECT-TYPE
    SYNTAX  SEQUENCE OF SlbNewAdvhcTftpEntry
    MAX-ACCESS  not-accessible
    STATUS  current
    DESCRIPTION
        "TFTP Health check path."
    ::= { advhcCfg 36 }

slbNewAdvhcTftpEntry OBJECT-TYPE
    SYNTAX  SlbNewAdvhcTftpEntry
    MAX-ACCESS  not-accessible
    STATUS  current
    DESCRIPTION
        "."
    INDEX   { slbNewAdvhcTftpID }
    ::= { slbNewAdvhcTftpTable 1 }

SlbNewAdvhcTftpEntry ::= SEQUENCE {
    slbNewAdvhcTftpID               DisplayString,
    slbNewAdvhcTftpName             DisplayString,
    slbNewAdvhcTftpDPort            INTEGER,
    slbNewAdvhcTftpIPVer            SlbAdvhcIPVer,
    slbNewAdvhcTftpHostName         DisplayString,
    slbNewAdvhcTftpTransparent      SlbAdvhcEnaDis,
    slbNewAdvhcTftpInterval         INTEGER,
    slbNewAdvhcTftpRetries          INTEGER,
    slbNewAdvhcTftpRestoreRetries   INTEGER,
    slbNewAdvhcTftpTimeout          INTEGER,
    slbNewAdvhcTftpOverflow         INTEGER,
    slbNewAdvhcTftpDownInterval     INTEGER,
    slbNewAdvhcTftpInvert           SlbAdvhcEnaDis,
    slbNewAdvhcTftpfileFullPath     RadwareLongDisplayString,
    slbNewAdvhcTftpCopy             DisplayString,
    slbNewAdvhcTftpDelete           SlbAdvhcDelete
    }

slbNewAdvhcTftpID OBJECT-TYPE
    SYNTAX   DisplayString (SIZE (0..128))
    MAX-ACCESS  read-only
    STATUS  current
    DESCRIPTION
        "TFTP Health check id."
    ::= { slbNewAdvhcTftpEntry 1 }

slbNewAdvhcTftpName OBJECT-TYPE
    SYNTAX   DisplayString (SIZE (0..128))
    MAX-ACCESS  read-write
    STATUS  current
    DESCRIPTION
        "TFTP Health check name."
    ::= { slbNewAdvhcTftpEntry 2 }

slbNewAdvhcTftpDPort OBJECT-TYPE
    SYNTAX  INTEGER (0..65534)
    MAX-ACCESS  read-write
    STATUS  current
    DESCRIPTION
        "TFTP Health check destination port."
    ::= { slbNewAdvhcTftpEntry 3 }

slbNewAdvhcTftpIPVer OBJECT-TYPE
    SYNTAX  SlbAdvhcIPVer
    MAX-ACCESS  read-write
    STATUS  current
    DESCRIPTION
        "TFTP Health check destination IP version."
    ::= { slbNewAdvhcTftpEntry 4 }

slbNewAdvhcTftpHostName OBJECT-TYPE
    SYNTAX   DisplayString (SIZE (0..128))
    MAX-ACCESS  read-write
    STATUS  current
    DESCRIPTION
        "TFTP Health check host name."
    ::= { slbNewAdvhcTftpEntry 5 }

slbNewAdvhcTftpTransparent OBJECT-TYPE
    SYNTAX  SlbAdvhcEnaDis
    MAX-ACCESS  read-write
    STATUS  current
    DESCRIPTION
        "TFTP Health check transparent flag."
    ::= { slbNewAdvhcTftpEntry 6 }

slbNewAdvhcTftpInterval OBJECT-TYPE
    SYNTAX  INTEGER (1..600)
    MAX-ACCESS  read-write
    STATUS  current
    DESCRIPTION
        "TFTP Health check interval."
    ::= { slbNewAdvhcTftpEntry 7 }

slbNewAdvhcTftpRetries OBJECT-TYPE
    SYNTAX  INTEGER (1..63)
    MAX-ACCESS  read-write
    STATUS  current
    DESCRIPTION
        "TFTP Health check retries counter."
    ::= { slbNewAdvhcTftpEntry 8 }

slbNewAdvhcTftpRestoreRetries OBJECT-TYPE
    SYNTAX  INTEGER (1..63)
    MAX-ACCESS  read-write
    STATUS  current
    DESCRIPTION
        "TFTP Health check retries counter in the down state."
    ::= { slbNewAdvhcTftpEntry 9 }

slbNewAdvhcTftpTimeout OBJECT-TYPE
    SYNTAX  INTEGER (1..63)
    MAX-ACCESS  read-write
    STATUS  current
    DESCRIPTION
        "TFTP Health check timeout."
    ::= { slbNewAdvhcTftpEntry 10 }

slbNewAdvhcTftpOverflow OBJECT-TYPE
    SYNTAX  INTEGER (0..600)
    MAX-ACCESS  read-write
    STATUS  current
    DESCRIPTION
        "TFTP Health check overflow flag."
    ::= { slbNewAdvhcTftpEntry 11 }

slbNewAdvhcTftpDownInterval OBJECT-TYPE
    SYNTAX  INTEGER (0..600)
    MAX-ACCESS  read-write
    STATUS  current
    DESCRIPTION
        "TFTP Health check interval in the down state."
    ::= { slbNewAdvhcTftpEntry 12 }

slbNewAdvhcTftpInvert OBJECT-TYPE
    SYNTAX  SlbAdvhcEnaDis
    MAX-ACCESS  read-write
    STATUS  current
    DESCRIPTION
        "TFTP Health check invert flag."
    ::= { slbNewAdvhcTftpEntry 13 }

slbNewAdvhcTftpfileFullPath OBJECT-TYPE
    SYNTAX   RadwareLongDisplayString (SIZE (0..256))
    MAX-ACCESS  read-write
    STATUS  current
    DESCRIPTION
        "TFTP Health check path."
    ::= { slbNewAdvhcTftpEntry 14 }

slbNewAdvhcTftpCopy OBJECT-TYPE
    SYNTAX   DisplayString (SIZE (0..128))
    MAX-ACCESS  read-write
    STATUS  current
    DESCRIPTION
        "TFTP Health check copy indicator."
    ::= { slbNewAdvhcTftpEntry 15 }

slbNewAdvhcTftpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcTftpEntry 16 }


-- Advance Health Check WAP
---------------------------

slbCurAdvhcWapTable  OBJECT-TYPE
    SYNTAX  SEQUENCE OF SlbCurAdvhcWapEntry
    MAX-ACCESS  not-accessible
    STATUS  current
    DESCRIPTION
        "Note:This mib is not supported on VX instance of Virtualization."
    ::= { advhcCfg 37 }

slbCurAdvhcWapEntry OBJECT-TYPE
    SYNTAX  SlbCurAdvhcWapEntry
    MAX-ACCESS  not-accessible
    STATUS  current
    DESCRIPTION
        "."
    INDEX   { slbCurAdvhcWapID }
    ::= { slbCurAdvhcWapTable 1 }

SlbCurAdvhcWapEntry ::= SEQUENCE {
    slbCurAdvhcWapID                DisplayString,
    slbCurAdvhcWapName              DisplayString,
    slbCurAdvhcWapDPort             INTEGER,
    slbCurAdvhcWapIPVer             SlbAdvhcIPVer,
    slbCurAdvhcWapHostName          DisplayString,
    slbCurAdvhcWapTransparent       SlbAdvhcEnaDis,
    slbCurAdvhcWapInterval          INTEGER,
    slbCurAdvhcWapRetries           INTEGER,
    slbCurAdvhcWapRestoreRetries    INTEGER,
    slbCurAdvhcWapTimeout           INTEGER,
    slbCurAdvhcWapOverflow          INTEGER,
    slbCurAdvhcWapDownInterval      INTEGER,
    slbCurAdvhcWapInvert            SlbAdvhcEnaDis,
    slbCurAdvhcWapType              INTEGER,
    slbCurAdvhcWapWspSendString     RadwareLongDisplayString,
    slbCurAdvhcWapWspReceiveString  RadwareLongDisplayString,
    slbCurAdvhcWapWspoffset         INTEGER,
    slbCurAdvhcWapConnectHeaders    RadwareLongDisplayString,
    slbCurAdvhcWapWtpSendString     RadwareLongDisplayString,
    slbCurAdvhcWapWtpReceiveString  RadwareLongDisplayString,
    slbCurAdvhcWapWtpoffset         INTEGER,
    slbCurAdvhcWapCouple            SlbAdvhcEnaDis
    }

slbCurAdvhcWapID OBJECT-TYPE
    SYNTAX   DisplayString (SIZE (0..128))
    MAX-ACCESS  read-only
    STATUS  current
    DESCRIPTION
        "WAP Health check id."
    ::= { slbCurAdvhcWapEntry 1 }

slbCurAdvhcWapName OBJECT-TYPE
    SYNTAX   DisplayString (SIZE (0..128))
    MAX-ACCESS  read-only
    STATUS  current
    DESCRIPTION
        "WAP Health check name."
    ::= { slbCurAdvhcWapEntry 2 }

slbCurAdvhcWapDPort OBJECT-TYPE
    SYNTAX  INTEGER (0..65534)
    MAX-ACCESS  read-only
    STATUS  current
    DESCRIPTION
        "WAP Health check destination port."
    ::= { slbCurAdvhcWapEntry 3 }

slbCurAdvhcWapIPVer OBJECT-TYPE
    SYNTAX  SlbAdvhcIPVer
    MAX-ACCESS  read-only
    STATUS  current
    DESCRIPTION
        "WAP Health check destination IP version."
    ::= { slbCurAdvhcWapEntry 4 }

slbCurAdvhcWapHostName OBJECT-TYPE
    SYNTAX   DisplayString (SIZE (0..128))
    MAX-ACCESS  read-only
    STATUS  current
    DESCRIPTION
        "WAP Health check destination host name."
    ::= { slbCurAdvhcWapEntry 5 }

slbCurAdvhcWapTransparent OBJECT-TYPE
    SYNTAX  SlbAdvhcEnaDis
    MAX-ACCESS  read-only
    STATUS  current
    DESCRIPTION
        "WAP Health check transparent flag."
    ::= { slbCurAdvhcWapEntry 6 }

slbCurAdvhcWapInterval OBJECT-TYPE
    SYNTAX  INTEGER (1..600)
    MAX-ACCESS  read-only
    STATUS  current
    DESCRIPTION
        "WAP Health check inteval."
    ::= { slbCurAdvhcWapEntry 7 }

slbCurAdvhcWapRetries OBJECT-TYPE
    SYNTAX  INTEGER (1..63)
    MAX-ACCESS  read-only
    STATUS  current
    DESCRIPTION
        "WAP Health check retries counter."
    ::= { slbCurAdvhcWapEntry 8 }

slbCurAdvhcWapRestoreRetries OBJECT-TYPE
    SYNTAX  INTEGER (1..63)
    MAX-ACCESS  read-only
    STATUS  current
    DESCRIPTION
        "WAP Health check retries counter when in the down state."
    ::= { slbCurAdvhcWapEntry 9 }

slbCurAdvhcWapTimeout OBJECT-TYPE
    SYNTAX  INTEGER (1..63)
    MAX-ACCESS  read-only
    STATUS  current
    DESCRIPTION
        "WAP Health check timeout."
    ::= { slbCurAdvhcWapEntry 10 }

slbCurAdvhcWapOverflow OBJECT-TYPE
    SYNTAX  INTEGER (0..600)
    MAX-ACCESS  read-only
    STATUS  current
    DESCRIPTION
        "WAP Health check overflow flag."
    ::= { slbCurAdvhcWapEntry 11 }

slbCurAdvhcWapDownInterval OBJECT-TYPE
    SYNTAX  INTEGER (0..600)
    MAX-ACCESS  read-only
    STATUS  current
    DESCRIPTION
        "WAP Health check interval when in the down state."
    ::= { slbCurAdvhcWapEntry 12 }

slbCurAdvhcWapInvert OBJECT-TYPE
    SYNTAX  SlbAdvhcEnaDis
    MAX-ACCESS  read-only
    STATUS  current
    DESCRIPTION
        "WAP Health check invert flag."
    ::= { slbCurAdvhcWapEntry 13 }

slbCurAdvhcWapType OBJECT-TYPE
    SYNTAX  INTEGER { wsp(1), wtp(2), wtlswsp(3), wtlswtp(4), wtls(5), unsupported(2147483647) }
    MAX-ACCESS  read-only
    STATUS  current
    DESCRIPTION
        "WAP Health check type.wtls mode allowed only for upgrade OOTB wtls object."
    ::= { slbCurAdvhcWapEntry 14 }

slbCurAdvhcWapWspSendString OBJECT-TYPE
    SYNTAX   RadwareLongDisplayString (SIZE (0..256))
    MAX-ACCESS  read-only
    STATUS  current
    DESCRIPTION
        "WAP Health check string to send."
    ::= { slbCurAdvhcWapEntry 15 }

slbCurAdvhcWapWspReceiveString OBJECT-TYPE
    SYNTAX   RadwareLongDisplayString (SIZE (0..256))
    MAX-ACCESS  read-only
    STATUS  current
    DESCRIPTION
        "WAP Health check expected string."
    ::= { slbCurAdvhcWapEntry 16 }

slbCurAdvhcWapWspoffset OBJECT-TYPE
    SYNTAX  INTEGER 
    MAX-ACCESS  read-only
    STATUS  current
    DESCRIPTION
        "WAP Health check wsp offeset."
    ::= { slbCurAdvhcWapEntry 17 }

slbCurAdvhcWapConnectHeaders OBJECT-TYPE
    SYNTAX   RadwareLongDisplayString (SIZE (0..256))
    MAX-ACCESS  read-only
    STATUS  current
    DESCRIPTION
        "WAP Health check connection header."
    ::= { slbCurAdvhcWapEntry 18 }

slbCurAdvhcWapWtpSendString OBJECT-TYPE
    SYNTAX   RadwareLongDisplayString (SIZE (0..256))
    MAX-ACCESS  read-only
    STATUS  current
    DESCRIPTION
        "WAP Health check wtp string to send."
    ::= { slbCurAdvhcWapEntry 19 }

slbCurAdvhcWapWtpReceiveString OBJECT-TYPE
    SYNTAX   RadwareLongDisplayString (SIZE (0..256))
    MAX-ACCESS  read-only
    STATUS  current
    DESCRIPTION
        "WAP Health check wtp expected string."
    ::= { slbCurAdvhcWapEntry 20 }

slbCurAdvhcWapWtpoffset OBJECT-TYPE
    SYNTAX  INTEGER 
    MAX-ACCESS  read-only
    STATUS  current
    DESCRIPTION
        "WAP Health check wtp offeset."
    ::= { slbCurAdvhcWapEntry 21 }
    
slbCurAdvhcWapCouple OBJECT-TYPE
    SYNTAX  SlbAdvhcEnaDis
    MAX-ACCESS  read-only
    STATUS  current
    DESCRIPTION
        "WAP Health check couple flag."
    ::= { slbCurAdvhcWapEntry 22 }


slbNewAdvhcWapTable  OBJECT-TYPE
    SYNTAX  SEQUENCE OF SlbNewAdvhcWapEntry
    MAX-ACCESS  not-accessible
    STATUS  current
    DESCRIPTION
        "Note:This mib is not supported on VX instance of Virtualization."
    ::= { advhcCfg 38 }

slbNewAdvhcWapEntry OBJECT-TYPE
    SYNTAX  SlbNewAdvhcWapEntry
    MAX-ACCESS  not-accessible
    STATUS  current
    DESCRIPTION
        "."
    INDEX   { slbNewAdvhcWapID }
    ::= { slbNewAdvhcWapTable 1 }

SlbNewAdvhcWapEntry ::= SEQUENCE {
    slbNewAdvhcWapID                DisplayString,
    slbNewAdvhcWapName              DisplayString,
    slbNewAdvhcWapDPort             INTEGER,
    slbNewAdvhcWapIPVer             SlbAdvhcIPVer,
    slbNewAdvhcWapHostName          DisplayString,
    slbNewAdvhcWapTransparent       SlbAdvhcEnaDis,
    slbNewAdvhcWapInterval          INTEGER,
    slbNewAdvhcWapRetries           INTEGER,
    slbNewAdvhcWapRestoreRetries    INTEGER,
    slbNewAdvhcWapTimeout           INTEGER,
    slbNewAdvhcWapOverflow          INTEGER,
    slbNewAdvhcWapDownInterval      INTEGER,
    slbNewAdvhcWapInvert            SlbAdvhcEnaDis,
    slbNewAdvhcWapType              INTEGER,
    slbNewAdvhcWapWspSendString     RadwareLongDisplayString,
    slbNewAdvhcWapWspReceiveString  RadwareLongDisplayString,
    slbNewAdvhcWapWspoffset         INTEGER,
    slbNewAdvhcWapConnectHeaders    RadwareLongDisplayString,
    slbNewAdvhcWapWtpSendString     RadwareLongDisplayString,
    slbNewAdvhcWapWtpReceiveString  RadwareLongDisplayString,
    slbNewAdvhcWapWtpoffset         INTEGER,
    slbNewAdvhcWapCouple            SlbAdvhcEnaDis,
    slbNewAdvhcWapCopy              DisplayString,
    slbNewAdvhcWapDelete            SlbAdvhcDelete
    }

slbNewAdvhcWapID OBJECT-TYPE
    SYNTAX   DisplayString (SIZE (0..128))
    MAX-ACCESS  read-only
    STATUS  current
    DESCRIPTION
        "WAP Health check id."
    ::= { slbNewAdvhcWapEntry 1 }

slbNewAdvhcWapName OBJECT-TYPE
    SYNTAX   DisplayString (SIZE (0..128))
    MAX-ACCESS  read-write
    STATUS  current
    DESCRIPTION
        "WAP Health check name."
    ::= { slbNewAdvhcWapEntry 2 }

slbNewAdvhcWapDPort OBJECT-TYPE
    SYNTAX  INTEGER (0..65534)
    MAX-ACCESS  read-write
    STATUS  current
    DESCRIPTION
        "WAP Health check destination port."
    ::= { slbNewAdvhcWapEntry 3 }

slbNewAdvhcWapIPVer OBJECT-TYPE
    SYNTAX  SlbAdvhcIPVer
    MAX-ACCESS  read-write
    STATUS  current
    DESCRIPTION
        "WAP Health check destination IP version."
    ::= { slbNewAdvhcWapEntry 4 }

slbNewAdvhcWapHostName OBJECT-TYPE
    SYNTAX   DisplayString (SIZE (0..128))
    MAX-ACCESS  read-write
    STATUS  current
    DESCRIPTION
        "WAP Health check destination host name."
    ::= { slbNewAdvhcWapEntry 5 }

slbNewAdvhcWapTransparent OBJECT-TYPE
    SYNTAX  SlbAdvhcEnaDis
    MAX-ACCESS  read-write
    STATUS  current
    DESCRIPTION
        "WAP Health check transparent flag."
    ::= { slbNewAdvhcWapEntry 6 }

slbNewAdvhcWapInterval OBJECT-TYPE
    SYNTAX  INTEGER (1..600)
    MAX-ACCESS  read-write
    STATUS  current
    DESCRIPTION
        "WAP Health check inteval."
    ::= { slbNewAdvhcWapEntry 7 }

slbNewAdvhcWapRetries OBJECT-TYPE
    SYNTAX  INTEGER (1..63)
    MAX-ACCESS  read-write
    STATUS  current
    DESCRIPTION
        "WAP Health check retries counter."
    ::= { slbNewAdvhcWapEntry 8 }

slbNewAdvhcWapRestoreRetries OBJECT-TYPE
    SYNTAX  INTEGER (1..63)
    MAX-ACCESS  read-write
    STATUS  current
    DESCRIPTION
        "WAP Health check retries counter when in the down state."
    ::= { slbNewAdvhcWapEntry 9 }

slbNewAdvhcWapTimeout OBJECT-TYPE
    SYNTAX  INTEGER (1..63)
    MAX-ACCESS  read-write
    STATUS  current
    DESCRIPTION
        "WAP Health check timeout."
    ::= { slbNewAdvhcWapEntry 10 }

slbNewAdvhcWapOverflow OBJECT-TYPE
    SYNTAX  INTEGER (0..600)
    MAX-ACCESS  read-write
    STATUS  current
    DESCRIPTION
        "WAP Health check overflow flag."
    ::= { slbNewAdvhcWapEntry 11 }

slbNewAdvhcWapDownInterval OBJECT-TYPE
    SYNTAX  INTEGER (0..600)
    MAX-ACCESS  read-write
    STATUS  current
    DESCRIPTION
        "WAP Health check interval when in the down state."
    ::= { slbNewAdvhcWapEntry 12 }

slbNewAdvhcWapInvert OBJECT-TYPE
    SYNTAX  SlbAdvhcEnaDis
    MAX-ACCESS  read-write
    STATUS  current
    DESCRIPTION
        "WAP Health check invert flag."
    ::= { slbNewAdvhcWapEntry 13 }

slbNewAdvhcWapType OBJECT-TYPE
    SYNTAX  INTEGER { wsp(1), wtp(2), wtlswsp(3), wtlswtp(4), wtls(5), unsupported(2147483647) }
    MAX-ACCESS  read-write
    STATUS  current
    DESCRIPTION
        "WAP Health check type.
         wtls mode allowed only for upgrade OOTB wtls object"
    ::= { slbNewAdvhcWapEntry 14 }

slbNewAdvhcWapWspSendString OBJECT-TYPE
    SYNTAX   RadwareLongDisplayString (SIZE (0..256))
    MAX-ACCESS  read-write
    STATUS  current
    DESCRIPTION
        "WAP Health check string to send."
    ::= { slbNewAdvhcWapEntry 15 }

slbNewAdvhcWapWspReceiveString OBJECT-TYPE
    SYNTAX   RadwareLongDisplayString (SIZE (0..256))
    MAX-ACCESS  read-write
    STATUS  current
    DESCRIPTION
        "WAP Health check expected string."
    ::= { slbNewAdvhcWapEntry 16 }

slbNewAdvhcWapWspoffset OBJECT-TYPE
    SYNTAX  INTEGER 
    MAX-ACCESS  read-write
    STATUS  current
    DESCRIPTION
        "WAP Health check wsp offeset."
    ::= { slbNewAdvhcWapEntry 17 }

slbNewAdvhcWapConnectHeaders OBJECT-TYPE
    SYNTAX   RadwareLongDisplayString (SIZE (0..256))
    MAX-ACCESS  read-write
    STATUS  current
    DESCRIPTION
        "WAP Health check connection header."
    ::= { slbNewAdvhcWapEntry 18 }

slbNewAdvhcWapWtpSendString OBJECT-TYPE
    SYNTAX   RadwareLongDisplayString (SIZE (0..256))
    MAX-ACCESS  read-write
    STATUS  current
    DESCRIPTION
        "WAP Health check wtp string to send."
    ::= { slbNewAdvhcWapEntry 19 }

slbNewAdvhcWapWtpReceiveString OBJECT-TYPE
    SYNTAX   RadwareLongDisplayString (SIZE (0..256))
    MAX-ACCESS  read-write
    STATUS  current
    DESCRIPTION
        "WAP Health check wtp expected string."
    ::= { slbNewAdvhcWapEntry 20 }

slbNewAdvhcWapWtpoffset OBJECT-TYPE
    SYNTAX  INTEGER 
    MAX-ACCESS  read-write
    STATUS  current
    DESCRIPTION
        "WAP Health check wtp offeset."
    ::= { slbNewAdvhcWapEntry 21 }
    
slbNewAdvhcWapCouple OBJECT-TYPE
    SYNTAX  SlbAdvhcEnaDis
    MAX-ACCESS  read-write
    STATUS  current
    DESCRIPTION
        "WAP Health check couple flag."
    ::= { slbNewAdvhcWapEntry 22 }

slbNewAdvhcWapCopy OBJECT-TYPE
    SYNTAX   DisplayString (SIZE (0..128))
    MAX-ACCESS  read-write
    STATUS  current
    DESCRIPTION
        "WAP Health check copy indicator."
    ::= { slbNewAdvhcWapEntry 23 }

slbNewAdvhcWapDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcWapEntry 24 }


-- Advance Health Check WTS
---------------------------

slbCurAdvhcWtsTable  OBJECT-TYPE
    SYNTAX  SEQUENCE OF SlbCurAdvhcWtsEntry
    MAX-ACCESS  not-accessible
    STATUS  current
    DESCRIPTION
        "Note:This mib is not supported on VX instance of Virtualization."
    ::= { advhcCfg 39 }

slbCurAdvhcWtsEntry OBJECT-TYPE
    SYNTAX  SlbCurAdvhcWtsEntry
    MAX-ACCESS  not-accessible
    STATUS  current
    DESCRIPTION
        "."
    INDEX   { slbCurAdvhcWtsID }
    ::= { slbCurAdvhcWtsTable 1 }

SlbCurAdvhcWtsEntry ::= SEQUENCE {
    slbCurAdvhcWtsID                DisplayString,
    slbCurAdvhcWtsName              DisplayString,
    slbCurAdvhcWtsDPort             INTEGER,
    slbCurAdvhcWtsIPVer             SlbAdvhcIPVer,
    slbCurAdvhcWtsHostName          DisplayString,
    slbCurAdvhcWtsTransparent       SlbAdvhcEnaDis,
    slbCurAdvhcWtsInterval          INTEGER,
    slbCurAdvhcWtsRetries           INTEGER,
    slbCurAdvhcWtsRestoreRetries    INTEGER,
    slbCurAdvhcWtsTimeout           INTEGER,
    slbCurAdvhcWtsOverflow          INTEGER,
    slbCurAdvhcWtsDownInterval      INTEGER,
    slbCurAdvhcWtsInvert            SlbAdvhcEnaDis,
    slbCurAdvhcWtsUserName          DisplayString
    }

slbCurAdvhcWtsID OBJECT-TYPE
    SYNTAX   DisplayString (SIZE (0..128))
    MAX-ACCESS  read-only
    STATUS  current
    DESCRIPTION
        "WTS Health check id."
    ::= { slbCurAdvhcWtsEntry 1 }

slbCurAdvhcWtsName OBJECT-TYPE
    SYNTAX   DisplayString (SIZE (0..128))
    MAX-ACCESS  read-only
    STATUS  current
    DESCRIPTION
        "WTS Health check name."
    ::= { slbCurAdvhcWtsEntry 2 }

slbCurAdvhcWtsDPort OBJECT-TYPE
    SYNTAX  INTEGER (0..65534)
    MAX-ACCESS  read-only
    STATUS  current
    DESCRIPTION
        "WTS Health check destination port."
    ::= { slbCurAdvhcWtsEntry 3 }

slbCurAdvhcWtsIPVer OBJECT-TYPE
    SYNTAX  SlbAdvhcIPVer
    MAX-ACCESS  read-only
    STATUS  current
    DESCRIPTION
        "WTS Health check destination IP version."
    ::= { slbCurAdvhcWtsEntry 4 }

slbCurAdvhcWtsHostName OBJECT-TYPE
    SYNTAX   DisplayString (SIZE (0..128))
    MAX-ACCESS  read-only
    STATUS  current
    DESCRIPTION
        "WTS Health check destination hostname."
    ::= { slbCurAdvhcWtsEntry 5 }

slbCurAdvhcWtsTransparent OBJECT-TYPE
    SYNTAX  SlbAdvhcEnaDis
    MAX-ACCESS  read-only
    STATUS  current
    DESCRIPTION
        "WTS Health check transparent flag."
    ::= { slbCurAdvhcWtsEntry 6 }

slbCurAdvhcWtsInterval OBJECT-TYPE
    SYNTAX  INTEGER (1..600)
    MAX-ACCESS  read-only
    STATUS  current
    DESCRIPTION
        "WTS Health check interval."
    ::= { slbCurAdvhcWtsEntry 7 }

slbCurAdvhcWtsRetries OBJECT-TYPE
    SYNTAX  INTEGER (1..63)
    MAX-ACCESS  read-only
    STATUS  current
    DESCRIPTION
        "WTS Health check retries counter."
    ::= { slbCurAdvhcWtsEntry 8 }

slbCurAdvhcWtsRestoreRetries OBJECT-TYPE
    SYNTAX  INTEGER (1..63)
    MAX-ACCESS  read-only
    STATUS  current
    DESCRIPTION
        "WTS Health check retries when in the down state counter."
    ::= { slbCurAdvhcWtsEntry 9 }

slbCurAdvhcWtsTimeout OBJECT-TYPE
    SYNTAX  INTEGER (1..63)
    MAX-ACCESS  read-only
    STATUS  current
    DESCRIPTION
        "WTS Health check timeout."
    ::= { slbCurAdvhcWtsEntry 10 }

slbCurAdvhcWtsOverflow OBJECT-TYPE
    SYNTAX  INTEGER (0..600)
    MAX-ACCESS  read-only
    STATUS  current
    DESCRIPTION
        "WTS Health check timeout."
    ::= { slbCurAdvhcWtsEntry 11 }

slbCurAdvhcWtsDownInterval OBJECT-TYPE
    SYNTAX  INTEGER (0..600)
    MAX-ACCESS  read-only
    STATUS  current
    DESCRIPTION
        "WTS Health check interval when in the down state."
    ::= { slbCurAdvhcWtsEntry 12 }

slbCurAdvhcWtsInvert OBJECT-TYPE
    SYNTAX  SlbAdvhcEnaDis
    MAX-ACCESS  read-only
    STATUS  current
    DESCRIPTION
        "WTS Health check invert flag."
    ::= { slbCurAdvhcWtsEntry 13 }

slbCurAdvhcWtsUserName OBJECT-TYPE
    SYNTAX   DisplayString (SIZE (0..32))
    MAX-ACCESS  read-only
    STATUS  current
    DESCRIPTION
        "WTS Health check user name."
    ::= { slbCurAdvhcWtsEntry 14 }


slbNewAdvhcWtsTable  OBJECT-TYPE
    SYNTAX  SEQUENCE OF SlbNewAdvhcWtsEntry
    MAX-ACCESS  not-accessible
    STATUS  current
    DESCRIPTION
        "Note:This mib is not supported on VX instance of Virtualization."
    ::= { advhcCfg 40 }

slbNewAdvhcWtsEntry OBJECT-TYPE
    SYNTAX  SlbNewAdvhcWtsEntry
    MAX-ACCESS  not-accessible
    STATUS  current
    DESCRIPTION
        "."
    INDEX   { slbNewAdvhcWtsID }
    ::= { slbNewAdvhcWtsTable 1 }

SlbNewAdvhcWtsEntry ::= SEQUENCE {
    slbNewAdvhcWtsID                DisplayString,
    slbNewAdvhcWtsName              DisplayString,
    slbNewAdvhcWtsDPort             INTEGER,
    slbNewAdvhcWtsIPVer             SlbAdvhcIPVer,
    slbNewAdvhcWtsHostName          DisplayString,
    slbNewAdvhcWtsTransparent       SlbAdvhcEnaDis,
    slbNewAdvhcWtsInterval          INTEGER,
    slbNewAdvhcWtsRetries           INTEGER,
    slbNewAdvhcWtsRestoreRetries    INTEGER,
    slbNewAdvhcWtsTimeout           INTEGER,
    slbNewAdvhcWtsOverflow          INTEGER,
    slbNewAdvhcWtsDownInterval      INTEGER,
    slbNewAdvhcWtsInvert            SlbAdvhcEnaDis,
    slbNewAdvhcWtsUserName          DisplayString,
    slbNewAdvhcWtsCopy              DisplayString,
    slbNewAdvhcWtsDelete            SlbAdvhcDelete
    }

slbNewAdvhcWtsID OBJECT-TYPE
    SYNTAX   DisplayString (SIZE (0..128))
    MAX-ACCESS  read-only
    STATUS  current
    DESCRIPTION
        "WTS Health check id."
    ::= { slbNewAdvhcWtsEntry 1 }

slbNewAdvhcWtsName OBJECT-TYPE
    SYNTAX   DisplayString (SIZE (0..128))
    MAX-ACCESS  read-write
    STATUS  current
    DESCRIPTION
        "WTS Health check name."
    ::= { slbNewAdvhcWtsEntry 2 }

slbNewAdvhcWtsDPort OBJECT-TYPE
    SYNTAX  INTEGER (0..65534)
    MAX-ACCESS  read-write
    STATUS  current
    DESCRIPTION
        "WTS Health check destination port."
    ::= { slbNewAdvhcWtsEntry 3 }

slbNewAdvhcWtsIPVer OBJECT-TYPE
    SYNTAX  SlbAdvhcIPVer
    MAX-ACCESS  read-write
    STATUS  current
    DESCRIPTION
        "WTS Health check destination IP version."
    ::= { slbNewAdvhcWtsEntry 4 }

slbNewAdvhcWtsHostName OBJECT-TYPE
    SYNTAX   DisplayString (SIZE (0..128))
    MAX-ACCESS  read-write
    STATUS  current
    DESCRIPTION
        "WTS Health check destination hostname."
    ::= { slbNewAdvhcWtsEntry 5 }

slbNewAdvhcWtsTransparent OBJECT-TYPE
    SYNTAX  SlbAdvhcEnaDis
    MAX-ACCESS  read-write
    STATUS  current
    DESCRIPTION
        "WTS Health check transparent flag."
    ::= { slbNewAdvhcWtsEntry 6 }

slbNewAdvhcWtsInterval OBJECT-TYPE
    SYNTAX  INTEGER (1..600)
    MAX-ACCESS  read-write
    STATUS  current
    DESCRIPTION
        "WTS Health check interval."
    ::= { slbNewAdvhcWtsEntry 7 }

slbNewAdvhcWtsRetries OBJECT-TYPE
    SYNTAX  INTEGER (1..63)
    MAX-ACCESS  read-write
    STATUS  current
    DESCRIPTION
        "WTS Health check retries counter."
    ::= { slbNewAdvhcWtsEntry 8 }

slbNewAdvhcWtsRestoreRetries OBJECT-TYPE
    SYNTAX  INTEGER (1..63)
    MAX-ACCESS  read-write
    STATUS  current
    DESCRIPTION
        "WTS Health check retries when in the down state counter."
    ::= { slbNewAdvhcWtsEntry 9 }

slbNewAdvhcWtsTimeout OBJECT-TYPE
    SYNTAX  INTEGER (1..63)
    MAX-ACCESS  read-write
    STATUS  current
    DESCRIPTION
        "WTS Health check timeout."
    ::= { slbNewAdvhcWtsEntry 10 }

slbNewAdvhcWtsOverflow OBJECT-TYPE
    SYNTAX  INTEGER (0..600)
    MAX-ACCESS  read-write
    STATUS  current
    DESCRIPTION
        "WTS Health check timeout."
    ::= { slbNewAdvhcWtsEntry 11 }

slbNewAdvhcWtsDownInterval OBJECT-TYPE
    SYNTAX  INTEGER (0..600)
    MAX-ACCESS  read-write
    STATUS  current
    DESCRIPTION
        "WTS Health check interval when in the down state."
    ::= { slbNewAdvhcWtsEntry 12 }

slbNewAdvhcWtsInvert OBJECT-TYPE
    SYNTAX  SlbAdvhcEnaDis
    MAX-ACCESS  read-write
    STATUS  current
    DESCRIPTION
        "WTS Health check invert flag."
    ::= { slbNewAdvhcWtsEntry 13 }

slbNewAdvhcWtsUserName OBJECT-TYPE
    SYNTAX   DisplayString (SIZE (0..32))
    MAX-ACCESS  read-write
    STATUS  current
    DESCRIPTION
        "WTS Health check user name."
    ::= { slbNewAdvhcWtsEntry 14 }

slbNewAdvhcWtsCopy OBJECT-TYPE
    SYNTAX   DisplayString (SIZE (0..128))
    MAX-ACCESS  read-write
    STATUS  current
    DESCRIPTION
        "WTS Health check copy indicator."
    ::= { slbNewAdvhcWtsEntry 15 }

slbNewAdvhcWtsDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcWtsEntry 16 }


-- Advance Health Check SCRIPTS
-------------------------------

slbCurAdvhcScriptTable  OBJECT-TYPE
    SYNTAX  SEQUENCE OF SlbCurAdvhcScriptEntry
    MAX-ACCESS  not-accessible
    STATUS  current
    DESCRIPTION
        "Note:This mib is not supported on VX instance of Virtualization."
    ::= { advhcCfg 41 }

slbCurAdvhcScriptEntry OBJECT-TYPE
    SYNTAX  SlbCurAdvhcScriptEntry
    MAX-ACCESS  not-accessible
    STATUS  current
    DESCRIPTION
        "."
    INDEX   { slbCurAdvhcScriptID }
    ::= { slbCurAdvhcScriptTable 1 }

SlbCurAdvhcScriptEntry ::= SEQUENCE {
    slbCurAdvhcScriptID                 DisplayString,
    slbCurAdvhcScriptName               DisplayString,
    slbCurAdvhcScriptString             RadwareLongDisplayString,
    slbCurAdvhcScriptIPVer              SlbAdvhcIPVer,
    slbCurAdvhcScriptHostName           DisplayString,
    slbCurAdvhcScriptInvert             SlbAdvhcEnaDis,
    slbCurAdvhcScriptRetries  	     	INTEGER,
    slbCurAdvhcScriptRestoreRetries	INTEGER,
    slbCurAdvhcScriptTimeout  	    	INTEGER,
    slbCurAdvhcScriptOverflow 	    	INTEGER,
    slbCurAdvhcScriptDownInterval       INTEGER,
    slbCurAdvhcScriptTransparent        SlbAdvhcEnaDis,
    slbCurAdvhcScriptInterval       	INTEGER,
    slbCurAdvhcScriptAlways             SlbAdvhcEnaDis
    }

slbCurAdvhcScriptID OBJECT-TYPE
    SYNTAX   DisplayString (SIZE (0..128))
    MAX-ACCESS  read-only
    STATUS  current
    DESCRIPTION
        "Script Health check id."
    ::= { slbCurAdvhcScriptEntry 1 }

slbCurAdvhcScriptName OBJECT-TYPE
    SYNTAX   DisplayString (SIZE (0..128))
    MAX-ACCESS  read-only
    STATUS  current
    DESCRIPTION
        "Script Health check name."
    ::= { slbCurAdvhcScriptEntry 2 }

slbCurAdvhcScriptString  OBJECT-TYPE
    SYNTAX   RadwareLongDisplayString
    MAX-ACCESS  read-only
    STATUS  current
    DESCRIPTION
        "Script Health check string."
    ::= { slbCurAdvhcScriptEntry 3 }

slbCurAdvhcScriptIPVer OBJECT-TYPE
    SYNTAX  SlbAdvhcIPVer
    MAX-ACCESS  read-only
    STATUS  current
    DESCRIPTION
        "Script Health check Ip Version."
    ::= { slbCurAdvhcScriptEntry 4 }

slbCurAdvhcScriptHostName OBJECT-TYPE
    SYNTAX  DisplayString (SIZE (0..128))
    MAX-ACCESS  read-only
    STATUS  current
    DESCRIPTION
        "Script Healtch check ip address / Hostname."
    ::= { slbCurAdvhcScriptEntry 5 }

slbCurAdvhcScriptInvert OBJECT-TYPE
    SYNTAX  SlbAdvhcEnaDis
    MAX-ACCESS  read-only
    STATUS  current
    DESCRIPTION
        " Invert Result"
    ::= { slbCurAdvhcScriptEntry 6 }
    
slbCurAdvhcScriptRetries OBJECT-TYPE
    SYNTAX  INTEGER (1..63)
    MAX-ACCESS  read-only
    STATUS  current
    DESCRIPTION
        "Script Health check retries counter."
    ::= { slbCurAdvhcScriptEntry 7 }

slbCurAdvhcScriptRestoreRetries OBJECT-TYPE
    SYNTAX  INTEGER (1..63)
    MAX-ACCESS  read-only
    STATUS  current
    DESCRIPTION
        "Script Health check retries in the down state counter."
    ::= { slbCurAdvhcScriptEntry 8 }

slbCurAdvhcScriptTimeout OBJECT-TYPE
    SYNTAX  INTEGER (1..63)
    MAX-ACCESS  read-only
    STATUS  current
    DESCRIPTION
        "Script Health check timeout."
    ::= { slbCurAdvhcScriptEntry 9 }

slbCurAdvhcScriptOverflow OBJECT-TYPE
    SYNTAX  INTEGER (0..600)
    MAX-ACCESS  read-only
    STATUS  current
    DESCRIPTION
        "Script Health check overflow flag."
    ::= { slbCurAdvhcScriptEntry 10 }

slbCurAdvhcScriptDownInterval OBJECT-TYPE
    SYNTAX  INTEGER (0..600)
    MAX-ACCESS  read-only
    STATUS  current
    DESCRIPTION
        "Script Health check interval in the down state."
    ::= { slbCurAdvhcScriptEntry 11 }    

slbCurAdvhcScriptTransparent OBJECT-TYPE
    SYNTAX  SlbAdvhcEnaDis
    MAX-ACCESS  read-only
    STATUS  current
    DESCRIPTION
        "Script Health check transparent flag."
    ::= { slbCurAdvhcScriptEntry 12 }

slbCurAdvhcScriptInterval OBJECT-TYPE
    SYNTAX  INTEGER (1..600)
    MAX-ACCESS  read-only
    STATUS  current
    DESCRIPTION
        "Script Health check interval."
    ::= { slbCurAdvhcScriptEntry 13 }

slbCurAdvhcScriptAlways OBJECT-TYPE
    SYNTAX  SlbAdvhcEnaDis
    MAX-ACCESS  read-only
    STATUS  current
    DESCRIPTION
        "This flag determines whether HC is allowed for standalone real."
    ::= { slbCurAdvhcScriptEntry 14 }

slbNewAdvhcScriptTable  OBJECT-TYPE
    SYNTAX  SEQUENCE OF SlbNewAdvhcScriptEntry
    MAX-ACCESS  not-accessible
    STATUS  current
    DESCRIPTION
        "Note:This mib is not supported on VX instance of Virtualization."
    ::= { advhcCfg 42 }

slbNewAdvhcScriptEntry OBJECT-TYPE
    SYNTAX  SlbNewAdvhcScriptEntry
    MAX-ACCESS  not-accessible
    STATUS  current
    DESCRIPTION
        "."
    INDEX   { slbNewAdvhcScriptID }
    ::= { slbNewAdvhcScriptTable 1 }

SlbNewAdvhcScriptEntry ::= SEQUENCE {
    slbNewAdvhcScriptID                 DisplayString,
    slbNewAdvhcScriptName               DisplayString,
    slbNewAdvhcScriptString             RadwareLongDisplayString,
    slbNewAdvhcScriptAddOpenCmd         DisplayString,
    slbNewAdvhcScriptAddSendCmd         DisplayString,
    slbNewAdvhcScriptAddBSendCmd        DisplayString,
    slbNewAdvhcScriptAddNSendCmd        DisplayString,
    slbNewAdvhcScriptAddExpectCmd       DisplayString,
    slbNewAdvhcScriptAddBEexpectCmd     DisplayString,
    slbNewAdvhcScriptAddNExpectCmd      DisplayString,
    slbNewAdvhcScriptAddOffsetCmd       INTEGER,
    slbNewAdvhcScriptAddDepthCmd        INTEGER,
    slbNewAdvhcScriptAddWaitCmd         INTEGER,
    slbNewAdvhcScriptAddCloseCmd        INTEGER,
    slbNewAdvhcScriptRemoveLastCmd      INTEGER,
    slbNewAdvhcScriptCopy               DisplayString,
    slbNewAdvhcScriptDelete             SlbAdvhcDelete,
    slbNewAdvhcScriptIPVer              SlbAdvhcIPVer,
    slbNewAdvhcScriptHostName           DisplayString,
    slbNewAdvhcScriptInvert             SlbAdvhcEnaDis,
    slbNewAdvhcScriptRetries          	INTEGER,
    slbNewAdvhcScriptRestoreRetries   	INTEGER,
    slbNewAdvhcScriptTimeout         	INTEGER,
    slbNewAdvhcScriptOverflow         	INTEGER,
    slbNewAdvhcScriptDownInterval     	INTEGER,
    slbNewAdvhcScriptTransparent        SlbAdvhcEnaDis,
    slbNewAdvhcScriptInterval     	INTEGER,
    slbNewAdvhcScriptAlways             SlbAdvhcEnaDis
    }

slbNewAdvhcScriptID OBJECT-TYPE
    SYNTAX   DisplayString (SIZE (0..128))
    MAX-ACCESS  read-only
    STATUS  current
    DESCRIPTION
        "Script Health check id."
    ::= { slbNewAdvhcScriptEntry 1 }

slbNewAdvhcScriptName OBJECT-TYPE
    SYNTAX   DisplayString (SIZE (0..128))
    MAX-ACCESS  read-write
    STATUS  current
    DESCRIPTION
        "Script Health check name."
    ::= { slbNewAdvhcScriptEntry 2 }

slbNewAdvhcScriptString  OBJECT-TYPE
    SYNTAX  RadwareLongDisplayString 
    MAX-ACCESS  read-only
    STATUS  current
    DESCRIPTION
        "Script Health check string."
    ::= { slbNewAdvhcScriptEntry 3 }

slbNewAdvhcScriptAddOpenCmd OBJECT-TYPE
    SYNTAX DisplayString (SIZE(0..31))
    MAX-ACCESS read-create
    STATUS current
    DESCRIPTION
        "Append an 'open' command to the script. The value of this object
         should be real server port number or name. Only the port number or
         name should be set. The 'open ' characters will be automatically
         appended. Also a 'null terminator'(\0) will be automatically appended.
         The null terminator and the 'open ' characters will be counted as
         characters in the script."
    ::= { slbNewAdvhcScriptEntry 4 }

slbNewAdvhcScriptAddSendCmd OBJECT-TYPE
    SYNTAX DisplayString (SIZE(0..255))
    MAX-ACCESS read-create
    STATUS current
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { slbNewAdvhcScriptEntry 5 }

slbNewAdvhcScriptAddBSendCmd OBJECT-TYPE
    SYNTAX DisplayString (SIZE(0..255))
    MAX-ACCESS read-create
    STATUS current
    DESCRIPTION
        "Append a 'bsend' command to the script. The set value of this
         object should be the exact binary data in hex format to be sent 
         on the port opened with the 'open' command. The 'bsend ' characters 
         will be automatically appended. Also a 'null terminator' (\0)
         will be automatically appended. The null terminator and the 'bsend '
         characters will be counted as characters in the script."
    ::= { slbNewAdvhcScriptEntry 6 }

slbNewAdvhcScriptAddNSendCmd OBJECT-TYPE
    SYNTAX DisplayString (SIZE(0..255))
    MAX-ACCESS read-create
    STATUS current
    DESCRIPTION
        "Append an 'nsend' command to the script. The 'nsend' command is
         used to append additional content to the packet generated by the
         'bsend' command when the desired 'bsend' content is more than 255
         characters.  The set value of this object should be the exact
         characters to be appended.  The 'nsend ' characters will be
         automatically appended.  Also a 'null terminator' (\0) will be
         automatically appended. The null terminator and the 'nsend '
         characters will be counted as characters in the script."
    ::= { slbNewAdvhcScriptEntry 7 }

slbNewAdvhcScriptAddExpectCmd OBJECT-TYPE
    SYNTAX DisplayString (SIZE(0..255))
    MAX-ACCESS read-create
    STATUS current
    DESCRIPTION
        "Append an 'expect' command to the script. The set value of this 
         object should be the exact characters expected to be received on
         the port opened with the 'open' command.  The value could also be
         a single wildcard character '*' which means any received content
         will be accepted.  The 'expect ' characters will be automatically 
         appended.  Also a 'null terminator'(\0) will be automatically  
         appended.  The null terminator and the 'expect ' characters will
         be counted as characters in the script."
    ::= { slbNewAdvhcScriptEntry 8 }

slbNewAdvhcScriptAddBEexpectCmd OBJECT-TYPE
    SYNTAX DisplayString (SIZE(0..255))
    MAX-ACCESS read-create
    STATUS current
    DESCRIPTION
        "Append a 'bexpect' command to the script. The set value of this 
         object should be the exact binary data in hex format expected to
         be received on the port opened with the 'open' command. The value 
         could also be a single wildcard character '*' which means any 
         received content will be accepted.  The 'bexpect ' characters 
         will be automatically appended.  Also a 'null terminator'(\0)
         will be automatically appended.  The null terminator and the 
         'bexpect ' characters will be counted as characters in the script."
    ::= { slbNewAdvhcScriptEntry 9 }
    
slbNewAdvhcScriptAddNExpectCmd OBJECT-TYPE
    SYNTAX DisplayString (SIZE(0..255))
    MAX-ACCESS read-create
    STATUS current
    DESCRIPTION
        "Append an 'nexpect' command to the script.  The 'nexpect' command
         is used to append additional characters to the 'bexpect' string
         when the desired 'bexpect' string is more than 255 characters.  The
         set value of this object should be the exact characters to be
         appended.  The 'nexpect ' characters will be automatically appended. 
         Also a 'null terminator'(\0) will be automatically appended. 
         The null terminator and the 'nexpect ' characters will be counted 
         as characters in the script."
    ::= { slbNewAdvhcScriptEntry 10 }

slbNewAdvhcScriptAddOffsetCmd OBJECT-TYPE
    SYNTAX INTEGER (1..1464)
    MAX-ACCESS read-create
    STATUS current
    DESCRIPTION
        "Append an 'offset' command to the script. The set value of this
         object should be the offset from the beginning of the data area
         of the TCP/UDP packet to start matching the string configured
         in the last bexpect command. The 'offset ' characters will be
         automatically appended. Also a 'null terminator'(\0) will be 
         automatically appended. The null terminator and the 'offset '
         characters will be counted as characters in the script.  When 
         read, the return value has no significant meaning, but a 1 is
         always returned."
    ::= { slbNewAdvhcScriptEntry 11 }

slbNewAdvhcScriptAddDepthCmd OBJECT-TYPE
    SYNTAX INTEGER (1..1464)
    MAX-ACCESS read-create
    STATUS current
    DESCRIPTION
        "Append a 'depth' command to the script. The set value of this
	 object should be the depth (search window) within the data
	 area of the TCP/UDP packet for matching the string configured
	 in the last bexpect command. The 'depth ' characters will be
         automatically appended. Also a 'null terminator'(\0) will be 
         automatically appended. The null terminator and the 'depth '
         characters will be counted as characters in the script. When 
	 read, the return value has no significant meaning, but a 1 is
	 always returned."
    ::= { slbNewAdvhcScriptEntry 12 }

slbNewAdvhcScriptAddWaitCmd OBJECT-TYPE
    SYNTAX INTEGER (1..65535)
    MAX-ACCESS read-create
    STATUS current
    DESCRIPTION
        "Append a 'wait' command to the script. The set value of this
         object should be the maximum waiting time for the packet
         containing the content configured in the last expect command.
         Wait time is in units of milliseconds, and the maximum
         supported is 65535 ms.  The 'wait ' characters will be 
         automatically appended. Also a 'null terminator'(\0) will be
         automatically appended. The null terminator and the 'wait ' 
         characters will be counted as characters in the script. When 
         read, the return value has no significant meaning, but a 1 is
         always returned. "
    ::= { slbNewAdvhcScriptEntry 13 }

slbNewAdvhcScriptAddCloseCmd OBJECT-TYPE
    SYNTAX INTEGER { other(1), close(2), unsupported(2147483647) }
    MAX-ACCESS read-create
    STATUS current
    DESCRIPTION
        "Add close command to end of the script. When set to the value of 2
         (add), 'close' will be appended to the script. Also, a 
         'null terminator'(\0) will be automatically appended. The null 
         terminator and the 'close' characters will be counted as characters 
         in the script.  This command is only valid for TCP."
    ::= { slbNewAdvhcScriptEntry 14 }

slbNewAdvhcScriptRemoveLastCmd OBJECT-TYPE
    SYNTAX INTEGER { other(1), remove(2), unsupported(2147483647) }
    MAX-ACCESS read-create
    STATUS current
    DESCRIPTION
        "Remove the last command from the script. When set to the value of 2
         (remove), last command will be removed from the script. When read,
         other(1) is returned."
    ::= { slbNewAdvhcScriptEntry 15 }            

slbNewAdvhcScriptCopy OBJECT-TYPE
    SYNTAX   DisplayString (SIZE (0..128))
    MAX-ACCESS  read-write
    STATUS  current
    DESCRIPTION
        "Script Health check copy indicator."
    ::= { slbNewAdvhcScriptEntry 16 }

slbNewAdvhcScriptDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcScriptEntry 17 }

slbNewAdvhcScriptIPVer OBJECT-TYPE
    SYNTAX  SlbAdvhcIPVer
    MAX-ACCESS  read-create
    STATUS  current
    DESCRIPTION
        "Script Health check Ip Version."
    ::= { slbNewAdvhcScriptEntry 18 }

slbNewAdvhcScriptHostName OBJECT-TYPE
    SYNTAX  DisplayString (SIZE (0..128))
    MAX-ACCESS  read-create
    STATUS  current
    DESCRIPTION
        "Script Healtch check ip address / Hostname."
    ::= { slbNewAdvhcScriptEntry 19 }

slbNewAdvhcScriptInvert OBJECT-TYPE
    SYNTAX  SlbAdvhcEnaDis
    MAX-ACCESS  read-write
    STATUS  current
    DESCRIPTION
        " Invert Result"
    ::= { slbNewAdvhcScriptEntry 20 }
    
slbNewAdvhcScriptRetries OBJECT-TYPE
    SYNTAX  INTEGER (1..63)
    MAX-ACCESS  read-write
    STATUS  current
    DESCRIPTION
        "Script Health check retries counter."
    ::= { slbNewAdvhcScriptEntry 21 }

slbNewAdvhcScriptRestoreRetries OBJECT-TYPE
    SYNTAX  INTEGER (1..63)
    MAX-ACCESS  read-write
    STATUS  current
    DESCRIPTION
        "Script Health check retries in the down state counter."
    ::= { slbNewAdvhcScriptEntry 22 }

slbNewAdvhcScriptTimeout OBJECT-TYPE
    SYNTAX  INTEGER (1..63)
    MAX-ACCESS  read-write
    STATUS  current
    DESCRIPTION
        "Script Health check timeout."
    ::= { slbNewAdvhcScriptEntry 23 }

slbNewAdvhcScriptOverflow OBJECT-TYPE
    SYNTAX  INTEGER (0..600)
    MAX-ACCESS  read-write
    STATUS  current
    DESCRIPTION
        "Script Health check overflow flag."
    ::= { slbNewAdvhcScriptEntry 24 }

slbNewAdvhcScriptDownInterval OBJECT-TYPE
    SYNTAX  INTEGER (0..600)
    MAX-ACCESS  read-write
    STATUS  current
    DESCRIPTION
        "Script Health check interval in the down state."
    ::= { slbNewAdvhcScriptEntry 25 }

slbNewAdvhcScriptTransparent OBJECT-TYPE
    SYNTAX  SlbAdvhcEnaDis
    MAX-ACCESS  read-write
    STATUS  current
    DESCRIPTION
        "Script Health check transparent flag."
    ::= { slbNewAdvhcScriptEntry 26 }
    
slbNewAdvhcScriptInterval OBJECT-TYPE
    SYNTAX  INTEGER (1..600)
    MAX-ACCESS  read-write
    STATUS  current
    DESCRIPTION
        "Script Health check interval."
    ::= { slbNewAdvhcScriptEntry 27 }

slbNewAdvhcScriptAlways OBJECT-TYPE
    SYNTAX  SlbAdvhcEnaDis
    MAX-ACCESS  read-write
    STATUS  current
    DESCRIPTION
        "This flag determines whether HC is allowed for standalone real."
    ::= { slbNewAdvhcScriptEntry 28 }
    
-- Advance Health Check LOGEXP
------------------------------

slbCurAdvhcLogexpTable  OBJECT-TYPE
    SYNTAX  SEQUENCE OF SlbCurAdvhcLogexpEntry
    MAX-ACCESS  not-accessible
    STATUS  current
    DESCRIPTION
        "Note:This mib is not supported on VX instance of Virtualization."
    ::= { advhcCfg 43 }

slbCurAdvhcLogexpEntry OBJECT-TYPE
    SYNTAX  SlbCurAdvhcLogexpEntry
    MAX-ACCESS  not-accessible
    STATUS  current
    DESCRIPTION
        "."
    INDEX   { slbCurAdvhcLogexpID }
    ::= { slbCurAdvhcLogexpTable 1 }

SlbCurAdvhcLogexpEntry ::= SEQUENCE {
    slbCurAdvhcLogexpID                 DisplayString,
    slbCurAdvhcLogexpName               DisplayString,
    slbCurAdvhcLogexpText               RadwareLongDisplayString,
    slbCurAdvhcLogexpAlways             SlbAdvhcEnaDis
    }

slbCurAdvhcLogexpID OBJECT-TYPE
    SYNTAX   DisplayString (SIZE (0..128))
    MAX-ACCESS  read-only
    STATUS  current
    DESCRIPTION
        "Logical expression health check id."
    ::= { slbCurAdvhcLogexpEntry 1 }

slbCurAdvhcLogexpName OBJECT-TYPE
    SYNTAX   DisplayString (SIZE (0..128))
    MAX-ACCESS  read-only
    STATUS  current
    DESCRIPTION
        "Logical expression health check name."
    ::= { slbCurAdvhcLogexpEntry 2 }

slbCurAdvhcLogexpText OBJECT-TYPE   
    SYNTAX RadwareLongDisplayString (SIZE(0..512))
    MAX-ACCESS read-only   
    STATUS current   
    DESCRIPTION 
        "Logical expression health check text."   
    ::= { slbCurAdvhcLogexpEntry 3 }

slbCurAdvhcLogexpAlways OBJECT-TYPE
    SYNTAX  SlbAdvhcEnaDis
    MAX-ACCESS  read-only
    STATUS  current
    DESCRIPTION
        "This flag determines whether HC is allowed for standalone real."
    ::= { slbCurAdvhcLogexpEntry 4 }

slbNewAdvhcLogexpTable  OBJECT-TYPE
    SYNTAX  SEQUENCE OF SlbNewAdvhcLogexpEntry
    MAX-ACCESS  not-accessible
    STATUS  current
    DESCRIPTION
        "Note:This mib is not supported on VX instance of Virtualization."
    ::= { advhcCfg 44 }

slbNewAdvhcLogexpEntry OBJECT-TYPE
    SYNTAX  SlbNewAdvhcLogexpEntry
    MAX-ACCESS  not-accessible
    STATUS  current
    DESCRIPTION
        "."
    INDEX   { slbNewAdvhcLogexpID }
    ::= { slbNewAdvhcLogexpTable 1 }

SlbNewAdvhcLogexpEntry ::= SEQUENCE {
    slbNewAdvhcLogexpID                 DisplayString,
    slbNewAdvhcLogexpName               DisplayString,
    slbNewAdvhcLogexpText               RadwareLongDisplayString,
    slbNewAdvhcLogexpCopy               DisplayString,
    slbNewAdvhcLogexpDelete             SlbAdvhcDelete,
    slbNewAdvhcLogexpAlways             SlbAdvhcEnaDis
    }

slbNewAdvhcLogexpID OBJECT-TYPE
    SYNTAX   DisplayString (SIZE (0..128))
    MAX-ACCESS  read-only
    STATUS  current
    DESCRIPTION
        "Logical expression health check id."
    ::= { slbNewAdvhcLogexpEntry 1 }

slbNewAdvhcLogexpName OBJECT-TYPE
    SYNTAX   DisplayString (SIZE (0..128))
    MAX-ACCESS  read-write
    STATUS  current
    DESCRIPTION
        "Logical expression health check name."
    ::= { slbNewAdvhcLogexpEntry 2 }

slbNewAdvhcLogexpText OBJECT-TYPE   
    SYNTAX RadwareLongDisplayString (SIZE(0..512))
    MAX-ACCESS read-write   
    STATUS current   
    DESCRIPTION 
        "Logical expression health check text."
    ::= { slbNewAdvhcLogexpEntry 3 }

slbNewAdvhcLogexpCopy OBJECT-TYPE
    SYNTAX   DisplayString (SIZE (0..128))
    MAX-ACCESS  read-write
    STATUS  current
    DESCRIPTION
        "Logical expression health check copy indicator."
    ::= { slbNewAdvhcLogexpEntry 4 }

slbNewAdvhcLogexpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcLogexpEntry 5 }

slbNewAdvhcLogexpAlways OBJECT-TYPE
    SYNTAX  SlbAdvhcEnaDis
    MAX-ACCESS  read-write
    STATUS  current
    DESCRIPTION
        "This flag determines whether HC is allowed for standalone real."
    ::= { slbNewAdvhcLogexpEntry 6 }

-- Advance Health Check ICMP
----------------------------

slbCurAdvhcIcmpTable  OBJECT-TYPE
    SYNTAX  SEQUENCE OF SlbCurAdvhcIcmpEntry
    MAX-ACCESS  not-accessible
    STATUS  current
    DESCRIPTION
        "Note:This mib is not supported on VX instance of Virtualization."
    ::= { advhcCfg 45 }

slbCurAdvhcIcmpEntry OBJECT-TYPE
    SYNTAX  SlbCurAdvhcIcmpEntry
    MAX-ACCESS  not-accessible
    STATUS  current
    DESCRIPTION
        "."
    INDEX   { slbCurAdvhcIcmpID }
    ::= { slbCurAdvhcIcmpTable 1 }

SlbCurAdvhcIcmpEntry ::= SEQUENCE {
    slbCurAdvhcIcmpID               DisplayString,
    slbCurAdvhcIcmpName             DisplayString,
    slbCurAdvhcIcmpDPort            INTEGER,
    slbCurAdvhcIcmpIPVer            SlbAdvhcIPVer,
    slbCurAdvhcIcmpHostName         DisplayString,
    slbCurAdvhcIcmpTransparent      SlbAdvhcEnaDis,
    slbCurAdvhcIcmpInterval         INTEGER,
    slbCurAdvhcIcmpRetries          INTEGER,
    slbCurAdvhcIcmpRestoreRetries   INTEGER,
    slbCurAdvhcIcmpTimeout          INTEGER,
    slbCurAdvhcIcmpOverflow         INTEGER,
    slbCurAdvhcIcmpDownInterval     INTEGER,
    slbCurAdvhcIcmpInvert           SlbAdvhcEnaDis
    }

slbCurAdvhcIcmpID OBJECT-TYPE
    SYNTAX   DisplayString (SIZE (0..128))
    MAX-ACCESS  read-only
    STATUS  current
    DESCRIPTION
        "ICMP health check id."
    ::= { slbCurAdvhcIcmpEntry 1 }

slbCurAdvhcIcmpName OBJECT-TYPE
    SYNTAX   DisplayString (SIZE (0..128))
    MAX-ACCESS  read-only
    STATUS  current
    DESCRIPTION
        "ICMP health check name."
    ::= { slbCurAdvhcIcmpEntry 2 }

slbCurAdvhcIcmpDPort OBJECT-TYPE
    SYNTAX  INTEGER (0..65534)
    MAX-ACCESS  read-only
    STATUS  current
    DESCRIPTION
        "ICMP health check destination port."
    ::= { slbCurAdvhcIcmpEntry 3 }

slbCurAdvhcIcmpIPVer OBJECT-TYPE
    SYNTAX  SlbAdvhcIPVer
    MAX-ACCESS  read-only
    STATUS  current
    DESCRIPTION
        "ICMP health check destination IP version."
    ::= { slbCurAdvhcIcmpEntry 4 }

slbCurAdvhcIcmpHostName OBJECT-TYPE
    SYNTAX   DisplayString (SIZE (0..128))
    MAX-ACCESS  read-only
    STATUS  current
    DESCRIPTION
        "ICMP health check destination hostname."
    ::= { slbCurAdvhcIcmpEntry 5 }

slbCurAdvhcIcmpTransparent OBJECT-TYPE
    SYNTAX  SlbAdvhcEnaDis
    MAX-ACCESS  read-only
    STATUS  current
    DESCRIPTION
        "ICMP health check transparent flag."
    ::= { slbCurAdvhcIcmpEntry 6 }

slbCurAdvhcIcmpInterval OBJECT-TYPE
    SYNTAX  INTEGER (1..600)
    MAX-ACCESS  read-only
    STATUS  current
    DESCRIPTION
        "ICMP health check interval."
    ::= { slbCurAdvhcIcmpEntry 7 }

slbCurAdvhcIcmpRetries OBJECT-TYPE
    SYNTAX  INTEGER (1..63)
    MAX-ACCESS  read-only
    STATUS  current
    DESCRIPTION
        "ICMP health check retries counter."
    ::= { slbCurAdvhcIcmpEntry 8 }

slbCurAdvhcIcmpRestoreRetries OBJECT-TYPE
    SYNTAX  INTEGER (1..63)
    MAX-ACCESS  read-only
    STATUS  current
    DESCRIPTION
        "ICMP health check retries counter to restore from the down state."
    ::= { slbCurAdvhcIcmpEntry 9 }

slbCurAdvhcIcmpTimeout OBJECT-TYPE
    SYNTAX  INTEGER (1..63)
    MAX-ACCESS  read-only
    STATUS  current
    DESCRIPTION
        "ICMP health check timeout."
    ::= { slbCurAdvhcIcmpEntry 10 }

slbCurAdvhcIcmpOverflow OBJECT-TYPE
    SYNTAX  INTEGER (0..600)
    MAX-ACCESS  read-only
    STATUS  current
    DESCRIPTION
        "ICMP health check overflow flag."
    ::= { slbCurAdvhcIcmpEntry 11 }

slbCurAdvhcIcmpDownInterval OBJECT-TYPE
    SYNTAX  INTEGER (0..600)
    MAX-ACCESS  read-only
    STATUS  current
    DESCRIPTION
        "ICMP health check interval in the down state."
    ::= { slbCurAdvhcIcmpEntry 12 }

slbCurAdvhcIcmpInvert OBJECT-TYPE
    SYNTAX  SlbAdvhcEnaDis
    MAX-ACCESS  read-only
    STATUS  current
    DESCRIPTION
        "ICMP health check invert flag."
    ::= { slbCurAdvhcIcmpEntry 13 }


slbNewAdvhcIcmpTable  OBJECT-TYPE
    SYNTAX  SEQUENCE OF SlbNewAdvhcIcmpEntry
    MAX-ACCESS  not-accessible
    STATUS  current
    DESCRIPTION
        "Note:This mib is not supported on VX instance of Virtualization."
    ::= { advhcCfg 46 }

slbNewAdvhcIcmpEntry OBJECT-TYPE
    SYNTAX  SlbNewAdvhcIcmpEntry
    MAX-ACCESS  not-accessible
    STATUS  current
    DESCRIPTION
        "."
    INDEX   { slbNewAdvhcIcmpID }
    ::= { slbNewAdvhcIcmpTable 1 }

SlbNewAdvhcIcmpEntry ::= SEQUENCE {
    slbNewAdvhcIcmpID               DisplayString,
    slbNewAdvhcIcmpName             DisplayString,
    slbNewAdvhcIcmpDPort            INTEGER,
    slbNewAdvhcIcmpIPVer            SlbAdvhcIPVer,
    slbNewAdvhcIcmpHostName         DisplayString,
    slbNewAdvhcIcmpTransparent      SlbAdvhcEnaDis,
    slbNewAdvhcIcmpInterval         INTEGER,
    slbNewAdvhcIcmpRetries          INTEGER,
    slbNewAdvhcIcmpRestoreRetries   INTEGER,
    slbNewAdvhcIcmpTimeout          INTEGER,
    slbNewAdvhcIcmpOverflow         INTEGER,
    slbNewAdvhcIcmpDownInterval     INTEGER,
    slbNewAdvhcIcmpInvert           SlbAdvhcEnaDis,
    slbNewAdvhcIcmpCopy             DisplayString,
    slbNewAdvhcIcmpDelete           SlbAdvhcDelete
    }

slbNewAdvhcIcmpID OBJECT-TYPE
    SYNTAX   DisplayString (SIZE (0..128))
    MAX-ACCESS  read-only
    STATUS  current
    DESCRIPTION
        "ICMP health check id."
    ::= { slbNewAdvhcIcmpEntry 1 }

slbNewAdvhcIcmpName OBJECT-TYPE
    SYNTAX   DisplayString (SIZE (0..128))
    MAX-ACCESS  read-write
    STATUS  current
    DESCRIPTION
        "ICMP health check name."
    ::= { slbNewAdvhcIcmpEntry 2 }

slbNewAdvhcIcmpDPort OBJECT-TYPE
    SYNTAX  INTEGER (0..65534)
    MAX-ACCESS  read-write
    STATUS  current
    DESCRIPTION
        "ICMP health check destination port."
    ::= { slbNewAdvhcIcmpEntry 3 }

slbNewAdvhcIcmpIPVer OBJECT-TYPE
    SYNTAX  SlbAdvhcIPVer
    MAX-ACCESS  read-write
    STATUS  current
    DESCRIPTION
        "ICMP health check destination IP version."
    ::= { slbNewAdvhcIcmpEntry 4 }

slbNewAdvhcIcmpHostName OBJECT-TYPE
    SYNTAX   DisplayString (SIZE (0..128))
    MAX-ACCESS  read-write
    STATUS  current
    DESCRIPTION
        "ICMP health check destination hostname."
    ::= { slbNewAdvhcIcmpEntry 5 }

slbNewAdvhcIcmpTransparent OBJECT-TYPE
    SYNTAX  SlbAdvhcEnaDis
    MAX-ACCESS  read-write
    STATUS  current
    DESCRIPTION
        "ICMP health check transparent flag."
    ::= { slbNewAdvhcIcmpEntry 6 }

slbNewAdvhcIcmpInterval OBJECT-TYPE
    SYNTAX  INTEGER (1..600)
    MAX-ACCESS  read-write
    STATUS  current
    DESCRIPTION
        "ICMP health check interval."
    ::= { slbNewAdvhcIcmpEntry 7 }

slbNewAdvhcIcmpRetries OBJECT-TYPE
    SYNTAX  INTEGER (1..63)
    MAX-ACCESS  read-write
    STATUS  current
    DESCRIPTION
        "ICMP health check retries counter."
    ::= { slbNewAdvhcIcmpEntry 8 }

slbNewAdvhcIcmpRestoreRetries OBJECT-TYPE
    SYNTAX  INTEGER (1..63)
    MAX-ACCESS  read-write
    STATUS  current
    DESCRIPTION
        "ICMP health check retries counter to restore from the down state."
    ::= { slbNewAdvhcIcmpEntry 9 }

slbNewAdvhcIcmpTimeout OBJECT-TYPE
    SYNTAX  INTEGER (1..63)
    MAX-ACCESS  read-write
    STATUS  current
    DESCRIPTION
        "ICMP health check timeout."
    ::= { slbNewAdvhcIcmpEntry 10 }

slbNewAdvhcIcmpOverflow OBJECT-TYPE
    SYNTAX  INTEGER (0..600)
    MAX-ACCESS  read-write
    STATUS  current
    DESCRIPTION
        "ICMP health check overflow flag."
    ::= { slbNewAdvhcIcmpEntry 11 }

slbNewAdvhcIcmpDownInterval OBJECT-TYPE
    SYNTAX  INTEGER (0..600)
    MAX-ACCESS  read-write
    STATUS  current
    DESCRIPTION
        "ICMP health check interval in the down state."
    ::= { slbNewAdvhcIcmpEntry 12 }

slbNewAdvhcIcmpInvert OBJECT-TYPE
    SYNTAX  SlbAdvhcEnaDis
    MAX-ACCESS  read-write
    STATUS  current
    DESCRIPTION
        "ICMP health check invert flag."
    ::= { slbNewAdvhcIcmpEntry 13 }

slbNewAdvhcIcmpCopy OBJECT-TYPE
    SYNTAX   DisplayString (SIZE (0..128))
    MAX-ACCESS  read-write
    STATUS  current
    DESCRIPTION
        "ICMP health check copy indicator."
    ::= { slbNewAdvhcIcmpEntry 14 }

slbNewAdvhcIcmpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcIcmpEntry 15 }


-- Advance Health Check UDP
---------------------------

slbCurAdvhcUdpTable  OBJECT-TYPE
    SYNTAX  SEQUENCE OF SlbCurAdvhcUdpEntry
    MAX-ACCESS  not-accessible
    STATUS  current
    DESCRIPTION
        "Note:This mib is not supported on VX instance of Virtualization."
    ::= { advhcCfg 47 }

slbCurAdvhcUdpEntry OBJECT-TYPE
    SYNTAX  SlbCurAdvhcUdpEntry
    MAX-ACCESS  not-accessible
    STATUS  current
    DESCRIPTION
        "."
    INDEX   { slbCurAdvhcUdpID }
    ::= { slbCurAdvhcUdpTable 1 }

SlbCurAdvhcUdpEntry ::= SEQUENCE {
    slbCurAdvhcUdpID               DisplayString,
    slbCurAdvhcUdpName             DisplayString,
    slbCurAdvhcUdpDPort            INTEGER,
    slbCurAdvhcUdpIPVer            SlbAdvhcIPVer,
    slbCurAdvhcUdpHostName         DisplayString,
    slbCurAdvhcUdpTransparent      SlbAdvhcEnaDis,
    slbCurAdvhcUdpInterval         INTEGER,
    slbCurAdvhcUdpRetries          INTEGER,
    slbCurAdvhcUdpRestoreRetries   INTEGER,
    slbCurAdvhcUdpTimeout          INTEGER,
    slbCurAdvhcUdpOverflow         INTEGER,
    slbCurAdvhcUdpDownInterval     INTEGER,
    slbCurAdvhcUdpInvert           SlbAdvhcEnaDis,
    slbCurAdvhcUdpPadding          SlbAdvhcEnaDis
    }

slbCurAdvhcUdpID OBJECT-TYPE
    SYNTAX   DisplayString (SIZE (0..128))
    MAX-ACCESS  read-only
    STATUS  current
    DESCRIPTION
        "UDP Health check id."
    ::= { slbCurAdvhcUdpEntry 1 }

slbCurAdvhcUdpName OBJECT-TYPE
    SYNTAX   DisplayString (SIZE (0..128))
    MAX-ACCESS  read-only
    STATUS  current
    DESCRIPTION
        "UDP Health check name."
    ::= { slbCurAdvhcUdpEntry 2 }

slbCurAdvhcUdpDPort OBJECT-TYPE
    SYNTAX  INTEGER (0..65534)
    MAX-ACCESS  read-only
    STATUS  current
    DESCRIPTION
        "UDP Health check destination port."
    ::= { slbCurAdvhcUdpEntry 3 }

slbCurAdvhcUdpIPVer OBJECT-TYPE
    SYNTAX  SlbAdvhcIPVer
    MAX-ACCESS  read-only
    STATUS  current
    DESCRIPTION
        "UDP Health check destination IP version."
    ::= { slbCurAdvhcUdpEntry 4 }

slbCurAdvhcUdpHostName OBJECT-TYPE
    SYNTAX   DisplayString (SIZE (0..128))
    MAX-ACCESS  read-only
    STATUS  current
    DESCRIPTION
        "UDP Health check destination hostname."
    ::= { slbCurAdvhcUdpEntry 5 }

slbCurAdvhcUdpTransparent OBJECT-TYPE
    SYNTAX  SlbAdvhcEnaDis
    MAX-ACCESS  read-only
    STATUS  current
    DESCRIPTION
        "UDP Health check transparent flag."
    ::= { slbCurAdvhcUdpEntry 6 }

slbCurAdvhcUdpInterval OBJECT-TYPE
    SYNTAX  INTEGER (1..600)
    MAX-ACCESS  read-only
    STATUS  current
    DESCRIPTION
        "UDP Health check interval."
    ::= { slbCurAdvhcUdpEntry 7 }

slbCurAdvhcUdpRetries OBJECT-TYPE
    SYNTAX  INTEGER (1..63)
    MAX-ACCESS  read-only
    STATUS  current
    DESCRIPTION
        "UDP Health check retries counter."
    ::= { slbCurAdvhcUdpEntry 8 }

slbCurAdvhcUdpRestoreRetries OBJECT-TYPE
    SYNTAX  INTEGER (1..63)
    MAX-ACCESS  read-only
    STATUS  current
    DESCRIPTION
        "UDP Health check retries counter in the down state."
    ::= { slbCurAdvhcUdpEntry 9 }

slbCurAdvhcUdpTimeout OBJECT-TYPE
    SYNTAX  INTEGER (1..63)
    MAX-ACCESS  read-only
    STATUS  current
    DESCRIPTION
        "UDP Health check timeout."
    ::= { slbCurAdvhcUdpEntry 10 }

slbCurAdvhcUdpOverflow OBJECT-TYPE
    SYNTAX  INTEGER (0..600)
    MAX-ACCESS  read-only
    STATUS  current
    DESCRIPTION
        "UDP Health check overflow flag."
    ::= { slbCurAdvhcUdpEntry 11 }

slbCurAdvhcUdpDownInterval OBJECT-TYPE
    SYNTAX  INTEGER (0..600)
    MAX-ACCESS  read-only
    STATUS  current
    DESCRIPTION
        "UDP Health check interval in the down state."
    ::= { slbCurAdvhcUdpEntry 12 }

slbCurAdvhcUdpInvert OBJECT-TYPE
    SYNTAX  SlbAdvhcEnaDis
    MAX-ACCESS  read-only
    STATUS  current
    DESCRIPTION
        "UDP Health check invert flag."
    ::= { slbCurAdvhcUdpEntry 13 }

slbCurAdvhcUdpPadding OBJECT-TYPE
    SYNTAX  SlbAdvhcEnaDis
    MAX-ACCESS  read-only
    STATUS  current
    DESCRIPTION
        "Current status of 'padding' setting for the UDP health check.
         This setting specifies if padding to 64 bytes should be done
         for the UDP health check packet."
    ::= { slbCurAdvhcUdpEntry 14 }


slbNewAdvhcUdpTable  OBJECT-TYPE
    SYNTAX  SEQUENCE OF SlbNewAdvhcUdpEntry
    MAX-ACCESS  not-accessible
    STATUS  current
    DESCRIPTION
        "Note:This mib is not supported on VX instance of Virtualization."
    ::= { advhcCfg 48 }

slbNewAdvhcUdpEntry OBJECT-TYPE
    SYNTAX  SlbNewAdvhcUdpEntry
    MAX-ACCESS  not-accessible
    STATUS  current
    DESCRIPTION
        "."
    INDEX   { slbNewAdvhcUdpID }
    ::= { slbNewAdvhcUdpTable 1 }

SlbNewAdvhcUdpEntry ::= SEQUENCE {
    slbNewAdvhcUdpID               DisplayString,
    slbNewAdvhcUdpName             DisplayString,
    slbNewAdvhcUdpDPort            INTEGER,
    slbNewAdvhcUdpIPVer            SlbAdvhcIPVer,
    slbNewAdvhcUdpHostName         DisplayString,
    slbNewAdvhcUdpTransparent      SlbAdvhcEnaDis,
    slbNewAdvhcUdpInterval         INTEGER,
    slbNewAdvhcUdpRetries          INTEGER,
    slbNewAdvhcUdpRestoreRetries   INTEGER,
    slbNewAdvhcUdpTimeout          INTEGER,
    slbNewAdvhcUdpOverflow         INTEGER,
    slbNewAdvhcUdpDownInterval     INTEGER,
    slbNewAdvhcUdpInvert           SlbAdvhcEnaDis,
    slbNewAdvhcUdpCopy             DisplayString,
    slbNewAdvhcUdpDelete           SlbAdvhcDelete,
    slbNewAdvhcUdpPadding          SlbAdvhcEnaDis
    }

slbNewAdvhcUdpID OBJECT-TYPE
    SYNTAX   DisplayString (SIZE (0..128))
    MAX-ACCESS  read-only
    STATUS  current
    DESCRIPTION
        "UDP Health check id."
    ::= { slbNewAdvhcUdpEntry 1 }

slbNewAdvhcUdpName OBJECT-TYPE
    SYNTAX   DisplayString (SIZE (0..128))
    MAX-ACCESS  read-write
    STATUS  current
    DESCRIPTION
        "UDP Health check name."
    ::= { slbNewAdvhcUdpEntry 2 }

slbNewAdvhcUdpDPort OBJECT-TYPE
    SYNTAX  INTEGER (0..65534)
    MAX-ACCESS  read-write
    STATUS  current
    DESCRIPTION
        "UDP Health check destination port."
    ::= { slbNewAdvhcUdpEntry 3 }

slbNewAdvhcUdpIPVer OBJECT-TYPE
    SYNTAX  SlbAdvhcIPVer
    MAX-ACCESS  read-write
    STATUS  current
    DESCRIPTION
        "UDP Health check destination IP version."
    ::= { slbNewAdvhcUdpEntry 4 }

slbNewAdvhcUdpHostName OBJECT-TYPE
    SYNTAX   DisplayString (SIZE (0..128))
    MAX-ACCESS  read-write
    STATUS  current
    DESCRIPTION
        "UDP Health check destination hostname."
    ::= { slbNewAdvhcUdpEntry 5 }

slbNewAdvhcUdpTransparent OBJECT-TYPE
    SYNTAX  SlbAdvhcEnaDis
    MAX-ACCESS  read-write
    STATUS  current
    DESCRIPTION
        "UDP Health check transparent flag."
    ::= { slbNewAdvhcUdpEntry 6 }

slbNewAdvhcUdpInterval OBJECT-TYPE
    SYNTAX  INTEGER (1..600)
    MAX-ACCESS  read-write
    STATUS  current
    DESCRIPTION
        "UDP Health check interval."
    ::= { slbNewAdvhcUdpEntry 7 }

slbNewAdvhcUdpRetries OBJECT-TYPE
    SYNTAX  INTEGER (1..63)
    MAX-ACCESS  read-write
    STATUS  current
    DESCRIPTION
        "UDP Health check retries counter."
    ::= { slbNewAdvhcUdpEntry 8 }

slbNewAdvhcUdpRestoreRetries OBJECT-TYPE
    SYNTAX  INTEGER (1..63)
    MAX-ACCESS  read-write
    STATUS  current
    DESCRIPTION
        "UDP Health check retries counter in the down state."
    ::= { slbNewAdvhcUdpEntry 9 }

slbNewAdvhcUdpTimeout OBJECT-TYPE
    SYNTAX  INTEGER (1..63)
    MAX-ACCESS  read-write
    STATUS  current
    DESCRIPTION
        "UDP Health check timeout."
    ::= { slbNewAdvhcUdpEntry 10 }

slbNewAdvhcUdpOverflow OBJECT-TYPE
    SYNTAX  INTEGER (0..600)
    MAX-ACCESS  read-write
    STATUS  current
    DESCRIPTION
        "UDP Health check overflow flag."
    ::= { slbNewAdvhcUdpEntry 11 }

slbNewAdvhcUdpDownInterval OBJECT-TYPE
    SYNTAX  INTEGER (0..600)
    MAX-ACCESS  read-write
    STATUS  current
    DESCRIPTION
        "UDP Health check interval in the down state."
    ::= { slbNewAdvhcUdpEntry 12 }

slbNewAdvhcUdpInvert OBJECT-TYPE
    SYNTAX  SlbAdvhcEnaDis
    MAX-ACCESS  read-write
    STATUS  current
    DESCRIPTION
        "UDP Health check invert flag."
    ::= { slbNewAdvhcUdpEntry 13 }

slbNewAdvhcUdpCopy OBJECT-TYPE
    SYNTAX   DisplayString (SIZE (0..128))
    MAX-ACCESS  read-write
    STATUS  current
    DESCRIPTION
        "UDP Health check copy indicator."
    ::= { slbNewAdvhcUdpEntry 14 }

slbNewAdvhcUdpDelete OBJECT-TYPE
    SYNTAX  SlbAdvhcDelete
    MAX-ACCESS  read-write
    STATUS  current
    DESCRIPTION
        "When set to the value of 2 (delete), the entire row is deleted. 
         When read, other(1) is returned. Setting the value to anything 
         other than 2(delete) has no effect on the state of the row."
    ::= { slbNewAdvhcUdpEntry 15 }

slbNewAdvhcUdpPadding OBJECT-TYPE
    SYNTAX  SlbAdvhcEnaDis
    MAX-ACCESS  read-write
    STATUS  current
    DESCRIPTION
        "Enabled/disable padding to 64 bytes for the UDP health check.
         When set to enable(1) UDP health check packets will be padded
         to 64 bytes. And when set to disable(2) the UDP health check
         packets will not be padded to 64 bytes."
    ::= { slbNewAdvhcUdpEntry 16 }


    -- ADVHC End

-- Advance Health Check LINK
---------------------------

slbCurAdvhcLinkTable  OBJECT-TYPE
    SYNTAX  SEQUENCE OF SlbCurAdvhcLinkEntry
    MAX-ACCESS  not-accessible
    STATUS  current
    DESCRIPTION
        "Note:This mib is not supported on VX instance of Virtualization."
    ::= { advhcCfg 49 }

slbCurAdvhcLinkEntry OBJECT-TYPE
    SYNTAX  SlbCurAdvhcLinkEntry
    MAX-ACCESS  not-accessible
    STATUS  current
    DESCRIPTION
        "."
    INDEX   { slbCurAdvhcLinkID }
    ::= { slbCurAdvhcLinkTable 1 }

SlbCurAdvhcLinkEntry ::= SEQUENCE {
    slbCurAdvhcLinkID               DisplayString,
    slbCurAdvhcLinkName             DisplayString,
    slbCurAdvhcLinkDPort            INTEGER,
    slbCurAdvhcLinkIPVer            SlbAdvhcIPVer,
    slbCurAdvhcLinkHostName         DisplayString,
    slbCurAdvhcLinkTransparent      SlbAdvhcEnaDis,
    slbCurAdvhcLinkInterval         INTEGER,
    slbCurAdvhcLinkRetries          INTEGER,
    slbCurAdvhcLinkRestoreRetries   INTEGER,
    slbCurAdvhcLinkTimeout          INTEGER,
    slbCurAdvhcLinkOverflow         INTEGER,
    slbCurAdvhcLinkDownInterval     INTEGER,
    slbCurAdvhcLinkInvert           SlbAdvhcEnaDis
    }

slbCurAdvhcLinkID OBJECT-TYPE
    SYNTAX   DisplayString (SIZE (0..128))
    MAX-ACCESS  read-only
    STATUS  current
    DESCRIPTION
        "Link Health check id."
    ::= { slbCurAdvhcLinkEntry 1 }

slbCurAdvhcLinkName OBJECT-TYPE
    SYNTAX   DisplayString (SIZE (0..128))
    MAX-ACCESS  read-only
    STATUS  current
    DESCRIPTION
        "Link Health check name."
    ::= { slbCurAdvhcLinkEntry 2 }

slbCurAdvhcLinkDPort OBJECT-TYPE
    SYNTAX  INTEGER (0..65534)
    MAX-ACCESS  read-only
    STATUS  current
    DESCRIPTION
        "Link Health check destination port."
    ::= { slbCurAdvhcLinkEntry 3 }

slbCurAdvhcLinkIPVer OBJECT-TYPE
    SYNTAX  SlbAdvhcIPVer
    MAX-ACCESS  read-only
    STATUS  current
    DESCRIPTION
        "Link Health check destination IP version."
    ::= { slbCurAdvhcLinkEntry 4 }

slbCurAdvhcLinkHostName OBJECT-TYPE
    SYNTAX   DisplayString (SIZE (0..128))
    MAX-ACCESS  read-only
    STATUS  current
    DESCRIPTION
        "Link Health check destination hostname."
    ::= { slbCurAdvhcLinkEntry 5 }

slbCurAdvhcLinkTransparent OBJECT-TYPE
    SYNTAX  SlbAdvhcEnaDis
    MAX-ACCESS  read-only
    STATUS  current
    DESCRIPTION
        "Link Health check transparent flag."
    ::= { slbCurAdvhcLinkEntry 6 }

slbCurAdvhcLinkInterval OBJECT-TYPE
    SYNTAX  INTEGER (1..600)
    MAX-ACCESS  read-only
    STATUS  current
    DESCRIPTION
        "Link Health check interval."
    ::= { slbCurAdvhcLinkEntry 7 }

slbCurAdvhcLinkRetries OBJECT-TYPE
    SYNTAX  INTEGER (1..63)
    MAX-ACCESS  read-only
    STATUS  current
    DESCRIPTION
        "Link Health check retries counter."
    ::= { slbCurAdvhcLinkEntry 8 }

slbCurAdvhcLinkRestoreRetries OBJECT-TYPE
    SYNTAX  INTEGER (1..63)
    MAX-ACCESS  read-only
    STATUS  current
    DESCRIPTION
        "Link Health check retries counter in down state."
    ::= { slbCurAdvhcLinkEntry 9 }

slbCurAdvhcLinkTimeout OBJECT-TYPE
    SYNTAX  INTEGER (1..63)
    MAX-ACCESS  read-only
    STATUS  current
    DESCRIPTION
        "Link Health check timeout."
    ::= { slbCurAdvhcLinkEntry 10 }

slbCurAdvhcLinkOverflow OBJECT-TYPE
    SYNTAX  INTEGER (0..600)
    MAX-ACCESS  read-only
    STATUS  current
    DESCRIPTION
        "Link Health check overflow flag."
    ::= { slbCurAdvhcLinkEntry 11 }

slbCurAdvhcLinkDownInterval OBJECT-TYPE
    SYNTAX  INTEGER (0..600)
    MAX-ACCESS  read-only
    STATUS  current
    DESCRIPTION
        "Link Health check interval in down state."
    ::= { slbCurAdvhcLinkEntry 12 }

slbCurAdvhcLinkInvert OBJECT-TYPE
    SYNTAX  SlbAdvhcEnaDis
    MAX-ACCESS  read-only
    STATUS  current
    DESCRIPTION
        "Link Health check invert flag."
    ::= { slbCurAdvhcLinkEntry 13 }

slbNewAdvhcLinkTable  OBJECT-TYPE
    SYNTAX  SEQUENCE OF SlbNewAdvhcLinkEntry
    MAX-ACCESS  not-accessible
    STATUS  current
    DESCRIPTION
        "Note:This mib is not supported on VX instance of Virtualization."
    ::= { advhcCfg 50 }

slbNewAdvhcLinkEntry OBJECT-TYPE
    SYNTAX  SlbNewAdvhcLinkEntry
    MAX-ACCESS  not-accessible
    STATUS  current
    DESCRIPTION
        "."
    INDEX   { slbNewAdvhcLinkID }
    ::= { slbNewAdvhcLinkTable 1 }

SlbNewAdvhcLinkEntry ::= SEQUENCE {
    slbNewAdvhcLinkID               DisplayString,
    slbNewAdvhcLinkName             DisplayString,
    slbNewAdvhcLinkDPort            INTEGER,
    slbNewAdvhcLinkIPVer            SlbAdvhcIPVer,
    slbNewAdvhcLinkHostName         DisplayString,
    slbNewAdvhcLinkTransparent      SlbAdvhcEnaDis,
    slbNewAdvhcLinkInterval         INTEGER,
    slbNewAdvhcLinkRetries          INTEGER,
    slbNewAdvhcLinkRestoreRetries   INTEGER,
    slbNewAdvhcLinkTimeout          INTEGER,
    slbNewAdvhcLinkOverflow         INTEGER,
    slbNewAdvhcLinkDownInterval     INTEGER,
    slbNewAdvhcLinkInvert           SlbAdvhcEnaDis,
    slbNewAdvhcLinkCopy             DisplayString,
    slbNewAdvhcLinkDelete           SlbAdvhcDelete
    }

slbNewAdvhcLinkID OBJECT-TYPE
    SYNTAX   DisplayString (SIZE (0..128))
    MAX-ACCESS  read-only
    STATUS  current
    DESCRIPTION
        "Link Health check id."
    ::= { slbNewAdvhcLinkEntry 1 }

slbNewAdvhcLinkName OBJECT-TYPE
    SYNTAX   DisplayString (SIZE (0..128))
    MAX-ACCESS  read-write
    STATUS  current
    DESCRIPTION
        "Link Health check name."
    ::= { slbNewAdvhcLinkEntry 2 }

slbNewAdvhcLinkDPort OBJECT-TYPE
    SYNTAX  INTEGER (0..65534)
    MAX-ACCESS  read-write
    STATUS  current
    DESCRIPTION
        "Link Health check destination port."
    ::= { slbNewAdvhcLinkEntry 3 }

slbNewAdvhcLinkIPVer OBJECT-TYPE
    SYNTAX  SlbAdvhcIPVer
    MAX-ACCESS  read-write
    STATUS  current
    DESCRIPTION
        "Link Health check destination IP version."
    ::= { slbNewAdvhcLinkEntry 4 }

slbNewAdvhcLinkHostName OBJECT-TYPE
    SYNTAX   DisplayString (SIZE (0..128))
    MAX-ACCESS  read-write
    STATUS  current
    DESCRIPTION
        "Link Health check destination hostname."
    ::= { slbNewAdvhcLinkEntry 5 }

slbNewAdvhcLinkTransparent OBJECT-TYPE
    SYNTAX  SlbAdvhcEnaDis
    MAX-ACCESS  read-write
    STATUS  current
    DESCRIPTION
        "Link Health check transparent flag."
    ::= { slbNewAdvhcLinkEntry 6 }

slbNewAdvhcLinkInterval OBJECT-TYPE
    SYNTAX  INTEGER (1..600)
    MAX-ACCESS  read-write
    STATUS  current
    DESCRIPTION
        "Link Health check interval."
    ::= { slbNewAdvhcLinkEntry 7 }

slbNewAdvhcLinkRetries OBJECT-TYPE
    SYNTAX  INTEGER (1..63)
    MAX-ACCESS  read-write
    STATUS  current
    DESCRIPTION
        "Link Health check retries counter."
    ::= { slbNewAdvhcLinkEntry 8 }

slbNewAdvhcLinkRestoreRetries OBJECT-TYPE
    SYNTAX  INTEGER (1..63)
    MAX-ACCESS  read-write
    STATUS  current
    DESCRIPTION
        "Link Health check retries counter in down state."
    ::= { slbNewAdvhcLinkEntry 9 }

slbNewAdvhcLinkTimeout OBJECT-TYPE
    SYNTAX  INTEGER (1..63)
    MAX-ACCESS  read-write
    STATUS  current
    DESCRIPTION
        "Link Health check timeout."
    ::= { slbNewAdvhcLinkEntry 10 }

slbNewAdvhcLinkOverflow OBJECT-TYPE
    SYNTAX  INTEGER (0..600)
    MAX-ACCESS  read-write
    STATUS  current
    DESCRIPTION
        "Link Health check overflow flag."
    ::= { slbNewAdvhcLinkEntry 11 }

slbNewAdvhcLinkDownInterval OBJECT-TYPE
    SYNTAX  INTEGER (0..600)
    MAX-ACCESS  read-write
    STATUS  current
    DESCRIPTION
        "Link Health check interval in down state."
    ::= { slbNewAdvhcLinkEntry 12 }

slbNewAdvhcLinkInvert OBJECT-TYPE
    SYNTAX  SlbAdvhcEnaDis
    MAX-ACCESS  read-write
    STATUS  current
    DESCRIPTION
        "Link Health check invert flag."
    ::= { slbNewAdvhcLinkEntry 13 }

slbNewAdvhcLinkCopy OBJECT-TYPE
    SYNTAX   DisplayString (SIZE (0..128))
    MAX-ACCESS  read-write
    STATUS  current
    DESCRIPTION
        "Link Health check copy indicator."
    ::= { slbNewAdvhcLinkEntry 14 }

slbNewAdvhcLinkDelete OBJECT-TYPE
    SYNTAX  SlbAdvhcDelete
    MAX-ACCESS  read-write
    STATUS  current
    DESCRIPTION
        "When set to the value of 2 (delete), the entire row is deleted.
         When read, other(1) is returned. Setting the value to anything
         other than 2(delete) has no effect on the state of the row."
    ::= { slbNewAdvhcLinkEntry 15 }

-- Advance Health Check Virtual Wire
---------------------------

slbCurAdvhcVirtualWireTable  OBJECT-TYPE
    SYNTAX  SEQUENCE OF SlbCurAdvhcVirtualWireEntry
    MAX-ACCESS  not-accessible
    STATUS  current
    DESCRIPTION
        "The table of Virtual Wire Health Check objects.
         Note:This mib is not supported on VX instance of Virtualization."
    ::= { advhcCfg 51 }

slbCurAdvhcVirtualWireEntry OBJECT-TYPE
    SYNTAX  SlbCurAdvhcVirtualWireEntry
    MAX-ACCESS  not-accessible
    STATUS  current
    DESCRIPTION
        "Information about a particular Virtual Wire Health Check configuration."
    INDEX   { slbCurAdvhcVirtualWireID }
    ::= { slbCurAdvhcVirtualWireTable 1 }

SlbCurAdvhcVirtualWireEntry ::= SEQUENCE {
    slbCurAdvhcVirtualWireID               DisplayString,
    slbCurAdvhcVirtualWireName             DisplayString,
    slbCurAdvhcVirtualWireDPort            INTEGER,
    slbCurAdvhcVirtualWireIPVer            SlbAdvhcIPVer,
    slbCurAdvhcVirtualWireHostName         DisplayString,
    slbCurAdvhcVirtualWireTransparent      SlbAdvhcEnaDis,
    slbCurAdvhcVirtualWireInterval         INTEGER,
    slbCurAdvhcVirtualWireRetries          INTEGER,
    slbCurAdvhcVirtualWireRestoreRetries   INTEGER,
    slbCurAdvhcVirtualWireTimeout          INTEGER,
    slbCurAdvhcVirtualWireOverflow         INTEGER,
    slbCurAdvhcVirtualWireDownInterval     INTEGER,
    slbCurAdvhcVirtualWireInvert           SlbAdvhcEnaDis
    }

slbCurAdvhcVirtualWireID OBJECT-TYPE
    SYNTAX   DisplayString (SIZE (0..128))
    MAX-ACCESS  read-only
    STATUS  current
    DESCRIPTION
        "Describes Virtual Wire Health Check ID."
    ::= { slbCurAdvhcVirtualWireEntry 1 }

slbCurAdvhcVirtualWireName OBJECT-TYPE
    SYNTAX   DisplayString (SIZE (0..128))
    MAX-ACCESS  read-only
    STATUS  current
    DESCRIPTION
        "Describes Virtual Wire Health Check Name."
    ::= { slbCurAdvhcVirtualWireEntry 2 }

slbCurAdvhcVirtualWireDPort OBJECT-TYPE
    SYNTAX  INTEGER (0..65534)
    MAX-ACCESS  read-only
    STATUS  current
    DESCRIPTION
        "Describes Virtual Wire Health Check destination port."
    ::= { slbCurAdvhcVirtualWireEntry 3 }

slbCurAdvhcVirtualWireIPVer OBJECT-TYPE
    SYNTAX  SlbAdvhcIPVer
    MAX-ACCESS  read-only
    STATUS  current
    DESCRIPTION
        "Describes Virtual Wire Health Check IP version."
    ::= { slbCurAdvhcVirtualWireEntry 4 }

slbCurAdvhcVirtualWireHostName OBJECT-TYPE
    SYNTAX   DisplayString (SIZE (0..128))
    MAX-ACCESS  read-only
    STATUS  current
    DESCRIPTION
        "Describes Virtual Wire Health Check host name."
    ::= { slbCurAdvhcVirtualWireEntry 5 }

slbCurAdvhcVirtualWireTransparent OBJECT-TYPE
    SYNTAX  SlbAdvhcEnaDis
    MAX-ACCESS  read-only
    STATUS  current
    DESCRIPTION
        "Describes Virtual Wire Health Check transparency mode."
    ::= { slbCurAdvhcVirtualWireEntry 6 }

slbCurAdvhcVirtualWireInterval OBJECT-TYPE
    SYNTAX  INTEGER (1..600)
    MAX-ACCESS  read-only
    STATUS  current
    DESCRIPTION
        "Describes Virtual Wire Health Check interval."
    ::= { slbCurAdvhcVirtualWireEntry 7 }

slbCurAdvhcVirtualWireRetries OBJECT-TYPE
    SYNTAX  INTEGER (1..63)
    MAX-ACCESS  read-only
    STATUS  current
    DESCRIPTION
        "Describes Virtual Wire Health Check maximum retries number."
    ::= { slbCurAdvhcVirtualWireEntry 8 }

slbCurAdvhcVirtualWireRestoreRetries OBJECT-TYPE
    SYNTAX  INTEGER (1..63)
    MAX-ACCESS  read-only
    STATUS  current
    DESCRIPTION
        "Describes Virtual Wire Health Check minimum restore retries number."
    ::= { slbCurAdvhcVirtualWireEntry 9 }

slbCurAdvhcVirtualWireTimeout OBJECT-TYPE
    SYNTAX  INTEGER (1..63)
    MAX-ACCESS  read-only
    STATUS  current
    DESCRIPTION
        "Describes Virtual Wire Health Check timeout."
    ::= { slbCurAdvhcVirtualWireEntry 10 }

slbCurAdvhcVirtualWireOverflow OBJECT-TYPE
    SYNTAX  INTEGER (0..600)
    MAX-ACCESS  read-only
    STATUS  current
    DESCRIPTION
        "Describes Virtual Wire Health Check Overflow."
    ::= { slbCurAdvhcVirtualWireEntry 11 }

slbCurAdvhcVirtualWireDownInterval OBJECT-TYPE
    SYNTAX  INTEGER (0..600)
    MAX-ACCESS  read-only
    STATUS  current
    DESCRIPTION
        "Describes Virtual Wire Health Check down interval."
    ::= { slbCurAdvhcVirtualWireEntry 12 }

slbCurAdvhcVirtualWireInvert OBJECT-TYPE
    SYNTAX  SlbAdvhcEnaDis
    MAX-ACCESS  read-only
    STATUS  current
    DESCRIPTION
        "Describes Virtual Wire Health Check invert state."
    ::= { slbCurAdvhcVirtualWireEntry 13 }

slbNewAdvhcVirtualWireTable  OBJECT-TYPE
    SYNTAX  SEQUENCE OF SlbNewAdvhcVirtualWireEntry
    MAX-ACCESS  not-accessible
    STATUS  current
    DESCRIPTION
        "The table of Virtual Wire Health Check objects.
         Note:This mib is not supported on VX instance of Virtualization."
    ::= { advhcCfg 52 }

slbNewAdvhcVirtualWireEntry OBJECT-TYPE
    SYNTAX  SlbNewAdvhcVirtualWireEntry
    MAX-ACCESS  not-accessible
    STATUS  current
    DESCRIPTION
        "Information about a particular Virtual Wire Health Check configuration."
    INDEX   { slbNewAdvhcVirtualWireID }
    ::= { slbNewAdvhcVirtualWireTable 1 }

SlbNewAdvhcVirtualWireEntry ::= SEQUENCE {
    slbNewAdvhcVirtualWireID               DisplayString,
    slbNewAdvhcVirtualWireName             DisplayString,
    slbNewAdvhcVirtualWireDPort            INTEGER,
    slbNewAdvhcVirtualWireIPVer            SlbAdvhcIPVer,
    slbNewAdvhcVirtualWireHostName         DisplayString,
    slbNewAdvhcVirtualWireTransparent      SlbAdvhcEnaDis,
    slbNewAdvhcVirtualWireInterval         INTEGER,
    slbNewAdvhcVirtualWireRetries          INTEGER,
    slbNewAdvhcVirtualWireRestoreRetries   INTEGER,
    slbNewAdvhcVirtualWireTimeout          INTEGER,
    slbNewAdvhcVirtualWireOverflow         INTEGER,
    slbNewAdvhcVirtualWireDownInterval     INTEGER,
    slbNewAdvhcVirtualWireInvert           SlbAdvhcEnaDis,
    slbNewAdvhcVirtualWireCopy             DisplayString,
    slbNewAdvhcVirtualWireDelete           SlbAdvhcDelete
    }

slbNewAdvhcVirtualWireID OBJECT-TYPE
    SYNTAX   DisplayString (SIZE (0..128))
    MAX-ACCESS  read-only
    STATUS  current
    DESCRIPTION
        "Set Virtual Wire Health Check ID."
    ::= { slbNewAdvhcVirtualWireEntry 1 }

slbNewAdvhcVirtualWireName OBJECT-TYPE
    SYNTAX   DisplayString (SIZE (0..128))
    MAX-ACCESS  read-write
    STATUS  current
    DESCRIPTION
        "Set Virtual Wire Health Check Name."
    ::= { slbNewAdvhcVirtualWireEntry 2 }

slbNewAdvhcVirtualWireDPort OBJECT-TYPE
    SYNTAX  INTEGER (0..65534)
    MAX-ACCESS  read-write
    STATUS  current
    DESCRIPTION
        "Set Virtual Wire Health Check destination port."
    ::= { slbNewAdvhcVirtualWireEntry 3 }

slbNewAdvhcVirtualWireIPVer OBJECT-TYPE
    SYNTAX  SlbAdvhcIPVer
    MAX-ACCESS  read-write
    STATUS  current
    DESCRIPTION
        "Set Virtual Wire Health Check IP version."
    ::= { slbNewAdvhcVirtualWireEntry 4 }

slbNewAdvhcVirtualWireHostName OBJECT-TYPE
    SYNTAX   DisplayString (SIZE (0..128))
    MAX-ACCESS  read-write
    STATUS  current
    DESCRIPTION
        "Set Virtual Wire Health Check host name."
    ::= { slbNewAdvhcVirtualWireEntry 5 }

slbNewAdvhcVirtualWireTransparent OBJECT-TYPE
    SYNTAX  SlbAdvhcEnaDis
    MAX-ACCESS  read-write
    STATUS  current
    DESCRIPTION
        "Set Virtual Wire Health Check transparency mode."
    ::= { slbNewAdvhcVirtualWireEntry 6 }

slbNewAdvhcVirtualWireInterval OBJECT-TYPE
    SYNTAX  INTEGER (1..600)
    MAX-ACCESS  read-write
    STATUS  current
    DESCRIPTION
        "Set Virtual Wire Health Check interval."
    ::= { slbNewAdvhcVirtualWireEntry 7 }

slbNewAdvhcVirtualWireRetries OBJECT-TYPE
    SYNTAX  INTEGER (1..63)
    MAX-ACCESS  read-write
    STATUS  current
    DESCRIPTION
        "Set Virtual Wire Health Check maximum retries number."
    ::= { slbNewAdvhcVirtualWireEntry 8 }

slbNewAdvhcVirtualWireRestoreRetries OBJECT-TYPE
    SYNTAX  INTEGER (1..63)
    MAX-ACCESS  read-write
    STATUS  current
    DESCRIPTION
        "Set Virtual Wire Health Check minimum restore retries number."
    ::= { slbNewAdvhcVirtualWireEntry 9 }

slbNewAdvhcVirtualWireTimeout OBJECT-TYPE
    SYNTAX  INTEGER (1..63)
    MAX-ACCESS  read-write
    STATUS  current
    DESCRIPTION
        "Set Virtual Wire Health Check timeout."
    ::= { slbNewAdvhcVirtualWireEntry 10 }

slbNewAdvhcVirtualWireOverflow OBJECT-TYPE
    SYNTAX  INTEGER (0..600)
    MAX-ACCESS  read-write
    STATUS  current
    DESCRIPTION
        "Set Virtual Wire Health Check Overflow."
    ::= { slbNewAdvhcVirtualWireEntry 11 }

slbNewAdvhcVirtualWireDownInterval OBJECT-TYPE
    SYNTAX  INTEGER (0..600)
    MAX-ACCESS  read-write
    STATUS  current
    DESCRIPTION
        "Set Virtual Wire Health Check down interval."
    ::= { slbNewAdvhcVirtualWireEntry 12 }

slbNewAdvhcVirtualWireInvert OBJECT-TYPE
    SYNTAX  SlbAdvhcEnaDis
    MAX-ACCESS  read-write
    STATUS  current
    DESCRIPTION
        "Set Virtual Wire Health Check invert state."
    ::= { slbNewAdvhcVirtualWireEntry 13 }

slbNewAdvhcVirtualWireCopy OBJECT-TYPE
    SYNTAX   DisplayString (SIZE (0..128))
    MAX-ACCESS  read-write
    STATUS  current
    DESCRIPTION
        "Copy Virtual Wire Health Check."
    ::= { slbNewAdvhcVirtualWireEntry 14 }

slbNewAdvhcVirtualWireDelete OBJECT-TYPE
    SYNTAX  SlbAdvhcDelete
    MAX-ACCESS  read-write
    STATUS  current
    DESCRIPTION
        "When set to the value of 2 (delete), the entire row is deleted.
         When read, other(1) is returned. Setting the value to anything
         other than 2(delete) has no effect on the state of the row."
    ::= { slbNewAdvhcVirtualWireEntry 15 }

slbAdvhcDsspTable  OBJECT-TYPE
    SYNTAX  SEQUENCE OF SlbAdvhcDsspEntry
    MAX-ACCESS  not-accessible
    STATUS  current
    DESCRIPTION
        "Note:This mib is not supported on VX instance of Virtualization."
    ::= { advhcCfg 53 }

slbAdvhcDsspEntry OBJECT-TYPE
    SYNTAX  SlbAdvhcDsspEntry
    MAX-ACCESS  not-accessible
    STATUS  current
    DESCRIPTION
        "."
    INDEX   { slbAdvhcDsspID }
    ::= { slbAdvhcDsspTable 1 }

SlbAdvhcDsspEntry ::= SEQUENCE {
    slbAdvhcDsspID               DisplayString,
    slbAdvhcDsspName             DisplayString,
    slbAdvhcDsspDPort            INTEGER,
    slbAdvhcDsspIPVer            SlbAdvhcIPVer,
    slbAdvhcDsspHostName         DisplayString,
    slbAdvhcDsspTransparent      SlbAdvhcEnaDis,
    slbAdvhcDsspInterval         INTEGER,
    slbAdvhcDsspRetries          INTEGER,
    slbAdvhcDsspRestoreRetries   INTEGER,
    slbAdvhcDsspTimeout          INTEGER
    }

slbAdvhcDsspID OBJECT-TYPE
    SYNTAX   DisplayString (SIZE (0..128))
    MAX-ACCESS  read-only
    STATUS  current
    DESCRIPTION
        "."
    ::= { slbAdvhcDsspEntry 1 }

slbAdvhcDsspName OBJECT-TYPE
    SYNTAX   DisplayString (SIZE (0..128))
    MAX-ACCESS  read-only
    STATUS  current
    DESCRIPTION
        "."
    ::= { slbAdvhcDsspEntry 2 }

slbAdvhcDsspDPort OBJECT-TYPE
    SYNTAX  INTEGER (0..65534)
    MAX-ACCESS  read-only
    STATUS  current
    DESCRIPTION
        "."
    ::= { slbAdvhcDsspEntry 3 }

slbAdvhcDsspIPVer OBJECT-TYPE
    SYNTAX  SlbAdvhcIPVer
    MAX-ACCESS  read-only
    STATUS  current
    DESCRIPTION
        "."
    ::= { slbAdvhcDsspEntry 4 }

slbAdvhcDsspHostName OBJECT-TYPE
    SYNTAX   DisplayString (SIZE (0..128))
    MAX-ACCESS  read-only
    STATUS  current
    DESCRIPTION
        "."
    ::= { slbAdvhcDsspEntry 5 }

slbAdvhcDsspTransparent OBJECT-TYPE
    SYNTAX  SlbAdvhcEnaDis
    MAX-ACCESS  read-only
    STATUS  current
    DESCRIPTION
        "."
    ::= { slbAdvhcDsspEntry 6 }

slbAdvhcDsspInterval OBJECT-TYPE
    SYNTAX  INTEGER (1..600)
    MAX-ACCESS  read-only
    STATUS  current
    DESCRIPTION
        "."
    ::= { slbAdvhcDsspEntry 7 }

slbAdvhcDsspRetries OBJECT-TYPE
    SYNTAX  INTEGER (1..63)
    MAX-ACCESS  read-only
    STATUS  current
    DESCRIPTION
        "."
    ::= { slbAdvhcDsspEntry 8 }

slbAdvhcDsspRestoreRetries OBJECT-TYPE
    SYNTAX  INTEGER (1..63)
    MAX-ACCESS  read-only
    STATUS  current
    DESCRIPTION
        "."
    ::= { slbAdvhcDsspEntry 9 }

slbAdvhcDsspTimeout OBJECT-TYPE
    SYNTAX  INTEGER (1..63)
    MAX-ACCESS  read-only
    STATUS  current
    DESCRIPTION
        "."
    ::= { slbAdvhcDsspEntry 10 }


-- Advance Health Check Advance Virtual Wire
---------------------------

slbCurAdvhcAdvVirtualWireTable  OBJECT-TYPE
    SYNTAX  SEQUENCE OF SlbCurAdvhcAdvVirtualWireEntry
    MAX-ACCESS  not-accessible
    STATUS  current
    DESCRIPTION
        "The table of Advanced Virtual Wire Health Check objects,
         Note:This mib is not supported for VX instance of Virtualization."
    ::= { advhcCfg 54 }

slbCurAdvhcAdvVirtualWireEntry OBJECT-TYPE
    SYNTAX  SlbCurAdvhcAdvVirtualWireEntry
    MAX-ACCESS  not-accessible
    STATUS  current
    DESCRIPTION
        "Information about a particular Advanced Virtual Wire Health Check configuration.
         Note:This mib is not supported for VX instance of Virtualization."
    INDEX   { slbCurAdvhcAdvVirtualWireID }
    ::= { slbCurAdvhcAdvVirtualWireTable 1 }

SlbCurAdvhcAdvVirtualWireEntry ::= SEQUENCE {
    slbCurAdvhcAdvVirtualWireID               DisplayString,
    slbCurAdvhcAdvVirtualWireName             DisplayString,
    slbCurAdvhcAdvVirtualWireDPort            INTEGER,
    slbCurAdvhcAdvVirtualWireIPVer            SlbAdvhcIPVer,
    slbCurAdvhcAdvVirtualWireHostName         DisplayString,
    slbCurAdvhcAdvVirtualWireTransparent      SlbAdvhcEnaDis,
    slbCurAdvhcAdvVirtualWireInterval         INTEGER,
    slbCurAdvhcAdvVirtualWireRetries          INTEGER,
    slbCurAdvhcAdvVirtualWireRestoreRetries   INTEGER,
    slbCurAdvhcAdvVirtualWireTimeout          INTEGER,
    slbCurAdvhcAdvVirtualWireOverflow         INTEGER,
    slbCurAdvhcAdvVirtualWireDownInterval     INTEGER,
    slbCurAdvhcAdvVirtualWireInvert           SlbAdvhcEnaDis
    }

slbCurAdvhcAdvVirtualWireID OBJECT-TYPE
    SYNTAX   DisplayString (SIZE (0..128))
    MAX-ACCESS  read-only
    STATUS  current
    DESCRIPTION
        "Describes Virtual Wire Health Check ID."
    ::= { slbCurAdvhcAdvVirtualWireEntry 1 }

slbCurAdvhcAdvVirtualWireName OBJECT-TYPE
    SYNTAX   DisplayString (SIZE (0..128))
    MAX-ACCESS  read-only
    STATUS  current
    DESCRIPTION
        "Describes Virtual Wire Health Check Name."
    ::= { slbCurAdvhcAdvVirtualWireEntry 2 }

slbCurAdvhcAdvVirtualWireDPort OBJECT-TYPE
    SYNTAX  INTEGER (0..65534)
    MAX-ACCESS  read-only
    STATUS  current
    DESCRIPTION
        "Describes Virtual Wire Health Check destination port."
    ::= { slbCurAdvhcAdvVirtualWireEntry 3 }

slbCurAdvhcAdvVirtualWireIPVer OBJECT-TYPE
    SYNTAX  SlbAdvhcIPVer
    MAX-ACCESS  read-only
    STATUS  current
    DESCRIPTION
        "Describes Virtual Wire Health Check IP version."
    ::= { slbCurAdvhcAdvVirtualWireEntry 4 }

slbCurAdvhcAdvVirtualWireHostName OBJECT-TYPE
    SYNTAX   DisplayString (SIZE (0..128))
    MAX-ACCESS  read-only
    STATUS  current
    DESCRIPTION
        "Describes Virtual Wire Health Check host name."
    ::= { slbCurAdvhcAdvVirtualWireEntry 5 }

slbCurAdvhcAdvVirtualWireTransparent OBJECT-TYPE
    SYNTAX  SlbAdvhcEnaDis
    MAX-ACCESS  read-only
    STATUS  current
    DESCRIPTION
        "Describes Virtual Wire Health Check transparency mode."
    ::= { slbCurAdvhcAdvVirtualWireEntry 6 }

slbCurAdvhcAdvVirtualWireInterval OBJECT-TYPE
    SYNTAX  INTEGER (1..600)
    MAX-ACCESS  read-only
    STATUS  current
    DESCRIPTION
        "Describes Virtual Wire Health Check interval."
    ::= { slbCurAdvhcAdvVirtualWireEntry 7 }

slbCurAdvhcAdvVirtualWireRetries OBJECT-TYPE
    SYNTAX  INTEGER (1..63)
    MAX-ACCESS  read-only
    STATUS  current
    DESCRIPTION
        "Describes Virtual Wire Health Check maximum retries number."
    ::= { slbCurAdvhcAdvVirtualWireEntry 8 }

slbCurAdvhcAdvVirtualWireRestoreRetries OBJECT-TYPE
    SYNTAX  INTEGER (1..63)
    MAX-ACCESS  read-only
    STATUS  current
    DESCRIPTION
        "Describes Virtual Wire Health Check minimum restore retries number."
    ::= { slbCurAdvhcAdvVirtualWireEntry 9 }

slbCurAdvhcAdvVirtualWireTimeout OBJECT-TYPE
    SYNTAX  INTEGER (1..600)
    MAX-ACCESS  read-only
    STATUS  current
    DESCRIPTION
        "Describes Virtual Wire Health Check timeout."
    ::= { slbCurAdvhcAdvVirtualWireEntry 10 }

slbCurAdvhcAdvVirtualWireOverflow OBJECT-TYPE
    SYNTAX  INTEGER (0..600)
    MAX-ACCESS  read-only
    STATUS  current
    DESCRIPTION
        "Describes Virtual Wire Health Check Overflow."
    ::= { slbCurAdvhcAdvVirtualWireEntry 11 }

slbCurAdvhcAdvVirtualWireDownInterval OBJECT-TYPE
    SYNTAX  INTEGER (0..600)
    MAX-ACCESS  read-only
    STATUS  current
    DESCRIPTION
        "Describes Virtual Wire Health Check down interval."
    ::= { slbCurAdvhcAdvVirtualWireEntry 12 }

slbCurAdvhcAdvVirtualWireInvert OBJECT-TYPE
    SYNTAX  SlbAdvhcEnaDis
    MAX-ACCESS  read-only
    STATUS  current
    DESCRIPTION
        "Describes Virtual Wire Health Check invert state."
    ::= { slbCurAdvhcAdvVirtualWireEntry 13 }

slbNewAdvhcAdvVirtualWireTable  OBJECT-TYPE
    SYNTAX  SEQUENCE OF SlbNewAdvhcAdvVirtualWireEntry
    MAX-ACCESS  not-accessible
    STATUS  current
    DESCRIPTION
        "The table of Advanced Virtual Wire Health Check objects,
         Note:This mib is not supported for VX instance of Virtualization."
    ::= { advhcCfg 55 }

slbNewAdvhcAdvVirtualWireEntry OBJECT-TYPE
    SYNTAX  SlbNewAdvhcAdvVirtualWireEntry
    MAX-ACCESS  not-accessible
    STATUS  current
    DESCRIPTION
        "Information about a particular Advanced Virtual Wire Health Check configuration.
         Note:This mib is not supported for VX instance of Virtualization."
    INDEX   { slbNewAdvhcAdvVirtualWireID }
    ::= { slbNewAdvhcAdvVirtualWireTable 1 }

SlbNewAdvhcAdvVirtualWireEntry ::= SEQUENCE {
    slbNewAdvhcAdvVirtualWireID               DisplayString,
    slbNewAdvhcAdvVirtualWireName             DisplayString,
    slbNewAdvhcAdvVirtualWireDPort            INTEGER,
    slbNewAdvhcAdvVirtualWireIPVer            SlbAdvhcIPVer,
    slbNewAdvhcAdvVirtualWireHostName         DisplayString,
    slbNewAdvhcAdvVirtualWireTransparent      SlbAdvhcEnaDis,
    slbNewAdvhcAdvVirtualWireInterval         INTEGER,
    slbNewAdvhcAdvVirtualWireRetries          INTEGER,
    slbNewAdvhcAdvVirtualWireRestoreRetries   INTEGER,
    slbNewAdvhcAdvVirtualWireTimeout          INTEGER,
    slbNewAdvhcAdvVirtualWireOverflow         INTEGER,
    slbNewAdvhcAdvVirtualWireDownInterval     INTEGER,
    slbNewAdvhcAdvVirtualWireInvert           SlbAdvhcEnaDis,
    slbNewAdvhcAdvVirtualWireCopy             DisplayString,
    slbNewAdvhcAdvVirtualWireDelete           SlbAdvhcDelete
    }

slbNewAdvhcAdvVirtualWireID OBJECT-TYPE
    SYNTAX   DisplayString (SIZE (0..128))
    MAX-ACCESS  read-only
    STATUS  current
    DESCRIPTION
        "Set Virtual Wire Health Check ID."
    ::= { slbNewAdvhcAdvVirtualWireEntry 1 }

slbNewAdvhcAdvVirtualWireName OBJECT-TYPE
    SYNTAX   DisplayString (SIZE (0..128))
    MAX-ACCESS  read-write
    STATUS  current
    DESCRIPTION
        "Set Virtual Wire Health Check Name."
    ::= { slbNewAdvhcAdvVirtualWireEntry 2 }

slbNewAdvhcAdvVirtualWireDPort OBJECT-TYPE
    SYNTAX  INTEGER (0..65534)
    MAX-ACCESS  read-write
    STATUS  current
    DESCRIPTION
        "Set Virtual Wire Health Check destination port."
    ::= { slbNewAdvhcAdvVirtualWireEntry 3 }

slbNewAdvhcAdvVirtualWireIPVer OBJECT-TYPE
    SYNTAX  SlbAdvhcIPVer
    MAX-ACCESS  read-write
    STATUS  current
    DESCRIPTION
        "Set Virtual Wire Health Check IP version."
    ::= { slbNewAdvhcAdvVirtualWireEntry 4 }

slbNewAdvhcAdvVirtualWireHostName OBJECT-TYPE
    SYNTAX   DisplayString (SIZE (0..128))
    MAX-ACCESS  read-write
    STATUS  current
    DESCRIPTION
        "Set Virtual Wire Health Check host name."
    ::= { slbNewAdvhcAdvVirtualWireEntry 5 }

slbNewAdvhcAdvVirtualWireTransparent OBJECT-TYPE
    SYNTAX  SlbAdvhcEnaDis
    MAX-ACCESS  read-write
    STATUS  current
    DESCRIPTION
        "Set Virtual Wire Health Check transparency mode."
    ::= { slbNewAdvhcAdvVirtualWireEntry 6 }

slbNewAdvhcAdvVirtualWireInterval OBJECT-TYPE
    SYNTAX  INTEGER (1..600)
    MAX-ACCESS  read-write
    STATUS  current
    DESCRIPTION
        "Set Virtual Wire Health Check interval."
    ::= { slbNewAdvhcAdvVirtualWireEntry 7 }

slbNewAdvhcAdvVirtualWireRetries OBJECT-TYPE
    SYNTAX  INTEGER (1..63)
    MAX-ACCESS  read-write
    STATUS  current
    DESCRIPTION
        "Set Virtual Wire Health Check maximum retries number."
    ::= { slbNewAdvhcAdvVirtualWireEntry 8 }

slbNewAdvhcAdvVirtualWireRestoreRetries OBJECT-TYPE
    SYNTAX  INTEGER (1..63)
    MAX-ACCESS  read-write
    STATUS  current
    DESCRIPTION
        "Set Virtual Wire Health Check minimum restore retries number."
    ::= { slbNewAdvhcAdvVirtualWireEntry 9 }

slbNewAdvhcAdvVirtualWireTimeout OBJECT-TYPE
    SYNTAX  INTEGER (1..600)
    MAX-ACCESS  read-write
    STATUS  current
    DESCRIPTION
        "Set Virtual Wire Health Check timeout."
    ::= { slbNewAdvhcAdvVirtualWireEntry 10 }

slbNewAdvhcAdvVirtualWireOverflow OBJECT-TYPE
    SYNTAX  INTEGER (0..600)
    MAX-ACCESS  read-write
    STATUS  current
    DESCRIPTION
        "Set Virtual Wire Health Check Overflow."
    ::= { slbNewAdvhcAdvVirtualWireEntry 11 }

slbNewAdvhcAdvVirtualWireDownInterval OBJECT-TYPE
    SYNTAX  INTEGER (0..600)
    MAX-ACCESS  read-write
    STATUS  current
    DESCRIPTION
        "Set Virtual Wire Health Check down interval."
    ::= { slbNewAdvhcAdvVirtualWireEntry 12 }

slbNewAdvhcAdvVirtualWireInvert OBJECT-TYPE
    SYNTAX  SlbAdvhcEnaDis
    MAX-ACCESS  read-write
    STATUS  current
    DESCRIPTION
        "Set Virtual Wire Health Check invert state."
    ::= { slbNewAdvhcAdvVirtualWireEntry 13 }

slbNewAdvhcAdvVirtualWireCopy OBJECT-TYPE
    SYNTAX   DisplayString (SIZE (0..128))
    MAX-ACCESS  read-write
    STATUS  current
    DESCRIPTION
        "Copy Virtual Wire Health Check."
    ::= { slbNewAdvhcAdvVirtualWireEntry 14 }

slbNewAdvhcAdvVirtualWireDelete OBJECT-TYPE
    SYNTAX  SlbAdvhcDelete
    MAX-ACCESS  read-write
    STATUS  current
    DESCRIPTION
        "When set to the value of 2 (delete), the entire row is deleted.
         When read, other(1) is returned. Setting the value to anything
         other than 2(delete) has no effect on the state of the row."
    ::= { slbNewAdvhcAdvVirtualWireEntry 15 }

-----------------------
-- Appwall Start
-----------------------

-- Appwall General Config

slbAppwallGeneralCfg  OBJECT IDENTIFIER ::= { appwallCfg 1 }

slbCurAppwallGenCfgWaf 	OBJECT-TYPE
    SYNTAX  INTEGER {
        disable(0),
        enable(1),
        unsupported(2147483647)
        }
     MAX-ACCESS  read-only
     STATUS  current
     DESCRIPTION
         "Appwall general config waf Ena \ Dis.
          Note:This mib is not supported for VX instance of Virtualization."
    ::= { slbAppwallGeneralCfg 1 }

slbNewAppwallGenCfgWaf 	OBJECT-TYPE
    SYNTAX  INTEGER {
        disable(0),
        enable(1),
        unsupported(2147483647)
        }
     MAX-ACCESS  read-write
     STATUS  current
     DESCRIPTION
         "Set Appwall general config waf Ena \ Dis.
          Note:This mib is not supported for VX instance of Virtualization."
    ::= { slbAppwallGeneralCfg 2 }

slbCurAppwallGenCfgAuthSso 	OBJECT-TYPE
    SYNTAX  INTEGER {
        disable(0),
        enable(1),
        unsupported(2147483647)
        }
     MAX-ACCESS  read-only
     STATUS  current
     DESCRIPTION
         "Appwall general config auth sso Ena \ Dis.
          Note:This mib is not supported for VX instance of Virtualization."
    ::= { slbAppwallGeneralCfg 3 }   
    
slbNewAppwallGenCfgAuthSso 	OBJECT-TYPE
    SYNTAX  INTEGER {
        disable(0),
        enable(1),
        unsupported(2147483647)
        }
     MAX-ACCESS  read-write
     STATUS  current
     DESCRIPTION
         "Set Appwall general config auth sso Ena \ Dis.
          Note:This mib is not supported for VX instance of Virtualization."
    ::= { slbAppwallGeneralCfg 4 } 
      
slbCurAppwallGenCfgCores 	OBJECT-TYPE
    SYNTAX  INTEGER (0..18)
     MAX-ACCESS  read-only
     STATUS  current
     DESCRIPTION
         "Set Appwall number of cores to use.
          Note:This mib is not supported for Virtualization and VA plateforms."
    ::= { slbAppwallGeneralCfg 5 }   

slbNewAppwallGenCfgCores 	OBJECT-TYPE
    SYNTAX  INTEGER (0..18)
     MAX-ACCESS  read-write
     STATUS  current
     DESCRIPTION
         "Set Appwall number of cores to use.
          Note:This mib is not supported for Virtualization and VA plateforms."
    ::= { slbAppwallGeneralCfg 6 }   
   
slbCurAppwallGenCfgHealthCheckStatus 	OBJECT-TYPE
    SYNTAX  INTEGER {
        disable(0),
        enable(1),
        unsupported(2147483647)
        }
     MAX-ACCESS  read-only
     STATUS  current
     DESCRIPTION
         "Appwall general config health check Ena \ Dis."
    ::= { slbAppwallGeneralCfg 9 }

slbNewAppwallGenCfgHealthCheckStatus 	OBJECT-TYPE
    SYNTAX  INTEGER {
        disable(0),
        enable(1),
        unsupported(2147483647)
        }
     MAX-ACCESS  read-write
     STATUS  current
     DESCRIPTION
         "Set Appwall general config health check Ena \ Dis."
    ::= { slbAppwallGeneralCfg 10 }
   
slbCurAppwallGenHealthCheckRetries 	OBJECT-TYPE
    SYNTAX  INTEGER (3..100)
     MAX-ACCESS  read-only
     STATUS  current
     DESCRIPTION
         "Set the number of failure health check retries before AppWall will be restarted."
    ::= { slbAppwallGeneralCfg 11 }

slbNewAppwallGenCfgHealthCheckRetries 	OBJECT-TYPE
    SYNTAX  INTEGER (3..100)
     MAX-ACCESS  read-write
     STATUS  current
     DESCRIPTION
         "Set the number of failure health check retries before AppWall will be restarted."
    ::= { slbAppwallGeneralCfg 12 }  

slbCurAppwallGenHealthCheckInterval 	OBJECT-TYPE
    SYNTAX  INTEGER (5..20)
     MAX-ACCESS  read-only
     STATUS  current
     DESCRIPTION
         "Set the time in seconds between health checks."
    ::= { slbAppwallGeneralCfg 13 }

slbNewAppwallGenCfgHealthCheckInterval 	OBJECT-TYPE
    SYNTAX  INTEGER (5..20)
     MAX-ACCESS  read-write
     STATUS  current
     DESCRIPTION
         "Set the time in seconds between health checks."
    ::= { slbAppwallGeneralCfg 14 }  

   
--- Cur Appwall Webapps 

slbCurAppwallWebappsCfgTable OBJECT-TYPE
    SYNTAX  SEQUENCE OF SlbCurAppwallCfgWebappsEntry
    MAX-ACCESS  not-accessible
    STATUS  current
    DESCRIPTION
        "Current secure web applications table.
         Note:This mib is not supported on VX instance of Virtualization."
    ::= { appwallCfg 2 }
    
slbCurAppwallCfgWebappsEntry OBJECT-TYPE
    SYNTAX  SlbCurAppwallCfgWebappsEntry
    MAX-ACCESS  not-accessible
    STATUS  current
    DESCRIPTION
        "A row in the current secure web applications table."
    INDEX   { slbCurAppwallWebappId }
    ::= { slbCurAppwallWebappsCfgTable 1 }

SlbCurAppwallCfgWebappsEntry ::= SEQUENCE {
    slbCurAppwallWebappId               DisplayString,
	slbCurAppwallWebappName             DisplayString,
	slbCurAppwallWebappEnable           INTEGER,
	slbCurAppwallWebappEnableWaf		INTEGER,
	slbCurAppwallWebappEnableAuthSso	INTEGER,
	slbCurAppwallWebappMode				INTEGER	
    }
    
slbCurAppwallWebappId OBJECT-TYPE
    SYNTAX   DisplayString (SIZE (0..32))
    MAX-ACCESS  read-only
    STATUS  current
    DESCRIPTION
        "Secure web application ID"
    ::= { slbCurAppwallCfgWebappsEntry 1 }
    	
slbCurAppwallWebappName OBJECT-TYPE
    SYNTAX   DisplayString (SIZE (0..32))
    MAX-ACCESS  read-only
    STATUS  current
    DESCRIPTION
        "Secure web application name."
    ::= { slbCurAppwallCfgWebappsEntry 2 }
	
slbCurAppwallWebappEnable OBJECT-TYPE
    SYNTAX  INTEGER {
        disable(0),
        enable(1),
        unsupported(2147483647)
        }
    MAX-ACCESS  read-only
    STATUS  current
    DESCRIPTION
        "Secure web application Ena \ Dis."
   ::= { slbCurAppwallCfgWebappsEntry 3 }

slbCurAppwallWebappEnableWaf OBJECT-TYPE
    SYNTAX  INTEGER {
        disable(0),
        enable(1),
        unsupported(2147483647)
        }
    MAX-ACCESS  read-only
    STATUS  current
    DESCRIPTION
        "Secure web application WAF Ena \ Dis."
   ::= { slbCurAppwallCfgWebappsEntry 4 }
   
slbCurAppwallWebappEnableAuthSso OBJECT-TYPE
    SYNTAX  INTEGER {
        disable(0),
        enable(1),
        unsupported(2147483647)
        }
    MAX-ACCESS  read-only
    STATUS  current
    DESCRIPTION
        "Secure web application Authentication SSO Ena \ Dis."
   ::= { slbCurAppwallCfgWebappsEntry 5 }   

slbCurAppwallWebappMode OBJECT-TYPE
    SYNTAX  INTEGER {
        oop(0),
        inline(1),
        unsupported(2147483647)
        }
    MAX-ACCESS  read-only
    STATUS  current
    DESCRIPTION
        "Secure web application mode."
   ::= { slbCurAppwallCfgWebappsEntry 6 }
   
--- New Appwall Webapps 
 
slbNewAppwallWebappsCfgTable OBJECT-TYPE
    SYNTAX  SEQUENCE OF SlbNewAppwallCfgWebappsEntry
    MAX-ACCESS  not-accessible
    STATUS  current
    DESCRIPTION
        "New secure web applications table.
         Note:This mib is not supported on VX instance of Virtualization."
    ::= { appwallCfg 3 }

slbNewAppwallCfgWebappsEntry OBJECT-TYPE
    SYNTAX  SlbNewAppwallCfgWebappsEntry
    MAX-ACCESS  not-accessible
    STATUS  current
    DESCRIPTION
        "A row in the new secure web applications table."
    INDEX   { slbNewAppwallWebappId }
    ::= { slbNewAppwallWebappsCfgTable 1 }
	
SlbNewAppwallCfgWebappsEntry ::= SEQUENCE {
    slbNewAppwallWebappId       		DisplayString,
	slbNewAppwallWebappName				DisplayString,
	slbNewAppwallWebappEnable			INTEGER,
	slbNewAppwallWebappEnableWaf		INTEGER,
	slbNewAppwallWebappEnableAuthSso	INTEGER,
	slbNewAppwallWebappMode				INTEGER,	
	slbNewAppwallWebappDel				INTEGER
    }	

slbNewAppwallWebappId OBJECT-TYPE
    SYNTAX   DisplayString (SIZE (0..32))
    MAX-ACCESS  read-only
    STATUS  current
    DESCRIPTION
        "Secure web application ID"
    ::= { slbNewAppwallCfgWebappsEntry 1 }
    
slbNewAppwallWebappName OBJECT-TYPE
    SYNTAX   DisplayString (SIZE (0..32))
    MAX-ACCESS  read-write
    STATUS  current
    DESCRIPTION
        "Secure web application name."
    ::= { slbNewAppwallCfgWebappsEntry 2 }

slbNewAppwallWebappEnable OBJECT-TYPE
    SYNTAX  INTEGER {
        disable(0),
        enable(1),
        unsupported(2147483647)
        }
    MAX-ACCESS  read-write
    STATUS  current
    DESCRIPTION
        "Secure web application Ena \ Dis."
   ::= { slbNewAppwallCfgWebappsEntry 3 }

slbNewAppwallWebappEnableWaf OBJECT-TYPE
    SYNTAX  INTEGER {
        disable(0),
        enable(1),
        unsupported(2147483647)
        }
    MAX-ACCESS  read-write
    STATUS  current
    DESCRIPTION
        "Secure web application WAF Ena \ Dis."
   ::= { slbNewAppwallCfgWebappsEntry 4 }
   
slbNewAppwallWebappEnableAuthSso OBJECT-TYPE
    SYNTAX  INTEGER {
        disable(0),
        enable(1),
        unsupported(2147483647)
        }
    MAX-ACCESS  read-write
    STATUS  current
    DESCRIPTION
        "Secure web application Authentication SSO Ena \ Dis."
   ::= { slbNewAppwallCfgWebappsEntry 5 }   

slbNewAppwallWebappMode OBJECT-TYPE
    SYNTAX  INTEGER {
        oop(0),
        inline(1),
        unsupported(2147483647)
        }
    MAX-ACCESS  read-write
    STATUS  current
    DESCRIPTION
        "Secure web application mode."
   ::= { slbNewAppwallCfgWebappsEntry 6 }
   
slbNewAppwallWebappDel OBJECT-TYPE
    SYNTAX  INTEGER {
        other(1),
        delete(2),
        unsupported(2147483647)
        }
    MAX-ACCESS  read-write
    STATUS  current
    DESCRIPTION
        "By setting the value to delete(2), the entire row is deleted."
    ::= { slbNewAppwallCfgWebappsEntry 7 }   


--- Cur Appwall Radius

slbCurAppwallRadiusCfgTable OBJECT-TYPE
    SYNTAX  SEQUENCE OF SlbCurAppwallCfgRadiusEntry
    MAX-ACCESS  not-accessible
    STATUS  current
    DESCRIPTION
        "Current secure web Radius servers table.
         Note:This mib is not supported on VX instance of Virtualization."
    ::= { appwallCfg 4 }
    
slbCurAppwallCfgRadiusEntry OBJECT-TYPE
    SYNTAX  SlbCurAppwallCfgRadiusEntry
    MAX-ACCESS  not-accessible
    STATUS  current
    DESCRIPTION
        "A row in the current secure web Radius servers table."
    INDEX   { slbCurAppwallRadiusId }
    ::= { slbCurAppwallRadiusCfgTable 1 }

SlbCurAppwallCfgRadiusEntry ::= SEQUENCE {
	slbCurAppwallRadiusId               	DisplayString,
	slbCurAppwallRadiusPrimaryIpAddress     DisplayString,
	slbCurAppwallRadiusPrimaryPort     	INTEGER,
	slbCurAppwallRadiusPrimarySecret     	DisplayString,
	slbCurAppwallRadiusSecondaryIpAddress   DisplayString,
	slbCurAppwallRadiusSecondaryPort     	INTEGER,
	slbCurAppwallRadiusSecondarySecret     	DisplayString,	
	slbCurAppwallRadiusRetries              INTEGER,
	slbCurAppwallRadiusTimeout              INTEGER,
	slbCurAppwallRadiusDel       		INTEGER,
	slbCurAppwallRadiusTertiaryIpAddress    DisplayString,
	slbCurAppwallRadiusTertiaryPort     	INTEGER,
	slbCurAppwallRadiusTertiarySecret     	DisplayString
    } 
	
slbCurAppwallRadiusId OBJECT-TYPE
    SYNTAX   DisplayString (SIZE (0..32))
    MAX-ACCESS  read-only
    STATUS  current
    DESCRIPTION
        "Secure web Radius server ID"
    ::= { slbCurAppwallCfgRadiusEntry 1 }	


slbCurAppwallRadiusPrimaryIpAddress OBJECT-TYPE
    SYNTAX DisplayString (SIZE (0..40))
    MAX-ACCESS  read-only
    STATUS  current
    DESCRIPTION
        "Secure web Radius Primary IP "
    ::= { slbCurAppwallCfgRadiusEntry 2 }  
          
slbCurAppwallRadiusPrimaryPort OBJECT-TYPE
    SYNTAX INTEGER (0..65535)
    MAX-ACCESS  read-only
    STATUS  current
    DESCRIPTION
        "Secure web Radius Primary Port "
    ::= { slbCurAppwallCfgRadiusEntry 3 }

slbCurAppwallRadiusPrimarySecret OBJECT-TYPE
    SYNTAX DisplayString (SIZE (0..32))
    MAX-ACCESS  read-only
    STATUS  current
    DESCRIPTION
        "Secure web Radius Primary secret "
    ::= { slbCurAppwallCfgRadiusEntry 4 }        


slbCurAppwallRadiusSecondaryIpAddress OBJECT-TYPE
    SYNTAX DisplayString (SIZE (0..40))
    MAX-ACCESS  read-only
    STATUS  current
    DESCRIPTION
        "Secure web Radius Secondary IP address "
    ::= { slbCurAppwallCfgRadiusEntry 5}	
    
slbCurAppwallRadiusSecondaryPort OBJECT-TYPE
    SYNTAX INTEGER (0..65535)
    MAX-ACCESS  read-only
    STATUS  current
    DESCRIPTION
        "Secure web Radius Secondary Port "
    ::= { slbCurAppwallCfgRadiusEntry 6}

slbCurAppwallRadiusSecondarySecret OBJECT-TYPE
    SYNTAX DisplayString (SIZE (0..32))
    MAX-ACCESS  read-only
    STATUS  current
    DESCRIPTION
        "Secure web Radius Secondary secret "
    ::= { slbCurAppwallCfgRadiusEntry 7 } 
        
slbCurAppwallRadiusRetries OBJECT-TYPE
    SYNTAX   INTEGER (0..5)
    MAX-ACCESS  read-only
    STATUS  current
    DESCRIPTION
        "Secure web Radius retries, default 3"
    ::= { slbCurAppwallCfgRadiusEntry 8 }

slbCurAppwallRadiusTimeout OBJECT-TYPE
    SYNTAX   INTEGER (1..30)
    MAX-ACCESS  read-only
    STATUS  current
    DESCRIPTION
        "Secure web Radius Timeout default 5 sec "
    ::= { slbCurAppwallCfgRadiusEntry 9 }

slbCurAppwallRadiusDel OBJECT-TYPE
    SYNTAX  INTEGER {
        other(1),
        delete(2),
        unsupported(2147483647)
        }
    MAX-ACCESS  read-only
    STATUS  current
    DESCRIPTION
        "By setting the value to delete(2), the entire row is deleted. On GET always other(1)"
    ::= { slbCurAppwallCfgRadiusEntry 12 }            	


slbCurAppwallRadiusTertiaryIpAddress OBJECT-TYPE
    SYNTAX DisplayString (SIZE (0..40))
    MAX-ACCESS  read-only
    STATUS  current
    DESCRIPTION
        "Secure web Radius Tertiary IP address "
    ::= { slbCurAppwallCfgRadiusEntry 13}	
    
slbCurAppwallRadiusTertiaryPort OBJECT-TYPE
    SYNTAX INTEGER (0..65535)
    MAX-ACCESS  read-only
    STATUS  current
    DESCRIPTION
        "Secure web Radius Tertiary Port "
    ::= { slbCurAppwallCfgRadiusEntry 14}

slbCurAppwallRadiusTertiarySecret OBJECT-TYPE
    SYNTAX DisplayString (SIZE (0..32))
    MAX-ACCESS  read-only
    STATUS  current
    DESCRIPTION
        "Secure web Radius Tertiary secret "
    ::= { slbCurAppwallCfgRadiusEntry 15 } 

--- New Appwall Radius

slbNewAppwallRadiusCfgTable OBJECT-TYPE
    SYNTAX  SEQUENCE OF SlbNewAppwallCfgRadiusEntry
    MAX-ACCESS  not-accessible
    STATUS  current
    DESCRIPTION
        "New secure web Radius servers table.
         Note:This mib is not supported on VX instance of Virtualization."
    ::= { appwallCfg 5 }
    
slbNewAppwallCfgRadiusEntry OBJECT-TYPE
    SYNTAX  SlbNewAppwallCfgRadiusEntry
    MAX-ACCESS  not-accessible
    STATUS  current
    DESCRIPTION
        "A row in the new secure web Radius servers table."
    INDEX   { slbNewAppwallRadiusId }
    ::= { slbNewAppwallRadiusCfgTable 1 }

SlbNewAppwallCfgRadiusEntry ::= SEQUENCE {
	slbNewAppwallRadiusId               	DisplayString,
	slbNewAppwallRadiusPrimaryIpAddress	DisplayString,
	slbNewAppwallRadiusPrimaryPort     	INTEGER,
	slbNewAppwallRadiusPrimarySecret     	DisplayString,
	slbNewAppwallRadiusSecondaryIpAddress  DisplayString,
	slbNewAppwallRadiusSecondaryPort     	INTEGER,
	slbNewAppwallRadiusSecondarySecret     	DisplayString,
	slbNewAppwallRadiusRetries              INTEGER,
	slbNewAppwallRadiusTimeout              INTEGER,
	slbNewAppwallRadiusDel			INTEGER,
	slbNewAppwallRadiusTertiaryIpAddress  DisplayString,
	slbNewAppwallRadiusTertiaryPort     	INTEGER,
	slbNewAppwallRadiusTertiarySecret     	DisplayString
    } 
	
slbNewAppwallRadiusId OBJECT-TYPE
    SYNTAX   DisplayString (SIZE (0..32))
    MAX-ACCESS  read-only
    STATUS  current
    DESCRIPTION
        "Secure web Radius server ID"
    ::= { slbNewAppwallCfgRadiusEntry 1 }

slbNewAppwallRadiusPrimaryIpAddress OBJECT-TYPE
    SYNTAX   DisplayString (SIZE (0..40))
    MAX-ACCESS  read-write
    STATUS  current
    DESCRIPTION
        "Secure web Radius Primary IP address "
    ::= { slbNewAppwallCfgRadiusEntry 2 }	
    
slbNewAppwallRadiusPrimaryPort OBJECT-TYPE
    SYNTAX INTEGER (0..65535)
    MAX-ACCESS  read-write
    STATUS  current
    DESCRIPTION
        "Secure web Radius Primary Port "
    ::= { slbNewAppwallCfgRadiusEntry 3 }

slbNewAppwallRadiusPrimarySecret OBJECT-TYPE
    SYNTAX DisplayString (SIZE (0..32))
    MAX-ACCESS  read-write
    STATUS  current
    DESCRIPTION
        "Secure web Radius Primary secret "
    ::= { slbNewAppwallCfgRadiusEntry 4 }        


slbNewAppwallRadiusSecondaryIpAddress OBJECT-TYPE
    SYNTAX   DisplayString (SIZE (0..40))
    MAX-ACCESS  read-write
    STATUS  current
    DESCRIPTION
        "Secure web Radius Secondary IP address "
    ::= { slbNewAppwallCfgRadiusEntry 5}	
    
slbNewAppwallRadiusSecondaryPort OBJECT-TYPE
    SYNTAX INTEGER (0..65535)
    MAX-ACCESS  read-write
    STATUS  current
    DESCRIPTION
        "Secure web Radius Secondary Port "
    ::= { slbNewAppwallCfgRadiusEntry 6 }

slbNewAppwallRadiusSecondarySecret OBJECT-TYPE
    SYNTAX DisplayString (SIZE (0..32))
    MAX-ACCESS  read-write
    STATUS  current
    DESCRIPTION
        "Secure web Radius Secondary secret "
    ::= { slbNewAppwallCfgRadiusEntry 7 }
    
slbNewAppwallRadiusRetries OBJECT-TYPE
    SYNTAX   INTEGER (0..5)
    MAX-ACCESS  read-write
    STATUS  current
    DESCRIPTION
        "Secure web Radius retries default 3"
    ::= { slbNewAppwallCfgRadiusEntry 8 }	
	
slbNewAppwallRadiusTimeout OBJECT-TYPE
    SYNTAX   INTEGER (1..30)
    MAX-ACCESS  read-write
    STATUS  current
    DESCRIPTION
        "Secure web Radius Timeout default 5 sec"
    ::= { slbNewAppwallCfgRadiusEntry 9 }
	
slbNewAppwallRadiusDel OBJECT-TYPE
    SYNTAX  INTEGER {
        other(1),
        delete(2),
        unsupported(2147483647)
        }
    MAX-ACCESS  read-write
    STATUS  current
    DESCRIPTION
        "By setting the value to delete(2), the entire row is deleted.On GET always other(1)"
    ::= { slbNewAppwallCfgRadiusEntry 12 }            	
	

slbNewAppwallRadiusTertiaryIpAddress OBJECT-TYPE
    SYNTAX   DisplayString (SIZE (0..40))
    MAX-ACCESS  read-write
    STATUS  current
    DESCRIPTION
        "Secure web Radius Tertiary IP address "
    ::= { slbNewAppwallCfgRadiusEntry 13}	
    
slbNewAppwallRadiusTertiaryPort OBJECT-TYPE
    SYNTAX INTEGER (0..65535)
    MAX-ACCESS  read-write
    STATUS  current
    DESCRIPTION
        "Secure web Radius Tertiary Port "
    ::= { slbNewAppwallCfgRadiusEntry 14 }

slbNewAppwallRadiusTertiarySecret OBJECT-TYPE
    SYNTAX DisplayString (SIZE (0..32))
    MAX-ACCESS  read-write
    STATUS  current
    DESCRIPTION
        "Secure web Radius Tertiary secret "
    ::= { slbNewAppwallCfgRadiusEntry 15 }

--- Current Appwall Ldap
slbCurAppwallLdapCfgTable OBJECT-TYPE
    SYNTAX  SEQUENCE OF SlbCurAppwallCfgLdapEntry
    MAX-ACCESS  not-accessible
    STATUS  current
    DESCRIPTION
        "Cur web Ldap servers table.
         Note:This mib is not supported on VX instance of Virtualization."
    ::= { appwallCfg 6 }
    
slbCurAppwallCfgLdapEntry OBJECT-TYPE
    SYNTAX  SlbCurAppwallCfgLdapEntry
    MAX-ACCESS  not-accessible
    STATUS  current
    DESCRIPTION
        "A row in the current secure web Ldap servers table."
    INDEX   { slbCurAppwallLdapId }
    ::= { slbCurAppwallLdapCfgTable 1 }

SlbCurAppwallCfgLdapEntry ::= SEQUENCE {
	slbCurAppwallLdapId               	DisplayString,
	slbCurAppwallLdapPrimaryIpAddress    	DisplayString,
	slbCurAppwallLdapPrimaryPort     	INTEGER,
	slbCurAppwallLdapSecondaryIpAddress  	DisplayString,
	slbCurAppwallLdapSecondaryPort     	INTEGER,
	slbCurAppwallLdapReqTimeoutSec		INTEGER,
	slbCurAppwallLdapHostTimeoutSec		INTEGER,
	slbCurAppwallLdapSSLEnable		INTEGER,
	slbCurAppwallLdapTLSEnable		INTEGER,
	slbCurAppwallLdapSrvType	        INTEGER,
	slbCurAppwallLdapBase    		DisplayString,
	slbCurAppwallLdapUserTest    		DisplayString,
	slbCurAppwallLdapPassTest    		DisplayString,
	slbCurAppwallLdapDel       		INTEGER,
	slbCurAppwallLdapIgnoreEnable		INTEGER
    } 
slbCurAppwallLdapId OBJECT-TYPE
    SYNTAX   DisplayString (SIZE (0..32))
    MAX-ACCESS  read-only
    STATUS  current
    DESCRIPTION
        "Secure web Ldap server ID"
    ::= { slbCurAppwallCfgLdapEntry 1 }	

slbCurAppwallLdapPrimaryIpAddress OBJECT-TYPE
    SYNTAX DisplayString (SIZE (0..40))
    MAX-ACCESS  read-only
    STATUS  current
    DESCRIPTION
        "Secure web Ldap Primary IP "
    ::= { slbCurAppwallCfgLdapEntry 2 }  
          
slbCurAppwallLdapPrimaryPort OBJECT-TYPE
    SYNTAX INTEGER (1..65535)
    MAX-ACCESS  read-only
    STATUS  current
    DESCRIPTION
        "Secure web Ldap Primary Port "
    ::= { slbCurAppwallCfgLdapEntry 3 }

slbCurAppwallLdapSecondaryIpAddress OBJECT-TYPE
    SYNTAX DisplayString (SIZE (0..40))
    MAX-ACCESS  read-only
    STATUS  current
    DESCRIPTION
        "Secure web Ldap Secondary IP address "
    ::= { slbCurAppwallCfgLdapEntry 4}	
    
slbCurAppwallLdapSecondaryPort OBJECT-TYPE
    SYNTAX INTEGER (1..65535)
    MAX-ACCESS  read-only
    STATUS  current
    DESCRIPTION
        "Secure web Ldap Secondary Port , default 3268"
    ::= { slbCurAppwallCfgLdapEntry 5}

slbCurAppwallLdapReqTimeoutSec OBJECT-TYPE
    SYNTAX INTEGER (1..30)
    MAX-ACCESS  read-only
    STATUS  current
    DESCRIPTION
        "Secure web Ldap Request timeout in seconds, default 5"
    ::= { slbCurAppwallCfgLdapEntry 6}

slbCurAppwallLdapHostTimeoutSec OBJECT-TYPE
    SYNTAX INTEGER (1..30)
    MAX-ACCESS  read-only
    STATUS  current
    DESCRIPTION
        "Secure web Ldap Host timeout in seconds, default 5"
    ::= { slbCurAppwallCfgLdapEntry 7}

slbCurAppwallLdapSSLEnable OBJECT-TYPE
    SYNTAX  INTEGER {
        disable(0),
        enable(1),
        unsupported(2147483647)
        }
    MAX-ACCESS  read-only
    STATUS  current
    DESCRIPTION
        "Secure web Ldap SSL En/Dis."
   ::= { slbCurAppwallCfgLdapEntry 8 }

slbCurAppwallLdapTLSEnable OBJECT-TYPE
    SYNTAX  INTEGER {
        disable(0),
        enable(1),
        unsupported(2147483647)
        }
    MAX-ACCESS  read-only
    STATUS  current
    DESCRIPTION
        "Secure web Ldap TLS En/Dis."
   ::= { slbCurAppwallCfgLdapEntry 9 }


slbCurAppwallLdapSrvType OBJECT-TYPE
    SYNTAX  INTEGER {
        microsoftActDirect(0),
	redhatDirect(1),
	appleOpenDirect(2),
	otherDirect(3),
        unsupported(2147483647)
        }
    MAX-ACCESS  read-only
    STATUS  current
    DESCRIPTION
        "Secure web Ldap server type.default microsoftActDirect"
   ::= { slbCurAppwallCfgLdapEntry 10 }

slbCurAppwallLdapBase OBJECT-TYPE
    SYNTAX   DisplayString (SIZE (0..100))
    MAX-ACCESS  read-only
    STATUS  current
    DESCRIPTION
        "Secure web Ldap Base path"
    ::= { slbCurAppwallCfgLdapEntry 11 }
    
slbCurAppwallLdapUserTest OBJECT-TYPE
    SYNTAX   DisplayString (SIZE (0..32))
    MAX-ACCESS  read-only
    STATUS  current
    DESCRIPTION
        "Secure web Ldap User Test"
    ::= { slbCurAppwallCfgLdapEntry 12 }

slbCurAppwallLdapPassTest OBJECT-TYPE
    SYNTAX   DisplayString (SIZE (0..150))
    MAX-ACCESS  read-only
    STATUS  current
    DESCRIPTION
        "Secure web Ldap Password"
    ::= { slbCurAppwallCfgLdapEntry 13 }

slbCurAppwallLdapDel OBJECT-TYPE
    SYNTAX  INTEGER {
        other(1),
        delete(2),
        unsupported(2147483647)
        }
    MAX-ACCESS  read-only
    STATUS  current
    DESCRIPTION
        "By setting the value to delete(2), the entire row is deleted.On GET always other(1)"
    ::= { slbCurAppwallCfgLdapEntry 14 }   
  
  
slbCurAppwallLdapIgnoreEnable OBJECT-TYPE
    SYNTAX  INTEGER {
        disable(0),
        enable(1),
        unsupported(2147483647)
        }
    MAX-ACCESS  read-only
    STATUS  current
    DESCRIPTION
        "Secure web Ldap Ignore En/Dis."
   ::= { slbCurAppwallCfgLdapEntry 15}
--- New Appwall Ldap

slbNewAppwallLdapCfgTable OBJECT-TYPE
    SYNTAX  SEQUENCE OF SlbNewAppwallCfgLdapEntry
    MAX-ACCESS  not-accessible
    STATUS  current
    DESCRIPTION
        "New web Ldap servers table.
         Note:This mib is not supported on VX instance of Virtualization."
    ::= { appwallCfg 7 }
    
slbNewAppwallCfgLdapEntry OBJECT-TYPE
    SYNTAX  SlbNewAppwallCfgLdapEntry
    MAX-ACCESS  not-accessible
    STATUS  current
    DESCRIPTION
        "A row in the current secure web Ldap servers table."
    INDEX   { slbNewAppwallLdapId }
    ::= { slbNewAppwallLdapCfgTable 1 }

SlbNewAppwallCfgLdapEntry ::= SEQUENCE {
	slbNewAppwallLdapId               	DisplayString,
	slbNewAppwallLdapPrimaryIpAddress    	DisplayString,
	slbNewAppwallLdapPrimaryPort     	INTEGER,
	slbNewAppwallLdapSecondaryIpAddress  	DisplayString,
	slbNewAppwallLdapSecondaryPort     	INTEGER,
	slbNewAppwallLdapReqTimeoutSec		INTEGER,
	slbNewAppwallLdapHostTimeoutSec		INTEGER,
	slbNewAppwallLdapSSLEnable		INTEGER,
	slbNewAppwallLdapTLSEnable		INTEGER,
	slbNewAppwallLdapSrvType	        INTEGER,
	slbNewAppwallLdapBase    		DisplayString,
	slbNewAppwallLdapUserTest    		DisplayString,
	slbNewAppwallLdapPassTest    		DisplayString,
	slbNewAppwallLdapDel       		INTEGER,
	slbNewAppwallLdapIgnoreEnable		INTEGER
    } 
	
slbNewAppwallLdapId OBJECT-TYPE
    SYNTAX   DisplayString (SIZE (0..32))
    MAX-ACCESS  read-only
    STATUS  current
    DESCRIPTION
        "Secure web Ldap server ID"
    ::= { slbNewAppwallCfgLdapEntry 1 }	

slbNewAppwallLdapPrimaryIpAddress OBJECT-TYPE
    SYNTAX DisplayString (SIZE (0..40))
    MAX-ACCESS  read-write
    STATUS  current
    DESCRIPTION
        "Secure web Ldap Primary IP "
    ::= { slbNewAppwallCfgLdapEntry 2 }  
          
slbNewAppwallLdapPrimaryPort OBJECT-TYPE
    SYNTAX INTEGER (1..65535)
    MAX-ACCESS  read-write
    STATUS  current
    DESCRIPTION
        "Secure web Ldap Primary Port "
    ::= { slbNewAppwallCfgLdapEntry 3 }

slbNewAppwallLdapSecondaryIpAddress OBJECT-TYPE
    SYNTAX DisplayString (SIZE (0..40))
    MAX-ACCESS  read-write
    STATUS  current
    DESCRIPTION
        "Secure web Ldap Secondary IP address "
    ::= { slbNewAppwallCfgLdapEntry 4}	
    
slbNewAppwallLdapSecondaryPort OBJECT-TYPE
    SYNTAX INTEGER (1..65535)
    MAX-ACCESS  read-write
    STATUS  current
    DESCRIPTION
        "Secure web Ldap Secondary Port "
    ::= { slbNewAppwallCfgLdapEntry 5}

slbNewAppwallLdapReqTimeoutSec OBJECT-TYPE
    SYNTAX INTEGER (1..30)
    MAX-ACCESS  read-write
    STATUS  current
    DESCRIPTION
        "Secure web Ldap Request timeout in seconds"
    ::= { slbNewAppwallCfgLdapEntry 6}

slbNewAppwallLdapHostTimeoutSec OBJECT-TYPE
    SYNTAX INTEGER (1..30)
    MAX-ACCESS  read-write
    STATUS  current
    DESCRIPTION
        "Secure web Ldap Host timeout in seconds"
    ::= { slbNewAppwallCfgLdapEntry 7}

slbNewAppwallLdapSSLEnable OBJECT-TYPE
    SYNTAX  INTEGER {
        disable(0),
        enable(1),
        unsupported(2147483647)
        }
    MAX-ACCESS  read-write
    STATUS  current
    DESCRIPTION
        "Secure web Ldap SSL En/Dis."
   ::= { slbNewAppwallCfgLdapEntry 8 }

slbNewAppwallLdapTLSEnable OBJECT-TYPE
    SYNTAX  INTEGER {
        disable(0),
        enable(1),
        unsupported(2147483647)
        }
    MAX-ACCESS  read-write
    STATUS  current
    DESCRIPTION
        "Secure web Ldap TLS En/Dis."
   ::= { slbNewAppwallCfgLdapEntry 9 }


slbNewAppwallLdapSrvType OBJECT-TYPE
    SYNTAX  INTEGER {
        microsoftActDirect(0),
	redhatDirect(1),
	appleOpenDirect(2),
	otherDirect(3),
        unsupported(2147483647)
        }
    MAX-ACCESS  read-write
    STATUS  current
    DESCRIPTION
        "Secure web Ldap server type."
   ::= { slbNewAppwallCfgLdapEntry 10 }

slbNewAppwallLdapBase OBJECT-TYPE
    SYNTAX   DisplayString (SIZE (0..100))
    MAX-ACCESS  read-write
    STATUS  current
    DESCRIPTION
        "Secure web Ldap Base path"
    ::= { slbNewAppwallCfgLdapEntry 11 }
    
slbNewAppwallLdapUserTest OBJECT-TYPE
    SYNTAX   DisplayString (SIZE (0..32))
    MAX-ACCESS  read-write
    STATUS  current
    DESCRIPTION
        "Secure web Ldap User Test"
    ::= { slbNewAppwallCfgLdapEntry 12 }

slbNewAppwallLdapPassTest OBJECT-TYPE
    SYNTAX   DisplayString (SIZE (0..150))
    MAX-ACCESS  read-write
    STATUS  current
    DESCRIPTION
        "Secure web Ldap Password"
    ::= { slbNewAppwallCfgLdapEntry 13 }

slbNewAppwallLdapDel OBJECT-TYPE
    SYNTAX  INTEGER {
        other(1),
        delete(2),
        unsupported(2147483647)
        }
    MAX-ACCESS  read-write
    STATUS  current
    DESCRIPTION
        "By setting the value to delete(2), the entire row is deleted.On GET always other(1)"
    ::= { slbNewAppwallCfgLdapEntry 14 }   
    
slbNewAppwallLdapIgnoreEnable OBJECT-TYPE
    SYNTAX  INTEGER {
        disable(0),
        enable(1),
        unsupported(2147483647)
        }
    MAX-ACCESS  read-write
    STATUS  current
    DESCRIPTION
        "Secure web Ldap Ignore En/Dis."
   ::= { slbNewAppwallCfgLdapEntry 15 } 

 --- Cur Appwall Reporter

slbCurAppwallReporterCfg  OBJECT IDENTIFIER ::= { appwallCfg 8}

slbCurAppwallReporterIpAddress OBJECT-TYPE
    SYNTAX DisplayString (SIZE (0..40))
    MAX-ACCESS  read-only
    STATUS  current
    DESCRIPTION
        "Secure web Reporter IP.
         Note:This mib is not supported for VX instance of Virtualization."
    ::= { slbCurAppwallReporterCfg 1 }  
          
slbCurAppwallReporterPort OBJECT-TYPE
    SYNTAX INTEGER (1..65535)
    MAX-ACCESS  read-only
    STATUS  current
    DESCRIPTION
        "Secure web Reporter Port.
         Note:This mib is not supported for VX instance of Virtualization."
    ::= { slbCurAppwallReporterCfg 2 } 


slbCurAppwallReporterPciRep OBJECT-TYPE
    SYNTAX  INTEGER {
        tcp(0),
        udp(1),
        unsupported(2147483647)
        }
    MAX-ACCESS  read-only
    STATUS  current
    DESCRIPTION
        "Secure web Reporter Pci tcp/udp, default tcp.
         Note:This mib is not supported for VX instance of Virtualization."
   ::= { slbCurAppwallReporterCfg 3 }

slbCurAppwallReporterSecLog OBJECT-TYPE
    SYNTAX  INTEGER {
        tcp(0),
        udp(1),
        unsupported(2147483647)
        }
    MAX-ACCESS  read-only
    STATUS  current
    DESCRIPTION
        "Secure web Reporter Secuirity LOG tcp/udp, default tcp.
         Note:This mib is not supported for VX instance of Virtualization."
   ::= { slbCurAppwallReporterCfg 4 }

slbCurAppwallReporterAudit OBJECT-TYPE
    SYNTAX  INTEGER {
        tcp(0),
        udp(1),
        unsupported(2147483647)
        }
    MAX-ACCESS  read-only
    STATUS  current
    DESCRIPTION
        "Secure web Reporter Audit tcp/udp, default tcp.
         Note:This mib is not supported for VX instance of Virtualization."
   ::= { slbCurAppwallReporterCfg 5 }

slbCurAppwallReporterOthLog OBJECT-TYPE
    SYNTAX  INTEGER {
        tcp(0),
        udp(1),
        unsupported(2147483647)
        }
    MAX-ACCESS  read-only
    STATUS  current
    DESCRIPTION
        "Secure web Reporter Other LOGS tcp/udp, default tcp.
         Note:This mib is not supported for VX instance of Virtualization."
   ::= { slbCurAppwallReporterCfg 6}

slbCurAppwallReporterTenant OBJECT-TYPE
    SYNTAX  INTEGER {
        disable(0),
        enable(1),
        unsupported(2147483647)
        }
    MAX-ACCESS  read-only
    STATUS  current
    DESCRIPTION
        "Secure web Reporter TenantEnable/disable, default disable.
         Note:This mib is not supported for VX instance of Virtualization."
   ::= { slbCurAppwallReporterCfg 7 }

slbCurAppwallReporterTenantHdrName OBJECT-TYPE
    SYNTAX DisplayString (SIZE (0..40))
    MAX-ACCESS  read-only
    STATUS  current
    DESCRIPTION
        "Secure web Tenant Header Name only if tenant enable, otherwise null.
         Note:This mib is not supported for VX instance of Virtualization."
    ::= { slbCurAppwallReporterCfg 8 }     
    
slbCurAppwallReporterTenantHdrNameId OBJECT-TYPE
    SYNTAX DisplayString (SIZE (0..40))
    MAX-ACCESS  read-only
    STATUS  current
    DESCRIPTION
        "Secure web Tenant Header Name Id only if tenant enable, otherwise null.
         Note:This mib is not supported for VX instance of Virtualization."
    ::= { slbCurAppwallReporterCfg 9 }          
    
slbCurAppwallReporterOnOff OBJECT-TYPE
    SYNTAX  INTEGER {
        off(0),
        on(1),
        unsupported(2147483647)
        }
    MAX-ACCESS  read-only
    STATUS  current
    DESCRIPTION
        "Secure web Reporter On/Off, default off.
         Note:This mib is not supported for VX instance of Virtualization."
   ::= { slbCurAppwallReporterCfg 10}

slbCurAppwallReporterHighPrio OBJECT-TYPE
    SYNTAX  INTEGER {
        tcp(0),
        udp(1),
        unsupported(2147483647)
        }
    MAX-ACCESS  read-only
    STATUS  current
    DESCRIPTION
        "Secure web Reporter High Priority tcp/udp, default tcp.
         Note:This mib is not supported for VX instance of Virtualization."
   ::= { slbCurAppwallReporterCfg 11 }


 --- New Appwall Reporter

slbNewAppwallReporterCfg  OBJECT IDENTIFIER ::= { appwallCfg 9}


slbNewAppwallReporterIpAddress OBJECT-TYPE
    SYNTAX DisplayString (SIZE (0..40))
    MAX-ACCESS  read-write
    STATUS  current
    DESCRIPTION
        "Secure web Reporter IP.
         Note:This mib is not supported for VX instance of Virtualization."
    ::= { slbNewAppwallReporterCfg 1 }  
          
slbNewAppwallReporterPort OBJECT-TYPE
    SYNTAX INTEGER (1..65535)
    MAX-ACCESS  read-write
    STATUS  current
    DESCRIPTION
        "Secure web Reporter Port.
         Note:This mib is not supported for VX instance of Virtualization."
    ::= { slbNewAppwallReporterCfg 2 } 


slbNewAppwallReporterPciRep OBJECT-TYPE
    SYNTAX  INTEGER {
        tcp(0),
        udp(1),
        unsupported(2147483647)
        }
    MAX-ACCESS  read-write
    STATUS  current
    DESCRIPTION
        "Secure web Reporter Pci tcp/udp, default tcp.
         Note:This mib is not supported for VX instance of Virtualization."
   ::= { slbNewAppwallReporterCfg 3 }

slbNewAppwallReporterSecLog OBJECT-TYPE
    SYNTAX  INTEGER {
        tcp(0),
        udp(1),
        unsupported(2147483647)
        }
    MAX-ACCESS  read-write
    STATUS  current
    DESCRIPTION
        "Secure web Reporter Secuirity LOG tcp/udp, default tcp.
         Note:This mib is not supported for VX instance of Virtualization."
   ::= { slbNewAppwallReporterCfg 4}

slbNewAppwallReporterAudit OBJECT-TYPE
    SYNTAX  INTEGER {
        tcp(0),
        udp(1),
        unsupported(2147483647)
        }
    MAX-ACCESS  read-write
    STATUS  current
    DESCRIPTION
        "Secure web Reporter Audit tcp/udp, default tcp.
         Note:This mib is not supported for VX instance of Virtualization."
   ::= { slbNewAppwallReporterCfg 5 }

slbNewAppwallReporterOthLog OBJECT-TYPE
    SYNTAX  INTEGER {
        tcp(0),
        udp(1),
        unsupported(2147483647)
        }
    MAX-ACCESS  read-write
    STATUS  current
    DESCRIPTION
        "Secure web Reporter Other LOGS tcp/udp, default tcp.
         Note:This mib is not supported for VX instance of Virtualization."
   ::= { slbNewAppwallReporterCfg 6 }

slbNewAppwallReporterTenant OBJECT-TYPE
    SYNTAX  INTEGER {
        disable(0),
        enable(1),
        unsupported(2147483647)
        }
    MAX-ACCESS  read-write
    STATUS  current
    DESCRIPTION
        "Secure web Reporter Tenant Enable/Disable, default disable.
         Note:This mib is not supported for VX instance of Virtualization."
   ::= { slbNewAppwallReporterCfg 7 }


slbNewAppwallReporterTenantHdrName OBJECT-TYPE
    SYNTAX DisplayString (SIZE (0..40))
    MAX-ACCESS  read-write
    STATUS  current
    DESCRIPTION
        "Secure web Tenant Header Name only if tenant enable, otherwise null.
         Note:This mib is not supported for VX instance of Virtualization."
    ::= { slbNewAppwallReporterCfg 8}     
    
slbNewAppwallReporterTenantHdrNameId OBJECT-TYPE
    SYNTAX DisplayString (SIZE (0..40))
    MAX-ACCESS  read-write
    STATUS  current
    DESCRIPTION
        "Secure web Tenant Header Name Id only if tenant enable, otherwise null.
         Note:This mib is not supported for VX instance of Virtualization."
    ::= { slbNewAppwallReporterCfg 9 }      


slbNewAppwallReporterOnOff OBJECT-TYPE
    SYNTAX  INTEGER {
        off(0),
        on(1),
        unsupported(2147483647)
        }
    MAX-ACCESS  read-write
    STATUS  current
    DESCRIPTION
        "Secure web Reporter On/Off, default off.
         Note:This mib is not supported for VX instance of Virtualization."
   ::= { slbNewAppwallReporterCfg 10 }


slbNewAppwallReporterHighPrio OBJECT-TYPE
    SYNTAX  INTEGER {
        tcp(0),
        udp(1),
        unsupported(2147483647)
        }
    MAX-ACCESS  read-write
    STATUS  current
    DESCRIPTION
        "Secure web Reporter High Prio tcp/udp, default tcp.
         Note:This mib is not supported for VX instance of Virtualization."
   ::= { slbNewAppwallReporterCfg 11 }







--- Current Appwall DP Signaling servers

slbCurAppwallDpSrvCfgTable OBJECT-TYPE
    SYNTAX  SEQUENCE OF SlbCurAppwallCfgDpSrvEntry
    MAX-ACCESS  not-accessible
    STATUS  current
    DESCRIPTION
        "Cur DP signaling servers table.
         Note:This mib is not supported on VX instance of Virtualization."
    ::= { appwallCfg 10 }
    
slbCurAppwallCfgDpSrvEntry OBJECT-TYPE
    SYNTAX  SlbCurAppwallCfgDpSrvEntry
    MAX-ACCESS  not-accessible
    STATUS  current
    DESCRIPTION
        "A row in the current DP signaling servers table."
    INDEX   { slbCurAppwallDpSrvId }
    ::= { slbCurAppwallDpSrvCfgTable 1 }

SlbCurAppwallCfgDpSrvEntry ::= SEQUENCE {
	slbCurAppwallDpSrvId               	DisplayString,
	slbCurAppwallDpSrvIpAddress    		DisplayString,
	slbCurAppwallDpSrvPort	     		INTEGER,
	slbCurAppwallDpSrvDel       		INTEGER
    } 
slbCurAppwallDpSrvId OBJECT-TYPE
    SYNTAX   DisplayString (SIZE (0..32))
    MAX-ACCESS  read-only
    STATUS  current
    DESCRIPTION
        "Dp signaling server ID"
    ::= { slbCurAppwallCfgDpSrvEntry 1 }	

slbCurAppwallDpSrvIpAddress OBJECT-TYPE
    SYNTAX DisplayString (SIZE (0..40))
    MAX-ACCESS  read-only
    STATUS  current
    DESCRIPTION
        "Dp signaling server IP "
    ::= { slbCurAppwallCfgDpSrvEntry 2 }  
          
slbCurAppwallDpSrvPort OBJECT-TYPE
    SYNTAX INTEGER (1..65535)
    MAX-ACCESS  read-only
    STATUS  current
    DESCRIPTION
        "Dp signaling server Port "
    ::= { slbCurAppwallCfgDpSrvEntry 3 }

slbCurAppwallDpSrvDel OBJECT-TYPE
    SYNTAX  INTEGER {
        other(1),
        delete(2),
        unsupported(2147483647)
        }
    MAX-ACCESS  read-only
    STATUS  current
    DESCRIPTION
        "By setting the value to delete(2), the entire row is deleted.On GET always other(1)"
    ::= { slbCurAppwallCfgDpSrvEntry 4 }   
  
  
--- New Appwall DP Signaling servers

slbNewAppwallDpSrvCfgTable OBJECT-TYPE
    SYNTAX  SEQUENCE OF SlbNewAppwallCfgDpSrvEntry
    MAX-ACCESS  not-accessible
    STATUS  current
    DESCRIPTION
        "New DP signaling servers table.
         Note:This mib is not supported on VX instance of Virtualization."
    ::= { appwallCfg 11 }
    
slbNewAppwallCfgDpSrvEntry OBJECT-TYPE
    SYNTAX  SlbNewAppwallCfgDpSrvEntry
    MAX-ACCESS  not-accessible
    STATUS  current
    DESCRIPTION
        "A row in the new DP signaling servers table."
    INDEX   { slbNewAppwallDpSrvId }
    ::= { slbNewAppwallDpSrvCfgTable 1 }

SlbNewAppwallCfgDpSrvEntry ::= SEQUENCE {
	slbNewAppwallDpSrvId               	DisplayString,
	slbNewAppwallDpSrvIpAddress    		DisplayString,
	slbNewAppwallDpSrvPort	     		INTEGER,
	slbNewAppwallDpSrvDel       		INTEGER
    } 
slbNewAppwallDpSrvId OBJECT-TYPE
    SYNTAX   DisplayString (SIZE (0..32))
    MAX-ACCESS  read-only
    STATUS  current
    DESCRIPTION
        "Dp signaling server ID"
    ::= { slbNewAppwallCfgDpSrvEntry 1 }	

slbNewAppwallDpSrvIpAddress OBJECT-TYPE
    SYNTAX DisplayString (SIZE (0..40))
    MAX-ACCESS  read-write
    STATUS  current
    DESCRIPTION
        "Dp signaling server IP "
    ::= { slbNewAppwallCfgDpSrvEntry 2 }  
          
slbNewAppwallDpSrvPort OBJECT-TYPE
    SYNTAX INTEGER (1..65535)
    MAX-ACCESS  read-write
    STATUS  current
    DESCRIPTION
        "Dp signaling server Port "
    ::= { slbNewAppwallCfgDpSrvEntry 3 }

slbNewAppwallDpSrvDel OBJECT-TYPE
    SYNTAX  INTEGER {
        other(1),
        delete(2),
        unsupported(2147483647)
        }
    MAX-ACCESS  read-write
    STATUS  current
    DESCRIPTION
        "By setting the value to delete(2), the entire row is deleted.On GET always other(1)"
    ::= { slbNewAppwallCfgDpSrvEntry 4 }   
  

-----------------------	
-- Appwall End
-----------------------

-- TCP policy

slbCurTcpPolTable OBJECT-TYPE
    SYNTAX  SEQUENCE OF SlbCurTcpPolEntry
    MAX-ACCESS  not-accessible
    STATUS  current
    DESCRIPTION
        "The table for configuring TCP policy.
         Note:This mib is not supported on VX instance of Virtualization."
    ::= { tcpOptPolCfg 1 }

slbCurTcpPolEntry OBJECT-TYPE
    SYNTAX  SlbCurTcpPolEntry
    MAX-ACCESS  not-accessible
    STATUS  current
    DESCRIPTION
        "A row in the TCP policy table."
    INDEX   { slbCurTcpPolNameIdIndex }
    ::= { slbCurTcpPolTable 1 }
	
SlbCurTcpPolEntry ::= SEQUENCE {
    slbCurTcpPolNameIdIndex      DisplayString,
    slbCurTcpPolName             DisplayString,
    slbCurTcpPolRcvWndSize       INTEGER,
    slbCurTcpPolSndWndSize       INTEGER,
    slbCurTcpPolMss              INTEGER,
    slbCurTcpPolCaAlgorithm      INTEGER,
    slbCurTcpPolAdaptiveTuning   INTEGER,
    slbCurTcpPolSelAck           INTEGER,
    slbCurTcpPolState            INTEGER,
    slbCurTcpPolReadBufferSize   INTEGER,
    slbCurTcpPolCaScale		     INTEGER,
    slbCurTcpPolCaDecrease	     INTEGER,
    slbCurTcpPolImmediateAck	 INTEGER,
    slbCurTcpPolNagle            INTEGER,
    slbCurTcpPolFinage           INTEGER
    }
		
slbCurTcpPolNameIdIndex OBJECT-TYPE
    SYNTAX   DisplayString
    MAX-ACCESS  read-only
    STATUS  current
    DESCRIPTION
        "The TCP policy name(key id) as an index."
    ::= { slbCurTcpPolEntry  1 }

slbCurTcpPolName  OBJECT-TYPE
    SYNTAX   DisplayString
    MAX-ACCESS  read-only
    STATUS  current
    DESCRIPTION
        "TCP policy name."
    ::= { slbCurTcpPolEntry  2 }

slbCurTcpPolRcvWndSize OBJECT-TYPE
    SYNTAX  INTEGER{
        sz128K(0),
	sz256K(1),
	sz512K(2),
	sz1M(3),
        sz2M(4),
        sz3M(5),
        sz4M(6),
        unsupported(2147483647)
        } 
    MAX-ACCESS  read-only
    STATUS  current
    DESCRIPTION
        "TCP read buffer size."
    ::= { slbCurTcpPolEntry  3 }

slbCurTcpPolSndWndSize OBJECT-TYPE
    SYNTAX   INTEGER{
        sz128K(0),
	sz256K(1),
	sz512K(2),
	sz1M(3),
        sz2M(4),
        sz3M(5),
        sz4M(6),
        unsupported(2147483647)
        }
    MAX-ACCESS  read-only
    STATUS  current
    DESCRIPTION
        "TCP write buffer size."
    ::= { slbCurTcpPolEntry  4 }

slbCurTcpPolMss OBJECT-TYPE
    SYNTAX   INTEGER{
        def(0),
        sz1460(1),
	sz1440(2),
	sz1360(3),
	sz1212(4),
	sz956(5),
	sz536(6),
	sz384(7),
	sz128(8),
        sz1400(9),
        unsupported(2147483647)
        }
    MAX-ACCESS  read-only
    STATUS  current
    DESCRIPTION
        "TCP maximum segment size."
    ::= {slbCurTcpPolEntry  5 }

slbCurTcpPolCaAlgorithm  OBJECT-TYPE
    SYNTAX  INTEGER{
        reno(0),
        hybla(1),
	hyblaAndPacing(2),
	westwood(3),
        unsupported(2147483647)
        }
    MAX-ACCESS  read-only
    STATUS  current
    DESCRIPTION
        "TCP congestion avoidance algorithm."
    ::= { slbCurTcpPolEntry  6 }

slbCurTcpPolAdaptiveTuning  OBJECT-TYPE
    SYNTAX  INTEGER{
        enabled(1),
        disabled(2),
        unsupported(2147483647)
        }
    MAX-ACCESS  read-only
    STATUS  current
    DESCRIPTION
        "Enable/Disable TCP Adaptive Tuning."
    ::= { slbCurTcpPolEntry  7 }

slbCurTcpPolSelAck  OBJECT-TYPE
    SYNTAX  INTEGER {
        enabled(1),
        disabled(2),
        unsupported(2147483647)
        }
    MAX-ACCESS  read-only
    STATUS  current
    DESCRIPTION
        "Enable/Disable selective ACK."
    ::= { slbCurTcpPolEntry  8 }

slbCurTcpPolState  OBJECT-TYPE
    SYNTAX  INTEGER {
        enabled(1),
        disabled(2),
        unsupported(2147483647)
        }
    MAX-ACCESS  read-only
    STATUS  current
    DESCRIPTION
        "Enable/Disable TCP policy."
    ::= { slbCurTcpPolEntry  9 }

slbCurTcpPolReadBufferSize  OBJECT-TYPE
    SYNTAX INTEGER (2..64)
    MAX-ACCESS  read-only
    STATUS  current
    DESCRIPTION
        "Read buffer size."
    ::= { slbCurTcpPolEntry  10 }

slbCurTcpPolCaScale  OBJECT-TYPE
    SYNTAX INTEGER (0..64)
    MAX-ACCESS  read-only
    STATUS  current
    DESCRIPTION
        "Congestion Scale."
    ::= { slbCurTcpPolEntry  11 }

slbCurTcpPolCaDecrease  OBJECT-TYPE
    SYNTAX INTEGER (0..3)
    MAX-ACCESS  read-only
    STATUS  current
    DESCRIPTION
        "Congestion Decrease policy."
    ::= { slbCurTcpPolEntry  12 }

slbCurTcpPolImmediateAck  OBJECT-TYPE
    SYNTAX  INTEGER {
        enabled(1),
        disabled(2),
        unsupported(2147483647)
        }
    MAX-ACCESS  read-only
    STATUS  current
    DESCRIPTION
        "Enable/Disable Immediate ACK on push."
    ::= { slbCurTcpPolEntry  13 }

slbCurTcpPolNagle  OBJECT-TYPE
    SYNTAX  INTEGER {
        enabled(1),
        disabled(2),
        unsupported(2147483647)
        }
    MAX-ACCESS  read-only
    STATUS  current
    DESCRIPTION
        "Enable/Disable Nagle Algorithm."
    ::= { slbCurTcpPolEntry  14 }

slbCurTcpPolFinage  OBJECT-TYPE
    SYNTAX INTEGER (0..86400)
    MAX-ACCESS  read-only
    STATUS  current
    DESCRIPTION
        "Connection closing aging in seconds on FIN receipt (0 - no aging)."
    ::= { slbCurTcpPolEntry  15 }

slbNewTcpPolTable  OBJECT-TYPE
    SYNTAX  SEQUENCE OF SlbNewTcpPolEntry
    MAX-ACCESS  not-accessible
    STATUS  current
    DESCRIPTION
        "The table for configuring TCP policy.
         Note:This mib is not supported on VX instance of Virtualization."
    ::= { tcpOptPolCfg 2 }

slbNewTcpPolEntry OBJECT-TYPE
    SYNTAX  SlbNewTcpPolEntry
    MAX-ACCESS  not-accessible
    STATUS  current
    DESCRIPTION
        "A row in the TCP policy table."
    INDEX   { slbNewTcpPolNameIdIndex }
    ::= { slbNewTcpPolTable 1 }

SlbNewTcpPolEntry ::= SEQUENCE {
    slbNewTcpPolNameIdIndex      DisplayString,
    slbNewTcpPolName             DisplayString,
    slbNewTcpPolRcvWndSize       INTEGER,
    slbNewTcpPolSndWndSize       INTEGER,
    slbNewTcpPolMss              INTEGER,
    slbNewTcpPolCaAlgorithm      INTEGER,
    slbNewTcpPolAdaptiveTuning   INTEGER,
    slbNewTcpPolSelAck           INTEGER,
    slbNewTcpPolState            INTEGER,
    slbNewTcpPolDel              INTEGER,
    slbNewTcpPolReadBufferSize   INTEGER,
    slbNewTcpPolCaScale          INTEGER,
    slbNewTcpPolCaDecrease       INTEGER,
    slbNewTcpPolImmediateAck     INTEGER,
    slbNewTcpPolNagle            INTEGER,
    slbNewTcpPolFinage           INTEGER
    }

slbNewTcpPolNameIdIndex OBJECT-TYPE
    SYNTAX   DisplayString
    MAX-ACCESS  read-create
    STATUS  current
    DESCRIPTION
        "The TCP policy name(key id) as an index."
    ::= { slbNewTcpPolEntry  1 }

slbNewTcpPolName  OBJECT-TYPE
    SYNTAX   DisplayString
    MAX-ACCESS  read-create
    STATUS  current
    DESCRIPTION
        "TCP policy name,length of the string should be 32 characters."
    ::= { slbNewTcpPolEntry  2 }

slbNewTcpPolRcvWndSize  OBJECT-TYPE
    SYNTAX  INTEGER{
        sz128K(0),
	sz256K(1),
	sz512K(2),
	sz1M(3),
        sz2M(4),
        sz3M(5),
        sz4M(6),
        unsupported(2147483647)
        }
    MAX-ACCESS  read-create
    STATUS  current
    DESCRIPTION
        "TCP read buffer size."
    ::= { slbNewTcpPolEntry  3 }

slbNewTcpPolSndWndSize  OBJECT-TYPE
    SYNTAX  INTEGER{
        sz128K(0),
	sz256K(1),
	sz512K(2),
	sz1M(3),
        sz2M(4),
        sz3M(5),
        sz4M(6),
        unsupported(2147483647)
        }
    MAX-ACCESS  read-create
    STATUS  current
    DESCRIPTION
        "TCP write buffer size."
    ::= { slbNewTcpPolEntry  4 }

slbNewTcpPolMss  OBJECT-TYPE
    SYNTAX  INTEGER{
	def(0),
        sz1460(1),
	sz1440(2),
	sz1360(3),
	sz1212(4),
	sz956(5),
	sz536(6),
	sz384(7),
	sz128(8),
        sz1400(9),
        sz1600(10),
        sz9156(11),
        sz9176(12),
        unsupported(2147483647)
        } 
    MAX-ACCESS  read-create
    STATUS  current
    DESCRIPTION
        "TCP maximum segment size."
    ::= { slbNewTcpPolEntry  5 }
	
slbNewTcpPolCaAlgorithm  OBJECT-TYPE
    SYNTAX  INTEGER{
        reno(0),
        hybla(1),
	hyblaAndPacing(2),
        westwood(3),
        unsupported(2147483647)
        }
    MAX-ACCESS  read-create
    STATUS  current
    DESCRIPTION
        "TCP congestion avoidance algorithm."
    ::= { slbNewTcpPolEntry  6 }

slbNewTcpPolAdaptiveTuning  OBJECT-TYPE
    SYNTAX  INTEGER{
        enabled(1),
        disabled(2),
        unsupported(2147483647)
        }
    MAX-ACCESS  read-create
    STATUS  current
    DESCRIPTION
        "Enable/Disable TCP Adaptive Tuning."
    ::= { slbNewTcpPolEntry  7 }

slbNewTcpPolSelAck  OBJECT-TYPE
    SYNTAX  INTEGER{
        enabled(1),
        disabled(2),
        unsupported(2147483647)
        }
    MAX-ACCESS  read-create
    STATUS  current
    DESCRIPTION
        "Enable/Disable selective ACK."
    ::= { slbNewTcpPolEntry  8 }
	
slbNewTcpPolState  OBJECT-TYPE
    SYNTAX  INTEGER {
        enabled(1),
        disabled(2),
        unsupported(2147483647)
        }
    MAX-ACCESS  read-create
    STATUS  current
    DESCRIPTION
        "Enable/Disable TCP policy."
    ::= { slbNewTcpPolEntry  9 }
    	
slbNewTcpPolDel  OBJECT-TYPE
    SYNTAX  INTEGER {
        other(1),
        delete(2),
        unsupported(2147483647)
    }
    MAX-ACCESS  read-create
    STATUS  current
    DESCRIPTION
        "Delete TCP policy."
    ::= { slbNewTcpPolEntry  10 }

slbNewTcpPolReadBufferSize  OBJECT-TYPE
    SYNTAX INTEGER (2..64)
    MAX-ACCESS  read-create
    STATUS  current
    DESCRIPTION
        "Read buffer size."
    ::= { slbNewTcpPolEntry  11 }

slbNewTcpPolCaScale  OBJECT-TYPE
    SYNTAX INTEGER (0..64)
    MAX-ACCESS  read-create
    STATUS  current
    DESCRIPTION
        "Congestion Scale."
    ::= { slbNewTcpPolEntry  12 }

slbNewTcpPolCaDecrease  OBJECT-TYPE
    SYNTAX INTEGER (0..3)
    MAX-ACCESS  read-create
    STATUS  current
    DESCRIPTION
        "Congestion Decrease policy."
    ::= { slbNewTcpPolEntry  13 }

slbNewTcpPolImmediateAck  OBJECT-TYPE
    SYNTAX  INTEGER {
        enabled(1),
        disabled(2),
        unsupported(2147483647)
        }
    MAX-ACCESS  read-create
    STATUS  current
    DESCRIPTION
        "Enable/Disable Immediate ACK on push."
    ::= { slbNewTcpPolEntry  14 }

slbNewTcpPolNagle  OBJECT-TYPE
    SYNTAX  INTEGER {
        enabled(1),
        disabled(2),
        unsupported(2147483647)
        }
    MAX-ACCESS  read-create
    STATUS  current
    DESCRIPTION
        "Enable/Disable Nagle."
    ::= { slbNewTcpPolEntry  15 }

slbNewTcpPolFinage  OBJECT-TYPE
    SYNTAX INTEGER (0..86400)
    MAX-ACCESS  read-create
    STATUS  current
    DESCRIPTION
        "Connection closing aging in seconds on FIN receipt (0 - no aging)."
    ::= { slbNewTcpPolEntry  16 }

lPGeneralCfg  OBJECT IDENTIFIER ::= { lpConfig 1 }

slbCurLpOn  OBJECT-TYPE
    SYNTAX  INTEGER {
        off(0),
        on(1),
        unsupported(2147483647)
        }
     MAX-ACCESS  read-only
     STATUS  current
     DESCRIPTION
         "on/off lp module.Can be turned on only if gslb/lp license is installed.
          Note:This mib is not supported for VX instance of Virtualization."
    ::= { lPGeneralCfg 1 }
 
slbNewLpOn  OBJECT-TYPE
    SYNTAX  INTEGER {
        off(0),
        on(1),
        unsupported(2147483647)
        }
     MAX-ACCESS  read-write
     STATUS  current
     DESCRIPTION
         "on/off lp module.Can be turned on only if gslb/lp license is installed.
          Note:This mib is not supported for VX instance of Virtualization."
    ::= { lPGeneralCfg 2 }

slbCurCfgSmartNatState OBJECT-TYPE
    SYNTAX INTEGER {
        enabled(1),
        disabled(2),
        unsupported(2147483647)
        }     
    MAX-ACCESS  read-only
    STATUS  current
    DESCRIPTION
        "Enable or disable Smart NAT.
         Note:This mib is not supported for VX instance of Virtualization."
    ::= { lPGeneralCfg 3 }

slbNewCfgSmartNatState OBJECT-TYPE
    SYNTAX INTEGER {
        enabled(1),
        disabled(2),
        unsupported(2147483647)
        }     
    MAX-ACCESS  read-write
    STATUS  current
    DESCRIPTION
        "Enable or disable Smart NAT.
         Note:This mib is not supported for VX instance of Virtualization."
    ::= { lPGeneralCfg 4 }

lpSmartNATCfg OBJECT IDENTIFIER ::= { lpConfig 2 }

slbCurCfgSmartNatTable OBJECT-TYPE
    SYNTAX  SEQUENCE OF SlbCurCfgSmartNatTableEntry
    MAX-ACCESS  not-accessible
    STATUS  current
    DESCRIPTION
        "The table of current Smart NAT configuration.
         Note:This mib is not supported on VX instance of Virtualization."
    ::= { lpSmartNATCfg 1 }

slbCurCfgSmartNatEntry OBJECT-TYPE
    SYNTAX  SlbCurCfgSmartNatTableEntry
    MAX-ACCESS  not-accessible
    STATUS  current
    DESCRIPTION
        "A row in the Smart NAT table."
    INDEX   { slbCurCfgSmartNatIndex }
    ::= { slbCurCfgSmartNatTable 1 }

SlbCurCfgSmartNatTableEntry ::= SEQUENCE {
     slbCurCfgSmartNatIndex          DisplayString,
     slbCurCfgSmartNatName           DisplayString,
     slbCurCfgSmartNatType           INTEGER,
     slbCurCfgSmartNatIpVer          INTEGER,
     slbCurCfgSmartNatMode           INTEGER,
     slbCurCfgSmartNatLocalIpV4      IpAddress,
     slbCurCfgSmartNatLocalIpV4Mask  IpAddress,
     slbCurCfgSmartNatLocalIpV6      DisplayString,
     slbCurCfgSmartNatLocalIpV6Mask  INTEGER,
     slbCurCfgSmartNatLocalNwclss    DisplayString,
     slbCurCfgSmartNatDnatMode       INTEGER,
     slbCurCfgSmartNatDnatIpV4       IpAddress,
     slbCurCfgSmartNatDnatIpV4Mask   IpAddress,
     slbCurCfgSmartNatDnatIpV6       DisplayString,
     slbCurCfgSmartNatDnatIpV6Mask   INTEGER,
     slbCurCfgSmartNatDnatNwclss     DisplayString,
     slbCurCfgSmartNatWanLink        DisplayString,
     slbCurCfgSmartNatDnatPersist    INTEGER
}

slbCurCfgSmartNatIndex OBJECT-TYPE
    SYNTAX DisplayString (SIZE(0..32))
    MAX-ACCESS  read-only
    STATUS  current
    DESCRIPTION
        "The SMART NAT id as an index."
    ::= { slbCurCfgSmartNatEntry 1 }

slbCurCfgSmartNatName OBJECT-TYPE
    SYNTAX DisplayString (SIZE(0..32))
    MAX-ACCESS  read-only
    STATUS  current
    DESCRIPTION
        "Descriptive name for Smart NAT entry."
    ::= { slbCurCfgSmartNatEntry 2 }

slbCurCfgSmartNatType OBJECT-TYPE
    SYNTAX  INTEGER {
        nonat(0),
        static(1),
        dynamic(2),
        unsupported(2147483647)
    }
    MAX-ACCESS  read-only
    STATUS  current
    DESCRIPTION
        "Smart NAT type."
    ::= {slbCurCfgSmartNatEntry 3 }

slbCurCfgSmartNatIpVer OBJECT-TYPE
    SYNTAX  INTEGER {
        ipv4(0),
        ipv6(1),
        unsupported(2147483647)
    }
    MAX-ACCESS  read-only
    STATUS  current
    DESCRIPTION
        "IP version for Smart NAT entry."
    ::= {slbCurCfgSmartNatEntry 4 }

slbCurCfgSmartNatMode OBJECT-TYPE
    SYNTAX  INTEGER {
        address(0),
        nwclass(1),
        none(2),
        unsupported(2147483647)
    }
    MAX-ACCESS  read-only
    STATUS  current
    DESCRIPTION
        "Smart NAT local mode."
    ::= {slbCurCfgSmartNatEntry 5 }

slbCurCfgSmartNatLocalIpV4 OBJECT-TYPE
    SYNTAX IpAddress
    MAX-ACCESS read-only
    STATUS current
    DESCRIPTION
        "Local ipv4 address of the Smart NAT entry. This is valid only when ip version is set to v4."
    ::= { slbCurCfgSmartNatEntry 6 }

slbCurCfgSmartNatLocalIpV4Mask OBJECT-TYPE
    SYNTAX IpAddress
    MAX-ACCESS read-only
    STATUS current
    DESCRIPTION
        "Local ipv4 network mask of the Smart NAT entry. This is valid only when ip version is set to v4."
    ::= { slbCurCfgSmartNatEntry 7 }

slbCurCfgSmartNatLocalIpV6 OBJECT-TYPE
   SYNTAX DisplayString (SIZE(0..40))
    MAX-ACCESS read-only
    STATUS  current
    DESCRIPTION
    "  The Local IPV6 address of the Smart NAT entry
       Address should be 4-byte hexadecimal colon notation. Valid IPv6 address should be in
       any of the following forms xxxx:xxxx:xxxx:xxxx:xxxx:xxxx:xxxx:xxxx or xxxx::xxxx:xxxx:xxxx:xxxx or ::xxxx
       This is valid only when ip version is set to ipv6."
   ::= { slbCurCfgSmartNatEntry 8 }

slbCurCfgSmartNatLocalIpV6Mask OBJECT-TYPE
    SYNTAX   INTEGER(0..128)
    MAX-ACCESS read-only
    STATUS  current
    DESCRIPTION
        "The prefix length associated with the local IPV6 address of the Smart NAT entry.
         This is valid only when ip version is set to ipv6."
    ::= { slbCurCfgSmartNatEntry 9 }

slbCurCfgSmartNatLocalNwclss OBJECT-TYPE
    SYNTAX   DisplayString (SIZE (0..32))
    MAX-ACCESS  read-only
    STATUS  current
    DESCRIPTION
        "Local network class name."
    ::= { slbCurCfgSmartNatEntry 10 }

slbCurCfgSmartNatDnatMode OBJECT-TYPE
    SYNTAX  INTEGER {
        address(0),
        nwclass(1),
        none(2),
        unsupported(2147483647)
    }
    MAX-ACCESS  read-only
    STATUS  current
    DESCRIPTION
        "NAT address mode for this Smart NAT entry"
    ::= {slbCurCfgSmartNatEntry 11 }

slbCurCfgSmartNatDnatIpV4 OBJECT-TYPE
    SYNTAX IpAddress
    MAX-ACCESS read-only
    STATUS current
    DESCRIPTION
        "NAT ipv4 address of the Smart NAT entry. This is valid only when ip version is set to ipv4."
    ::= { slbCurCfgSmartNatEntry 12 }

slbCurCfgSmartNatDnatIpV4Mask OBJECT-TYPE
    SYNTAX IpAddress
    MAX-ACCESS read-only
    STATUS current
    DESCRIPTION
        "NAT ipv4 network mask of the Smart NAT entry. This is valid only when ip version is set to ipv4."
    ::= { slbCurCfgSmartNatEntry 13 }

slbCurCfgSmartNatDnatIpV6 OBJECT-TYPE
   SYNTAX DisplayString (SIZE(0..40))
    MAX-ACCESS read-only
    STATUS  current
    DESCRIPTION
    "  NAT IPV6 address of the Smart NAT entry
       Address should be 4-byte hexadecimal colon notation. Valid IPv6 address should be in
       any of the following forms xxxx:xxxx:xxxx:xxxx:xxxx:xxxx:xxxx:xxxx or xxxx::xxxx:xxxx:xxxx:xxxx or ::xxxx
       This is valid only when ip version is set to ipv6."
   ::= { slbCurCfgSmartNatEntry 14 }


slbCurCfgSmartNatDnatIpV6Mask OBJECT-TYPE
    SYNTAX   INTEGER(0..128)
    MAX-ACCESS read-only
    STATUS  current
    DESCRIPTION
        "The prefix length associated with the NAT IPV6 address of the Smart NAT entry.
         This is valid only when ip version is set to ipv6."
    ::= { slbCurCfgSmartNatEntry 15 }

slbCurCfgSmartNatDnatNwclss OBJECT-TYPE
    SYNTAX   DisplayString (SIZE (0..32))
    MAX-ACCESS  read-only
    STATUS  current
    DESCRIPTION
        "NAT Network class name for the SMART NAT entry."
    ::= { slbCurCfgSmartNatEntry 16 }

slbCurCfgSmartNatWanLink OBJECT-TYPE
    SYNTAX   DisplayString (SIZE (0..255))
    MAX-ACCESS  read-only
    STATUS  current
    DESCRIPTION
        "Wanlink Server name for this Smart NAT entry."
    ::= { slbCurCfgSmartNatEntry 17 }


slbCurCfgSmartNatDnatPersist OBJECT-TYPE
    SYNTAX  INTEGER {
        none(1),
        host(2),
        client(3),
        unsupported(2147483647)
    }
    MAX-ACCESS  read-only
    STATUS  current
    DESCRIPTION
        "Persistence type for the Smart NAT entry. This is valid only for type Dynamic NAT."
    ::= {slbCurCfgSmartNatEntry 18 }

slbNewCfgSmartNatTable OBJECT-TYPE
    SYNTAX  SEQUENCE OF SlbNewCfgSmartNatTableEntry
    MAX-ACCESS  not-accessible
    STATUS  current
    DESCRIPTION
        "The table for configuring Smart NAT.
         Note:This mib is not supported on VX instance of Virtualization."
    ::= { lpSmartNATCfg 2 }


slbNewCfgSmartNatEntry OBJECT-TYPE
    SYNTAX  SlbNewCfgSmartNatTableEntry
    MAX-ACCESS  not-accessible
    STATUS  current
    DESCRIPTION
        "A row in the Smart NAT table."
    INDEX   { slbNewCfgSmartNatIndex }
    ::= { slbNewCfgSmartNatTable 1 }


SlbNewCfgSmartNatTableEntry ::= SEQUENCE {
     slbNewCfgSmartNatIndex          DisplayString,
     slbNewCfgSmartNatName           DisplayString,
     slbNewCfgSmartNatType           INTEGER,
     slbNewCfgSmartNatIpVer          INTEGER,
     slbNewCfgSmartNatMode           INTEGER,
     slbNewCfgSmartNatLocalIpV4      IpAddress,
     slbNewCfgSmartNatLocalIpV4Mask  IpAddress,
     slbNewCfgSmartNatLocalIpV6      DisplayString,
     slbNewCfgSmartNatLocalIpV6Mask  INTEGER,
     slbNewCfgSmartNatLocalNwclss    DisplayString,
     slbNewCfgSmartNatDnatMode       INTEGER,
     slbNewCfgSmartNatDnatIpV4       IpAddress,
     slbNewCfgSmartNatDnatIpV4Mask   IpAddress,
     slbNewCfgSmartNatDnatIpV6       DisplayString,
     slbNewCfgSmartNatDnatIpV6Mask   INTEGER,
     slbNewCfgSmartNatDnatNwclss     DisplayString,
     slbNewCfgSmartNatWanLink        DisplayString,
     slbNewCfgSmartNatDel            INTEGER,
     slbNewCfgSmartNatDnatPersist    INTEGER
}

slbNewCfgSmartNatIndex OBJECT-TYPE
    SYNTAX DisplayString (SIZE(0..32))
    MAX-ACCESS  read-create
    STATUS  current
    DESCRIPTION
        "The Smart NAT id as an index."
    ::= { slbNewCfgSmartNatEntry 1 }

slbNewCfgSmartNatName OBJECT-TYPE
    SYNTAX DisplayString (SIZE(0..32))
    MAX-ACCESS  read-create
    STATUS  current
    DESCRIPTION
        "Descriptive name for Smart NAT entry."
    ::= { slbNewCfgSmartNatEntry 2 }

slbNewCfgSmartNatType OBJECT-TYPE
    SYNTAX  INTEGER {
        nonat(0),
        static(1),
        dynamic(2),
        unsupported(2147483647)
    }
    MAX-ACCESS  read-create
    STATUS  current
    DESCRIPTION
        "Smart NAT type."
    ::= {slbNewCfgSmartNatEntry 3 }

slbNewCfgSmartNatIpVer OBJECT-TYPE
    SYNTAX  INTEGER {
        ipv4(0),
        ipv6(1),
        unsupported(2147483647)
    }
    MAX-ACCESS  read-create
    STATUS  current
    DESCRIPTION
        "IP version for Smart NAT entry."
    ::= {slbNewCfgSmartNatEntry 4 }

slbNewCfgSmartNatMode OBJECT-TYPE
    SYNTAX  INTEGER {
        address(0),
        nwclass(1),
        none(2),
        unsupported(2147483647)
    }
    MAX-ACCESS  read-create
    STATUS  current
    DESCRIPTION
        "Smart NAT local address mode."
    ::= {slbNewCfgSmartNatEntry 5 }

slbNewCfgSmartNatLocalIpV4 OBJECT-TYPE
    SYNTAX IpAddress
    MAX-ACCESS read-create
    STATUS current
    DESCRIPTION
        "Local ipv4 address of the Smart NAT entry. This is valid only when ip version is set to v4."
    ::= { slbNewCfgSmartNatEntry 6 }

slbNewCfgSmartNatLocalIpV4Mask OBJECT-TYPE
    SYNTAX IpAddress
    MAX-ACCESS read-create
    STATUS current
    DESCRIPTION
        "Local ipv4 network mask of the Smart NAT entry. This is valid only ip version is set to v4."
    ::= { slbNewCfgSmartNatEntry 7 }

slbNewCfgSmartNatLocalIpV6 OBJECT-TYPE
   SYNTAX DisplayString (SIZE(0..40))
    MAX-ACCESS read-create
    STATUS  current
    DESCRIPTION
    "  The Local IPV6 address of the Smart NAT entry
       Address should be 4-byte hexadecimal colon notation. Valid IPv6 address should be in
       any of the following forms xxxx:xxxx:xxxx:xxxx:xxxx:xxxx:xxxx:xxxx or xxxx::xxxx:xxxx:xxxx:xxxx or ::xxxx
       This is valid only when ip version is set to ipv6."
   ::= { slbNewCfgSmartNatEntry 8 }

slbNewCfgSmartNatLocalIpV6Mask OBJECT-TYPE
    SYNTAX   INTEGER(0..128)
    MAX-ACCESS read-create
    STATUS  current
    DESCRIPTION
        "The prefix length associated with the local IPV6 address of the Smart NAT entry.
         This is valid only when ip version is set to ipv6."
    ::= { slbNewCfgSmartNatEntry 9 }

slbNewCfgSmartNatLocalNwclss OBJECT-TYPE
    SYNTAX   DisplayString (SIZE (0..32))
    MAX-ACCESS  read-create
    STATUS  current
    DESCRIPTION
        "Local Network class name. This is valid only when mode is nwclass."
    ::= { slbNewCfgSmartNatEntry 10 }

slbNewCfgSmartNatDnatMode OBJECT-TYPE
    SYNTAX  INTEGER {
        address(0),
        nwclass(1),
        none(2),
        unsupported(2147483647)
    }
    MAX-ACCESS  read-create
    STATUS  current
    DESCRIPTION
        "NAT address mode for this Smart NAT entry."
    ::= {slbNewCfgSmartNatEntry 11 }

slbNewCfgSmartNatDnatIpV4 OBJECT-TYPE
    SYNTAX IpAddress
    MAX-ACCESS read-create
    STATUS current
    DESCRIPTION
        "NAT ipv4 address of the Smart NAT entry.
         This is valid only ip version is set to ipv4."
    ::= { slbNewCfgSmartNatEntry 12 }

slbNewCfgSmartNatDnatIpV4Mask OBJECT-TYPE
    SYNTAX IpAddress
    MAX-ACCESS read-create
    STATUS current
    DESCRIPTION
        "NAT ipv4 network mask of the Smart NAT entry.
         This is valid only when ip version is set to ipv4."
    ::= { slbNewCfgSmartNatEntry 13 }

slbNewCfgSmartNatDnatIpV6 OBJECT-TYPE
   SYNTAX DisplayString (SIZE(0..40))
    MAX-ACCESS read-create
    STATUS  current
    DESCRIPTION
    "  NAT IPV6 address of the Smart NAT entry
       Address should be 4-byte hexadecimal colon notation. Valid IPv6 address should be in
       any of the following forms xxxx:xxxx:xxxx:xxxx:xxxx:xxxx:xxxx:xxxx or xxxx::xxxx:xxxx:xxxx:xxxx or ::xxxx
       This is valid only when ip version is set to ipv6."
   ::= { slbNewCfgSmartNatEntry 14 }


slbNewCfgSmartNatDnatIpV6Mask OBJECT-TYPE
    SYNTAX   INTEGER(0..128)
    MAX-ACCESS read-create
    STATUS  current
    DESCRIPTION
        "The prefix length associated with the NAT IPV6 address of the SMART nat entry.
         This is valid only when ip version is set to ipv6."
    ::= { slbNewCfgSmartNatEntry 15 }

slbNewCfgSmartNatDnatNwclss OBJECT-TYPE
    SYNTAX   DisplayString (SIZE (0..32))
    MAX-ACCESS  read-create
    STATUS  current
    DESCRIPTION
        "NAT Network class name."
    ::= { slbNewCfgSmartNatEntry 16 }

slbNewCfgSmartNatWanLink OBJECT-TYPE
    SYNTAX   DisplayString (SIZE (0..255))
    MAX-ACCESS  read-create
    STATUS  current
    DESCRIPTION
        "Wanlink Server name for this Smart NAT entry."
    ::= { slbNewCfgSmartNatEntry 17 }

slbNewCfgSmartNatDel OBJECT-TYPE
    SYNTAX  INTEGER {
        other(1),
        delete(2),
        unsupported(2147483647)
    }
    MAX-ACCESS  read-create
    STATUS  current
    DESCRIPTION
        "Delete Smart Nat entry."
    ::= { slbNewCfgSmartNatEntry 18 }

slbNewCfgSmartNatDnatPersist OBJECT-TYPE
    SYNTAX  INTEGER {
        none(1),
        host(2),
        client(3),
        unsupported(2147483647)
    }
    MAX-ACCESS  read-create
    STATUS  current
    DESCRIPTION
        "Persistence type for this Smart NAT entry. This is valid only for type Dynamic NAT."
    ::= { slbNewCfgSmartNatEntry 19 }
  
-- Proximity

slbGslbProxInfoTable OBJECT-TYPE
    SYNTAX  SEQUENCE OF SlbGslbProxInfoEntry
    MAX-ACCESS  not-accessible
    STATUS  current
    DESCRIPTION
        "Proximity view table.
         Note:This mib is not supported on VX instance of Virtualization."
    ::= { layer4Info 19 }

slbGslbProxInfoEntry OBJECT-TYPE
    SYNTAX  SlbGslbProxInfoEntry
    MAX-ACCESS  not-accessible
    STATUS  current
    DESCRIPTION
         "A row in proximity table."
INDEX   { slbGslbSubnetIndex }
    ::= { slbGslbProxInfoTable 1 }

SlbGslbProxInfoEntry ::= SEQUENCE {
    slbGslbSubnetIndex          Integer32,
    slbGslbSubnetIp             DisplayString,
    slbGslbNhrRank1             DisplayString,
    slbGslbNhrRank2             DisplayString,
    slbGslbNhrRank3             DisplayString,
    slbGslbNhrRTT1              DisplayString,
    slbGslbNhrRTT2              DisplayString,
    slbGslbNhrRTT3              DisplayString, 
    slbGslbNhrHOP1              INTEGER, 
    slbGslbNhrHOP2              INTEGER, 
    slbGslbNhrHOP3              INTEGER,
    slbGslbNhrAge               INTEGER 
    }


slbGslbSubnetIndex OBJECT-TYPE
    SYNTAX  Integer32
    MAX-ACCESS  read-only
    STATUS  current
    DESCRIPTION
        "The Subnet index."
    ::= { slbGslbProxInfoEntry 1 }

slbGslbSubnetIp OBJECT-TYPE
    SYNTAX DisplayString (SIZE(1..40))
    MAX-ACCESS  read-only
    STATUS  current
    DESCRIPTION
        "Subnet/Destination ip."
    ::= { slbGslbProxInfoEntry 2 }

slbGslbNhrRank1 OBJECT-TYPE
    SYNTAX DisplayString (SIZE(1..40))
    MAX-ACCESS  read-only
    STATUS  current
    DESCRIPTION
        "Rank 1 Nhr ip."
    ::= { slbGslbProxInfoEntry 3 }

slbGslbNhrRank2 OBJECT-TYPE
    SYNTAX DisplayString (SIZE(1..40))
    MAX-ACCESS  read-only
    STATUS  current
    DESCRIPTION
        "Rank 2 Nhr ip."
    ::= { slbGslbProxInfoEntry 4 }

slbGslbNhrRank3 OBJECT-TYPE
    SYNTAX DisplayString (SIZE(1..40))
    MAX-ACCESS  read-only
    STATUS  current
    DESCRIPTION
        "Rank 3 Nhr ip."
    ::= { slbGslbProxInfoEntry 5 }

slbGslbNhrRTT1 OBJECT-TYPE
   SYNTAX DisplayString (SIZE(1..40))
   MAX-ACCESS  read-only
   STATUS  current
   DESCRIPTION
       "The roundtrip time for Rank1 Nhr Ip."
   ::= { slbGslbProxInfoEntry 6 }

slbGslbNhrRTT2 OBJECT-TYPE
   SYNTAX DisplayString (SIZE(1..40))
   MAX-ACCESS  read-only
   STATUS  current
   DESCRIPTION
       "The roundtrip time for Rank2 Nhr Ip."
   ::= { slbGslbProxInfoEntry 7 }

slbGslbNhrRTT3 OBJECT-TYPE
   SYNTAX DisplayString (SIZE(1..40))
   MAX-ACCESS  read-only
   STATUS  current
   DESCRIPTION
       "The roundtrip time for Rank3 Nhr Ip."
   ::= { slbGslbProxInfoEntry 8 }

slbGslbNhrHOP1 OBJECT-TYPE
    SYNTAX  INTEGER
    MAX-ACCESS  read-only
    STATUS  current
    DESCRIPTION
        "Number of Hops to reach Destination via Rank1 NHR"
    ::= { slbGslbProxInfoEntry 9 }

slbGslbNhrHOP2 OBJECT-TYPE
    SYNTAX  INTEGER
    MAX-ACCESS  read-only
    STATUS  current
    DESCRIPTION
        "Number of Hops to reach Destination via Rank2 NHR"
    ::= { slbGslbProxInfoEntry 10 }

slbGslbNhrHOP3 OBJECT-TYPE
    SYNTAX  INTEGER
    MAX-ACCESS  read-only
    STATUS  current
    DESCRIPTION
        "Number of Hops to reach Destination via Rank3 NHR"
    ::= { slbGslbProxInfoEntry 11 }

slbGslbNhrAge OBJECT-TYPE
    SYNTAX  INTEGER
    MAX-ACCESS  read-only
    STATUS  current
    DESCRIPTION
        "Aging of each Entry"
    ::= { slbGslbProxInfoEntry 12 }


slbGslbProximityClear OBJECT-TYPE
    SYNTAX INTEGER {
        ok(1),
        clear(2),
        unsupported(2147483647)
        }
    MAX-ACCESS read-write
    STATUS current
    DESCRIPTION
        "This is an action object to clear the Proximity entries.
         ok(1) is returned when read.
         Note:This mib is not supported for VX instance of Virtualization."
    ::= { layer4Info 20 }

slbCurSecCfgSecPolTable OBJECT-TYPE
    SYNTAX  SEQUENCE OF SlbCurSecCfgSecPolEntry
    MAX-ACCESS  not-accessible
    STATUS  current
    DESCRIPTION
        "The table for configuring security policy.
         Note:This mib is not supported on VX instance of Virtualization."
    ::= { secPol 1 }



slbCurSecCfgSecPolEntry OBJECT-TYPE
    SYNTAX  SlbCurSecCfgSecPolEntry
    MAX-ACCESS  not-accessible
    STATUS  current
    DESCRIPTION
        "A row in the security policy table."
    INDEX   { slbCurSecCfgSecPolNameIdIndex }
    ::= { slbCurSecCfgSecPolTable 1 }


SlbCurSecCfgSecPolEntry ::= SEQUENCE {
    slbCurSecCfgSecPolNameIdIndex             DisplayString,
    slbCurSecCfgSecPolName                    DisplayString,
    slbCurSecCfgSecPolBW                      INTEGER,   
    slbCurSecCfgSecPolBWmin                   INTEGER,  
    slbCurSecCfgSecPolBWin                    INTEGER,
    slbCurSecCfgSecPolPPS                     INTEGER,   
    slbCurSecCfgSecPolPPSmin                  INTEGER,  
    slbCurSecCfgSecPolPPSin                   INTEGER,   
    slbCurSecCfgSecPolCPS                     INTEGER,   
    slbCurSecCfgSecPolCPSmin                  INTEGER,  
    slbCurSecCfgSecPolCPSin                   INTEGER,   
    slbCurSecCfgSecPolCEC                     INTEGER,   
    slbCurSecCfgSecPolCECmin                  INTEGER,  
    slbCurSecCfgSecPolCECin                   INTEGER, 
    slbCurSecCfgSecPolLearnPeriod             INTEGER,  
    slbCurSecCfgSecPolAdminStatus             INTEGER, 
    slbCurSecCfgSecPolLatencyAbs              INTEGER, 
    slbCurSecCfgSecPolLatencyPercent          INTEGER,
    slbCurSecCfgSecPolLatencyMin              INTEGER  
    }

slbCurSecCfgSecPolNameIdIndex OBJECT-TYPE
    SYNTAX   DisplayString
    MAX-ACCESS  read-only
    STATUS  current
    DESCRIPTION
        "The Security policy name(key id) as an index."
    ::= {slbCurSecCfgSecPolEntry  1 }

slbCurSecCfgSecPolName  OBJECT-TYPE
    SYNTAX   DisplayString
    MAX-ACCESS  read-only
    STATUS  current
    DESCRIPTION
        "Security policy name."
    ::= {slbCurSecCfgSecPolEntry  2 }

slbCurSecCfgSecPolBW  OBJECT-TYPE
    SYNTAX  INTEGER (0..102400)
    MAX-ACCESS  read-only
    STATUS  current
    DESCRIPTION
        "Security policy BW max threshold value."
    ::= {slbCurSecCfgSecPolEntry  3 }

slbCurSecCfgSecPolBWmin  OBJECT-TYPE
    SYNTAX   INTEGER (0..102400)
    MAX-ACCESS  read-only
    STATUS  current
    DESCRIPTION
        "Security policy BW min threshold value."
    ::= {slbCurSecCfgSecPolEntry  4 }

slbCurSecCfgSecPolBWin  OBJECT-TYPE
    SYNTAX   INTEGER (0..1000)
    MAX-ACCESS  read-only
    STATUS  current
    DESCRIPTION
        "Security policy BW ratio value."
    ::= {slbCurSecCfgSecPolEntry  5 }

slbCurSecCfgSecPolPPS  OBJECT-TYPE
    SYNTAX   INTEGER (0..10000000)
    MAX-ACCESS  read-only
    STATUS  current
    DESCRIPTION
        "Security policy PPS max threshold value."
    ::= {slbCurSecCfgSecPolEntry  6 }

slbCurSecCfgSecPolPPSmin  OBJECT-TYPE
    SYNTAX   INTEGER (0..10000000)
    MAX-ACCESS  read-only
    STATUS  current
    DESCRIPTION
        "Security policy PPS min threshold value."
    ::= {slbCurSecCfgSecPolEntry  7 }

slbCurSecCfgSecPolPPSin  OBJECT-TYPE
    SYNTAX   INTEGER (0..1000)
    MAX-ACCESS  read-only
    STATUS  current
    DESCRIPTION
        "Security policy PPS ratio value."
    ::= {slbCurSecCfgSecPolEntry  8 }

slbCurSecCfgSecPolCPS  OBJECT-TYPE
    SYNTAX   INTEGER (0..5000000)
    MAX-ACCESS  read-only
    STATUS  current
    DESCRIPTION
        "Security policy CPS max threshold value."
    ::= {slbCurSecCfgSecPolEntry  9 }

slbCurSecCfgSecPolCPSmin  OBJECT-TYPE
    SYNTAX   INTEGER (0..5000000)
    MAX-ACCESS  read-only
    STATUS  current
    DESCRIPTION
        "Security policy CPS min threshold value."
    ::= {slbCurSecCfgSecPolEntry  10 }

slbCurSecCfgSecPolCPSin  OBJECT-TYPE
    SYNTAX   INTEGER (0..1000)
    MAX-ACCESS  read-only
    STATUS  current
    DESCRIPTION
        "Security policy CPS ratio value."
    ::= {slbCurSecCfgSecPolEntry  11 }

slbCurSecCfgSecPolCEC  OBJECT-TYPE
    SYNTAX   INTEGER (0..10000)
    MAX-ACCESS  read-only
    STATUS  current
    DESCRIPTION
        "Security policy CEC max threshold value."
    ::= {slbCurSecCfgSecPolEntry  12 }

slbCurSecCfgSecPolCECmin  OBJECT-TYPE
    SYNTAX   INTEGER (0..10000)
    MAX-ACCESS  read-only
    STATUS  current
    DESCRIPTION
        "Security policy CEC min threshold value."
    ::= {slbCurSecCfgSecPolEntry  13 }

slbCurSecCfgSecPolCECin  OBJECT-TYPE
    SYNTAX   INTEGER (0..1000)
    MAX-ACCESS  read-only
    STATUS  current
    DESCRIPTION
        "Security policy CEC ratio value."
    ::= {slbCurSecCfgSecPolEntry  14 }

slbCurSecCfgSecPolLearnPeriod OBJECT-TYPE
    SYNTAX  INTEGER (1..168)
    MAX-ACCESS  read-only
    STATUS  current
    DESCRIPTION
        "Security policy learning period (in hours)."
    ::= { slbCurSecCfgSecPolEntry 15 }


slbCurSecCfgSecPolAdminStatus OBJECT-TYPE
    SYNTAX INTEGER {
        enabled(1),
        disabled(2),
        unsupported(2147483647)
        }
    MAX-ACCESS read-only
    STATUS current
    DESCRIPTION
        "Enable or disable security policy."
    ::= { slbCurSecCfgSecPolEntry 16 }

slbCurSecCfgSecPolLatencyAbs OBJECT-TYPE
    SYNTAX   INTEGER (0..10000000)
    MAX-ACCESS  read-only
    STATUS  current
    DESCRIPTION
        "Security policy Latency alert threshold (in microseconds)."
    ::= { slbCurSecCfgSecPolEntry 17 }

slbCurSecCfgSecPolLatencyPercent OBJECT-TYPE
    SYNTAX   INTEGER (0..1000)
    MAX-ACCESS  read-only
    STATUS  current
    DESCRIPTION
        "Security policy Latency increased ratio (current/history)."
    ::= { slbCurSecCfgSecPolEntry 18 }


slbCurSecCfgSecPolLatencyMin OBJECT-TYPE
    SYNTAX   INTEGER (0..10000000)
    MAX-ACCESS  read-only
    STATUS  current
    DESCRIPTION
        "Security policy Latency minimum alert threshold for detection."
    ::= { slbCurSecCfgSecPolEntry 19 }

slbNewSecCfgSecPolTable OBJECT-TYPE
    SYNTAX  SEQUENCE OF SlbNewSecCfgSecPolEntry
    MAX-ACCESS  not-accessible
    STATUS  current
    DESCRIPTION
        "The table for configuring security policy.
         Note:This mib is not supported on VX instance of Virtualization."
    ::= { secPol 2 }



slbNewSecCfgSecPolEntry OBJECT-TYPE
    SYNTAX  SlbNewSecCfgSecPolEntry
    MAX-ACCESS  not-accessible
    STATUS  current
    DESCRIPTION
        "A row in the security policy table."
    INDEX   { slbNewSecCfgSecPolNameIdIndex }
    ::= { slbNewSecCfgSecPolTable 1 }


SlbNewSecCfgSecPolEntry ::= SEQUENCE {
    slbNewSecCfgSecPolNameIdIndex             DisplayString,
    slbNewSecCfgSecPolName                    DisplayString,
    slbNewSecCfgSecPolBW                      INTEGER,   
    slbNewSecCfgSecPolBWmin                   INTEGER,  
    slbNewSecCfgSecPolBWin                    INTEGER,
    slbNewSecCfgSecPolPPS                     INTEGER,   
    slbNewSecCfgSecPolPPSmin                  INTEGER,  
    slbNewSecCfgSecPolPPSin                   INTEGER,   
    slbNewSecCfgSecPolCPS                     INTEGER,   
    slbNewSecCfgSecPolCPSmin                  INTEGER,  
    slbNewSecCfgSecPolCPSin                   INTEGER,   
    slbNewSecCfgSecPolCEC                     INTEGER,   
    slbNewSecCfgSecPolCECmin                  INTEGER,  
    slbNewSecCfgSecPolCECin                   INTEGER, 
    slbNewSecCfgSecPolLearnPeriod             INTEGER,  
    slbNewSecCfgSecPolAdminStatus             INTEGER,
    slbNewSecCfgSecPolDel                     INTEGER, 
    slbNewSecCfgSecPolLatencyAbs              INTEGER, 
    slbNewSecCfgSecPolLatencyPercent          INTEGER,
    slbNewSecCfgSecPolLatencyMin              INTEGER  
    }

slbNewSecCfgSecPolNameIdIndex OBJECT-TYPE
    SYNTAX   DisplayString
    MAX-ACCESS  read-create
    STATUS  current
    DESCRIPTION
        "The Security policy name(key id) as an index."
    ::= {slbNewSecCfgSecPolEntry  1 }

slbNewSecCfgSecPolName  OBJECT-TYPE
    SYNTAX   DisplayString
    MAX-ACCESS  read-create
    STATUS  current
    DESCRIPTION
        "Security policy name."
    ::= {slbNewSecCfgSecPolEntry  2 }

slbNewSecCfgSecPolBW  OBJECT-TYPE
    SYNTAX   INTEGER (0..102400)
    MAX-ACCESS  read-create
    STATUS  current
    DESCRIPTION
        "Security policy BW max threshold value."
    ::= {slbNewSecCfgSecPolEntry  3 }

slbNewSecCfgSecPolBWmin  OBJECT-TYPE
    SYNTAX   INTEGER (0..102400)
    MAX-ACCESS  read-create
    STATUS  current
    DESCRIPTION
        "Security policy BW min threshold value."
    ::= {slbNewSecCfgSecPolEntry  4 }

slbNewSecCfgSecPolBWin  OBJECT-TYPE
    SYNTAX   INTEGER (0..1000)
    MAX-ACCESS  read-create
    STATUS  current
    DESCRIPTION
        "Security policy BW ratio value."
    ::= {slbNewSecCfgSecPolEntry  5 }

slbNewSecCfgSecPolPPS  OBJECT-TYPE
    SYNTAX   INTEGER (0..10000000)
    MAX-ACCESS  read-create
    STATUS  current
    DESCRIPTION
        "Security policy PPS max threshold value."
    ::= {slbNewSecCfgSecPolEntry  6 }

slbNewSecCfgSecPolPPSmin  OBJECT-TYPE
    SYNTAX   INTEGER (0..10000000)
    MAX-ACCESS  read-create
    STATUS  current
    DESCRIPTION
        "Security policy PPS min threshold value."
    ::= {slbNewSecCfgSecPolEntry  7 }

slbNewSecCfgSecPolPPSin  OBJECT-TYPE
    SYNTAX   INTEGER (0..1000)
    MAX-ACCESS  read-create
    STATUS  current
    DESCRIPTION
        "Security policy PPS ratio value."
    ::= {slbNewSecCfgSecPolEntry  8 }

slbNewSecCfgSecPolCPS  OBJECT-TYPE
    SYNTAX   INTEGER (0..5000000)
    MAX-ACCESS  read-create
    STATUS  current
    DESCRIPTION
        "Security policy CPS max threshold value."
    ::= {slbNewSecCfgSecPolEntry  9 }

slbNewSecCfgSecPolCPSmin  OBJECT-TYPE
    SYNTAX   INTEGER (0..5000000)
    MAX-ACCESS  read-create
    STATUS  current
    DESCRIPTION
        "Security policy CPS min threshold value."
    ::= {slbNewSecCfgSecPolEntry  10 }

slbNewSecCfgSecPolCPSin  OBJECT-TYPE
    SYNTAX   INTEGER (0..1000)
    MAX-ACCESS  read-create
    STATUS  current
    DESCRIPTION
        "Security policy CPS ratio value."
    ::= {slbNewSecCfgSecPolEntry  11 }

slbNewSecCfgSecPolCEC  OBJECT-TYPE
    SYNTAX   INTEGER (0..10000)
    MAX-ACCESS  read-create
    STATUS  current
    DESCRIPTION
        "Security policy CEC max threshold value."
    ::= {slbNewSecCfgSecPolEntry  12 }

slbNewSecCfgSecPolCECmin  OBJECT-TYPE
    SYNTAX   INTEGER (0..10000)
    MAX-ACCESS  read-create
    STATUS  current
    DESCRIPTION
        "Security policy CEC min threshold value."
    ::= {slbNewSecCfgSecPolEntry  13 }

slbNewSecCfgSecPolCECin  OBJECT-TYPE
    SYNTAX   INTEGER (0..1000)
    MAX-ACCESS  read-create
    STATUS  current
    DESCRIPTION
        "Security policy CEC ratio value."
    ::= {slbNewSecCfgSecPolEntry  14 }

slbNewSecCfgSecPolLearnPeriod OBJECT-TYPE
    SYNTAX  INTEGER (1..168)
    MAX-ACCESS  read-create
    STATUS  current
    DESCRIPTION
        "Security policy learning period (in hours)."
    ::= { slbNewSecCfgSecPolEntry 15 }


slbNewSecCfgSecPolAdminStatus OBJECT-TYPE
    SYNTAX INTEGER {
        enabled(1),
        disabled(2),
        unsupported(2147483647)
        }
    MAX-ACCESS read-create
    STATUS current
    DESCRIPTION
        "Enable or disable security policy."
    ::= { slbNewSecCfgSecPolEntry 16 }

slbNewSecCfgSecPolDel OBJECT-TYPE
    SYNTAX  INTEGER {
        other(1),
        delete(2),
	delWithAssociations(3),
        unsupported(2147483647)
    }
    MAX-ACCESS  read-create
    STATUS  current
    DESCRIPTION
        "Delete Security policy."
    ::= { slbNewSecCfgSecPolEntry 17 }

 
slbNewSecCfgSecPolLatencyAbs OBJECT-TYPE
    SYNTAX   INTEGER (0..10000000)
    MAX-ACCESS  read-create
    STATUS  current
    DESCRIPTION
        "Security policy Latency alert threshold (in microseconds)."
    ::= { slbNewSecCfgSecPolEntry 18 }

slbNewSecCfgSecPolLatencyPercent OBJECT-TYPE
    SYNTAX   INTEGER (0..1000)
    MAX-ACCESS  read-create
    STATUS  current
    DESCRIPTION
        "Security policy Latency increased ratio (current/history)."
    ::= { slbNewSecCfgSecPolEntry 19 }

slbNewSecCfgSecPolLatencyMin OBJECT-TYPE
    SYNTAX   INTEGER (0..10000000)
    MAX-ACCESS  read-create
    STATUS  current
    DESCRIPTION
        "Security policy Latency minimum alert threshold for detection."
    ::= { slbNewSecCfgSecPolEntry 20 }

--SECPOL statistics

secPolPerServStatsTable OBJECT-TYPE
   SYNTAX SEQUENCE OF SecPolPerServStatsEntry
   MAX-ACCESS not-accessible
   STATUS current
   DESCRIPTION
       "A table for security policy statistics per virtual service.
        Note:This mib is not supported on VX instance of Virtualization."
   ::= {secSlbStats 1}

secPolPerServStatsEntry OBJECT-TYPE
   SYNTAX SecPolPerServStatsEntry
   MAX-ACCESS not-accessible
   STATUS  current
   DESCRIPTION
       " The row definition for security policy statistics per virtual service table."
   INDEX  { secPolPerServVirtServIndex, secPolPerServVirtServiceIndex}
   ::= {secPolPerServStatsTable 1}

SecPolPerServStatsEntry  ::= SEQUENCE {
        secPolPerServVirtServIndex           DisplayString,
        secPolPerServVirtServiceIndex        Integer32,
	secPolPerServVirtServPort            Integer32,
	secPolPerServSecPolId                DisplayString,
	secPolPerServBwCurVal		     Integer32,
	secPolPerServBwLastPeriodAvg         Integer32,
	secPolPerServBwCurPeriodAvg          Integer32,
	secPolPerServBwPeak		     Integer32,
	secPolPerServBwPeakTimestamp         DisplayString,
	secPolPerServPPSCurVal		     Integer32,
	secPolPerServPPSLastPeriodAvg        Integer32,
	secPolPerServPPSCurPeriodAvg          Integer32,
	secPolPerServPPSPeak		     Integer32,
	secPolPerServPPSPeakTimestamp        DisplayString,
	secPolPerServCPSCurVal		     Integer32,
	secPolPerServCPSLastPeriodAvg        Integer32,
	secPolPerServCPSCurPeriodAvg         Integer32,
	secPolPerServCPSPeak		     Integer32,
	secPolPerServCPSPeakTimestamp        DisplayString,
	secPolPerServCECCurVal		     Integer32,
	secPolPerServCECLastPeriodAvg        Integer32,
	secPolPerServCECCurPeriodAvg         Integer32,
	secPolPerServCECPeak		     Integer32,
	secPolPerServCECPeakTimestamp        DisplayString,
        secPolPerServLatencyCurVal           Integer32,
        secPolPerServLatencyLastPeriodAvg    Integer32,
        secPolPerServLatencyCurPeriodAvg     Integer32,
        secPolPerServLatencyPeak             Integer32,
        secPolPerServLatencyPeakTimestamp    DisplayString
        }

secPolPerServVirtServIndex  OBJECT-TYPE
   SYNTAX  DisplayString (SIZE(1..255))
   MAX-ACCESS  read-only
   STATUS  current
   DESCRIPTION
       "Virtual server number in alphanumeric."
   ::= {secPolPerServStatsEntry 1}

secPolPerServVirtServiceIndex  OBJECT-TYPE
   SYNTAX  Integer32 
   MAX-ACCESS  read-only
   STATUS  current
   DESCRIPTION
       "Virtual server service index."
   ::= {secPolPerServStatsEntry 2}

secPolPerServVirtServPort  OBJECT-TYPE
   SYNTAX  Integer32 
   MAX-ACCESS  read-only
   STATUS  current
   DESCRIPTION
       "Virtual server service port number."
   ::= {secPolPerServStatsEntry 3}

secPolPerServSecPolId  OBJECT-TYPE
   SYNTAX  DisplayString 
   MAX-ACCESS  read-only
   STATUS  current
   DESCRIPTION
       "Security policy identifier associated with the virtual service."
   ::= {secPolPerServStatsEntry 4}

secPolPerServBwCurVal  OBJECT-TYPE
   SYNTAX  Integer32 
   MAX-ACCESS  read-only
   STATUS  current
   DESCRIPTION
       "Virtual service security policy stats - Bandwidth current value."
   ::= {secPolPerServStatsEntry 5}

secPolPerServBwLastPeriodAvg  OBJECT-TYPE
   SYNTAX  Integer32 
   MAX-ACCESS  read-only
   STATUS  current
   DESCRIPTION
       "Virtual service security policy stats - Bandwidth last period average."
   ::= {secPolPerServStatsEntry 6}

secPolPerServBwCurPeriodAvg  OBJECT-TYPE
   SYNTAX  Integer32 
   MAX-ACCESS  read-only
   STATUS  current
   DESCRIPTION
       "Virtual service security policy stats - Bandwidth current period average."
   ::= {secPolPerServStatsEntry 7}

secPolPerServBwPeak  OBJECT-TYPE
   SYNTAX  Integer32 
   MAX-ACCESS  read-only
   STATUS  current
   DESCRIPTION
       "Virtual service security policy stats - Bandwidth peak value."
   ::= {secPolPerServStatsEntry 8}

secPolPerServBwPeakTimestamp  OBJECT-TYPE
   SYNTAX  DisplayString 
   MAX-ACCESS  read-only
   STATUS  current
   DESCRIPTION
       "Virtual service security policy stats - Bandwidth peak timestamp."
   ::= {secPolPerServStatsEntry 9}

secPolPerServPPSCurVal  OBJECT-TYPE
   SYNTAX  Integer32 
   MAX-ACCESS  read-only
   STATUS  current
   DESCRIPTION
       "Virtual service security policy stats - PPS current value."
   ::= {secPolPerServStatsEntry 10}

secPolPerServPPSLastPeriodAvg  OBJECT-TYPE
   SYNTAX  Integer32 
   MAX-ACCESS  read-only
   STATUS  current
   DESCRIPTION
       "Virtual service security policy stats - PPS last period average."
   ::= {secPolPerServStatsEntry 11}

secPolPerServPPSCurPeriodAvg  OBJECT-TYPE
   SYNTAX  Integer32 
   MAX-ACCESS  read-only
   STATUS  current
   DESCRIPTION
       "Virtual service security policy stats - PPS current period average."
   ::= {secPolPerServStatsEntry 12}

secPolPerServPPSPeak  OBJECT-TYPE
   SYNTAX  Integer32 
   MAX-ACCESS  read-only
   STATUS  current
   DESCRIPTION
       "Virtual service security policy stats - PPS peak value."
   ::= {secPolPerServStatsEntry 13}

secPolPerServPPSPeakTimestamp  OBJECT-TYPE
   SYNTAX  DisplayString 
   MAX-ACCESS  read-only
   STATUS  current
   DESCRIPTION
       "Virtual service security policy stats - PPS peak timestamp."
   ::= {secPolPerServStatsEntry 14}

secPolPerServCPSCurVal  OBJECT-TYPE
   SYNTAX  Integer32 
   MAX-ACCESS  read-only
   STATUS  current
   DESCRIPTION
       "Virtual service security policy stats - CPS current value."
   ::= {secPolPerServStatsEntry 15}

secPolPerServCPSLastPeriodAvg  OBJECT-TYPE
   SYNTAX  Integer32 
   MAX-ACCESS  read-only
   STATUS  current
   DESCRIPTION
       "Virtual service security policy stats - CPS last period average."
   ::= {secPolPerServStatsEntry 16}

secPolPerServCPSCurPeriodAvg  OBJECT-TYPE
   SYNTAX  Integer32 
   MAX-ACCESS  read-only
   STATUS  current
   DESCRIPTION
       "Virtual service security policy stats - CPS current period average."
   ::= {secPolPerServStatsEntry 17}

secPolPerServCPSPeak  OBJECT-TYPE
   SYNTAX  Integer32 
   MAX-ACCESS  read-only
   STATUS  current
   DESCRIPTION
       "Virtual service security policy stats - CPS peak value."
   ::= {secPolPerServStatsEntry 18}

secPolPerServCPSPeakTimestamp  OBJECT-TYPE
   SYNTAX  DisplayString 
   MAX-ACCESS  read-only
   STATUS  current
   DESCRIPTION
       "Virtual service security policy stats - CPS peak timestamp."
   ::= {secPolPerServStatsEntry 19}

secPolPerServCECCurVal  OBJECT-TYPE
   SYNTAX  Integer32 
   MAX-ACCESS  read-only
   STATUS  current
   DESCRIPTION
       "Virtual service security policy stats - CEC current value."
   ::= {secPolPerServStatsEntry 20}

secPolPerServCECLastPeriodAvg  OBJECT-TYPE
   SYNTAX  Integer32 
   MAX-ACCESS  read-only
   STATUS  current
   DESCRIPTION
       "Virtual service security policy stats - CEC last period average."
   ::= {secPolPerServStatsEntry 21}

secPolPerServCECCurPeriodAvg  OBJECT-TYPE
   SYNTAX  Integer32 
   MAX-ACCESS  read-only
   STATUS  current
   DESCRIPTION
       "Virtual service security policy stats - CEC current period average."
   ::= {secPolPerServStatsEntry 22}

secPolPerServCECPeak  OBJECT-TYPE
   SYNTAX  Integer32 
   MAX-ACCESS  read-only
   STATUS  current
   DESCRIPTION
       "Virtual service security policy stats - CEC peak value."
   ::= {secPolPerServStatsEntry 23}

secPolPerServCECPeakTimestamp  OBJECT-TYPE
   SYNTAX  DisplayString 
   MAX-ACCESS  read-only
   STATUS  current
   DESCRIPTION
       "Virtual service security policy stats - CEC peak timestamp."
   ::= {secPolPerServStatsEntry 24}


secPolPerServLatencyCurVal  OBJECT-TYPE
   SYNTAX  Integer32
   MAX-ACCESS  read-only
   STATUS  current
   DESCRIPTION
       "Virtual service security policy stats - Latency current value."
   ::= {secPolPerServStatsEntry 25 }

secPolPerServLatencyLastPeriodAvg  OBJECT-TYPE
   SYNTAX  Integer32
   MAX-ACCESS  read-only
   STATUS  current
   DESCRIPTION
       "Virtual service security policy stats - Latency last period average."
   ::= {secPolPerServStatsEntry 26}

secPolPerServLatencyCurPeriodAvg  OBJECT-TYPE
   SYNTAX  Integer32
   MAX-ACCESS  read-only
   STATUS  current
   DESCRIPTION
       "Virtual service security policy stats - Latency current period average."
   ::= {secPolPerServStatsEntry 27}

secPolPerServLatencyPeak  OBJECT-TYPE
   SYNTAX  Integer32
   MAX-ACCESS  read-only
   STATUS  current
   DESCRIPTION
       "Virtual service security policy stats - Latency peak value."
   ::= {secPolPerServStatsEntry 28 }

secPolPerServLatencyPeakTimestamp  OBJECT-TYPE
   SYNTAX  DisplayString
   MAX-ACCESS  read-only
   STATUS  current
   DESCRIPTION
       "Virtual service security policy stats - Latency peak timestamp."
   ::= {secPolPerServStatsEntry 29}


--CDP Group Statistics


slbCDPGrpStatsTable OBJECT-TYPE
   SYNTAX SEQUENCE OF SlbCDPGrpStatsEntry
   MAX-ACCESS not-accessible
   STATUS current
   DESCRIPTION
       "A table for CDP group statistics.
        Note:This mib is not supported on VX instance of Virtualization."
   ::= {cdpGrpStats 1}

slbCDPGrpStatsEntry OBJECT-TYPE
   SYNTAX SlbCDPGrpStatsEntry
   MAX-ACCESS not-accessible
   STATUS  current
   DESCRIPTION
       " The row definition for security policy statistics per virtual service table."
   INDEX  { slbCDPGrpIndex}
   ::= {slbCDPGrpStatsTable 1}

  SlbCDPGrpStatsEntry::= SEQUENCE {
        slbCDPGrpIndex           DisplayString,
	slbCDPGrpLastSuccess     DisplayString,
	slbCDPGrpLastFailed      DisplayString
	}

  slbCDPGrpIndex OBJECT-TYPE
   SYNTAX  DisplayString (SIZE(1..255))
   MAX-ACCESS  read-only
   STATUS  current
   DESCRIPTION
       "CDP group index in alphanumeric."
   ::= {slbCDPGrpStatsEntry 1}

   slbCDPGrpLastSuccess OBJECT-TYPE
   SYNTAX  DisplayString (SIZE(1..255))
   MAX-ACCESS  read-only
   STATUS  current
   DESCRIPTION
       "Last Successful Download."
   ::= {slbCDPGrpStatsEntry 2}

   slbCDPGrpLastFailed OBJECT-TYPE
   SYNTAX  DisplayString (SIZE(1..255))
   MAX-ACCESS  read-only
   STATUS  current
   DESCRIPTION
       "Last Failed Download."
   ::= {slbCDPGrpStatsEntry 3}


sslOffPerCiphServStatsTable OBJECT-TYPE
   SYNTAX SEQUENCE OF SslOffPerCiphServStatsEntry
   MAX-ACCESS not-accessible
   STATUS current
   DESCRIPTION
       "A table for SSL statistics per virtual service.
        Note:This mib is not supported on VX instance of Virtualization."
   ::= {sslSlbStats 24}

sslOffPerCiphServStatsEntry OBJECT-TYPE
   SYNTAX SslOffPerCiphServStatsEntry
   MAX-ACCESS not-accessible
   STATUS  current
   DESCRIPTION
       " The row definition for SSL statistics per virtual service table."
   INDEX  { sslOffPerCiphServVirtServIndex, sslOffPerCiphServVirtServiceIndex, sslOffPerCiphServVirtCiphIndex}
   ::= {sslOffPerCiphServStatsTable 1}

SslOffPerCiphServStatsEntry  ::= SEQUENCE {
        sslOffPerCiphServVirtServIndex           DisplayString,
        sslOffPerCiphServVirtServiceIndex        Integer32,
        sslOffPerCiphServVirtCiphIndex           Integer32,
        sslOffPerCiphServCiphName                DisplayString,
        sslOffPerCiphServNewhandShake            Integer32,
        sslOffPerCiphServVirtServPort            Integer32,
        sslOffPerCiphServNewhandShakeTotal       Integer32
        }

sslOffPerCiphServVirtServIndex  OBJECT-TYPE
    SYNTAX  DisplayString
    MAX-ACCESS  read-only
    STATUS  current
    DESCRIPTION
        "The virtual server name that identifies the service."
   ::= {sslOffPerCiphServStatsEntry 1}

sslOffPerCiphServVirtServiceIndex  OBJECT-TYPE
   SYNTAX  Integer32
   MAX-ACCESS  read-only
   STATUS  current
   DESCRIPTION
       "Virtual server service index."
   ::= {sslOffPerCiphServStatsEntry 2}

sslOffPerCiphServVirtCiphIndex  OBJECT-TYPE
   SYNTAX  Integer32
   MAX-ACCESS  read-only
   STATUS  current
   DESCRIPTION
       "Virtual server service cipher index."
   ::= {sslOffPerCiphServStatsEntry 3}

sslOffPerCiphServCiphName  OBJECT-TYPE
   SYNTAX  DisplayString
   MAX-ACCESS  read-only
   STATUS  current
   DESCRIPTION
       "Virtual server service cipher name."
   ::= {sslOffPerCiphServStatsEntry 4}

sslOffPerCiphServNewhandShake  OBJECT-TYPE
   SYNTAX  Integer32
   MAX-ACCESS  read-only
   STATUS  current
   DESCRIPTION
       "Number of New SSL handshakes between Clients and AAS per second for this virtual service."
   ::= {sslOffPerCiphServStatsEntry 5}

sslOffPerCiphServVirtServPort  OBJECT-TYPE
   SYNTAX  Integer32
   MAX-ACCESS  read-only
   STATUS  current
   DESCRIPTION
       "Virtual server service port number."
   ::= {sslOffPerCiphServStatsEntry 6}
   
   sslOffPerCiphServNewhandShakeTotal  OBJECT-TYPE
   SYNTAX  Integer32
   MAX-ACCESS  read-only
   STATUS  current
   DESCRIPTION
       "Number of Total SSL handshakes between Clients and AAS per second for this virtual service."
   ::= {sslOffPerCiphServStatsEntry 7}
   
-- Overlay 

overlayCurCfgEnatFilt OBJECT-TYPE
    SYNTAX  INTEGER {
        vxlan(1),
            disabled(2),
        unsupported(2147483647)
    }
    MAX-ACCESS  read-only
    STATUS  current
    DESCRIPTION
        "Enable or disable overlay tunnel processing.
         Note:This mib is not supported for VX instance of Virtualization."
    ::= { overlayCfgGeneral 1 }

	
overlayNewCfgEnatFilt OBJECT-TYPE
    SYNTAX  INTEGER {
        vxlan(1),
            disabled(2),
        unsupported(2147483647)
    }
    MAX-ACCESS  read-write
    STATUS  current
    DESCRIPTION
        "Enable or disable overlay tunnel processing.
         Note:This mib is not supported for VX instance of Virtualization."
    ::= { overlayCfgGeneral 2 }	
	
overlayCfgMapTableMaxSize OBJECT-TYPE
    SYNTAX  Integer32 
    MAX-ACCESS  read-only 
    STATUS  current 
    DESCRIPTION 
        "The maximum number of entries in overlay mapping table.
         Note:This mib is not supported for VX instance of Virtualization."
    ::= { overlayCfg 2 }	

overlayCurCfgMapTable OBJECT-TYPE
    SYNTAX  SEQUENCE OF OverlayCurCfgMapTableEntry
    MAX-ACCESS  not-accessible
    STATUS  current
    DESCRIPTION
        "The mapping table of slb overlay,
         Note:This mib is not supported for VX instance of Virtualization."
    ::= { overlayCfg 3 }	
	
overlayCurCfgMapTableEntry OBJECT-TYPE
    SYNTAX  OverlayCurCfgMapTableEntry
    MAX-ACCESS  not-accessible
    STATUS  current
    DESCRIPTION
        "A row in overlay mapping table.
         Note:This mib is not supported for VX instance of Virtualization."
    INDEX   { overlayCurCfgMapIndex }
    ::= { overlayCurCfgMapTable 1 }	
    
OverlayCurCfgMapTableEntry ::= SEQUENCE {
    overlayCurCfgMapIndex       	DisplayString,
    overlayCurCfgMapIdmackey        PhysAddress,
    overlayCurCfgMap6Osip     		DisplayString,
    overlayCurCfgMapOsmac        	PhysAddress,
    overlayCurCfgMap6Odip        	DisplayString,
    overlayCurCfgMapOdmac           PhysAddress,
    overlayCurCfgMapPort      		INTEGER,
    overlayCurCfgMapVlan           	INTEGER
    }   
    
overlayCurCfgMapIndex OBJECT-TYPE
    SYNTAX DisplayString (SIZE(1..255))
    MAX-ACCESS  read-only
    STATUS  current
    DESCRIPTION
        "Overlay tunnel mapping table index."
    ::= { overlayCurCfgMapTableEntry 1 }	
		
overlayCurCfgMapIdmackey OBJECT-TYPE
    SYNTAX  PhysAddress 
    MAX-ACCESS  read-only
    STATUS  current
    DESCRIPTION
        "Inner packet Dest mac key for mapping table entry:
        		get a valid mac number.
    			ff:ff:ff:ff:ff:ff as (any) - only for last entry."   
    ::= { overlayCurCfgMapTableEntry 2 }	
	
overlayCurCfgMap6Osip OBJECT-TYPE
    SYNTAX   DisplayString (SIZE(0..40))
    MAX-ACCESS  read-only
    STATUS  current
    DESCRIPTION
        "Outer packet source IP address for tunnel wrapper.
	 	 Address should be 4-byte hexadecimal colon notation.
         Valid IPv6 address should be in any of the following forms
           xxxx:xxxx:xxxx:xxxx:xxxx:xxxx:xxxx:xxxx or
           xxxx::xxxx:xxxx:xxxx:xxxx or ::xxxx"
    ::= { overlayCurCfgMapTableEntry 3 }
	
overlayCurCfgMapOsmac OBJECT-TYPE
    SYNTAX  PhysAddress 
    MAX-ACCESS  read-only
    STATUS  current
    DESCRIPTION
        "Outer packet source mac for tunnel wrapper."
    ::= { overlayCurCfgMapTableEntry 4 }	

overlayCurCfgMap6Odip OBJECT-TYPE
    SYNTAX   DisplayString (SIZE(0..40))
    MAX-ACCESS  read-only
    STATUS  current
    DESCRIPTION
        "Outer packet Dest IP address for tunnel wrapper..
	 	 Address should be 4-byte hexadecimal colon notation.
         Valid IPv6 address should be in any of the following forms
           xxxx:xxxx:xxxx:xxxx:xxxx:xxxx:xxxx:xxxx or
           xxxx::xxxx:xxxx:xxxx:xxxx or ::xxxx"
       
    ::= { overlayCurCfgMapTableEntry 5 }	
	
overlayCurCfgMapOdmac OBJECT-TYPE
    SYNTAX  PhysAddress 
    MAX-ACCESS  read-only
    STATUS  current
    DESCRIPTION
        "Outer packet dest mac for tunnel wrapper."
    ::= { overlayCurCfgMapTableEntry 6 }	

overlayCurCfgMapPort OBJECT-TYPE
    SYNTAX  INTEGER (0..255)
    MAX-ACCESS  read-only
    STATUS  current
    DESCRIPTION
         "Outer packet Alteon egress port:
        	0	- auto
        	1-max port	- port number"    
    ::= { overlayCurCfgMapTableEntry 7 }	


overlayCurCfgMapVlan OBJECT-TYPE
    SYNTAX  INTEGER (0..4095)
    MAX-ACCESS  read-only
    STATUS  current
    DESCRIPTION
        "Outer packet VLAN Id:
        	0	- auto
        	1-4090	- vlan id" 
    ::= { overlayCurCfgMapTableEntry 8 }
    
overlayNewCfgMapTable OBJECT-TYPE
    SYNTAX  SEQUENCE OF OverlayNewCfgMapTableEntry
    MAX-ACCESS  not-accessible
    STATUS  current
    DESCRIPTION
        "The mapping table of slb overlay,
         Note:This mib is not supported for VX instance of Virtualization."
    ::= { overlayCfg 4 }	
    
overlayNewCfgMapTableEntry OBJECT-TYPE
    SYNTAX  OverlayNewCfgMapTableEntry
    MAX-ACCESS  not-accessible
    STATUS  current
    DESCRIPTION
        "A row in overlay mapping table.
         Note:This mib is not supported for VX instance of Virtualization."
    INDEX   { overlayNewCfgMapIndex }
    ::= { overlayNewCfgMapTable 1 }	
	
OverlayNewCfgMapTableEntry ::= SEQUENCE {
    overlayNewCfgMapIndex       	DisplayString,
    overlayNewCfgMapIdmackey        PhysAddress,
    overlayNewCfgMap6Osip     		DisplayString,
    overlayNewCfgMapOsmac        	PhysAddress,
    overlayNewCfgMap6Odip        	DisplayString,
    overlayNewCfgMapOdmac           PhysAddress,
    overlayNewCfgMapPort      		INTEGER,
    overlayNewCfgMapVlan           	INTEGER,
    overlayNewCfgMapDelete			INTEGER
    }	

overlayNewCfgMapIndex OBJECT-TYPE
    SYNTAX  DisplayString (SIZE(1..255))
    MAX-ACCESS  read-only
    STATUS  current
    DESCRIPTION
        "Overlay tunnel mapping table index."
    ::= { overlayNewCfgMapTableEntry 1 }	
		
overlayNewCfgMapIdmackey OBJECT-TYPE
    SYNTAX  PhysAddress 
    MAX-ACCESS  read-write
    STATUS  current
    DESCRIPTION
        "Inner packet Dest mac key for mapping table entry:
        	usage:
        		set a valid mac number.
    			ff:ff:ff:ff:ff:ff as (any) - only for last entry."
    ::= { overlayNewCfgMapTableEntry 2 }	
	
overlayNewCfgMap6Osip OBJECT-TYPE
    SYNTAX   DisplayString (SIZE(0..40))
    MAX-ACCESS  read-write
    STATUS  current
    DESCRIPTION
        "Outer packet source IP address for tunnel wrapper.
	 	 Address should be 4-byte hexadecimal colon notation.
         Valid IPv6 address should be in any of the following forms
           xxxx:xxxx:xxxx:xxxx:xxxx:xxxx:xxxx:xxxx or
           xxxx::xxxx:xxxx:xxxx:xxxx or ::xxxx"
    ::= { overlayNewCfgMapTableEntry 3 }
	
overlayNewCfgMapOsmac OBJECT-TYPE
    SYNTAX  PhysAddress 
    MAX-ACCESS  read-write
    STATUS  current
    DESCRIPTION
        "Outer packet source mac for tunnel wrapper."
    ::= { overlayNewCfgMapTableEntry 4 }	

overlayNewCfgMap6Odip OBJECT-TYPE
    SYNTAX   DisplayString (SIZE(0..40))
    MAX-ACCESS  read-write
    STATUS  current
    DESCRIPTION
        "Outer packet Dest IP address for tunnel wrapper.
	 	 Address should be 4-byte hexadecimal colon notation.
         Valid IPv6 address should be in any of the following forms
           xxxx:xxxx:xxxx:xxxx:xxxx:xxxx:xxxx:xxxx or
           xxxx::xxxx:xxxx:xxxx:xxxx or ::xxxx"
    ::= { overlayNewCfgMapTableEntry 5 }	
	
overlayNewCfgMapOdmac OBJECT-TYPE
    SYNTAX  PhysAddress 
    MAX-ACCESS  read-write
    STATUS  current
    DESCRIPTION
        "Outer packet dest mac for tunnel wrapper."
    ::= { overlayNewCfgMapTableEntry 6 }	

overlayNewCfgMapPort OBJECT-TYPE
    SYNTAX  INTEGER (0..255)
    MAX-ACCESS  read-write
    STATUS  current
    DESCRIPTION
        "Outer packet Alteon egress port:
         usage:
        	0	- auto
        	1-max port	- port number"         
    ::= { overlayNewCfgMapTableEntry 7 }	


overlayNewCfgMapVlan OBJECT-TYPE
    SYNTAX  INTEGER (0..4090)
    MAX-ACCESS  read-write
    STATUS  current
    DESCRIPTION
        "Outer packet VLAN Id:
        usage:
        	0	- auto
        	1-4090	- vlan id" 
    ::= { overlayNewCfgMapTableEntry 8 }

    
overlayNewCfgMapDelete OBJECT-TYPE
    SYNTAX  INTEGER {
        other(1),
        delete(2),
        all(3),
        unsupported(2147483647)
    }
    MAX-ACCESS  read-write
    STATUS  current
    DESCRIPTION
        "By setting the value to delete(2), Delete a specific overlay mapping table entry."
    ::= { overlayNewCfgMapTableEntry 9 }	
    
    
--Overlay statistics

slbOverlayStatsMapTable OBJECT-TYPE
   SYNTAX SEQUENCE OF SlbOverlayStatsMapEntry 
   MAX-ACCESS not-accessible
   STATUS current
   DESCRIPTION
       "A table for slb overlay mapping statistics .
        Note:This mib is not supported for VX instance of Virtualization."
   ::= {slbOverlayStats 1}

slbOverlayStatsMapEntry OBJECT-TYPE
   SYNTAX SlbOverlayStatsMapEntry
   MAX-ACCESS not-accessible
   STATUS  current
   DESCRIPTION
       " The row definition for slb overlay mapping entry statistics.
        Note:This mib is not supported for VX instance of Virtualization."
   INDEX  { slbOverlayStatsMapIndex}
   ::= {slbOverlayStatsMapTable 1}

SlbOverlayStatsMapEntry ::= SEQUENCE {
    slbOverlayStatsMapIndex    DisplayString,
    slbOverlayStatsMapHits     Counter64
    }

slbOverlayStatsMapIndex OBJECT-TYPE
    SYNTAX DisplayString (SIZE(1..255))
    MAX-ACCESS  read-only
    STATUS  current
    DESCRIPTION
        "slb overlay mapping stats table index."
    ::= { slbOverlayStatsMapEntry 1 }

slbOverlayStatsMapHits OBJECT-TYPE
    SYNTAX  Counter64 
    MAX-ACCESS  read-only
    STATUS  current
    DESCRIPTION
        "Overlay mapping table hits per entry."   
    ::= { slbOverlayStatsMapEntry 2 }

slbOverlayStatsTotalHits OBJECT-TYPE
    SYNTAX  Counter64 
    MAX-ACCESS  read-only
    STATUS  current
    DESCRIPTION
        "Overlay mapping table total hits per mapping entry.
         Note:This mib is not supported for VX instance of Virtualization."
    ::= { slbOverlayStats 2 }
    
slbOverlayStatsTotalMisses OBJECT-TYPE
    SYNTAX  Counter64 
    MAX-ACCESS  read-only
    STATUS  current
    DESCRIPTION
        "Overlay mapping table total misses per mapping table.
         Note:This mib is not supported for VX instance of Virtualization."
    ::= { slbOverlayStats 3 }    
    
slbOverlayStatsTotalBypass OBJECT-TYPE
    SYNTAX  Counter64 
    MAX-ACCESS  read-only
    STATUS  current
    DESCRIPTION
        "Overlay mapping table total bypass.
         Note:This mib is not supported for VX instance of Virtualization."
    ::= { slbOverlayStats 4 }     

slbOverlaySpStatsMapTable OBJECT-TYPE
   SYNTAX SEQUENCE OF SlbOverlaySpStatsMapEntry
   MAX-ACCESS not-accessible
   STATUS current
   DESCRIPTION
       "A table for slb overlay mapping statistics .
        Note:This mib is not supported for VX instance of Virtualization."
   ::= {slbOverlaySpStats 1}

slbOverlaySpStatsMapEntry OBJECT-TYPE
   SYNTAX SlbOverlaySpStatsMapEntry
   MAX-ACCESS not-accessible
   STATUS  current
   DESCRIPTION
       " The row definition for slb overlay mapping entry statistics.
       The following table has 2 indeces, in order to retrive
       valid values, please do to following:
       OID.<str len>.<entry(str)>.<sp val(decimal)> --> OID.2.49.50.10,
       Note:This mib is not supported for VX instance of Virtualization."
   INDEX  { slbOverlaySpStatsSpIndex, slbOverlaySpStatsMapIndex}
   ::= {slbOverlaySpStatsMapTable 1}

SlbOverlaySpStatsMapEntry ::= SEQUENCE {
	slbOverlaySpStatsSpIndex     Integer32,
    slbOverlaySpStatsMapIndex    DisplayString,
    slbOverlaySpStatsMapHits     Counter64,
    slbOverlaySpStatsTotalHits   Counter64,
    slbOverlaySpStatsTotalMisses Counter64, 
    slbOverlaySpStatsTotalBypass Counter64
    }

slbOverlaySpStatsSpIndex OBJECT-TYPE
    SYNTAX Integer32
    MAX-ACCESS  read-only
    STATUS  current
    DESCRIPTION
        "SP index."
    ::= { slbOverlaySpStatsMapEntry 1 }
    
slbOverlaySpStatsMapIndex OBJECT-TYPE
    SYNTAX DisplayString (SIZE(1..255))
    MAX-ACCESS  read-only
    STATUS  current
    DESCRIPTION
        "slb overlay mapping stats table index.
        This is an alpha numeric index so use it as follows:
        OID.<str len>.<entry(str)>.<sp val(decimal)> --> OID.2.49.50.10"
    ::= { slbOverlaySpStatsMapEntry 2 }    

slbOverlaySpStatsMapHits OBJECT-TYPE
    SYNTAX  Counter64 
    MAX-ACCESS  read-only
    STATUS  current
    DESCRIPTION
        "Overlay mapping table hits per SP."   
    ::= { slbOverlaySpStatsMapEntry 3 }

slbOverlaySpStatsTotalHits OBJECT-TYPE
    SYNTAX  Counter64 
    MAX-ACCESS  read-only
    STATUS  current
    DESCRIPTION
        "Overlay mapping table total hits per SP.
        In oder to retrive the following parameter please do as follow:
        set entry as 0 with a valid sp number.
        i.e OID.1.0.<sp num>"    
    ::= { slbOverlaySpStatsMapEntry 4 }
    
slbOverlaySpStatsTotalMisses OBJECT-TYPE
    SYNTAX  Counter64 
    MAX-ACCESS  read-only
    STATUS  current
    DESCRIPTION
        "Overlay mapping table total misses per SP.
        In oder to retrive the following parameter please do as follow:
        set entry as 0 with a valid sp number.
        i.e OID.1.0.<sp num>"   
    ::= { slbOverlaySpStatsMapEntry 5 }    
    
slbOverlaySpStatsTotalBypass OBJECT-TYPE
    SYNTAX  Counter64 
    MAX-ACCESS  read-only
    STATUS  current
    DESCRIPTION
        "Overlay mapping table total bypass per SP.
        In oder to retrive the following parameter please do as follow:
        set entry as 0 with a valid sp number.
        i.e OID.1.0.<sp num>"    
    ::= { slbOverlaySpStatsMapEntry 6 }          

-- Traffic Events Stats per Virtual Server Service Table

trafficEventsVirtServcStatsTable OBJECT-TYPE
    SYNTAX SEQUENCE OF TrafficEventsVirtServcStatsEntry
    MAX-ACCESS  not-accessible
    STATUS  current
    DESCRIPTION
      "Table for traffic event stats per service.
       Note:This mib is not supported for VX instance of Virtualization."
    ::= {trafficEventStats 1 }

trafficEventsVirtServcStatsEntry OBJECT-TYPE
    SYNTAX TrafficEventsVirtServcStatsEntry
    MAX-ACCESS  not-accessible
    STATUS current
    DESCRIPTION
      "A row n the traffic events stats table.
       Note:This mib is not supported for VX instance of Virtualization."
    INDEX { virtTrafficEventsStatVirtIndex, virtTrafficEventsStatSvcIndex }
    ::= { trafficEventsVirtServcStatsTable 1 }

TrafficEventsVirtServcStatsEntry ::= SEQUENCE {
    virtTrafficEventsStatVirtIndex                DisplayString,
    virtTrafficEventsStatSvcIndex                 Integer32,
    virtHttpReqSuccessPerSec                      Counter32,
    virtHttpReqSuccessTotal                       Counter64,
    virtHttpRespSuccessPerSec                     Counter32,
    virtHttpRespSuccessTotal                      Counter64,
    virtFeSSLInfoSuccessPerSec                    Counter32,
    virtFeSSLInfoSuccessTotal                     Counter64,
    virtBeSSLInfoSuccessPerSec                    Counter32,
    virtBeSSLInfoSuccessTotal                     Counter64,
    virtHostNameBypassSuccessPerSec               Counter32,
    virtHostNameBypassSuccessTotal                Counter64,
    virtHttpReqFailPerSec                         Counter32,
    virtHttpReqFailTotal                          Counter64,
    virtHttpRespFailPerSec                        Counter32,
    virtHttpRespFailTotal                         Counter64,
    virtFeSSLInfoFailPerSec                       Counter32,
    virtFeSSLInfoFailTotal                        Counter64,
    virtBeSSLInfoFailPerSec                       Counter32,
    virtBeSSLInfoFailTotal                        Counter64,
    virtHostNameBypassFailPerSec                  Counter32,
    virtHostNameBypassFailTotal                   Counter64,
    virtEventsFieldMissingPerSec                  Counter32,
    virtEventsFieldMissingTotal                   Counter64,
    virtEventsAllocFailPerSec                     Counter32,
    virtEventsAllocFailTotal                      Counter64,
    virtEventsQueueFullPerSec                     Counter32,
    virtEventsQueueFullTotal                      Counter64,
    virtLayer4ReqSuccessPerSec                    Counter32,
    virtLayer4ReqSuccessTotal                     Counter64,
    virtLayer4ReqFailPerSec                       Counter32,
    virtLayer4ReqFailTotal                        Counter64,
    virtLayer4ServicePort                         INTEGER,
    virtUnifiedSucessTotal                        Counter64,
    virtUnifiedSucessPerSec                       Counter32,
    virtUnifiedFailTotal                          Counter64,
    virtUnifiedFailPerSec                         Counter32,
    virtNormalUnifiedSucessTotal                  Counter64,
    virtNormalUnifiedSucessTotalPercentage        INTEGER,
    virtNormalUnifiedSucessPerSec                 Counter32,
    virtNormalUnifiedSucessPerSecPercentage       INTEGER,
    virtExceptionUnifiedSucessTotal               Counter64,
    virtExceptionUnifiedSucessTotalPercentage     INTEGER,
    virtExceptionUnifiedSucessPerSec              Counter32,
    virtExceptionUnifiedSucessPerSecPercentage    INTEGER
    }

virtTrafficEventsStatVirtIndex OBJECT-TYPE
     SYNTAX DisplayString (SIZE(1..255))
     MAX-ACCESS  read-only
     STATUS  current
     DESCRIPTION
         "The virtual server index."
     ::= { trafficEventsVirtServcStatsEntry 1 }

virtTrafficEventsStatSvcIndex OBJECT-TYPE
     SYNTAX  Integer32
     MAX-ACCESS  read-only
     STATUS  current
     DESCRIPTION
         "The virtual service index."
     ::= { trafficEventsVirtServcStatsEntry 2 }

virtHttpReqSuccessPerSec OBJECT-TYPE
     SYNTAX Counter32
     MAX-ACCESS  read-only
     STATUS  current
     DESCRIPTION
         "No of Http Requests sent as traffic events per second."
     ::= {trafficEventsVirtServcStatsEntry 3}

virtHttpReqSuccessTotal OBJECT-TYPE
     SYNTAX Counter64
     MAX-ACCESS  read-only
     STATUS  current
     DESCRIPTION
         "No of Http Requests sent successfully as traffic events in total."
     ::= {trafficEventsVirtServcStatsEntry 4}

virtHttpRespSuccessPerSec OBJECT-TYPE
     SYNTAX Counter32
     MAX-ACCESS  read-only
     STATUS  current
     DESCRIPTION
         "No of Http responses sent as traffic events per second."
     ::= {trafficEventsVirtServcStatsEntry 5}

virtHttpRespSuccessTotal OBJECT-TYPE
     SYNTAX Counter64
     MAX-ACCESS  read-only
     STATUS  current
     DESCRIPTION
         "No of Http responses sent successfully as traffic events in total."
     ::= {trafficEventsVirtServcStatsEntry 6}

virtFeSSLInfoSuccessPerSec OBJECT-TYPE
     SYNTAX Counter32
     MAX-ACCESS  read-only
     STATUS  current
     DESCRIPTION
         "No of fessl sent successfully as traffice events per second."
     ::= {trafficEventsVirtServcStatsEntry 7}

virtFeSSLInfoSuccessTotal OBJECT-TYPE
     SYNTAX Counter64
     MAX-ACCESS  read-only
     STATUS  current
     DESCRIPTION
         "No of fessl sent successfully as traffic events in total."
     ::= {trafficEventsVirtServcStatsEntry 8}

virtBeSSLInfoSuccessPerSec OBJECT-TYPE
     SYNTAX Counter32
     MAX-ACCESS  read-only
     STATUS  current
     DESCRIPTION
         "No of bessl sent successfully as traffice events per second."
     ::= {trafficEventsVirtServcStatsEntry 9}

virtBeSSLInfoSuccessTotal OBJECT-TYPE
     SYNTAX Counter64
     MAX-ACCESS  read-only
     STATUS  current
     DESCRIPTION
         "No of bessl sent successfully as traffic events in total."
     ::= {trafficEventsVirtServcStatsEntry 10}

virtHostNameBypassSuccessPerSec OBJECT-TYPE
     SYNTAX Counter32
     MAX-ACCESS  read-only
     STATUS  current
     DESCRIPTION
         "No of host names bypass sent successfully as traffice events per second."
     ::= {trafficEventsVirtServcStatsEntry 11}

virtHostNameBypassSuccessTotal OBJECT-TYPE
     SYNTAX Counter64
     MAX-ACCESS  read-only
     STATUS  current
     DESCRIPTION
         "No of host names bypass sent successfully as traffic events in total."
     ::= {trafficEventsVirtServcStatsEntry 12}

virtHttpReqFailPerSec OBJECT-TYPE
     SYNTAX Counter32
     MAX-ACCESS  read-only
     STATUS  current
     DESCRIPTION
         "No of Http requests failed to send as traffic events per second."
     ::= {trafficEventsVirtServcStatsEntry 13}

virtHttpReqFailTotal OBJECT-TYPE
     SYNTAX Counter64
     MAX-ACCESS  read-only
     STATUS  current
     DESCRIPTION
         "No of Http requests failed to send as traffic events in total."
     ::= {trafficEventsVirtServcStatsEntry 14}

virtHttpRespFailPerSec OBJECT-TYPE
     SYNTAX Counter32
     MAX-ACCESS  read-only
     STATUS  current
     DESCRIPTION
         "No of Http responses failed to send as traffic events per second."
     ::= {trafficEventsVirtServcStatsEntry 15}

virtHttpRespFailTotal OBJECT-TYPE
     SYNTAX Counter64
     MAX-ACCESS  read-only
     STATUS  current
     DESCRIPTION
         "No of Http responses failed to send as traffic events in total."
     ::= {trafficEventsVirtServcStatsEntry 16}

virtFeSSLInfoFailPerSec OBJECT-TYPE
     SYNTAX Counter32
     MAX-ACCESS  read-only
     STATUS  current
     DESCRIPTION
         "No of fessl failed to send as traffice events per second."
     ::= {trafficEventsVirtServcStatsEntry 17}

virtFeSSLInfoFailTotal OBJECT-TYPE
     SYNTAX Counter64
     MAX-ACCESS  read-only
     STATUS  current
     DESCRIPTION
        "No of fessl failed to send as traffice events in total." 
     ::= {trafficEventsVirtServcStatsEntry 18}

virtBeSSLInfoFailPerSec OBJECT-TYPE
     SYNTAX Counter32
     MAX-ACCESS  read-only
     STATUS  current
     DESCRIPTION
         "No of bessl failed to send as traffice events per second."
     ::= {trafficEventsVirtServcStatsEntry 19}

virtBeSSLInfoFailTotal OBJECT-TYPE
     SYNTAX Counter64
     MAX-ACCESS  read-only
     STATUS  current
     DESCRIPTION
         "No of bessl failed to send as traffice events in total."
     ::= {trafficEventsVirtServcStatsEntry 20}

virtHostNameBypassFailPerSec OBJECT-TYPE
     SYNTAX Counter32
     MAX-ACCESS  read-only
     STATUS  current
     DESCRIPTION
         "No of host name bypass failed to send as traffic events per second."
     ::= {trafficEventsVirtServcStatsEntry 21}

virtHostNameBypassFailTotal OBJECT-TYPE
     SYNTAX Counter64
     MAX-ACCESS  read-only
     STATUS  current
     DESCRIPTION
         "No of host name bypass failed to send as traffic events in total."
     ::= {trafficEventsVirtServcStatsEntry 22}

virtEventsFieldMissingPerSec OBJECT-TYPE
     SYNTAX Counter32
     MAX-ACCESS  read-only
     STATUS  current
     DESCRIPTION
         "Event field missing failure per second."
     ::= {trafficEventsVirtServcStatsEntry 23}

virtEventsFieldMissingTotal OBJECT-TYPE
     SYNTAX Counter64
     MAX-ACCESS  read-only
     STATUS  current
     DESCRIPTION
         "Event field missing failure in total."
     ::= {trafficEventsVirtServcStatsEntry 24}

virtEventsAllocFailPerSec OBJECT-TYPE
     SYNTAX Counter32
     MAX-ACCESS  read-only
     STATUS  current
     DESCRIPTION
         "Event allocation failure per second."
     ::= {trafficEventsVirtServcStatsEntry 25}

virtEventsAllocFailTotal OBJECT-TYPE
     SYNTAX Counter64
     MAX-ACCESS  read-only
     STATUS  current
     DESCRIPTION
         "Event allocation failure in total."
     ::= {trafficEventsVirtServcStatsEntry 26}

virtEventsQueueFullPerSec OBJECT-TYPE
     SYNTAX Counter32
     MAX-ACCESS  read-only
     STATUS  current
     DESCRIPTION
         "Event queue full failure per second."
     ::= {trafficEventsVirtServcStatsEntry 27}

virtEventsQueueFullTotal OBJECT-TYPE
     SYNTAX Counter64
     MAX-ACCESS  read-only
     STATUS  current
     DESCRIPTION
         "Event queue full failure in total."
     ::= {trafficEventsVirtServcStatsEntry 28}

virtLayer4ReqSuccessPerSec OBJECT-TYPE
     SYNTAX Counter32
     MAX-ACCESS  read-only
     STATUS  current
     DESCRIPTION
         "layer 4 events sent per second."
     ::= {trafficEventsVirtServcStatsEntry 29}

virtLayer4ReqSuccessTotal OBJECT-TYPE
     SYNTAX Counter64
     MAX-ACCESS  read-only
     STATUS  current
     DESCRIPTION
         "layer 4 events sent in total."
     ::= {trafficEventsVirtServcStatsEntry 30}

virtLayer4ReqFailPerSec OBJECT-TYPE
     SYNTAX Counter32
     MAX-ACCESS  read-only
     STATUS  current
     DESCRIPTION
         "layer 4 events failure per second."
     ::= {trafficEventsVirtServcStatsEntry 31}

virtLayer4ReqFailTotal OBJECT-TYPE
     SYNTAX Counter64
     MAX-ACCESS  read-only
     STATUS  current
     DESCRIPTION
         "layer 4 events failure in total."
     ::= {trafficEventsVirtServcStatsEntry 32}

virtLayer4ServicePort OBJECT-TYPE
     SYNTAX  INTEGER (1..65534)
     MAX-ACCESS  read-only
     STATUS  current
     DESCRIPTION
         "The layer4 virtual port number of the service."
     ::= {trafficEventsVirtServcStatsEntry 33}

virtUnifiedSucessTotal OBJECT-TYPE
     SYNTAX Counter64
     MAX-ACCESS  read-only
     STATUS  current
     DESCRIPTION
         "No. of total unified traffic events that successfully generated."
     ::= {trafficEventsVirtServcStatsEntry 34}

virtUnifiedSucessPerSec OBJECT-TYPE
     SYNTAX Counter32
     MAX-ACCESS  read-only
     STATUS  current
     DESCRIPTION
         "No. of unified traffic events per second that successfully generated."
     ::= {trafficEventsVirtServcStatsEntry 35}

virtUnifiedFailTotal OBJECT-TYPE
     SYNTAX Counter64
     MAX-ACCESS  read-only
     STATUS  current
     DESCRIPTION
         "No. of total unified traffic events that failed to be generated."
     ::= {trafficEventsVirtServcStatsEntry 36}

virtUnifiedFailPerSec OBJECT-TYPE
     SYNTAX Counter32
     MAX-ACCESS  read-only
     STATUS  current
     DESCRIPTION
         "No. of unified traffic events per second that failed to be generated."
     ::= {trafficEventsVirtServcStatsEntry 37}

virtNormalUnifiedSucessTotal OBJECT-TYPE
     SYNTAX Counter64
     MAX-ACCESS  read-only
     STATUS  current
     DESCRIPTION
         "No. of total normal unified traffic events that successfully generated."
     ::= {trafficEventsVirtServcStatsEntry 38}

virtNormalUnifiedSucessTotalPercentage OBJECT-TYPE
     SYNTAX INTEGER (0..100)
     MAX-ACCESS  read-only
     STATUS  current
     DESCRIPTION
         "Percentage of total normal unified traffic events that successfully generated based on the defined threshold."
     ::= {trafficEventsVirtServcStatsEntry 39}

virtNormalUnifiedSucessPerSec OBJECT-TYPE
     SYNTAX Counter32
     MAX-ACCESS  read-only
     STATUS  current
     DESCRIPTION
         "No. of normal unified traffic events per second that successfully generated."
     ::= {trafficEventsVirtServcStatsEntry 40}

virtNormalUnifiedSucessPerSecPercentage OBJECT-TYPE
     SYNTAX INTEGER (0..100)
     MAX-ACCESS  read-only
     STATUS  current
     DESCRIPTION
         "Percentage of normal unified traffic events per second that successfully generated based on the defined threshold."
     ::= {trafficEventsVirtServcStatsEntry 41}

virtExceptionUnifiedSucessTotal OBJECT-TYPE
     SYNTAX Counter64
     MAX-ACCESS  read-only
     STATUS  current
     DESCRIPTION
         "No. of Exception unified traffic events that successfully generated."
     ::= {trafficEventsVirtServcStatsEntry 42}

virtExceptionUnifiedSucessTotalPercentage OBJECT-TYPE
     SYNTAX INTEGER (0..100)
     MAX-ACCESS  read-only
     STATUS  current
     DESCRIPTION
         "Percentage of Exception unified traffic events that successfully generated based on the defined threshold."
     ::= {trafficEventsVirtServcStatsEntry 43}

virtExceptionUnifiedSucessPerSec OBJECT-TYPE
     SYNTAX Counter32
     MAX-ACCESS  read-only
     STATUS  current
     DESCRIPTION
         "No. of Exception unified traffic events per second that successfully generated."
     ::= {trafficEventsVirtServcStatsEntry 44}

virtExceptionUnifiedSucessPerSecPercentage OBJECT-TYPE
     SYNTAX INTEGER (0..100)
     MAX-ACCESS  read-only
     STATUS  current
     DESCRIPTION
         "Percentage of Exception unified traffic events per second that successfully generated based on the defined threshold."
     ::= {trafficEventsVirtServcStatsEntry 45}

-- traffic Events Summary

httpReqSuccessPerSec OBJECT-TYPE
   SYNTAX Counter32
   MAX-ACCESS  read-only
   STATUS  current
   DESCRIPTION
       "No of Http Requests sent as traffic events per second.
        Note:This mib is not supported for VX instance of Virtualization."
   ::= {trafficEventSummaryStats 1}

httpReqSuccessTotal OBJECT-TYPE
   SYNTAX Counter64
   MAX-ACCESS  read-only
   STATUS  current
   DESCRIPTION
       "No of Http Requests sent successfully as traffic events in total.
        Note:This mib is not supported for VX instance of Virtualization."
   ::= {trafficEventSummaryStats 2}

httpRespSuccessPerSec OBJECT-TYPE
   SYNTAX Counter32
   MAX-ACCESS  read-only
   STATUS  current
   DESCRIPTION
       "No of Http responses sent as traffic events per second.
        Note:This mib is not supported for VX instance of Virtualization."
   ::= {trafficEventSummaryStats 3}

httpRespSuccessTotal OBJECT-TYPE
   SYNTAX Counter64
   MAX-ACCESS  read-only
   STATUS  current
   DESCRIPTION
       "No of Http responses sent successfully as traffic events in total.
        Note:This mib is not supported for VX instance of Virtualization."
   ::= {trafficEventSummaryStats 4}

feSSLInfoSuccessPerSec OBJECT-TYPE
   SYNTAX Counter32
   MAX-ACCESS  read-only
   STATUS  current
   DESCRIPTION
       "No of fessl sent successfully as traffice events per second.
        Note:This mib is not supported for VX instance of Virtualization."
   ::= {trafficEventSummaryStats 5}

feSSLInfoSuccessTotal OBJECT-TYPE
   SYNTAX Counter64
   MAX-ACCESS  read-only
   STATUS  current
   DESCRIPTION
       "No of fessl sent successfully as traffic events in total.
        Note:This mib is not supported for VX instance of Virtualization."
   ::= {trafficEventSummaryStats 6}

beSSLInfoSuccessPerSec OBJECT-TYPE
   SYNTAX Counter32
   MAX-ACCESS  read-only
   STATUS  current
   DESCRIPTION
       "No of bessl sent successfully as traffice events per second.
        Note:This mib is not supported for VX instance of Virtualization."
   ::= {trafficEventSummaryStats 7}

beSSLInfoSuccessTotal OBJECT-TYPE
   SYNTAX Counter64
   MAX-ACCESS  read-only
   STATUS  current
   DESCRIPTION
       "No of bessl sent successfully as traffic events in total.
        Note:This mib is not supported for VX instance of Virtualization."
   ::= {trafficEventSummaryStats 8}

hostNameBypassSuccessPerSec OBJECT-TYPE
   SYNTAX Counter32
   MAX-ACCESS  read-only
   STATUS  current
   DESCRIPTION
       "No of host names bypass sent successfully as traffice events per second.
        Note:This mib is not supported for VX instance of Virtualization."
   ::= {trafficEventSummaryStats 9}

hostNameBypassSuccessTotal OBJECT-TYPE
   SYNTAX Counter64
   MAX-ACCESS  read-only
   STATUS  current
   DESCRIPTION
       "No of host names bypass sent successfully as traffic events in total.
        Note:This mib is not supported for VX instance of Virtualization."
   ::= {trafficEventSummaryStats 10}

httpReqFailPerSec OBJECT-TYPE
   SYNTAX Counter32
   MAX-ACCESS  read-only
   STATUS  current
   DESCRIPTION
       "No of Http requests failed to send as traffic events per second.
        Note:This mib is not supported for VX instance of Virtualization."
   ::= {trafficEventSummaryStats 11}

httpReqFailTotal OBJECT-TYPE
   SYNTAX Counter64
   MAX-ACCESS  read-only
   STATUS  current
   DESCRIPTION
       "No of Http requests failed to send as traffic events in total.
        Note:This mib is not supported for VX instance of Virtualization."
   ::= {trafficEventSummaryStats 12}

httpRespFailPerSec OBJECT-TYPE
   SYNTAX Counter32
   MAX-ACCESS  read-only
   STATUS  current
   DESCRIPTION
       "No of Http responses failed to send as traffic events per second.
        Note:This mib is not supported for VX instance of Virtualization."
   ::= {trafficEventSummaryStats 13}

httpRespFailTotal OBJECT-TYPE
   SYNTAX Counter64
   MAX-ACCESS  read-only
   STATUS  current
   DESCRIPTION
       "No of Http responses failed to send as traffic events in total.
        Note:This mib is not supported for VX instance of Virtualization."
   ::= {trafficEventSummaryStats 14}

feSSLInfoFailPerSec OBJECT-TYPE
   SYNTAX Counter32
   MAX-ACCESS  read-only
   STATUS  current
   DESCRIPTION
       "No of fessl failed to send as traffice events per second.
        Note:This mib is not supported for VX instance of Virtualization."
   ::= {trafficEventSummaryStats 15}

feSSLInfoFailTotal OBJECT-TYPE
   SYNTAX Counter64
   MAX-ACCESS  read-only
   STATUS  current
   DESCRIPTION
       "No of fessl failed to send as traffice events in total.
        Note:This mib is not supported for VX instance of Virtualization."
   ::= {trafficEventSummaryStats 16}

beSSLInfoFailPerSec OBJECT-TYPE
   SYNTAX Counter32
   MAX-ACCESS  read-only
   STATUS  current
   DESCRIPTION
       "No of bessl failed to send as traffice events per second.
        Note:This mib is not supported for VX instance of Virtualization."
   ::= {trafficEventSummaryStats 17}

beSSLInfoFailTotal OBJECT-TYPE
   SYNTAX Counter64
   MAX-ACCESS  read-only
   STATUS  current
   DESCRIPTION
       "No of bessl failed to send as traffice events in total.
        Note:This mib is not supported for VX instance of Virtualization."
   ::= {trafficEventSummaryStats 18}

hostNameBypassFailPerSec OBJECT-TYPE
   SYNTAX Counter32
   MAX-ACCESS  read-only
   STATUS  current
   DESCRIPTION
       "No of host name bypass failed to send as traffic events per second.
        Note:This mib is not supported for VX instance of Virtualization." 
   ::= {trafficEventSummaryStats 19}

hostNameBypassFailTotal OBJECT-TYPE
   SYNTAX Counter64
   MAX-ACCESS  read-only
   STATUS  current
   DESCRIPTION
       "No of host name bypass failed to send as traffic events in total.
        Note:This mib is not supported for VX instance of Virtualization."
   ::= {trafficEventSummaryStats 20}

eventsFieldMissingPerSec OBJECT-TYPE
   SYNTAX Counter32
   MAX-ACCESS  read-only
   STATUS  current
   DESCRIPTION
       "Event field missing failure per second.
        Note:This mib is not supported for VX instance of Virtualization."
   ::= {trafficEventSummaryStats 21}

eventsFieldMissingTotal OBJECT-TYPE
   SYNTAX Counter64
   MAX-ACCESS  read-only
   STATUS  current
   DESCRIPTION
       "Event field missing failure in total.
        Note:This mib is not supported for VX instance of Virtualization."
   ::= {trafficEventSummaryStats 22}

eventsAllocFailPerSec OBJECT-TYPE
   SYNTAX Counter32
   MAX-ACCESS  read-only
   STATUS  current
   DESCRIPTION
       "Event allocation failure per second.
        Note:This mib is not supported for VX instance of Virtualization."
   ::= {trafficEventSummaryStats 23}

eventsAllocFailTotal OBJECT-TYPE
   SYNTAX Counter64
   MAX-ACCESS  read-only
   STATUS  current
   DESCRIPTION
       "Event allocation failure in total.
        Note:This mib is not supported for VX instance of Virtualization."
   ::= {trafficEventSummaryStats 24}

eventsQueueFullPerSec OBJECT-TYPE
   SYNTAX Counter32
   MAX-ACCESS  read-only
   STATUS  current
   DESCRIPTION
       "Event queue full failure per second.
        Note:This mib is not supported for VX instance of Virtualization."
   ::= {trafficEventSummaryStats 25}

eventsQueueFullTotal OBJECT-TYPE
   SYNTAX Counter64
   MAX-ACCESS  read-only
   STATUS  current
   DESCRIPTION
       "Event queue full failure in total.
        Note:This mib is not supported for VX instance of Virtualization."
   ::= {trafficEventSummaryStats 26}

layer4ReqSuccessPerSec OBJECT-TYPE
   SYNTAX Counter32
   MAX-ACCESS  read-only
   STATUS current
   DESCRIPTION
       "No of layer4 requests sent successfully as traffic events per second.
        Note:This mib is not supported for VX instance of Virtualization."
   ::= {trafficEventSummaryStats 27}

layer4ReqSuccessTotal OBJECT-TYPE
   SYNTAX Counter64
   MAX-ACCESS  read-only
   STATUS  current
   DESCRIPTION
       "No of layer4 requests sent successfully as traffic events in total.
        Note:This mib is not supported for VX instance of Virtualization."
   ::= {trafficEventSummaryStats 28}

layer4ReqFailPerSec OBJECT-TYPE
   SYNTAX Counter32
   MAX-ACCESS  read-only
   STATUS current
   DESCRIPTION
       "No of layer4 requests failed to be sent as traffic events per second.
        Note:This mib is not supported for VX instance of Virtualization."
   ::= {trafficEventSummaryStats 29}

layer4ReqFailTotal OBJECT-TYPE
   SYNTAX Counter64
   MAX-ACCESS  read-only
   STATUS current
   DESCRIPTION
       "No of layer4 requests failed to be sent as traffic events in total.
        Note:This mib is not supported for VX instance of Virtualization."
   ::= {trafficEventSummaryStats 30}

unifiedSucessTotal OBJECT-TYPE
     SYNTAX Counter64
     MAX-ACCESS  read-only
     STATUS  current
     DESCRIPTION
         "No. of total unified traffic events that successfully generated.
          Note:This mib is not supported for VX instance of Virtualization."
     ::= {trafficEventSummaryStats 31}

unifiedSucessPerSec OBJECT-TYPE
     SYNTAX Counter32
     MAX-ACCESS  read-only
     STATUS  current
     DESCRIPTION
         "No. of unified traffic events per second that successfully generated.
          Note:This mib is not supported for VX instance of Virtualization."
     ::= {trafficEventSummaryStats 32}

unifiedFailTotal OBJECT-TYPE
     SYNTAX Counter64
     MAX-ACCESS  read-only
     STATUS  current
     DESCRIPTION
         "No. of total unified traffic events that failed to be generated.
          Note:This mib is not supported for VX instance of Virtualization."
     ::= {trafficEventSummaryStats 33}

unifiedFailPerSec OBJECT-TYPE
     SYNTAX Counter32
     MAX-ACCESS  read-only
     STATUS  current
     DESCRIPTION
         "No. of unified traffic events per second that failed to be generated.
          Note:This mib is not supported for VX instance of Virtualization."
     ::= {trafficEventSummaryStats 34}

normalUnifiedSucessTotal OBJECT-TYPE
     SYNTAX Counter64
     MAX-ACCESS  read-only
     STATUS  current
     DESCRIPTION
         "No. of total normal unified traffic events that successfully generated.
          Note:This mib is not supported for VX instance of Virtualization."
     ::= {trafficEventSummaryStats 35}

normalUnifiedSucessTotalPercentage OBJECT-TYPE
     SYNTAX INTEGER (0..100)
     MAX-ACCESS  read-only
     STATUS  current
     DESCRIPTION
         "Percentage of total normal unified traffic events that successfully generated based on the defined threshold.
          Note:This mib is not supported for VX instance of Virtualization."
     ::= {trafficEventSummaryStats 36}

normalUnifiedSucessPerSec OBJECT-TYPE
     SYNTAX Counter32
     MAX-ACCESS  read-only
     STATUS  current
     DESCRIPTION
         "No. of normal unified traffic events per second that successfully generated.
          Note:This mib is not supported for VX instance of Virtualization."
     ::= {trafficEventSummaryStats 37}

normalUnifiedSucessPerSecPercentage OBJECT-TYPE
     SYNTAX INTEGER (0..100)
     MAX-ACCESS  read-only
     STATUS  current
     DESCRIPTION
         "Percentage of normal unified traffic events per second that successfully generated based on the defined threshold.
          Note:This mib is not supported for VX instance of Virtualization."
     ::= {trafficEventSummaryStats 38}

exceptionUnifiedSucessTotal OBJECT-TYPE
     SYNTAX Counter64
     MAX-ACCESS  read-only
     STATUS  current
     DESCRIPTION
         "No. of Exception unified traffic events that successfully generated.
          Note:This mib is not supported for VX instance of Virtualization."
     ::= {trafficEventSummaryStats 39}

exceptionUnifiedSucessTotalPercentage OBJECT-TYPE
     SYNTAX INTEGER (0..100)
     MAX-ACCESS  read-only
     STATUS  current
     DESCRIPTION
         "Percentage of Exception unified traffic events that successfully generated based on the defined threshold.
          Note:This mib is not supported for VX instance of Virtualization."
     ::= {trafficEventSummaryStats 40}

exceptionUnifiedSucessPerSec OBJECT-TYPE
     SYNTAX Counter32
     MAX-ACCESS  read-only
     STATUS  current
     DESCRIPTION
         "No. of Exception unified traffic events per second that successfully generated.
          Note:This mib is not supported for VX instance of Virtualization."
     ::= {trafficEventSummaryStats 41}

exceptionUnifiedSucessPerSecPercentage OBJECT-TYPE
     SYNTAX INTEGER (0..100)
     MAX-ACCESS  read-only
     STATUS  current
     DESCRIPTION
         "Percentage of Exception unified traffic events per second that successfully generated based on the defined threshold.
          Note:This mib is not supported for VX instance of Virtualization."
     ::= {trafficEventSummaryStats 42}

-- Remote Logging configuration - START
slbCurRemoteLoggingTable OBJECT-TYPE
    SYNTAX SEQUENCE OF SlbCurRemoteLoggingTableEntry
    MAX-ACCESS  not-accessible
    STATUS  current
    DESCRIPTION
        " Remote logging current configuration table.
         Note:This mib is not supported for VX instance of Virtualization."
    ::= { remoteLoggingCfg 1 }

slbCurRemoteLoggingTableEntry OBJECT-TYPE
    SYNTAX SlbCurRemoteLoggingTableEntry
    MAX-ACCESS  not-accessible
    STATUS  current
    DESCRIPTION
        "A row in the Remote logging Table.
         Note:This mib is not supported for VX instance of Virtualization."
    INDEX { slbCurRemoteLoggingID }
    ::= { slbCurRemoteLoggingTable 1 }

SlbCurRemoteLoggingTableEntry ::= SEQUENCE {
    slbCurRemoteLoggingID        DisplayString,
    slbCurRemoteLoggingProtocol  INTEGER,
    slbCurRemoteLoggingPort      INTEGER,
    slbCurRemoteLoggingGroup     DisplayString,
    slbCurRemoteLoggingSslPol    DisplayString,
    slbCurRemoteLoggingEnaDis    INTEGER
}

slbCurRemoteLoggingID OBJECT-TYPE
    SYNTAX DisplayString (SIZE(0..32))
    MAX-ACCESS  read-only
    STATUS  current
    DESCRIPTION
        "Remote logging Index."
    ::= { slbCurRemoteLoggingTableEntry 1 }

slbCurRemoteLoggingProtocol OBJECT-TYPE
    SYNTAX  INTEGER {
        udp(0),
        tcp(1),
        unsupported(2147483647)
    }
    MAX-ACCESS  read-only
    STATUS  current
    DESCRIPTION
        "Remote logging protocol type."
    ::= { slbCurRemoteLoggingTableEntry 2 }

slbCurRemoteLoggingPort OBJECT-TYPE
   SYNTAX  INTEGER (1..65535)
   MAX-ACCESS  read-only
   STATUS  current
   DESCRIPTION
       "Remote logging server port."
   ::= { slbCurRemoteLoggingTableEntry 3 }

slbCurRemoteLoggingGroup OBJECT-TYPE
   SYNTAX  DisplayString (SIZE(0..255))
   MAX-ACCESS  read-only
   STATUS  current
   DESCRIPTION
       "Remote logging group."
   ::= { slbCurRemoteLoggingTableEntry 4 }

slbCurRemoteLoggingSslPol OBJECT-TYPE
   SYNTAX  DisplayString (SIZE(0..32))
   MAX-ACCESS  read-only
   STATUS  current
   DESCRIPTION
       "Remote logging SSL policy."
   ::= { slbCurRemoteLoggingTableEntry 5 }

slbCurRemoteLoggingEnaDis OBJECT-TYPE
   SYNTAX  INTEGER {
       enabled(1),
       disabled(2),
       unsupported(2147483647)
   }
   MAX-ACCESS  read-only
   STATUS  current
   DESCRIPTION
       "Enable/Disable remote logging server."
   ::= { slbCurRemoteLoggingTableEntry 6 }

slbNewRemoteLoggingTable OBJECT-TYPE
    SYNTAX SEQUENCE OF SlbNewRemoteLoggingTableEntry
    MAX-ACCESS  not-accessible
    STATUS  current
    DESCRIPTION
        " Remote logging new configuration table.
         Note:This mib is not supported for VX instance of Virtualization."
    ::= { remoteLoggingCfg 2 }

slbNewRemoteLoggingTableEntry OBJECT-TYPE
    SYNTAX SlbNewRemoteLoggingTableEntry
    MAX-ACCESS  not-accessible
    STATUS  current
    DESCRIPTION
        "A row in the Remote logging Table.
         Note:This mib is not supported for VX instance of Virtualization."
    INDEX { slbNewRemoteLoggingID }
    ::= { slbNewRemoteLoggingTable 1 }

SlbNewRemoteLoggingTableEntry ::= SEQUENCE {
    slbNewRemoteLoggingID        DisplayString,
    slbNewRemoteLoggingProtocol  INTEGER,
    slbNewRemoteLoggingPort      INTEGER,
    slbNewRemoteLoggingGroup     DisplayString,
    slbNewRemoteLoggingSslPol    DisplayString,
    slbNewRemoteLoggingEnaDis    INTEGER,
    slbNewRemoteLoggingDel       INTEGER
}

slbNewRemoteLoggingID OBJECT-TYPE
    SYNTAX DisplayString (SIZE(0..32))
    MAX-ACCESS  read-only
    STATUS  current
    DESCRIPTION
        "Remote logging Index."
    ::= { slbNewRemoteLoggingTableEntry 1 }

slbNewRemoteLoggingProtocol OBJECT-TYPE
    SYNTAX  INTEGER {
        udp(0),
        tcp(1),
        unsupported(2147483647)
    }
    MAX-ACCESS  read-create
    STATUS  current
    DESCRIPTION
        "Remote logging protocol type."
    ::= { slbNewRemoteLoggingTableEntry 2 }

slbNewRemoteLoggingPort OBJECT-TYPE
   SYNTAX  INTEGER (1..65535)
   MAX-ACCESS  read-create
   STATUS  current
   DESCRIPTION
       "Remote logging server port."
   ::= { slbNewRemoteLoggingTableEntry 3 }

slbNewRemoteLoggingGroup OBJECT-TYPE
   SYNTAX  DisplayString (SIZE(0..255))
   MAX-ACCESS  read-create
   STATUS  current
   DESCRIPTION
       "Remote logging group."
   ::= { slbNewRemoteLoggingTableEntry 4 }

slbNewRemoteLoggingSslPol OBJECT-TYPE
   SYNTAX  DisplayString (SIZE(0..32))
   MAX-ACCESS  read-create
   STATUS  current
   DESCRIPTION
       "Remote logging SSL policy."
   ::= { slbNewRemoteLoggingTableEntry 5 }

slbNewRemoteLoggingEnaDis OBJECT-TYPE
   SYNTAX  INTEGER {
       enabled(1),
       disabled(2),
       unsupported(2147483647)
   }
   MAX-ACCESS  read-create
   STATUS  current
   DESCRIPTION
       "Enable/Disable remote logging server."
   ::= { slbNewRemoteLoggingTableEntry 6 }

slbNewRemoteLoggingDel OBJECT-TYPE
   SYNTAX  INTEGER {
       other(1),
       delete(2),
       unsupported(2147483647)
   }
   MAX-ACCESS  read-create
   STATUS  current
   DESCRIPTION
        "When set to the value of 2 (delete), the entire row is deleted.
         When read, other(1) is returned. Setting the value to anything
         other than 2(delete) has no effect on the state of the row."
   ::= { slbNewRemoteLoggingTableEntry 7 }

-- Remote Logging configuration - END

--Sync Peer Cluster Start.

cluster    OBJECT IDENTIFIER ::= { syncCfg 5 }

slbSyncClusterTableMaxSize OBJECT-TYPE
    SYNTAX  Integer32
    MAX-ACCESS  read-only
    STATUS  current
    DESCRIPTION
        "The maximum number of entries in SLB sync cluster peer table.
         Note:This mib is not supported for VX instance of Virtualization."
    ::= { cluster 1 }

slbCurSyncClusterState OBJECT-TYPE
    SYNTAX  INTEGER {
        enabled(2),
        disabled(3),
        unsupported(2147483647)
        }
    MAX-ACCESS  read-only
    STATUS  current
    DESCRIPTION
        "The global state of SLB sync cluster peer.
         Note:This mib is not supported for VX instance of Virtualization."
    ::= { cluster 2 }

slbNewSyncClusterState OBJECT-TYPE
    SYNTAX  INTEGER {
        enabled(2),
        disabled(3),
        unsupported(2147483647)
        }
    MAX-ACCESS  read-write
    STATUS  current
    DESCRIPTION
        "Set global state of SLB sync cluster peer.
         Note:This mib is not supported for VX instance of Virtualization."
    ::= { cluster 3 }


slbCurSyncClusterPeerInterval OBJECT-TYPE
    SYNTAX  INTEGER (100..600)
    MAX-ACCESS  read-only
    STATUS  current
    DESCRIPTION
        "Cluster sync peer keepalive interval between 100 to 600 seconds.
         Note:This mib is not supported for VX instance of Virtualization."
    ::= { cluster 4 }

slbNewSyncClusterPeerInterval OBJECT-TYPE
    SYNTAX  INTEGER (100..600)
    MAX-ACCESS  read-write
    STATUS  current
    DESCRIPTION
        "Set cluster sync peer keepalive interval between 100 to 600 seconds.
         Note:This mib is not supported for VX instance of Virtualization."
    ::= { cluster 5 }

slbCurCfgClusterPeerTable OBJECT-TYPE
    SYNTAX SEQUENCE OF SlbCurCfgClusterPeerEntry
    MAX-ACCESS not-accessible
    STATUS current
    DESCRIPTION
        "The sync cluster peer wwitch configuration in the current_config.
         Note:This mib is not supported for VX instance of Virtualization."
    ::= { cluster 6 }

slbCurCfgClusterPeerEntry OBJECT-TYPE
    SYNTAX SlbCurCfgClusterPeerEntry
    MAX-ACCESS not-accessible
    STATUS current
    DESCRIPTION
        "Information about Cluster Sync Peer Switch configuration.
         Note:This mib is not supported for VX instance of Virtualization."
    INDEX { slbCurCfgClusterPeerIndex }
    ::= { slbCurCfgClusterPeerTable 1 }

SlbCurCfgClusterPeerEntry ::= SEQUENCE {
    slbCurCfgClusterPeerIndex          Integer32,
    slbCurCfgClusterPeerIpAddr         IpAddress,
    slbCurCfgClusterPeerIpVer          INTEGER,
    slbCurCfgClusterPeerIpv6Addr       DisplayString
    }

slbCurCfgClusterPeerIndex OBJECT-TYPE
    SYNTAX Integer32
    MAX-ACCESS read-only
    STATUS current
    DESCRIPTION
        "The index for cluster sync peer switchs."
    ::= { slbCurCfgClusterPeerEntry 1 }

slbCurCfgClusterPeerIpAddr OBJECT-TYPE
    SYNTAX IpAddress
    MAX-ACCESS read-only
    STATUS current
    DESCRIPTION
        "The IP address of the cluster sync peer switch."
    ::= { slbCurCfgClusterPeerEntry 2 }

slbCurCfgClusterPeerIpVer OBJECT-TYPE
    SYNTAX  INTEGER{
        ipv4(1),
        ipv6(2),
        unsupported(2147483647)
    }
    MAX-ACCESS  read-only
    STATUS  current
    DESCRIPTION
        "The type of cluster sync peer IP address."
    ::= { slbCurCfgClusterPeerEntry 3 }

slbCurCfgClusterPeerIpv6Addr OBJECT-TYPE
    SYNTAX DisplayString (SIZE(0..40))
    MAX-ACCESS read-only
    STATUS current
    DESCRIPTION
        "The IPv6 address of the cluster Peer switch.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { slbCurCfgClusterPeerEntry 4 }

slbNewCfgClusterPeerTable OBJECT-TYPE
    SYNTAX SEQUENCE OF SlbNewCfgClusterPeerEntry
    MAX-ACCESS not-accessible
    STATUS current
    DESCRIPTION
        "The table of sync cluster peer switch configuration in the current_config.
         Note:This mib is not supported for VX instance of Virtualization."
    ::= { cluster 7 }

slbNewCfgClusterPeerEntry OBJECT-TYPE
    SYNTAX SlbNewCfgClusterPeerEntry
    MAX-ACCESS not-accessible
    STATUS current
    DESCRIPTION
        "Information about Cluster Sync Peer Switch configuration.
         Note:This mib is not supported for VX instance of Virtualization."
    INDEX { slbNewCfgClusterPeerIndex }
    ::= { slbNewCfgClusterPeerTable 1 }

SlbNewCfgClusterPeerEntry ::= SEQUENCE {
    slbNewCfgClusterPeerIndex          Integer32,
    slbNewCfgClusterPeerIpAddr         IpAddress,
    slbNewCfgClusterPeerIpVer          INTEGER,
    slbNewCfgClusterPeerIpv6Addr       DisplayString,
    slbNewCfgClusterPeerDelete         INTEGER
    }

slbNewCfgClusterPeerIndex OBJECT-TYPE
    SYNTAX Integer32
    MAX-ACCESS read-only
    STATUS current
    DESCRIPTION
        "The index for cluster sync peer switchs."
    ::= { slbNewCfgClusterPeerEntry 1 }

slbNewCfgClusterPeerIpAddr OBJECT-TYPE
    SYNTAX IpAddress
    MAX-ACCESS read-create
    STATUS current
    DESCRIPTION
        "The IP address of the cluster sync peer switch."
    ::= { slbNewCfgClusterPeerEntry 2 }

slbNewCfgClusterPeerIpVer OBJECT-TYPE
    SYNTAX  INTEGER{
        ipv4(1),
        ipv6(2),
        unsupported(2147483647)
    }
    MAX-ACCESS read-create
    STATUS  current
    DESCRIPTION
        "The type of cluster peer IP address version."
    ::= { slbNewCfgClusterPeerEntry 3 }

slbNewCfgClusterPeerIpv6Addr OBJECT-TYPE
    SYNTAX DisplayString (SIZE(0..40))
    MAX-ACCESS read-create
    STATUS current
    DESCRIPTION
        "The IPv6 address of the cluster Peer switch.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { slbNewCfgClusterPeerEntry 4 }

slbNewCfgClusterPeerDelete OBJECT-TYPE
    SYNTAX INTEGER {
        other(1),
        delete(2),
        unsupported(2147483647)
        }
    MAX-ACCESS  read-create
    STATUS  current
    DESCRIPTION
        "By setting the value to delete(2), the entire row is
         deleted."
    ::= { slbNewCfgClusterPeerEntry 5 }

--Sync Peer Cluster End

-- DNS NS Start
slbCurCfgDnsNsGroupTable OBJECT-TYPE
    SYNTAX  SEQUENCE OF SlbCurCfgDnsNsGroupEntry
    MAX-ACCESS  not-accessible
    STATUS  current
    DESCRIPTION
        "The table of DNS NS groups.
         Note:This mib is not supported on VX instance of Virtualization."
    ::= { gslbDnsNsCfg 1 }

slbCurCfgDnsNsGroupEntry OBJECT-TYPE
    SYNTAX  SlbCurCfgDnsNsGroupEntry
    MAX-ACCESS  not-accessible
    STATUS  current
    DESCRIPTION
        "A row in the DNS NS group table."
    INDEX   { slbCurCfgDnsNsGroupId }
    ::= { slbCurCfgDnsNsGroupTable 1 }

SlbCurCfgDnsNsGroupEntry ::= SEQUENCE {
    slbCurCfgDnsNsGroupId           DisplayString,
    slbCurCfgDnsNsGroupTtl          INTEGER
}

slbCurCfgDnsNsGroupId OBJECT-TYPE
    SYNTAX  DisplayString (SIZE(1..128))
    MAX-ACCESS  read-only
    STATUS  current
    DESCRIPTION
        "The DNS NS group id as index."
    ::= { slbCurCfgDnsNsGroupEntry 1 }

slbCurCfgDnsNsGroupTtl OBJECT-TYPE
    SYNTAX  INTEGER (1..86400)
    MAX-ACCESS  read-only
    STATUS  current
    DESCRIPTION
        "The DNS NS group TTL value."
    ::= { slbCurCfgDnsNsGroupEntry 2 }

slbNewCfgDnsNsGroupTable OBJECT-TYPE
    SYNTAX  SEQUENCE OF SlbNewCfgDnsNsGroupEntry
    MAX-ACCESS  not-accessible
    STATUS  current
    DESCRIPTION
        "The table of DNS NS groups.
         Note:This mib is not supported on VX instance of Virtualization."
    ::= { gslbDnsNsCfg 2 }

slbNewCfgDnsNsGroupEntry OBJECT-TYPE
    SYNTAX  SlbNewCfgDnsNsGroupEntry
    MAX-ACCESS  not-accessible
    STATUS  current
    DESCRIPTION
        "A row in the DNS NS group table."
    INDEX   { slbNewCfgDnsNsGroupId }
    ::= { slbNewCfgDnsNsGroupTable 1 }

SlbNewCfgDnsNsGroupEntry ::= SEQUENCE {
    slbNewCfgDnsNsGroupId           DisplayString,
    slbNewCfgDnsNsGroupTtl          INTEGER,
    slbNewCfgDnsNsGroupDelete       INTEGER
}

slbNewCfgDnsNsGroupId OBJECT-TYPE
    SYNTAX  DisplayString (SIZE(1..128))
    MAX-ACCESS  read-create
    STATUS  current
    DESCRIPTION
        "The DNS NS group id as index."
    ::= { slbNewCfgDnsNsGroupEntry 2 }

slbNewCfgDnsNsGroupTtl OBJECT-TYPE
    SYNTAX  INTEGER (1..86400)
    MAX-ACCESS  read-create
    STATUS  current
    DESCRIPTION
        "The DNS NS group TTL value."
    ::= { slbNewCfgDnsNsGroupEntry 3 }

slbNewCfgDnsNsGroupDelete OBJECT-TYPE
    SYNTAX  INTEGER {
        other(1),
        delete(2)
    }
    MAX-ACCESS  read-create
    STATUS  current
    DESCRIPTION
        "When set to the value of 2(delete), the entire DNS NS group is deleted.
        When read, other(1) is returned. Setting the value to anything
        other than 2(delete) has no effect on the state of the row."
    ::= { slbNewCfgDnsNsGroupEntry 4 }

slbCurCfgDnsNsRecordTable OBJECT-TYPE
    SYNTAX  SEQUENCE OF SlbCurCfgDnsNsRecordEntry
    MAX-ACCESS  not-accessible
    STATUS  current
    DESCRIPTION
        "The table of DNS NS records for each NS group.
         Note:This mib is not supported on VX instance of Virtualization."
    ::= { gslbDnsNsCfg 3 }

slbCurCfgDnsNsRecordEntry OBJECT-TYPE
    SYNTAX  SlbCurCfgDnsNsRecordEntry
    MAX-ACCESS  not-accessible
    STATUS  current
    DESCRIPTION
        "A row in the DNS NS records table per NS group."
    INDEX   { slbCurCfgDnsNsRecordGroupId, slbCurCfgDnsNsRecordString }
    ::= { slbCurCfgDnsNsRecordTable 1 }

SlbCurCfgDnsNsRecordEntry ::= SEQUENCE {
    slbCurCfgDnsNsRecordGroupId         DisplayString,
    slbCurCfgDnsNsRecordString          DisplayString,
    slbCurCfgDnsNsRecordIpv4Addr        IpAddress,
    slbCurCfgDnsNsRecordIpv6Addr        DisplayString
}

slbCurCfgDnsNsRecordGroupId OBJECT-TYPE
    SYNTAX  DisplayString (SIZE(1..128))
    MAX-ACCESS  read-only
    STATUS  current
    DESCRIPTION
        "The DNS NS group id as index. Each group can have upto 10 NS records."
    ::= { slbCurCfgDnsNsRecordEntry 1 }

slbCurCfgDnsNsRecordString OBJECT-TYPE
    SYNTAX   DisplayString (SIZE (0..253))
    MAX-ACCESS  read-only
    STATUS  current
    DESCRIPTION
        "Defines the NS record string in fqdn format."
    ::= { slbCurCfgDnsNsRecordEntry 2 }

slbCurCfgDnsNsRecordIpv4Addr OBJECT-TYPE
    SYNTAX  IpAddress
    MAX-ACCESS  read-only
    STATUS  current
    DESCRIPTION
        "Defines the IPv4 glue address for this NS record entry. This is optional.
         Returns 0 when not set."
    ::= { slbCurCfgDnsNsRecordEntry 3 }

slbCurCfgDnsNsRecordIpv6Addr OBJECT-TYPE
    SYNTAX  DisplayString (SIZE(0..40))
    MAX-ACCESS  read-only
    STATUS  current
    DESCRIPTION
        "Defines the IPv6 glue address for this NS record entry. This is optional.
         Returns 0 when not set."
    ::= { slbCurCfgDnsNsRecordEntry 4 }

slbNewCfgDnsNsRecordTable OBJECT-TYPE
    SYNTAX  SEQUENCE OF SlbNewCfgDnsNsRecordEntry
    MAX-ACCESS  not-accessible
    STATUS  current
    DESCRIPTION
        "The table of DNS NS records for each NS group.
         Note:This mib is not supported on VX instance of Virtualization."
    ::= { gslbDnsNsCfg 4 }

slbNewCfgDnsNsRecordEntry OBJECT-TYPE
    SYNTAX  SlbNewCfgDnsNsRecordEntry
    MAX-ACCESS  not-accessible
    STATUS  current
    DESCRIPTION
        "A row in the NS records table per NS group."
    INDEX   { slbNewCfgDnsNsRecordGroupId, slbNewCfgDnsNsRecordString }
    ::= { slbNewCfgDnsNsRecordTable 1 }

SlbNewCfgDnsNsRecordEntry ::= SEQUENCE {
    slbNewCfgDnsNsRecordGroupId         DisplayString,
    slbNewCfgDnsNsRecordString          DisplayString,
    slbNewCfgDnsNsRecordIpv4Addr        IpAddress,
    slbNewCfgDnsNsRecordIpv6Addr        DisplayString,
    slbNewCfgDnsNsRecordDelete          INTEGER
}

slbNewCfgDnsNsRecordGroupId OBJECT-TYPE
    SYNTAX  DisplayString (SIZE(1..128))
    MAX-ACCESS  read-create
    STATUS  current
    DESCRIPTION
        "The DNS NS group id as index. Each group can have upto 10 records."
    ::= { slbNewCfgDnsNsRecordEntry 1 }

slbNewCfgDnsNsRecordString OBJECT-TYPE
    SYNTAX   DisplayString (SIZE (0..253))
    MAX-ACCESS  read-create
    STATUS  current
    DESCRIPTION
        "Defines the NS record string in fqdn format."
    ::= { slbNewCfgDnsNsRecordEntry 2 }

slbNewCfgDnsNsRecordIpv4Addr OBJECT-TYPE
    SYNTAX  IpAddress
    MAX-ACCESS  read-create
    STATUS  current
    DESCRIPTION
        "Defines the IPv4 glue address for this NS record entry. This is optional.
         Returns 0 when not set."
    ::= { slbNewCfgDnsNsRecordEntry 3 }

slbNewCfgDnsNsRecordIpv6Addr OBJECT-TYPE
    SYNTAX  DisplayString (SIZE(0..40))
    MAX-ACCESS  read-create
    STATUS  current
    DESCRIPTION
        "Defines the IPv6 glue address for this NS record entry. This is optional.
         Returns 0 when not set."
    ::= { slbNewCfgDnsNsRecordEntry 4 }

slbNewCfgDnsNsRecordDelete OBJECT-TYPE
    SYNTAX  INTEGER {
        other(1),
        delete(2)
    }
    MAX-ACCESS  read-create
    STATUS  current
    DESCRIPTION
        "When set to the value of 2(delete), the entire NS record is deleted.
        When read, other(1) is returned. Setting the value to anything
        other than 2(delete) has no effect on the state of the row."
    ::= { slbNewCfgDnsNsRecordEntry 5 }

-- DNS NS End

END
