MIMOSA-MIB-TC DEFINITIONS ::= BEGIN

--  Copyright (C) 2017, Mimosa Networks, Inc. All Rights Reserved.
--
--  Mimosa Networks MIB
--  Revision: 1.00
--  Date: February 15, 2017
--
--  Mimosa Networks, Inc.
--  469 El Camino Real, Suite 100
--  Santa Clara, CA 95050
--  support@mimosa.co
--
--  This MIB defines the base MIB specification for Mimosa Network's
--  products.
--
--  Mimosa reserves the right to make changes to this MIB specification as
--  well as other information related to this specification without prior
--  notice.  The user of this specification should consult Mimosa Networks,
--  to determine if any such changes have been made.
--
--  Current MIBs are available from Mimosa Networks at the following URLs:
--
--      http://help.mimosa.co
--
--  In no event shall Mimosa Networks, Inc. be liable for any indirect,
--  consequential, special or incidental damages whatsoever (including
--  but not limited to lost profits or lost revenue) arising out of or
--  related to this specification or the information contained in it.
--  This non-liability extends to even if Mimosa Networks Inc. has been
--  advised of, known, or should have known, the potential for such damages.
--  Mimosa Networks, Inc. hereby grants end-users, and other parties a                                                                                         
--  a non-exclusive license to use this MIB specification in order to
--  manage products of Mimosa Networks, Inc.

IMPORTS
    MODULE-IDENTITY, Integer32              FROM SNMPv2-SMI
    TEXTUAL-CONVENTION                      FROM SNMPv2-TC
    mimosa                                  FROM MIMOSA-NETWORKS-BASE-MIB;

mimosaMibTC     MODULE-IDENTITY
    LAST-UPDATED    "201702150000Z"
    ORGANIZATION "Mimosa Networks
    			  www.mimosa.co"
    CONTACT-INFO
    	"postal:
    	Mimosa Networks, Inc.
		469 El Camino Real, Suite 100
		Santa Clara, CA 95050
        email: support@mimosa.co"
    DESCRIPTION
		"Mimosa device MIB definitions"
	REVISION	"201702150000Z"
    DESCRIPTION
		"First Revision of Textual Conventions defined for MIMOSA-MIB modules."
    ::= { mimosa 3 }

-- *****************************************************************
-- ***                   Mimosa Textual Conventions              ***
-- *****************************************************************

DecimalOne ::= TEXTUAL-CONVENTION
    DISPLAY-HINT "d-1"
    STATUS       current
    DESCRIPTION  "Fixed point, one decimal"
    SYNTAX       Integer32

DecimalTwo ::= TEXTUAL-CONVENTION
    DISPLAY-HINT "d-2"
    STATUS       current
    DESCRIPTION  "Fixed point, two decimals"
    SYNTAX       Integer32

DecimalFive ::= TEXTUAL-CONVENTION
    DISPLAY-HINT "d-5"
    STATUS       current
    DESCRIPTION  "Fixed point, five decimals"
    SYNTAX       Integer32

Mimosa5GHzFrequency ::= TEXTUAL-CONVENTION
    STATUS       current
    DESCRIPTION  "Represents the frequency in the range of 4800 to 6200"
    SYNTAX       Integer32 (4800..6200)

Mimosa5GHzChannelNumber ::= TEXTUAL-CONVENTION
    STATUS       current
    DESCRIPTION  "Reprensents the channel Wifi ChannelWidth"
    SYNTAX       Integer32

END
