ANUE-MIB DEFINITIONS ::= BEGIN

IMPORTS
        enterprises,
        MODULE-IDENTITY,
        OBJECT-TYPE,
        NOTIFICATION-TYPE,
        Counter32,
        Counter64,
        Gauge32,
        Integer32,
        TimeTicks
                FROM SNMPv2-SMI
        DisplayString,
        TimeStamp,
        DateAndTime,
        TruthValue,
        TEXTUAL-CONVENTION
                FROM SNMPv2-TC
        SnmpUDPAddress,
        snmpUDPDomain
                FROM SNMPv2-TM
        InterfaceIndex,
        InterfaceIndexOrZero,
        ifIndex,
        ifEntry,
        ifTable
                FROM IF-MIB
        InetAddress,
        InetAddressType
                FROM INET-ADDRESS-MIB
        SnmpSecurityModel
                FROM SNMP-FRAMEWORK-MIB
        CounterBasedGauge64,
        ZeroBasedCounter64,
        hcnumTC
                FROM HCNUM-TC
        OBJECT-GROUP,
        NOTIFICATION-GROUP,
        MODULE-COMPLIANCE
                FROM SNMPv2-CONF;

anueMIB MODULE-IDENTITY
        LAST-UPDATED "201506121700Z"    -- Jun 12, 2015 5:00:00 PM GMT
        ORGANIZATION "Anue Systems"
        CONTACT-INFO
           "support@ixiacom.com"
        DESCRIPTION
           "This Anue proprietary MIB provides access to
            Network Tool Optimizer (NTO) configuration and statistics
            which cannot be modeled in a straight forward manner using
            standard MIBs.  The objects in this MIB include filter
            configuration, history, connections, and statistics.  The
            Anue proprietary MIB also includes extended interface
            information and authentication objects/traps.

            All statistics are provided in both High Capacity (HC) 64-bit
            tables and in 32-bit tables to accommodate backward
            compatibility with SNMPv1."

        REVISION "201506121700Z"    -- Jun 12, 2015 5:00:00 PM GMT
        DESCRIPTION
           "Merged 5200, 7300, and GSC again, adding room for expansion."

        REVISION "201501291700Z"    -- Jan 29, 2015 5:00:00 PM GMT
        DESCRIPTION
           "Added support for L2GRE and ERSPAN stripping."

        REVISION "201501271700Z"    -- Jan 27, 2015 5:00:00 PM GMT
        DESCRIPTION
           "Added support for simplex/loopback ports, PBCU/DBCM filters."

        REVISION "201412171700Z"    -- Dec 17, 2014 5:00:00 PM GMT
        DESCRIPTION
           "Added support for VXLAN stripping."

        REVISION "201406261700Z"    -- Jun 26, 2014 5:00:00 PM GMT
        DESCRIPTION
           "Merged 5200 and 7300 series"

        REVISION "201403131700Z"    -- Mar 13, 2014 5:00:00 PM GMT
        DESCRIPTION
           "Added support for Capture statistics."

        REVISION "201403111700Z"    -- Mar 11, 2014 5:00:00 PM GMT
        DESCRIPTION
           "Added support for Capture properties."

        REVISION "201403051700Z"    -- Mar 05, 2014 5:00:00 PM GMT
        DESCRIPTION
           "Merged 5200 and 7300 series and GSC."

        REVISION "201309051700Z"    -- Sep 05, 2013 5:00:00 PM GMT
        DESCRIPTION
           "Added support for test notification."

        REVISION "201403041700Z"    -- Mar 04, 2014 5:00:00 PM GMT
        DESCRIPTION
           "Added support for NTO 7300."

        REVISION "201207301700Z"    -- Jul 30, 2012 5:00:00 PM GMT
        DESCRIPTION
           "Added support for VNTag stripping."

        REVISION "201206131700Z"    -- Jun 13, 2012 5:00:00 PM GMT
        DESCRIPTION
           "Added preliminary support for VLAN stripping."

        REVISION "201203271700Z"    -- Mar 27, 2012 5:00:00 PM GMT
        DESCRIPTION
           "Added support for event monitor notification actions."

        REVISION "201202061700Z"    -- Feb 6, 2012 5:00:00 PM
        DESCRIPTION
           "Added support for AFM features, release 3.5"

        REVISION "201109201700Z"    -- Sep 20, 2011 5:00:00 PM
        DESCRIPTION
           "Minor updates to eliminate platform dependent descriptions.
            MIB object definitions did not change."

        REVISION "201010131908Z"    -- Oct 13, 2010 7:08:00 PM
        DESCRIPTION
           "Initial version."
        -- 1.3.6.1.4.1.32620
        ::= { enterprises 32620 }


--
-- Textual conventions used in this MIB
--

AnueStageType ::= TEXTUAL-CONVENTION
    STATUS  current
    DESCRIPTION
        "Each bit enumeration identifies a stage in a filter pipeline.
        Some - but not all - of these enumerations correspond to advanced
        capabilities. The numerical values of these enumerations do not
        imply an operational order."
    SYNTAX BITS {
        anueStageTypeNPFilter(0),
        anueStageTypeTPFilter(1),
        anueStageTypeAfmDrop(2),
        anueStageTypeAfmStripGtp(3),
        anueStageTypeAfmStripMpls(4),
        anueStageTypeAfmDedup(5),
        anueStageTypeAfmTrim(6),
        anueStageTypeAfmBurstBuffer(7),
        anueStageTypeNPError(8),
        anueStageTypeStripVlan(9),
        anueStageTypeAfmStripVntag(10),
        anueStageTypeAfmTimestamping(11),
        anueStageTypeAfmStripTrailer(12),
        anueStageTypePortTagging(13),
        anueStageTypeLCInput(15),
        anueStageTypeLCOutput(16),
        anueStageTypeAfmGtpFd(17),
        anueStageTypeAfmStripFabricPath(18),
        anueStageTypeAfmStripVxlan(19),
        anueStageTypeAfmStripL2Gre(20),
        anueStageTypeAfmStripErspan(21),
        anueStageTypeAfmPacketLength(22),
        anueStageTypeAfmDataMasking(23),

    --  room for expansion between NTO and GSC  --
        anueStageTypeGscBufOverflow(32),
        anueStageTypeGscNetworkPorts(33),
        anueStageTypeGscSessionToolPorts(34)
        }

AnueFilterTypeDT ::= TEXTUAL-CONVENTION
    STATUS  current
    DESCRIPTION
        "Datatype (DT) describing NTO filters. Each integer
        enumeration identifies a filter type.  Some filters may be
        composed as a pipeline of multiple stages."
    SYNTAX  INTEGER {
        anueFilterTypeNetworkPort(1),
        anueFilterTypeToolPort(2),
        anueFilterTypeDynamic(3),
        anueFilterTypeNetworkPortGroup(4),
        anueFilterTypeToolPortGroup(5),
        anueFilterTypeLineCard(6),
        anueFilterTypeRecAfmResource(7),

    --  room for expansion between NTO and GSC  --
        anueFilterTypeGscNetworkPort(100),
        anueFilterTypeGscSessionToolPort(101),
        anueFilterTypeGscNetworkPortGroup(102),
        anueFilterTypeGscSessionToolPortGroup(103)
        }

AnueThresholdCrossing ::= TEXTUAL-CONVENTION
    STATUS      current
    DESCRIPTION
       "Defines a direction of threshold crossing for event monitors."
    SYNTAX  INTEGER {
        thresholdCrossingUpward(1),
        thresholdCrossingDownward(2)
        }

AnueNtoUnionMemberActionType ::= TEXTUAL-CONVENTION
    STATUS      current
    DESCRIPTION
       "Defines a union member action."
    SYNTAX  INTEGER {
        memberActionJoinSucceeded(1),
        memberActionJoinFailed(2),
        memberActionLeaveSucceeded(3),
        memberActionLeaveFailed(4),
        memberActionReconnected(5)
        }

AnueTimeSourceType ::= TEXTUAL-CONVENTION
    STATUS  current
    DESCRIPTION
        "Datatype describing the time source type that can be configured on the NTO.
        Can be one of Local, NTP Server, GPS or not available if timestamping is
        not supported by the NTO platform."
    SYNTAX  INTEGER {
        anueTimeSourceTypeLocal(1),
        anueTimeSourceTypeNTP(2),
        anueTimeSourceTypeGPS(3),
        anueTimeSourceTypeNA(4)
        }



-- Scalars and Tables
--

anueObjects OBJECT IDENTIFIER
    -- 1.3.6.1.4.1.32620.1
    ::= { anueMIB 1 }


anueNtoObjects OBJECT IDENTIFIER
    -- 1.3.6.1.4.1.32620.1.1
    ::= { anueObjects 1 }



-- anueNtoSystem
--

anueNtoSystem OBJECT IDENTIFIER
    -- 1.3.6.1.4.1.32620.1.1.1
    ::= { anueNtoObjects 1 }


-- anueNtoLastSnmpAuthnFailure
--
-- The anueNtoLastSnmpAuthnFailure object allows the user to query
-- the system for the last failed SNMP query attempt.  This object
-- contains enhanced information about the query attempt including
-- time, source ip address, message security model and user name.
-- The variables in this object are used in forming
-- anueSnmpAuthenticationFailure notification message.
-- This object exists regardless of whether either the standard
-- RFC 3418 snmpEnableAuthenTraps or the enhanced
-- anueSnmpAuthnFailureTrapEnable is TRUE.

anueNtoLastSnmpAuthnFailure OBJECT IDENTIFIER
    -- 1.3.6.1.4.1.32620.1.1.1.1
    ::= { anueNtoSystem 1 }

anueSnmpAuthnFailureTime OBJECT-TYPE
    SYNTAX  DateAndTime
    MAX-ACCESS read-only
    STATUS  current
    DESCRIPTION
       "The time of the most recent failed SNMP request.
        If there is no failed SNMP query since system
        initialization, this object is null."
    -- 1.3.6.1.4.1.32620.1.1.1.1.1
    ::= { anueNtoLastSnmpAuthnFailure 1 }

anueSnmpAuthnFailureUsername OBJECT-TYPE
    SYNTAX  DisplayString
    MAX-ACCESS read-only
    STATUS  current
    DESCRIPTION
        "The variable contains the username (SNMPV3) or
        communityString (SNMPV2 or SNMPV1) used by the
        last failed SNMP request. If there is no failed SNMP
        query since system initialization, this object is
        an empty string."
    -- 1.3.6.1.4.1.32620.1.1.1.1.2
    ::= { anueNtoLastSnmpAuthnFailure 2 }

anueSnmpAuthnFailureSrcIpType OBJECT-TYPE
    SYNTAX  InetAddressType
    MAX-ACCESS read-only
    STATUS  current
    DESCRIPTION
        "The variable contains the source ip address type (ipv4 or ipv6)
        of the last failed SNMP request.  The data type is defined
        in INET-ADDRESS-MIB (RFC 4001).
        If there is no failed SNMP query since the system initialization,
        this object is unknown(0)."
    -- 1.3.6.1.4.1.32620.1.1.1.1.3
    ::= { anueNtoLastSnmpAuthnFailure 3 }

anueSnmpAuthnFailureSrcIp OBJECT-TYPE
    SYNTAX  InetAddress
    MAX-ACCESS read-only
    STATUS  current
    DESCRIPTION
        "The variable contains the source ip address of the last
        failed SNMP request.  The data type is defined in
        INET-ADDRESS-MIB (RFC 4001).
        If there is no failed SNMP query since the system initialization,
        this object is an empty string."
    -- 1.3.6.1.4.1.32620.1.1.1.1.4
    ::= { anueNtoLastSnmpAuthnFailure 4 }

anueSnmpAuthnFailureSecModel OBJECT-TYPE
    SYNTAX  SnmpSecurityModel
    MAX-ACCESS read-only
    STATUS  current
    DESCRIPTION
        "The SNMP security model as received in the last
        improperly authenticated SNMP message.
        If there is no failed SNMP query since the system initialization,
        this object is any(0)."
    -- 1.3.6.1.4.1.32620.1.1.1.1.5
    ::= { anueNtoLastSnmpAuthnFailure 5 }


-- anueNtoLastClientLoginFailure
--

-- The anueNtoLastClientLoginFailure object allows a user to query the
-- last failed client login attempt.  This object contains time,
-- source ip address, and username of the last client login failure.
-- The variables in this object are used in forming anueClientLoginFailure
-- notification message.  This object exists regardless of the state of
-- anueClientLoginFailureTrapEnable.

anueNtoLastClientLoginFailure OBJECT IDENTIFIER
    -- 1.3.6.1.4.1.32620.1.1.1.2
    ::= { anueNtoSystem 2 }

anueClientLoginFailureTime OBJECT-TYPE
    SYNTAX  DateAndTime
    MAX-ACCESS read-only
    STATUS  current
    DESCRIPTION
        "The time of the most recent failed client login.
        If there is no failed client login since system initialization,
        this object is null."
    -- 1.3.6.1.4.1.32620.1.1.1.2.1
    ::= { anueNtoLastClientLoginFailure 1 }

anueClientLoginFailureId OBJECT-TYPE
    SYNTAX  DisplayString
    MAX-ACCESS read-only
    STATUS  current
    DESCRIPTION
        "The variable contains the user name of the last failed client login.
        If there is no failed client login since system initialization,
        this object is null."
    -- 1.3.6.1.4.1.32620.1.1.1.2.2
    ::= { anueNtoLastClientLoginFailure 2 }


anueClientLoginFailureSrcIpType OBJECT-TYPE
    SYNTAX  InetAddressType
    MAX-ACCESS read-only
    STATUS  current
    DESCRIPTION
        "The variable contains the source ip address type
        (ipv4 or ipv6) of the last failed client login.
        The data type is defined in INET-ADDRESS-MIB (RFC 4001).
        If there is no failed client login since system initialization,
        this object is unknown(0)."
    -- 1.3.6.1.4.1.32620.1.1.1.2.3
    ::= { anueNtoLastClientLoginFailure 3 }


anueClientLoginFailureSrcIp OBJECT-TYPE
    SYNTAX  InetAddress
    MAX-ACCESS read-only
    STATUS  current
    DESCRIPTION
        "The variable contains the source ip address of the last
        failed client login.  The data type is defined in
        INET-ADDRESS-MIB (RFC 4001).
        If there is no failed client login since system initialization,
        this object is an empty string."
    -- 1.3.6.1.4.1.32620.1.1.1.2.4
    ::= { anueNtoLastClientLoginFailure 4 }


anueClientLoginFailureReason OBJECT-TYPE
    SYNTAX  DisplayString
    MAX-ACCESS read-only
    STATUS  current
    DESCRIPTION
        "The variable explains the reason for the last failed client login.
        If there is no failed client login since system initialization,
        this object is an empty string."
    -- 1.3.6.1.4.1.32620.1.1.1.2.5
    ::= { anueNtoLastClientLoginFailure 5 }


anueSnmpAuthnFailureTrapEnable OBJECT-TYPE
    SYNTAX  TruthValue
    MAX-ACCESS read-only
    STATUS  current
    DESCRIPTION
       "NTO supports a global setting to enable/disable SNMP
        trap generation and also allows individual trap types
        to be enabled/disabled on a per trap recipient basis.
        Both settings must be enabled to permit a trap to be
        generated to a recipient.

        This MIB object contains the global setting of whether
        the SNMP agent is permitted to generate the Anue enhanced
        version of SNMP authentication failure notification.
        This object is enabled when an Anue client has
        SNMP trap generation globally enabled.

        The VACM MIB contains whether the Anue enhanced SNMP
        authentication failure notification has been enabled
        for a particular trap recipient.  Note that each trap
        recipient may be configured via an Anue client to
        receive either the RFC 3418 authenticationFailure
        notification or the enhanced anueSnmpAuthenticationFailure
        notification."
    -- 1.3.6.1.4.1.32620.1.1.1.3
    ::= { anueNtoSystem 3 }


anueClientLoginFailureTrapEnable OBJECT-TYPE
    SYNTAX  TruthValue
    MAX-ACCESS read-only
    STATUS  current
    DESCRIPTION
       "NTO supports a global setting to enable/disable SNMP
        trap generation and also allows individual trap types
        to be enabled/disabled on a per trap recipient basis.
        Both settings must be enabled to permit a trap to be
        generated to a recipient.

        This MIB object contains the global setting of whether
        the SNMP agent is permitted to generate a client login
        failure notification.  This object is enabled when an
        Anue client has SNMP trap generation globally enabled.

        The VACM MIB contains whether the Anue client login
        failure notification has been enabled for a particular
        trap recipient."
    -- 1.3.6.1.4.1.32620.1.1.1.4
    ::= { anueNtoSystem 4 }


anueLoginBanner OBJECT-TYPE
    SYNTAX  DisplayString
    MAX-ACCESS read-only
    STATUS  current
    DESCRIPTION
       "The text displayed when the user logs into the NTO."
    -- 1.3.6.1.4.1.32620.1.1.1.5
    ::= { anueNtoSystem 5 }


-- Timestamping related

anueTimestampingTimeSource OBJECT-TYPE
    SYNTAX  AnueTimeSourceType
    MAX-ACCESS read-only
    STATUS  current
    DESCRIPTION
        "Specifies the type of time source used by the timestamping afm feature."
    -- 1.3.6.1.4.1.32620.1.1.1.6
    ::= { anueNtoSystem 6 }


anueTimestampingStatus OBJECT-TYPE
    SYNTAX  DisplayString
    MAX-ACCESS read-only
    STATUS  current
    DESCRIPTION
       "Displays the status of the timestamping feature. Can have one of the
       following values :
       Not available    - if there are no AFM cards present
       Not in use       - AFM card present but timestamping is not enabled on any port
       NTP (status)     - where status describes the current state of the connection with the NTP Server
       Using NTP time   - currently using NTP timesource
       GPS (status)     - where status describes the current state of the GPS module
       Using GPS time   - currently using GPS timesource
       Using Local time - currently using the local system time."
    -- 1.3.6.1.4.1.32620.1.1.1.7
    ::= { anueNtoSystem 7 }


-- Custom Offset Filtering related

anueNtoCustomFilterSetConfig OBJECT IDENTIFIER
    -- 1.3.6.1.4.1.32620.1.1.1.8
    ::= { anueNtoSystem 8 }

anueCustomFieldSetEnableState OBJECT-TYPE
    SYNTAX  INTEGER {
        bothFieldSetsDisabled(1),
        fieldSet1Enabled(2),
        bothFieldSetsEnabledDiffFilters(3),
        bothFieldSetsEnabledSameFilters(4),
        notAvailable(5)
        }
    MAX-ACCESS read-only
    STATUS     current
    DESCRIPTION
       "The enabled state of the two field sets."
    -- 1.3.6.1.4.1.32620.1.1.1.8.1
    ::= { anueNtoCustomFilterSetConfig 1 }


-- custom field sets table

anueCustomFieldSetsTable OBJECT-TYPE
    SYNTAX  SEQUENCE OF AnueCustomFieldSetsEntry
    MAX-ACCESS not-accessible
    STATUS     current
    DESCRIPTION
        "Contains all the custom field sets."
    -- 1.3.6.1.4.1.32620.1.1.1.8.2
    ::= { anueNtoCustomFilterSetConfig 2 }

anueCustomFieldSetsEntry OBJECT-TYPE
    SYNTAX     AnueCustomFieldSetsEntry
    MAX-ACCESS not-accessible
    STATUS     current
    DESCRIPTION
       "An address mapping for a particular custom field."
    INDEX {
        anueFieldSetId }
    -- 1.3.6.1.4.1.32620.1.1.1.8.2.1
    ::= { anueCustomFieldSetsTable 1 }

AnueCustomFieldSetsEntry ::= SEQUENCE {
    anueFieldSetId                  Integer32,
    anueFieldSetAvailOuterHdrFlds   DisplayString,
    anueFieldSetIsAdditOuterHdrs    TruthValue }

anueFieldSetId OBJECT-TYPE
    SYNTAX  Integer32 (1..2147483647)
    MAX-ACCESS read-only
    STATUS  current
    DESCRIPTION
       "Indicates the id of the custom field set."
    -- 1.3.6.1.4.1.32620.1.1.1.8.2.1.1
    ::= { anueCustomFieldSetsEntry 1 }

anueFieldSetAvailOuterHdrFlds OBJECT-TYPE
    SYNTAX     DisplayString
    MAX-ACCESS read-only
    STATUS     current
    DESCRIPTION
       "Available outer header fields."
    -- 1.3.6.1.4.1.32620.1.1.1.8.2.1.2
    ::= { anueCustomFieldSetsEntry 2 }


anueFieldSetIsAdditOuterHdrs OBJECT-TYPE
    SYNTAX     TruthValue
    MAX-ACCESS read-only
    STATUS     current
    DESCRIPTION
       "Provide additional outer header fields capacity."
    -- 1.3.6.1.4.1.32620.1.1.1.8.2.1.3
    ::= { anueCustomFieldSetsEntry 3 }


-- custom fields table

anueCustomFieldsTable OBJECT-TYPE
    SYNTAX     SEQUENCE OF AnueCustomFieldsEntry
    MAX-ACCESS not-accessible
    STATUS     current
    DESCRIPTION
       "Contains all the custom fields defined on this custom field set."
    -- 1.3.6.1.4.1.32620.1.1.1.8.3
    ::= { anueNtoCustomFilterSetConfig 3 }

anueCustomFieldsEntry OBJECT-TYPE
    SYNTAX     AnueCustomFieldsEntry
    MAX-ACCESS not-accessible
    STATUS     current
    DESCRIPTION
       "An address mapping for a particular custom field."
    INDEX {
        anueFieldSetId,
        anueCustomFieldId }
    -- 1.3.6.1.4.1.32620.1.1.1.8.3.1
    ::= { anueCustomFieldsTable 1 }

AnueCustomFieldsEntry ::= SEQUENCE {
    anueCustomFieldId                       Integer32,
    anueCustomFieldPktType                  INTEGER,
    anueCustomFieldSize                     Integer32,
    anueCustomFieldName                     DisplayString,
    anueCustomFieldSpecificAttrList         DisplayString,
    anueCustomFieldConfirmFldsList          DisplayString }

anueCustomFieldId OBJECT-TYPE
    SYNTAX  Integer32 (1..2147483647)
    MAX-ACCESS read-only
    STATUS  current
    DESCRIPTION
       "Indicates the id of the custom field."
    -- 1.3.6.1.4.1.32620.1.1.1.8.3.1.1
    ::= { anueCustomFieldsEntry 1 }

anueCustomFieldPktType OBJECT-TYPE
    SYNTAX  INTEGER {
        raw(1),
        gtpU(2),
        gtpC(3),
        mpls(4)
    }
    MAX-ACCESS read-only
    STATUS  current
    DESCRIPTION
       "Packet Type"
    -- 1.3.6.1.4.1.32620.1.1.1.8.3.1.2
    ::= { anueCustomFieldsEntry 2 }

anueCustomFieldSize OBJECT-TYPE
    SYNTAX  Integer32
    MAX-ACCESS read-only
    STATUS  current
    DESCRIPTION
       "Indicates the size of the custom field in bytes."
    -- 1.3.6.1.4.1.32620.1.1.1.8.3.1.3
    ::= { anueCustomFieldsEntry 3 }

anueCustomFieldName OBJECT-TYPE
    SYNTAX  DisplayString
    MAX-ACCESS read-only
    STATUS  current
    DESCRIPTION
       "Indicates the name of the custom field."
    -- 1.3.6.1.4.1.32620.1.1.1.8.3.1.4
    ::= { anueCustomFieldsEntry 4 }

anueCustomFieldSpecificAttrList OBJECT-TYPE
    SYNTAX  DisplayString
    MAX-ACCESS read-only
    STATUS  current
    DESCRIPTION
       "Contains a comma separated list of key value pairs
        which represent attributes of specific packet types
        (MPLS, GTP_U, GTP_C and RAW)."
    -- 1.3.6.1.4.1.32620.1.1.1.8.3.1.5
    ::= { anueCustomFieldsEntry 5 }

anueCustomFieldConfirmFldsList OBJECT-TYPE
    SYNTAX  DisplayString
    MAX-ACCESS read-only
    STATUS  current
    DESCRIPTION
       "Contains a comma separated list of this field's confirmation fields
        in the format confirmation_field_type (size)."
    -- 1.3.6.1.4.1.32620.1.1.1.8.3.1.6
    ::= { anueCustomFieldsEntry 6 }



-- anueNtoIfExt
--

anueNtoIfExt OBJECT IDENTIFIER
    -- 1.3.6.1.4.1.32620.1.1.2
    ::= { anueNtoObjects 2 }


anueNtoIfExtTable OBJECT-TYPE
    SYNTAX  SEQUENCE OF AnueNtoIfExtEntry
    MAX-ACCESS not-accessible
    STATUS  current
    DESCRIPTION
       "A list of interface entries which extend the rows in ifTable.
        This table contains physical interfaces, whether the port
        is present or not. It also contains logical port groups and
        management ports."
    REFERENCE
       "RFC 2863 The Interfaces Group MIB."
    -- 1.3.6.1.4.1.32620.1.1.2.1
    ::= { anueNtoIfExt 1 }


anueNtoIfExtEntry OBJECT-TYPE
    SYNTAX  AnueNtoIfExtEntry
    MAX-ACCESS not-accessible
    STATUS  current
    DESCRIPTION
        "An entry containing additional management information
        about an interface on Anue NTO devices."
    INDEX {
        ifIndex
    }
    -- 1.3.6.1.4.1.32620.1.1.2.1.1
    ::= { anueNtoIfExtTable 1 }


AnueNtoIfExtEntry ::= SEQUENCE {
    anueIfIsLicensed       TruthValue,
    anueIfLicensedMaxSpeed Gauge32,
    anueIfMode             INTEGER,
    anueIfDesc             DisplayString,
    anueIfOnAfm            TruthValue,
    anueIfAdvCapabilities  AnueStageType }


anueIfIsLicensed OBJECT-TYPE
    SYNTAX  TruthValue
    MAX-ACCESS read-only
    STATUS  current
    DESCRIPTION
       "Indicates whether the physical interface is licensed or not.
        This object has a value of true (1) if a interface is licensed.
        The value is false (2) if the interface is not licensed.
        This object value is always true(1) for management ports
        and port groups"
    -- 1.3.6.1.4.1.32620.1.1.2.1.1.2
    ::= { anueNtoIfExtEntry 2 }


anueIfLicensedMaxSpeed OBJECT-TYPE
    SYNTAX  Gauge32
    MAX-ACCESS read-only
    STATUS  current
    DESCRIPTION
        "The licensed maximum line rate for this port.  For port groups,
        this is the sum of licensed maximum line rates of its member ports.
        Line rate is specified in units of 1,000,000 bits per second.
        The object value is 0 if the interface is not licensed."
    -- 1.3.6.1.4.1.32620.1.1.2.1.1.3
    ::= { anueNtoIfExtEntry 3 }


anueIfMode OBJECT-TYPE
    SYNTAX  INTEGER {
        anueIfModeUnknown(1),
        anueIfModeNetwork(2),
        anueIfModeTool(3),
        anueIfModeBidirectional(4),
        anueIfModeSimplex(5),
        anueIfModeLoopback(6)
        }
    MAX-ACCESS read-only
    STATUS  current
    DESCRIPTION
        "The interface mode identifies whether a port or port group
        is configured to be a network, tool, or bidirectional
        interface.  Ports that are members of a port group
        inherit the interface mode of their parent port group.
        Management ports have interface mode bidirectional.
        The object value is anueIfModeUnknown if the interface
        is not licensed."
    -- 1.3.6.1.4.1.32620.1.1.2.1.1.4
    ::= { anueNtoIfExtEntry 4 }

anueIfDesc OBJECT-TYPE
    SYNTAX  DisplayString
    MAX-ACCESS read-only
    STATUS  current
    DESCRIPTION
        "The interface description contains a system generated
        interface description prepended to the user entered
        textual description for ports and port groups.  The
        system generated description identifies whether the port
        is a Network port, Tool port, Bidirectional port, or
        Management port.  It also includes the port/port group's
        default name as described in anueFilterDefaultName.
        The object value for ports that are not physically present
        is 'Port # -- pluggable module is not present'.
        The object value for ports that are not licensed is
        'Port # -- not licensed."
    -- 1.3.6.1.4.1.32620.1.1.2.1.1.5
    ::= { anueNtoIfExtEntry 5 }

anueIfOnAfm OBJECT-TYPE
    SYNTAX  TruthValue
    MAX-ACCESS read-only
    STATUS  current
    DESCRIPTION
        "Indicates whether or not the port or port group physically
        resides on an Advanced Feature Module (AFM)."
    -- 1.3.6.1.4.1.32620.1.1.2.1.1.6
    ::= { anueNtoIfExtEntry 6 }

anueIfAdvCapabilities OBJECT-TYPE
    SYNTAX  AnueStageType
    MAX-ACCESS read-only
    STATUS  current
    DESCRIPTION
        "Identifies the packet processing features available on this port
        or port group, either in the standard filtering hardware or on an
        AFM.  This object reflects the capabilities present in the hardware
        itself, independent of how that hardware is currently configured.
        If no packet processing features are available, this object will
        return an octet string with all bit enumerations set to zero."
    -- 1.3.6.1.4.1.32620.1.1.2.1.1.7
    ::= { anueNtoIfExtEntry 7 }



-- anueNtoFilter
--

anueNtoFilter OBJECT IDENTIFIER
    -- 1.3.6.1.4.1.32620.1.1.3
    ::= { anueNtoObjects 3 }

anueFilterCollectionPeriod OBJECT-TYPE
    SYNTAX  Gauge32
    MAX-ACCESS read-only
    STATUS  current
    DESCRIPTION
        "The interval in seconds over which the filter statistics
        data is collected.  This is the actual statistics sampling period.
        On the 5200 platform users can change the collection period. On the
        7300 platform users can not change the collection period. The value (1 second)
        is defined within the NTO application. The statistics data in
        anueNtoFilterStatsCntRstTable, anueNtoFilterStatsCurTable,
        anueNtoFilterStatsPeakTable, anueNtoFilterStatsAvgTable,
        anueNtoFilterStatsCntRstHCTable, anueNtoFilterStatsCurHCTable,
        anueNtoFilterStatsPeakHCTable, and anueNtoFilterStatsAvgHCTable
        are all collected within the period of time defined in this object."
    -- 1.3.6.1.4.1.32620.1.1.3.1
    ::= { anueNtoFilter 1 }


-- anueNtoFilterDefTable
--

anueNtoFilterDefTable OBJECT-TYPE
    SYNTAX  SEQUENCE OF AnueNtoFilterDefEntry
    MAX-ACCESS not-accessible
    STATUS  current
    DESCRIPTION
        "The NTO filter definition table contains filter configuration
        properties.  NTO supports three types of filters:
        Network Port Filter, Dynamic Filter, and Tool Port filter.
        Network Port and Tool Port filters can either be associated
        with a physical interface or a logical port group.
        Logical port group filters contain 0 to 8 physical interfaces.
        The port group filter and each of its contained physical interfaces
        are considered to be port filters.  The contained port filters
        inherit the filter type, mode, criteria, and connections from
        their parent port group.
        Unlicensed physical ports do not have port filter objects so
        they don't have rows in the filter tables.
        Every licensed physical port has a port filter object
        configured in one of the valid filter modes:
        Pass All, Deny All, Pass by Criteria, or Deny by Criteria.
        Dynamic filters and Logical port group filter objects are
        created, configured, and deleted by the user using one of the
        client interfaces (NTO Control Panel or scripting interface).
        Filter creation, modification of filter properties, and
        filter deletion are reflected in anueNtoFilterDefTable.
        Several filter statistics tables and a filter history table
        extend (logically augment) anueNtoFilterDefTable."
    -- 1.3.6.1.4.1.32620.1.1.3.2
    ::= { anueNtoFilter 2 }

anueNtoFilterDefEntry OBJECT-TYPE
    SYNTAX  AnueNtoFilterDefEntry
    MAX-ACCESS not-accessible
    STATUS  current
    DESCRIPTION
        "Each filter is represented by a row in the
        anueNtoFilterDefTable and a row in each of the filter history
        and filter statistics tables that logically augment that table.
        Unlicensed ports are not filters so they are not represented
        by rows in the filter tables.
        Dynamic filters and standalone port filters are each
        represented by a single row in the filter tables.
        A network or tool port group containing n port members
        is represented by n+1 rows in the filter tables.
        A bidirectional port has two filter definition rows.  One
        row models its role as a network port and another models
        its role as a tool port.  A bidirectional port group
        containing n port members is represented by 2*(n+1) rows
        in the filter tables."
    INDEX {
        anueFilterType,
        anueFilterNumber
         }
    -- 1.3.6.1.4.1.32620.1.1.3.2.1
    ::= { anueNtoFilterDefTable 1 }


AnueNtoFilterDefEntry ::= SEQUENCE {
    anueFilterType            AnueFilterTypeDT,
    anueFilterNumber          Integer32,
    anueFilterDefaultName     DisplayString,
    anueFilterName            DisplayString,
    anueFilterDesc            DisplayString,
    anueFilterIfIndex         Integer32,
    anueFilterIsTwoStage      INTEGER,
    anueFilterMode            INTEGER,
    anueFilterCriteria        DisplayString,
    anueFilterTag             DisplayString,
    anueFilterAfmEnabled      TruthValue,
    anueFilterEnabledFeatures AnueStageType,
    anueFilterCustomFieldSets DisplayString }

anueFilterType OBJECT-TYPE
    SYNTAX  AnueFilterTypeDT
    MAX-ACCESS read-only
    STATUS  current
    DESCRIPTION
        "Filter type indicates whether the row is modeling a physical
        network port, a physical tool port, a dynamic filter,
        a logical network port group, or a logical tool port group.
        The combination of filter type and filter number allows users
        to uniquely locate a filter definition row.  These two values
        form the table key used by the filter tables."
    -- 1.3.6.1.4.1.32620.1.1.3.2.1.1
    ::= { anueNtoFilterDefEntry 1 }

anueFilterNumber OBJECT-TYPE
    SYNTAX  Integer32  (1..2147483647)
    MAX-ACCESS read-only
    STATUS  current
    DESCRIPTION
        "Filter number is a number which identifies a dynamic filter,
        port filter, or a port group filter.  The combination of
        filter type and filter number allows users to uniquely
        locate a filter definition row.  These two values form
        the table key used by the filter tables.
        A dynamic filter 'number' is the numeric portion of its
        anueFilterDefaultName.  For example, the 'filter number'
        for F15 is 15.
        The 'filter number' for a port or a port group corresponds
        to the port ifIndex in the ifTable."
    -- 1.3.6.1.4.1.32620.1.1.3.2.1.2
    ::= { anueNtoFilterDefEntry 2 }


anueFilterDefaultName OBJECT-TYPE
    SYNTAX  DisplayString
    MAX-ACCESS read-only
    STATUS  current
    DESCRIPTION
        "Filter default name is the system assigned name for a
        filter entry.  These names are displayed in various locations
        in the NTO Control Panel, including in bold letters on
        the diagram view.

        The default name for dynamic filters is assigned by the
        system when the filter is created.  A dynamic filter's default
        name begins with the letter 'F' followed by the first unused
        number starting with 1.  The first dynamic filter created
        in the system is F1, followed by F2.  If F1 is deleted the
        next dynamic filter that is created will have default name F1.

        The default name for port filters is platform dependent. All
        licensed ports are assigned a default name which corresponds to
        the default port name displayed in the NTO Control Panel.
        Port filters which are members of bidirectional port groups
        will have two filter rows with the same default name - one for
        the network port filter and one for the tool port filter.
        For port filters, the value of anueFilterDefaultName maps to
        the ifMIB ifXTable ifName field.

        The default name for port group filters is assigned by the
        system when the port group is created.  A Port group's default
        name begins with the letters 'PG' followed by the first unused
        number starting with 1.  The first port group created
        in the system is PG1, followed by PG2.  If PG1 is deleted the
        next port group that is created will have default name PG1.
        Port group filters which are configured as bidirectional
        will have two filter rows with the same default name - one for
        the network port group filter and one for the tool port group
        filter.  For port group filters, the value of
        anueFilterDefaultName maps to the ifMIB ifXTable ifName field."
    -- 1.3.6.1.4.1.32620.1.1.3.2.1.3
    ::= { anueNtoFilterDefEntry 3 }


anueFilterName OBJECT-TYPE
    SYNTAX  DisplayString
    MAX-ACCESS read-only
    STATUS  current
    DESCRIPTION
        "Filter name is the user entered dynamic filter name, port name,
        or port group name.  The filter name defaults to anueFilterDefaultName
        if the user hasn't entered the name.  The filter name reverts to
        anueFilterDefaultName if the name is deleted, which prevents
        the object value from being an empty string (Null)."
    -- 1.3.6.1.4.1.32620.1.1.3.2.1.4
    ::= { anueNtoFilterDefEntry 4 }


anueFilterDesc OBJECT-TYPE
    SYNTAX  DisplayString
    MAX-ACCESS read-only
    STATUS  current
    DESCRIPTION
        "This is the user entered dynamic filter description.
        The object value is an empty string (Null) if there is no user
        entered description.  The value is an empty string for network
        and tool port filters, and for network and tool port group filters."
    -- 1.3.6.1.4.1.32620.1.1.3.2.1.5
    ::= { anueNtoFilterDefEntry 5 }


anueFilterIfIndex OBJECT-TYPE
    SYNTAX  Integer32
    MAX-ACCESS read-only
    STATUS  current
    DESCRIPTION
        "This field identifies the ifIndex that corresponds to this
        filter row.  The ifIndex is the interface row in ifTable for
        network and tool port filters, and for network and tool
        port group filters.  ifIndex is set to a meaningless value 0
        for a dynamic filter.  Associating the ifIndex with each
        filter allows SNMP management applications to easily
        navigate from Anue port filter tables to the corresponding
        port information in standard MIBs"
    -- 1.3.6.1.4.1.32620.1.1.3.2.1.6
    ::= { anueNtoFilterDefEntry 6 }

anueFilterIsTwoStage OBJECT-TYPE
    SYNTAX  INTEGER {
            anueFilterIsOneStage(1),
            anueFilterIsTwoStage(2),
            anueFilterNA(3)  }
    MAX-ACCESS read-only
    STATUS  current
    DESCRIPTION
        "This field identifies whether a dynamic filter is configured
        to be a One Stage or a Two Stage filter.  By default, dynamic
        filters are two stage.  This field is always set to anueFilterNA
        (not applicable) for network/tool port filters, and for
        network/tool port group filters."
    -- 1.3.6.1.4.1.32620.1.1.3.2.1.7
    ::= { anueNtoFilterDefEntry 7 }


anueFilterMode   OBJECT-TYPE
    SYNTAX  INTEGER {
            anueFilterModePassAll(1),
            anueFilterModePassByCriteria(2),
            anueFilterModeDenyAll(3),
            anueFilterModeDenyByCriteria(4),
            anueFilterModePassByCriteriaUnmatched(5),
            anueFilterModeDenyByCriteriaMatched(6)
            }
    MAX-ACCESS read-only
    STATUS  current
    DESCRIPTION
        "Filter mode identifies whether the filter is configured to
         Pass All traffic, Pass by Criteria, Deny All traffic, or
         Deny by Criteria.  Pass by Criteria filters allow traffic
         to pass if it matches the defined criteria.  Deny by Criteria
         filters deny traffic from passing if it matches the defined
         criteria.  All filter types support Pass All and Deny All modes.
         Network port (group) filters support Pass by Criteria and
         Deny by Criteria.  Dynamic filters support Pass by Criteria.
         Tool port (group) filters support Deny by Criteria."
    -- 1.3.6.1.4.1.32620.1.1.3.2.1.8
    ::= { anueNtoFilterDefEntry 8 }

anueFilterCriteria OBJECT-TYPE
    SYNTAX  DisplayString
    MAX-ACCESS read-only
    STATUS  current
    DESCRIPTION
        "A textual representation of the filter criteria configured
        for the filter.  This text string summarizes the filter
        criteria/values and includes boolean AND and OR operators
        when multiple criteria are configured.  The text string uses
        the same format as the scripting 'show filter f1 -prop criteria'
        or 'prop-get filter f1 criteria' commands.
        The anueFilterCriteria is a zero length string if the filter
        mode is PassAll or DenyAll. The maximum string length is 255.
        If the string displayed on the Control Panel is longer than 255,
        this object only stores the first 255 characters."
    -- 1.3.6.1.4.1.32620.1.1.3.2.1.9
    ::= { anueNtoFilterDefEntry 9 }

anueFilterTag OBJECT-TYPE
    SYNTAX  DisplayString
    MAX-ACCESS read-only
    STATUS  current
    DESCRIPTION
        "Filter tag is a free form text field that users may optionally
        configure for each filter.  A user can configure one or more
        keywords using comma, space, or colon as separators.
        A management system can use keywords for search and sort
        operations, and for aggregating MIB values."
    -- 1.3.6.1.4.1.32620.1.1.3.2.1.10
    ::= { anueNtoFilterDefEntry 10 }


anueFilterAfmEnabled OBJECT-TYPE
    SYNTAX  TruthValue (0)
    MAX-ACCESS read-only
    STATUS  current
    DESCRIPTION
        "Indicates whether or not any AFM features are enabled on this
        filter. On bi-directional AFM ports, this object can be true in
        only one direction. The possible values are:
                        1 - true
                        2 - false "
    -- 1.3.6.1.4.1.32620.1.1.3.2.1.11
    ::= { anueNtoFilterDefEntry 11 }


anueFilterEnabledFeatures OBJECT-TYPE
    SYNTAX  AnueStageType
    MAX-ACCESS read-only
    STATUS  current
    DESCRIPTION
        "Identifies the pipeline stages that are present or enabled on
        this filter, either in the standard filtering hardware or on an
        AFM.  Detailed statistics for each enabled stage are contained in
        separate stage tables.  The numerical values of these
        enumerations do not imply an operational order.  If no pipeline
        stages are present or enabled, this object will return an octet
        string with all bit enumerations set to zero."
    -- 1.3.6.1.4.1.32620.1.1.3.2.1.12
    ::= { anueNtoFilterDefEntry 12 }


anueFilterCustomFieldSets OBJECT-TYPE
    SYNTAX  DisplayString
    MAX-ACCESS read-only
    STATUS  current
    DESCRIPTION
       "A comma separated string of custom field set ids. Indicates whether
        a custom offset field criteria is used and if so, from which field set(s)."
    -- 1.3.6.1.4.1.32620.1.1.3.2.1.13
    ::= { anueNtoFilterDefEntry 13 }


-- anueNtoFilterConnTable
--

anueNtoFilterConnTable OBJECT-TYPE
    SYNTAX  SEQUENCE OF AnueNtoFilterConnEntry
    MAX-ACCESS not-accessible
    STATUS  current
    DESCRIPTION
        "Filter connection table entries model the connection
        relationships between filters.  This table can be used to derive
        the filter topology, and to traverse from connected filter to
        connected filter.  The information in this table maps to the
        connections displayed on the NTO Control Panel diagram view.
        Each row in this table maps to a single connecting line
        in the diagram view."
    -- 1.3.6.1.4.1.32620.1.1.3.3
    ::= { anueNtoFilter 3 }


anueNtoFilterConnEntry OBJECT-TYPE
    SYNTAX  AnueNtoFilterConnEntry
    MAX-ACCESS not-accessible
    STATUS  current
    DESCRIPTION
        "Filter connection row entries model a single from/to
        connection between filters.  The connection is either
        from a network filter to a dynamic filter, or from a
        dynamic filter to a tool filter.
        Multiple rows can be used to model 1:m, m:1,
        and m:m connection relationships between filters.

        For port group filter connections, there will be a row for each
        connection between the port group and a dynamic filter,

        and n rows for each connection between the n port members
        and the dynamic filter.

        Each row represents a connection relationship regardless of
        whether packets are passing through a filter.  The connection
        relationship exists when ports are disabled and when filter mode
        is configured to Deny All."
    INDEX {
        anueFilterConnFromOid,
        anueFilterConnToOid }
    -- 1.3.6.1.4.1.32620.1.1.3.3.1
    ::= { anueNtoFilterConnTable 1 }

AnueNtoFilterConnEntry ::= SEQUENCE {
    anueFilterConnFromOid OBJECT IDENTIFIER,
    anueFilterConnToOid   OBJECT IDENTIFIER }

anueFilterConnFromOid OBJECT-TYPE
    SYNTAX  OBJECT IDENTIFIER
    MAX-ACCESS read-only
    STATUS  current
    DESCRIPTION
        "The value of this object is a reference to an anueFilterNumber
        entry in the anueNtoFilterDefTable."
    -- 1.3.6.1.4.1.32620.1.1.3.3.1.1
    ::= { anueNtoFilterConnEntry 1 }

anueFilterConnToOid OBJECT-TYPE
    SYNTAX  OBJECT IDENTIFIER
    MAX-ACCESS read-only
    STATUS  current
    DESCRIPTION
        "The value of this object is a reference to an anueFilterNumber
        entry in the anueNtoFilterDefTable."
    -- 1.3.6.1.4.1.32620.1.1.3.3.1.2
    ::= { anueNtoFilterConnEntry 2 }


-- anueNtoFilterHistEntry
--

anueNtoFilterHistTable OBJECT-TYPE
    SYNTAX  SEQUENCE OF AnueNtoFilterHistEntry
    MAX-ACCESS not-accessible
    STATUS  current
    DESCRIPTION
        "A table that models filter creation, modification, and statistics
         reset history."
    -- 1.3.6.1.4.1.32620.1.1.3.4
    ::= { anueNtoFilter 4 }

anueNtoFilterHistEntry OBJECT-TYPE
    SYNTAX  AnueNtoFilterHistEntry
    MAX-ACCESS not-accessible
    STATUS  current
    DESCRIPTION
        "An entry in the filter history table."
    INDEX {
        anueFilterType,
        anueFilterNumber
    }
    -- 1.3.6.1.4.1.32620.1.1.3.4.1
    ::= { anueNtoFilterHistTable 1 }

AnueNtoFilterHistEntry ::= SEQUENCE {
    anueFilterCreatedTime          DateAndTime,
    anueFilterCreatedBy            DisplayString,
    anueFilterCriteriaModTime      DateAndTime,
    anueFilterCriteriaModTimeStamp TimeStamp,
    anueFilterCriteriaModBy        DisplayString,
    anueFilterConfigModTime        DateAndTime,
    anueFilterConfigModBy          DisplayString,
    anueFilterConfigModFields      DisplayString,
    anueFilterStatsResetTime       DateAndTime,
    anueFilterStatsResetBy         DisplayString,
    anueFilterDropResetTime        DateAndTime,
    anueFilterDropResetBy          DisplayString }


anueFilterCreatedTime OBJECT-TYPE
    SYNTAX  DateAndTime
    MAX-ACCESS read-only
    STATUS  current
    DESCRIPTION
        "The entry creation date and time.  For a dynamic filter or
        a port group, the value of this object can be earlier than
        the current NTO system start time since FilterCreatedTime
        is stored persistently. For a port filter, this field
        is always an empty string."
    -- 1.3.6.1.4.1.32620.1.1.3.4.1.3
    ::= { anueNtoFilterHistEntry 3 }


anueFilterCreatedBy OBJECT-TYPE
    SYNTAX  DisplayString
    MAX-ACCESS read-only
    STATUS  current
    DESCRIPTION
        "The login id of a user who initially created the filter.
         For port filters, this field is always an empty string."
    -- 1.3.6.1.4.1.32620.1.1.3.4.1.4
    ::= { anueNtoFilterHistEntry 4 }


anueFilterCriteriaModTime OBJECT-TYPE
    SYNTAX  DateAndTime
    MAX-ACCESS read-only
    STATUS  current
    DESCRIPTION
        "The CriteriaModTime identifies the date and time of the last
        configuration event which significantly changed the behavior
        of this filter.  This date and time is not displayed in the
        client NTO Control Panel.

        When a dynamic filter is created, it's CriteriaModTime and
        anueFilterCreatedTime are both set to the creation time.  A
        port filter's CriteriaModTime will be an empty string until
        one of the filter configuration events listed below occurs.

        Events that cause CriteriaModTime to be updated:
        1. Modify the filter mode;
        2. Modify the filter criteria including type or values;
        3. Modify the filter's port mode (for ports and port group) from
           network to tool, or visa versa;
        4. Modify a dynamic filter from one-stage to two-stage, or visa versa;
        5. Modify dynamic filter ordering;
        6. Modify a 5204 dynamic filter to 'Count Matches In' packets or bytes.

        When any of the above events occur, all statistics are reset
        for this filter's row in anueNtoFilterStatsCntModHCTable and
        anueNtoFilterStatsCntModTable.  The fields anueFilterCriteriaModTime,
        anueFilterCriteriaModTimestamp, anueFilterCriteriaModBy,
        anueFilterConfigModTimestamp, anueFilterConfigModBy, and
        anueFilterConfigModFields are updated.

        The fields anueFilterStatResetTime, anueFilterStatResetBy,
        anueFilterDropResetTime, and anueFilterDropResetBy are also
        updated since the filter configuration change triggers a
        statistics reset.  The corresponding row in
        anueNtoFilterStatsCntRstHCTable and anueNtoFilterStatsCntRstTable
        are reset, as are all current, peak, and average statistics tables.

        When CriteriaModTime is updated previous statistics are no longer
        relevant for this filter since its behavior has been modified.
        Statistics aggregation and analysis should be restarted after
        CriteriaModTime is updated.

        CriteriaModTime is persistently stored in the object model.
        If one of the configuration events listed above has not occurred
        since the NTO system has been re-initialized, then the value of this
        object will pre-date the current system start time."
    -- 1.3.6.1.4.1.32620.1.1.3.4.1.5
    ::= { anueNtoFilterHistEntry 5 }

anueFilterCriteriaModTimeStamp OBJECT-TYPE
    SYNTAX  TimeStamp
    MAX-ACCESS read-only
    STATUS  current
    DESCRIPTION
        "This field is redundant to anueFilterCriteriaModTime, except it
        uses datatype TimeStamp.  The field may be useful for SNMP management
        applications to programmatically aggregate filter statistics.
        This object contains a zero value if anueFilterCriteriaModTime
        pre-dates the current system start time.  Otherwise, this object
        contains the sysUpTime when anueFilterCriteriaModTime was last
        updated."
    -- 1.3.6.1.4.1.32620.1.1.3.4.1.6
    ::= { anueNtoFilterHistEntry 6 }

anueFilterCriteriaModBy OBJECT-TYPE
    SYNTAX  DisplayString
    MAX-ACCESS read-only
    STATUS  current
    DESCRIPTION
        "The login id of a user who made the last configuration change that
        altered anueFilterCriteriaModTime for this filter."
    -- 1.3.6.1.4.1.32620.1.1.3.4.1.7
    ::= { anueNtoFilterHistEntry 7 }


anueFilterConfigModTime OBJECT-TYPE
    SYNTAX  DateAndTime
    MAX-ACCESS read-only
    STATUS  current
    DESCRIPTION
        "The date and time that any filter setting was last modified.  This
        includes any modification that occurs in the Client NTO Control
        Panel for the corresponding Edit Port, Edit Port Group, or Edit
        Filter property dialog.  Modifying settings that do not affect
        filter behavior such as filter name and description cause the date
        and time to update."
    -- 1.3.6.1.4.1.32620.1.1.3.4.1.8
    ::= { anueNtoFilterHistEntry 8 }


anueFilterConfigModBy OBJECT-TYPE
    SYNTAX  DisplayString
    MAX-ACCESS read-only
    STATUS  current
    DESCRIPTION
        "The login id of a user who made the last configuration change
        to any setting of this filter."
    -- 1.3.6.1.4.1.32620.1.1.3.4.1.9
    ::= { anueNtoFilterHistEntry 9 }

anueFilterConfigModFields OBJECT-TYPE
    SYNTAX  DisplayString
    MAX-ACCESS read-only
    STATUS  current
    DESCRIPTION
        "The field(s) of the filter that were modified in the last
        configuration change."
    -- 1.3.6.1.4.1.32620.1.1.3.4.1.10
    ::= { anueNtoFilterHistEntry 10 }


anueFilterStatsResetTime OBJECT-TYPE
    SYNTAX  DateAndTime
    MAX-ACCESS read-only
    STATUS  current
    DESCRIPTION
        "Various events can cause the Client NTO Control Panel to
        reset the statistics displayed for a filter.
        When a filter's statistics are reset, the corresponding row in
        anueNtoFilterStatsCntRstHCTable, anueNtoFilterStatsCurHCTable,
        anueNtoFilterStatsPeakHCTable, anueNtoFilterStatsAvgHCTable
        and the 32-bit version of these stats tables are all reset.
        The events that cause a filter's anueFilterCriteriaModTime
        to update will reset the above statistics tables, as well as
        the following events:
        1. A user resets the filter's statistics;
        2. A Port filter's media type is changed between copper and fiber, or
            between 1GSFP and 10GSFP+;
        3. A Port/Port Group filter's enabled state (administrative state)
           is modified;
        4. The system's filter memory allocation is modified;
        5. A dynamic filter's statistics are reset when its connections change;"
    -- 1.3.6.1.4.1.32620.1.1.3.4.1.11
    ::= { anueNtoFilterHistEntry 11 }


anueFilterStatsResetBy OBJECT-TYPE
    SYNTAX  DisplayString
    MAX-ACCESS read-only
    STATUS  current
    DESCRIPTION
        "The login id of a user who initiated the modification that caused
        the filter's statistics to last be reset."
    -- 1.3.6.1.4.1.32620.1.1.3.4.1.12
    ::= { anueNtoFilterHistEntry 12 }


anueFilterDropResetTime OBJECT-TYPE
    SYNTAX  DateAndTime
    MAX-ACCESS read-only
    STATUS  current
    DESCRIPTION
        "The date and time that a tool port/port group filter's drop count
        was last reset.  Note that stats reset also resets the tool port
        drop count.  For network filters and dynamic filters, this field is
        an empty string."
    -- 1.3.6.1.4.1.32620.1.1.3.4.1.13
    ::= { anueNtoFilterHistEntry 13 }

anueFilterDropResetBy OBJECT-TYPE
    SYNTAX  DisplayString
    MAX-ACCESS read-only
    STATUS  current
    DESCRIPTION
        "The login id of a user who last reset the drop counts (or stats)
          for this filter."
    -- 1.3.6.1.4.1.32620.1.1.3.4.1.14
    ::= { anueNtoFilterHistEntry 14 }


-- anueNtoFilterStatsCntModHCTable
--

anueNtoFilterStatsCntModHCTable OBJECT-TYPE
    SYNTAX  SEQUENCE OF AnueNtoFilterStatsCntModHCEntry
    MAX-ACCESS not-accessible
    STATUS  current
    DESCRIPTION
        "A table of statistics entries that model accumulated filter
         counts since anueFilterCriteriaModTime.  The table values count
         filter statistics since the time the filter's data handling
         behavior was last modified.
         The values for a port group filter are the sum of accumulated
         counts of each port filter that is a member of the port group."
    -- 1.3.6.1.4.1.32620.1.1.3.5
    ::= { anueNtoFilter 5 }

anueNtoFilterStatsCntModHCEntry OBJECT-TYPE
    SYNTAX  AnueNtoFilterStatsCntModHCEntry
    MAX-ACCESS not-accessible
    STATUS  current
    DESCRIPTION
        "This entry extends anueNtoFilterDefEntry with
         accumulated 64-bit filter counters."
    INDEX {
        anueFilterType,
        anueFilterNumber
    }
    -- 1.3.6.1.4.1.32620.1.1.3.5.1
    ::= { anueNtoFilterStatsCntModHCTable 1 }

AnueNtoFilterStatsCntModHCEntry ::= SEQUENCE {
    anueFilterCntModHCInOctets  Counter64,
    anueFilterCntModHCOutOctets Counter64,
    anueFilterCntModHCInPkts    Counter64,
    anueFilterCntModHCOutPkts   Counter64,
    anueFilterCntModHCDropPkts  Counter64,
    anueFilterCntModHCDropTime  DateAndTime }

anueFilterCntModHCInOctets OBJECT-TYPE
    SYNTAX  Counter64
    MAX-ACCESS read-only
    STATUS  current
    DESCRIPTION
        "The total number of octets received by the filter since
         anueFilterCriteriaModTime.
         Tool filters return 0, since they do not support this value."
    -- 1.3.6.1.4.1.32620.1.1.3.5.1.3
    ::= { anueNtoFilterStatsCntModHCEntry 3 }


anueFilterCntModHCOutOctets OBJECT-TYPE
    SYNTAX  Counter64
    MAX-ACCESS read-only
    STATUS  current
    DESCRIPTION
        "The total number of octets passed by the filter since
         anueFilterCriteriaModTime.
         On the 5204 platform, dynamic pass by criteria filters configured
         to count matches in packets are set to a value of 0."
    -- 1.3.6.1.4.1.32620.1.1.3.5.1.4
    ::= { anueNtoFilterStatsCntModHCEntry 4 }


anueFilterCntModHCInPkts OBJECT-TYPE
    SYNTAX  Counter64
    MAX-ACCESS read-only
    STATUS  current
    DESCRIPTION
        "The total number of packets received by the filter since
         anueFilterCriteriaModTime"
    -- 1.3.6.1.4.1.32620.1.1.3.5.1.5
    ::= { anueNtoFilterStatsCntModHCEntry 5 }


anueFilterCntModHCOutPkts OBJECT-TYPE
    SYNTAX  Counter64
    MAX-ACCESS read-only
    STATUS  current
    DESCRIPTION
        "The total number of packets passed by the filter since
         anueFilterCriteriaModTime.
         On the 5204 platform, dynamic pass by criteria filters configured
         to count matches in bytes are set to a value of 0."
    -- 1.3.6.1.4.1.32620.1.1.3.5.1.6
    ::= { anueNtoFilterStatsCntModHCEntry 6 }


anueFilterCntModHCDropPkts OBJECT-TYPE
    SYNTAX  Counter64
    MAX-ACCESS read-only
    STATUS  current
    DESCRIPTION
        "The total number of packets dropped at a tool port filter
         since anueFilterCriteriaModTime.  Drops may occur at a tool
         port when the rate of traffic directed to the tool port
         exceeds the port's line rate.  Drops occur prior to the actual
         filtering that may be configured for the tool port.
         Drop counts are always 0 for network and dynamic filters."
    -- 1.3.6.1.4.1.32620.1.1.3.5.1.7
    ::= { anueNtoFilterStatsCntModHCEntry 7 }

anueFilterCntModHCDropTime OBJECT-TYPE
    SYNTAX  DateAndTime
    MAX-ACCESS read-only
    STATUS  current
    DESCRIPTION
        "The date and time of last drop event.  If no packets have been
         dropped since anueFilterCriteriaModTime, this field is an empty string.
         For network filters and dynamic filters, this field is an empty string."
    -- 1.3.6.1.4.1.32620.1.1.3.5.1.8
    ::= { anueNtoFilterStatsCntModHCEntry 8 }


-- anueNtoFilterStatsCntRstHCTable
--

anueNtoFilterStatsCntRstHCTable OBJECT-TYPE
    SYNTAX  SEQUENCE OF AnueNtoFilterStatsCntRstHCEntry
    MAX-ACCESS not-accessible
    STATUS  current
    DESCRIPTION
       "A table of statistics entries that model accumulated filter
        counts since anueFilterStatsResetTime.  The table values map to the
        accumulated counts displayed in the NTO Control Panel's filter
        statistics windows.  This table's values are reset by the same
        conditions that reset the Control Panel's statistics, as described in
        anueFilterStatsResetTime.

        The values for a port group filter are the sum of accumulated
        counts of each port filter that is a member of the port group."
    -- 1.3.6.1.4.1.32620.1.1.3.6
    ::= { anueNtoFilter 6 }

anueNtoFilterStatsCntRstHCEntry OBJECT-TYPE
    SYNTAX  AnueNtoFilterStatsCntRstHCEntry
    MAX-ACCESS not-accessible
    STATUS  current
    DESCRIPTION
        "This entry extends anueNtoFilterDefEntry with
         accumulated 64-bit filter counters. "
    INDEX {
        anueFilterType,
        anueFilterNumber
    }
    -- 1.3.6.1.4.1.32620.1.1.3.6.1
    ::= { anueNtoFilterStatsCntRstHCTable 1 }

AnueNtoFilterStatsCntRstHCEntry ::= SEQUENCE {
    anueFilterCntRstHCInOctets  Counter64,
    anueFilterCntRstHCOutOctets Counter64,
    anueFilterCntRstHCInPkts    Counter64,
    anueFilterCntRstHCOutPkts   Counter64,
    anueFilterCntRstHCDropPkts  Counter64,
    anueFilterCntRstHCDropTime  DateAndTime }

anueFilterCntRstHCInOctets OBJECT-TYPE
    SYNTAX  Counter64
    MAX-ACCESS read-only
    STATUS  current
    DESCRIPTION
        "The total number of octets received by the filter since
         anueFilterStatsResetTime.
         Tool filters return 0, since they do not support this value."
    -- 1.3.6.1.4.1.32620.1.1.3.6.1.3
    ::= { anueNtoFilterStatsCntRstHCEntry 3 }


anueFilterCntRstHCOutOctets OBJECT-TYPE
    SYNTAX  Counter64
    MAX-ACCESS read-only
    STATUS  current
    DESCRIPTION
        "The total number of octets passed by the filter since
         anueFilterStatsResetTime.
         On the 5204 platform, dynamic pass by criteria filters configured
         to count matches in packets are set to a value of 0"
    -- 1.3.6.1.4.1.32620.1.1.3.6.1.4
    ::= { anueNtoFilterStatsCntRstHCEntry 4 }


anueFilterCntRstHCInPkts OBJECT-TYPE
    SYNTAX  Counter64
    MAX-ACCESS read-only
    STATUS  current
    DESCRIPTION
        "The total number of packets received by the filter since
         anueFilterStatsResetTime."
    -- 1.3.6.1.4.1.32620.1.1.3.6.1.5
    ::= { anueNtoFilterStatsCntRstHCEntry 5 }


anueFilterCntRstHCOutPkts OBJECT-TYPE
    SYNTAX  Counter64
    MAX-ACCESS read-only
    STATUS  current
    DESCRIPTION
        "The total number of packets passed by the filter
         since anueFilterStatsResetTime.
         On the 5204 platform, dynamic pass by criteria filters configured
         to count matches in bytes are set to a value of 0."
    -- 1.3.6.1.4.1.32620.1.1.3.6.1.6
    ::= { anueNtoFilterStatsCntRstHCEntry 6 }


anueFilterCntRstHCDropPkts OBJECT-TYPE
    SYNTAX  Counter64
    MAX-ACCESS read-only
    STATUS  current
    DESCRIPTION
        "The total number of packets dropped by a tool port filter
         since anueFilterStatsResetTime.  Drops may occur at a tool
         port when the rate of traffic directed to the tool port
         exceeds the port's line rate.  Drops occur prior to the actual
         filtering that may be configured for the tool port.

         Drop counts are always 0 for network and dynamic filters."
    -- 1.3.6.1.4.1.32620.1.1.3.6.1.7
    ::= { anueNtoFilterStatsCntRstHCEntry 7 }

anueFilterCntRstHCDropTime OBJECT-TYPE
    SYNTAX  DateAndTime
    MAX-ACCESS read-only
    STATUS  current
    DESCRIPTION
        "The date and time of last drop event since
         anueFilterStatsResetTime.  If no packets have been dropped
         since anueFilterStatsResetTime, this field is an empty string.
         For network filters and dynamic filters, this field is an empty string."
    -- 1.3.6.1.4.1.32620.1.1.3.6.1.8
    ::= { anueNtoFilterStatsCntRstHCEntry 8 }

-- anueNtoFilterStatsCurHCTable
--

anueNtoFilterStatsCurHCTable OBJECT-TYPE
    SYNTAX  SEQUENCE OF AnueNtoFilterStatsCurHCEntry
    MAX-ACCESS not-accessible
    STATUS  current
    DESCRIPTION
        "A table of statistics entries that model the filter counts
         collected in the current (most recent) sampling period.
         The table values map to the current counts displayed in the
         NTO Control Panel's filter statistics windows.  The NTO statistics
         sampling period is stored in anueFilterCollectionPeriod.

         The values for a port group filter take the sum of the current
         counts of each port filter that is a member of the port group.
         Percentage values take into account the aggregate speed of the
         port group."
    -- 1.3.6.1.4.1.32620.1.1.3.7
    ::= { anueNtoFilter 7 }

anueNtoFilterStatsCurHCEntry OBJECT-TYPE
    SYNTAX  AnueNtoFilterStatsCurHCEntry
    MAX-ACCESS not-accessible
    STATUS  current
    DESCRIPTION
        "This entry extends anueNtoFilterDefEntry with
         64-bit filter counters. "
    INDEX {
        anueFilterType,
        anueFilterNumber
    }
    -- 1.3.6.1.4.1.32620.1.1.3.7.1
    ::= { anueNtoFilterStatsCurHCTable 1 }

AnueNtoFilterStatsCurHCEntry ::= SEQUENCE {
    anueFilterCurHCInOctets   CounterBasedGauge64,
    anueFilterCurHCOutOctets  CounterBasedGauge64,
    anueFilterCurHCRateOctets CounterBasedGauge64,
    anueFilterCurHCInPkts     CounterBasedGauge64,
    anueFilterCurHCOutPkts    CounterBasedGauge64,
    anueFilterCurHCRatePkts   CounterBasedGauge64,
    anueFilterCurHCDropPkts   CounterBasedGauge64,
    anueFilterCurHCUtil       CounterBasedGauge64 }

anueFilterCurHCInOctets OBJECT-TYPE
    SYNTAX  CounterBasedGauge64
    MAX-ACCESS read-only
    STATUS  current
    DESCRIPTION
        "The number of octets received by the filter in the current
         (most recent) sampling period.

         Tool filters return 0, since they do not support this value.
         Note that the corresponding NTO Control Panel counts are
         displayed as bits/sec."
    -- 1.3.6.1.4.1.32620.1.1.3.7.1.3
    ::= { anueNtoFilterStatsCurHCEntry 3 }


anueFilterCurHCOutOctets OBJECT-TYPE
    SYNTAX  CounterBasedGauge64
    MAX-ACCESS read-only
    STATUS  current
    DESCRIPTION
        "The number of octets passed by the filter in the current
         (most recent) sampling period.  Note that the corresponding
         NTO Control Panel counts are displayed as bits/sec.

         On the 5204 platform, dynamic pass by criteria filters configured
         to count matches in packets are set to a value of 0."
    -- 1.3.6.1.4.1.32620.1.1.3.7.1.4
    ::= { anueNtoFilterStatsCurHCEntry 4 }

anueFilterCurHCRateOctets OBJECT-TYPE
    SYNTAX  CounterBasedGauge64
    MAX-ACCESS read-only
    STATUS  current
    DESCRIPTION
        "The percentage of received octets that passed this filter
         in the current (most recent) sampling period.

         This value is always 0 for tool filters.  On the 5204 platform,
         dynamic pass by criteria filters configured to count matches in
         packets are set to a value of 0.  Note that the corresponding NTO
         Control Panel counts are displayed as bits/sec."
    -- 1.3.6.1.4.1.32620.1.1.3.7.1.5
    ::= { anueNtoFilterStatsCurHCEntry 5 }


anueFilterCurHCInPkts OBJECT-TYPE
    SYNTAX  CounterBasedGauge64
    MAX-ACCESS read-only
    STATUS  current
    DESCRIPTION
        "The number of packets received by the filter in the current
         (most recent) sampling period."
    -- 1.3.6.1.4.1.32620.1.1.3.7.1.6
    ::= { anueNtoFilterStatsCurHCEntry 6 }


anueFilterCurHCOutPkts OBJECT-TYPE
    SYNTAX  CounterBasedGauge64
    MAX-ACCESS read-only
    STATUS  current
    DESCRIPTION
        "The number of packets passed by the filter in the current
         (most recent) sampling period.

         On the 5204 platform, dynamic pass by criteria filters configured
         to count matches in bytes are set to a value of 0."
    -- 1.3.6.1.4.1.32620.1.1.3.7.1.7
    ::= { anueNtoFilterStatsCurHCEntry 7 }

anueFilterCurHCRatePkts OBJECT-TYPE
    SYNTAX  CounterBasedGauge64
    MAX-ACCESS read-only
    STATUS  current
    DESCRIPTION
        "The percentage of received packets that passed this filter
         in the current (most recent) sampling period.

         On the 5204 platform, dynamic pass by criteria filters configured
         to count matches in bytes are set to a value of 0."
    -- 1.3.6.1.4.1.32620.1.1.3.7.1.8
    ::= { anueNtoFilterStatsCurHCEntry 8 }

anueFilterCurHCDropPkts OBJECT-TYPE
    SYNTAX  CounterBasedGauge64
    MAX-ACCESS read-only
    STATUS  current
    DESCRIPTION
        "The number of packets dropped by a tool port filter in the
         current (most recent) sampling period.  Drops may occur at a
         tool port when the rate of traffic directed to the tool port
         exceeds the port's line rate.  Drops occur prior to the actual
         filtering that may be configured for the tool port.

         Drop counts are always 0 for network and dynamic filters."
    -- 1.3.6.1.4.1.32620.1.1.3.7.1.9
    ::= { anueNtoFilterStatsCurHCEntry 9 }

anueFilterCurHCUtil OBJECT-TYPE
    SYNTAX  CounterBasedGauge64
    MAX-ACCESS read-only
    STATUS  current
    DESCRIPTION
        "The percentage of port bandwidth utilized in the
         current (most recent) sampling period by network port filter
         receive (incoming) traffic, or tool port filter transmit traffic.
         For port groups the percentage is based on the aggregate
         link bandwidth.

         Utilization is always 0 for dynamic filters."
    -- 1.3.6.1.4.1.32620.1.1.3.7.1.10
    ::= { anueNtoFilterStatsCurHCEntry 10 }


-- anueNtoFilterStatsAvgHCTable
--

anueNtoFilterStatsAvgHCTable OBJECT-TYPE
    SYNTAX  SEQUENCE OF AnueNtoFilterStatsAvgHCEntry
    MAX-ACCESS not-accessible
    STATUS  current
    DESCRIPTION
       "A table of filter statistics entries that model the average
        of the counts collected in each sampling period since
        anueFilterStatsResetTime.  The table values map to the average
        counts displayed in the NTO Control Panel's filter statistics
        windows.  The NTO statistics sampling period is stored in
        anueFilterCollectionPeriod.

        The values for a port group filter average the sum of counts
        collected by each port filter that is a member of the port group.
        Percentage values take into account the aggregate speed of the
        port group."
    -- 1.3.6.1.4.1.32620.1.1.3.8
    ::= { anueNtoFilter 8 }

anueNtoFilterStatsAvgHCEntry OBJECT-TYPE
    SYNTAX  AnueNtoFilterStatsAvgHCEntry
    MAX-ACCESS not-accessible
    STATUS  current
    DESCRIPTION
        "This entry extends anueNtoFilterDefEntry with
         64-bit filter counters."
    INDEX {
        anueFilterType,
        anueFilterNumber
    }
    -- 1.3.6.1.4.1.32620.1.1.3.8.1
    ::= { anueNtoFilterStatsAvgHCTable 1 }

AnueNtoFilterStatsAvgHCEntry ::= SEQUENCE {
    anueFilterAvgHCInOctets   CounterBasedGauge64,
    anueFilterAvgHCOutOctets  CounterBasedGauge64,
    anueFilterAvgHCRateOctets CounterBasedGauge64,
    anueFilterAvgHCInPkts     CounterBasedGauge64,
    anueFilterAvgHCOutPkts    CounterBasedGauge64,
    anueFilterAvgHCRatePkts   CounterBasedGauge64,
    anueFilterAvgHCDropPkts   CounterBasedGauge64,
    anueFilterAvgHCUtil       CounterBasedGauge64 }

anueFilterAvgHCInOctets OBJECT-TYPE
    SYNTAX  CounterBasedGauge64
    MAX-ACCESS read-only
    STATUS  current
    DESCRIPTION
        "The average number of octets received by the filter in each sampling
         period since anueFilterStatsResetTime.

         Tool filters return 0, since they do not support this value.
         Note that the corresponding NTO Control Panel counts are displayed
         as bits/sec."
    -- 1.3.6.1.4.1.32620.1.1.3.8.1.3
    ::= { anueNtoFilterStatsAvgHCEntry 3 }


anueFilterAvgHCOutOctets OBJECT-TYPE
    SYNTAX  CounterBasedGauge64
    MAX-ACCESS read-only
    STATUS  current
    DESCRIPTION
        "The average number of octets passed by the filter in each sampling
         period since anueFilterStatsResetTime.  Note that the corresponding
         NTO Control Panel counts are displayed as bits/sec.

         On the 5204 platform, dynamic pass by criteria filters configured
         to count matches in packets are set to a value of 0."
    -- 1.3.6.1.4.1.32620.1.1.3.8.1.4
    ::= { anueNtoFilterStatsAvgHCEntry 4 }

anueFilterAvgHCRateOctets OBJECT-TYPE
    SYNTAX  CounterBasedGauge64
    MAX-ACCESS read-only
    STATUS  current
    DESCRIPTION
        "The average percentage of received octets that passed this filter
         in each sampling period since anueFilterStatsResetTime.

         This value is always 0 for tool filters.  On the 5204 platform,
         dynamic pass by criteria filters configured to count matches in
         packets are set to a value of 0.  Note that the corresponding NTO
         Control Panel counts are displayed as bits/sec."
    -- 1.3.6.1.4.1.32620.1.1.3.8.1.5
    ::= { anueNtoFilterStatsAvgHCEntry 5 }


anueFilterAvgHCInPkts OBJECT-TYPE
    SYNTAX  CounterBasedGauge64
    MAX-ACCESS read-only
    STATUS  current
    DESCRIPTION
        "The average number of packets received by the filter in each sampling
         period since anueFilterStatsResetTime."
    -- 1.3.6.1.4.1.32620.1.1.3.8.1.6
    ::= { anueNtoFilterStatsAvgHCEntry 6 }


anueFilterAvgHCOutPkts OBJECT-TYPE
    SYNTAX  CounterBasedGauge64
    MAX-ACCESS read-only
    STATUS  current
    DESCRIPTION
        "The average number of packets passed by the filter in each sampling
         period since anueFilterStatsResetTime.

         On the 5204 platform, dynamic pass by criteria filters configured
         to count matches in bytes are set to a value of 0."
    -- 1.3.6.1.4.1.32620.1.1.3.8.1.7
    ::= { anueNtoFilterStatsAvgHCEntry 7 }

anueFilterAvgHCRatePkts OBJECT-TYPE
    SYNTAX  CounterBasedGauge64
    MAX-ACCESS read-only
    STATUS  current
    DESCRIPTION
        "The average percentage of received packets that passed this filter
         in each sampling period since anueFilterStatsResetTime.

         On the 5204 platform, dynamic pass by criteria filters configured
         to count matches in bytes are set to a value of 0."
    -- 1.3.6.1.4.1.32620.1.1.3.8.1.8
    ::= { anueNtoFilterStatsAvgHCEntry 8 }

anueFilterAvgHCDropPkts OBJECT-TYPE
    SYNTAX  CounterBasedGauge64
    MAX-ACCESS read-only
    STATUS  current
    DESCRIPTION
        "The average number of packets dropped by a tool port filter in each
         sampling period since anueFilterStatsResetTime.  Drops may occur at
         a tool port when the rate of traffic directed to the tool port
         exceeds the port's line rate.  Drops occur prior to the actual
         filtering that may be configured for the tool port.

         Drop counts are always 0 for network and dynamic filters."
    -- 1.3.6.1.4.1.32620.1.1.3.8.1.9
    ::= { anueNtoFilterStatsAvgHCEntry 9 }

anueFilterAvgHCUtil OBJECT-TYPE
    SYNTAX  CounterBasedGauge64
    MAX-ACCESS read-only
    STATUS  current
    DESCRIPTION
        "The average percentage of port bandwidth utilized in each sampling
         period since anueFilterStatsResetTime.  These values are valid for
         network port filter receive (incoming) traffic and tool port
         filter transmit traffic.  For port groups the percentage is
         based on the aggregate link bandwidth.

         Utilization is always 0 for dynamic filters."
    -- 1.3.6.1.4.1.32620.1.1.3.8.1.10
    ::= { anueNtoFilterStatsAvgHCEntry 10 }


-- anueNtoFilterStatsPeakHCTable
--

anueNtoFilterStatsPeakHCTable OBJECT-TYPE
    SYNTAX  SEQUENCE OF AnueNtoFilterStatsPeakHCEntry
    MAX-ACCESS not-accessible
    STATUS  current
    DESCRIPTION
       "A table of filter statistics entries that model the peak
        count (largest value) collected in any sampling period since
        anueFilterStatsResetTime.  Note that peak counts are based
        on the total traffic measured during a sampling period.
        The table values map to the peak counts displayed in the
        NTO Control Panel's filter statistics windows.  The NTO
        statistics sampling period is stored in
        anueFilterCollectionPeriod.

        The values for a port group filter model the peak sum of
        counts collected by each port filter that is a member of
        the port group.  Percentage values take into account the
        aggregate speed of the port group."
    -- 1.3.6.1.4.1.32620.1.1.3.9
    ::= { anueNtoFilter 9 }

anueNtoFilterStatsPeakHCEntry OBJECT-TYPE
    SYNTAX  AnueNtoFilterStatsPeakHCEntry
    MAX-ACCESS not-accessible
    STATUS  current
    DESCRIPTION
        "This entry extends anueNtoFilterDefEntry with
         64-bit filter counters."
    INDEX {
        anueFilterType,
        anueFilterNumber
    }
    -- 1.3.6.1.4.1.32620.1.1.3.9.1
    ::= { anueNtoFilterStatsPeakHCTable 1 }

AnueNtoFilterStatsPeakHCEntry ::= SEQUENCE {
    anueFilterPeakHCInOctets       CounterBasedGauge64,
    anueFilterPeakHCInOctetsTime   DateAndTime,
    anueFilterPeakHCOutOctets      CounterBasedGauge64,
    anueFilterPeakHCOutOctetsTime  DateAndTime,
    anueFilterPeakHCRateOctets     CounterBasedGauge64,
    anueFilterPeakHCRateOctetsTime DateAndTime,
    anueFilterPeakHCInPkts         CounterBasedGauge64,
    anueFilterPeakHCInPktsTime     DateAndTime,
    anueFilterPeakHCOutPkts        CounterBasedGauge64,
    anueFilterPeakHCOutPktsTime    DateAndTime,
    anueFilterPeakHCRatePkts       CounterBasedGauge64,
    anueFilterPeakHCRatePktsTime   DateAndTime,
    anueFilterPeakHCDropPkts       CounterBasedGauge64,
    anueFilterPeakHCDropPktsTime   DateAndTime,
    anueFilterPeakHCUtil           CounterBasedGauge64,
    anueFilterPeakHCUtilTime       DateAndTime }

anueFilterPeakHCInOctets OBJECT-TYPE
    SYNTAX  CounterBasedGauge64
    MAX-ACCESS read-only
    STATUS  current
    DESCRIPTION
        "The peak number of octets received by the filter in any sampling
         period since anueFilterStatsResetTime.

         Tool filters return 0, since they do not support this value.
         Note that the corresponding NTO Control Panel counts are displayed
         as bits/sec."
    -- 1.3.6.1.4.1.32620.1.1.3.9.1.3
    ::= { anueNtoFilterStatsPeakHCEntry 3 }

anueFilterPeakHCInOctetsTime OBJECT-TYPE
    SYNTAX  DateAndTime
    MAX-ACCESS read-only
    STATUS  current
    DESCRIPTION
        "The date and time of the PeakInOctet event.
         For tool filters, this field is an empty string."
    -- 1.3.6.1.4.1.32620.1.1.3.9.1.4
    ::= { anueNtoFilterStatsPeakHCEntry 4 }

anueFilterPeakHCOutOctets OBJECT-TYPE
    SYNTAX  CounterBasedGauge64
    MAX-ACCESS read-only
    STATUS  current
    DESCRIPTION
        "The peak number of octets passed by the filter in any sampling
         period since anueFilterStatsResetTime.  Note that the corresponding
         NTO Control Panel counts are displayed as bits/sec.

         On the 5204 platform, dynamic pass by criteria filters configured
         to count matches in packets are set to a value of 0."
    -- 1.3.6.1.4.1.32620.1.1.3.9.1.5
    ::= { anueNtoFilterStatsPeakHCEntry 5 }

anueFilterPeakHCOutOctetsTime OBJECT-TYPE
    SYNTAX  DateAndTime
    MAX-ACCESS read-only
    STATUS  current
    DESCRIPTION
        "The date and time of the PeakOutOctet event.
         On the 5204 platform, this field is an empty string for dynamic
         pass by criteria filters configured to count matches in packets."
    -- 1.3.6.1.4.1.32620.1.1.3.9.1.6
    ::= { anueNtoFilterStatsPeakHCEntry 6 }

anueFilterPeakHCRateOctets OBJECT-TYPE
    SYNTAX  CounterBasedGauge64
    MAX-ACCESS read-only
    STATUS  current
    DESCRIPTION
        "The peak percentage of received octets that passed this filter
         in any sampling period since anueFilterStatsResetTime.

         This value is always 0 for tool filters.  On the 5204 platform,
         dynamic pass by criteria filters configured to count matches in
         packets are set to a value of 0.  Note that the corresponding NTO
         Control Panel counts are displayed as bits/sec."
    -- 1.3.6.1.4.1.32620.1.1.3.9.1.7
    ::= { anueNtoFilterStatsPeakHCEntry 7 }

anueFilterPeakHCRateOctetsTime OBJECT-TYPE
    SYNTAX  DateAndTime
    MAX-ACCESS read-only
    STATUS  current
    DESCRIPTION
        "The date and time of the PeakRateOctet event.
         On the 5204 platform, this field is an empty string for dynamic
         pass by criteria filters configured to count matches in packets."
    -- 1.3.6.1.4.1.32620.1.1.3.9.1.8
    ::= { anueNtoFilterStatsPeakHCEntry 8 }

anueFilterPeakHCInPkts OBJECT-TYPE
    SYNTAX  CounterBasedGauge64
    MAX-ACCESS read-only
    STATUS  current
    DESCRIPTION
        "The peak number of packets received by the filter in any sampling
         period since anueFilterStatsResetTime."
    -- 1.3.6.1.4.1.32620.1.1.3.9.1.9
    ::= { anueNtoFilterStatsPeakHCEntry 9 }

anueFilterPeakHCInPktsTime OBJECT-TYPE
    SYNTAX  DateAndTime
    MAX-ACCESS read-only
    STATUS  current
    DESCRIPTION
        "The date and time of the PeakInPkts event."
    -- 1.3.6.1.4.1.32620.1.1.3.9.1.10
    ::= { anueNtoFilterStatsPeakHCEntry 10 }

anueFilterPeakHCOutPkts OBJECT-TYPE
    SYNTAX  CounterBasedGauge64
    MAX-ACCESS read-only
    STATUS  current
    DESCRIPTION
        "The peak number of packets passed by the filter in any sampling
         period since anueFilterStatsResetTime.

         On the 5204 platform, dynamic pass by criteria filters configured
         to count matches in bytes are set to a value of 0."
    -- 1.3.6.1.4.1.32620.1.1.3.9.1.11
    ::= { anueNtoFilterStatsPeakHCEntry 11 }

anueFilterPeakHCOutPktsTime OBJECT-TYPE
    SYNTAX  DateAndTime
    MAX-ACCESS read-only
    STATUS  current
    DESCRIPTION
        "The date and time of the PeakOutPkts event.
         On the 5204 platform, this field is an empty string for dynamic
         pass by criteria filters configured to count matches in bytes."
    -- 1.3.6.1.4.1.32620.1.1.3.9.1.12
    ::= { anueNtoFilterStatsPeakHCEntry 12 }

anueFilterPeakHCRatePkts OBJECT-TYPE
    SYNTAX  CounterBasedGauge64
    MAX-ACCESS read-only
    STATUS  current
    DESCRIPTION
        "The peak percentage of received packets that passed this filter
         in any sampling period since anueFilterStatsResetTime.

         On the 5204 platform, dynamic pass by criteria filters configured
         to count matches in bytes are set to a value of 0."
    -- 1.3.6.1.4.1.32620.1.1.3.9.1.13
    ::= { anueNtoFilterStatsPeakHCEntry 13 }

anueFilterPeakHCRatePktsTime OBJECT-TYPE
    SYNTAX  DateAndTime
    MAX-ACCESS read-only
    STATUS  current
    DESCRIPTION
        "The date and time of the PeakRatePkts event.
         On the 5204 platform, this field is an empty string for dynamic
         pass by criteria filters configured to count matches in packets."
    -- 1.3.6.1.4.1.32620.1.1.3.9.1.14
    ::= { anueNtoFilterStatsPeakHCEntry 14 }

anueFilterPeakHCDropPkts OBJECT-TYPE
    SYNTAX  CounterBasedGauge64
    MAX-ACCESS read-only
    STATUS  current
    DESCRIPTION
        "The peak number of packets dropped by a tool port filter in any
         sampling period since anueFilterStatsResetTime.  Drops may occur at
         a tool port when the rate of traffic directed to the tool port
         exceeds the port's line rate.  Drops occur prior to the actual
         filtering that may be configured for the tool port.

         Drop counts are always 0 for network and dynamic filters."
    -- 1.3.6.1.4.1.32620.1.1.3.9.1.15
    ::= { anueNtoFilterStatsPeakHCEntry 15 }

anueFilterPeakHCDropPktsTime OBJECT-TYPE
    SYNTAX  DateAndTime
    MAX-ACCESS read-only
    STATUS  current
    DESCRIPTION
        "The date and time of the PeakDropPkts event.
         For network and dynamic filters, this field is an empty string."
    -- 1.3.6.1.4.1.32620.1.1.3.9.1.16
    ::= { anueNtoFilterStatsPeakHCEntry 16 }

anueFilterPeakHCUtil OBJECT-TYPE
    SYNTAX  CounterBasedGauge64
    MAX-ACCESS read-only
    STATUS  current
    DESCRIPTION
        "The peak percentage of port bandwidth utilized in
         any sampling period since anueFilterStatsResetTime by
         network port filter receive (incoming) traffic, or tool port
         filter transmit traffic.  For port groups the percentage is
         based on the aggregate link bandwidth.

         Utilization is always 0 for dynamic filters."
    -- 1.3.6.1.4.1.32620.1.1.3.9.1.17
    ::= { anueNtoFilterStatsPeakHCEntry 17 }

anueFilterPeakHCUtilTime OBJECT-TYPE
    SYNTAX  DateAndTime
    MAX-ACCESS read-only
    STATUS  current
    DESCRIPTION
        "The date and time of the PeakUtil event.
         For dynamic filters, this field is an empty string."
    -- 1.3.6.1.4.1.32620.1.1.3.9.1.18
    ::= { anueNtoFilterStatsPeakHCEntry 18 }


-- anueNtoFilterStatsCntModTable
--

anueNtoFilterStatsCntModTable OBJECT-TYPE
    SYNTAX  SEQUENCE OF AnueNtoFilterStatsCntModEntry
    MAX-ACCESS not-accessible
    STATUS  current
    DESCRIPTION
        "This table is the 32-bit version of the 64-bit
         anueNtoFilterStatsCntModHCTable.  Refer to the 64-bit
         table for variable descriptions.
         Unless backward compatibility with SNMPV1 only management
         applications is required, use of the High Capacity (HC)
         64-bit tables is recommended."
    -- 1.3.6.1.4.1.32620.1.1.3.10
    ::= { anueNtoFilter 10 }

anueNtoFilterStatsCntModEntry OBJECT-TYPE
    SYNTAX  AnueNtoFilterStatsCntModEntry
    MAX-ACCESS not-accessible
    STATUS  current
    DESCRIPTION
        "This entry extends anueNtoFilterDefEntry with accumulated
         32-bit filter counters since anueFilterCriteriaModTime."
    INDEX {
        anueFilterType,
        anueFilterNumber
    }
    -- 1.3.6.1.4.1.32620.1.1.3.10.1
    ::= { anueNtoFilterStatsCntModTable 1 }

AnueNtoFilterStatsCntModEntry ::= SEQUENCE {
    anueFilterCntModInOctets  Counter32,
    anueFilterCntModOutOctets Counter32,
    anueFilterCntModInPkts    Counter32,
    anueFilterCntModOutPkts   Counter32,
    anueFilterCntModDropPkts  Counter32,
    anueFilterCntModDropTime  DateAndTime }

anueFilterCntModInOctets OBJECT-TYPE
    SYNTAX  Counter32
    MAX-ACCESS read-only
    STATUS  current
    DESCRIPTION ""
    -- 1.3.6.1.4.1.32620.1.1.3.10.1.3
    ::= { anueNtoFilterStatsCntModEntry 3 }


anueFilterCntModOutOctets OBJECT-TYPE
    SYNTAX  Counter32
    MAX-ACCESS read-only
    STATUS  current
    DESCRIPTION ""
    -- 1.3.6.1.4.1.32620.1.1.3.10.1.4
    ::= { anueNtoFilterStatsCntModEntry 4 }


anueFilterCntModInPkts OBJECT-TYPE
    SYNTAX  Counter32
    MAX-ACCESS read-only
    STATUS  current
    DESCRIPTION ""
    -- 1.3.6.1.4.1.32620.1.1.3.10.1.5
    ::= { anueNtoFilterStatsCntModEntry 5 }


anueFilterCntModOutPkts OBJECT-TYPE
    SYNTAX  Counter32
    MAX-ACCESS read-only
    STATUS  current
    DESCRIPTION ""
    -- 1.3.6.1.4.1.32620.1.1.3.10.1.6
    ::= { anueNtoFilterStatsCntModEntry 6 }


anueFilterCntModDropPkts OBJECT-TYPE
    SYNTAX  Counter32
    MAX-ACCESS read-only
    STATUS  current
    DESCRIPTION ""
    -- 1.3.6.1.4.1.32620.1.1.3.10.1.7
    ::= { anueNtoFilterStatsCntModEntry 7 }

anueFilterCntModDropTime OBJECT-TYPE
    SYNTAX  DateAndTime
    MAX-ACCESS read-only
    STATUS  current
    DESCRIPTION ""
    -- 1.3.6.1.4.1.32620.1.1.3.10.1.8
    ::= { anueNtoFilterStatsCntModEntry 8 }


-- anueNtoFilterStatsCntRstTable
--

anueNtoFilterStatsCntRstTable OBJECT-TYPE
    SYNTAX  SEQUENCE OF AnueNtoFilterStatsCntRstEntry
    MAX-ACCESS not-accessible
    STATUS  current
    DESCRIPTION
        "This table is the 32-bit version of the 64-bit
         anueNtoFilterStatsCntRstHCTable.  Refer to the 64-bit
         table for variable descriptions.
         Unless backward compatibility with SNMPV1 only management
         applications is required, use of the High Capacity (HC)
         64-bit tables is recommended."
    -- 1.3.6.1.4.1.32620.1.1.3.11
    ::= { anueNtoFilter 11 }

anueNtoFilterStatsCntRstEntry OBJECT-TYPE
    SYNTAX  AnueNtoFilterStatsCntRstEntry
    MAX-ACCESS not-accessible
    STATUS  current
    DESCRIPTION
        "This entry extends anueNtoFilterDefEntry with accumulated
         32-bit filter counters since anueFilterStatsResetTime."
    INDEX {
        anueFilterType,
        anueFilterNumber
    }
    -- 1.3.6.1.4.1.32620.1.1.3.11.1
    ::= { anueNtoFilterStatsCntRstTable 1 }

AnueNtoFilterStatsCntRstEntry ::= SEQUENCE {
    anueFilterCntRstInOctets  Counter32,
    anueFilterCntRstOutOctets Counter32,
    anueFilterCntRstInPkts    Counter32,
    anueFilterCntRstOutPkts   Counter32,
    anueFilterCntRstDropPkts  Counter32,
    anueFilterCntRstDropTime  DateAndTime }

anueFilterCntRstInOctets OBJECT-TYPE
    SYNTAX  Counter32
    MAX-ACCESS read-only
    STATUS  current
    DESCRIPTION ""
    -- 1.3.6.1.4.1.32620.1.1.3.11.1.3
    ::= { anueNtoFilterStatsCntRstEntry 3 }


anueFilterCntRstOutOctets OBJECT-TYPE
    SYNTAX  Counter32
    MAX-ACCESS read-only
    STATUS  current
    DESCRIPTION ""
    -- 1.3.6.1.4.1.32620.1.1.3.11.1.4
    ::= { anueNtoFilterStatsCntRstEntry 4 }


anueFilterCntRstInPkts OBJECT-TYPE
    SYNTAX  Counter32
    MAX-ACCESS read-only
    STATUS  current
    DESCRIPTION ""
    -- 1.3.6.1.4.1.32620.1.1.3.11.1.5
    ::= { anueNtoFilterStatsCntRstEntry 5 }


anueFilterCntRstOutPkts OBJECT-TYPE
    SYNTAX  Counter32
    MAX-ACCESS read-only
    STATUS  current
    DESCRIPTION ""
    -- 1.3.6.1.4.1.32620.1.1.3.11.1.6
    ::= { anueNtoFilterStatsCntRstEntry 6 }


anueFilterCntRstDropPkts OBJECT-TYPE
    SYNTAX  Counter32
    MAX-ACCESS read-only
    STATUS  current
    DESCRIPTION ""
    -- 1.3.6.1.4.1.32620.1.1.3.11.1.7
    ::= { anueNtoFilterStatsCntRstEntry 7 }

anueFilterCntRstDropTime OBJECT-TYPE
    SYNTAX  DateAndTime
    MAX-ACCESS read-only
    STATUS  current
    DESCRIPTION ""
    -- 1.3.6.1.4.1.32620.1.1.3.11.1.8
    ::= { anueNtoFilterStatsCntRstEntry 8 }

-- anueNtoFilterStatsCurTable
--

anueNtoFilterStatsCurTable OBJECT-TYPE
    SYNTAX  SEQUENCE OF AnueNtoFilterStatsCurEntry
    MAX-ACCESS not-accessible
    STATUS  current
    DESCRIPTION
        "This table is the 32-bit version of the 64-bit
         anueNtoFilterStatsCurHCTable.  Refer to the 64-bit
         table for variable descriptions.
         Unless backward compatibility with SNMPV1 only management
         applications is required, use of the High Capacity (HC)
         64-bit tables is recommended."
    -- 1.3.6.1.4.1.32620.1.1.3.12
    ::= { anueNtoFilter 12 }

anueNtoFilterStatsCurEntry OBJECT-TYPE
    SYNTAX  AnueNtoFilterStatsCurEntry
    MAX-ACCESS not-accessible
    STATUS  current
    DESCRIPTION
        "This entry extends anueNtoFilterDefEntry with
         32-bit filter statistics that model counts collected
         in the current (most recent) sampling period."
    INDEX {
        anueFilterType,
        anueFilterNumber
    }
    -- 1.3.6.1.4.1.32620.1.1.3.12.1
    ::= { anueNtoFilterStatsCurTable 1 }

AnueNtoFilterStatsCurEntry ::= SEQUENCE {
    anueFilterCurInOctets   Gauge32,
    anueFilterCurOutOctets  Gauge32,
    anueFilterCurRateOctets Gauge32,
    anueFilterCurInPkts     Gauge32,
    anueFilterCurOutPkts    Gauge32,
    anueFilterCurRatePkts   Gauge32,
    anueFilterCurDropPkts   Gauge32,
    anueFilterCurUtil       Gauge32 }

anueFilterCurInOctets OBJECT-TYPE
    SYNTAX  Gauge32
    MAX-ACCESS read-only
    STATUS  current
    DESCRIPTION ""
    -- 1.3.6.1.4.1.32620.1.1.3.12.1.3
    ::= { anueNtoFilterStatsCurEntry 3 }


anueFilterCurOutOctets OBJECT-TYPE
    SYNTAX  Gauge32
    MAX-ACCESS read-only
    STATUS  current
    DESCRIPTION ""
    -- 1.3.6.1.4.1.32620.1.1.3.12.1.4
    ::= { anueNtoFilterStatsCurEntry 4 }

anueFilterCurRateOctets OBJECT-TYPE
    SYNTAX  Gauge32
    MAX-ACCESS read-only
    STATUS  current
    DESCRIPTION ""
    -- 1.3.6.1.4.1.32620.1.1.3.12.1.5
    ::= { anueNtoFilterStatsCurEntry 5 }


anueFilterCurInPkts OBJECT-TYPE
    SYNTAX  Gauge32
    MAX-ACCESS read-only
    STATUS  current
    DESCRIPTION ""
    -- 1.3.6.1.4.1.32620.1.1.3.12.1.6
    ::= { anueNtoFilterStatsCurEntry 6 }


anueFilterCurOutPkts OBJECT-TYPE
    SYNTAX  Gauge32
    MAX-ACCESS read-only
    STATUS  current
    DESCRIPTION ""
    -- 1.3.6.1.4.1.32620.1.1.3.12.1.7
    ::= { anueNtoFilterStatsCurEntry 7 }

anueFilterCurRatePkts OBJECT-TYPE
    SYNTAX  Gauge32
    MAX-ACCESS read-only
    STATUS  current
    DESCRIPTION ""
    -- 1.3.6.1.4.1.32620.1.1.3.12.1.8
    ::= { anueNtoFilterStatsCurEntry 8 }

anueFilterCurDropPkts OBJECT-TYPE
    SYNTAX  Gauge32
    MAX-ACCESS read-only
    STATUS  current
    DESCRIPTION ""
    -- 1.3.6.1.4.1.32620.1.1.3.12.1.9
    ::= { anueNtoFilterStatsCurEntry 9 }

anueFilterCurUtil OBJECT-TYPE
    SYNTAX  Gauge32
    MAX-ACCESS read-only
    STATUS  current
    DESCRIPTION ""
    -- 1.3.6.1.4.1.32620.1.1.3.12.1.10
    ::= { anueNtoFilterStatsCurEntry 10 }

-- anueNtoFilterStatsAvgTable
--

anueNtoFilterStatsAvgTable OBJECT-TYPE
    SYNTAX  SEQUENCE OF AnueNtoFilterStatsAvgEntry
    MAX-ACCESS not-accessible
    STATUS  current
    DESCRIPTION
        "This table is the 32-bit version of the 64-bit
         anueNtoFilterStatsAvgHCTable.  Refer to the 64-bit
         table for variable descriptions.
         Unless backward compatibility with SNMPV1 only management
         applications is required, use of the High Capacity (HC)
         64-bit tables is recommended."
    -- 1.3.6.1.4.1.32620.1.1.3.13
    ::= { anueNtoFilter 13 }

anueNtoFilterStatsAvgEntry OBJECT-TYPE
    SYNTAX  AnueNtoFilterStatsAvgEntry
    MAX-ACCESS not-accessible
    STATUS  current
    DESCRIPTION
        "This entry extends anueNtoFilterDefEntry with
         32-bit filter statistics that model the average of
         counts collected in each sampling period since
         anueFilterStatsResetTime."
    INDEX {
        anueFilterType,
        anueFilterNumber
    }
    -- 1.3.6.1.4.1.32620.1.1.3.13.1
    ::= { anueNtoFilterStatsAvgTable 1 }

AnueNtoFilterStatsAvgEntry ::= SEQUENCE {
    anueFilterAvgInOctets   Gauge32,
    anueFilterAvgOutOctets  Gauge32,
    anueFilterAvgRateOctets Gauge32,
    anueFilterAvgInPkts     Gauge32,
    anueFilterAvgOutPkts    Gauge32,
    anueFilterAvgRatePkts   Gauge32,
    anueFilterAvgDropPkts   Gauge32,
    anueFilterAvgUtil       Gauge32 }

anueFilterAvgInOctets OBJECT-TYPE
    SYNTAX  Gauge32
    MAX-ACCESS read-only
    STATUS  current
    DESCRIPTION ""
    -- 1.3.6.1.4.1.32620.1.1.3.13.1.3
    ::= { anueNtoFilterStatsAvgEntry 3 }


anueFilterAvgOutOctets OBJECT-TYPE
    SYNTAX  Gauge32
    MAX-ACCESS read-only
    STATUS  current
    DESCRIPTION ""
    -- 1.3.6.1.4.1.32620.1.1.3.13.1.4
    ::= { anueNtoFilterStatsAvgEntry 4 }

anueFilterAvgRateOctets OBJECT-TYPE
    SYNTAX  Gauge32
    MAX-ACCESS read-only
    STATUS  current
    DESCRIPTION ""
    -- 1.3.6.1.4.1.32620.1.1.3.13.1.5
    ::= { anueNtoFilterStatsAvgEntry 5 }


anueFilterAvgInPkts OBJECT-TYPE
    SYNTAX  Gauge32
    MAX-ACCESS read-only
    STATUS  current
    DESCRIPTION ""
    -- 1.3.6.1.4.1.32620.1.1.3.13.1.6
    ::= { anueNtoFilterStatsAvgEntry 6 }


anueFilterAvgOutPkts OBJECT-TYPE
    SYNTAX  Gauge32
    MAX-ACCESS read-only
    STATUS  current
    DESCRIPTION ""
    -- 1.3.6.1.4.1.32620.1.1.3.13.1.7
    ::= { anueNtoFilterStatsAvgEntry 7 }

anueFilterAvgRatePkts OBJECT-TYPE
    SYNTAX  Gauge32
    MAX-ACCESS read-only
    STATUS  current
    DESCRIPTION ""
    -- 1.3.6.1.4.1.32620.1.1.3.13.1.8
    ::= { anueNtoFilterStatsAvgEntry 8 }

anueFilterAvgDropPkts OBJECT-TYPE
    SYNTAX  Gauge32
    MAX-ACCESS read-only
    STATUS  current
    DESCRIPTION ""
    -- 1.3.6.1.4.1.32620.1.1.3.13.1.9
    ::= { anueNtoFilterStatsAvgEntry 9 }

anueFilterAvgUtil OBJECT-TYPE
    SYNTAX  Gauge32
    MAX-ACCESS read-only
    STATUS  current
    DESCRIPTION ""
    -- 1.3.6.1.4.1.32620.1.1.3.13.1.10
    ::= { anueNtoFilterStatsAvgEntry 10 }

-- anueNtoFilterStatsPeakTable
--

anueNtoFilterStatsPeakTable OBJECT-TYPE
    SYNTAX  SEQUENCE OF AnueNtoFilterStatsPeakEntry
    MAX-ACCESS not-accessible
    STATUS  current
    DESCRIPTION
        "This table is the 32-bit version of the 64-bit
         anueNtoFilterStatsPeakHCTable.  Refer to the 64-bit
         table for variable descriptions.
         Unless backward compatibility with SNMPV1 only management
         applications is required, use of the High Capacity (HC)
         64-bit tables is recommended."
    -- 1.3.6.1.4.1.32620.1.1.3.14
    ::= { anueNtoFilter 14 }

anueNtoFilterStatsPeakEntry OBJECT-TYPE
    SYNTAX  AnueNtoFilterStatsPeakEntry
    MAX-ACCESS not-accessible
    STATUS  current
    DESCRIPTION
        "This entry extends anueNtoFilterDefEntry with
         32-bit filter statistics that model the peak count
         (largest value) collected in any sampling period since
         anueFilterStatsResetTime."
    INDEX {
        anueFilterType,
        anueFilterNumber
    }
    -- 1.3.6.1.4.1.32620.1.1.3.14.1
    ::= { anueNtoFilterStatsPeakTable 1 }

AnueNtoFilterStatsPeakEntry ::= SEQUENCE {
    anueFilterPeakInOctets       Gauge32,
    anueFilterPeakInOctetsTime   DateAndTime,
    anueFilterPeakOutOctets      Gauge32,
    anueFilterPeakOutOctetsTime  DateAndTime,
    anueFilterPeakRateOctets     Gauge32,
    anueFilterPeakRateOctetsTime DateAndTime,
    anueFilterPeakInPkts         Gauge32,
    anueFilterPeakInPktsTime     DateAndTime,
    anueFilterPeakOutPkts        Gauge32,
    anueFilterPeakOutPktsTime    DateAndTime,
    anueFilterPeakRatePkts       Gauge32,
    anueFilterPeakRatePktsTime   DateAndTime,
    anueFilterPeakDropPkts       Gauge32,
    anueFilterPeakDropPktsTime   DateAndTime,
    anueFilterPeakUtil           Gauge32,
    anueFilterPeakUtilTime       DateAndTime }

anueFilterPeakInOctets OBJECT-TYPE
    SYNTAX  Gauge32
    MAX-ACCESS read-only
    STATUS  current
    DESCRIPTION ""
    -- 1.3.6.1.4.1.32620.1.1.3.14.1.3
    ::= { anueNtoFilterStatsPeakEntry 3 }

anueFilterPeakInOctetsTime OBJECT-TYPE
    SYNTAX  DateAndTime
    MAX-ACCESS read-only
    STATUS  current
    DESCRIPTION ""
    -- 1.3.6.1.4.1.32620.1.1.3.14.1.4
    ::= { anueNtoFilterStatsPeakEntry 4 }

anueFilterPeakOutOctets OBJECT-TYPE
    SYNTAX  Gauge32
    MAX-ACCESS read-only
    STATUS  current
    DESCRIPTION ""
    -- 1.3.6.1.4.1.32620.1.1.3.14.1.5
    ::= { anueNtoFilterStatsPeakEntry 5 }

anueFilterPeakOutOctetsTime OBJECT-TYPE
    SYNTAX  DateAndTime
    MAX-ACCESS read-only
    STATUS  current
    DESCRIPTION ""
    -- 1.3.6.1.4.1.32620.1.1.3.14.1.6
    ::= { anueNtoFilterStatsPeakEntry 6 }

anueFilterPeakRateOctets OBJECT-TYPE
    SYNTAX  Gauge32
    MAX-ACCESS read-only
    STATUS  current
    DESCRIPTION ""
    -- 1.3.6.1.4.1.32620.1.1.3.14.1.7
    ::= { anueNtoFilterStatsPeakEntry 7 }

anueFilterPeakRateOctetsTime OBJECT-TYPE
    SYNTAX  DateAndTime
    MAX-ACCESS read-only
    STATUS  current
    DESCRIPTION ""
    -- 1.3.6.1.4.1.32620.1.1.3.14.1.8
    ::= { anueNtoFilterStatsPeakEntry 8 }

anueFilterPeakInPkts OBJECT-TYPE
    SYNTAX  Gauge32
    MAX-ACCESS read-only
    STATUS  current
    DESCRIPTION ""
    -- 1.3.6.1.4.1.32620.1.1.3.14.1.9
    ::= { anueNtoFilterStatsPeakEntry 9 }

anueFilterPeakInPktsTime OBJECT-TYPE
    SYNTAX  DateAndTime
    MAX-ACCESS read-only
    STATUS  current
    DESCRIPTION ""
    -- 1.3.6.1.4.1.32620.1.1.3.14.1.10
    ::= { anueNtoFilterStatsPeakEntry 10 }

anueFilterPeakOutPkts OBJECT-TYPE
    SYNTAX  Gauge32
    MAX-ACCESS read-only
    STATUS  current
    DESCRIPTION ""
    -- 1.3.6.1.4.1.32620.1.1.3.14.1.11
    ::= { anueNtoFilterStatsPeakEntry 11 }

anueFilterPeakOutPktsTime OBJECT-TYPE
    SYNTAX  DateAndTime
    MAX-ACCESS read-only
    STATUS  current
    DESCRIPTION ""
    -- 1.3.6.1.4.1.32620.1.1.3.14.1.12
    ::= { anueNtoFilterStatsPeakEntry 12 }

anueFilterPeakRatePkts OBJECT-TYPE
    SYNTAX  Gauge32
    MAX-ACCESS read-only
    STATUS  current
    DESCRIPTION ""
    -- 1.3.6.1.4.1.32620.1.1.3.14.1.13
    ::= { anueNtoFilterStatsPeakEntry 13 }

anueFilterPeakRatePktsTime OBJECT-TYPE
    SYNTAX  DateAndTime
    MAX-ACCESS read-only
    STATUS  current
    DESCRIPTION ""
    -- 1.3.6.1.4.1.32620.1.1.3.14.1.14
    ::= { anueNtoFilterStatsPeakEntry 14 }

anueFilterPeakDropPkts OBJECT-TYPE
    SYNTAX  Gauge32
    MAX-ACCESS read-only
    STATUS  current
    DESCRIPTION ""
    -- 1.3.6.1.4.1.32620.1.1.3.14.1.15
    ::= { anueNtoFilterStatsPeakEntry 15 }

anueFilterPeakDropPktsTime OBJECT-TYPE
    SYNTAX  DateAndTime
    MAX-ACCESS read-only
    STATUS  current
    DESCRIPTION ""
    -- 1.3.6.1.4.1.32620.1.1.3.14.1.16
    ::= { anueNtoFilterStatsPeakEntry 16 }

anueFilterPeakUtil OBJECT-TYPE
    SYNTAX  Gauge32
    MAX-ACCESS read-only
    STATUS  current
    DESCRIPTION ""
    -- 1.3.6.1.4.1.32620.1.1.3.14.1.17
    ::= { anueNtoFilterStatsPeakEntry 17 }

anueFilterPeakUtilTime OBJECT-TYPE
    SYNTAX  DateAndTime
    MAX-ACCESS read-only
    STATUS  current
    DESCRIPTION ""
    -- 1.3.6.1.4.1.32620.1.1.3.14.1.18
    ::= { anueNtoFilterStatsPeakEntry 18 }


anueFilterDefLastChange OBJECT-TYPE
    SYNTAX TimeTicks
    MAX-ACCESS read-only
    STATUS current
    DESCRIPTION
        "The value of sysUpTime at the time of the last creation or
        deletion of an entry in the anueNtoFilterDefTable. If the number of
        entries has been unchanged since the last re-initialization
        of the local network management subsystem, then this object
        contains a zero value."
    -- 1.3.6.1.4.1.32620.1.1.3.15
    ::= { anueNtoFilter 15}


anueFilterConnLastChange OBJECT-TYPE
    SYNTAX TimeTicks
    MAX-ACCESS read-only
    STATUS current
    DESCRIPTION
        "The value of sysUpTime at the time of the last creation or
        deletion of an entry in the anueNtoFilterConnTable.
        If the number of
        entries has been unchanged since the last re-initialization
        of the local network management subsystem, then this object
        contains a zero value."
    -- 1.3.6.1.4.1.32620.1.1.3.16
    ::= { anueNtoFilter 16}


-- GSC filter entries begin here.

-- anueNtoFilterStatsGscSessTable
--

anueNtoFilterStatsGscSessTable OBJECT-TYPE
    SYNTAX  SEQUENCE OF AnueNtoFilterStatsGscSessEntry
    MAX-ACCESS not-accessible
    STATUS  current
    DESCRIPTION
        "A table of statistics entries that model the GSC filter counts
        collected in the current (most recent) sampling period.
        The table values map to the current counts displayed in the
        GSC Control Panel's filter statistics windows."
    --  room for expansion between NTO and GSC  --
    -- 1.3.6.1.4.1.32620.1.1.3.100
    ::= { anueNtoFilter 100 }

anueNtoFilterStatsGscSessEntry OBJECT-TYPE
    SYNTAX  AnueNtoFilterStatsGscSessEntry
    MAX-ACCESS not-accessible
    STATUS  current
    DESCRIPTION
        "This entry extends anueNtoFilterDefEntry with 64-bit filter
         counters."
    INDEX {
        anueFilterType,
        anueFilterNumber
    }

    -- 1.3.6.1.4.1.32620.1.1.3.100.1
    ::= { anueNtoFilterStatsGscSessTable 1 }

AnueNtoFilterStatsGscSessEntry ::= SEQUENCE {
    anueFilterGscCurDenyGtpV0Sess   Counter64,
    anueFilterGscCurDenyGtpV1Sess   Counter64,
    anueFilterGscCurDenyGtpV2Sess   Counter64,
    anueFilterGscCurDenyGtpTotSess  Counter64,
    anueFilterGscAvgDenyGtpV0Sess   Counter64,
    anueFilterGscAvgDenyGtpV1Sess   Counter64,
    anueFilterGscAvgDenyGtpV2Sess   Counter64,
    anueFilterGscAvgDenyGtpTotSess  Counter64,
    anueFilterGscPkDenyGtpV0Sess    Counter64,
    anueFilterGscPkDenyGtpV1Sess    Counter64,
    anueFilterGscPkDenyGtpV2Sess    Counter64,
    anueFilterGscPkDenyGtpTotSess   Counter64,
    anueFilterGscPkDenyGtpV0SessT   DateAndTime,
    anueFilterGscPkDenyGtpV1SessT   DateAndTime,
    anueFilterGscPkDenyGtpV2SessT   DateAndTime,
    anueFilterGscPkDenyGtpTotSessT  DateAndTime,
    anueFilterGscTotOversizePktsTx  Counter64,
    anueFilterGscCurOversizePktsTx  Counter64,
    anueFilterGscAvgOversizePktsTx  Counter64,
    anueFilterGscPkOversizePktsTx   Counter64,
    anueFilterGscPkOversizePktsTxT  DateAndTime,
    anueFilterGscTotDroppedPkts     Counter64,
    anueFilterGscCurDroppedPkts     Counter64,
    anueFilterGscAvgDroppedPkts     Counter64,
    anueFilterGscPkDroppedPkts      Counter64,
    anueFilterGscPkDroppedPktsT     DateAndTime,
    anueFilterGscTotDroppedBytes    Counter64,
    anueFilterGscCurDroppedBytes    Counter64,
    anueFilterGscAvgDroppedBytes    Counter64,
    anueFilterGscPkDroppedBytes     Counter64,
    anueFilterGscPkDroppedBytesT    DateAndTime }

anueFilterGscCurDenyGtpV0Sess OBJECT-TYPE
    SYNTAX  Counter64
    MAX-ACCESS read-only
    STATUS  current
    DESCRIPTION
        ""
    -- 1.3.6.1.4.1.32620.1.1.3.100.1.3
    ::= { anueNtoFilterStatsGscSessEntry 3 }


anueFilterGscCurDenyGtpV1Sess OBJECT-TYPE
    SYNTAX  Counter64
    MAX-ACCESS read-only
    STATUS  current
    DESCRIPTION
        ""
    -- 1.3.6.1.4.1.32620.1.1.3.100.1.4
    ::= { anueNtoFilterStatsGscSessEntry 4 }


anueFilterGscCurDenyGtpV2Sess OBJECT-TYPE
    SYNTAX  Counter64
    MAX-ACCESS read-only
    STATUS  current
    DESCRIPTION
        ""
    -- 1.3.6.1.4.1.32620.1.1.3.100.1.5
    ::= { anueNtoFilterStatsGscSessEntry 5 }


anueFilterGscCurDenyGtpTotSess OBJECT-TYPE
    SYNTAX  Counter64
    MAX-ACCESS read-only
    STATUS  current
    DESCRIPTION
        ""
    -- 1.3.6.1.4.1.32620.1.1.3.100.1.6
    ::= { anueNtoFilterStatsGscSessEntry 6 }


anueFilterGscAvgDenyGtpV0Sess OBJECT-TYPE
    SYNTAX  Counter64
    MAX-ACCESS read-only
    STATUS  current
    DESCRIPTION
        ""
    -- 1.3.6.1.4.1.32620.1.1.3.100.1.7
    ::= { anueNtoFilterStatsGscSessEntry 7 }


anueFilterGscAvgDenyGtpV1Sess OBJECT-TYPE
    SYNTAX  Counter64
    MAX-ACCESS read-only
    STATUS  current
    DESCRIPTION
        ""
    -- 1.3.6.1.4.1.32620.1.1.3.100.1.8
    ::= { anueNtoFilterStatsGscSessEntry 8 }


anueFilterGscAvgDenyGtpV2Sess OBJECT-TYPE
    SYNTAX  Counter64
    MAX-ACCESS read-only
    STATUS  current
    DESCRIPTION
        ""
    -- 1.3.6.1.4.1.32620.1.1.3.100.1.9
    ::= { anueNtoFilterStatsGscSessEntry 9 }


anueFilterGscAvgDenyGtpTotSess OBJECT-TYPE
    SYNTAX  Counter64
    MAX-ACCESS read-only
    STATUS  current
    DESCRIPTION
        ""
    -- 1.3.6.1.4.1.32620.1.1.3.100.1.10
    ::= { anueNtoFilterStatsGscSessEntry 10 }


anueFilterGscPkDenyGtpV0Sess OBJECT-TYPE
    SYNTAX  Counter64
    MAX-ACCESS read-only
    STATUS  current
    DESCRIPTION
        ""
    -- 1.3.6.1.4.1.32620.1.1.3.100.1.11
    ::= { anueNtoFilterStatsGscSessEntry 11 }


anueFilterGscPkDenyGtpV1Sess OBJECT-TYPE
    SYNTAX  Counter64
    MAX-ACCESS read-only
    STATUS  current
    DESCRIPTION
        ""
    -- 1.3.6.1.4.1.32620.1.1.3.100.1.12
    ::= { anueNtoFilterStatsGscSessEntry 12 }


anueFilterGscPkDenyGtpV2Sess OBJECT-TYPE
    SYNTAX  Counter64
    MAX-ACCESS read-only
    STATUS  current
    DESCRIPTION
        ""
    -- 1.3.6.1.4.1.32620.1.1.3.100.1.13
    ::= { anueNtoFilterStatsGscSessEntry 13 }


anueFilterGscPkDenyGtpTotSess OBJECT-TYPE
    SYNTAX  Counter64
    MAX-ACCESS read-only
    STATUS  current
    DESCRIPTION
        ""
    -- 1.3.6.1.4.1.32620.1.1.3.100.1.14
    ::= { anueNtoFilterStatsGscSessEntry 14 }


anueFilterGscPkDenyGtpV0SessT OBJECT-TYPE
    SYNTAX  DateAndTime
    MAX-ACCESS read-only
    STATUS  current
    DESCRIPTION
        ""
    -- 1.3.6.1.4.1.32620.1.1.3.100.1.15
    ::= { anueNtoFilterStatsGscSessEntry 15 }


anueFilterGscPkDenyGtpV1SessT OBJECT-TYPE
    SYNTAX  DateAndTime
    MAX-ACCESS read-only
    STATUS  current
    DESCRIPTION
        ""
    -- 1.3.6.1.4.1.32620.1.1.3.100.1.16
    ::= { anueNtoFilterStatsGscSessEntry 16 }


anueFilterGscPkDenyGtpV2SessT OBJECT-TYPE
    SYNTAX  DateAndTime
    MAX-ACCESS read-only
    STATUS  current
    DESCRIPTION
        ""
    -- 1.3.6.1.4.1.32620.1.1.3.100.1.17
    ::= { anueNtoFilterStatsGscSessEntry 17 }


anueFilterGscPkDenyGtpTotSessT OBJECT-TYPE
    SYNTAX  DateAndTime
    MAX-ACCESS read-only
    STATUS  current
    DESCRIPTION
        ""
    -- 1.3.6.1.4.1.32620.1.1.3.100.1.18
    ::= { anueNtoFilterStatsGscSessEntry 18 }


anueFilterGscTotOversizePktsTx OBJECT-TYPE
    SYNTAX  Counter64
    MAX-ACCESS read-only
    STATUS  current
    DESCRIPTION
        ""
    -- 1.3.6.1.4.1.32620.1.1.3.100.1.19
    ::= { anueNtoFilterStatsGscSessEntry 19 }


anueFilterGscCurOversizePktsTx OBJECT-TYPE
    SYNTAX  Counter64
    MAX-ACCESS read-only
    STATUS  current
    DESCRIPTION
        ""
    -- 1.3.6.1.4.1.32620.1.1.3.100.1.20
    ::= { anueNtoFilterStatsGscSessEntry 20 }


anueFilterGscAvgOversizePktsTx OBJECT-TYPE
    SYNTAX  Counter64
    MAX-ACCESS read-only
    STATUS  current
    DESCRIPTION
        ""
    -- 1.3.6.1.4.1.32620.1.1.3.100.1.21
    ::= { anueNtoFilterStatsGscSessEntry 21 }


anueFilterGscPkOversizePktsTx OBJECT-TYPE
    SYNTAX  Counter64
    MAX-ACCESS read-only
    STATUS  current
    DESCRIPTION
        ""
    -- 1.3.6.1.4.1.32620.1.1.3.100.1.22
    ::= { anueNtoFilterStatsGscSessEntry 22 }


anueFilterGscPkOversizePktsTxT OBJECT-TYPE
    SYNTAX  DateAndTime
    MAX-ACCESS read-only
    STATUS  current
    DESCRIPTION
        ""
    -- 1.3.6.1.4.1.32620.1.1.3.100.1.23
    ::= { anueNtoFilterStatsGscSessEntry 23 }


anueFilterGscTotDroppedPkts OBJECT-TYPE
    SYNTAX  Counter64
    MAX-ACCESS read-only
    STATUS  current
    DESCRIPTION
        ""
    -- 1.3.6.1.4.1.32620.1.1.3.100.1.24
    ::= { anueNtoFilterStatsGscSessEntry 24 }


anueFilterGscCurDroppedPkts OBJECT-TYPE
    SYNTAX  Counter64
    MAX-ACCESS read-only
    STATUS  current
    DESCRIPTION
        ""
    -- 1.3.6.1.4.1.32620.1.1.3.100.1.25
    ::= { anueNtoFilterStatsGscSessEntry 25 }


anueFilterGscAvgDroppedPkts OBJECT-TYPE
    SYNTAX  Counter64
    MAX-ACCESS read-only
    STATUS  current
    DESCRIPTION
        ""
    -- 1.3.6.1.4.1.32620.1.1.3.100.1.26
    ::= { anueNtoFilterStatsGscSessEntry 26 }


anueFilterGscPkDroppedPkts OBJECT-TYPE
    SYNTAX  Counter64
    MAX-ACCESS read-only
    STATUS  current
    DESCRIPTION
        ""
    -- 1.3.6.1.4.1.32620.1.1.3.100.1.27
    ::= { anueNtoFilterStatsGscSessEntry 27 }


anueFilterGscPkDroppedPktsT OBJECT-TYPE
    SYNTAX  DateAndTime
    MAX-ACCESS read-only
    STATUS  current
    DESCRIPTION
        ""
    -- 1.3.6.1.4.1.32620.1.1.3.100.1.28
    ::= { anueNtoFilterStatsGscSessEntry 28 }


anueFilterGscTotDroppedBytes OBJECT-TYPE
    SYNTAX  Counter64
    MAX-ACCESS read-only
    STATUS  current
    DESCRIPTION
        ""
    -- 1.3.6.1.4.1.32620.1.1.3.100.1.29
    ::= { anueNtoFilterStatsGscSessEntry 29 }


anueFilterGscCurDroppedBytes OBJECT-TYPE
    SYNTAX  Counter64
    MAX-ACCESS read-only
    STATUS  current
    DESCRIPTION
        ""
    -- 1.3.6.1.4.1.32620.1.1.3.100.1.30
    ::= { anueNtoFilterStatsGscSessEntry 30 }


anueFilterGscAvgDroppedBytes OBJECT-TYPE
    SYNTAX  Counter64
    MAX-ACCESS read-only
    STATUS  current
    DESCRIPTION
        ""
    -- 1.3.6.1.4.1.32620.1.1.3.100.1.31
    ::= { anueNtoFilterStatsGscSessEntry 31 }


anueFilterGscPkDroppedBytes OBJECT-TYPE
    SYNTAX  Counter64
    MAX-ACCESS read-only
    STATUS  current
    DESCRIPTION
        ""
    -- 1.3.6.1.4.1.32620.1.1.3.100.1.32
    ::= { anueNtoFilterStatsGscSessEntry 32 }


anueFilterGscPkDroppedBytesT OBJECT-TYPE
    SYNTAX  DateAndTime
    MAX-ACCESS read-only
    STATUS  current
    DESCRIPTION
        ""
    -- 1.3.6.1.4.1.32620.1.1.3.100.1.33
    ::= { anueNtoFilterStatsGscSessEntry 33 }


-- anueNtoFilterStatsGscTable
--

anueNtoFilterStatsGscTable OBJECT-TYPE
    SYNTAX  SEQUENCE OF AnueNtoFilterStatsGscEntry
    MAX-ACCESS not-accessible
    STATUS  current
    DESCRIPTION
        "A table of statistics entries that model the GSC filter packet rates
        collected in the current (most recent) sampling period.
        The table values map to the current counts displayed in the
        GSC Control Panel's filter statistics windows."
    -- 1.3.6.1.4.1.32620.1.1.3.101
    ::= { anueNtoFilter 101 }

anueNtoFilterStatsGscEntry OBJECT-TYPE
    SYNTAX  AnueNtoFilterStatsGscEntry
    MAX-ACCESS not-accessible
    STATUS  current
    DESCRIPTION
        "This entry extends anueNtoFilterDefEntry with 64-bit filter
        counters."
    INDEX {
        anueFilterType,
        anueFilterNumber,
        anueFilterGTPPktType }
    -- 1.3.6.1.4.1.32620.1.1.3.101.1
    ::= { anueNtoFilterStatsGscTable 1 }

AnueNtoFilterStatsGscEntry ::= SEQUENCE {
    anueFilterCurGscPktsRate      CounterBasedGauge64,
    anueFilterAvgGscPktsRate      CounterBasedGauge64,
    anueFilterPeakGscPktsRate     CounterBasedGauge64,
    anueFilterPeakTimeGscPktsRate DateAndTime,
    anueFilterGTPPktType          DisplayString }


anueFilterCurGscPktsRate OBJECT-TYPE
    SYNTAX  CounterBasedGauge64
    MAX-ACCESS read-only
    STATUS  current
    DESCRIPTION
        "The current rate of GTP packets received in the current (most recent) sampling period.

        This field applies to GSC network and tool port/port group filters.
        For dynamic filters, the value for this field will be 0."
    -- 1.3.6.1.4.1.32620.1.1.3.101.1.3
    ::= { anueNtoFilterStatsGscEntry 3 }

anueFilterAvgGscPktsRate OBJECT-TYPE
    SYNTAX  CounterBasedGauge64
    MAX-ACCESS read-only
    STATUS  current
    DESCRIPTION
        "The average rate of GTP packets received in the current (most recent) sampling period.

        This field applies to GSC network and tool port/port group filters.
        For dynamic filters, the value for this field will be 0."
    -- 1.3.6.1.4.1.32620.1.1.3.101.1.4
    ::= { anueNtoFilterStatsGscEntry 4 }

anueFilterPeakGscPktsRate OBJECT-TYPE
    SYNTAX  CounterBasedGauge64
    MAX-ACCESS read-only
    STATUS  current
    DESCRIPTION
        "The peak rate of GTP packets received in the current (most recent) sampling period.

        This field applies to GSC network and tool port/port group filters.
        For dynamic filters, the value for this field will be 0."
    -- 1.3.6.1.4.1.32620.1.1.3.101.1.5
    ::= { anueNtoFilterStatsGscEntry 5 }

anueFilterPeakTimeGscPktsRate OBJECT-TYPE
    SYNTAX  DateAndTime
    MAX-ACCESS read-only
    STATUS  current
    DESCRIPTION
        "The time when the peak rate of GTP packets received in the current (most recent)
        sampling period was hit.

        This field applies to GSC network and tool port/port group filters.
        For dynamic filters, the value for this field will be 0."
    -- 1.3.6.1.4.1.32620.1.1.3.101.1.6
    ::= { anueNtoFilterStatsGscEntry 6 }

anueFilterGTPPktType OBJECT-TYPE
    SYNTAX  DisplayString
    MAX-ACCESS read-only
    STATUS  current
    DESCRIPTION
        "The type of the GTP packets that are stored in the current row"
    -- 1.3.6.1.4.1.32620.1.1.3.101.1.7
    ::= { anueNtoFilterStatsGscEntry 7 }

-- GSC filter entries end here.



-- anueNtoStage
--

anueNtoStage OBJECT IDENTIFIER
    -- 1.3.6.1.4.1.32620.1.1.4
    ::= { anueNtoObjects 4 }


-- anueNtoStageStripTable
--

anueNtoStageStripTable OBJECT-TYPE
    SYNTAX  SEQUENCE OF AnueNtoStageStripEntry
    MAX-ACCESS not-accessible
    STATUS  current
    DESCRIPTION
        "Table of entries holding detailed statistics for all strip
        stages enabled in all port or port group filters."
    -- 1.3.6.1.4.1.32620.1.1.4.1
    ::= { anueNtoStage 1 }

anueNtoStageStripEntry OBJECT-TYPE
    SYNTAX  AnueNtoStageStripEntry
    MAX-ACCESS not-accessible
    STATUS  current
    DESCRIPTION
        "A specific entry for a single strip stage enabled on a single
        port or port group filter."
    INDEX {
        anueStageStripFilterType,
        anueStageStripFilterNumber,
        anueStageStripFeature }
    -- 1.3.6.1.4.1.32620.1.1.4.1.1
    ::= { anueNtoStageStripTable 1 }

AnueNtoStageStripEntry ::= SEQUENCE {
    anueStageStripFilterType       AnueFilterTypeDT,
    anueStageStripFilterNumber     Integer32,
    anueStageStripFeature          AnueStageType,
    anueStageStripOrder            Integer32,
    anueStageStripType             INTEGER,
    anueStageStripModPkts          Counter64,
    anueStageStripModPktPct        Gauge32,
    anueStageStripErrorPkts        Counter64,
    anueStageStripRstModPkts       Counter64,
    anueStageStripRstModPktPct     Gauge32,
    anueStageStripRstErrorPkts     Counter64,
    anueStageStripAttributes       DisplayString }

anueStageStripFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.1.1.1
    ::= { anueNtoStageStripEntry 1 }

anueStageStripFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.1.1.2
    ::= { anueNtoStageStripEntry 2 }

anueStageStripFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.1.1.3
    ::= { anueNtoStageStripEntry 3 }

anueStageStripOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.1.1.4
    ::= { anueNtoStageStripEntry 4 }

anueStageStripType OBJECT-TYPE
    SYNTAX  INTEGER {
        anueStageStripMplsL3Vpn(1),
        anueStageStripMplsL2VpnPwcwL3Vpn(2),
        anueStageStripMplsL2VpnNoPwcw(3),
        anueStageStripGtp(4),
        anueStageStripVlan(5),
        anueStageStripVntag(6),
        anueStageStripTrailer(7),
        anueStageStripFabricPath(8),
        anueStageStripVxlan(9),
        anueStageStripL2Gre(10),
        anueStageStripErspan(11) }
    MAX-ACCESS read-only
    STATUS  current
    DESCRIPTION
        "Specifies the protocol and/or configuration of stripping for
        this stage.
        Pwcw stands for pseudowire control words.

        anueStageStripMplsL3Vpn(1)              MPLS L3 VPN service
        anueStageStripMplsL2VpnPwcwL3Vpn(2)     MPLS L2 VPN service with
                                                pseudo wire control words or L3 VPN
        anueStageStripMplsL2VpnNoPwcw(3)        MPLS L2 VPN service without
                                                pseudo wire control words
        anueStageStripGtp(4)                    GTP
        anueStageStripVlan(5)                   VLAN
        anueStageStripVntag(6)                  virtual network tag
        anueStageStripTrailer(7)                trailer stripping
        anueStageStripFabricPath(8)             Fabric Path
        anueStageStripVxlan(9)                  VXLAN
        anueStageStripL2Gre(10)                 L2Gre stripping
        anueStageStripErspan(11)                ERSPAN stripping"
    -- 1.3.6.1.4.1.32620.1.1.4.1.1.5
    ::= { anueNtoStageStripEntry 5 }

anueStageStripModPkts OBJECT-TYPE
    SYNTAX  Counter64
    MAX-ACCESS read-only
    STATUS  current
    DESCRIPTION
        "The total number of packets modified by this stage since
        anueFilterCriteriaModTime. On the 7300 platform, this statistic is
            unavailable for VLAN Stripping."
    -- 1.3.6.1.4.1.32620.1.1.4.1.1.6
    ::= { anueNtoStageStripEntry 6 }

anueStageStripModPktPct OBJECT-TYPE
    SYNTAX  Gauge32
    MAX-ACCESS read-only
    STATUS  current
    DESCRIPTION
        "The percentage of packets received by this stage since
        anueFilterCriteriaModTime that have been modified. On the 7300 platform,
            this statistic is unavailable for VLAN Stripping."
    -- 1.3.6.1.4.1.32620.1.1.4.1.1.7
    ::= { anueNtoStageStripEntry 7 }

anueStageStripErrorPkts OBJECT-TYPE
    SYNTAX  Counter64
    MAX-ACCESS read-only
    STATUS  current
    DESCRIPTION
        "The total number of packet transmit errors detected at egress
        since anueFilterCriteriaModTime. The cause of these transmit
        errors is the receipt of MPLS packets that are not of the same
        MPLS service type that was configured when enabling MPLS
        stripping on this port (e.g. with/without pseudowire control
        words).  This statistic applies only to MPLS stripping.  It is
        possible that some MPLS packets of the wrong service type will be
        incorrectly modified (stripped) and passed through successfully
        without being counted here."
    -- 1.3.6.1.4.1.32620.1.1.4.1.1.8
    ::= { anueNtoStageStripEntry 8 }

anueStageStripRstModPkts OBJECT-TYPE
    SYNTAX  Counter64
    MAX-ACCESS read-only
    STATUS  current
    DESCRIPTION
        "The total number of packets modified by this stage since
        anueFilterStatsResetTime.  On the 7300 platform, this statistic is unavailable for
        VLAN Stripping."
    -- 1.3.6.1.4.1.32620.1.1.4.1.1.9
    ::= { anueNtoStageStripEntry 9 }

anueStageStripRstModPktPct OBJECT-TYPE
    SYNTAX  Gauge32
    MAX-ACCESS read-only
    STATUS  current
    DESCRIPTION
        "The percentage of packets received by this stage since
        anueFilterStatsResetTime that have been modified. On the 7300 platform,
            this statistic is unavailable for VLAN Stripping."
    -- 1.3.6.1.4.1.32620.1.1.4.1.1.10
    ::= { anueNtoStageStripEntry 10 }

anueStageStripRstErrorPkts OBJECT-TYPE
    SYNTAX  Counter64
    MAX-ACCESS read-only
    STATUS  current
    DESCRIPTION
        "The total number of packet transmit errors detected at egress
        since anueFilterStatsResetTime. See anueStageStripErrorPkts above
        for a more detailed description of these errors."
    -- 1.3.6.1.4.1.32620.1.1.4.1.1.11
    ::= { anueNtoStageStripEntry 11 }

anueStageStripAttributes OBJECT-TYPE
    SYNTAX  DisplayString
    MAX-ACCESS read-only
    STATUS  current
    DESCRIPTION
        "Shows any additional attributes that the stripping feature may have.
        Is a comma separated string of key-value pairs, where the key is the
        attribute's name."
    -- 1.3.6.1.4.1.32620.1.1.4.1.1.12
    ::= { anueNtoStageStripEntry 12 }


-- anueNtoStageNPErrorTable
--

anueNtoStageNPErrorTable OBJECT-TYPE
    SYNTAX  SEQUENCE OF AnueNtoStageNPErrorEntry
    MAX-ACCESS not-accessible
    STATUS  current
    DESCRIPTION
        "Table of entries holding detailed statistics for all network
        port error stages present in all port or port group filters.
        On NTO 7300 this also contains the Line Card Invalid Packets."
    -- 1.3.6.1.4.1.32620.1.1.4.2
    ::= { anueNtoStage 2 }

anueNtoStageNPErrorEntry OBJECT-TYPE
    SYNTAX  AnueNtoStageNPErrorEntry
    MAX-ACCESS not-accessible
    STATUS  current
    DESCRIPTION
        "A specific entry for a single network port error stage present
        on a single port or port group filter."
    INDEX {
        anueStageNPErrorFilterType,
        anueStageNPErrorFilterNumber,
        anueStageNPErrorFeature }
    -- 1.3.6.1.4.1.32620.1.1.4.2.1
    ::= { anueNtoStageNPErrorTable 1 }

AnueNtoStageNPErrorEntry ::= SEQUENCE {
    anueStageNPErrorFilterType   AnueFilterTypeDT,
    anueStageNPErrorFilterNumber Integer32,
    anueStageNPErrorFeature      AnueStageType,
    anueStageNPErrorOrder        Integer32,
    anueStageNPErrorPkts         Counter64,
    anueStageNPErrorRstPkts      Counter64 }

anueStageNPErrorFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.2.1.1
    ::= { anueNtoStageNPErrorEntry 1 }

anueStageNPErrorFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.2.1.2
    ::= { anueNtoStageNPErrorEntry 2 }

anueStageNPErrorFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.2.1.3
    ::= { anueNtoStageNPErrorEntry 3 }

anueStageNPErrorOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.2.1.4
    ::= { anueNtoStageNPErrorEntry 4 }

anueStageNPErrorPkts OBJECT-TYPE
    SYNTAX  Counter64
    MAX-ACCESS read-only
    STATUS  current
    DESCRIPTION
        "The total number of invalid packets dropped at this stage since
        anueFilterCriteriaModTime."
    -- 1.3.6.1.4.1.32620.1.1.4.2.1.5
    ::= { anueNtoStageNPErrorEntry 5 }

anueStageNPErrorRstPkts OBJECT-TYPE
    SYNTAX  Counter64
    MAX-ACCESS read-only
    STATUS  current
    DESCRIPTION
        "The total number of invalid packets dropped at this stage since
        anueFilterStatsResetTime."
    -- 1.3.6.1.4.1.32620.1.1.4.2.1.6
    ::= { anueNtoStageNPErrorEntry 6 }


-- anueNtoStageDedupTable
--

anueNtoStageDedupTable OBJECT-TYPE
    SYNTAX  SEQUENCE OF AnueNtoStageDedupEntry
    MAX-ACCESS not-accessible
    STATUS  current
    DESCRIPTION
        "Table of entries holding detailed statistics for all dedup
        stages enabled in all port or port group filters."
    -- 1.3.6.1.4.1.32620.1.1.4.3
    ::= { anueNtoStage 3 }

anueNtoStageDedupEntry OBJECT-TYPE
    SYNTAX  AnueNtoStageDedupEntry
    MAX-ACCESS not-accessible
    STATUS  current
    DESCRIPTION
        "A specific entry for a single dedup stage enabled on a single
        port or port group filter."
    INDEX {
        anueStageDedupFilterType,
        anueStageDedupFilterNumber,
        anueStageDedupFeature }
    -- 1.3.6.1.4.1.32620.1.1.4.3.1
    ::= { anueNtoStageDedupTable 1 }

AnueNtoStageDedupEntry ::= SEQUENCE {
    anueStageDedupFilterType       AnueFilterTypeDT,
    anueStageDedupFilterNumber     Integer32,
    anueStageDedupFeature          AnueStageType,
    anueStageDedupOrder            Integer32,
    anueStageDedupType             INTEGER,
    anueStageDedupTimeWindows      Integer32,
    anueStageDedupRmvPkts          Counter64,
    anueStageDedupRmvPktPct        Gauge32,
    anueStageDedupRstRmvPkts       Counter64,
    anueStageDedupRstRmvPktPct     Gauge32 }

anueStageDedupFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.3.1.1
    ::= { anueNtoStageDedupEntry 1 }

anueStageDedupFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.3.1.2
    ::= { anueNtoStageDedupEntry 2 }

anueStageDedupFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.3.1.3
    ::= { anueNtoStageDedupEntry 3 }

anueStageDedupOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.3.1.4
    ::= { anueNtoStageDedupEntry 4 }

anueStageDedupType OBJECT-TYPE
    SYNTAX  INTEGER {
        anueStageDedupNone(1),
        anueStageDedupMac(2),
        anueStageDedupMacVlan(3),
        anueStageDedupMacVlanMpls(4),
        anueStageDedupMacVlanMplsL3(5)
        }
    MAX-ACCESS read-only
    STATUS  current
    DESCRIPTION
        "Specifies what header information is ignored when determining if
        packets are duplicates.

        anueStageDedupNone(1)          no header fields are ignored
        anueStageDedupMac(2)           MAC header fields are ignored
        anueStageDedupMacVlan(3)       MAC and VLAN header fields are
                                       ignored
        anueStageDedupMacVlanMpls(4)   MAC, VLAN, and MPLS header fields
                                       are ignored
        anueStageDedupMacVlanMplsL3(5) The L3 header will be ignored, including IP
                                       source and destination addresses."
    -- 1.3.6.1.4.1.32620.1.1.4.3.1.5
    ::= { anueNtoStageDedupEntry 5 }

anueStageDedupTimeWindows OBJECT-TYPE
    SYNTAX  Integer32
    MAX-ACCESS read-only
    STATUS  current
    DESCRIPTION
        "Specifies the packet arrival time window (in microseconds)
        within which packets may be considered to be duplicates."
    -- 1.3.6.1.4.1.32620.1.1.4.3.1.6
    ::= { anueNtoStageDedupEntry 6 }

anueStageDedupRmvPkts OBJECT-TYPE
    SYNTAX  Counter64
    MAX-ACCESS read-only
    STATUS  current
    DESCRIPTION
        "The total number of duplicate packets removed by this stage
        since anueFilterCriteriaModTime."
    -- 1.3.6.1.4.1.32620.1.1.4.3.1.7
    ::= { anueNtoStageDedupEntry 7 }

anueStageDedupRmvPktPct OBJECT-TYPE
    SYNTAX  Gauge32
    MAX-ACCESS read-only
    STATUS  current
    DESCRIPTION
        "The percentage of packets received by this stage since
        anueFilterCriteriaModTime that have been removed as duplicates."
    -- 1.3.6.1.4.1.32620.1.1.4.3.1.8
    ::= { anueNtoStageDedupEntry 8 }

anueStageDedupRstRmvPkts OBJECT-TYPE
    SYNTAX  Counter64
    MAX-ACCESS read-only
    STATUS  current
    DESCRIPTION
        "The total number of duplicate packets removed by this stage
        since anueFilterStatsResetTime."
    -- 1.3.6.1.4.1.32620.1.1.4.3.1.9
    ::= { anueNtoStageDedupEntry 9 }

anueStageDedupRstRmvPktPct OBJECT-TYPE
    SYNTAX  Gauge32
    MAX-ACCESS read-only
    STATUS  current
    DESCRIPTION
        "The percentage of packets received by this stage since
        anueFilterStatsResetTime that have been removed as duplicates."
    -- 1.3.6.1.4.1.32620.1.1.4.3.1.10
    ::= { anueNtoStageDedupEntry 10 }


-- anueNtoStageTrimTable
--

anueNtoStageTrimTable OBJECT-TYPE
    SYNTAX  SEQUENCE OF AnueNtoStageTrimEntry
    MAX-ACCESS not-accessible
    STATUS  current
    DESCRIPTION
        "Table of entries holding detailed statistics for all trim
        stages enabled in all port or port group filters."
    -- 1.3.6.1.4.1.32620.1.1.4.4
    ::= { anueNtoStage 4 }

anueNtoStageTrimEntry OBJECT-TYPE
    SYNTAX  AnueNtoStageTrimEntry
    MAX-ACCESS not-accessible
    STATUS  current
    DESCRIPTION
        "A specific entry for a single trim stage enabled on a single
        port or port group filter."
    INDEX {
        anueStageTrimFilterType,
        anueStageTrimFilterNumber,
        anueStageTrimFeature }
    -- 1.3.6.1.4.1.32620.1.1.4.4.1
    ::= { anueNtoStageTrimTable 1 }

AnueNtoStageTrimEntry ::= SEQUENCE {
    anueStageTrimFilterType       AnueFilterTypeDT,
    anueStageTrimFilterNumber     Integer32,
    anueStageTrimFeature          AnueStageType,
    anueStageTrimOrder            Integer32,
    anueStageTrimType             INTEGER,
    anueStageTrimRetainOctets     Integer32,
    anueStageTrimModPkts          Counter64,
    anueStageTrimModPktPct        Gauge32,
    anueStageTrimRmvOctets        Counter64,
    anueStageTrimRmvOctetPct      Gauge32,
    anueStageTrimRstModPkts       Counter64,
    anueStageTrimRstModPktPct     Gauge32,
    anueStageTrimRstRmvOctets     Counter64,
    anueStageTrimRstRmvOctetPct   Gauge32 }

anueStageTrimFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.4.1.1
    ::= { anueNtoStageTrimEntry 1 }

anueStageTrimFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.4.1.2
    ::= { anueNtoStageTrimEntry 2 }

anueStageTrimFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.4.1.3
    ::= { anueNtoStageTrimEntry 3 }

anueStageTrimOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.4.1.4
    ::= { anueNtoStageTrimEntry 4 }

anueStageTrimType OBJECT-TYPE
    SYNTAX  INTEGER {
            anueStageTrimRetainedMac(1),
            anueStageTrimRetainedMacVlan(2),
            anueStageTrimRetainedMacVlanMpls(3),
            anueStageTrimRetainedMacMacVlanMplsL3(4) }
    MAX-ACCESS read-only
    STATUS  current
    DESCRIPTION
        "Specifies what header information is retained when trimming
        packets.

        anueStageTrimRetainedMac(1)            MAC header fields are
                                               retained
        anueStageTrimRetainedMacVlan(2)        MAC and VLAN header fields
                                               are retained
        anueStageTrimRetainedMacVlanMpls(3)    MAC, VLAN, and MPLS header
                                               fields are retained
        anueStageTrimRetainedMacVlanMPlsL3(4)  MAC, VLAN, MPLS, and L3
                                               header fields are
                                               retained"
    -- 1.3.6.1.4.1.32620.1.1.4.4.1.5
    ::= { anueNtoStageTrimEntry 5 }

anueStageTrimRetainOctets OBJECT-TYPE
    SYNTAX  Integer32
    MAX-ACCESS read-only
    STATUS  current
    DESCRIPTION
        "Specifies the number of octets beyond the retained headers that
        are also retained."
    -- 1.3.6.1.4.1.32620.1.1.4.4.1.6
    ::= { anueNtoStageTrimEntry 6 }

anueStageTrimModPkts OBJECT-TYPE
    SYNTAX  Counter64
    MAX-ACCESS read-only
    STATUS  current
    DESCRIPTION
        "The total number of packets modified by this stage since
        anueFilterCriteriaModTime."
    -- 1.3.6.1.4.1.32620.1.1.4.4.1.7
    ::= { anueNtoStageTrimEntry 7 }

anueStageTrimModPktPct OBJECT-TYPE
    SYNTAX  Gauge32
    MAX-ACCESS read-only
    STATUS  current
    DESCRIPTION
        "The percentage of packets received by this stage since
        anueFilterCriteriaModTime that have been modified."
    -- 1.3.6.1.4.1.32620.1.1.4.4.1.8
    ::= { anueNtoStageTrimEntry 8 }

anueStageTrimRmvOctets OBJECT-TYPE
    SYNTAX  Counter64
    MAX-ACCESS read-only
    STATUS  current
    DESCRIPTION
        "The total number of octets removed from packets by this stage
        since anueFilterCriteriaModTime."
    -- 1.3.6.1.4.1.32620.1.1.4.4.1.9
    ::= { anueNtoStageTrimEntry 9 }

anueStageTrimRmvOctetPct OBJECT-TYPE
    SYNTAX  Gauge32
    MAX-ACCESS read-only
    STATUS  current
    DESCRIPTION
        "The percentage of octets received by this stage since
        anueFilterCriteriaModTime that have been removed."
    -- 1.3.6.1.4.1.32620.1.1.4.4.1.10
    ::= { anueNtoStageTrimEntry 10 }

anueStageTrimRstModPkts OBJECT-TYPE
    SYNTAX  Counter64
    MAX-ACCESS read-only
    STATUS  current
    DESCRIPTION
        "The total number of packets modified by this stage since
        anueFilterStatsResetTime."
    -- 1.3.6.1.4.1.32620.1.1.4.4.1.11
    ::= { anueNtoStageTrimEntry 11 }

anueStageTrimRstModPktPct OBJECT-TYPE
    SYNTAX  Gauge32
    MAX-ACCESS read-only
    STATUS  current
    DESCRIPTION
        "The percentage of packets received by this stage since
        anueFilterStatsResetTime that have been modified."
    -- 1.3.6.1.4.1.32620.1.1.4.4.1.12
    ::= { anueNtoStageTrimEntry 12 }

anueStageTrimRstRmvOctets OBJECT-TYPE
    SYNTAX  Counter64
    MAX-ACCESS read-only
    STATUS  current
    DESCRIPTION
        "The total number of octets removed from packets by this stage
        since anueFilterStatsResetTime."
    -- 1.3.6.1.4.1.32620.1.1.4.4.1.13
    ::= { anueNtoStageTrimEntry 13 }

anueStageTrimRstRmvOctetPct OBJECT-TYPE
    SYNTAX  Gauge32
    MAX-ACCESS read-only
    STATUS  current
    DESCRIPTION
        "The percentage of octets received by this stage since
        anueFilterStatsResetTime that have been removed."
    -- 1.3.6.1.4.1.32620.1.1.4.4.1.14
    ::= { anueNtoStageTrimEntry 14 }


-- anueNtoStageBurstBufferTable
--

anueNtoStageBurstBufferTable OBJECT-TYPE
    SYNTAX  SEQUENCE OF AnueNtoStageBurstBufferEntry
    MAX-ACCESS not-accessible
    STATUS  current
    DESCRIPTION
        "Table of entries holding detailed statistics for all burst
        buffer stages enabled in all port or port group filters."
    -- 1.3.6.1.4.1.32620.1.1.4.5
    ::= { anueNtoStage 5 }

anueNtoStageBurstBufferEntry OBJECT-TYPE
    SYNTAX  AnueNtoStageBurstBufferEntry
    MAX-ACCESS not-accessible
    STATUS  current
    DESCRIPTION
        "A specific entry for a single burst buffer stage enabled on a
        single port or port group filter."
    INDEX {
        anueStageBufferFilterType,
        anueStageBufferFilterNumber,
        anueStageBufferFeature }
    -- 1.3.6.1.4.1.32620.1.1.4.5.1
    ::= { anueNtoStageBurstBufferTable 1 }

AnueNtoStageBurstBufferEntry ::= SEQUENCE {
    anueStageBufferFilterType       AnueFilterTypeDT,
    anueStageBufferFilterNumber     Integer32,
    anueStageBufferFeature          AnueStageType,
    anueStageBufferOrder            Integer32,
    anueStageBufferSize             Integer32,
    anueStageBufferCurBufferLevel   Gauge32,
    anueStageBufferPeakBufferLevel  Counter32,
    anueStageBufferPeakBufferTime   DateAndTime,
    anueStageBufferDropPkts         Counter64,
    anueStageBufferDropTime         DateAndTime,
    anueStageBufferRstDropPkts      Counter64,
    anueStageBufferRstDropTime      DateAndTime }

anueStageBufferFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.5.1.1
    ::= { anueNtoStageBurstBufferEntry 1 }

anueStageBufferFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.5.1.2
    ::= { anueNtoStageBurstBufferEntry 2 }

anueStageBufferFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.5.1.3
    ::= { anueNtoStageBurstBufferEntry 3 }

anueStageBufferOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.5.1.4
    ::= { anueNtoStageBurstBufferEntry 4 }

anueStageBufferSize OBJECT-TYPE
    SYNTAX  Integer32
    MAX-ACCESS read-only
    STATUS  current
    DESCRIPTION
        "Specifies the maximum burst buffer size in MB."
    -- 1.3.6.1.4.1.32620.1.1.4.5.1.5
    ::= { anueNtoStageBurstBufferEntry 5 }

anueStageBufferCurBufferLevel OBJECT-TYPE
    SYNTAX  Gauge32
    UNITS "Megabytes"
    MAX-ACCESS read-only
    STATUS  current
    DESCRIPTION
        "Indicates the current fill level of the buffer in MB."
    -- 1.3.6.1.4.1.32620.1.1.4.5.1.6
    ::= { anueNtoStageBurstBufferEntry 6 }

anueStageBufferPeakBufferLevel OBJECT-TYPE
    SYNTAX  Counter32
    UNITS "Megabytes"
    MAX-ACCESS read-only
    STATUS  current
    DESCRIPTION
        "Indicates the peak fill level of the buffer in MB."
    -- 1.3.6.1.4.1.32620.1.1.4.5.1.7
    ::= { anueNtoStageBurstBufferEntry 7 }

anueStageBufferPeakBufferTime OBJECT-TYPE
    SYNTAX  DateAndTime
    MAX-ACCESS read-only
    STATUS  current
    DESCRIPTION
        "Indicates the time that peak fill level was reached."
    -- 1.3.6.1.4.1.32620.1.1.4.5.1.8
    ::= { anueNtoStageBurstBufferEntry 8 }

anueStageBufferDropPkts OBJECT-TYPE
    SYNTAX  Counter64
    MAX-ACCESS read-only
    STATUS  current
    DESCRIPTION
        "The total number of packets dropped by this stage due to buffer
        overflow since anueFilterCriteriaModTime."
    -- 1.3.6.1.4.1.32620.1.1.4.5.1.9
    ::= { anueNtoStageBurstBufferEntry 9 }

anueStageBufferDropTime OBJECT-TYPE
    SYNTAX  DateAndTime
    MAX-ACCESS read-only
    STATUS  current
    DESCRIPTION
        "The time the last packet was dropped."
    -- 1.3.6.1.4.1.32620.1.1.4.5.1.10
    ::= { anueNtoStageBurstBufferEntry 10 }

anueStageBufferRstDropPkts OBJECT-TYPE
    SYNTAX  Counter64
    MAX-ACCESS read-only
    STATUS  current
    DESCRIPTION
        "The total number of packets dropped by this stage due to buffer
        overflow since anueFilterStatsResetTime."
    -- 1.3.6.1.4.1.32620.1.1.4.5.1.11
    ::= { anueNtoStageBurstBufferEntry 11 }

anueStageBufferRstDropTime OBJECT-TYPE
    SYNTAX  DateAndTime
    MAX-ACCESS read-only
    STATUS  current
    DESCRIPTION
        "The time the last packet was dropped."
    -- 1.3.6.1.4.1.32620.1.1.4.5.1.12
    ::= { anueNtoStageBurstBufferEntry 12 }


-- anueNtoStageNPFilterTable
--

anueNtoStageNPFilterTable OBJECT-TYPE
    SYNTAX  SEQUENCE OF AnueNtoStageNPFilterEntry
    MAX-ACCESS not-accessible
    STATUS  current
    DESCRIPTION
        "Table of entries holding detailed statistics for all network
        port filter stages present in all port or port group filters."
    -- 1.3.6.1.4.1.32620.1.1.4.6
    ::= { anueNtoStage 6 }

anueNtoStageNPFilterEntry OBJECT-TYPE
    SYNTAX  AnueNtoStageNPFilterEntry
    MAX-ACCESS not-accessible
    STATUS  current
    DESCRIPTION
        "A specific entry for a single network port filter stage present
        on a single port or port group filter."
    INDEX {
        anueStageNPFilterFilterType,
        anueStageNPFilterFilterNumber,
        anueStageNPFilterFeature }
    -- 1.3.6.1.4.1.32620.1.1.4.6.1
    ::= { anueNtoStageNPFilterTable 1 }

AnueNtoStageNPFilterEntry ::= SEQUENCE {
    anueStageNPFilterFilterType       AnueFilterTypeDT,
    anueStageNPFilterFilterNumber     Integer32,
    anueStageNPFilterFeature          AnueStageType,
    anueStageNPFilterOrder            Integer32,
    anueStageNPFilterDenyPkts         Counter64,
    anueStageNPFilterDenyPktPct       Gauge32,
    anueStageNPFilterDenyOctets       Counter64,
    anueStageNPFilterDenyOctetPct     Gauge32,
    anueStageNPFilterRstDenyPkts      Counter64,
    anueStageNPFilterRstDenyPktPct    Gauge32,
    anueStageNPFilterRstDenyOctets    Counter64,
    anueStageNPFilterRstDenyOctetPct  Gauge32 }

anueStageNPFilterFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.6.1.1
    ::= { anueNtoStageNPFilterEntry 1 }

anueStageNPFilterFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.6.1.2
    ::= { anueNtoStageNPFilterEntry 2 }

anueStageNPFilterFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.6.1.3
    ::= { anueNtoStageNPFilterEntry 3 }

anueStageNPFilterOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.6.1.4
    ::= { anueNtoStageNPFilterEntry 4 }

anueStageNPFilterDenyPkts OBJECT-TYPE
    SYNTAX  Counter64
    MAX-ACCESS read-only
    STATUS  current
    DESCRIPTION
        "The total number of packets denied by this filter since
        anueFilterCriteriaModTime."
    -- 1.3.6.1.4.1.32620.1.1.4.6.1.5
    ::= { anueNtoStageNPFilterEntry 5 }

anueStageNPFilterDenyPktPct OBJECT-TYPE
    SYNTAX  Gauge32
    MAX-ACCESS read-only
    STATUS  current
    DESCRIPTION
        "The percentage of packets received by this filter since
        anueFilterCriteriaModTime that have been denied."
    -- 1.3.6.1.4.1.32620.1.1.4.6.1.6
    ::= { anueNtoStageNPFilterEntry 6 }

anueStageNPFilterDenyOctets OBJECT-TYPE
    SYNTAX  Counter64
    MAX-ACCESS read-only
    STATUS  current
    DESCRIPTION
        "The total number of octets denied by this filter since
        anueFilterCriteriaModTime."
    -- 1.3.6.1.4.1.32620.1.1.4.6.1.7
    ::= { anueNtoStageNPFilterEntry 7 }

anueStageNPFilterDenyOctetPct OBJECT-TYPE
    SYNTAX  Gauge32
    MAX-ACCESS read-only
    STATUS  current
    DESCRIPTION
        "The percentage of octets received by this filter since
        anueFilterCriteriaModTime that have been denied."
    -- 1.3.6.1.4.1.32620.1.1.4.6.1.8
    ::= { anueNtoStageNPFilterEntry 8 }

anueStageNPFilterRstDenyPkts OBJECT-TYPE
    SYNTAX  Counter64
    MAX-ACCESS read-only
    STATUS  current
    DESCRIPTION
        "The total number of packets denied by this filter since
        anueFilterStatsResetTime."
    -- 1.3.6.1.4.1.32620.1.1.4.6.1.9
    ::= { anueNtoStageNPFilterEntry 9 }

anueStageNPFilterRstDenyPktPct OBJECT-TYPE
    SYNTAX  Gauge32
    MAX-ACCESS read-only
    STATUS  current
    DESCRIPTION
        "The percentage of packets received by this filter since
        anueFilterStatsResetTime that have been denied."
    -- 1.3.6.1.4.1.32620.1.1.4.6.1.10
    ::= { anueNtoStageNPFilterEntry 10 }

anueStageNPFilterRstDenyOctets OBJECT-TYPE
    SYNTAX  Counter64
    MAX-ACCESS read-only
    STATUS  current
    DESCRIPTION
        "The total number of octets denied by this filter since
        anueFilterStatsResetTime."
    -- 1.3.6.1.4.1.32620.1.1.4.6.1.11
    ::= { anueNtoStageNPFilterEntry 11 }

anueStageNPFilterRstDenyOctetPct OBJECT-TYPE
    SYNTAX  Gauge32
    MAX-ACCESS read-only
    STATUS  current
    DESCRIPTION
        "The percentage of octets received by this filter since
        anueFilterStatsResetTime that have been denied."
    -- 1.3.6.1.4.1.32620.1.1.4.6.1.12
    ::= { anueNtoStageNPFilterEntry 12 }


-- anueNtoStageTPFilterTable
--

anueNtoStageTPFilterTable OBJECT-TYPE
    SYNTAX  SEQUENCE OF AnueNtoStageTPFilterEntry
    MAX-ACCESS not-accessible
    STATUS  current
    DESCRIPTION
        "Table of entries holding detailed statistics for all tool
        port filter stages present in all port or port group filters."
    -- 1.3.6.1.4.1.32620.1.1.4.7
    ::= { anueNtoStage 7 }

anueNtoStageTPFilterEntry OBJECT-TYPE
    SYNTAX  AnueNtoStageTPFilterEntry
    MAX-ACCESS not-accessible
    STATUS  current
    DESCRIPTION
        "A specific entry for a single tool port filter stage present
        on a single port or port group filter."
    INDEX {
        anueStageTPFilterFilterType,
        anueStageTPFilterFilterNumber,
        anueStageTPFilterFeature }
    -- 1.3.6.1.4.1.32620.1.1.4.7.1
    ::= { anueNtoStageTPFilterTable 1 }

AnueNtoStageTPFilterEntry ::= SEQUENCE {
    anueStageTPFilterFilterType       AnueFilterTypeDT,
    anueStageTPFilterFilterNumber     Integer32,
    anueStageTPFilterFeature          AnueStageType,
    anueStageTPFilterOrder            Integer32,
    anueStageTPFilterDenyPkts         Counter64,
    anueStageTPFilterDenyPktPct       Gauge32,
    anueStageTPFilterDropPkts         Counter64,
    anueStageTPFilterDropTime         DateAndTime,
    anueStageTPFilterRstDenyPkts      Counter64,
    anueStageTPFilterRstDenyPktPct    Gauge32,
    anueStageTPFilterRstDropPkts      Counter64,
    anueStageTPFilterRstDropTime      DateAndTime }

anueStageTPFilterFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.7.1.1
    ::= { anueNtoStageTPFilterEntry 1 }

anueStageTPFilterFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.7.1.2
    ::= { anueNtoStageTPFilterEntry 2 }

anueStageTPFilterFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.7.1.3
    ::= { anueNtoStageTPFilterEntry 3 }

anueStageTPFilterOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.7.1.4
    ::= { anueNtoStageTPFilterEntry 4 }

anueStageTPFilterDenyPkts OBJECT-TYPE
    SYNTAX  Counter64
    MAX-ACCESS read-only
    STATUS  current
    DESCRIPTION
        "The total number of packets denied by this filter since
        anueFilterCriteriaModTime."
    -- 1.3.6.1.4.1.32620.1.1.4.7.1.5
    ::= { anueNtoStageTPFilterEntry 5 }

anueStageTPFilterDenyPktPct OBJECT-TYPE
    SYNTAX  Gauge32
    MAX-ACCESS read-only
    STATUS  current
    DESCRIPTION
        "The percentage of packets received by this filter since
        anueFilterCriteriaModTime that have been denied."
    -- 1.3.6.1.4.1.32620.1.1.4.7.1.6
    ::= { anueNtoStageTPFilterEntry 6 }

anueStageTPFilterDropPkts OBJECT-TYPE
    SYNTAX  Counter64
    MAX-ACCESS read-only
    STATUS  current
    DESCRIPTION
        "The total number of pre-filter packet drops at this stage since
        anueFilterCriteriaModTime."
    -- 1.3.6.1.4.1.32620.1.1.4.7.1.7
    ::= { anueNtoStageTPFilterEntry 7 }

anueStageTPFilterDropTime OBJECT-TYPE
    SYNTAX  DateAndTime
    MAX-ACCESS read-only
    STATUS  current
    DESCRIPTION
        "The time the last packet was dropped."
    -- 1.3.6.1.4.1.32620.1.1.4.7.1.8
    ::= { anueNtoStageTPFilterEntry 8 }

anueStageTPFilterRstDenyPkts OBJECT-TYPE
    SYNTAX  Counter64
    MAX-ACCESS read-only
    STATUS  current
    DESCRIPTION
        "The total number of packets denied by this filter since
        anueFilterStatsResetTime."
    -- 1.3.6.1.4.1.32620.1.1.4.7.1.9
    ::= { anueNtoStageTPFilterEntry 9 }

anueStageTPFilterRstDenyPktPct OBJECT-TYPE
    SYNTAX  Gauge32
    MAX-ACCESS read-only
    STATUS  current
    DESCRIPTION
        "The percentage of packets received by this filter since
        anueFilterStatsResetTime that have been denied."
    -- 1.3.6.1.4.1.32620.1.1.4.7.1.10
    ::= { anueNtoStageTPFilterEntry 10 }

anueStageTPFilterRstDropPkts OBJECT-TYPE
    SYNTAX  Counter64
    MAX-ACCESS read-only
    STATUS  current
    DESCRIPTION
        "The total number of pre-filter packet drops at this stage since
        anueFilterStatsResetTime."
    -- 1.3.6.1.4.1.32620.1.1.4.7.1.11
    ::= { anueNtoStageTPFilterEntry 11 }

anueStageTPFilterRstDropTime OBJECT-TYPE
    SYNTAX  DateAndTime
    MAX-ACCESS read-only
    STATUS  current
    DESCRIPTION
        "The time the last packet was dropped."
    -- 1.3.6.1.4.1.32620.1.1.4.7.1.12
    ::= { anueNtoStageTPFilterEntry 12 }


--anueNtoStageAfmDropTable
--

anueNtoStageAfmDropTable OBJECT-TYPE
    SYNTAX  SEQUENCE OF AnueNtoStageAfmDropEntry
    MAX-ACCESS not-accessible
    STATUS  current
    DESCRIPTION
        "Table of entries holding detailed statistics for all AFM drop
        stages present in all port or port group filters."
    -- 1.3.6.1.4.1.32620.1.1.4.8
    ::= { anueNtoStage 8 }

anueNtoStageAfmDropEntry OBJECT-TYPE
    SYNTAX  AnueNtoStageAfmDropEntry
    MAX-ACCESS not-accessible
    STATUS  current
    DESCRIPTION
        "A specific entry for a single AFM drop stage present on a single
        port or port group filter."
    INDEX {
        anueStageAfmDropFilterType,
        anueStageAfmDropFilterNumber,
        anueStageAfmDropFeature }
    -- 1.3.6.1.4.1.32620.1.1.4.8.1
    ::= { anueNtoStageAfmDropTable 1 }

AnueNtoStageAfmDropEntry ::= SEQUENCE {
    anueStageAfmDropFilterType             AnueFilterTypeDT,
    anueStageAfmDropFilterNumber           Integer32,
    anueStageAfmDropFeature                AnueStageType,
    anueStageAfmDropOrder                  Integer32,
    anueStageAfmDropDropPkts               Counter64,
    anueStageAfmDropDropTime               DateAndTime,
    anueStageAfmDropRstDropPkts            Counter64,
    anueStageAfmDropRstDropTime            DateAndTime }

anueStageAfmDropFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.8.1.1
    ::= { anueNtoStageAfmDropEntry 1 }

anueStageAfmDropFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.8.1.2
    ::= { anueNtoStageAfmDropEntry 2 }

anueStageAfmDropFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.8.1.3
    ::= { anueNtoStageAfmDropEntry 3 }

anueStageAfmDropOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.8.1.4
    ::= { anueNtoStageAfmDropEntry 4 }

anueStageAfmDropDropPkts OBJECT-TYPE
    SYNTAX  Counter64
    MAX-ACCESS read-only
    STATUS  current
    DESCRIPTION
        "The total number of packets dropped due to clock speed mismatch
        at this stage since anueFilterCriteriaModTime."
    -- 1.3.6.1.4.1.32620.1.1.4.8.1.5
    ::= { anueNtoStageAfmDropEntry 5 }

anueStageAfmDropDropTime OBJECT-TYPE
    SYNTAX  DateAndTime
    MAX-ACCESS read-only
    STATUS  current
    DESCRIPTION
        "The time the last packet was dropped."
    -- 1.3.6.1.4.1.32620.1.1.4.8.1.6
    ::= { anueNtoStageAfmDropEntry 6 }

anueStageAfmDropRstDropPkts OBJECT-TYPE
    SYNTAX  Counter64
    MAX-ACCESS read-only
    STATUS  current
    DESCRIPTION
        "The total number of packets dropped due to clock speed mismatch
        at this stage since anueFilterStatsResetTime."
    -- 1.3.6.1.4.1.32620.1.1.4.8.1.7
    ::= { anueNtoStageAfmDropEntry 7 }

anueStageAfmDropRstDropTime OBJECT-TYPE
    SYNTAX  DateAndTime
    MAX-ACCESS read-only
    STATUS  current
    DESCRIPTION
        "The time the last packet was dropped."
    -- 1.3.6.1.4.1.32620.1.1.4.8.1.8
    ::= { anueNtoStageAfmDropEntry 8 }


-- anueNtoStageTagTable
--

anueNtoStageTagTable OBJECT-TYPE
    SYNTAX  SEQUENCE OF AnueNtoStageTagEntry
    MAX-ACCESS not-accessible
    STATUS  current
    DESCRIPTION
        "Table of entries holding detailed statistics, pipeline order and
        configuration attributes for all packet tagging
        stages enabled in all port or port group filters."
    -- 1.3.6.1.4.1.32620.1.1.4.9
    ::= { anueNtoStage 9 }

anueNtoStageTagEntry OBJECT-TYPE
    SYNTAX  AnueNtoStageTagEntry
    MAX-ACCESS not-accessible
    STATUS  current
    DESCRIPTION
        "A specific entry for a single tagging stage enabled on a single
        port or port group filter."
    INDEX {
        anueStageTagFilterType,
        anueStageTagFilterNumber,
        anueStageTagFeature }
    -- 1.3.6.1.4.1.32620.1.1.4.9.1
    ::= { anueNtoStageTagTable 1 }

AnueNtoStageTagEntry ::= SEQUENCE {
    anueStageTagFilterType       AnueFilterTypeDT,
    anueStageTagFilterNumber     Integer32,
    anueStageTagFeature          AnueStageType,
    anueStageTagOrder            Integer32,
    anueStageTagAttributes       DisplayString,
    anueStageTagModPkts          Counter64,
    anueStageTagModPktPct        Gauge32,
    anueStageTagRstModPkts       Counter64,
    anueStageTagRstModPktPct     Gauge32 }


anueStageTagFilterType OBJECT-TYPE
    SYNTAX  AnueFilterTypeDT
    MAX-ACCESS read-only
    STATUS  current
    DESCRIPTION
        "Partial index identifying the filter entry in the
        anueNtoStageTagEntry to which this stage is subordinate."
    -- 1.3.6.1.4.1.32620.1.1.4.9.1.1
    ::= { anueNtoStageTagEntry 1 }

anueStageTagFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.9.1.2
    ::= { anueNtoStageTagEntry 2 }

anueStageTagFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.9.1.3
    ::= { anueNtoStageTagEntry 3 }

anueStageTagOrder OBJECT-TYPE
    SYNTAX  Integer32 (1..2147483647)
    MAX-ACCESS read-only
    STATUS  current
    DESCRIPTION
        "Indicates the (one-based) ingress-to-egress relative positional
        order that this stage holds in the superordinate filter
        pipeline."
    -- 1.3.6.1.4.1.32620.1.1.4.9.1.4
    ::= { anueNtoStageTagEntry 4 }

anueStageTagAttributes OBJECT-TYPE
    SYNTAX  DisplayString
    MAX-ACCESS read-only
    STATUS  current
    DESCRIPTION
        "Shows any additional attributes that the tagging feature may have.
        It is a comma separated string of key-value pairs, where the key is the
        attribute's name."
    -- 1.3.6.1.4.1.32620.1.1.4.9.1.5
    ::= { anueNtoStageTagEntry 5 }

anueStageTagModPkts OBJECT-TYPE
    SYNTAX  Counter64
    MAX-ACCESS read-only
    STATUS  current
    DESCRIPTION
        "The total number of modified packets by this stage
        since anueFilterCriteriaModTime."
    -- 1.3.6.1.4.1.32620.1.1.4.9.1.6
    ::= { anueNtoStageTagEntry 6 }

anueStageTagModPktPct OBJECT-TYPE
    SYNTAX  Gauge32
    MAX-ACCESS read-only
    STATUS  current
    DESCRIPTION
        "The percentage of packets received by this stage since
        anueFilterCriteriaModTime that have been modified."
    -- 1.3.6.1.4.1.32620.1.1.4.9.1.7
    ::= { anueNtoStageTagEntry 7 }

anueStageTagRstModPkts OBJECT-TYPE
    SYNTAX  Counter64
    MAX-ACCESS read-only
    STATUS  current
    DESCRIPTION
        "The total number of modified packets by this stage
        since anueFilterStatsResetTime."
    -- 1.3.6.1.4.1.32620.1.1.4.9.1.8
    ::= { anueNtoStageTagEntry 8 }

anueStageTagRstModPktPct OBJECT-TYPE
    SYNTAX  Gauge32
    MAX-ACCESS read-only
    STATUS  current
    DESCRIPTION
        "The percentage of packets received by this stage since
        anueFilterStatsResetTime that have been modified."
    -- 1.3.6.1.4.1.32620.1.1.4.9.1.9
    ::= { anueNtoStageTagEntry 9 }


-- anueNtoStageDropTable
--

anueNtoStageDropTable OBJECT-TYPE
    SYNTAX  SEQUENCE OF AnueNtoStageDropEntry
    MAX-ACCESS not-accessible
    STATUS  current
    DESCRIPTION
        "Table of entries holding detailed non AFM drop statistics."
    -- 1.3.6.1.4.1.32620.1.1.4.10
    ::= { anueNtoStage 10 }

anueNtoStageDropEntry OBJECT-TYPE
    SYNTAX  AnueNtoStageDropEntry
    MAX-ACCESS not-accessible
    STATUS  current
    DESCRIPTION
        "A specific entry for a single non AFM drop."
    INDEX {
        anueStageDropFilterType,
        anueStageDropFilterNumber,
        anueStageDropFeature }
    -- 1.3.6.1.4.1.32620.1.1.4.10.1
    ::= { anueNtoStageDropTable 1 }

AnueNtoStageDropEntry ::= SEQUENCE {
    anueStageDropFilterType    AnueFilterTypeDT,
    anueStageDropFilterNumber  Integer32,
    anueStageDropFeature       AnueStageType,
    anueStageCntDropPkts       Counter64,
    anueStageCntDropTime       DateAndTime,
    anueStageCurDropPkts       Counter64,
    anueStageAvgDropPkts       Counter64,
    anueStagePeakDropPkts      Counter64,
    anueStagePeakDropTime      DateAndTime }

anueStageDropFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.10.1.1
    ::= { anueNtoStageDropEntry 1 }

anueStageDropFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.10.1.2
    ::= { anueNtoStageDropEntry 2 }

anueStageDropFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.10.1.3
    ::= { anueNtoStageDropEntry 3 }

anueStageCntDropPkts OBJECT-TYPE
    SYNTAX  Counter64
    MAX-ACCESS read-only
    STATUS  current
    DESCRIPTION
        "The total number of packets dropped since anueFilterDropResetTime."
    -- 1.3.6.1.4.1.32620.1.1.4.10.1.4
    ::= { anueNtoStageDropEntry 4 }

anueStageCntDropTime OBJECT-TYPE
    SYNTAX  DateAndTime
    MAX-ACCESS read-only
    STATUS  current
    DESCRIPTION
        " The time the last packet was dropped."
    -- 1.3.6.1.4.1.32620.1.1.4.10.1.5
    ::= { anueNtoStageDropEntry 5 }

anueStageCurDropPkts OBJECT-TYPE
    SYNTAX  Counter64
    MAX-ACCESS read-only
    STATUS  current
    DESCRIPTION
        "The number of packets dropped in the current (most recent) sampling period."
    -- 1.3.6.1.4.1.32620.1.1.4.10.1.6
    ::= { anueNtoStageDropEntry 6 }

anueStageAvgDropPkts OBJECT-TYPE
    SYNTAX  Counter64
    MAX-ACCESS read-only
    STATUS  current
    DESCRIPTION
        "The average number of packets dropped in each sampling period
        since anueFilterDropResetTime."
    -- 1.3.6.1.4.1.32620.1.1.4.10.1.7
    ::= { anueNtoStageDropEntry 7 }

anueStagePeakDropPkts OBJECT-TYPE
    SYNTAX  Counter64
    MAX-ACCESS read-only
    STATUS  current
    DESCRIPTION
        "The peak number of packets dropped in any sampling period
        since anueFilterDropResetTime."
    -- 1.3.6.1.4.1.32620.1.1.4.10.1.8
    ::= { anueNtoStageDropEntry 8 }

anueStagePeakDropTime OBJECT-TYPE
    SYNTAX  DateAndTime
    MAX-ACCESS read-only
    STATUS  current
    DESCRIPTION
        "The date and time of the drop peak event."
    -- 1.3.6.1.4.1.32620.1.1.4.10.1.9
    ::= { anueNtoStageDropEntry 9 }


-- anueNtoStageGtpFdTable
--

anueNtoStageGtpFdTable OBJECT-TYPE
    SYNTAX  SEQUENCE OF AnueNtoStageGtpFdEntry
    MAX-ACCESS not-accessible
    STATUS  current
    DESCRIPTION
        "Table of entries holding detailed statistics for all GTP
        Flow Distribution stages enabled in all port or port group filters."
    -- 1.3.6.1.4.1.32620.1.1.4.11
    ::= { anueNtoStage 11 }

anueNtoStageGtpFdEntry OBJECT-TYPE
    SYNTAX  AnueNtoStageGtpFdEntry
    MAX-ACCESS not-accessible
    STATUS  current
    DESCRIPTION
        "A specific entry for a single GTP Flow Distribution stage
         enabled on a single port or port group filter."
    INDEX {
        anueStageGtpFdFilterType,
        anueStageGtpFdFilterNumber,
        anueStageGtpFdFeature }
    -- 1.3.6.1.4.1.32620.1.1.4.11.1
    ::= { anueNtoStageGtpFdTable 1 }

AnueNtoStageGtpFdEntry ::= SEQUENCE {
    anueStageGtpFdFilterType       AnueFilterTypeDT,
    anueStageGtpFdFilterNumber     Integer32,
    anueStageGtpFdFeature          AnueStageType,
    anueStageRateGtpCPps           Counter64,
    anueStageRateGtpUPps           Counter64,
    anueStageRateGtpCBps           Counter64,
    anueStageRateGtpUBps           Counter64 }

anueStageGtpFdFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.11.1.1
    ::= { anueNtoStageGtpFdEntry 1 }

anueStageGtpFdFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.11.1.2
    ::= { anueNtoStageGtpFdEntry 2 }

anueStageGtpFdFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.11.1.3
    ::= { anueNtoStageGtpFdEntry 3 }

anueStageRateGtpCPps OBJECT-TYPE
    SYNTAX  Counter64
    MAX-ACCESS read-only
    STATUS  current
    DESCRIPTION
        "The rate of GTP-C packets."
    -- 1.3.6.1.4.1.32620.1.1.4.11.1.4
    ::= { anueNtoStageGtpFdEntry 4 }

anueStageRateGtpUPps OBJECT-TYPE
    SYNTAX  Counter64
    MAX-ACCESS read-only
    STATUS  current
    DESCRIPTION
        "The rate of GTP-U packets."
    -- 1.3.6.1.4.1.32620.1.1.4.11.1.5
    ::= { anueNtoStageGtpFdEntry 5 }

anueStageRateGtpCBps OBJECT-TYPE
    SYNTAX  Counter64
    MAX-ACCESS read-only
    STATUS  current
    DESCRIPTION
        "The rate of GTP-C bytes."
    -- 1.3.6.1.4.1.32620.1.1.4.11.1.6
    ::= { anueNtoStageGtpFdEntry 6 }

anueStageRateGtpUBps OBJECT-TYPE
    SYNTAX  Counter64
    MAX-ACCESS read-only
    STATUS  current
    DESCRIPTION
        "The rate of GTP-U bytes."
    -- 1.3.6.1.4.1.32620.1.1.4.11.1.7
    ::= { anueNtoStageGtpFdEntry 7 }

-- anueNtoStageDataMaskingTable
--

anueNtoStageDataMaskingTable OBJECT-TYPE
    SYNTAX  SEQUENCE OF AnueNtoStageDataMaskingEntry
    MAX-ACCESS not-accessible
    STATUS  current
    DESCRIPTION
        "Table of entries holding detailed statistics for all data masking
        stages enabled in all port or port group filters."
    -- 1.3.6.1.4.1.32620.1.1.4.12
    ::= { anueNtoStage 12 }

anueNtoStageDataMaskingEntry OBJECT-TYPE
    SYNTAX  AnueNtoStageDataMaskingEntry
    MAX-ACCESS not-accessible
    STATUS  current
    DESCRIPTION
        "A specific entry for a single data masking stage enabled on a single
        port or port group filter."
    INDEX {
        anueStageDataMaskingFilterType,
        anueStageDataMaskingFilterNumber,
        anueStageDataMaskingFeature }
    -- 1.3.6.1.4.1.32620.1.1.4.12.1
    ::= { anueNtoStageDataMaskingTable 1 }

AnueNtoStageDataMaskingEntry ::= SEQUENCE {
    anueStageDataMaskingFilterType       AnueFilterTypeDT,
    anueStageDataMaskingFilterNumber     Integer32,
    anueStageDataMaskingFeature          AnueStageType,
    anueStageDataMaskingOrder            Integer32,
    anueStageDataMaskingOffsetLayer      INTEGER,
    anueStageDataMaskingOffset           Counter64,
    anueStageDataMaskingLength           Counter64,
    anueStageDataMaskingFillValue        OCTET STRING,
    anueStageDataMaskingModPkts          Counter64,
    anueStageDataMaskingModPktPct        Gauge32,
    anueStageDataMaskingRstModPkts       Counter64,
    anueStageDataMaskingRstModPktPct     Gauge32 }

anueStageDataMaskingFilterType OBJECT-TYPE
    SYNTAX  AnueFilterTypeDT
    MAX-ACCESS read-only
    STATUS  current
    DESCRIPTION
        "Partial index identifying the filter entry in the
        anueNtoFilterDefTable to which this stage is subordinate."
    -- 1.3.6.1.4.1.32620.1.1.4.12.1.1
    ::= { anueNtoStageDataMaskingEntry 1 }

anueStageDataMaskingFilterNumber OBJECT-TYPE
    SYNTAX  Integer32 (1..2147483647)
    MAX-ACCESS read-only
    STATUS  current
    DESCRIPTION
        "Partial index identifying the filter entry in the
        anueNtoFilterDefTable to which this stage is subordinate."
    -- 1.3.6.1.4.1.32620.1.1.4.12.1.2
    ::= { anueNtoStageDataMaskingEntry 2 }

anueStageDataMaskingFeature OBJECT-TYPE
    SYNTAX  AnueStageType
    MAX-ACCESS read-only
    STATUS  current
    DESCRIPTION
        "Partial index identifying which specific stage (subordinate to
        the indicated filter) this entry models.  This bit enumeration
        will have exactly one stage type bit set."
    -- 1.3.6.1.4.1.32620.1.1.4.12.1.3
    ::= { anueNtoStageDataMaskingEntry 3 }

anueStageDataMaskingOrder OBJECT-TYPE
    SYNTAX  Integer32 (1..2147483647)
    MAX-ACCESS read-only
    STATUS  current
    DESCRIPTION
        "Indicates the (one-based) ingress-to-egress relative positional
        order that this stage holds in the superordinate filter pipeline."
    -- 1.3.6.1.4.1.32620.1.1.4.12.1.4
    ::= { anueNtoStageDataMaskingEntry 4 }

anueStageDataMaskingOffsetLayer OBJECT-TYPE
    SYNTAX  INTEGER {
        anueStageDataMaskingL2Start(1),
        anueStageDataMaskingL2End(2),
        anueStageDataMaskingL3End(3)
        }
    MAX-ACCESS read-only
    STATUS  current
    DESCRIPTION
        "Specifies the offset layer:

        anueStageDataMaskingL2Start(1)      L2_START
        anueStageDataMaskingL2End(2)        L2_END
        anueStageDataMaskingL3End(3)        L3_END."
    -- 1.3.6.1.4.1.32620.1.1.4.12.1.5
    ::= { anueNtoStageDataMaskingEntry 5 }

anueStageDataMaskingOffset OBJECT-TYPE
    SYNTAX  Counter64
    MAX-ACCESS read-only
    STATUS  current
    DESCRIPTION
        "Specifies the offset to begin masking."
    -- 1.3.6.1.4.1.32620.1.1.4.12.1.6
    ::= { anueNtoStageDataMaskingEntry 6 }

anueStageDataMaskingLength OBJECT-TYPE
    SYNTAX  Counter64
    MAX-ACCESS read-only
    STATUS  current
    DESCRIPTION
        "Specifies the length of masked data."
    -- 1.3.6.1.4.1.32620.1.1.4.12.1.7
    ::= { anueNtoStageDataMaskingEntry 7 }

anueStageDataMaskingFillValue OBJECT-TYPE
    SYNTAX  OCTET STRING
    MAX-ACCESS read-only
    STATUS  current
    DESCRIPTION
        "Specifies the value used to overwrite the data being masked."
    -- 1.3.6.1.4.1.32620.1.1.4.12.1.8
    ::= { anueNtoStageDataMaskingEntry 8 }

anueStageDataMaskingModPkts OBJECT-TYPE
    SYNTAX  Counter64
    MAX-ACCESS read-only
    STATUS  current
    DESCRIPTION
        "The total number of packets modified by this stage since
        anueFilterCriteriaModTime."
    -- 1.3.6.1.4.1.32620.1.1.4.12.1.9
    ::= { anueNtoStageDataMaskingEntry 9 }

anueStageDataMaskingModPktPct OBJECT-TYPE
    SYNTAX  Gauge32
    MAX-ACCESS read-only
    STATUS  current
    DESCRIPTION
        "The percentage of packets received by this stage since
        anueFilterCriteriaModTime that have been modified."
    -- 1.3.6.1.4.1.32620.1.1.4.12.1.10
    ::= { anueNtoStageDataMaskingEntry 10 }

anueStageDataMaskingRstModPkts OBJECT-TYPE
    SYNTAX  Counter64
    MAX-ACCESS read-only
    STATUS  current
    DESCRIPTION
        "The total number of packets modified by this stage since
        anueFilterStatsResetTime."
    -- 1.3.6.1.4.1.32620.1.1.4.12.1.11
    ::= { anueNtoStageDataMaskingEntry 11 }

anueStageDataMaskingRstModPktPct OBJECT-TYPE
    SYNTAX  Gauge32
    MAX-ACCESS read-only
    STATUS  current
    DESCRIPTION
        "The percentage of packets received by this stage since
        anueFilterStatsResetTime that have been modified."
    -- 1.3.6.1.4.1.32620.1.1.4.12.1.12
    ::= { anueNtoStageDataMaskingEntry 12 }

-- GSC stage entries begin here.

-- anueNtoStageGscNetworkFilterTable
--

anueNtoStageGscNetworkFilterTable OBJECT-TYPE
    SYNTAX  SEQUENCE OF AnueNtoStageGscNetworkFilterEntry
    MAX-ACCESS not-accessible
    STATUS  current
    DESCRIPTION ""
    --  room for expansion between NTO and GSC  --
    -- 1.3.6.1.4.1.32620.1.1.4.100
    ::= { anueNtoStage 100 }


anueNtoStageGscNetworkFilterEntry OBJECT-TYPE
    SYNTAX  AnueNtoStageGscNetworkFilterEntry
    MAX-ACCESS not-accessible
    STATUS  current
    DESCRIPTION ""
    INDEX {
        anueNtoStageGscNetworkFilterType,
        anueNtoStageGscNetworkFilterNumber,
        anueNtoStageGscNetworkFilterFeature }
    -- 1.3.6.1.4.1.32620.1.1.4.100.1
    ::= { anueNtoStageGscNetworkFilterTable 1 }


AnueNtoStageGscNetworkFilterEntry ::= SEQUENCE {
    anueNtoStageGscNetworkFilterType                                AnueFilterTypeDT,
    anueNtoStageGscNetworkFilterNumber                              Integer32,
    anueGscNWFltrExcSess                                            Counter64,
    anueNtoStageGscNetworkFilterFeature                             AnueStageType,
    anueGscNWFltrAvgGscPktFrag                                      Counter64,
    anueGscNWFltrAvgTdoutFrag                                       Counter64,
    anueGscNWFltrCurPacketFrag                                      Counter64,
    anueGscNWFltrCurTdoutFrag                                       Counter64,
    anueGscNWFltrPkPacketFrag                                       Counter64,
    anueGscNWFltrPkPacketFragT                                      DateAndTime,
    anueGscNWFltrPkTdOutFrag                                        Counter64,
    anueGscNWFltrPkTdOutFragT                                       DateAndTime,
    anueGscNWFltrTotFrag                                            Counter64,
    anueGscNWFltrTotRxCountFrag                                     Counter64,
    anueGscNWFltrTotTdOutFrag                                       Counter64,
    anueGscNWFltrAvgCompFragPkts                                    Counter64,
    anueGscNWFltrAvgCompFragPktsPerc                                Counter64,
    anueGscNWFltrAvgIncomFragPkts                                   Counter64,
    anueGscNWFltrCurCompFragPkts                                    Counter64,
    anueGscNWFltrCurCompFragPktsPerc                                Counter64,
    anueGscNWFltrCurIncomFragPkts                                   Counter64,
    anueGscNWFltrPkCompFragPkts                                     Counter64,
    anueGscNWFltrPkCompFragPktsT                                    DateAndTime,
    anueGscNWFltrPkCompFragPktsPerc                                 Counter64,
    anueGscNWFltrPkCompFragPktsPercT                                DateAndTime,
    anueGscNWFltrPkIncomFragPkts                                    Counter64,
    anueGscNWFltrPkIncomFragPktsT                                   DateAndTime,
    anueGscNWFltrPkTotCompFragPkts                                  Counter64,
    anueGscNWFltrAvgActiveUsers                                     Counter64,
    anueGscNWFltrCurActiveUsers                                     Counter64,
    anueGscNWFltrPkActiveUsers                                      Counter64,
    anueGscNWFltrPkActiveUsersT                                     DateAndTime,
    anueGscNWFltrAvgExcSess                                         Counter64,
    anueGscNWFltrCurExcSess                                         Counter64,
    anueGscNWFltrPkExcSess                                          Counter64,
    anueGscNWFltrPkExcSessT                                         DateAndTime,
    anueGscNWFltrTotExcSess                                         Counter64,
    anueGscNWFltrTotGtpV0CrSess                                     Counter64,
    anueGscNWFltrTotGtpV1CrSess                                     Counter64,
    anueGscNWFltrTotGtpV2CrSess                                     Counter64,
    anueGscNWFltrTotGtpTotCrSess                                    Counter64,
    anueGscNWFltrAvgGtpV0CrSess                                     Counter64,
    anueGscNWFltrAvgGtpV1CrSess                                     Counter64,
    anueGscNWFltrAvgGtpV2CrSess                                     Counter64,
    anueGscNWFltrAvgGtpTotCrSess                                    Counter64,
    anueGscNWFltrCurGtpV0CrSess                                     Counter64,
    anueGscNWFltrCurGtpV1CrSess                                     Counter64,
    anueGscNWFltrCurGtpV2CrSess                                     Counter64,
    anueGscNWFltrCurGtpTotCrSess                                    Counter64,
    anueGscNWFltrPkGtpV0CrSess                                      Counter64,
    anueGscNWFltrPkGtpV1CrSess                                      Counter64,
    anueGscNWFltrPkGtpV2CrSess                                      Counter64,
    anueGscNWFltrPkGtpTotCrSess                                     Counter64,
    anueGscNWFltrPkGtpV0CrSessT                                     DateAndTime,
    anueGscNWFltrPkGtpV1CrSessT                                     DateAndTime,
    anueGscNWFltrPkGtpV2CrSessT                                     DateAndTime,
    anueGscNWFltrPkGtpTotCrSessT                                    DateAndTime,
    anueGscNWFltrTotGtpV0DelSess                                    Counter64,
    anueGscNWFltrTotGtpV1DelSess                                    Counter64,
    anueGscNWFltrTotGtpV2DelSess                                    Counter64,
    anueGscNWFltrTotGtpTotDelSess                                   Counter64,
    anueGscNWFltrAvgGtpV0DelSess                                    Counter64,
    anueGscNWFltrAvgGtpV1DelSess                                    Counter64,
    anueGscNWFltrAvgGtpV2DelSess                                    Counter64,
    anueGscNWFltrAvgGtpTotDelSess                                   Counter64,
    anueGscNWFltrCurGtpV0DelSess                                    Counter64,
    anueGscNWFltrCurGtpV1DelSess                                    Counter64,
    anueGscNWFltrCurGtpV2DelSess                                    Counter64,
    anueGscNWFltrCurGtpTotDelSess                                   Counter64,
    anueGscNWFltrPkGtpV0DelSess                                     Counter64,
    anueGscNWFltrPkGtpV1DelSess                                     Counter64,
    anueGscNWFltrPkGtpV2DelSess                                     Counter64,
    anueGscNWFltrPkGtpTotDelSess                                    Counter64,
    anueGscNWFltrPkGtpV0DelSessT                                    DateAndTime,
    anueGscNWFltrPkGtpV1DelSessT                                    DateAndTime,
    anueGscNWFltrPkGtpV2DelSessT                                    DateAndTime,
    anueGscNWFltrPkGtpTotDelSessT                                   DateAndTime,
    anueGscNWFltrAvgGtpV0Bearers                                    Counter64,
    anueGscNWFltrAvgGtpV1Bearers                                    Counter64,
    anueGscNWFltrAvgGtpV2Bearers                                    Counter64,
    anueGscNWFltrAvgGtpTotBearers                                   Counter64,
    anueGscNWFltrCurGtpV0Bearers                                    Counter64,
    anueGscNWFltrCurGtpV1Bearers                                    Counter64,
    anueGscNWFltrCurGtpV2Bearers                                    Counter64,
    anueGscNWFltrCurGtpTotBearers                                   Counter64,
    anueGscNWFltrPkGtpV0Bearers                                     Counter64,
    anueGscNWFltrPkGtpV1Bearers                                     Counter64,
    anueGscNWFltrPkGtpV2Bearers                                     Counter64,
    anueGscNWFltrPkGtpTotBearers                                    Counter64,
    anueGscNWFltrPkGtpV0BearersT                                    DateAndTime,
    anueGscNWFltrPkGtpV1BearersT                                    DateAndTime,
    anueGscNWFltrPkGtpV2BearersT                                    DateAndTime,
    anueGscNWFltrPkGtpTotBearersT                                   DateAndTime,
    anueGscNWFltrAvgGtpV0Pkts                                       Counter64,
    anueGscNWFltrAvgGtpV1Pkts                                       Counter64,
    anueGscNWFltrAvgGtpV2Pkts                                       Counter64,
    anueGscNWFltrAvgGtpTotPkts                                      Counter64,
    anueGscNWFltrCurGtpV0Pkts                                       Counter64,
    anueGscNWFltrCurGtpV1Pkts                                       Counter64,
    anueGscNWFltrCurGtpV2Pkts                                       Counter64,
    anueGscNWFltrCurGtpTotPkts                                      Counter64,
    anueGscNWFltrTotGtpV1Pkts                                       Counter64,
    anueGscNWFltrTotGtpV0Pkts                                       Counter64,
    anueGscNWFltrTotGtpV2Pkts                                       Counter64,
    anueGscNWFltrTotGtpTotPkts                                      Counter64,
    anueGscNWFltrPkGtpV0Pkts                                        Counter64,
    anueGscNWFltrPkGtpV1Pkts                                        Counter64,
    anueGscNWFltrPkGtpV2Pkts                                        Counter64,
    anueGscNWFltrPkGtpTotPkts                                       Counter64,
    anueGscNWFltrPkGtpV0PktsT                                       DateAndTime,
    anueGscNWFltrPkGtpV1PktsT                                       DateAndTime,
    anueGscNWFltrPkGtpV2PktsT                                       DateAndTime,
    anueGscNWFltrPkGtpTotPktsT                                      DateAndTime,
    anueGscNWFltrTotGtpV0ToutSess                                   Counter64,
    anueGscNWFltrTotGtpV1ToutSess                                   Counter64,
    anueGscNWFltrTotGtpV2ToutSess                                   Counter64,
    anueGscNWFltrTotGtpTotToutSess                                  Counter64,
    anueGscNWFltrAvgGtpV0ToutSess                                   Counter64,
    anueGscNWFltrAvgGtpV1ToutSess                                   Counter64,
    anueGscNWFltrAvgGtpV2ToutSess                                   Counter64,
    anueGscNWFltrAvgGtpTotToutSess                                  Counter64,
    anueGscNWFltrCurGtpV0ToutSess                                   Counter64,
    anueGscNWFltrCurGtpV1ToutSess                                   Counter64,
    anueGscNWFltrCurGtpV2ToutSess                                   Counter64,
    anueGscNWFltrCurGtpTotToutSess                                  Counter64,
    anueGscNWFltrPkGtpV0ToutSess                                    Counter64,
    anueGscNWFltrPkGtpV1ToutSess                                    Counter64,
    anueGscNWFltrPkGtpV2ToutSess                                    Counter64,
    anueGscNWFltrPkGtpTotToutSess                                   Counter64,
    anueGscNWFltrPkGtpV0ToutSessT                                   DateAndTime,
    anueGscNWFltrPkGtpV1ToutSessT                                   DateAndTime,
    anueGscNWFltrPkGtpV2ToutSessT                                   DateAndTime,
    anueGscNWFltrPkGtpTotToutSessT                                  DateAndTime,
    anueGscNWFltrAvgGtpCPkts                                        Counter64,
    anueGscNWFltrAvgGtpUPkts                                        Counter64,
    anueGscNWFltrAvgDiameterPkts                                    Counter64,
    anueGscNWFltrAvgDnsPkts                                         Counter64,
    anueGscNWFltrAvgRadiusPkts                                      Counter64,
    anueGscNWFltrAvgNonGtpPkts                                      Counter64,
    anueGscNWFltrCurGtpCPkts                                        Counter64,
    anueGscNWFltrCurGtpUPkts                                        Counter64,
    anueGscNWFltrCurDiameterPkts                                    Counter64,
    anueGscNWFltrCurDnsPkts                                         Counter64,
    anueGscNWFltrCurRadiusPkts                                      Counter64,
    anueGscNWFltrCurNonGtpPkts                                      Counter64,
    anueGscNWFltrPkGtpCPkts                                         Counter64,
    anueGscNWFltrPkGtpUPkts                                         Counter64,
    anueGscNWFltrPkDiameterPkts                                     Counter64,
    anueGscNWFltrPkDnsPkts                                          Counter64,
    anueGscNWFltrPkRadiusPkts                                       Counter64,
    anueGscNWFltrPkNonGtpPkts                                       Counter64,
    anueGscNWFltrPkGtpCPktsT                                        DateAndTime,
    anueGscNWFltrPkGtpUPktsT                                        DateAndTime,
    anueGscNWFltrPkDiameterPktsT                                    DateAndTime,
    anueGscNWFltrPkDnsPktsT                                         DateAndTime,
    anueGscNWFltrPkRadiusPktsT                                      DateAndTime,
    anueGscNWFltrPkNonGtpPktsT                                      DateAndTime,
    anueGscNWFltrTotGtpCPkts                                        Counter64,
    anueGscNWFltrTotGtpUPkts                                        Counter64,
    anueGscNWFltrTotDiameterPkts                                    Counter64,
    anueGscNWFltrTotDnsPkts                                         Counter64,
    anueGscNWFltrTotRadiusPkts                                      Counter64,
    anueGscNWFltrTotNonGtpPkts                                      Counter64,
    anueGscNWFltrTotGscDropPkts                                     Counter64,
    anueGscNWFltrCurGscSessLoad                                     CounterBasedGauge64,
    anueGscNWFltrAvgGscSessLoad                                     CounterBasedGauge64,
    anueGscNWFltrPeakGscSessLoad                                    CounterBasedGauge64,
    anueGscNWFltrPeakGscSessLoadT                                   DateAndTime,
    anueGscNWFltrCurNetwElemLoad                                    CounterBasedGauge64,
    anueGscNWFltrPeakNetwElemLoad                                   CounterBasedGauge64,
    anueGscNWFltrPeakNetwElemLoadT                                  DateAndTime,
    anueGscNWFltrCurReqRespLoad                                     CounterBasedGauge64,
    anueGscNWFltrPeakReqRespLoad                                    CounterBasedGauge64,
    anueGscNWFltrPeakReqRespLoadT                                   DateAndTime,
    anueGscNWFltrCurFragLoad                                        CounterBasedGauge64,
    anueGscNWFltrPeakFragLoad                                       CounterBasedGauge64,
    anueGscNWFltrPeakFragLoadT                                      DateAndTime,
    anueGscNWFltrAvgGscUnassignedSess                               Counter64,
    anueGscNWFltrCurGscUnassignedSess                               Counter64,
    anueGscNWFltrPkGscUnassignedSess                                Counter64,
    anueGscNWFltrPkGscUnassignedSessT                               DateAndTime,
    anueGscNWFltrTotGscUnassignedSess                               Counter64,
    anueGscNWFltrAvgUnprocReq                                       Counter64,
    anueGscNWFltrCurUnprocReq                                       Counter64,
    anueGscNWFltrPkUnprocReq                                        Counter64,
    anueGscNWFltrPkUnprocReqT                                       DateAndTime,
    anueGscNWFltrTotUnprocReq                                       Counter64,
    anueGscNWFltrAvgTdOutReq                                        Counter64,
    anueGscNWFltrCurTdOutReq                                        Counter64,
    anueGscNWFltrPkTdOutReq                                         Counter64,
    anueGscNWFltrPkTdOutReqT                                        DateAndTime,
    anueGscNWFltrTotTdOutReq                                        Counter64,
    anueGscNWFltrAvgUnmatchedResp                                   Counter64,
    anueGscNWFltrCurUnmatchedResp                                   Counter64,
    anueGscNWFltrPkUnmatchedResp                                    Counter64,
    anueGscNWFltrPkUnmatchedRespT                                   DateAndTime,
    anueGscNWFltrTotUnmatchedResp                                   Counter64,
    anueGscNWFltrOverloadErrCode                                    Counter64,
    anueGscNWFltrOverloadT                                          DateAndTime }


anueNtoStageGscNetworkFilterType OBJECT-TYPE
    SYNTAX  AnueFilterTypeDT
    MAX-ACCESS read-only
    STATUS  current
    DESCRIPTION ""
    -- 1.3.6.1.4.1.32620.1.1.4.100.1.1
    ::= { anueNtoStageGscNetworkFilterEntry 1 }


anueNtoStageGscNetworkFilterNumber OBJECT-TYPE
    SYNTAX  Integer32 (1..2147483647)
    MAX-ACCESS read-only
    STATUS  current
    DESCRIPTION ""
    -- 1.3.6.1.4.1.32620.1.1.4.100.1.2
    ::= { anueNtoStageGscNetworkFilterEntry 2 }


anueGscNWFltrExcSess OBJECT-TYPE
    SYNTAX  Counter64
    MAX-ACCESS read-only
    STATUS  current
    DESCRIPTION ""
    -- 1.3.6.1.4.1.32620.1.1.4.100.1.3
    ::= { anueNtoStageGscNetworkFilterEntry 3 }


anueNtoStageGscNetworkFilterFeature OBJECT-TYPE
    SYNTAX  AnueStageType
    MAX-ACCESS read-only
    STATUS  current
    DESCRIPTION ""
    -- 1.3.6.1.4.1.32620.1.1.4.100.1.4
    ::= { anueNtoStageGscNetworkFilterEntry 4 }


anueGscNWFltrAvgGscPktFrag OBJECT-TYPE
    SYNTAX  Counter64
    MAX-ACCESS read-only
    STATUS  current
    DESCRIPTION ""
    -- 1.3.6.1.4.1.32620.1.1.4.100.1.5
    ::= { anueNtoStageGscNetworkFilterEntry 5 }


anueGscNWFltrAvgTdoutFrag OBJECT-TYPE
    SYNTAX  Counter64
    MAX-ACCESS read-only
    STATUS  current
    DESCRIPTION ""
    -- 1.3.6.1.4.1.32620.1.1.4.100.1.6
    ::= { anueNtoStageGscNetworkFilterEntry 6 }


anueGscNWFltrCurPacketFrag OBJECT-TYPE
    SYNTAX  Counter64
    MAX-ACCESS read-only
    STATUS  current
    DESCRIPTION ""
    -- 1.3.6.1.4.1.32620.1.1.4.100.1.7
    ::= { anueNtoStageGscNetworkFilterEntry 7 }


anueGscNWFltrCurTdoutFrag OBJECT-TYPE
    SYNTAX  Counter64
    MAX-ACCESS read-only
    STATUS  current
    DESCRIPTION ""
    -- 1.3.6.1.4.1.32620.1.1.4.100.1.8
    ::= { anueNtoStageGscNetworkFilterEntry 8 }


anueGscNWFltrPkPacketFrag OBJECT-TYPE
    SYNTAX  Counter64
    MAX-ACCESS read-only
    STATUS  current
    DESCRIPTION ""
    -- 1.3.6.1.4.1.32620.1.1.4.100.1.9
    ::= { anueNtoStageGscNetworkFilterEntry 9 }


anueGscNWFltrPkPacketFragT OBJECT-TYPE
    SYNTAX  DateAndTime
    MAX-ACCESS read-only
    STATUS  current
    DESCRIPTION ""
    -- 1.3.6.1.4.1.32620.1.1.4.100.1.10
    ::= { anueNtoStageGscNetworkFilterEntry 10 }


anueGscNWFltrPkTdOutFrag OBJECT-TYPE
    SYNTAX  Counter64
    MAX-ACCESS read-only
    STATUS  current
    DESCRIPTION ""
    -- 1.3.6.1.4.1.32620.1.1.4.100.1.11
    ::= { anueNtoStageGscNetworkFilterEntry 11 }


anueGscNWFltrPkTdOutFragT OBJECT-TYPE
    SYNTAX  DateAndTime
    MAX-ACCESS read-only
    STATUS  current
    DESCRIPTION ""
    -- 1.3.6.1.4.1.32620.1.1.4.100.1.12
    ::= { anueNtoStageGscNetworkFilterEntry 12 }


anueGscNWFltrTotFrag OBJECT-TYPE
    SYNTAX  Counter64
    MAX-ACCESS read-only
    STATUS  current
    DESCRIPTION ""
    -- 1.3.6.1.4.1.32620.1.1.4.100.1.13
    ::= { anueNtoStageGscNetworkFilterEntry 13 }


anueGscNWFltrTotRxCountFrag OBJECT-TYPE
    SYNTAX  Counter64
    MAX-ACCESS read-only
    STATUS  current
    DESCRIPTION ""
    -- 1.3.6.1.4.1.32620.1.1.4.100.1.14
    ::= { anueNtoStageGscNetworkFilterEntry 14 }


anueGscNWFltrTotTdOutFrag OBJECT-TYPE
    SYNTAX  Counter64
    MAX-ACCESS read-only
    STATUS  current
    DESCRIPTION ""
    -- 1.3.6.1.4.1.32620.1.1.4.100.1.15
    ::= { anueNtoStageGscNetworkFilterEntry 15 }


anueGscNWFltrAvgCompFragPkts OBJECT-TYPE
    SYNTAX  Counter64
    MAX-ACCESS read-only
    STATUS  current
    DESCRIPTION ""
    -- 1.3.6.1.4.1.32620.1.1.4.100.1.16
    ::= { anueNtoStageGscNetworkFilterEntry 16 }


anueGscNWFltrAvgCompFragPktsPerc OBJECT-TYPE
    SYNTAX  Counter64
    MAX-ACCESS read-only
    STATUS  current
    DESCRIPTION ""
    -- 1.3.6.1.4.1.32620.1.1.4.100.1.17
    ::= { anueNtoStageGscNetworkFilterEntry 17 }


anueGscNWFltrAvgIncomFragPkts OBJECT-TYPE
    SYNTAX  Counter64
    MAX-ACCESS read-only
    STATUS  current
    DESCRIPTION ""
    -- 1.3.6.1.4.1.32620.1.1.4.100.1.18
    ::= { anueNtoStageGscNetworkFilterEntry 18 }


anueGscNWFltrCurCompFragPkts OBJECT-TYPE
    SYNTAX  Counter64
    MAX-ACCESS read-only
    STATUS  current
    DESCRIPTION ""
    -- 1.3.6.1.4.1.32620.1.1.4.100.1.19
    ::= { anueNtoStageGscNetworkFilterEntry 19 }


anueGscNWFltrCurCompFragPktsPerc OBJECT-TYPE
    SYNTAX  Counter64
    MAX-ACCESS read-only
    STATUS  current
    DESCRIPTION ""
    -- 1.3.6.1.4.1.32620.1.1.4.100.1.20
    ::= { anueNtoStageGscNetworkFilterEntry 20 }


anueGscNWFltrCurIncomFragPkts OBJECT-TYPE
    SYNTAX  Counter64
    MAX-ACCESS read-only
    STATUS  current
    DESCRIPTION ""
    -- 1.3.6.1.4.1.32620.1.1.4.100.1.21
    ::= { anueNtoStageGscNetworkFilterEntry 21 }


anueGscNWFltrPkCompFragPkts OBJECT-TYPE
    SYNTAX  Counter64
    MAX-ACCESS read-only
    STATUS  current
    DESCRIPTION ""
    -- 1.3.6.1.4.1.32620.1.1.4.100.1.22
    ::= { anueNtoStageGscNetworkFilterEntry 22 }

anueGscNWFltrPkCompFragPktsT OBJECT-TYPE
    SYNTAX  DateAndTime
    MAX-ACCESS read-only
    STATUS  current
    DESCRIPTION ""
    -- 1.3.6.1.4.1.32620.1.1.4.100.1.23
    ::= { anueNtoStageGscNetworkFilterEntry 23 }


anueGscNWFltrPkCompFragPktsPerc OBJECT-TYPE
    SYNTAX  Counter64
    MAX-ACCESS read-only
    STATUS  current
    DESCRIPTION ""
    -- 1.3.6.1.4.1.32620.1.1.4.100.1.24
    ::= { anueNtoStageGscNetworkFilterEntry 24 }


anueGscNWFltrPkCompFragPktsPercT OBJECT-TYPE
    SYNTAX  DateAndTime
    MAX-ACCESS read-only
    STATUS  current
    DESCRIPTION ""
    -- 1.3.6.1.4.1.32620.1.1.4.100.1.25
    ::= { anueNtoStageGscNetworkFilterEntry 25 }


anueGscNWFltrPkIncomFragPkts OBJECT-TYPE
    SYNTAX  Counter64
    MAX-ACCESS read-only
    STATUS  current
    DESCRIPTION ""
    -- 1.3.6.1.4.1.32620.1.1.4.100.1.26
    ::= { anueNtoStageGscNetworkFilterEntry 26 }


anueGscNWFltrPkIncomFragPktsT OBJECT-TYPE
    SYNTAX  DateAndTime
    MAX-ACCESS read-only
    STATUS  current
    DESCRIPTION ""
    -- 1.3.6.1.4.1.32620.1.1.4.100.1.27
    ::= { anueNtoStageGscNetworkFilterEntry 27 }


anueGscNWFltrPkTotCompFragPkts OBJECT-TYPE
    SYNTAX  Counter64
    MAX-ACCESS read-only
    STATUS  current
    DESCRIPTION ""
    -- 1.3.6.1.4.1.32620.1.1.4.100.1.28
    ::= { anueNtoStageGscNetworkFilterEntry 28 }


anueGscNWFltrAvgActiveUsers OBJECT-TYPE
    SYNTAX  Counter64
    MAX-ACCESS read-only
    STATUS  current
    DESCRIPTION ""
    -- 1.3.6.1.4.1.32620.1.1.4.100.1.29
    ::= { anueNtoStageGscNetworkFilterEntry 29 }


anueGscNWFltrCurActiveUsers OBJECT-TYPE
    SYNTAX  Counter64
    MAX-ACCESS read-only
    STATUS  current
    DESCRIPTION ""
    -- 1.3.6.1.4.1.32620.1.1.4.100.1.30
    ::= { anueNtoStageGscNetworkFilterEntry 30 }


anueGscNWFltrPkActiveUsers OBJECT-TYPE
    SYNTAX  Counter64
    MAX-ACCESS read-only
    STATUS  current
    DESCRIPTION ""
    -- 1.3.6.1.4.1.32620.1.1.4.100.1.31
    ::= { anueNtoStageGscNetworkFilterEntry 31 }


anueGscNWFltrPkActiveUsersT OBJECT-TYPE
    SYNTAX  DateAndTime
    MAX-ACCESS read-only
    STATUS  current
    DESCRIPTION ""
    -- 1.3.6.1.4.1.32620.1.1.4.100.1.32
    ::= { anueNtoStageGscNetworkFilterEntry 32 }


anueGscNWFltrAvgExcSess OBJECT-TYPE
    SYNTAX  Counter64
    MAX-ACCESS read-only
    STATUS  current
    DESCRIPTION ""
    -- 1.3.6.1.4.1.32620.1.1.4.100.1.33
    ::= { anueNtoStageGscNetworkFilterEntry 33 }


anueGscNWFltrCurExcSess OBJECT-TYPE
    SYNTAX  Counter64
    MAX-ACCESS read-only
    STATUS  current
    DESCRIPTION ""
    -- 1.3.6.1.4.1.32620.1.1.4.100.1.34
    ::= { anueNtoStageGscNetworkFilterEntry 34 }


anueGscNWFltrPkExcSess OBJECT-TYPE
    SYNTAX  Counter64
    MAX-ACCESS read-only
    STATUS  current
    DESCRIPTION ""
    -- 1.3.6.1.4.1.32620.1.1.4.100.1.35
    ::= { anueNtoStageGscNetworkFilterEntry 35 }


anueGscNWFltrPkExcSessT OBJECT-TYPE
    SYNTAX  DateAndTime
    MAX-ACCESS read-only
    STATUS  current
    DESCRIPTION ""
    -- 1.3.6.1.4.1.32620.1.1.4.100.1.36
    ::= { anueNtoStageGscNetworkFilterEntry 36 }


anueGscNWFltrTotExcSess OBJECT-TYPE
    SYNTAX  Counter64
    MAX-ACCESS read-only
    STATUS  current
    DESCRIPTION ""
    -- 1.3.6.1.4.1.32620.1.1.4.100.1.37
    ::= { anueNtoStageGscNetworkFilterEntry 37 }


anueGscNWFltrTotGtpV0CrSess OBJECT-TYPE
    SYNTAX  Counter64
    MAX-ACCESS read-only
    STATUS  current
    DESCRIPTION ""
    -- 1.3.6.1.4.1.32620.1.1.4.100.1.38
    ::= { anueNtoStageGscNetworkFilterEntry 38 }


anueGscNWFltrTotGtpV1CrSess OBJECT-TYPE
    SYNTAX  Counter64
    MAX-ACCESS read-only
    STATUS  current
    DESCRIPTION ""
    -- 1.3.6.1.4.1.32620.1.1.4.100.1.39
    ::= { anueNtoStageGscNetworkFilterEntry 39 }


anueGscNWFltrTotGtpV2CrSess OBJECT-TYPE
    SYNTAX  Counter64
    MAX-ACCESS read-only
    STATUS  current
    DESCRIPTION ""
    -- 1.3.6.1.4.1.32620.1.1.4.100.1.40
    ::= { anueNtoStageGscNetworkFilterEntry 40 }


anueGscNWFltrTotGtpTotCrSess OBJECT-TYPE
    SYNTAX  Counter64
    MAX-ACCESS read-only
    STATUS  current
    DESCRIPTION ""
    -- 1.3.6.1.4.1.32620.1.1.4.100.1.41
    ::= { anueNtoStageGscNetworkFilterEntry 41 }


anueGscNWFltrAvgGtpV0CrSess OBJECT-TYPE
    SYNTAX  Counter64
    MAX-ACCESS read-only
    STATUS  current
    DESCRIPTION ""
    -- 1.3.6.1.4.1.32620.1.1.4.100.1.42
    ::= { anueNtoStageGscNetworkFilterEntry 42 }


anueGscNWFltrAvgGtpV1CrSess OBJECT-TYPE
    SYNTAX  Counter64
    MAX-ACCESS read-only
    STATUS  current
    DESCRIPTION ""
    -- 1.3.6.1.4.1.32620.1.1.4.100.1.43
    ::= { anueNtoStageGscNetworkFilterEntry 43 }


anueGscNWFltrAvgGtpV2CrSess OBJECT-TYPE
    SYNTAX  Counter64
    MAX-ACCESS read-only
    STATUS  current
    DESCRIPTION ""
    -- 1.3.6.1.4.1.32620.1.1.4.100.1.44
    ::= { anueNtoStageGscNetworkFilterEntry 44 }


anueGscNWFltrAvgGtpTotCrSess OBJECT-TYPE
    SYNTAX  Counter64
    MAX-ACCESS read-only
    STATUS  current
    DESCRIPTION ""
    -- 1.3.6.1.4.1.32620.1.1.4.100.1.45
    ::= { anueNtoStageGscNetworkFilterEntry 45 }


anueGscNWFltrCurGtpV0CrSess OBJECT-TYPE
    SYNTAX  Counter64
    MAX-ACCESS read-only
    STATUS  current
    DESCRIPTION ""
    -- 1.3.6.1.4.1.32620.1.1.4.100.1.46
    ::= { anueNtoStageGscNetworkFilterEntry 46 }


anueGscNWFltrCurGtpV1CrSess OBJECT-TYPE
    SYNTAX  Counter64
    MAX-ACCESS read-only
    STATUS  current
    DESCRIPTION ""
    -- 1.3.6.1.4.1.32620.1.1.4.100.1.47
    ::= { anueNtoStageGscNetworkFilterEntry 47 }


anueGscNWFltrCurGtpV2CrSess OBJECT-TYPE
    SYNTAX  Counter64
    MAX-ACCESS read-only
    STATUS  current
    DESCRIPTION ""
    -- 1.3.6.1.4.1.32620.1.1.4.100.1.48
    ::= { anueNtoStageGscNetworkFilterEntry 48 }


anueGscNWFltrCurGtpTotCrSess OBJECT-TYPE
    SYNTAX  Counter64
    MAX-ACCESS read-only
    STATUS  current
    DESCRIPTION ""
    -- 1.3.6.1.4.1.32620.1.1.4.100.1.49
    ::= { anueNtoStageGscNetworkFilterEntry 49 }


anueGscNWFltrPkGtpV0CrSess OBJECT-TYPE
    SYNTAX  Counter64
    MAX-ACCESS read-only
    STATUS  current
    DESCRIPTION ""
    -- 1.3.6.1.4.1.32620.1.1.4.100.1.50
    ::= { anueNtoStageGscNetworkFilterEntry 50 }


anueGscNWFltrPkGtpV1CrSess OBJECT-TYPE
    SYNTAX  Counter64
    MAX-ACCESS read-only
    STATUS  current
    DESCRIPTION ""
    -- 1.3.6.1.4.1.32620.1.1.4.100.1.51
    ::= { anueNtoStageGscNetworkFilterEntry 51 }


anueGscNWFltrPkGtpV2CrSess OBJECT-TYPE
    SYNTAX  Counter64
    MAX-ACCESS read-only
    STATUS  current
    DESCRIPTION ""
    -- 1.3.6.1.4.1.32620.1.1.4.100.1.52
    ::= { anueNtoStageGscNetworkFilterEntry 52 }


anueGscNWFltrPkGtpTotCrSess OBJECT-TYPE
    SYNTAX  Counter64
    MAX-ACCESS read-only
    STATUS  current
    DESCRIPTION ""
    -- 1.3.6.1.4.1.32620.1.1.4.100.1.53
    ::= { anueNtoStageGscNetworkFilterEntry 53 }


anueGscNWFltrPkGtpV0CrSessT OBJECT-TYPE
    SYNTAX  DateAndTime
    MAX-ACCESS read-only
    STATUS  current
    DESCRIPTION ""
    -- 1.3.6.1.4.1.32620.1.1.4.100.1.54
    ::= { anueNtoStageGscNetworkFilterEntry 54 }


anueGscNWFltrPkGtpV1CrSessT OBJECT-TYPE
    SYNTAX  DateAndTime
    MAX-ACCESS read-only
    STATUS  current
    DESCRIPTION ""
    -- 1.3.6.1.4.1.32620.1.1.4.100.1.55
    ::= { anueNtoStageGscNetworkFilterEntry 55 }


anueGscNWFltrPkGtpV2CrSessT OBJECT-TYPE
    SYNTAX  DateAndTime
    MAX-ACCESS read-only
    STATUS  current
    DESCRIPTION ""
    -- 1.3.6.1.4.1.32620.1.1.4.100.1.56
    ::= { anueNtoStageGscNetworkFilterEntry 56 }


anueGscNWFltrPkGtpTotCrSessT OBJECT-TYPE
    SYNTAX  DateAndTime
    MAX-ACCESS read-only
    STATUS  current
    DESCRIPTION ""
    -- 1.3.6.1.4.1.32620.1.1.4.100.1.57
    ::= { anueNtoStageGscNetworkFilterEntry 57 }


anueGscNWFltrTotGtpV0DelSess OBJECT-TYPE
    SYNTAX  Counter64
    MAX-ACCESS read-only
    STATUS  current
    DESCRIPTION ""
    -- 1.3.6.1.4.1.32620.1.1.4.100.1.58
    ::= { anueNtoStageGscNetworkFilterEntry 58 }


anueGscNWFltrTotGtpV1DelSess OBJECT-TYPE
    SYNTAX  Counter64
    MAX-ACCESS read-only
    STATUS  current
    DESCRIPTION ""
    -- 1.3.6.1.4.1.32620.1.1.4.100.1.59
    ::= { anueNtoStageGscNetworkFilterEntry 59 }


anueGscNWFltrTotGtpV2DelSess OBJECT-TYPE
    SYNTAX  Counter64
    MAX-ACCESS read-only
    STATUS  current
    DESCRIPTION ""
    -- 1.3.6.1.4.1.32620.1.1.4.100.1.60
    ::= { anueNtoStageGscNetworkFilterEntry 60 }


anueGscNWFltrTotGtpTotDelSess OBJECT-TYPE
    SYNTAX  Counter64
    MAX-ACCESS read-only
    STATUS  current
    DESCRIPTION ""
    -- 1.3.6.1.4.1.32620.1.1.4.100.1.61
    ::= { anueNtoStageGscNetworkFilterEntry 61 }


anueGscNWFltrAvgGtpV0DelSess OBJECT-TYPE
    SYNTAX  Counter64
    MAX-ACCESS read-only
    STATUS  current
    DESCRIPTION ""
    -- 1.3.6.1.4.1.32620.1.1.4.100.1.62
    ::= { anueNtoStageGscNetworkFilterEntry 62 }


anueGscNWFltrAvgGtpV1DelSess OBJECT-TYPE
    SYNTAX  Counter64
    MAX-ACCESS read-only
    STATUS  current
    DESCRIPTION ""
    -- 1.3.6.1.4.1.32620.1.1.4.100.1.63
    ::= { anueNtoStageGscNetworkFilterEntry 63 }


anueGscNWFltrAvgGtpV2DelSess OBJECT-TYPE
    SYNTAX  Counter64
    MAX-ACCESS read-only
    STATUS  current
    DESCRIPTION ""
    -- 1.3.6.1.4.1.32620.1.1.4.100.1.64
    ::= { anueNtoStageGscNetworkFilterEntry 64 }


anueGscNWFltrAvgGtpTotDelSess OBJECT-TYPE
    SYNTAX  Counter64
    MAX-ACCESS read-only
    STATUS  current
    DESCRIPTION ""
    -- 1.3.6.1.4.1.32620.1.1.4.100.1.65
    ::= { anueNtoStageGscNetworkFilterEntry 65 }


anueGscNWFltrCurGtpV0DelSess OBJECT-TYPE
    SYNTAX  Counter64
    MAX-ACCESS read-only
    STATUS  current
    DESCRIPTION ""
    -- 1.3.6.1.4.1.32620.1.1.4.100.1.66
    ::= { anueNtoStageGscNetworkFilterEntry 66 }


anueGscNWFltrCurGtpV1DelSess OBJECT-TYPE
    SYNTAX  Counter64
    MAX-ACCESS read-only
    STATUS  current
    DESCRIPTION ""
    -- 1.3.6.1.4.1.32620.1.1.4.100.1.67
    ::= { anueNtoStageGscNetworkFilterEntry 67 }


anueGscNWFltrCurGtpV2DelSess OBJECT-TYPE
    SYNTAX  Counter64
    MAX-ACCESS read-only
    STATUS  current
    DESCRIPTION ""
    -- 1.3.6.1.4.1.32620.1.1.4.100.1.68
    ::= { anueNtoStageGscNetworkFilterEntry 68 }


anueGscNWFltrCurGtpTotDelSess OBJECT-TYPE
    SYNTAX  Counter64
    MAX-ACCESS read-only
    STATUS  current
    DESCRIPTION ""
    -- 1.3.6.1.4.1.32620.1.1.4.100.1.69
    ::= { anueNtoStageGscNetworkFilterEntry 69 }


anueGscNWFltrPkGtpV0DelSess OBJECT-TYPE
    SYNTAX  Counter64
    MAX-ACCESS read-only
    STATUS  current
    DESCRIPTION ""
    -- 1.3.6.1.4.1.32620.1.1.4.100.1.70
    ::= { anueNtoStageGscNetworkFilterEntry 70 }


anueGscNWFltrPkGtpV1DelSess OBJECT-TYPE
    SYNTAX  Counter64
    MAX-ACCESS read-only
    STATUS  current
    DESCRIPTION ""
    -- 1.3.6.1.4.1.32620.1.1.4.100.1.71
    ::= { anueNtoStageGscNetworkFilterEntry 71 }


anueGscNWFltrPkGtpV2DelSess OBJECT-TYPE
    SYNTAX  Counter64
    MAX-ACCESS read-only
    STATUS  current
    DESCRIPTION ""
    -- 1.3.6.1.4.1.32620.1.1.4.100.1.72
    ::= { anueNtoStageGscNetworkFilterEntry 72 }


anueGscNWFltrPkGtpTotDelSess OBJECT-TYPE
    SYNTAX  Counter64
    MAX-ACCESS read-only
    STATUS  current
    DESCRIPTION ""
    -- 1.3.6.1.4.1.32620.1.1.4.100.1.73
    ::= { anueNtoStageGscNetworkFilterEntry 73 }


anueGscNWFltrPkGtpV0DelSessT OBJECT-TYPE
    SYNTAX  DateAndTime
    MAX-ACCESS read-only
    STATUS  current
    DESCRIPTION ""
    -- 1.3.6.1.4.1.32620.1.1.4.100.1.74
    ::= { anueNtoStageGscNetworkFilterEntry 74 }


anueGscNWFltrPkGtpV1DelSessT OBJECT-TYPE
    SYNTAX  DateAndTime
    MAX-ACCESS read-only
    STATUS  current
    DESCRIPTION ""
    -- 1.3.6.1.4.1.32620.1.1.4.100.1.75
    ::= { anueNtoStageGscNetworkFilterEntry 75 }


anueGscNWFltrPkGtpV2DelSessT OBJECT-TYPE
    SYNTAX  DateAndTime
    MAX-ACCESS read-only
    STATUS  current
    DESCRIPTION ""
    -- 1.3.6.1.4.1.32620.1.1.4.100.1.76
    ::= { anueNtoStageGscNetworkFilterEntry 76 }


anueGscNWFltrPkGtpTotDelSessT OBJECT-TYPE
    SYNTAX  DateAndTime
    MAX-ACCESS read-only
    STATUS  current
    DESCRIPTION ""
    -- 1.3.6.1.4.1.32620.1.1.4.100.1.77
    ::= { anueNtoStageGscNetworkFilterEntry 77 }


anueGscNWFltrAvgGtpV0Bearers OBJECT-TYPE
    SYNTAX  Counter64
    MAX-ACCESS read-only
    STATUS  current
    DESCRIPTION ""
    -- 1.3.6.1.4.1.32620.1.1.4.100.1.78
    ::= { anueNtoStageGscNetworkFilterEntry 78 }


anueGscNWFltrAvgGtpV1Bearers OBJECT-TYPE
    SYNTAX  Counter64
    MAX-ACCESS read-only
    STATUS  current
    DESCRIPTION ""
    -- 1.3.6.1.4.1.32620.1.1.4.100.1.79
    ::= { anueNtoStageGscNetworkFilterEntry 79 }


anueGscNWFltrAvgGtpV2Bearers OBJECT-TYPE
    SYNTAX  Counter64
    MAX-ACCESS read-only
    STATUS  current
    DESCRIPTION ""
    -- 1.3.6.1.4.1.32620.1.1.4.100.1.80
    ::= { anueNtoStageGscNetworkFilterEntry 80 }


anueGscNWFltrAvgGtpTotBearers OBJECT-TYPE
    SYNTAX  Counter64
    MAX-ACCESS read-only
    STATUS  current
    DESCRIPTION ""
    -- 1.3.6.1.4.1.32620.1.1.4.100.1.81
    ::= { anueNtoStageGscNetworkFilterEntry 81 }


anueGscNWFltrCurGtpV0Bearers OBJECT-TYPE
    SYNTAX  Counter64
    MAX-ACCESS read-only
    STATUS  current
    DESCRIPTION ""
    -- 1.3.6.1.4.1.32620.1.1.4.100.1.82
    ::= { anueNtoStageGscNetworkFilterEntry 82 }


anueGscNWFltrCurGtpV1Bearers OBJECT-TYPE
    SYNTAX  Counter64
    MAX-ACCESS read-only
    STATUS  current
    DESCRIPTION ""
    -- 1.3.6.1.4.1.32620.1.1.4.100.1.83
    ::= { anueNtoStageGscNetworkFilterEntry 83 }


anueGscNWFltrCurGtpV2Bearers OBJECT-TYPE
    SYNTAX  Counter64
    MAX-ACCESS read-only
    STATUS  current
    DESCRIPTION ""
    -- 1.3.6.1.4.1.32620.1.1.4.100.1.84
    ::= { anueNtoStageGscNetworkFilterEntry 84 }


anueGscNWFltrCurGtpTotBearers OBJECT-TYPE
    SYNTAX  Counter64
    MAX-ACCESS read-only
    STATUS  current
    DESCRIPTION ""
    -- 1.3.6.1.4.1.32620.1.1.4.100.1.85
    ::= { anueNtoStageGscNetworkFilterEntry 85 }


anueGscNWFltrPkGtpV0Bearers OBJECT-TYPE
    SYNTAX  Counter64
    MAX-ACCESS read-only
    STATUS  current
    DESCRIPTION ""
    -- 1.3.6.1.4.1.32620.1.1.4.100.1.86
    ::= { anueNtoStageGscNetworkFilterEntry 86 }


anueGscNWFltrPkGtpV1Bearers OBJECT-TYPE
    SYNTAX  Counter64
    MAX-ACCESS read-only
    STATUS  current
    DESCRIPTION ""
    -- 1.3.6.1.4.1.32620.1.1.4.100.1.87
    ::= { anueNtoStageGscNetworkFilterEntry 87 }


anueGscNWFltrPkGtpV2Bearers OBJECT-TYPE
    SYNTAX  Counter64
    MAX-ACCESS read-only
    STATUS  current
    DESCRIPTION ""
    -- 1.3.6.1.4.1.32620.1.1.4.100.1.88
    ::= { anueNtoStageGscNetworkFilterEntry 88 }


anueGscNWFltrPkGtpTotBearers OBJECT-TYPE
    SYNTAX  Counter64
    MAX-ACCESS read-only
    STATUS  current
    DESCRIPTION ""
    -- 1.3.6.1.4.1.32620.1.1.4.100.1.89
    ::= { anueNtoStageGscNetworkFilterEntry 89 }


anueGscNWFltrPkGtpV0BearersT OBJECT-TYPE
    SYNTAX  DateAndTime
    MAX-ACCESS read-only
    STATUS  current
    DESCRIPTION ""
    -- 1.3.6.1.4.1.32620.1.1.4.100.1.90
    ::= { anueNtoStageGscNetworkFilterEntry 90 }


anueGscNWFltrPkGtpV1BearersT OBJECT-TYPE
    SYNTAX  DateAndTime
    MAX-ACCESS read-only
    STATUS  current
    DESCRIPTION ""
    -- 1.3.6.1.4.1.32620.1.1.4.100.1.91
    ::= { anueNtoStageGscNetworkFilterEntry 91 }


anueGscNWFltrPkGtpV2BearersT OBJECT-TYPE
    SYNTAX  DateAndTime
    MAX-ACCESS read-only
    STATUS  current
    DESCRIPTION ""
    -- 1.3.6.1.4.1.32620.1.1.4.100.1.92
    ::= { anueNtoStageGscNetworkFilterEntry 92 }


anueGscNWFltrPkGtpTotBearersT OBJECT-TYPE
    SYNTAX  DateAndTime
    MAX-ACCESS read-only
    STATUS  current
    DESCRIPTION ""
    -- 1.3.6.1.4.1.32620.1.1.4.100.1.93
    ::= { anueNtoStageGscNetworkFilterEntry 93 }


anueGscNWFltrAvgGtpV0Pkts OBJECT-TYPE
    SYNTAX  Counter64
    MAX-ACCESS read-only
    STATUS  current
    DESCRIPTION ""
    -- 1.3.6.1.4.1.32620.1.1.4.100.1.94
    ::= { anueNtoStageGscNetworkFilterEntry 94 }


anueGscNWFltrAvgGtpV1Pkts OBJECT-TYPE
    SYNTAX  Counter64
    MAX-ACCESS read-only
    STATUS  current
    DESCRIPTION ""
    -- 1.3.6.1.4.1.32620.1.1.4.100.1.95
    ::= { anueNtoStageGscNetworkFilterEntry 95 }


anueGscNWFltrAvgGtpV2Pkts OBJECT-TYPE
    SYNTAX  Counter64
    MAX-ACCESS read-only
    STATUS  current
    DESCRIPTION ""
    -- 1.3.6.1.4.1.32620.1.1.4.100.1.96
    ::= { anueNtoStageGscNetworkFilterEntry 96 }


anueGscNWFltrAvgGtpTotPkts OBJECT-TYPE
    SYNTAX  Counter64
    MAX-ACCESS read-only
    STATUS  current
    DESCRIPTION ""
    -- 1.3.6.1.4.1.32620.1.1.4.100.1.97
    ::= { anueNtoStageGscNetworkFilterEntry 97 }


anueGscNWFltrCurGtpV0Pkts OBJECT-TYPE
    SYNTAX  Counter64
    MAX-ACCESS read-only
    STATUS  current
    DESCRIPTION ""
    -- 1.3.6.1.4.1.32620.1.1.4.100.1.98
    ::= { anueNtoStageGscNetworkFilterEntry 98 }


anueGscNWFltrCurGtpV1Pkts OBJECT-TYPE
    SYNTAX  Counter64
    MAX-ACCESS read-only
    STATUS  current
    DESCRIPTION ""
    -- 1.3.6.1.4.1.32620.1.1.4.100.1.99
    ::= { anueNtoStageGscNetworkFilterEntry 99 }


anueGscNWFltrCurGtpV2Pkts OBJECT-TYPE
    SYNTAX  Counter64
    MAX-ACCESS read-only
    STATUS  current
    DESCRIPTION ""
    -- 1.3.6.1.4.1.32620.1.1.4.100.1.100
    ::= { anueNtoStageGscNetworkFilterEntry 100 }


anueGscNWFltrCurGtpTotPkts OBJECT-TYPE
    SYNTAX  Counter64
    MAX-ACCESS read-only
    STATUS  current
    DESCRIPTION ""
    -- 1.3.6.1.4.1.32620.1.1.4.100.1.101
    ::= { anueNtoStageGscNetworkFilterEntry 101 }


anueGscNWFltrTotGtpV1Pkts OBJECT-TYPE
    SYNTAX  Counter64
    MAX-ACCESS read-only
    STATUS  current
    DESCRIPTION ""
    -- 1.3.6.1.4.1.32620.1.1.4.100.1.102
    ::= { anueNtoStageGscNetworkFilterEntry 102 }


anueGscNWFltrTotGtpV0Pkts OBJECT-TYPE
    SYNTAX  Counter64
    MAX-ACCESS read-only
    STATUS  current
    DESCRIPTION ""
    -- 1.3.6.1.4.1.32620.1.1.4.100.1.103
    ::= { anueNtoStageGscNetworkFilterEntry 103 }


anueGscNWFltrTotGtpV2Pkts OBJECT-TYPE
    SYNTAX  Counter64
    MAX-ACCESS read-only
    STATUS  current
    DESCRIPTION ""
    -- 1.3.6.1.4.1.32620.1.1.4.100.1.104
    ::= { anueNtoStageGscNetworkFilterEntry 104 }


anueGscNWFltrTotGtpTotPkts OBJECT-TYPE
    SYNTAX  Counter64
    MAX-ACCESS read-only
    STATUS  current
    DESCRIPTION ""
    -- 1.3.6.1.4.1.32620.1.1.4.100.1.105
    ::= { anueNtoStageGscNetworkFilterEntry 105 }


anueGscNWFltrPkGtpV0Pkts OBJECT-TYPE
    SYNTAX  Counter64
    MAX-ACCESS read-only
    STATUS  current
    DESCRIPTION ""
    -- 1.3.6.1.4.1.32620.1.1.4.100.1.106
    ::= { anueNtoStageGscNetworkFilterEntry 106 }


anueGscNWFltrPkGtpV1Pkts OBJECT-TYPE
    SYNTAX  Counter64
    MAX-ACCESS read-only
    STATUS  current
    DESCRIPTION ""
    -- 1.3.6.1.4.1.32620.1.1.4.100.1.107
    ::= { anueNtoStageGscNetworkFilterEntry 107 }


anueGscNWFltrPkGtpV2Pkts OBJECT-TYPE
    SYNTAX  Counter64
    MAX-ACCESS read-only
    STATUS  current
    DESCRIPTION ""
    -- 1.3.6.1.4.1.32620.1.1.4.100.1.108
    ::= { anueNtoStageGscNetworkFilterEntry 108 }


anueGscNWFltrPkGtpTotPkts OBJECT-TYPE
    SYNTAX  Counter64
    MAX-ACCESS read-only
    STATUS  current
    DESCRIPTION ""
    -- 1.3.6.1.4.1.32620.1.1.4.100.1.109
    ::= { anueNtoStageGscNetworkFilterEntry 109 }


anueGscNWFltrPkGtpV0PktsT OBJECT-TYPE
    SYNTAX  DateAndTime
    MAX-ACCESS read-only
    STATUS  current
    DESCRIPTION ""
    -- 1.3.6.1.4.1.32620.1.1.4.100.1.110
    ::= { anueNtoStageGscNetworkFilterEntry 110 }


anueGscNWFltrPkGtpV1PktsT OBJECT-TYPE
    SYNTAX  DateAndTime
    MAX-ACCESS read-only
    STATUS  current
    DESCRIPTION ""
    -- 1.3.6.1.4.1.32620.1.1.4.100.1.111
    ::= { anueNtoStageGscNetworkFilterEntry 111 }


anueGscNWFltrPkGtpV2PktsT OBJECT-TYPE
    SYNTAX  DateAndTime
    MAX-ACCESS read-only
    STATUS  current
    DESCRIPTION ""
    -- 1.3.6.1.4.1.32620.1.1.4.100.1.112
    ::= { anueNtoStageGscNetworkFilterEntry 112 }


anueGscNWFltrPkGtpTotPktsT OBJECT-TYPE
    SYNTAX  DateAndTime
    MAX-ACCESS read-only
    STATUS  current
    DESCRIPTION ""
    -- 1.3.6.1.4.1.32620.1.1.4.100.1.113
    ::= { anueNtoStageGscNetworkFilterEntry 113 }


anueGscNWFltrTotGtpV0ToutSess OBJECT-TYPE
    SYNTAX  Counter64
    MAX-ACCESS read-only
    STATUS  current
    DESCRIPTION ""
    -- 1.3.6.1.4.1.32620.1.1.4.100.1.114
    ::= { anueNtoStageGscNetworkFilterEntry 114 }


anueGscNWFltrTotGtpV1ToutSess OBJECT-TYPE
    SYNTAX  Counter64
    MAX-ACCESS read-only
    STATUS  current
    DESCRIPTION ""
    -- 1.3.6.1.4.1.32620.1.1.4.100.1.115
    ::= { anueNtoStageGscNetworkFilterEntry 115 }


anueGscNWFltrTotGtpV2ToutSess OBJECT-TYPE
    SYNTAX  Counter64
    MAX-ACCESS read-only
    STATUS  current
    DESCRIPTION ""
    -- 1.3.6.1.4.1.32620.1.1.4.100.1.116
    ::= { anueNtoStageGscNetworkFilterEntry 116 }


anueGscNWFltrTotGtpTotToutSess OBJECT-TYPE
    SYNTAX  Counter64
    MAX-ACCESS read-only
    STATUS  current
    DESCRIPTION ""
    -- 1.3.6.1.4.1.32620.1.1.4.100.1.117
    ::= { anueNtoStageGscNetworkFilterEntry 117 }


anueGscNWFltrAvgGtpV0ToutSess OBJECT-TYPE
    SYNTAX  Counter64
    MAX-ACCESS read-only
    STATUS  current
    DESCRIPTION ""
    -- 1.3.6.1.4.1.32620.1.1.4.100.1.118
    ::= { anueNtoStageGscNetworkFilterEntry 118 }


anueGscNWFltrAvgGtpV1ToutSess OBJECT-TYPE
    SYNTAX  Counter64
    MAX-ACCESS read-only
    STATUS  current
    DESCRIPTION ""
    -- 1.3.6.1.4.1.32620.1.1.4.100.1.119
    ::= { anueNtoStageGscNetworkFilterEntry 119 }


anueGscNWFltrAvgGtpV2ToutSess OBJECT-TYPE
    SYNTAX  Counter64
    MAX-ACCESS read-only
    STATUS  current
    DESCRIPTION ""
    -- 1.3.6.1.4.1.32620.1.1.4.100.1.120
    ::= { anueNtoStageGscNetworkFilterEntry 120 }


anueGscNWFltrAvgGtpTotToutSess OBJECT-TYPE
    SYNTAX  Counter64
    MAX-ACCESS read-only
    STATUS  current
    DESCRIPTION ""
    -- 1.3.6.1.4.1.32620.1.1.4.100.1.121
    ::= { anueNtoStageGscNetworkFilterEntry 121 }


anueGscNWFltrCurGtpV0ToutSess OBJECT-TYPE
    SYNTAX  Counter64
    MAX-ACCESS read-only
    STATUS  current
    DESCRIPTION ""
    -- 1.3.6.1.4.1.32620.1.1.4.100.1.122
    ::= { anueNtoStageGscNetworkFilterEntry 122 }


anueGscNWFltrCurGtpV1ToutSess OBJECT-TYPE
    SYNTAX  Counter64
    MAX-ACCESS read-only
    STATUS  current
    DESCRIPTION ""
    -- 1.3.6.1.4.1.32620.1.1.4.100.1.123
    ::= { anueNtoStageGscNetworkFilterEntry 123 }


anueGscNWFltrCurGtpV2ToutSess OBJECT-TYPE
    SYNTAX  Counter64
    MAX-ACCESS read-only
    STATUS  current
    DESCRIPTION ""
    -- 1.3.6.1.4.1.32620.1.1.4.100.1.124
    ::= { anueNtoStageGscNetworkFilterEntry 124 }


anueGscNWFltrCurGtpTotToutSess OBJECT-TYPE
    SYNTAX  Counter64
    MAX-ACCESS read-only
    STATUS  current
    DESCRIPTION ""
    -- 1.3.6.1.4.1.32620.1.1.4.100.1.125
    ::= { anueNtoStageGscNetworkFilterEntry 125 }


anueGscNWFltrPkGtpV0ToutSess OBJECT-TYPE
    SYNTAX  Counter64
    MAX-ACCESS read-only
    STATUS  current
    DESCRIPTION ""
    -- 1.3.6.1.4.1.32620.1.1.4.100.1.126
    ::= { anueNtoStageGscNetworkFilterEntry 126 }


anueGscNWFltrPkGtpV1ToutSess OBJECT-TYPE
    SYNTAX  Counter64
    MAX-ACCESS read-only
    STATUS  current
    DESCRIPTION ""
    -- 1.3.6.1.4.1.32620.1.1.4.100.1.127
    ::= { anueNtoStageGscNetworkFilterEntry 127 }


anueGscNWFltrPkGtpV2ToutSess OBJECT-TYPE
    SYNTAX  Counter64
    MAX-ACCESS read-only
    STATUS  current
    DESCRIPTION ""
    -- 1.3.6.1.4.1.32620.1.1.4.100.1.128
    ::= { anueNtoStageGscNetworkFilterEntry 128 }


anueGscNWFltrPkGtpTotToutSess OBJECT-TYPE
    SYNTAX  Counter64
    MAX-ACCESS read-only
    STATUS  current
    DESCRIPTION ""
    -- 1.3.6.1.4.1.32620.1.1.4.100.1.129
    ::= { anueNtoStageGscNetworkFilterEntry 129 }


anueGscNWFltrPkGtpV0ToutSessT OBJECT-TYPE
    SYNTAX  DateAndTime
    MAX-ACCESS read-only
    STATUS  current
    DESCRIPTION ""
    -- 1.3.6.1.4.1.32620.1.1.4.100.1.130
    ::= { anueNtoStageGscNetworkFilterEntry 130 }


anueGscNWFltrPkGtpV1ToutSessT OBJECT-TYPE
    SYNTAX  DateAndTime
    MAX-ACCESS read-only
    STATUS  current
    DESCRIPTION ""
    -- 1.3.6.1.4.1.32620.1.1.4.100.1.131
    ::= { anueNtoStageGscNetworkFilterEntry 131 }


anueGscNWFltrPkGtpV2ToutSessT OBJECT-TYPE
    SYNTAX  DateAndTime
    MAX-ACCESS read-only
    STATUS  current
    DESCRIPTION ""
    -- 1.3.6.1.4.1.32620.1.1.4.100.1.132
    ::= { anueNtoStageGscNetworkFilterEntry 132 }


anueGscNWFltrPkGtpTotToutSessT OBJECT-TYPE
    SYNTAX  DateAndTime
    MAX-ACCESS read-only
    STATUS  current
    DESCRIPTION ""
    -- 1.3.6.1.4.1.32620.1.1.4.100.1.133
    ::= { anueNtoStageGscNetworkFilterEntry 133 }


anueGscNWFltrAvgGtpCPkts OBJECT-TYPE
    SYNTAX  Counter64
    MAX-ACCESS read-only
    STATUS  current
    DESCRIPTION ""
    -- 1.3.6.1.4.1.32620.1.1.4.100.1.134
    ::= { anueNtoStageGscNetworkFilterEntry 134 }


anueGscNWFltrAvgGtpUPkts OBJECT-TYPE
    SYNTAX  Counter64
    MAX-ACCESS read-only
    STATUS  current
    DESCRIPTION ""
    -- 1.3.6.1.4.1.32620.1.1.4.100.1.135
    ::= { anueNtoStageGscNetworkFilterEntry 135 }


anueGscNWFltrAvgDiameterPkts OBJECT-TYPE
    SYNTAX  Counter64
    MAX-ACCESS read-only
    STATUS  current
    DESCRIPTION ""
    -- 1.3.6.1.4.1.32620.1.1.4.100.1.136
    ::= { anueNtoStageGscNetworkFilterEntry 136 }


anueGscNWFltrAvgDnsPkts OBJECT-TYPE
    SYNTAX  Counter64
    MAX-ACCESS read-only
    STATUS  current
    DESCRIPTION ""
    -- 1.3.6.1.4.1.32620.1.1.4.100.1.137
    ::= { anueNtoStageGscNetworkFilterEntry 137 }


anueGscNWFltrAvgRadiusPkts OBJECT-TYPE
    SYNTAX  Counter64
    MAX-ACCESS read-only
    STATUS  current
    DESCRIPTION ""
    -- 1.3.6.1.4.1.32620.1.1.4.100.1.138
    ::= { anueNtoStageGscNetworkFilterEntry 138 }


anueGscNWFltrAvgNonGtpPkts OBJECT-TYPE
    SYNTAX  Counter64
    MAX-ACCESS read-only
    STATUS  current
    DESCRIPTION ""
    -- 1.3.6.1.4.1.32620.1.1.4.100.1.139
    ::= { anueNtoStageGscNetworkFilterEntry 139 }


anueGscNWFltrCurGtpCPkts OBJECT-TYPE
    SYNTAX  Counter64
    MAX-ACCESS read-only
    STATUS  current
    DESCRIPTION ""
    -- 1.3.6.1.4.1.32620.1.1.4.100.1.140
    ::= { anueNtoStageGscNetworkFilterEntry 140 }


anueGscNWFltrCurGtpUPkts OBJECT-TYPE
    SYNTAX  Counter64
    MAX-ACCESS read-only
    STATUS  current
    DESCRIPTION ""
    -- 1.3.6.1.4.1.32620.1.1.4.100.1.141
    ::= { anueNtoStageGscNetworkFilterEntry 141 }


anueGscNWFltrCurDiameterPkts OBJECT-TYPE
    SYNTAX  Counter64
    MAX-ACCESS read-only
    STATUS  current
    DESCRIPTION ""
    -- 1.3.6.1.4.1.32620.1.1.4.100.1.142
    ::= { anueNtoStageGscNetworkFilterEntry 142 }


anueGscNWFltrCurDnsPkts OBJECT-TYPE
    SYNTAX  Counter64
    MAX-ACCESS read-only
    STATUS  current
    DESCRIPTION ""
    -- 1.3.6.1.4.1.32620.1.1.4.100.1.143
    ::= { anueNtoStageGscNetworkFilterEntry 143 }


anueGscNWFltrCurRadiusPkts OBJECT-TYPE
    SYNTAX  Counter64
    MAX-ACCESS read-only
    STATUS  current
    DESCRIPTION ""
    -- 1.3.6.1.4.1.32620.1.1.4.100.1.144
    ::= { anueNtoStageGscNetworkFilterEntry 144 }


anueGscNWFltrCurNonGtpPkts OBJECT-TYPE
    SYNTAX  Counter64
    MAX-ACCESS read-only
    STATUS  current
    DESCRIPTION ""
    -- 1.3.6.1.4.1.32620.1.1.4.100.1.145
    ::= { anueNtoStageGscNetworkFilterEntry 145 }


anueGscNWFltrPkGtpCPkts OBJECT-TYPE
    SYNTAX  Counter64
    MAX-ACCESS read-only
    STATUS  current
    DESCRIPTION ""
    -- 1.3.6.1.4.1.32620.1.1.4.100.1.146
    ::= { anueNtoStageGscNetworkFilterEntry 146 }


anueGscNWFltrPkGtpUPkts OBJECT-TYPE
    SYNTAX  Counter64
    MAX-ACCESS read-only
    STATUS  current
    DESCRIPTION ""
    -- 1.3.6.1.4.1.32620.1.1.4.100.1.147
    ::= { anueNtoStageGscNetworkFilterEntry 147 }


anueGscNWFltrPkDiameterPkts OBJECT-TYPE
    SYNTAX  Counter64
    MAX-ACCESS read-only
    STATUS  current
    DESCRIPTION ""
    -- 1.3.6.1.4.1.32620.1.1.4.100.1.148
    ::= { anueNtoStageGscNetworkFilterEntry 148 }


anueGscNWFltrPkDnsPkts OBJECT-TYPE
    SYNTAX  Counter64
    MAX-ACCESS read-only
    STATUS  current
    DESCRIPTION ""
    -- 1.3.6.1.4.1.32620.1.1.4.100.1.149
    ::= { anueNtoStageGscNetworkFilterEntry 149 }


anueGscNWFltrPkRadiusPkts OBJECT-TYPE
    SYNTAX  Counter64
    MAX-ACCESS read-only
    STATUS  current
    DESCRIPTION ""
    -- 1.3.6.1.4.1.32620.1.1.4.100.1.150
    ::= { anueNtoStageGscNetworkFilterEntry 150 }


anueGscNWFltrPkNonGtpPkts OBJECT-TYPE
    SYNTAX  Counter64
    MAX-ACCESS read-only
    STATUS  current
    DESCRIPTION ""
    -- 1.3.6.1.4.1.32620.1.1.4.100.1.151
    ::= { anueNtoStageGscNetworkFilterEntry 151 }


anueGscNWFltrPkGtpCPktsT OBJECT-TYPE
    SYNTAX  DateAndTime
    MAX-ACCESS read-only
    STATUS  current
    DESCRIPTION ""
    -- 1.3.6.1.4.1.32620.1.1.4.100.1.152
    ::= { anueNtoStageGscNetworkFilterEntry 152 }


anueGscNWFltrPkGtpUPktsT OBJECT-TYPE
    SYNTAX  DateAndTime
    MAX-ACCESS read-only
    STATUS  current
    DESCRIPTION ""
    -- 1.3.6.1.4.1.32620.1.1.4.100.1.153
    ::= { anueNtoStageGscNetworkFilterEntry 153 }


anueGscNWFltrPkDiameterPktsT OBJECT-TYPE
    SYNTAX  DateAndTime
    MAX-ACCESS read-only
    STATUS  current
    DESCRIPTION ""
    -- 1.3.6.1.4.1.32620.1.1.4.100.1.154
    ::= { anueNtoStageGscNetworkFilterEntry 154 }


anueGscNWFltrPkDnsPktsT OBJECT-TYPE
    SYNTAX  DateAndTime
    MAX-ACCESS read-only
    STATUS  current
    DESCRIPTION ""
    -- 1.3.6.1.4.1.32620.1.1.4.100.1.155
    ::= { anueNtoStageGscNetworkFilterEntry 155 }


anueGscNWFltrPkRadiusPktsT OBJECT-TYPE
    SYNTAX  DateAndTime
    MAX-ACCESS read-only
    STATUS  current
    DESCRIPTION ""
    -- 1.3.6.1.4.1.32620.1.1.4.100.1.156
    ::= { anueNtoStageGscNetworkFilterEntry 156 }


anueGscNWFltrPkNonGtpPktsT OBJECT-TYPE
    SYNTAX  DateAndTime
    MAX-ACCESS read-only
    STATUS  current
    DESCRIPTION ""
    -- 1.3.6.1.4.1.32620.1.1.4.100.1.157
    ::= { anueNtoStageGscNetworkFilterEntry 157 }


anueGscNWFltrTotGtpCPkts OBJECT-TYPE
    SYNTAX  Counter64
    MAX-ACCESS read-only
    STATUS  current
    DESCRIPTION ""
    -- 1.3.6.1.4.1.32620.1.1.4.100.1.158
    ::= { anueNtoStageGscNetworkFilterEntry 158 }


anueGscNWFltrTotGtpUPkts OBJECT-TYPE
    SYNTAX  Counter64
    MAX-ACCESS read-only
    STATUS  current
    DESCRIPTION ""
    -- 1.3.6.1.4.1.32620.1.1.4.100.1.159
    ::= { anueNtoStageGscNetworkFilterEntry 159 }


anueGscNWFltrTotDiameterPkts OBJECT-TYPE
    SYNTAX  Counter64
    MAX-ACCESS read-only
    STATUS  current
    DESCRIPTION ""
    -- 1.3.6.1.4.1.32620.1.1.4.100.1.160
    ::= { anueNtoStageGscNetworkFilterEntry 160 }


anueGscNWFltrTotDnsPkts OBJECT-TYPE
    SYNTAX  Counter64
    MAX-ACCESS read-only
    STATUS  current
    DESCRIPTION ""
    -- 1.3.6.1.4.1.32620.1.1.4.100.1.161
    ::= { anueNtoStageGscNetworkFilterEntry 161 }


anueGscNWFltrTotRadiusPkts OBJECT-TYPE
    SYNTAX  Counter64
    MAX-ACCESS read-only
    STATUS  current
    DESCRIPTION ""
    -- 1.3.6.1.4.1.32620.1.1.4.100.1.162
    ::= { anueNtoStageGscNetworkFilterEntry 162 }


anueGscNWFltrTotNonGtpPkts OBJECT-TYPE
    SYNTAX  Counter64
    MAX-ACCESS read-only
    STATUS  current
    DESCRIPTION ""
    -- 1.3.6.1.4.1.32620.1.1.4.100.1.163
    ::= { anueNtoStageGscNetworkFilterEntry 163 }


anueGscNWFltrTotGscDropPkts OBJECT-TYPE
    SYNTAX  Counter64
    MAX-ACCESS read-only
    STATUS  current
    DESCRIPTION ""
    -- 1.3.6.1.4.1.32620.1.1.4.100.1.164
    ::= { anueNtoStageGscNetworkFilterEntry 164 }


anueGscNWFltrCurGscSessLoad OBJECT-TYPE
    SYNTAX  CounterBasedGauge64
    MAX-ACCESS read-only
    STATUS  current
    DESCRIPTION
        "The percentage of sessions table bandwidth utilized in the
         current (most recent) sampling period by network port group filter
         receive (incoming) traffic. As the load nears 100% new sessions
         might not fit in the table and could be sent to the non-session
         pool."

    -- 1.3.6.1.4.1.32620.1.1.4.100.1.165
    ::= { anueNtoStageGscNetworkFilterEntry 165 }


anueGscNWFltrAvgGscSessLoad OBJECT-TYPE
    SYNTAX  CounterBasedGauge64
    MAX-ACCESS read-only
    STATUS  current
    DESCRIPTION
        "The percentage of sessions table bandwidth utilized in the
         current (most recent) sampling period by network port group filter
         receive (incoming) traffic. As the load nears 100% new sessions
         might not fit in the table and could be sent to the non-session
         pool."

    -- 1.3.6.1.4.1.32620.1.1.4.100.1.166
    ::= { anueNtoStageGscNetworkFilterEntry 166 }


anueGscNWFltrPeakGscSessLoad OBJECT-TYPE
    SYNTAX  CounterBasedGauge64
    MAX-ACCESS read-only
    STATUS  current
    DESCRIPTION
        "The peak percentage of sessions table bandwidth utilized in the
         in any sampling period since anueFilterStatsResetTime by network
         port group filter receive (incoming) traffic. As the load nears
         100% new sessions might not fit in the table and could be sent to
         the non-session pool."

    -- 1.3.6.1.4.1.32620.1.1.4.100.1.167
    ::= { anueNtoStageGscNetworkFilterEntry 167 }


anueGscNWFltrPeakGscSessLoadT OBJECT-TYPE
    SYNTAX  DateAndTime
    MAX-ACCESS read-only
    STATUS  current
    DESCRIPTION
        "The date and time of the PeakGscSessLoad event."

    -- 1.3.6.1.4.1.32620.1.1.4.100.1.168
    ::= { anueNtoStageGscNetworkFilterEntry 168 }


anueGscNWFltrCurNetwElemLoad OBJECT-TYPE
    SYNTAX  CounterBasedGauge64
    MAX-ACCESS read-only
    STATUS  current
    DESCRIPTION
        ""

    -- 1.3.6.1.4.1.32620.1.1.4.100.1.169
    ::= { anueNtoStageGscNetworkFilterEntry 169 }


anueGscNWFltrPeakNetwElemLoad OBJECT-TYPE
    SYNTAX  CounterBasedGauge64
    MAX-ACCESS read-only
    STATUS  current
    DESCRIPTION
        ""

    -- 1.3.6.1.4.1.32620.1.1.4.100.1.170
    ::= { anueNtoStageGscNetworkFilterEntry 170 }


anueGscNWFltrPeakNetwElemLoadT OBJECT-TYPE
    SYNTAX  DateAndTime
    MAX-ACCESS read-only
    STATUS  current
    DESCRIPTION
        ""

    -- 1.3.6.1.4.1.32620.1.1.4.100.1.171
    ::= { anueNtoStageGscNetworkFilterEntry 171 }


anueGscNWFltrCurReqRespLoad OBJECT-TYPE
    SYNTAX  CounterBasedGauge64
    MAX-ACCESS read-only
    STATUS  current
    DESCRIPTION
        ""

    -- 1.3.6.1.4.1.32620.1.1.4.100.1.172
    ::= { anueNtoStageGscNetworkFilterEntry 172 }


anueGscNWFltrPeakReqRespLoad OBJECT-TYPE
    SYNTAX  CounterBasedGauge64
    MAX-ACCESS read-only
    STATUS  current
    DESCRIPTION
        ""

    -- 1.3.6.1.4.1.32620.1.1.4.100.1.173
    ::= { anueNtoStageGscNetworkFilterEntry 173 }


anueGscNWFltrPeakReqRespLoadT OBJECT-TYPE
    SYNTAX  DateAndTime
    MAX-ACCESS read-only
    STATUS  current
    DESCRIPTION
        ""

    -- 1.3.6.1.4.1.32620.1.1.4.100.1.174
    ::= { anueNtoStageGscNetworkFilterEntry 174 }


anueGscNWFltrCurFragLoad OBJECT-TYPE
    SYNTAX  CounterBasedGauge64
    MAX-ACCESS read-only
    STATUS  current
    DESCRIPTION
        ""

    -- 1.3.6.1.4.1.32620.1.1.4.100.1.175
    ::= { anueNtoStageGscNetworkFilterEntry 175 }


anueGscNWFltrPeakFragLoad OBJECT-TYPE
    SYNTAX  CounterBasedGauge64
    MAX-ACCESS read-only
    STATUS  current
    DESCRIPTION
        ""

    -- 1.3.6.1.4.1.32620.1.1.4.100.1.176
    ::= { anueNtoStageGscNetworkFilterEntry 176 }


anueGscNWFltrPeakFragLoadT OBJECT-TYPE
    SYNTAX  DateAndTime
    MAX-ACCESS read-only
    STATUS  current
    DESCRIPTION
        ""

    -- 1.3.6.1.4.1.32620.1.1.4.100.1.177
    ::= { anueNtoStageGscNetworkFilterEntry 177 }


anueGscNWFltrAvgGscUnassignedSess OBJECT-TYPE
    SYNTAX  Counter64
    MAX-ACCESS read-only
    STATUS  current
    DESCRIPTION
        ""
    -- 1.3.6.1.4.1.32620.1.1.4.100.1.178
    ::= { anueNtoStageGscNetworkFilterEntry 178 }


anueGscNWFltrCurGscUnassignedSess OBJECT-TYPE
    SYNTAX  Counter64
    MAX-ACCESS read-only
    STATUS  current
    DESCRIPTION
        ""
    -- 1.3.6.1.4.1.32620.1.1.4.100.1.179
    ::= { anueNtoStageGscNetworkFilterEntry 179 }


anueGscNWFltrPkGscUnassignedSess OBJECT-TYPE
    SYNTAX  Counter64
    MAX-ACCESS read-only
    STATUS  current
    DESCRIPTION
        ""
    -- 1.3.6.1.4.1.32620.1.1.4.100.1.180
    ::= { anueNtoStageGscNetworkFilterEntry 180 }


anueGscNWFltrPkGscUnassignedSessT OBJECT-TYPE
    SYNTAX  DateAndTime
    MAX-ACCESS read-only
    STATUS  current
    DESCRIPTION
        ""
    -- 1.3.6.1.4.1.32620.1.1.4.100.1.181
    ::= { anueNtoStageGscNetworkFilterEntry 181 }


anueGscNWFltrTotGscUnassignedSess OBJECT-TYPE
    SYNTAX  Counter64
    MAX-ACCESS read-only
    STATUS  current
    DESCRIPTION
        ""
    -- 1.3.6.1.4.1.32620.1.1.4.100.1.182
    ::= { anueNtoStageGscNetworkFilterEntry 182 }


anueGscNWFltrAvgUnprocReq OBJECT-TYPE
    SYNTAX  Counter64
    MAX-ACCESS read-only
    STATUS  current
    DESCRIPTION
        ""
    -- 1.3.6.1.4.1.32620.1.1.4.100.1.183
    ::= { anueNtoStageGscNetworkFilterEntry 183 }


anueGscNWFltrCurUnprocReq OBJECT-TYPE
    SYNTAX  Counter64
    MAX-ACCESS read-only
    STATUS  current
    DESCRIPTION
        ""
    -- 1.3.6.1.4.1.32620.1.1.4.100.1.184
    ::= { anueNtoStageGscNetworkFilterEntry 184 }


anueGscNWFltrPkUnprocReq OBJECT-TYPE
    SYNTAX  Counter64
    MAX-ACCESS read-only
    STATUS  current
    DESCRIPTION
        ""
    -- 1.3.6.1.4.1.32620.1.1.4.100.1.185
    ::= { anueNtoStageGscNetworkFilterEntry 185 }


anueGscNWFltrPkUnprocReqT OBJECT-TYPE
    SYNTAX  DateAndTime
    MAX-ACCESS read-only
    STATUS  current
    DESCRIPTION
        ""
    -- 1.3.6.1.4.1.32620.1.1.4.100.1.186
    ::= { anueNtoStageGscNetworkFilterEntry 186 }


anueGscNWFltrTotUnprocReq OBJECT-TYPE
    SYNTAX  Counter64
    MAX-ACCESS read-only
    STATUS  current
    DESCRIPTION
        ""
    -- 1.3.6.1.4.1.32620.1.1.4.100.1.187
    ::= { anueNtoStageGscNetworkFilterEntry 187 }


anueGscNWFltrAvgTdOutReq OBJECT-TYPE
    SYNTAX  Counter64
    MAX-ACCESS read-only
    STATUS  current
    DESCRIPTION
        ""
    -- 1.3.6.1.4.1.32620.1.1.4.100.1.188
    ::= { anueNtoStageGscNetworkFilterEntry 188 }


anueGscNWFltrCurTdOutReq OBJECT-TYPE
    SYNTAX  Counter64
    MAX-ACCESS read-only
    STATUS  current
    DESCRIPTION
        ""
    -- 1.3.6.1.4.1.32620.1.1.4.100.1.189
    ::= { anueNtoStageGscNetworkFilterEntry 189 }


anueGscNWFltrPkTdOutReq OBJECT-TYPE
    SYNTAX  Counter64
    MAX-ACCESS read-only
    STATUS  current
    DESCRIPTION
        ""
    -- 1.3.6.1.4.1.32620.1.1.4.100.1.190
    ::= { anueNtoStageGscNetworkFilterEntry 190 }


anueGscNWFltrPkTdOutReqT OBJECT-TYPE
    SYNTAX  DateAndTime
    MAX-ACCESS read-only
    STATUS  current
    DESCRIPTION
        ""
    -- 1.3.6.1.4.1.32620.1.1.4.100.1.191
    ::= { anueNtoStageGscNetworkFilterEntry 191 }


anueGscNWFltrTotTdOutReq OBJECT-TYPE
    SYNTAX  Counter64
    MAX-ACCESS read-only
    STATUS  current
    DESCRIPTION
        ""
    -- 1.3.6.1.4.1.32620.1.1.4.100.1.192
    ::= { anueNtoStageGscNetworkFilterEntry 192 }


anueGscNWFltrAvgUnmatchedResp OBJECT-TYPE
    SYNTAX  Counter64
    MAX-ACCESS read-only
    STATUS  current
    DESCRIPTION
        ""
    -- 1.3.6.1.4.1.32620.1.1.4.100.1.193
    ::= { anueNtoStageGscNetworkFilterEntry 193 }


anueGscNWFltrCurUnmatchedResp OBJECT-TYPE
    SYNTAX  Counter64
    MAX-ACCESS read-only
    STATUS  current
    DESCRIPTION
        ""
    -- 1.3.6.1.4.1.32620.1.1.4.100.1.194
    ::= { anueNtoStageGscNetworkFilterEntry 194 }


anueGscNWFltrPkUnmatchedResp OBJECT-TYPE
    SYNTAX  Counter64
    MAX-ACCESS read-only
    STATUS  current
    DESCRIPTION
        ""
    -- 1.3.6.1.4.1.32620.1.1.4.100.1.195
    ::= { anueNtoStageGscNetworkFilterEntry 195 }


anueGscNWFltrPkUnmatchedRespT OBJECT-TYPE
    SYNTAX  DateAndTime
    MAX-ACCESS read-only
    STATUS  current
    DESCRIPTION
        ""
    -- 1.3.6.1.4.1.32620.1.1.4.100.1.196
    ::= { anueNtoStageGscNetworkFilterEntry 196 }


anueGscNWFltrTotUnmatchedResp OBJECT-TYPE
    SYNTAX  Counter64
    MAX-ACCESS read-only
    STATUS  current
    DESCRIPTION
        ""
    -- 1.3.6.1.4.1.32620.1.1.4.100.1.197
    ::= { anueNtoStageGscNetworkFilterEntry 197 }


anueGscNWFltrOverloadErrCode OBJECT-TYPE
    SYNTAX  Counter64
    MAX-ACCESS read-only
    STATUS  current
    DESCRIPTION
        ""
    -- 1.3.6.1.4.1.32620.1.1.4.100.1.198
    ::= { anueNtoStageGscNetworkFilterEntry 198 }


anueGscNWFltrOverloadT OBJECT-TYPE
    SYNTAX  DateAndTime
    MAX-ACCESS read-only
    STATUS  current
    DESCRIPTION
        ""
    -- 1.3.6.1.4.1.32620.1.1.4.100.1.199
    ::= { anueNtoStageGscNetworkFilterEntry 199 }


anueNtoStageGscToolFilterTable OBJECT-TYPE
    SYNTAX  SEQUENCE OF AnueNtoStageGscToolFilterEntry
    MAX-ACCESS not-accessible
    STATUS  current
    DESCRIPTION
        ""
    -- 1.3.6.1.4.1.32620.1.1.4.101
    ::= { anueNtoStage 101 }


anueNtoStageGscToolFilterEntry OBJECT-TYPE
    SYNTAX  AnueNtoStageGscToolFilterEntry
    MAX-ACCESS not-accessible
    STATUS  current
    DESCRIPTION
        ""
    INDEX {
        anueNtoStageGscToolFilterType,
        anueNtoStageGscToolFilterNumber,
        anueNtoStageGscToolFilterFeature }
    -- 1.3.6.1.4.1.32620.1.1.4.101.1
    ::= { anueNtoStageGscToolFilterTable 1 }


AnueNtoStageGscToolFilterEntry ::= SEQUENCE {
    anueNtoStageGscToolFilterType                    AnueFilterTypeDT,
    anueNtoStageGscToolFilterNumber                  Integer32,
    anueNtoStageGscToolFilterFeature                 AnueStageType,
    anueGscTFltrCurGtpV0ActSess                      Counter64,
    anueGscTFltrCurGtpV1ActSess                      Counter64,
    anueGscTFltrCurGtpV2ActSess                      Counter64,
    anueGscTFltrCurGtpTotActSess                     Counter64,
    anueGscTFltrAvgGtpV0ActSess                      Counter64,
    anueGscTFltrAvgGtpV1ActSess                      Counter64,
    anueGscTFltrAvgGtpV2ActSess                      Counter64,
    anueGscTFltrAvgGtpTotActSess                     Counter64,
    anueGscTFltrPeakGtpV0ActSess                     Counter64,
    anueGscTFltrPeakGtpV1ActSess                     Counter64,
    anueGscTFltrPeakGtpV2ActSess                     Counter64,
    anueGscTFltrPeakGtpTotActSess                    Counter64,
    anueGscTFltrPeakGtpV0ActSessT                    DateAndTime,
    anueGscTFltrPeakGtpV1ActSessT                    DateAndTime,
    anueGscTFltrPeakGtpV2ActSessT                    DateAndTime,
    anueGscTFltrPeakGtpTotActSessT                   DateAndTime,
    anueGscTFltrAvgGtpCPkts                          Counter64,
    anueGscTFltrAvgGtpUPkts                          Counter64,
    anueGscTFltrAvgDiameterPkts                      Counter64,
    anueGscTFltrAvgDnsPkts                           Counter64,
    anueGscTFltrAvgRadiusPkts                        Counter64,
    anueGscTFltrPeakGtpCPkts                         Counter64,
    anueGscTFltrPeakGtpUPkts                         Counter64,
    anueGscTFltrPeakDiameterPkts                     Counter64,
    anueGscTFltrPeakDnsPkts                          Counter64,
    anueGscTFltrPeakRadiusPkts                       Counter64,
    anueGscTFltrPeakGtpCPktsT                        DateAndTime,
    anueGscTFltrPeakGtpUPktsT                        DateAndTime,
    anueGscTFltrPeakDiameterPktsT                    DateAndTime,
    anueGscTFltrPeakDnsPktsT                         DateAndTime,
    anueGscTFltrPeakRadiusPktsT                      DateAndTime,
    anueGscTFltrTotGtpCPkts                          Counter64,
    anueGscTFltrTotGtpUPkts                          Counter64,
    anueGscTFltrTotDiameterPkts                      Counter64,
    anueGscTFltrTotDnsPkts                           Counter64,
    anueGscTFltrTotRadiusPkts                        Counter64,
    anueGscTFltrCurGtpCPkts                          Counter64,
    anueGscTFltrCurGtpUPkts                          Counter64,
    anueGscTFltrCurDiameterPkts                      Counter64,
    anueGscTFltrCurDnsPkts                           Counter64,
    anueGscTFltrCurRadiusPkts                        Counter64 }


anueNtoStageGscToolFilterType OBJECT-TYPE
    SYNTAX  AnueFilterTypeDT
    MAX-ACCESS read-only
    STATUS  current
    DESCRIPTION
        ""
    -- 1.3.6.1.4.1.32620.1.1.4.101.1.1
    ::= { anueNtoStageGscToolFilterEntry 1 }


anueNtoStageGscToolFilterNumber OBJECT-TYPE
    SYNTAX  Integer32 (1..2147483647)
    MAX-ACCESS read-only
    STATUS  current
    DESCRIPTION
        ""
    -- 1.3.6.1.4.1.32620.1.1.4.101.1.2
    ::= { anueNtoStageGscToolFilterEntry 2 }


anueNtoStageGscToolFilterFeature OBJECT-TYPE
    SYNTAX  AnueStageType
    MAX-ACCESS read-only
    STATUS  current
    DESCRIPTION
        ""
    -- 1.3.6.1.4.1.32620.1.1.4.101.1.3
    ::= { anueNtoStageGscToolFilterEntry 3 }


anueGscTFltrCurGtpV0ActSess OBJECT-TYPE
    SYNTAX  Counter64
    MAX-ACCESS read-only
    STATUS  current
    DESCRIPTION
        ""
    -- 1.3.6.1.4.1.32620.1.1.4.101.1.4
    ::= { anueNtoStageGscToolFilterEntry 4 }


anueGscTFltrCurGtpV1ActSess OBJECT-TYPE
    SYNTAX  Counter64
    MAX-ACCESS read-only
    STATUS  current
    DESCRIPTION
        ""
    -- 1.3.6.1.4.1.32620.1.1.4.101.1.5
    ::= { anueNtoStageGscToolFilterEntry 5 }


anueGscTFltrCurGtpV2ActSess OBJECT-TYPE
    SYNTAX  Counter64
    MAX-ACCESS read-only
    STATUS  current
    DESCRIPTION
        ""
    -- 1.3.6.1.4.1.32620.1.1.4.101.1.6
    ::= { anueNtoStageGscToolFilterEntry 6 }


anueGscTFltrCurGtpTotActSess OBJECT-TYPE
    SYNTAX  Counter64
    MAX-ACCESS read-only
    STATUS  current
    DESCRIPTION
        ""
    -- 1.3.6.1.4.1.32620.1.1.4.101.1.7
    ::= { anueNtoStageGscToolFilterEntry 7 }


anueGscTFltrAvgGtpV0ActSess OBJECT-TYPE
    SYNTAX  Counter64
    MAX-ACCESS read-only
    STATUS  current
    DESCRIPTION
        ""
    -- 1.3.6.1.4.1.32620.1.1.4.101.1.8
    ::= { anueNtoStageGscToolFilterEntry 8 }


anueGscTFltrAvgGtpV1ActSess OBJECT-TYPE
    SYNTAX  Counter64
    MAX-ACCESS read-only
    STATUS  current
    DESCRIPTION
        ""
    -- 1.3.6.1.4.1.32620.1.1.4.101.1.9
    ::= { anueNtoStageGscToolFilterEntry 9 }


anueGscTFltrAvgGtpV2ActSess OBJECT-TYPE
    SYNTAX  Counter64
    MAX-ACCESS read-only
    STATUS  current
    DESCRIPTION
        ""
    -- 1.3.6.1.4.1.32620.1.1.4.101.1.10
    ::= { anueNtoStageGscToolFilterEntry 10 }


anueGscTFltrAvgGtpTotActSess OBJECT-TYPE
    SYNTAX  Counter64
    MAX-ACCESS read-only
    STATUS  current
    DESCRIPTION
        ""
    -- 1.3.6.1.4.1.32620.1.1.4.101.1.11
    ::= { anueNtoStageGscToolFilterEntry 11 }


anueGscTFltrPeakGtpV0ActSess OBJECT-TYPE
    SYNTAX  Counter64
    MAX-ACCESS read-only
    STATUS  current
    DESCRIPTION
        ""
    -- 1.3.6.1.4.1.32620.1.1.4.101.1.12
    ::= { anueNtoStageGscToolFilterEntry 12 }


anueGscTFltrPeakGtpV1ActSess OBJECT-TYPE
    SYNTAX  Counter64
    MAX-ACCESS read-only
    STATUS  current
    DESCRIPTION
        ""
    -- 1.3.6.1.4.1.32620.1.1.4.101.1.13
    ::= { anueNtoStageGscToolFilterEntry 13 }


anueGscTFltrPeakGtpV2ActSess OBJECT-TYPE
    SYNTAX  Counter64
    MAX-ACCESS read-only
    STATUS  current
    DESCRIPTION
        ""
    -- 1.3.6.1.4.1.32620.1.1.4.101.1.14
    ::= { anueNtoStageGscToolFilterEntry 14 }


anueGscTFltrPeakGtpTotActSess OBJECT-TYPE
    SYNTAX  Counter64
    MAX-ACCESS read-only
    STATUS  current
    DESCRIPTION
        ""
    -- 1.3.6.1.4.1.32620.1.1.4.101.1.15
    ::= { anueNtoStageGscToolFilterEntry 15 }


anueGscTFltrPeakGtpV0ActSessT OBJECT-TYPE
    SYNTAX  DateAndTime
    MAX-ACCESS read-only
    STATUS  current
    DESCRIPTION
        ""
    -- 1.3.6.1.4.1.32620.1.1.4.101.1.16
    ::= { anueNtoStageGscToolFilterEntry 16 }


anueGscTFltrPeakGtpV1ActSessT OBJECT-TYPE
    SYNTAX  DateAndTime
    MAX-ACCESS read-only
    STATUS  current
    DESCRIPTION
        ""
    -- 1.3.6.1.4.1.32620.1.1.4.101.1.17
    ::= { anueNtoStageGscToolFilterEntry 17 }


anueGscTFltrPeakGtpV2ActSessT OBJECT-TYPE
    SYNTAX  DateAndTime
    MAX-ACCESS read-only
    STATUS  current
    DESCRIPTION
        ""
    -- 1.3.6.1.4.1.32620.1.1.4.101.1.18
    ::= { anueNtoStageGscToolFilterEntry 18 }


anueGscTFltrPeakGtpTotActSessT OBJECT-TYPE
    SYNTAX  DateAndTime
    MAX-ACCESS read-only
    STATUS  current
    DESCRIPTION
        ""
    -- 1.3.6.1.4.1.32620.1.1.4.101.1.19
    ::= { anueNtoStageGscToolFilterEntry 19 }


anueGscTFltrAvgGtpCPkts OBJECT-TYPE
    SYNTAX  Counter64
    MAX-ACCESS read-only
    STATUS  current
    DESCRIPTION
        ""
    -- 1.3.6.1.4.1.32620.1.1.4.101.1.20
    ::= { anueNtoStageGscToolFilterEntry 20 }


anueGscTFltrAvgGtpUPkts OBJECT-TYPE
    SYNTAX  Counter64
    MAX-ACCESS read-only
    STATUS  current
    DESCRIPTION
        ""
    -- 1.3.6.1.4.1.32620.1.1.4.101.1.21
    ::= { anueNtoStageGscToolFilterEntry 21 }


anueGscTFltrAvgDiameterPkts OBJECT-TYPE
    SYNTAX  Counter64
    MAX-ACCESS read-only
    STATUS  current
    DESCRIPTION
        ""
    -- 1.3.6.1.4.1.32620.1.1.4.101.1.22
    ::= { anueNtoStageGscToolFilterEntry 22 }


anueGscTFltrAvgDnsPkts OBJECT-TYPE
    SYNTAX  Counter64
    MAX-ACCESS read-only
    STATUS  current
    DESCRIPTION
        ""
    -- 1.3.6.1.4.1.32620.1.1.4.101.1.23
    ::= { anueNtoStageGscToolFilterEntry 23 }


anueGscTFltrAvgRadiusPkts OBJECT-TYPE
    SYNTAX  Counter64
    MAX-ACCESS read-only
    STATUS  current
    DESCRIPTION
        ""
    -- 1.3.6.1.4.1.32620.1.1.4.101.1.24
    ::= { anueNtoStageGscToolFilterEntry 24 }


anueGscTFltrPeakGtpCPkts OBJECT-TYPE
    SYNTAX  Counter64
    MAX-ACCESS read-only
    STATUS  current
    DESCRIPTION
        ""
    -- 1.3.6.1.4.1.32620.1.1.4.101.1.25
    ::= { anueNtoStageGscToolFilterEntry 25 }


anueGscTFltrPeakGtpUPkts OBJECT-TYPE
    SYNTAX  Counter64
    MAX-ACCESS read-only
    STATUS  current
    DESCRIPTION
        ""
    -- 1.3.6.1.4.1.32620.1.1.4.101.1.26
    ::= { anueNtoStageGscToolFilterEntry 26 }


anueGscTFltrPeakDiameterPkts OBJECT-TYPE
    SYNTAX  Counter64
    MAX-ACCESS read-only
    STATUS  current
    DESCRIPTION
        ""
    -- 1.3.6.1.4.1.32620.1.1.4.101.1.27
    ::= { anueNtoStageGscToolFilterEntry 27 }


anueGscTFltrPeakDnsPkts OBJECT-TYPE
    SYNTAX  Counter64
    MAX-ACCESS read-only
    STATUS  current
    DESCRIPTION
        ""
    -- 1.3.6.1.4.1.32620.1.1.4.101.1.28
    ::= { anueNtoStageGscToolFilterEntry 28 }


anueGscTFltrPeakRadiusPkts OBJECT-TYPE
    SYNTAX  Counter64
    MAX-ACCESS read-only
    STATUS  current
    DESCRIPTION
        ""
    -- 1.3.6.1.4.1.32620.1.1.4.101.1.29
    ::= { anueNtoStageGscToolFilterEntry 29 }


anueGscTFltrPeakGtpCPktsT OBJECT-TYPE
    SYNTAX  DateAndTime
    MAX-ACCESS read-only
    STATUS  current
    DESCRIPTION
        ""
    -- 1.3.6.1.4.1.32620.1.1.4.101.1.30
    ::= { anueNtoStageGscToolFilterEntry 30 }

anueGscTFltrPeakGtpUPktsT OBJECT-TYPE
    SYNTAX  DateAndTime
    MAX-ACCESS read-only
    STATUS  current
    DESCRIPTION
        ""
    -- 1.3.6.1.4.1.32620.1.1.4.101.1.31
    ::= { anueNtoStageGscToolFilterEntry 31 }


anueGscTFltrPeakDiameterPktsT OBJECT-TYPE
    SYNTAX  DateAndTime
    MAX-ACCESS read-only
    STATUS  current
    DESCRIPTION
        ""
    -- 1.3.6.1.4.1.32620.1.1.4.101.1.32
    ::= { anueNtoStageGscToolFilterEntry 32 }


anueGscTFltrPeakDnsPktsT OBJECT-TYPE
    SYNTAX  DateAndTime
    MAX-ACCESS read-only
    STATUS  current
    DESCRIPTION
        ""
    -- 1.3.6.1.4.1.32620.1.1.4.101.1.33
    ::= { anueNtoStageGscToolFilterEntry 33 }


anueGscTFltrPeakRadiusPktsT OBJECT-TYPE
    SYNTAX  DateAndTime
    MAX-ACCESS read-only
    STATUS  current
    DESCRIPTION
        ""
    -- 1.3.6.1.4.1.32620.1.1.4.101.1.34
    ::= { anueNtoStageGscToolFilterEntry 34 }


anueGscTFltrTotGtpCPkts OBJECT-TYPE
    SYNTAX  Counter64
    MAX-ACCESS read-only
    STATUS  current
    DESCRIPTION
        ""
    -- 1.3.6.1.4.1.32620.1.1.4.101.1.35
    ::= { anueNtoStageGscToolFilterEntry 35 }


anueGscTFltrTotGtpUPkts OBJECT-TYPE
    SYNTAX  Counter64
    MAX-ACCESS read-only
    STATUS  current
    DESCRIPTION
        ""
    -- 1.3.6.1.4.1.32620.1.1.4.101.1.36
    ::= { anueNtoStageGscToolFilterEntry 36 }


anueGscTFltrTotDiameterPkts OBJECT-TYPE
    SYNTAX  Counter64
    MAX-ACCESS read-only
    STATUS  current
    DESCRIPTION
        ""
    -- 1.3.6.1.4.1.32620.1.1.4.101.1.37
    ::= { anueNtoStageGscToolFilterEntry 37 }


anueGscTFltrTotDnsPkts OBJECT-TYPE
    SYNTAX  Counter64
    MAX-ACCESS read-only
    STATUS  current
    DESCRIPTION
        ""
    -- 1.3.6.1.4.1.32620.1.1.4.101.1.38
    ::= { anueNtoStageGscToolFilterEntry 38 }


anueGscTFltrTotRadiusPkts OBJECT-TYPE
    SYNTAX  Counter64
    MAX-ACCESS read-only
    STATUS  current
    DESCRIPTION
        ""
    -- 1.3.6.1.4.1.32620.1.1.4.101.1.39
    ::= { anueNtoStageGscToolFilterEntry 39 }


anueGscTFltrCurGtpCPkts OBJECT-TYPE
    SYNTAX  Counter64
    MAX-ACCESS read-only
    STATUS  current
    DESCRIPTION
        ""
    -- 1.3.6.1.4.1.32620.1.1.4.101.1.40
    ::= { anueNtoStageGscToolFilterEntry 40 }


anueGscTFltrCurGtpUPkts OBJECT-TYPE
    SYNTAX  Counter64
    MAX-ACCESS read-only
    STATUS  current
    DESCRIPTION
        ""
    -- 1.3.6.1.4.1.32620.1.1.4.101.1.41
    ::= { anueNtoStageGscToolFilterEntry 41 }


anueGscTFltrCurDiameterPkts OBJECT-TYPE
    SYNTAX  Counter64
    MAX-ACCESS read-only
    STATUS  current
    DESCRIPTION
        ""
    -- 1.3.6.1.4.1.32620.1.1.4.101.1.42
    ::= { anueNtoStageGscToolFilterEntry 42 }


anueGscTFltrCurDnsPkts OBJECT-TYPE
    SYNTAX  Counter64
    MAX-ACCESS read-only
    STATUS  current
    DESCRIPTION
        ""
    -- 1.3.6.1.4.1.32620.1.1.4.101.1.43
    ::= { anueNtoStageGscToolFilterEntry 43 }


anueGscTFltrCurRadiusPkts OBJECT-TYPE
    SYNTAX  Counter64
    MAX-ACCESS read-only
    STATUS  current
    DESCRIPTION
        ""
    -- 1.3.6.1.4.1.32620.1.1.4.101.1.44
    ::= { anueNtoStageGscToolFilterEntry 44 }

-- GSC stage entries end here.



--                      --
-- Notification payload --
--                      --

anueNtoPayload OBJECT IDENTIFIER
    -- 1.3.6.1.4.1.32620.1.1.5
    ::= { anueNtoObjects 5 }

-- Event monitor subsystem notification payload
--
-- These variables are used by multiple notification types.
-- The first block of payload data derives from a specific triggering event.
-- The second block of payload data derives from the monitor definition.

anueNtoEventMonData OBJECT IDENTIFIER
    -- 1.3.6.1.4.1.32620.1.1.5.1
    ::= { anueNtoPayload 1 }

-- Payload data from a specific triggering event.

anueNtoEventMonDataDateAndTime OBJECT-TYPE
    SYNTAX      DateAndTime
    MAX-ACCESS  accessible-for-notify
    STATUS      current
    DESCRIPTION
       "The date and time at which this notification occurred."
    -- 1.3.6.1.4.1.32620.1.1.5.1.1
    ::= { anueNtoEventMonData 1 }

anueNtoEventMonDataTriggerCause OBJECT-TYPE
    SYNTAX      OBJECT IDENTIFIER
    MAX-ACCESS  accessible-for-notify
    STATUS      current
    DESCRIPTION
       "The cause of this notification, including both the statistic being
        monitored (e.g., port utilization) and the triggering entity (e.g.,
        filter, port group) whose value crossed the predefined threshold.
        The statistic being monitored is specified as a table column OID.
        The triggering entity is specified by the indices of that OID.
        Example: anueFilterCurHCUtil.anueFilterTypeToolPort.4"
    -- 1.3.6.1.4.1.32620.1.1.5.1.2
    ::= { anueNtoEventMonData 2 }

anueNtoEventMonDataTriggerValue OBJECT-TYPE
    SYNTAX      DisplayString
    MAX-ACCESS  accessible-for-notify
    STATUS      current
    DESCRIPTION
       "The value of the statistic being monitored that crossed the
        predefined threshold.  Depending on smoothing options defined in the
        event monitor, this value may be blended with other samples."
    -- 1.3.6.1.4.1.32620.1.1.5.1.3
    ::= { anueNtoEventMonData 3 }

anueNtoEventMonDataDirection OBJECT-TYPE
    SYNTAX      AnueThresholdCrossing
    MAX-ACCESS  accessible-for-notify
    STATUS      current
    DESCRIPTION
       "The direction (up or down) in which the statistic being monitored
        crossed the predefined threshold."
    -- 1.3.6.1.4.1.32620.1.1.5.1.4
    ::= { anueNtoEventMonData 4 }

anueNtoEventMonDataStatName OBJECT-TYPE
    SYNTAX      DisplayString
    MAX-ACCESS  accessible-for-notify
    STATUS      current
    DESCRIPTION
       "A human-readable string containing the name of the statistic being
        monitored.  Example: TP_TOTAL_DROP_COUNT_PACKETS"
    -- 1.3.6.1.4.1.32620.1.1.5.1.5
    ::= { anueNtoEventMonData 5 }

anueNtoEventMonDataEntityName OBJECT-TYPE
    SYNTAX      DisplayString
    MAX-ACCESS  accessible-for-notify
    STATUS      current
    DESCRIPTION
       "A human-readable string containing the name of the triggering entity.
        Example: P04"
    -- 1.3.6.1.4.1.32620.1.1.5.1.6
    ::= { anueNtoEventMonData 6 }

anueNtoEventMonDataNotSent OBJECT-TYPE
    SYNTAX      Counter32
    MAX-ACCESS  accessible-for-notify
    STATUS      current
    DESCRIPTION
       "The number of notifications not sent for this event monitor because
        of the configured minimum time interval between event actions."
    -- 1.3.6.1.4.1.32620.1.1.5.1.7
    ::= { anueNtoEventMonData 7 }

anueNtoEventMonDataTriggerDescr OBJECT-TYPE
    SYNTAX      DisplayString
    MAX-ACCESS  accessible-for-notify
    STATUS      current
    DESCRIPTION
       "A human-readable string describing the cause of this notification.
        This is used only when there is no OID available for this purpose."
    -- 1.3.6.1.4.1.32620.1.1.5.1.8
    ::= { anueNtoEventMonData 8 }

-- Payload data from the monitor definition.

anueNtoEventMonDataThreshold OBJECT-TYPE
    SYNTAX      CounterBasedGauge64
    MAX-ACCESS  accessible-for-notify
    STATUS      current
    DESCRIPTION
       "The threshold value defined in the event monitor that causes this
        event to trigger."
    -- 1.3.6.1.4.1.32620.1.1.5.1.11
    ::= { anueNtoEventMonData 11 }

anueNtoEventMonDataInterval OBJECT-TYPE
    SYNTAX      Integer32
    MAX-ACCESS  accessible-for-notify
    STATUS      current
    DESCRIPTION
       "The minimum time (in seconds) that must elapse between event actions
        for this monitor."
    -- 1.3.6.1.4.1.32620.1.1.5.1.12
    ::= { anueNtoEventMonData 12 }

anueNtoEventMonDataWindowSize OBJECT-TYPE
    SYNTAX      Integer32
    MAX-ACCESS  accessible-for-notify
    STATUS      current
    DESCRIPTION
       "On the 7300 platform it represents the duration (in seconds)of the
            time window over which the value being monitored is calculated.
            On the 5200 platform it represents the duration (in statistics polling intervals)
            of the time window over which the value being monitored is calculated."
    -- 1.3.6.1.4.1.32620.1.1.5.1.13
    ::= { anueNtoEventMonData 13 }

anueNtoEventMonDataWindowCount OBJECT-TYPE
    SYNTAX      Integer32
    MAX-ACCESS  accessible-for-notify
    STATUS      current
    DESCRIPTION
       "The number of consecutive time windows for which a monitored value must
        stay across a specified threshold in order for an action to be triggered."
    -- 1.3.6.1.4.1.32620.1.1.5.1.14
    ::= { anueNtoEventMonData 14 }


-- Test notification payload
--

anueNtoEventTestData OBJECT IDENTIFIER
    -- 1.3.6.1.4.1.32620.1.1.5.2
    ::= { anueNtoPayload 2 }

anueNtoEventTestTime OBJECT-TYPE
    SYNTAX  DateAndTime
    MAX-ACCESS read-only
    STATUS  current
    DESCRIPTION
       "The time when test notification was generated."
    -- 1.3.6.1.4.1.32620.1.1.5.2.1
    ::= { anueNtoEventTestData 1 }

anueNtoEventTestMessage OBJECT-TYPE
    SYNTAX  DisplayString
    MAX-ACCESS read-only
    STATUS  current
    DESCRIPTION
       "The message can be 'Anue Test Alarm' or 'Clear Anue Test Alarm'."
    -- 1.3.6.1.4.1.32620.1.1.5.2.2
    ::= { anueNtoEventTestData 2 }


-- Member action notification payload
--

anueMemberActionData OBJECT IDENTIFIER
    -- 1.3.6.1.4.1.32620.1.1.5.3
    ::= { anueNtoPayload 3 }

anueMemberActionDataMemberName OBJECT-TYPE
    SYNTAX  DisplayString
    MAX-ACCESS read-only
    STATUS  current
    DESCRIPTION
       "The name of union member involved in action."
    -- 1.3.6.1.4.1.32620.1.1.5.3.1
    ::= { anueMemberActionData 1 }

anueMemberActionDataType OBJECT-TYPE
    SYNTAX      AnueNtoUnionMemberActionType
    MAX-ACCESS  accessible-for-notify
    STATUS      current
    DESCRIPTION
       "The union member action type that occurred."
    -- 1.3.6.1.4.1.32620.1.1.5.3.2
    ::= { anueMemberActionData 2 }



-- anueNtoCapture
--

anueNtoCapture OBJECT IDENTIFIER
    -- 1.3.6.1.4.1.32620.1.1.6
    ::= { anueNtoObjects 6 }


anueNtoCaptureTable OBJECT-TYPE
    SYNTAX  SEQUENCE OF AnueNtoCaptureEntry
    MAX-ACCESS not-accessible
    STATUS  current
    DESCRIPTION
       "A list of capture entries.
        This table contains the available capture resources"

    -- 1.3.6.1.4.1.32620.1.1.6.1
    ::= { anueNtoCapture 1 }


anueNtoCaptureEntry OBJECT-TYPE
    SYNTAX  AnueNtoCaptureEntry
    MAX-ACCESS not-accessible
    STATUS  current
    DESCRIPTION
        "An entry containing additional information
        about an capture port on Anue NTO devices.  "
    INDEX {
        anueCaptureNumber
    }
    -- 1.3.6.1.4.1.32620.1.1.6.1.1
    ::= { anueNtoCaptureTable 1 }


AnueNtoCaptureEntry ::= SEQUENCE {
    anueCaptureNumber                               Integer32,
    anueCaptureDefaultName                          DisplayString,
    anueCaptureName                                 DisplayString,
    anueCaptureDesc                                 DisplayString,
    anueCaptureStatus                               INTEGER,
    anueCaptureBufferSize                           INTEGER,
    anueCaptureBufferType                           INTEGER,
    anueCaptureTriggerMode                          INTEGER,
    anueCaptureTriggerPosition                      INTEGER,
    anueCaptureFillBufferToTrigger                  TruthValue,
    anueCaptureEnableTrailerStripping               INTEGER,
    anueCaptureTriggerCriteria                      DisplayString,
    anueCaptureConnection                           OBJECT IDENTIFIER }

anueCaptureNumber OBJECT-TYPE
    SYNTAX  Integer32  (1..2147483647)
    MAX-ACCESS read-only
    STATUS  current
    DESCRIPTION
        "Capture number is a number which identifies a
        capture port."
    -- 1.3.6.1.4.1.32620.1.1.6.1.1.1
    ::= { anueNtoCaptureEntry 1 }


anueCaptureDefaultName OBJECT-TYPE
    SYNTAX  DisplayString
    MAX-ACCESS read-only
    STATUS  current
    DESCRIPTION
        "Capture default name is the system assigned name for a
        capture entry.  These names are displayed in various locations
        in the NTO Control Panel.

        A capture resource's default name begins with the letter 'L'
        followed by the first unused number starting with 1.  The first
        capture resource is L1-CAP, followed by L2-CAP and so on.

        The default name for capture resource is platform dependent."
    -- 1.3.6.1.4.1.32620.1.1.6.1.1.2
    ::= { anueNtoCaptureEntry 2 }


anueCaptureName OBJECT-TYPE
    SYNTAX  DisplayString
    MAX-ACCESS read-only
    STATUS  current
    DESCRIPTION
        "Capture name is the user entered capture resource's name.
        The capture name defaults to anueCaptureDefaultName
        if the user hasn't entered the name."
    -- 1.3.6.1.4.1.32620.1.1.6.1.1.3
    ::= { anueNtoCaptureEntry 3 }

anueCaptureDesc OBJECT-TYPE
    SYNTAX  DisplayString
    MAX-ACCESS read-only
    STATUS  current
    DESCRIPTION
        "This is the user entered capture resource description.
        The object value is an empty string (Null) if there is no user
        entered description."
    -- 1.3.6.1.4.1.32620.1.1.6.1.1.4
    ::= { anueNtoCaptureEntry 4 }

anueCaptureStatus OBJECT-TYPE
    SYNTAX  INTEGER {
        anueCaptureStatusIdleEmpty(1),
        anueCaptureStatusStartedEmpty(2),
        anueCaptureStatusStartedWithData(3),
        anueCaptureStatusStartedTriggered(4),
        anueCaptureStatusIdleWithData(5),
        anueCaptureStatusUnassigned(6),
        anueCaptureStatusPlaybackStopped(7),
        anueCaptureStatusPlaybackStarted(8),
        anueCaptureStatusOffline(9),
        anueCaptureStatusError(10) }
    MAX-ACCESS read-only
    STATUS  current
    DESCRIPTION
        "Status of this capture resource."
    -- 1.3.6.1.4.1.32620.1.1.6.1.1.5
    ::= { anueNtoCaptureEntry 5 }

anueCaptureBufferSize OBJECT-TYPE
    SYNTAX  INTEGER
    MAX-ACCESS read-only
    STATUS  current
    DESCRIPTION
        "Size in MB of the maximum buffer size."
    -- 1.3.6.1.4.1.32620.1.1.6.1.1.6
    ::= { anueNtoCaptureEntry 6 }

anueCaptureBufferType OBJECT-TYPE
    SYNTAX  INTEGER {
        anueCaptureBufferTypeStopOnBufferFull(1),
        anueCaptureBufferTypeCircular(2) }
    MAX-ACCESS read-only
    STATUS  current
    DESCRIPTION
        "The type of buffer used"
    -- 1.3.6.1.4.1.32620.1.1.6.1.1.7
    ::= { anueNtoCaptureEntry 7 }

anueCaptureTriggerMode OBJECT-TYPE
    SYNTAX  INTEGER {
        anueCaptureTriggerModeManual(1),
        anueCaptureTrigerModeTriggered(2) }
    MAX-ACCESS read-only
    STATUS  current
    DESCRIPTION
        "The type of trigger"
    -- 1.3.6.1.4.1.32620.1.1.6.1.1.8
    ::= { anueNtoCaptureEntry 8 }

        anueCaptureTriggerPosition OBJECT-TYPE
    SYNTAX  INTEGER
    MAX-ACCESS read-only
    STATUS  current
    DESCRIPTION
        "Trigger position percentage"
    -- 1.3.6.1.4.1.32620.1.1.6.1.1.9
    ::= { anueNtoCaptureEntry 9 }

        anueCaptureFillBufferToTrigger OBJECT-TYPE
    SYNTAX  TruthValue
    MAX-ACCESS read-only
    STATUS  current
    DESCRIPTION
        "Tells if to fill the buffer before the trigger"
    -- 1.3.6.1.4.1.32620.1.1.6.1.1.10
    ::= { anueNtoCaptureEntry 10 }

        anueCaptureEnableTrailerStripping OBJECT-TYPE
    SYNTAX  INTEGER {
        anueCaptureEnableTrailerStrippingDisabled(1),
        anueCaptureEnableTrailerStrippingPreserveAndTimeStamp(2),
        anueCaptureEnableTrailerStrippingLocalTime (3)}
    MAX-ACCESS read-only
    STATUS  current
    DESCRIPTION
        "The type of trailer stripping"
    -- 1.3.6.1.4.1.32620.1.1.6.1.1.11
    ::= { anueNtoCaptureEntry 11 }

anueCaptureTriggerCriteria OBJECT-TYPE
    SYNTAX  DisplayString
    MAX-ACCESS read-only
    STATUS  current
    DESCRIPTION
        "A textual representation of the trigger criteria configured for the capture resource."
    -- 1.3.6.1.4.1.32620.1.1.6.1.1.12
    ::= { anueNtoCaptureEntry 12 }

anueCaptureConnection OBJECT-TYPE
    SYNTAX  OBJECT IDENTIFIER
    MAX-ACCESS read-only
    STATUS  current
    DESCRIPTION
        "The port or dynamic filter OID to which this capture is connected to."
    -- 1.3.6.1.4.1.32620.1.1.6.1.1.13
    ::= { anueNtoCaptureEntry 13 }

anueNtoCaptureStatsTable OBJECT-TYPE
    SYNTAX  SEQUENCE OF AnueNtoCaptureStatsEntry
    MAX-ACCESS not-accessible
    STATUS  current
    DESCRIPTION
       "A list of capture stats entries.
        This table contains statistics for each capture resource available"

    -- 1.3.6.1.4.1.32620.1.1.6.2
    ::= { anueNtoCapture 2 }


anueNtoCaptureStatsEntry OBJECT-TYPE
    SYNTAX  AnueNtoCaptureStatsEntry
    MAX-ACCESS not-accessible
    STATUS  current
    DESCRIPTION
        "An entry containing additional information
        about capture statistics.  "
    INDEX {
        anueCaptureNumber
    }
    -- 1.3.6.1.4.1.32620.1.1.6.2.1
    ::= { anueNtoCaptureStatsTable 1 }


AnueNtoCaptureStatsEntry ::= SEQUENCE {
    anueCaptureTransBytesTotal                      Counter64,
    anueCaptureTransBytesCur                        Counter64,
    anueCaptureTransBytesAvg                        Counter64,
    anueCaptureTransBytesPeak                       Counter64,
    anueCaptureTransBytesPeakTime                   DateAndTime,
    anueCaptureTransBytesTimeSincePeak              Counter64,
    anueCaptureTransPktsTotal                       Counter64,
    anueCaptureTransPktsCur                         Counter64,
    anueCaptureTransPktsAvg                         Counter64,
    anueCaptureTransPktsPeak                        Counter64,
    anueCaptureTransPktsPeakTime                    DateAndTime,
    anueCaptureTransPktsTimeSincePeak               Counter64,
    anueCaptureDropPktsTotal                        Counter64,
    anueCaptureDropPktsCur                          Counter64,
    anueCaptureDropPktsAvg                          Counter64,
    anueCaptureDropPktsPeak                         Counter64,
    anueCaptureDropPktsPeakTime                     DateAndTime,
    anueCaptureDropPktsTimeSincePeak                Counter64,
    anueCaptureBufferUtilizationPerc                Counter64,
    anueCaptureTimeSinceReset                       Counter64,
    anueCaptureResetById                            DisplayString }

anueCaptureTransBytesTotal OBJECT-TYPE
    SYNTAX  Counter64
    MAX-ACCESS read-only
    STATUS  current
    DESCRIPTION
        "Transmitted(To-Capture) Bytes Total"
    -- 1.3.6.1.4.1.32620.1.1.6.2.1.1
    ::= { anueNtoCaptureStatsEntry 1 }

anueCaptureTransBytesCur OBJECT-TYPE
    SYNTAX  Counter64
    MAX-ACCESS read-only
    STATUS  current
    DESCRIPTION
        "Transmitted(To-Capture) Cur Bits/Sec"
    -- 1.3.6.1.4.1.32620.1.1.6.2.1.2
    ::= { anueNtoCaptureStatsEntry 2 }

anueCaptureTransBytesAvg OBJECT-TYPE
    SYNTAX  Counter64
    MAX-ACCESS read-only
    STATUS  current
    DESCRIPTION
        "Transmitted(To-Capture) Avg Bits/Sec"
    -- 1.3.6.1.4.1.32620.1.1.6.2.1.3
    ::= { anueNtoCaptureStatsEntry 3 }

anueCaptureTransBytesPeak OBJECT-TYPE
    SYNTAX  Counter64
    MAX-ACCESS read-only
    STATUS  current
    DESCRIPTION
        "Transmitted(To-Capture) Peak Bits/Sec"
    -- 1.3.6.1.4.1.32620.1.1.6.2.1.4
    ::= { anueNtoCaptureStatsEntry 4 }

anueCaptureTransBytesPeakTime OBJECT-TYPE
    SYNTAX  DateAndTime
    MAX-ACCESS read-only
    STATUS  current
    DESCRIPTION
        "Transmitted(To-Capture) Returns the time at which a peak Tx rate was observed."
    -- 1.3.6.1.4.1.32620.1.1.6.2.1.5
    ::= { anueNtoCaptureStatsEntry 5 }

anueCaptureTransBytesTimeSincePeak OBJECT-TYPE
    SYNTAX  Counter64
    MAX-ACCESS read-only
    STATUS  current
    DESCRIPTION
        "Transmitted(To-Capture) Returns the number of milliseconds since a Tx peak rate was observed."
    -- 1.3.6.1.4.1.32620.1.1.6.2.1.6
    ::= { anueNtoCaptureStatsEntry 6 }

anueCaptureTransPktsTotal OBJECT-TYPE
    SYNTAX  Counter64
    MAX-ACCESS read-only
    STATUS  current
    DESCRIPTION
        "Transmitted(To-Capture) Pkts Total"
    -- 1.3.6.1.4.1.32620.1.1.6.2.1.7
    ::= { anueNtoCaptureStatsEntry 7 }

anueCaptureTransPktsCur OBJECT-TYPE
    SYNTAX  Counter64
    MAX-ACCESS read-only
    STATUS  current
    DESCRIPTION
        "Transmitted(To-Capture) Cur Pkts/Sec"
    -- 1.3.6.1.4.1.32620.1.1.6.2.1.8
    ::= { anueNtoCaptureStatsEntry 8 }

anueCaptureTransPktsAvg OBJECT-TYPE
    SYNTAX  Counter64
    MAX-ACCESS read-only
    STATUS  current
    DESCRIPTION
        "Transmitted(To-Capture) Avg Pkts/Sec"
    -- 1.3.6.1.4.1.32620.1.1.6.2.1.9
    ::= { anueNtoCaptureStatsEntry 9 }

anueCaptureTransPktsPeak OBJECT-TYPE
    SYNTAX  Counter64
    MAX-ACCESS read-only
    STATUS  current
    DESCRIPTION
        "Transmitted(To-Capture) Peak Pkts/Sec"
    -- 1.3.6.1.4.1.32620.1.1.6.2.1.10
    ::= { anueNtoCaptureStatsEntry 10 }

anueCaptureTransPktsPeakTime OBJECT-TYPE
    SYNTAX  DateAndTime
    MAX-ACCESS read-only
    STATUS  current
    DESCRIPTION
        "Transmitted(To-Capture) Returns the time at which a peak Tx rate was observed."
    -- 1.3.6.1.4.1.32620.1.1.6.2.1.11
    ::= { anueNtoCaptureStatsEntry 11 }

anueCaptureTransPktsTimeSincePeak OBJECT-TYPE
    SYNTAX  Counter64
    MAX-ACCESS read-only
    STATUS  current
    DESCRIPTION
        "Transmitted(To-Capture) Returns the number of milliseconds since a Tx peak rate was observed."
    -- 1.3.6.1.4.1.32620.1.1.6.2.1.12
    ::= { anueNtoCaptureStatsEntry 12 }

anueCaptureDropPktsTotal OBJECT-TYPE
    SYNTAX  Counter64
    MAX-ACCESS read-only
    STATUS  current
    DESCRIPTION
        "Dropped(Pre-Capture) Pkts Total"
    -- 1.3.6.1.4.1.32620.1.1.6.2.1.13
    ::= { anueNtoCaptureStatsEntry 13 }

anueCaptureDropPktsCur OBJECT-TYPE
    SYNTAX  Counter64
    MAX-ACCESS read-only
    STATUS  current
    DESCRIPTION
        "Dropped(Pre-Capture) Cur Pkts/Sec"
    -- 1.3.6.1.4.1.32620.1.1.6.2.1.14
    ::= { anueNtoCaptureStatsEntry 14 }

anueCaptureDropPktsAvg OBJECT-TYPE
    SYNTAX  Counter64
    MAX-ACCESS read-only
    STATUS  current
    DESCRIPTION
        "Dropped(Pre-Capture) Avg Pkts/Sec"
    -- 1.3.6.1.4.1.32620.1.1.6.2.1.15
    ::= { anueNtoCaptureStatsEntry 15 }

anueCaptureDropPktsPeak OBJECT-TYPE
    SYNTAX  Counter64
    MAX-ACCESS read-only
    STATUS  current
    DESCRIPTION
        "Dropped(Pre-Capture) Peak Pkts/Sec"
    -- 1.3.6.1.4.1.32620.1.1.6.2.1.16
    ::= { anueNtoCaptureStatsEntry 16 }

anueCaptureDropPktsPeakTime OBJECT-TYPE
    SYNTAX  DateAndTime
    MAX-ACCESS read-only
    STATUS  current
    DESCRIPTION
        "Dropped(Pre-Capture) Returns the time at which a peak Dx rate was observed."
    -- 1.3.6.1.4.1.32620.1.1.6.2.1.17
    ::= { anueNtoCaptureStatsEntry 17 }

anueCaptureDropPktsTimeSincePeak OBJECT-TYPE
    SYNTAX  Counter64
    MAX-ACCESS read-only
    STATUS  current
    DESCRIPTION
        "Dropped(Pre-Capture) Returns the number of milliseconds since a Dx peak rate was observed."
    -- 1.3.6.1.4.1.32620.1.1.6.2.1.18
    ::= { anueNtoCaptureStatsEntry 18 }

anueCaptureBufferUtilizationPerc OBJECT-TYPE
    SYNTAX  Counter64
    MAX-ACCESS read-only
    STATUS  current
    DESCRIPTION
        "Buffer utilization percent. "
    -- 1.3.6.1.4.1.32620.1.1.6.2.1.19
    ::= { anueNtoCaptureStatsEntry 19 }

anueCaptureTimeSinceReset OBJECT-TYPE
    SYNTAX  Counter64
    MAX-ACCESS read-only
    STATUS  current
    DESCRIPTION
        "Time in milliseconds since the last reset for this capture resource. "
    -- 1.3.6.1.4.1.32620.1.1.6.2.1.20
    ::= { anueNtoCaptureStatsEntry 20 }


anueCaptureResetById OBJECT-TYPE
    SYNTAX  DisplayString
    MAX-ACCESS read-only
    STATUS  current
    DESCRIPTION
        "User Id who did the last stats reset. "
    -- 1.3.6.1.4.1.32620.1.1.6.2.1.21
    ::= { anueNtoCaptureStatsEntry 21 }

--anueNtoResource
--

anueNtoResource OBJECT IDENTIFIER
    -- 1.3.6.1.4.1.32620.1.1.7
    ::= { anueNtoObjects 7 }

anueNtoResourceTable OBJECT-TYPE
    SYNTAX  SEQUENCE OF AnueNtoResourceEntry
    MAX-ACCESS not-accessible
    STATUS  current
    DESCRIPTION
       "A list of Resource entries.
        This table contains the available resources"

    -- 1.3.6.1.4.1.32620.1.1.7.1
    ::= { anueNtoResource 1 }

anueNtoResourceEntry OBJECT-TYPE
    SYNTAX  AnueNtoResourceEntry
    MAX-ACCESS not-accessible
    STATUS  current
    DESCRIPTION
        "An entry containing additional information
        about a resource on Anue NTO devices.  "
    INDEX {
        anueResourceFilterType,
        anueResourceNumber
    }
    -- 1.3.6.1.4.1.32620.1.1.7.1.1
    ::= { anueNtoResourceTable 1 }

    AnueNtoResourceEntry ::= SEQUENCE {
    anueResourceFilterType                           AnueFilterTypeDT,
    anueResourceNumber                               Integer32,
    anueResourceDefaultName                          DisplayString,
    anueResourceName                                 DisplayString,
    anueResourceDesc                                 DisplayString,
    anueResourceStatus                               INTEGER }

anueResourceFilterType OBJECT-TYPE
    SYNTAX  AnueFilterTypeDT
    MAX-ACCESS read-only
    STATUS  current
    DESCRIPTION
        "Partial index identifying the filter entry in the
        anueNtoResourceTable to which this stage is subordinate."
    -- 1.3.6.1.4.1.32620.1.1.7.1.1.1
    ::= { anueNtoResourceEntry 1 }

anueResourceNumber OBJECT-TYPE
    SYNTAX  Integer32  (1..2147483647)
    MAX-ACCESS read-only
    STATUS  current
    DESCRIPTION
        "Resource number is a number which identifies a
        resource port."
    -- 1.3.6.1.4.1.32620.1.1.7.1.1.2
    ::= { anueNtoResourceEntry 2 }

anueResourceDefaultName OBJECT-TYPE
    SYNTAX  DisplayString
    MAX-ACCESS read-only
    STATUS  current
    DESCRIPTION
        "Resource default name is the system assigned name for a
        resource entry.  These names are displayed in various locations
        in the NTO Control Panel."
    -- 1.3.6.1.4.1.32620.1.1.7.1.1.3
    ::= { anueNtoResourceEntry 3 }

anueResourceName OBJECT-TYPE
    SYNTAX  DisplayString
    MAX-ACCESS read-only
    STATUS  current
    DESCRIPTION
        "Resource name is the user entered resource's name.
        The resource name defaults to anueResourceDefaultName
        if the user hasn't entered the name."
    -- 1.3.6.1.4.1.32620.1.1.7.1.1.4
    ::= { anueNtoResourceEntry 4 }

anueResourceDesc OBJECT-TYPE
    SYNTAX  DisplayString
    MAX-ACCESS read-only
    STATUS  current
    DESCRIPTION
        "This is the user entered resource description.
        The object value is an empty string (Null) if there is no user
        entered description."
    -- 1.3.6.1.4.1.32620.1.1.7.1.1.5
    ::= { anueNtoResourceEntry 5 }

anueResourceStatus OBJECT-TYPE
    SYNTAX  INTEGER {
        anueResourceStatusInitializing(1),
        anueResourceStatusUpgrading(2),
        anueResourceStatusInitializationFailed(3),
        anueResourceStatusNotPresent(4),
        anueResourceStatusReady(5),
        anueResourceStatusNotLicensed(6)}
    MAX-ACCESS read-only
    STATUS  current
    DESCRIPTION
        "Status of this resource."
    -- 1.3.6.1.4.1.32620.1.1.7.1.1.6
    ::= { anueNtoResourceEntry 6 }

-- GSC objects not part of filters or stages begin here.
--

anueGscObjects OBJECT IDENTIFIER
    -- 1.3.6.1.4.1.32620.1.2
    ::= { anueObjects 2 }



-- anueGscSystem
--

anueGscSystem OBJECT IDENTIFIER
    -- 1.3.6.1.4.1.32620.1.2.1
    ::= { anueGscObjects 1 }


-- anueGscLastCriticalFailure
--
-- The anueGscLastCriticalFailure object contains the date, time,
-- and the type of the last GSC critical failure notice.
-- The variables in this object are used in forming the
-- anueGscCriticalFailure notification message.

anueGscLastCriticalFailure OBJECT IDENTIFIER
    -- 1.3.6.1.4.1.32620.1.2.1.9
    ::= { anueGscSystem 9 }

anueCriticalFailureDateAndTime OBJECT-TYPE
    SYNTAX  DateAndTime
    MAX-ACCESS read-only
    STATUS  current
    DESCRIPTION
        "The date and time at which this notice occurred."
    -- 1.3.6.1.4.1.32620.1.2.1.9.1
    ::= { anueGscLastCriticalFailure 1 }

anueCriticalFailureType OBJECT-TYPE
    SYNTAX  DisplayString
    MAX-ACCESS read-only
    STATUS  current
    DESCRIPTION
        "The type of the last GSC critical failure notice."
    -- 1.3.6.1.4.1.32620.1.2.1.9.2
    ::= { anueGscLastCriticalFailure 2 }



-- anueGscData
--

anueGscData OBJECT IDENTIFIER
    -- 1.3.6.1.4.1.32620.1.2.6
    ::= { anueGscObjects 6 }

anueGscPortProbeTable OBJECT-TYPE
    SYNTAX  SEQUENCE OF AnueGscPortProbeEntry
    MAX-ACCESS not-accessible
    STATUS  current
    DESCRIPTION
        "Table of entries holding the conection between ports
        and the GSC probes to which they belong."
    -- 1.3.6.1.4.1.32620.1.2.6.1
    ::= { anueGscData 1 }


anueGscPortProbeEntry OBJECT-TYPE
    SYNTAX  AnueGscPortProbeEntry
    MAX-ACCESS not-accessible
    STATUS  current
    DESCRIPTION
        "Each port that belongs to a probe is represented
        by a row in the anueGscPortProbeTable."
    INDEX {
        ifIndex }
    -- 1.3.6.1.4.1.32620.1.2.6.1.1
    ::= { anueGscPortProbeTable 1 }


AnueGscPortProbeEntry ::= SEQUENCE {
    anueGscPortIfIndex InterfaceIndex,
    anueGscPortProbeId Integer32 }


anueGscPortIfIndex OBJECT-TYPE
    SYNTAX  InterfaceIndex
    MAX-ACCESS read-only
    STATUS  current
    DESCRIPTION
        "The port ifIndex. More information about the port
        can be found under the same index in the ifTable."
    -- 1.3.6.1.4.1.32620.1.2.6.1.1.2
    ::= { anueGscPortProbeEntry 2 }


anueGscPortProbeId OBJECT-TYPE
    SYNTAX  Integer32 (1..2147483647)
    MAX-ACCESS read-only
    STATUS  current
    DESCRIPTION
        "The id of the Probe to which this port belongs to."
    -- 1.3.6.1.4.1.32620.1.2.6.1.1.3
    ::= { anueGscPortProbeEntry 3 }


anueGscProbeTable OBJECT-TYPE
    SYNTAX  SEQUENCE OF AnueGscProbeEntry
    MAX-ACCESS not-accessible
    STATUS  current
    DESCRIPTION
        "Table of entries holding details for GSC Probes."
    -- 1.3.6.1.4.1.32620.1.2.6.2
    ::= { anueGscData 2 }


anueGscProbeEntry OBJECT-TYPE
    SYNTAX  AnueGscProbeEntry
    MAX-ACCESS not-accessible
    STATUS  current
    DESCRIPTION
        "Each GSC Probe is represented by a row in the anueGscProbeTable."
    INDEX {
        anueGscProbeId }
    -- 1.3.6.1.4.1.32620.1.2.6.2.1
    ::= { anueGscProbeTable 1 }


AnueGscProbeEntry ::= SEQUENCE {
    anueGscProbeId                  Integer32,
    anueGscProbePgIfIndex           InterfaceIndex,
    anueGscProbeName                DisplayString,
    anueGscProbeIp                  InetAddress,
    anueGscProbeIsActive            TruthValue,
    anueGscProbeIsRedundant         TruthValue,
    anueGscProbeLastRxHeartbeatTime DateAndTime,
    anueGscProbeLastRxFailMsgTime   DateAndTime,
    anueGscProbeFailoverId          Integer32 }


anueGscProbeId OBJECT-TYPE
    SYNTAX  Integer32 (1..2147483647)
    MAX-ACCESS read-only
    STATUS  current
    DESCRIPTION
        "The probe id."
    -- 1.3.6.1.4.1.32620.1.2.6.2.1.1
    ::= { anueGscProbeEntry 1 }

anueGscProbePgIfIndex OBJECT-TYPE
    SYNTAX  InterfaceIndex
    MAX-ACCESS read-only
    STATUS  current
    DESCRIPTION
        "The ifIndex of the Port Group to which this probes belongs to.
        This conects the anueGscProbeTable to the ifTable."
    -- 1.3.6.1.4.1.32620.1.2.6.2.1.2
    ::= { anueGscProbeEntry 2 }

anueGscProbeName OBJECT-TYPE
    SYNTAX  DisplayString
    MAX-ACCESS read-only
    STATUS  current
    DESCRIPTION
        "The name of the Probe."
    -- 1.3.6.1.4.1.32620.1.2.6.2.1.3
    ::= { anueGscProbeEntry 3 }


anueGscProbeIp OBJECT-TYPE
    SYNTAX  InetAddress
    MAX-ACCESS read-only
    STATUS  current
    DESCRIPTION
        "The IP address of the probe."
    -- 1.3.6.1.4.1.32620.1.2.6.2.1.4
    ::= { anueGscProbeEntry 4 }


anueGscProbeIsActive OBJECT-TYPE
    SYNTAX  TruthValue
    MAX-ACCESS read-only
    STATUS  current
    DESCRIPTION
        "The state of the probe. This has a value of TRUE if
        the probe is active or FALSE if the probe has failed."
    -- 1.3.6.1.4.1.32620.1.2.6.2.1.5
    ::= { anueGscProbeEntry 5 }


anueGscProbeIsRedundant OBJECT-TYPE
    SYNTAX  TruthValue
    MAX-ACCESS read-only
    STATUS  current
    DESCRIPTION
        "This indicates if the probe is marked as redundant."
    -- 1.3.6.1.4.1.32620.1.2.6.2.1.6
    ::= { anueGscProbeEntry 6 }


anueGscProbeLastRxHeartbeatTime OBJECT-TYPE
    SYNTAX  DateAndTime
    MAX-ACCESS read-only
    STATUS  current
    DESCRIPTION
        "The date and time of the last received heartbeat
        for the probe."
    -- 1.3.6.1.4.1.32620.1.2.6.2.1.7
    ::= { anueGscProbeEntry 7 }


anueGscProbeLastRxFailMsgTime OBJECT-TYPE
    SYNTAX  DateAndTime
    MAX-ACCESS read-only
    STATUS  current
    DESCRIPTION
        "The date and time of the last received failed
        message for the probe (if such a message was sent)."
    -- 1.3.6.1.4.1.32620.1.2.6.2.1.8
    ::= { anueGscProbeEntry 8 }


anueGscProbeFailoverId OBJECT-TYPE
    SYNTAX  Integer32 (1..2147483647)
    MAX-ACCESS read-only
    STATUS  current
    DESCRIPTION
        "The id of the probe to which the traffic was
        redirected in case this probe has failed."
    -- 1.3.6.1.4.1.32620.1.2.6.2.1.9
    ::= { anueGscProbeEntry 9 }



-- anueGscPayload
--

anueGscPayload OBJECT IDENTIFIER
    -- 1.3.6.1.4.1.32620.1.2.7
    ::= { anueGscObjects 7 }

anueGscEventFailedProbeData OBJECT IDENTIFIER
    -- 1.3.6.1.4.1.32620.1.2.7.1
    ::= { anueGscPayload 1 }

anueGscEvFailedPbDateAndTime OBJECT-TYPE
    SYNTAX  DateAndTime
    MAX-ACCESS read-only
    STATUS  current
    DESCRIPTION
        "The date and time at which this notification occurred."
    -- 1.3.6.1.4.1.32620.1.2.7.1.1
    ::= { anueGscEventFailedProbeData 1 }

anueGscEvFailedPbId OBJECT-TYPE
    SYNTAX  Integer32 (1..2147483647)
    MAX-ACCESS read-only
    STATUS  current
    DESCRIPTION
        "The ID of the GSC probe that has failed."
    -- 1.3.6.1.4.1.32620.1.2.7.1.2
    ::= { anueGscEventFailedProbeData 2 }

anueGscEvFailedPbName OBJECT-TYPE
    SYNTAX  DisplayString
    MAX-ACCESS read-only
    STATUS  current
    DESCRIPTION
        "The name of the GSC probe that has failed."
    -- 1.3.6.1.4.1.32620.1.2.7.1.3
    ::= { anueGscEventFailedProbeData 3 }


anueGscEvFailedPbIP OBJECT-TYPE
    SYNTAX  InetAddress
    MAX-ACCESS read-only
    STATUS  current
    DESCRIPTION
        "The IP address of the GSC probe that has failed."
    -- 1.3.6.1.4.1.32620.1.2.7.1.4
    ::= { anueGscEventFailedProbeData 4 }


anueGscEvFailedPbPortList OBJECT-TYPE
    SYNTAX  DisplayString
    MAX-ACCESS read-only
    STATUS  current
    DESCRIPTION
        "The ports that are part of the GSC probe that has failed."
    -- 1.3.6.1.4.1.32620.1.2.7.1.5
    ::= { anueGscEventFailedProbeData 5 }


anueGscEvFailedPbLastRxHeartbeat OBJECT-TYPE
    SYNTAX  DateAndTime
    MAX-ACCESS read-only
    STATUS  current
    DESCRIPTION
        "The date and time of the last received heartbeat
        for the GSC probe that has failed."
    -- 1.3.6.1.4.1.32620.1.2.7.1.6
    ::= { anueGscEventFailedProbeData 6 }


anueGscEvFailedPbLastRxFailMsg OBJECT-TYPE
    SYNTAX  DateAndTime
    MAX-ACCESS read-only
    STATUS  current
    DESCRIPTION
        "The date and time of the last received fail message
        for the GSC probe that has failed."
    -- 1.3.6.1.4.1.32620.1.2.7.1.7
    ::= { anueGscEventFailedProbeData 7 }

anueGscEvFailoverPbId OBJECT-TYPE
    SYNTAX  Integer32 (1..2147483647)
    MAX-ACCESS read-only
    STATUS  current
    DESCRIPTION
        "The GSC redundant probes ID to which the traffic
        was failed over, if such a probe exists."
    -- 1.3.6.1.4.1.32620.1.2.7.1.8
    ::= { anueGscEventFailedProbeData 8 }

anueGscEvFailoverPbName OBJECT-TYPE
    SYNTAX  DisplayString
    MAX-ACCESS read-only
    STATUS  current
    DESCRIPTION
        "The GSC redundant probes name to which the traffic was failed over,
        if such a probe exists."
    -- 1.3.6.1.4.1.32620.1.2.7.1.9
    ::= { anueGscEventFailedProbeData 9 }


anueGscEvFailoverPbIP OBJECT-TYPE
    SYNTAX  InetAddress
    MAX-ACCESS read-only
    STATUS  current
    DESCRIPTION
        "The GSC redundant probes IP address to which the traffic
        was failed over, if such a probe exists."
    -- 1.3.6.1.4.1.32620.1.2.7.1.10
    ::= { anueGscEventFailedProbeData 10 }


anueGscEvFailoverPbPortList OBJECT-TYPE
    SYNTAX  DisplayString
    MAX-ACCESS read-only
    STATUS  current
    DESCRIPTION
        "The ports that belong to the GSC redundant probe to which the
        traffic was failed over, if such a probe exists."
    -- 1.3.6.1.4.1.32620.1.2.7.1.11
    ::= { anueGscEventFailedProbeData 11 }



--
-- Notification Types
--

anueEvents OBJECT IDENTIFIER
    -- 1.3.6.1.4.1.32620.2
    ::= { anueMIB 2 }


anueNtoEvents OBJECT IDENTIFIER
    -- 1.3.6.1.4.1.32620.2.1
    ::= { anueEvents 1 }


anueSnmpAuthenticationFailure NOTIFICATION-TYPE
    OBJECTS {
        anueSnmpAuthnFailureTime,
        anueSnmpAuthnFailureUsername,
        anueSnmpAuthnFailureSrcIp,
        anueSnmpAuthnFailureSrcIpType,
        anueSnmpAuthnFailureSecModel }
    STATUS  current
    DESCRIPTION
        "The Anue version of AuenticationFailure notification
        provides extra information about improperly authenticated PDUs
        when compared with the RFC 3418 AuenticationFailure notification.
        It includes username (or community string), message security model,
        source ip address, and type (ipv4 or ipv6).

        The RFC 3418 notification does not include the Source IP address
        of the offending host, so the notification recipient cannot
        determine the source of the invalid SNMP."
    REFERENCE
        "Please see RFC 3418 for definition of the SNMP authentication failure trap."
    -- 1.3.6.1.4.1.32620.2.1.1
    ::= { anueNtoEvents 1 }


anueClientLoginFailure NOTIFICATION-TYPE
    OBJECTS {
        anueClientLoginFailureTime,
        anueClientLoginFailureId,
        anueClientLoginFailureSrcIpType,
        anueClientLoginFailureSrcIp,
        anueClientLoginFailureReason }
    STATUS  current
    DESCRIPTION
        "The Anue client login failure notification signifies that
        a user's login attempt failed due to improper authentication.
        The client login failure notification occurs when an
        invalid user name or password is entered by an Anue client."
    -- 1.3.6.1.4.1.32620.2.1.2
    ::= { anueNtoEvents 2 }


-- Event monitor subsystem notifications
--

-- Statistical counter event monitor notifications

anueNtoEventMonStatInvalidCount NOTIFICATION-TYPE
    OBJECTS {
        anueNtoEventMonDataDateAndTime,
        anueNtoEventMonDataTriggerCause,
        anueNtoEventMonDataTriggerValue,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS      current
    DESCRIPTION
       "A notification from the Anue NTO event monitor subsystem.
        This notification type indicates that an invalid packet counter
        value being monitored exceeded a predefined threshold."
    -- 1.3.6.1.4.1.32620.2.1.3
    ::= { anueNtoEvents 3 }


anueNtoEventMonStatDropCount NOTIFICATION-TYPE
    OBJECTS {
        anueNtoEventMonDataDateAndTime,
        anueNtoEventMonDataTriggerCause,
        anueNtoEventMonDataTriggerValue,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS      current
    DESCRIPTION
       "A notification from the Anue NTO event monitor subsystem.
        This notification type indicates that a dropped packet counter
        value being monitored exceeded a predefined threshold."
    -- 1.3.6.1.4.1.32620.2.1.4
    ::= { anueNtoEvents 4 }


-- Statistical percentage event monitor notifications

anueNtoEventMonStatRxUtilization NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS      current
    DESCRIPTION
       "A notification from the Anue NTO event monitor subsystem.
        This notification type indicates that a receive utilization
        value being monitored crossed a predefined threshold."
    -- 1.3.6.1.4.1.32620.2.1.5
    ::= { anueNtoEvents 5 }


anueNtoEventMonStatTxUtilization NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS      current
    DESCRIPTION
       "A notification from the Anue NTO event monitor subsystem.
        This notification type indicates that a transmit utilization
        value being monitored crossed a predefined threshold."
    -- 1.3.6.1.4.1.32620.2.1.6
    ::= { anueNtoEvents 6 }


-- Other event monitor notifications

anueNtoEventTest NOTIFICATION-TYPE
    OBJECTS {
        anueNtoEventTestTime,
        anueNtoEventTestMessage }
    STATUS      current
    DESCRIPTION
       "On-demand notification type generated at user's request to validate
        the SNMP configuration on the agent and SNMP management system."
    -- 1.3.6.1.4.1.32620.2.1.7
    ::= { anueNtoEvents 7 }


anueNtoEventUnionMemberAction NOTIFICATION-TYPE
    OBJECTS {
        anueNtoEventMonDataDateAndTime,
        anueMemberActionDataType,
        anueMemberActionDataMemberName }
    STATUS      current
    DESCRIPTION
       "This notification type indicates that a union member action has occurred."
    -- 1.3.6.1.4.1.32620.2.1.8
    ::= { anueNtoEvents 8 }


anueNtoEventMonStatLoadDistribution NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS      current
    DESCRIPTION
       "A notification from the Anue NTO event monitor subsystem.
        This notification type indicates that a tool port is not
        load balanced in comparison with the other tool ports that
        have the GTP-U option enabled. This indicated that the received
        data rate on the tool port has crossed a predefined threshold."
    -- 1.3.6.1.4.1.32620.2.1.9
    ::= { anueNtoEvents 9 }

anueGscEvents OBJECT IDENTIFIER
    -- 1.3.6.1.4.1.32620.2.2
    ::= { anueEvents 2 }


anueGscEventMonStatOverflowPkts NOTIFICATION-TYPE
    OBJECTS {
        anueNtoEventMonDataDateAndTime,
        anueNtoEventMonDataTriggerCause,
        anueNtoEventMonDataTriggerValue,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
        "A notification from the Anue GSC event monitor subsystem.
         This notification type indicates that the total number of packets dropped on a network
         port due to a full ingress buffer crossed a predefined threshold."
    -- 1.3.6.1.4.1.32620.2.2.1
    ::= { anueGscEvents 1 }


anueGscEventMonStatControlPlanePktRate NOTIFICATION-TYPE
    OBJECTS {
        anueNtoEventMonDataDateAndTime,
        anueNtoEventMonDataTriggerCause,
        anueNtoEventMonDataTriggerValue,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that the GTP-C packets rate
        value being monitored exceeded a predefined threshold."
    -- 1.3.6.1.4.1.32620.2.2.2
    ::= { anueGscEvents 2 }


anueGscEventMonStatExcessSessions NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that the excess sessions
        value being monitored crossed a predefined threshold."
    -- 1.3.6.1.4.1.32620.2.2.3
    ::= { anueGscEvents 3 }


anueGscEventMonStatIngressPktDrops NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that an ingress packets
        dropped value being monitored crossed a predefined threshold."
    -- 1.3.6.1.4.1.32620.2.2.4
    ::= { anueGscEvents 4 }


anueGscEventMonStatSessionsTableLoad NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that a sessions table load
        value being monitored crossed a predefined threshold."
    -- 1.3.6.1.4.1.32620.2.2.5
    ::= { anueGscEvents 5 }


anueGscEventMonStatNetworkElemLoad NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that a network element load
        value being monitored crossed a predefined threshold."
    -- 1.3.6.1.4.1.32620.2.2.6
    ::= { anueGscEvents 6 }


anueGscEventMonStatReqRespLoad NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that a request response load
        value being monitored crossed a predefined threshold."
    -- 1.3.6.1.4.1.32620.2.2.7
    ::= { anueGscEvents 7 }


anueGscEventMonStatFragmentationLoad NOTIFICATION-TYPE
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataThreshold,
        anueNtoEventMonDataInterval,
        anueNtoEventMonDataWindowSize,
        anueNtoEventMonDataWindowCount }
    STATUS  current
    DESCRIPTION
       "A notification from the Anue GSC event monitor subsystem.
        This notification type indicates that a fragmentation load
        value being monitored crossed a predefined threshold."
    -- 1.3.6.1.4.1.32620.2.2.8
    ::= { anueGscEvents 8 }


anueGscCriticalFailure NOTIFICATION-TYPE
    OBJECTS {
        anueCriticalFailureDateAndTime,
        anueCriticalFailureType }
    STATUS  current
    DESCRIPTION
        "The Anue GSC critical failure notification provides
         information about the appearance of a non-recoverable error.
         This error requires the GSC to be restarted and restored."
    -- 1.3.6.1.4.1.32620.2.2.9
    ::= { anueGscEvents 9 }


anueGscProbeFailure NOTIFICATION-TYPE
    OBJECTS {
        anueGscEvFailedPbDateAndTime,
        anueGscEvFailedPbId,
        anueGscEvFailedPbName,
        anueGscEvFailedPbIP,
        anueGscEvFailedPbPortList,
        anueGscEvFailedPbLastRxHeartbeat,
        anueGscEvFailedPbLastRxFailMsg,
        anueGscEvFailoverPbId,
        anueGscEvFailoverPbName,
        anueGscEvFailoverPbIP,
        anueGscEvFailoverPbPortList }
    STATUS  current
    DESCRIPTION
        "This notification provides information about the
        failure of a GSC probe."
    -- 1.3.6.1.4.1.32620.2.2.10
    ::= { anueGscEvents 10 }


-- Conformance information
--

anueConformance OBJECT IDENTIFIER
    -- 1.3.6.1.4.1.32620.3
    ::= { anueMIB 3 }

anueNtoConformance OBJECT IDENTIFIER
    -- 1.3.6.1.4.1.32620.3.1
    ::= { anueConformance 1 }


anueGroups OBJECT IDENTIFIER
    -- 1.3.6.1.4.1.32620.3.1.1
    ::= { anueNtoConformance 1 }

anueNtoGroups OBJECT IDENTIFIER
    -- 1.3.6.1.4.1.32620.3.1.1.1
    ::= { anueGroups 1 }

anueNtoSystemGroup OBJECT-GROUP
    OBJECTS {
        anueSnmpAuthnFailureTime,
        anueSnmpAuthnFailureUsername,
        anueSnmpAuthnFailureSrcIpType,
        anueSnmpAuthnFailureSrcIp,
        anueSnmpAuthnFailureSecModel,
        anueClientLoginFailureId,
        anueClientLoginFailureSrcIpType,
        anueClientLoginFailureSrcIp,
        anueClientLoginFailureReason,
        anueClientLoginFailureTime,
        anueSnmpAuthnFailureTrapEnable,
        anueClientLoginFailureTrapEnable,
        anueLoginBanner,
        anueTimestampingTimeSource,
        anueTimestampingStatus,
        anueCustomFieldSetEnableState,
        anueFieldSetId,
        anueFieldSetAvailOuterHdrFlds,
        anueFieldSetIsAdditOuterHdrs,
        anueCustomFieldId,
        anueCustomFieldName,
        anueCustomFieldPktType,
        anueCustomFieldSize,
        anueCustomFieldSpecificAttrList,
        anueCustomFieldConfirmFldsList,
        anueCriticalFailureDateAndTime,
        anueCriticalFailureType }
    STATUS  current
    DESCRIPTION ""
    -- 1.3.6.1.4.1.32620.3.1.1.1.1
    ::= { anueNtoGroups 1 }

anueNtoIfExtGroup OBJECT-GROUP
    OBJECTS {
        anueIfIsLicensed,
        anueIfLicensedMaxSpeed,
        anueIfMode,
        anueIfDesc,
        anueIfOnAfm,
        anueIfAdvCapabilities
        }
    STATUS  current
    DESCRIPTION ""
    -- 1.3.6.1.4.1.32620.3.1.1.1.2
    ::= { anueNtoGroups 2 }

anueNtoFilterGroup OBJECT-GROUP
    OBJECTS {
        anueFilterCollectionPeriod,
        anueFilterType,
        anueFilterNumber,
        anueFilterDefaultName,
        anueFilterName,
        anueFilterDesc,
        anueFilterIfIndex,
        anueFilterIsTwoStage,
        anueFilterMode,
        anueFilterCriteria,
        anueFilterTag,
        anueFilterAfmEnabled,
        anueFilterEnabledFeatures,
        anueFilterCustomFieldSets,
        anueFilterConnFromOid,
        anueFilterConnToOid,
        anueFilterCntModHCInOctets,
        anueFilterCntModHCOutOctets,
        anueFilterCntModHCInPkts,
        anueFilterCntModHCOutPkts,
        anueFilterCntModHCDropPkts,
        anueFilterCntModHCDropTime,
        anueFilterCntModInOctets,
        anueFilterCntModOutOctets,
        anueFilterCntModInPkts,
        anueFilterCntModOutPkts,
        anueFilterCntModDropPkts,
        anueFilterCntModDropTime,
        anueFilterCntRstHCInOctets,
        anueFilterCntRstHCOutOctets,
        anueFilterCntRstHCInPkts,
        anueFilterCntRstHCOutPkts,
        anueFilterCntRstHCDropPkts,
        anueFilterCntRstHCDropTime,
        anueFilterCntRstInOctets,
        anueFilterCntRstOutOctets,
        anueFilterCntRstInPkts,
        anueFilterCntRstOutPkts,
        anueFilterCntRstDropPkts,
        anueFilterCntRstDropTime,
        anueFilterCurHCInOctets,
        anueFilterCurHCOutOctets,
        anueFilterCurHCRateOctets,
        anueFilterCurHCInPkts,
        anueFilterCurHCOutPkts,
        anueFilterCurHCRatePkts,
        anueFilterCurHCDropPkts,
        anueFilterCurHCUtil,
        anueFilterAvgHCInOctets,
        anueFilterAvgHCOutOctets,
        anueFilterAvgHCRateOctets,
        anueFilterAvgHCInPkts,
        anueFilterAvgHCOutPkts,
        anueFilterAvgHCRatePkts,
        anueFilterAvgHCDropPkts,
        anueFilterAvgHCUtil,
        anueFilterPeakHCInOctets,
        anueFilterPeakHCInOctetsTime,
        anueFilterPeakHCOutOctets,
        anueFilterPeakHCOutOctetsTime,
        anueFilterPeakHCRateOctets,
        anueFilterPeakHCRateOctetsTime,
        anueFilterPeakHCInPkts,
        anueFilterPeakHCInPktsTime,
        anueFilterPeakHCOutPkts,
        anueFilterPeakHCOutPktsTime,
        anueFilterPeakHCRatePkts,
        anueFilterPeakHCRatePktsTime,
        anueFilterPeakHCDropPkts,
        anueFilterPeakHCDropPktsTime,
        anueFilterPeakHCUtil,
        anueFilterPeakHCUtilTime,
        anueFilterCurInOctets,
        anueFilterCurOutOctets,
        anueFilterCurRateOctets,
        anueFilterCurInPkts,
        anueFilterCurOutPkts,
        anueFilterCurRatePkts,
        anueFilterCurDropPkts,
        anueFilterCurUtil,
        anueFilterAvgInOctets,
        anueFilterAvgOutOctets,
        anueFilterAvgRateOctets,
        anueFilterAvgInPkts,
        anueFilterAvgOutPkts,
        anueFilterAvgRatePkts,
        anueFilterAvgDropPkts,
        anueFilterAvgUtil,
        anueFilterPeakInOctets,
        anueFilterPeakInOctetsTime,
        anueFilterPeakOutOctets,
        anueFilterPeakOutOctetsTime,
        anueFilterPeakRateOctets,
        anueFilterPeakRateOctetsTime,
        anueFilterPeakInPkts,
        anueFilterPeakInPktsTime,
        anueFilterPeakOutPkts,
        anueFilterPeakOutPktsTime,
        anueFilterPeakRatePkts,
        anueFilterPeakRatePktsTime,
        anueFilterPeakDropPkts,
        anueFilterPeakDropPktsTime,
        anueFilterPeakUtil,
        anueFilterPeakUtilTime,
        anueFilterCreatedTime,
        anueFilterCreatedBy,
        anueFilterCriteriaModTime,
        anueFilterCriteriaModTimeStamp,
        anueFilterCriteriaModBy,
        anueFilterConfigModTime,
        anueFilterConfigModBy,
        anueFilterConfigModFields,
        anueFilterStatsResetTime,
        anueFilterStatsResetBy,
        anueFilterDropResetTime,
        anueFilterDropResetBy,
        anueFilterDefLastChange,
        anueFilterConnLastChange,
        anueFilterCurGscPktsRate,
        anueFilterAvgGscPktsRate,
        anueFilterPeakGscPktsRate,
        anueFilterPeakTimeGscPktsRate,
        anueFilterGTPPktType,
        anueFilterGscCurDenyGtpV0Sess,
        anueFilterGscCurDenyGtpV1Sess,
        anueFilterGscCurDenyGtpV2Sess,
        anueFilterGscCurDenyGtpTotSess,
        anueFilterGscAvgDenyGtpV0Sess,
        anueFilterGscAvgDenyGtpV1Sess,
        anueFilterGscAvgDenyGtpV2Sess,
        anueFilterGscAvgDenyGtpTotSess,
        anueFilterGscPkDenyGtpV0Sess,
        anueFilterGscPkDenyGtpV1Sess,
        anueFilterGscPkDenyGtpV2Sess,
        anueFilterGscPkDenyGtpTotSess,
        anueFilterGscPkDenyGtpV0SessT,
        anueFilterGscPkDenyGtpV1SessT,
        anueFilterGscPkDenyGtpV2SessT,
        anueFilterGscPkDenyGtpTotSessT,
        anueFilterGscTotOversizePktsTx,
        anueFilterGscCurOversizePktsTx,
        anueFilterGscAvgOversizePktsTx,
        anueFilterGscPkOversizePktsTx,
        anueFilterGscPkOversizePktsTxT,
        anueFilterGscTotDroppedPkts,
        anueFilterGscCurDroppedPkts,
        anueFilterGscAvgDroppedPkts,
        anueFilterGscPkDroppedPkts,
        anueFilterGscPkDroppedPktsT,
        anueFilterGscTotDroppedBytes,
        anueFilterGscCurDroppedBytes,
        anueFilterGscAvgDroppedBytes,
        anueFilterGscPkDroppedBytes,
        anueFilterGscPkDroppedBytesT
        }
    STATUS  current
    DESCRIPTION ""
    -- 1.3.6.1.4.1.32620.3.1.1.1.3
    ::= { anueNtoGroups 3 }

anueNtoPayloadGroup OBJECT-GROUP
    OBJECTS {
        anueNtoEventMonDataDateAndTime,
        anueNtoEventMonDataTriggerCause,
        anueNtoEventMonDataTriggerValue,
        anueNtoEventMonDataDirection,
        anueNtoEventMonDataStatName,
        anueNtoEventMonDataEntityName,
        anueNtoEventMonDataNotSent,
        anueNtoEventMonDataTriggerDescr,
        anueNtoEventMonDataThreshold,
        anueNtoEventMonDataInterval,
        anueNtoEventMonDataWindowSize,
        anueNtoEventMonDataWindowCount,
        anueNtoEventTestTime,
        anueNtoEventTestMessage,
        anueMemberActionDataMemberName,
        anueMemberActionDataType
    }
    STATUS  current
    DESCRIPTION "Notification payload objects"
    -- 1.3.6.1.4.1.32620.3.1.1.1.4
    ::= { anueNtoGroups 4 }

anueNtoCaptureGroup OBJECT-GROUP
    OBJECTS {
        anueCaptureNumber,
        anueCaptureDefaultName,
        anueCaptureName,
        anueCaptureDesc,
        anueCaptureStatus,
        anueCaptureBufferSize,
        anueCaptureBufferType,
        anueCaptureTriggerMode,
        anueCaptureTriggerPosition,
        anueCaptureFillBufferToTrigger,
        anueCaptureEnableTrailerStripping,
        anueCaptureTriggerCriteria,
        anueCaptureConnection
    }
    STATUS  current
    DESCRIPTION "Capture resource objects"
    -- 1.3.6.1.4.1.32620.3.1.1.1.5
    ::= { anueNtoGroups 5 }

anueNtoCaptureStatsGroup OBJECT-GROUP
    OBJECTS {
        anueCaptureTransBytesTotal,
        anueCaptureTransBytesCur,
        anueCaptureTransBytesAvg,
        anueCaptureTransBytesPeak,
        anueCaptureTransBytesPeakTime,
        anueCaptureTransBytesTimeSincePeak,
        anueCaptureTransPktsTotal,
        anueCaptureTransPktsCur,
        anueCaptureTransPktsAvg,
        anueCaptureTransPktsPeak,
        anueCaptureTransPktsPeakTime,
        anueCaptureTransPktsTimeSincePeak,
        anueCaptureDropPktsTotal,
        anueCaptureDropPktsCur,
        anueCaptureDropPktsAvg,
        anueCaptureDropPktsPeak,
        anueCaptureDropPktsPeakTime     ,
        anueCaptureDropPktsTimeSincePeak,
        anueCaptureBufferUtilizationPerc,
        anueCaptureTimeSinceReset,
        anueCaptureResetById
    }
    STATUS  current
    DESCRIPTION "Capture resource stats objects"
    -- 1.3.6.1.4.1.32620.3.1.1.1.6
    ::= { anueNtoGroups 6 }


anueNtoEventGroup NOTIFICATION-GROUP
    NOTIFICATIONS {
        anueSnmpAuthenticationFailure,
        anueClientLoginFailure,
        anueNtoEventMonStatInvalidCount,
        anueNtoEventMonStatDropCount,
        anueNtoEventMonStatRxUtilization,
        anueNtoEventMonStatTxUtilization,
        anueNtoEventTest,
        anueNtoEventMonStatLoadDistribution,
        anueNtoEventUnionMemberAction
    }
    STATUS  current
    DESCRIPTION ""
    -- 1.3.6.1.4.1.32620.3.1.1.1.7
    ::= { anueNtoGroups 7 }


anueNtoStageGroup OBJECT-GROUP
    OBJECTS {
        anueStageStripFilterType,
        anueStageStripFilterNumber,
        anueStageStripFeature,
        anueStageStripOrder,
        anueStageStripType,
        anueStageStripModPkts,
        anueStageStripModPktPct,
        anueStageStripErrorPkts,
        anueStageStripRstModPkts,
        anueStageStripRstModPktPct,
        anueStageStripRstErrorPkts,
        anueStageStripAttributes,
        anueStageDedupFilterType,
        anueStageDedupFilterNumber,
        anueStageDedupFeature,
        anueStageDedupOrder,
        anueStageDedupType,
        anueStageDedupTimeWindows,
        anueStageDedupRmvPkts,
        anueStageDedupRmvPktPct,
        anueStageDedupRstRmvPkts,
        anueStageDedupRstRmvPktPct,
        anueStageTrimFilterType,
        anueStageTrimFilterNumber,
        anueStageTrimFeature,
        anueStageTrimOrder,
        anueStageTrimType,
        anueStageTrimRetainOctets,
        anueStageTrimModPkts,
        anueStageTrimModPktPct,
        anueStageTrimRmvOctets,
        anueStageTrimRmvOctetPct,
        anueStageTrimRstModPkts,
        anueStageTrimRstModPktPct,
        anueStageTrimRstRmvOctets,
        anueStageTrimRstRmvOctetPct,
        anueStageBufferFilterType,
        anueStageBufferFilterNumber,
        anueStageBufferFeature,
        anueStageBufferOrder,
        anueStageBufferSize,
        anueStageBufferCurBufferLevel,
        anueStageBufferPeakBufferLevel,
        anueStageBufferPeakBufferTime,
        anueStageBufferDropPkts,
        anueStageBufferDropTime,
        anueStageBufferRstDropPkts,
        anueStageBufferRstDropTime,
        anueStageNPFilterFilterType,
        anueStageNPFilterFilterNumber,
        anueStageNPFilterFeature,
        anueStageNPFilterOrder,
        anueStageNPFilterDenyPkts,
        anueStageNPFilterDenyPktPct,
        anueStageNPFilterDenyOctets,
        anueStageNPFilterDenyOctetPct,
        anueStageNPFilterRstDenyPkts,
        anueStageNPFilterRstDenyPktPct,
        anueStageNPFilterRstDenyOctets,
        anueStageNPFilterRstDenyOctetPct,
        anueStageTPFilterFilterType,
        anueStageTPFilterFilterNumber,
        anueStageTPFilterFeature,
        anueStageTPFilterOrder,
        anueStageTPFilterDenyPkts,
        anueStageTPFilterDenyPktPct,
        anueStageTPFilterDropPkts,
        anueStageTPFilterDropTime,
        anueStageTPFilterRstDenyPkts,
        anueStageTPFilterRstDenyPktPct,
        anueStageTPFilterRstDropPkts,
        anueStageTPFilterRstDropTime,
        anueStageAfmDropFilterType,
        anueStageAfmDropFilterNumber,
        anueStageAfmDropFeature,
        anueStageAfmDropOrder,
        anueStageAfmDropDropPkts,
        anueStageAfmDropDropTime,
        anueStageAfmDropRstDropPkts,
        anueStageAfmDropRstDropTime,
        anueStageTagFilterType,
        anueStageTagFilterNumber,
        anueStageTagFeature,
        anueStageTagOrder,
        anueStageTagModPkts,
        anueStageTagModPktPct,
        anueStageTagRstModPkts,
        anueStageTagRstModPktPct,
        anueStageTagAttributes,
        anueStageNPErrorFilterType,
        anueStageNPErrorFilterNumber,
        anueStageNPErrorFeature,
        anueStageNPErrorOrder,
        anueStageNPErrorPkts,
        anueStageNPErrorRstPkts,
        anueStageDropFilterType,
        anueStageDropFilterNumber,
        anueStageDropFeature,
        anueStageCntDropPkts,
        anueStageCntDropTime,
        anueStageCurDropPkts,
        anueStageAvgDropPkts,
        anueStagePeakDropPkts,
        anueStagePeakDropTime,
        anueNtoStageGscNetworkFilterType,
        anueNtoStageGscNetworkFilterNumber,
        anueGscNWFltrExcSess,
        anueNtoStageGscNetworkFilterFeature,
        anueGscNWFltrAvgGscPktFrag,
        anueGscNWFltrAvgTdoutFrag,
        anueGscNWFltrCurPacketFrag,
        anueGscNWFltrCurTdoutFrag,
        anueGscNWFltrPkPacketFrag,
        anueGscNWFltrPkPacketFragT,
        anueGscNWFltrPkTdOutFrag,
        anueGscNWFltrPkTdOutFragT,
        anueGscNWFltrTotFrag,
        anueGscNWFltrTotRxCountFrag,
        anueGscNWFltrTotTdOutFrag,
        anueGscNWFltrAvgCompFragPkts,
        anueGscNWFltrAvgCompFragPktsPerc,
        anueGscNWFltrAvgIncomFragPkts,
        anueGscNWFltrCurCompFragPkts,
        anueGscNWFltrCurCompFragPktsPerc,
        anueGscNWFltrCurIncomFragPkts,
        anueGscNWFltrPkCompFragPkts,
        anueGscNWFltrPkCompFragPktsT,
        anueGscNWFltrPkCompFragPktsPerc,
        anueGscNWFltrPkCompFragPktsPercT,
        anueGscNWFltrPkIncomFragPkts,
        anueGscNWFltrPkIncomFragPktsT,
        anueGscNWFltrPkTotCompFragPkts,
        anueGscNWFltrAvgActiveUsers,
        anueGscNWFltrCurActiveUsers,
        anueGscNWFltrPkActiveUsers,
        anueGscNWFltrPkActiveUsersT,
        anueGscNWFltrAvgExcSess,
        anueGscNWFltrCurExcSess,
        anueGscNWFltrPkExcSess,
        anueGscNWFltrPkExcSessT,
        anueGscNWFltrTotExcSess,
        anueGscNWFltrTotGtpV0CrSess,
        anueGscNWFltrTotGtpV1CrSess,
        anueGscNWFltrTotGtpV2CrSess,
        anueGscNWFltrTotGtpTotCrSess,
        anueGscNWFltrAvgGtpV0CrSess,
        anueGscNWFltrAvgGtpV1CrSess,
        anueGscNWFltrAvgGtpV2CrSess,
        anueGscNWFltrAvgGtpTotCrSess,
        anueGscNWFltrCurGtpV0CrSess,
        anueGscNWFltrCurGtpV1CrSess,
        anueGscNWFltrCurGtpV2CrSess,
        anueGscNWFltrCurGtpTotCrSess,
        anueGscNWFltrPkGtpV0CrSess,
        anueGscNWFltrPkGtpV1CrSess,
        anueGscNWFltrPkGtpV2CrSess,
        anueGscNWFltrPkGtpTotCrSess,
        anueGscNWFltrPkGtpV0CrSessT,
        anueGscNWFltrPkGtpV1CrSessT,
        anueGscNWFltrPkGtpV2CrSessT,
        anueGscNWFltrPkGtpTotCrSessT,
        anueGscNWFltrTotGtpV0DelSess,
        anueGscNWFltrTotGtpV1DelSess,
        anueGscNWFltrTotGtpV2DelSess,
        anueGscNWFltrTotGtpTotDelSess,
        anueGscNWFltrAvgGtpV0DelSess,
        anueGscNWFltrAvgGtpV1DelSess,
        anueGscNWFltrAvgGtpV2DelSess,
        anueGscNWFltrAvgGtpTotDelSess,
        anueGscNWFltrCurGtpV0DelSess,
        anueGscNWFltrCurGtpV1DelSess,
        anueGscNWFltrCurGtpV2DelSess,
        anueGscNWFltrCurGtpTotDelSess,
        anueGscNWFltrPkGtpV0DelSess,
        anueGscNWFltrPkGtpV1DelSess,
        anueGscNWFltrPkGtpV2DelSess,
        anueGscNWFltrPkGtpTotDelSess,
        anueGscNWFltrPkGtpV0DelSessT,
        anueGscNWFltrPkGtpV1DelSessT,
        anueGscNWFltrPkGtpV2DelSessT,
        anueGscNWFltrPkGtpTotDelSessT,
        anueGscNWFltrAvgGtpV0Bearers,
        anueGscNWFltrAvgGtpV1Bearers,
        anueGscNWFltrAvgGtpV2Bearers,
        anueGscNWFltrAvgGtpTotBearers,
        anueGscNWFltrCurGtpV0Bearers,
        anueGscNWFltrCurGtpV1Bearers,
        anueGscNWFltrCurGtpV2Bearers,
        anueGscNWFltrCurGtpTotBearers,
        anueGscNWFltrPkGtpV0Bearers,
        anueGscNWFltrPkGtpV1Bearers,
        anueGscNWFltrPkGtpV2Bearers,
        anueGscNWFltrPkGtpTotBearers,
        anueGscNWFltrPkGtpV0BearersT,
        anueGscNWFltrPkGtpV1BearersT,
        anueGscNWFltrPkGtpV2BearersT,
        anueGscNWFltrPkGtpTotBearersT,
        anueGscNWFltrAvgGtpV0Pkts,
        anueGscNWFltrAvgGtpV1Pkts,
        anueGscNWFltrAvgGtpV2Pkts,
        anueGscNWFltrAvgGtpTotPkts,
        anueGscNWFltrCurGtpV0Pkts,
        anueGscNWFltrCurGtpV1Pkts,
        anueGscNWFltrCurGtpV2Pkts,
        anueGscNWFltrCurGtpTotPkts,
        anueGscNWFltrTotGtpV1Pkts,
        anueGscNWFltrTotGtpV0Pkts,
        anueGscNWFltrTotGtpV2Pkts,
        anueGscNWFltrTotGtpTotPkts,
        anueGscNWFltrPkGtpV0Pkts,
        anueGscNWFltrPkGtpV1Pkts,
        anueGscNWFltrPkGtpV2Pkts,
        anueGscNWFltrPkGtpTotPkts,
        anueGscNWFltrPkGtpV0PktsT,
        anueGscNWFltrPkGtpV1PktsT,
        anueGscNWFltrPkGtpV2PktsT,
        anueGscNWFltrPkGtpTotPktsT,
        anueGscNWFltrTotGtpV0ToutSess,
        anueGscNWFltrTotGtpV1ToutSess,
        anueGscNWFltrTotGtpV2ToutSess,
        anueGscNWFltrTotGtpTotToutSess,
        anueGscNWFltrAvgGtpV0ToutSess,
        anueGscNWFltrAvgGtpV1ToutSess,
        anueGscNWFltrAvgGtpV2ToutSess,
        anueGscNWFltrAvgGtpTotToutSess,
        anueGscNWFltrCurGtpV0ToutSess,
        anueGscNWFltrCurGtpV1ToutSess,
        anueGscNWFltrCurGtpV2ToutSess,
        anueGscNWFltrCurGtpTotToutSess,
        anueGscNWFltrPkGtpV0ToutSess,
        anueGscNWFltrPkGtpV1ToutSess,
        anueGscNWFltrPkGtpV2ToutSess,
        anueGscNWFltrPkGtpTotToutSess,
        anueGscNWFltrPkGtpV0ToutSessT,
        anueGscNWFltrPkGtpV1ToutSessT,
        anueGscNWFltrPkGtpV2ToutSessT,
        anueGscNWFltrPkGtpTotToutSessT,
        anueGscNWFltrAvgGtpCPkts,
        anueGscNWFltrAvgGtpUPkts,
        anueGscNWFltrAvgDiameterPkts,
        anueGscNWFltrAvgDnsPkts,
        anueGscNWFltrAvgRadiusPkts,
        anueGscNWFltrAvgNonGtpPkts,
        anueGscNWFltrCurGtpCPkts,
        anueGscNWFltrCurGtpUPkts,
        anueGscNWFltrCurDiameterPkts,
        anueGscNWFltrCurDnsPkts,
        anueGscNWFltrCurRadiusPkts,
        anueGscNWFltrCurNonGtpPkts,
        anueGscNWFltrPkGtpCPkts,
        anueGscNWFltrPkGtpUPkts,
        anueGscNWFltrPkDiameterPkts,
        anueGscNWFltrPkDnsPkts,
        anueGscNWFltrPkRadiusPkts,
        anueGscNWFltrPkNonGtpPkts,
        anueGscNWFltrPkGtpCPktsT,
        anueGscNWFltrPkGtpUPktsT,
        anueGscNWFltrPkDiameterPktsT,
        anueGscNWFltrPkDnsPktsT,
        anueGscNWFltrPkRadiusPktsT,
        anueGscNWFltrPkNonGtpPktsT,
        anueGscNWFltrTotGtpCPkts,
        anueGscNWFltrTotGtpUPkts,
        anueGscNWFltrTotDiameterPkts,
        anueGscNWFltrTotDnsPkts,
        anueGscNWFltrTotRadiusPkts,
        anueGscNWFltrTotNonGtpPkts,
        anueGscNWFltrTotGscDropPkts,
        anueGscNWFltrCurGscSessLoad,
        anueGscNWFltrAvgGscSessLoad,
        anueGscNWFltrPeakGscSessLoad,
        anueGscNWFltrPeakGscSessLoadT,
        anueGscNWFltrCurNetwElemLoad,
        anueGscNWFltrPeakNetwElemLoad,
        anueGscNWFltrPeakNetwElemLoadT,
        anueGscNWFltrCurReqRespLoad,
        anueGscNWFltrPeakReqRespLoad,
        anueGscNWFltrPeakReqRespLoadT,
        anueGscNWFltrCurFragLoad,
        anueGscNWFltrPeakFragLoad,
        anueGscNWFltrPeakFragLoadT,
        anueGscNWFltrAvgGscUnassignedSess,
        anueGscNWFltrCurGscUnassignedSess,
        anueGscNWFltrPkGscUnassignedSess,
        anueGscNWFltrPkGscUnassignedSessT,
        anueGscNWFltrTotGscUnassignedSess,
        anueGscNWFltrAvgUnprocReq,
        anueGscNWFltrCurUnprocReq,
        anueGscNWFltrPkUnprocReq,
        anueGscNWFltrPkUnprocReqT,
        anueGscNWFltrTotUnprocReq,
        anueGscNWFltrAvgTdOutReq,
        anueGscNWFltrCurTdOutReq,
        anueGscNWFltrPkTdOutReq,
        anueGscNWFltrPkTdOutReqT,
        anueGscNWFltrTotTdOutReq,
        anueGscNWFltrAvgUnmatchedResp,
        anueGscNWFltrCurUnmatchedResp,
        anueGscNWFltrPkUnmatchedResp,
        anueGscNWFltrPkUnmatchedRespT,
        anueGscNWFltrTotUnmatchedResp,
        anueGscNWFltrOverloadErrCode,
        anueGscNWFltrOverloadT,
        anueNtoStageGscToolFilterType,
        anueNtoStageGscToolFilterNumber,
        anueNtoStageGscToolFilterFeature,
        anueGscTFltrCurGtpV0ActSess,
        anueGscTFltrCurGtpV1ActSess,
        anueGscTFltrCurGtpV2ActSess,
        anueGscTFltrCurGtpTotActSess,
        anueGscTFltrAvgGtpV0ActSess,
        anueGscTFltrAvgGtpV1ActSess,
        anueGscTFltrAvgGtpV2ActSess,
        anueGscTFltrAvgGtpTotActSess,
        anueGscTFltrPeakGtpV0ActSess,
        anueGscTFltrPeakGtpV1ActSess,
        anueGscTFltrPeakGtpV2ActSess,
        anueGscTFltrPeakGtpTotActSess,
        anueGscTFltrPeakGtpV0ActSessT,
        anueGscTFltrPeakGtpV1ActSessT,
        anueGscTFltrPeakGtpV2ActSessT,
        anueGscTFltrPeakGtpTotActSessT,
        anueGscTFltrAvgGtpCPkts,
        anueGscTFltrAvgGtpUPkts,
        anueGscTFltrAvgDiameterPkts,
        anueGscTFltrAvgDnsPkts,
        anueGscTFltrAvgRadiusPkts,
        anueGscTFltrPeakGtpCPkts,
        anueGscTFltrPeakGtpUPkts,
        anueGscTFltrPeakDiameterPkts,
        anueGscTFltrPeakDnsPkts,
        anueGscTFltrPeakRadiusPkts,
        anueGscTFltrPeakGtpCPktsT,
        anueGscTFltrPeakGtpUPktsT,
        anueGscTFltrPeakDiameterPktsT,
        anueGscTFltrPeakDnsPktsT,
        anueGscTFltrPeakRadiusPktsT,
        anueGscTFltrTotGtpCPkts,
        anueGscTFltrTotGtpUPkts,
        anueGscTFltrTotDiameterPkts,
        anueGscTFltrTotDnsPkts,
        anueGscTFltrTotRadiusPkts,
        anueGscTFltrCurGtpCPkts,
        anueGscTFltrCurGtpUPkts,
        anueGscTFltrCurDiameterPkts,
        anueGscTFltrCurDnsPkts,
        anueGscTFltrCurRadiusPkts,
        anueStageGtpFdFilterType,
        anueStageGtpFdFilterNumber,
        anueStageGtpFdFeature,
        anueStageRateGtpCPps,
        anueStageRateGtpUPps,
        anueStageRateGtpCBps,
        anueStageRateGtpUBps,
        anueStageDataMaskingFilterType,
        anueStageDataMaskingFilterNumber,
        anueStageDataMaskingFeature,
        anueStageDataMaskingOrder,
        anueStageDataMaskingOffsetLayer,
        anueStageDataMaskingOffset,
        anueStageDataMaskingLength,
        anueStageDataMaskingFillValue,
        anueStageDataMaskingModPkts,
        anueStageDataMaskingModPktPct,
        anueStageDataMaskingRstModPkts,
        anueStageDataMaskingRstModPktPct
        }
    STATUS  current
    DESCRIPTION ""
    -- 1.3.6.1.4.1.32620.3.1.1.1.8
    ::= { anueNtoGroups 8 }

anueNtoResourceGroup OBJECT-GROUP
    OBJECTS {
        anueResourceFilterType,
        anueResourceNumber,
        anueResourceDefaultName,
        anueResourceName,
        anueResourceDesc,
        anueResourceStatus
    }
    STATUS  current
    DESCRIPTION "Resource objects"
    -- 1.3.6.1.4.1.32620.3.1.1.1.9
    ::= { anueNtoGroups 9 }

anueGscGroups OBJECT IDENTIFIER
    -- 1.3.6.1.4.1.32620.3.1.1.2
    ::= { anueGroups 2 }

anueGscEventGroup NOTIFICATION-GROUP
    NOTIFICATIONS {
        anueGscEventMonStatOverflowPkts,
        anueGscEventMonStatControlPlanePktRate,
        anueGscEventMonStatExcessSessions,
        anueGscEventMonStatIngressPktDrops,
        anueGscEventMonStatSessionsTableLoad,
        anueGscEventMonStatNetworkElemLoad,
        anueGscEventMonStatReqRespLoad,
        anueGscEventMonStatFragmentationLoad,
        anueGscCriticalFailure,
        anueGscProbeFailure
        }
    STATUS  current
    DESCRIPTION ""
    -- 1.3.6.1.4.1.32620.3.1.1.2.1
    ::= { anueGscGroups 1 }


anueGscDataGroup OBJECT-GROUP
    OBJECTS {
        anueGscProbeId,
        anueGscProbePgIfIndex,
        anueGscProbeName,
        anueGscProbeIp,
        anueGscProbeIsActive,
        anueGscProbeIsRedundant,
        anueGscProbeLastRxHeartbeatTime,
        anueGscProbeLastRxFailMsgTime,
        anueGscProbeFailoverId,
        anueGscPortIfIndex,
        anueGscPortProbeId }
    STATUS  current
    DESCRIPTION
        ""
    -- 1.3.6.1.4.1.32620.3.1.1.2.2
    ::= { anueGscGroups 2 }

anueGscPayloadGroup OBJECT-GROUP
    OBJECTS {
        anueGscEvFailedPbDateAndTime,
        anueGscEvFailedPbId,
        anueGscEvFailedPbName,
        anueGscEvFailedPbIP,
        anueGscEvFailedPbPortList,
        anueGscEvFailedPbLastRxHeartbeat,
        anueGscEvFailedPbLastRxFailMsg,
        anueGscEvFailoverPbId,
        anueGscEvFailoverPbName,
        anueGscEvFailoverPbIP,
        anueGscEvFailoverPbPortList }
    STATUS  current
    DESCRIPTION
        ""
    -- 1.3.6.1.4.1.32620.3.1.1.2.3
    ::= { anueGscGroups 3 }

anueCompliances OBJECT IDENTIFIER
    -- 1.3.6.1.4.1.32620.3.1.2
    ::= { anueNtoConformance 2 }


anueMIBCompliances MODULE-COMPLIANCE
    STATUS  current
    DESCRIPTION ""
    MODULE
    MANDATORY-GROUPS {
        anueNtoSystemGroup,
        anueNtoEventGroup,
        anueNtoFilterGroup,
        anueNtoIfExtGroup,
        anueNtoStageGroup,
        anueNtoCaptureGroup,
        anueNtoCaptureStatsGroup,
        anueNtoResourceGroup,
        anueGscEventGroup }

    -- 1.3.6.1.4.1.32620.3.1.2.2
    ::= { anueCompliances 2 }

END
