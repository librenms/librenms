-- *------------------------------------------------------------------
-- * ALTIGA-GENERAL-STATS-MIB.my:  Altiga General Statistics MIB.
-- *
-- * Altiga Networks was acquired by Cisco Systems on March 29, 2000
-- *
-- * Copyright (c) 2002 by Cisco Systems, Inc.
-- * All rights reserved.
-- *
-- *------------------------------------------------------------------

ALTIGA-GENERAL-STATS-MIB DEFINITIONS ::= BEGIN

   IMPORTS
      MODULE-IDENTITY, OBJECT-TYPE, NOTIFICATION-TYPE,
      Gauge32, Counter32, Integer32
         FROM SNMPv2-SMI
      MODULE-COMPLIANCE, OBJECT-GROUP, NOTIFICATION-GROUP
         FROM SNMPv2-CONF
      alStatsGeneral, alGeneralGroup
         FROM ALTIGA-MIB
      alGeneralMibModule
         FROM ALTIGA-GLOBAL-REG;

   altigaGeneralStatsMibModule MODULE-IDENTITY
      LAST-UPDATED   "200209111300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga General Statistics MIB models counters and 
          objects that are of management interest.
         
          Acronyms
          The following acronyms are used in this document:

            AVP:        Attribute/Value Pair

            CLID:       Calling Line ID

            DNIS:       Dialed Number Identification Service

            L2TP:       Layer 2 Tunnel Protocol

            LAC:        L2TP Access Concentrator

            LNS:        L2TP Network Server

            RWS:        Receive Window Size
         
         "

        REVISION "200209111300Z"
        DESCRIPTION
                "Added module compliance and fix comments."

        REVISION "200207100000Z"
        DESCRIPTION
                "Updated with new header"

      ::= { alGeneralMibModule 2 }

-- +++++++++++++++++++++++++++++++++++++++++++++++++++++++
-- MIB Objects
-- +++++++++++++++++++++++++++++++++++++++++++++++++++++++

alStatsGeneralGlobal  OBJECT IDENTIFIER ::= { alStatsGeneral 1 }

alGeneralTime		OBJECT-TYPE
	SYNTAX		Counter32
	MAX-ACCESS	read-only
	STATUS		current
	DESCRIPTION
      "The current time on the box, represented as a time_t.

       In 1.2, this was the box's local time.
       
       After 1.2, it was corrected to represent UTC (which is what it
       is supposed to be). So all boxes should have this be the same 
       value +/- a few seconds."
	::= { alStatsGeneralGlobal 1 }

alGeneralGaugeCpuUtil	OBJECT-TYPE
	SYNTAX		Gauge32 (0..100)
	MAX-ACCESS	read-only
	STATUS		current
	DESCRIPTION
      "The value of the CPU Utilization gauge which indicates 
       percentage of CPU utilized."
	::= { alStatsGeneralGlobal 2 }

alGeneralGaugeActiveSessions	OBJECT-TYPE
	SYNTAX			Gauge32 (0..100)
	MAX-ACCESS		read-only
	STATUS			current
	DESCRIPTION
      "The value of the Active Sessions gauge which indicates the
       percentage of total permitted session that are active."
	::= { alStatsGeneralGlobal 3 }

alGeneralGaugeThroughput	OBJECT-TYPE
	SYNTAX			Gauge32 (0..100)
	MAX-ACCESS		read-only
	STATUS			current
	DESCRIPTION
      "The value of the Throughput gauge which indicates the
       percentage of total available throughput in-use."
	::= { alStatsGeneralGlobal 4 }

alGeneralTimeZone	OBJECT-TYPE
	SYNTAX		Integer32
	MAX-ACCESS	read-only
	STATUS		current
	DESCRIPTION
      "The time zone configured on the box. Measured in minutes from
       UTC. e.g. EST = -300."
	::= { alStatsGeneralGlobal 5 }

altigaGeneralStatsMibConformance OBJECT IDENTIFIER 
   ::= { altigaGeneralStatsMibModule 1 }

altigaGeneralStatsMibCompliances OBJECT IDENTIFIER
    ::= { altigaGeneralStatsMibConformance 1 }

altigaGeneralStatsMibCompliance MODULE-COMPLIANCE
   STATUS         current
   DESCRIPTION
      "The compliance statement for agents which implement the
       Altiga General Statistics MIB."
   MODULE
   MANDATORY-GROUPS { 
      altigaGeneralStatsGroup
   }
   ::= { altigaGeneralStatsMibCompliances 1 }

altigaGeneralStatsGroup OBJECT-GROUP
	OBJECTS
	{
		alGeneralTime,
		alGeneralGaugeCpuUtil,
		alGeneralGaugeActiveSessions,
		alGeneralGaugeThroughput,
		alGeneralTimeZone
	}
	STATUS 	current
	DESCRIPTION
      "The objects for general information."
	::= { alGeneralGroup 2 }

END
