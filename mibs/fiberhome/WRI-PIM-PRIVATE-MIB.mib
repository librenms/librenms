--
-- wriPim.mib
-- MIB generated by MG-SOFT Visual MIB Builder Version 4.0 Build 349
-- Thursday, January 06, 2011 at 09:56:54
--

	WRI-PIM-PRIVATE-MIB DEFINITIONS ::= BEGIN
 
		IMPORTS
			mib-2			
				FROM RFC1213-MIB			
			TimeTicks, IpAddress, Integer32, Gauge32, Counter32,Unsigned32, 
			OBJECT-TYPE, MODULE-IDENTITY, NOTIFICATION-TYPE			
				FROM SNMPv2-SMI			
			DisplayString, RowStatus, TruthValue			
				FROM SNMPv2-TC			
			wriProtocol			
				FROM WRI-SMI;
	
	
		-- 1.3.6.1.4.1.3807.2.1619
		pimMIB MODULE-IDENTITY 
			LAST-UPDATED "200208211830Z"		-- August 21, 2002 at 18:30 GMT
			ORGANIZATION 
				"Fiberhomenetworks software group"
			CONTACT-INFO 
				"postal :-
				Fiberhomenetworks Ltd.,
				88,youkeyuan road,wuhan
				china
				Phone 
				EMail: "
			DESCRIPTION 
				"The MIB module for management of PIM Routers
				Initial Version"
			::= { wriProtocol 1619 }

		
	
	
--
-- Node definitions
--	
		-- 1.3.6.1.4.1.3807.2.1619.1
		wriPimScalars OBJECT IDENTIFIER ::= { pimMIB 1 }

		
		-- 1.3.6.1.4.1.3807.2.1619.1.1
		wriPimVersionString OBJECT-TYPE
			SYNTAX DisplayString
			MAX-ACCESS read-only
			STATUS current
			DESCRIPTION
				"The version number of the PIM protocol in the router"
			::= { wriPimScalars 1 }	
	
		-- 1.3.6.1.4.1.3807.2.1619.1.2
		wriPimEnable OBJECT-TYPE
			SYNTAX INTEGER
				{
				enable(1),
				disable(2)
				}
			MAX-ACCESS read-write
			STATUS current
			DESCRIPTION
				"wriPimEnable."
			::= { wriPimScalars 2 }
       
       -- 1.3.6.1.4.1.3807.2.1619.1.3
      wriPimCurrentTime OBJECT-TYPE
			SYNTAX INTEGER
			MAX-ACCESS read-only
			STATUS current
			DESCRIPTION
				"wriPimEnable."
			::= { wriPimScalars 3 }  
			
		-- 1.3.6.1.4.1.3807.2.1619.2
		wriPimTables OBJECT IDENTIFIER ::= { pimMIB 2 }

				
        -- 1.3.6.1.4.1.3807.2.1619.2.1
		wriPimInstanceTable OBJECT-TYPE
			SYNTAX SEQUENCE OF WriPimInstanceEntry
			MAX-ACCESS not-accessible
			STATUS current
			DESCRIPTION
				"The (conceptual) table listing the router's PIM instance				
				table."
			::= { wriPimTables 1 }

		
		-- 1.3.6.1.4.1.3807.2.1619.2.1
		wriPimInstanceEntry OBJECT-TYPE
			SYNTAX WriPimInstanceEntry       
			MAX-ACCESS not-accessible
			STATUS current
			DESCRIPTION
				"An entry (conceptual row) in the pimInstanceTable."
			INDEX { wriPimInstance }
			::= { wriPimInstanceTable 1 }

		
		WriPimInstanceEntry ::=
			SEQUENCE {  
				wriPimInstance
					INTEGER,
				wriPimInstanceJoinPruneInterval
					Integer32,
				wriPimInstanceSPTGroupThreshold
					INTEGER,
				wriPimInstanceEnableFastfowardMcastPkt
					INTEGER,
				wriPimInstanceEnableNeighborLossTrap
					INTEGER,
				wriPimInstanceIpMRouteEntryCount
					Gauge32,    
				wriPimInstanceIpMemeryAllocatedCount
					Gauge32,				
				wriPimInstanceRegisterFragment
					INTEGER,
				wriPimInstanceRegisterMtu
					INTEGER,
				wriPimInstanceAcceptUnkownRp
					INTEGER,
				wriPimInstanceExternsionChecksum
					INTEGER,
				wriPimInstanceRegisterThreshold												
			        INTEGER,
			    wriPimInstanceScopeStatus												
			        INTEGER, 
			    wriPimInstanceIfCount												
			        Gauge32, 
                wriPimInstanceCrpGrpCount												
			        Gauge32, 
			    wriPimInstanceIsCrp												
			        INTEGER,    
			 	wriPimInstanceStatus	 		
					RowStatus,
				wriPimInstanceMrouteFlush
					INTEGER,
				wriPimInstanceStateFlashInterval
					INTEGER,		
				wriPimInstanceStateFlashRateLimit
					INTEGER,			                         				
				wriPimInstanceStateFlashTtl
					INTEGER
            }

  		-- 1.3.6.1.4.1.3807.2.1619.2.1.1
		wriPimInstance   OBJECT-TYPE
			SYNTAX INTEGER
			MAX-ACCESS read-only
			STATUS current
			DESCRIPTION
				"The vpn instance id ."
			::= { wriPimInstanceEntry 1 }

						
		-- 1.3.6.1.4.1.3807.2.1619.2.1.2
		wriPimInstanceJoinPruneInterval OBJECT-TYPE
			SYNTAX Integer32 (1..65535)
			UNITS "seconds"
			MAX-ACCESS read-write
			STATUS current
			DESCRIPTION
				"The default interval at which periodic PIM-SM Join/Prune
				messages are to be sent."
			DEFVAL { 60 }
			::= { wriPimInstanceEntry 2 }

		
		-- 1.3.6.1.4.1.3807.2.1619.2.1.3
		wriPimInstanceSPTGroupThreshold OBJECT-TYPE
			SYNTAX INTEGER (1..2147483647)
			MAX-ACCESS read-write
			STATUS current
			DESCRIPTION
				"The threshold of data rate for any group when exceeded,
				source specific counters are initiated for that particular group
				It is based on number of bits per sec.
				To initiate SPT switching counter, this threshold MUST be
				configured"
			::= { wriPimInstanceEntry 3 }

		
		-- 1.3.6.1.4.1.3807.2.1619.2.1.4
		wriPimInstanceEnableFastfowardMcastPkt OBJECT-TYPE
			SYNTAX INTEGER
				{
				enable(1),
				disable(2)
				}
			MAX-ACCESS read-write
			STATUS current
			DESCRIPTION
				"The threshold of data rate for any group when exceeded,
				source specific counters are initiated for that particular group
				It is based on number of bits per sec.
				To initiate SPT switching counter, this threshold MUST be
				configured"
			::= { wriPimInstanceEntry 4 }

		
		-- 1.3.6.1.4.1.3807.2.1619.2.1.5
		wriPimInstanceEnableNeighborLossTrap OBJECT-TYPE
			SYNTAX INTEGER
				{
				enable(1),
				disable(2)
				}
			MAX-ACCESS read-write
			STATUS current
			DESCRIPTION
				"The threshold of data rate for any group when exceeded,
				source specific counters are initiated for that particular group
				It is based on number of bits per sec.
				To initiate SPT switching counter, this threshold MUST be
				configured"
			::= { wriPimInstanceEntry 5 }

		
		-- 1.3.6.1.4.1.3807.2.1619.2.1.6
		wriPimInstanceIpMRouteEntryCount OBJECT-TYPE
			SYNTAX Gauge32
			MAX-ACCESS read-only
			STATUS current
			DESCRIPTION
				"The number of rows in the pimIpMRouteTable. This can be used
				to monitor the multicast routing table size."
			::= { wriPimInstanceEntry 6 }

		
		-- 1.3.6.1.4.1.3807.2.1619.2.1.7
		wriPimInstanceIpMemeryAllocatedCount OBJECT-TYPE
			SYNTAX Gauge32
			MAX-ACCESS read-only
			STATUS current
			DESCRIPTION
				"This attributes holds the memory allocated for the PIM in Bytes."
			::= { wriPimInstanceEntry 7 }

		
				
		-- 1.3.6.1.4.1.3807.2.1619.2.1.8
		wriPimInstanceRegisterFragment OBJECT-TYPE
			SYNTAX INTEGER
				{
				no(0),
				fragment(1)
				}
			MAX-ACCESS read-write
			STATUS current
			DESCRIPTION
				"Description."
			::= { wriPimInstanceEntry 8 }

		
		-- 1.3.6.1.4.1.3807.2.1619.2.1.9
		wriPimInstanceRegisterMtu OBJECT-TYPE
			SYNTAX INTEGER (750..1600)
			MAX-ACCESS read-write
			STATUS current
			DESCRIPTION
				"Description."
			::= { wriPimInstanceEntry 9 }

		
		-- 1.3.6.1.4.1.3807.2.1619.2.1.10
		wriPimInstanceAcceptUnkownRp OBJECT-TYPE
			SYNTAX INTEGER
				{
				no(0),
				unkownRp(1)
				}
			MAX-ACCESS read-write
			STATUS current
			DESCRIPTION
				"Description."
			::= { wriPimInstanceEntry 10 }

		
		-- 1.3.6.1.4.1.3807.2.1619.2.1.11
		wriPimInstanceExternsionChecksum OBJECT-TYPE
			SYNTAX INTEGER
				{
				no(0),
				checksum(1)
				}
			MAX-ACCESS read-write
			STATUS current
			DESCRIPTION
				"Description."
			::= { wriPimInstanceEntry 11 }

		
		-- 1.3.6.1.4.1.3807.2.1619.2.1.12
		wriPimInstanceRegisterThreshold OBJECT-TYPE
			SYNTAX INTEGER (1..2147483647)
			MAX-ACCESS read-write
			STATUS current
			DESCRIPTION
				"Description."
			::= { wriPimInstanceEntry 12 }

		
		-- 1.3.6.1.4.1.3807.2.1619.2.1.13
		wriPimInstanceScopeStatus OBJECT-TYPE
			SYNTAX INTEGER
			MAX-ACCESS read-write
			STATUS current
			DESCRIPTION
				"Description."
			::= { wriPimInstanceEntry 13 }
       
       -- 1.3.6.1.4.1.3807.2.1619.2.1.14
       wriPimInstanceIfCount OBJECT-TYPE
			SYNTAX Gauge32
			MAX-ACCESS read-only
			STATUS current
			DESCRIPTION
				"Description."
			::= { wriPimInstanceEntry 14 }
			
	   -- 1.3.6.1.4.1.3807.2.1619.2.1.15
       wriPimInstanceCrpGrpCount OBJECT-TYPE
			SYNTAX Gauge32
			MAX-ACCESS read-only
			STATUS current
			DESCRIPTION
				"Description."
			::= { wriPimInstanceEntry 15 }
					
     
      -- 1.3.6.1.4.1.3807.2.1619.2.1.16
      wriPimInstanceIsCrp OBJECT-TYPE
			SYNTAX INTEGER
			MAX-ACCESS read-only
			STATUS current
			DESCRIPTION
				"Description."
			::= { wriPimInstanceEntry 16 }
  	
  	  -- 1.3.6.1.4.1.3807.2.1619.2.1.17
      wriPimInstanceStatus OBJECT-TYPE
			SYNTAX RowStatus
			MAX-ACCESS read-write
			STATUS current
			DESCRIPTION
				"Description."
			::= { wriPimInstanceEntry 17 }

      wriPimInstanceMrouteFlush  OBJECT-TYPE
			SYNTAX INTEGER
			MAX-ACCESS read-write
			STATUS current
			DESCRIPTION
				"Description."
			::= { wriPimInstanceEntry 18 }

     wriPimInstanceStateFlashInterval  OBJECT-TYPE
			SYNTAX INTEGER(1..65535)
			MAX-ACCESS read-write
			STATUS current
			DESCRIPTION
				"Description."
			::= { wriPimInstanceEntry 19 }
				
				
	   wriPimInstanceStateFlashRateLimit  OBJECT-TYPE
			SYNTAX INTEGER(1..65535)
			MAX-ACCESS read-write
			STATUS current
			DESCRIPTION
				"Description."
			::= { wriPimInstanceEntry 20 }
			
							                         				
	   wriPimInstanceStateFlashTtl OBJECT-TYPE
			SYNTAX INTEGER(1..255)
			MAX-ACCESS read-write
			STATUS current
			DESCRIPTION
				"Description."
			::= { wriPimInstanceEntry 21 }

    

		-- 1.3.6.1.4.1.3807.2.1619.2.2
		wriPimInterfaceTable OBJECT-TYPE
			SYNTAX SEQUENCE OF WriPimInterfaceEntry
			MAX-ACCESS not-accessible
			STATUS current
			DESCRIPTION
				"The (conceptual) table listing the router's PIM interfaces.
				IGMP and PIM are enabled on all interfaces listed in this
				table."
			::= { wriPimTables 2 }

		
		-- 1.3.6.1.4.1.3807.2.1619.2.2.1
		wriPimInterfaceEntry OBJECT-TYPE
			SYNTAX WriPimInterfaceEntry       
			MAX-ACCESS not-accessible
			STATUS current
			DESCRIPTION
				"An entry (conceptual row) in the pimInterfaceTable."
			INDEX { wriPimInterfaceIfIndex }
			::= { wriPimInterfaceTable 1 }

		
		WriPimInterfaceEntry ::=
			SEQUENCE { 
				wriPimInterfaceIfIndex
					Integer32,
				wriPimInterfaceName
					OCTET STRING,
				wriPimInterfaceLocalOverrideTime
					INTEGER,
				wriPimInterfaceLanPruneDelayTime
					INTEGER,
				wriPimInterfaceAddress
					IpAddress,
				wriPimInterfaceNetMask
					INTEGER,
				wriPimInterfaceSMMode
					INTEGER,    
				wriPimInterfaceDMMode
					INTEGER,	
				wriPimInterfaceGenerationId
					Integer32,
				wriPimInterfaceDR
					IpAddress,
				wriPimInterfaceDRPriority
					Integer32,
				wriPimInterfaceHelloInterval
					Integer32,
				wriPimInterfaceStatus
					RowStatus,
				wriPimInterfaceJoinPruneInterval
					Integer32,
				wriPimInterfaceCBSRPreference
					Integer32,
				wriPimInterfaceLocalDRPriority
					Integer32,
				wriPimInterfaceDRFlag
					INTEGER,
				wriPimInterfaceTimerFlags
					INTEGER,
				wriPimInterfaceNeighborCnt
					INTEGER,
				wriPimInterfaceLocalPruneDelay
					INTEGER,
				wriPimInterfaceOverrideInterval
					INTEGER,
				wriPimInterfaceDomainBorder
					TruthValue,	
				wriPimInterfaceHelloTimer
					INTEGER,
				wriPimInterfaceIgmpTimer
					INTEGER,	
				wriPimInterfaceJoinPruneTimer
					INTEGER,
				wriPimInterfaceNbrListCount
				    Gauge32,
				wriPimInterfaceMNbrListCount
				    Gauge32,
				wriPimInterfaceLinkState
				    INTEGER,
				wriPimInterfaceInBadPacket
				    Counter32,
				wriPimInterfaceInPacket
				    Counter32, 
				wriPimInterfaceOutPacket
				    Counter32, 
				wriPimInterfaceJoinPruneInPacket
				    Counter32,  
				wriPimInterfaceJoinPruneOutPacket
				    Counter32,
				wriPimInterfaceLanDelayEnabled
					TruthValue,
				wriPimInterfacePruneDelay
					INTEGER,  
				wriPimInterfaceStateFlashCapable
					INTEGER,
				wriPimInterfaceGraftRetryInterval
					INTEGER,
				--xf add 2015-5-20
				wriPimInterfaceBfdState
					INTEGER		
			}			
		-- 1.3.6.1.4.1.3807.2.1619.2.2.1.1
		wriPimInterfaceIfIndex OBJECT-TYPE
			SYNTAX Integer32 (1..65535)
			MAX-ACCESS read-only
			STATUS current
			DESCRIPTION
				"The ifIndex value of this PIM interface."
			::= { wriPimInterfaceEntry 1 }

		
		-- 1.3.6.1.4.1.3807.2.1619.2.2.1.2
		wriPimInterfaceName OBJECT-TYPE
			SYNTAX OCTET STRING
			MAX-ACCESS read-only
			STATUS current
			DESCRIPTION
				"The interface name."
			::= { wriPimInterfaceEntry 2 }

		
		-- 1.3.6.1.4.1.3807.2.1619.2.2.1.3
		wriPimInterfaceLocalOverrideTime OBJECT-TYPE
			SYNTAX INTEGER 
			MAX-ACCESS read-only
			STATUS current
			DESCRIPTION
				"."
			::= { wriPimInterfaceEntry 3 }

		
		-- 1.3.6.1.4.1.3807.2.1619.2.2.1.4
		wriPimInterfaceLanPruneDelayTime OBJECT-TYPE
			SYNTAX INTEGER 
			MAX-ACCESS read-write
			STATUS current
			DESCRIPTION
				""
			::= { wriPimInterfaceEntry 4 }

		
	  -- 1.3.6.1.4.1.3807.2.1619.2.2.1.5
		wriPimInterfaceAddress OBJECT-TYPE
			SYNTAX IpAddress
			MAX-ACCESS read-only
			STATUS current
			DESCRIPTION
				"The IP address of the PIM interface."
			::= { wriPimInterfaceEntry 5 }

		
		-- 1.3.6.1.4.1.3807.2.1619.2.2.1.6
		wriPimInterfaceNetMask OBJECT-TYPE
			SYNTAX INTEGER
			MAX-ACCESS read-only
			STATUS current
			DESCRIPTION
				"The network mask for the IP address of the PIM interface."
			::= { wriPimInterfaceEntry 6 }

		
		-- 1.3.6.1.4.1.3807.2.1619.2.2.1.7
		wriPimInterfaceSMMode OBJECT-TYPE
			SYNTAX INTEGER
				{
				enable(1),	
				disable(2)				
				}
			MAX-ACCESS read-write
			STATUS current
			DESCRIPTION
				"The configured mode sparse of this PIM interface."
			::= { wriPimInterfaceEntry 7 }

		-- 1.3.6.1.4.1.3807.2.1619.2.2.1.8	
		wriPimInterfaceDMMode   OBJECT-TYPE
			SYNTAX INTEGER
				{
				enable(1),	
				disable(2)				
				}
			MAX-ACCESS read-write
			STATUS current
			DESCRIPTION
				"The configured mode Dense of this PIM interface."
			::= { wriPimInterfaceEntry 8 }
			
		-- 1.3.6.1.4.1.3807.2.1619.2.2.1.9
		wriPimInterfaceGenerationId OBJECT-TYPE
			SYNTAX Integer32
			MAX-ACCESS read-only
			STATUS current
			DESCRIPTION
				"The Generation identifier of this interface. This is used to inform
				neighbour routers to quickly detect the change of itself"
			::= { wriPimInterfaceEntry 9 }

		
		-- 1.3.6.1.4.1.3807.2.1619.2.2.1.10
		wriPimInterfaceDR OBJECT-TYPE
			SYNTAX IpAddress
			MAX-ACCESS read-only
			STATUS current
			DESCRIPTION
				"The Designated Router on this PIM interface.  For point-to-
				point interfaces, this object has the value 0.0.0.0."
			::= { wriPimInterfaceEntry 10 }

		
		-- 1.3.6.1.4.1.3807.2.1619.2.2.1.11
		wriPimInterfaceDRPriority OBJECT-TYPE
			SYNTAX Integer32
			MAX-ACCESS read-only
			STATUS current
			DESCRIPTION
				"The priority of the DR on this interface. "
			::= { wriPimInterfaceEntry 11 }

		
		-- 1.3.6.1.4.1.3807.2.1619.2.2.1.12
		wriPimInterfaceHelloInterval OBJECT-TYPE
			SYNTAX Integer32
			UNITS "seconds"
			MAX-ACCESS read-create
			STATUS current
			DESCRIPTION
				"The frequency at which PIM Hello messages are transmitted
				on this interface."
			DEFVAL { 30 }
			::= { wriPimInterfaceEntry 12 }

		
		-- 1.3.6.1.4.1.3807.2.1619.2.2.1.13
		wriPimInterfaceStatus OBJECT-TYPE
			SYNTAX RowStatus
			MAX-ACCESS read-create
			STATUS current
			DESCRIPTION
				"The status of this entry.	Creating the entry enables PIM
				on the interface; destroying the entry disables PIM on the
				interface."
			::= { wriPimInterfaceEntry 13 }

		
		-- 1.3.6.1.4.1.3807.2.1619.2.2.1.14
		wriPimInterfaceJoinPruneInterval OBJECT-TYPE
			SYNTAX Integer32
			UNITS "seconds"
			MAX-ACCESS read-create
			STATUS current
			DESCRIPTION
				"The frequency at which PIM Join/Prune messages are
				transmitted on this PIM interface.	The default value of
				this object is the pimJoinPruneInterval."
			DEFVAL { 60 }
			::= { wriPimInterfaceEntry 14 }

		
		-- 1.3.6.1.4.1.3807.2.1619.2.2.1.15
		wriPimInterfaceCBSRPreference OBJECT-TYPE
			SYNTAX Integer32 (-1..255)
			MAX-ACCESS read-create
			STATUS current
			DESCRIPTION
				"The preference value for the local interface as a candidate
				bootstrap router.  The value of -1 is used to indicate that
				the local interface is not a candidate BSR interface."
			DEFVAL { -1 }
			::= { wriPimInterfaceEntry 15 }

		
		-- 1.3.6.1.4.1.3807.2.1619.2.2.1.16
		wriPimInterfaceLocalDRPriority OBJECT-TYPE
			SYNTAX Integer32
			MAX-ACCESS read-create
			STATUS current
			DESCRIPTION
				"The DR priority of this interface. "
			::= { wriPimInterfaceEntry 16 }

		
		-- 1.3.6.1.4.1.3807.2.1619.2.2.1.17
		wriPimInterfaceDRFlag OBJECT-TYPE
			SYNTAX INTEGER
			MAX-ACCESS read-only
			STATUS current
			DESCRIPTION
				"The flag indicate wether the interface is DR or not.
				1  PIM_LOCAL_RTR_IS_DR
				2  PIM_LOCAL_RTR_IS_NON_DR
				3  PIM_DR_TRANSITION_TO_NONDR
				4  PIM_NONDR_TRANSITION_TO_DR"
			::= { wriPimInterfaceEntry 17 }

		
		-- 1.3.6.1.4.1.3807.2.1619.2.2.1.18
		wriPimInterfaceTimerFlags OBJECT-TYPE
			SYNTAX INTEGER
			MAX-ACCESS read-only
			STATUS current
			DESCRIPTION
				"This object describes PIM-specific Timer flags related to a
				Interface. Bits setting in this objects correspond to the 
				       starting of a interface specific timer. The bits corresponding
				       to the timers are as follows:
				       0 - Hello Timer, 1 - JP Timer.
				       For example, If this object value is 3 (0000 0011), then
				       it means that Hello timer and JP timer are running.
				This is for both SM and DM. The bits which are not applicable 
				       to DM/SM will be filled with 0 "
			::= { wriPimInterfaceEntry 18 }

		
		-- 1.3.6.1.4.1.3807.2.1619.2.2.1.19
		wriPimInterfaceNeighborCnt OBJECT-TYPE
			SYNTAX INTEGER
			MAX-ACCESS read-only
			STATUS current
			DESCRIPTION
				"This object indicates how many pim neighbor on this interface. "
			::= { wriPimInterfaceEntry 19 }

		
		-- 1.3.6.1.4.1.3807.2.1619.2.2.1.20
		wriPimInterfaceLocalPruneDelay OBJECT-TYPE
			SYNTAX INTEGER (0..65535)
			MAX-ACCESS read-write
			STATUS current
			DESCRIPTION
				"Description."
			::= { wriPimInterfaceEntry 20 }

		
		-- 1.3.6.1.4.1.3807.2.1619.2.2.1.21
		wriPimInterfaceOverrideInterval OBJECT-TYPE
			SYNTAX INTEGER (0..65535)
			MAX-ACCESS read-write
			STATUS current
			DESCRIPTION
				"Description."
			::= { wriPimInterfaceEntry 21 }

		
		-- 1.3.6.1.4.1.3807.2.1619.2.2.1.22
		wriPimInterfaceDomainBorder OBJECT-TYPE
			SYNTAX TruthValue
			MAX-ACCESS read-write
			STATUS current
			DESCRIPTION
				"Description."
			::= { wriPimInterfaceEntry 22 }
                                           
		-- 1.3.6.1.4.1.3807.2.1619.2.2.1.23                                           
        wriPimInterfaceHelloTimer OBJECT-TYPE
			SYNTAX INTEGER
			MAX-ACCESS read-write
			STATUS current
			DESCRIPTION
				"Description."
			::= { wriPimInterfaceEntry 23 }
       
       -- 1.3.6.1.4.1.3807.2.1619.2.2.1.24
        wriPimInterfaceIgmpTimer OBJECT-TYPE
			SYNTAX INTEGER
			MAX-ACCESS read-write
			STATUS current
			DESCRIPTION
				"Description."
			::= { wriPimInterfaceEntry 24 }
			
       -- 1.3.6.1.4.1.3807.2.1619.2.2.1.25
         wriPimInterfaceJoinPruneTimer  OBJECT-TYPE
			SYNTAX INTEGER
			MAX-ACCESS read-write
			STATUS current
			DESCRIPTION
				"Description."
			::= { wriPimInterfaceEntry 25 }
			
        -- 1.3.6.1.4.1.3807.2.1619.2.2.1.26
		wriPimInterfaceNbrListCount  OBJECT-TYPE
			SYNTAX Gauge32
			MAX-ACCESS read-only
			STATUS current
			DESCRIPTION
				"Description."
			::= { wriPimInterfaceEntry 26 }
       
       -- 1.3.6.1.4.1.3807.2.1619.2.2.1.27   
        wriPimInterfaceMNbrListCount OBJECT-TYPE
			SYNTAX Gauge32
			MAX-ACCESS read-only
			STATUS current
			DESCRIPTION
				"Description."
			::= { wriPimInterfaceEntry 27 }

		-- 1.3.6.1.4.1.3807.2.1619.2.2.1.28			
		wriPimInterfaceLinkState OBJECT-TYPE
			SYNTAX INTEGER
			MAX-ACCESS read-only
			STATUS current
			DESCRIPTION
				"Description."
			::= { wriPimInterfaceEntry 28 }	
			                               
		-- 1.3.6.1.4.1.3807.2.1619.2.2.1.29	                               
		wriPimInterfaceInBadPacket 	OBJECT-TYPE
			SYNTAX Counter32
			MAX-ACCESS read-only
			STATUS current
			DESCRIPTION
				"Description."
			::= { wriPimInterfaceEntry 29 }			
			                               
		-- 1.3.6.1.4.1.3807.2.1619.2.2.1.30	                               
	   wriPimInterfaceInPacket  OBJECT-TYPE
			SYNTAX Counter32
			MAX-ACCESS read-only
			STATUS current
			DESCRIPTION
				"Description."
			::= { wriPimInterfaceEntry 30 }	 
			
	                                       
	    -- 1.3.6.1.4.1.3807.2.1619.2.2.1.31                                   
		wriPimInterfaceOutPacket OBJECT-TYPE
			SYNTAX Counter32
			MAX-ACCESS read-only
			STATUS current
			DESCRIPTION
				"Description."
			::= { wriPimInterfaceEntry 31 }	 	
		
		
		-- 1.3.6.1.4.1.3807.2.1619.2.2.1.32     
		wriPimInterfaceJoinPruneInPacket OBJECT-TYPE
			SYNTAX Counter32
			MAX-ACCESS read-only
			STATUS current
			DESCRIPTION
				"Description."
			::= { wriPimInterfaceEntry 32 }	     
		                                   
		                                   
		-- 1.3.6.1.4.1.3807.2.1619.2.2.1.33                                      
		wriPimInterfaceJoinPruneOutPacket  OBJECT-TYPE
			SYNTAX Counter32
			MAX-ACCESS read-only
			STATUS current
			DESCRIPTION
				"Description."
			::= { wriPimInterfaceEntry 33 }
		                                   
		                                   
		-- 1.3.6.1.4.1.3807.2.1619.2.2.1.34                                   
		wriPimInterfaceLanDelayEnabled OBJECT-TYPE
			SYNTAX TruthValue
			MAX-ACCESS read-only
			STATUS current
			DESCRIPTION
				"Description."
			::= { wriPimInterfaceEntry 34 }
                                           
                                           
      -- 1.3.6.1.4.1.3807.2.1619.2.2.1.35                                     
	  wriPimInterfacePruneDelay	 OBJECT-TYPE
			SYNTAX INTEGER
			MAX-ACCESS read-only
			STATUS current
			DESCRIPTION
				"Description."
			::= { wriPimInterfaceEntry 35 }
      
      
      wriPimInterfaceStateFlashCapable OBJECT-TYPE
			SYNTAX INTEGER{ enable(1),disable(2)}
			MAX-ACCESS read-write
			STATUS current
			DESCRIPTION
				"Description."
			::= { wriPimInterfaceEntry 36 }
					
					
			
	   wriPimInterfaceGraftRetryInterval OBJECT-TYPE
			SYNTAX INTEGER(1..65535)
			MAX-ACCESS read-write
			STATUS current
			DESCRIPTION
				"Description."
			::= { wriPimInterfaceEntry 37 }
		--xf add 2015-5-20
		wriPimInterfaceBfdState OBJECT-TYPE
			SYNTAX INTEGER
			{
				enable(1),
				disable(2)
			}
			MAX-ACCESS read-write
			STATUS current
			DESCRIPTION
				"Description."
			::= { wriPimInterfaceEntry 38 }
	                              
		                                      
		-- 1.3.6.1.4.1.3807.2.1619.2.3
		wriPimNeighborTable OBJECT-TYPE                    
			SYNTAX SEQUENCE OF WriPimNeighborEntry
			MAX-ACCESS not-accessible
			STATUS current
			DESCRIPTION
				"The (conceptual) table listing the router's PIM neighbors."
			::= { wriPimTables 3 }

		
		-- 1.3.6.1.4.1.3807.2.1619.2.3.1
		wriPimNeighborEntry OBJECT-TYPE
			SYNTAX WriPimNeighborEntry
			MAX-ACCESS not-accessible
			STATUS current
			DESCRIPTION
				"An entry (conceptual row) in the pimNeighborTable."
			INDEX { wriPimNeighborIfIndex,wriPimNeighborAddress }
			::= { wriPimNeighborTable 1 }

		
		WriPimNeighborEntry ::=
			SEQUENCE { 
				wriPimNeighborAddress
					IpAddress,
				wriPimNeighborIfIndex
					INTEGER,
				wriPimNeighborUpTime
					Unsigned32,
				wriPimNeighborExpiryTime
					Unsigned32,
				wriPimNeighborMode
					INTEGER,
				wriPimNeighborGenerationId
					Integer32,
				wriPimNeighborDRPriority
					Integer32,
				wriPimNeighborDRState
					INTEGER,
				wriPimNeighborTBit
					TruthValue,  
				wriPimNeighborLanPruneDelayPresent	
		            TruthValue,
		        wriPimNeighborPropagationDelay
		        	 INTEGER,
		        wriPimNeighborOverrideInterval
		           	 INTEGER,  
		        wriPimNeighborJoinPruneCount
		        	 Counter32,
				--xf add 2015-5-20
				wriPimNeighborBfdState
					 INTEGER
			 }

	   -- 1.3.6.1.4.1.3807.2.1619.2.3.1.1
			wriPimNeighborAddress OBJECT-TYPE
			SYNTAX IpAddress
			MAX-ACCESS read-only
			STATUS current
			DESCRIPTION
				"The IP address of the PIM neighbor for which this entry
				contains information."
			::= { wriPimNeighborEntry 1 }

		
	   -- 1.3.6.1.4.1.3807.2.1619.2.3.1.2
		wriPimNeighborIfIndex OBJECT-TYPE
			SYNTAX INTEGER
			MAX-ACCESS read-only
			STATUS current
			DESCRIPTION
				"The value of ifIndex for the interface used to reach this
				PIM neighbor."
			::= { wriPimNeighborEntry 2 }

		
		-- 1.3.6.1.4.1.3807.2.1619.2.3.1.3
		wriPimNeighborUpTime OBJECT-TYPE
			SYNTAX Unsigned32
			MAX-ACCESS read-only
			STATUS current
			DESCRIPTION
				"The time since this PIM neighbor (last) became a neighbor
				of the local router."
			::= { wriPimNeighborEntry 3 }

		
		-- 1.3.6.1.4.1.3807.2.1619.2.3.1.4
		wriPimNeighborExpiryTime OBJECT-TYPE
			SYNTAX Unsigned32
			MAX-ACCESS read-only
			STATUS current
			DESCRIPTION
				"The minimum time remaining before this PIM neighbor will be
				aged out."
			::= { wriPimNeighborEntry 4 }

		
		-- 1.3.6.1.4.1.3807.2.1619.2.3.1.5
		wriPimNeighborMode OBJECT-TYPE
			SYNTAX INTEGER
				{
				dense(1),
				sparse(2)
				}
			MAX-ACCESS read-only
			STATUS deprecated
			DESCRIPTION
				"The active PIM mode of this neighbor.  This object is
				deprecated for PIMv2 routers since all neighbors on the
				interface must be either dense or sparse as determined by
				the protocol running on the interface."
			::= { wriPimNeighborEntry 5 }

		
		-- 1.3.6.1.4.1.3807.2.1619.2.3.1.6
		wriPimNeighborGenerationId OBJECT-TYPE
			SYNTAX Integer32
			MAX-ACCESS read-only
			STATUS current
			DESCRIPTION
				"The Generation identifier of the router. This is used by
				neighbour routers to quickly detect router reboot and synchronize
				RP-Set information and forwarding states by triggering Bootstrap
				and Join/Prune messages to the rebooted router"
			::= { wriPimNeighborEntry 6 }

		
		-- 1.3.6.1.4.1.3807.2.1619.2.3.1.7
		wriPimNeighborDRPriority OBJECT-TYPE
			SYNTAX Integer32
			MAX-ACCESS read-only
			STATUS current
			DESCRIPTION
				"The DR priority used to elect DR of the neighbor"
			::= { wriPimNeighborEntry 7 }

		
		-- 1.3.6.1.4.1.3807.2.1619.2.3.1.8
		wriPimNeighborDRState OBJECT-TYPE
			SYNTAX INTEGER
				{
				yes(1),
				no(2)
				}
			MAX-ACCESS read-only
			STATUS current
			DESCRIPTION
				"It to indicate whether the neighbor is DR or not."
			::= { wriPimNeighborEntry 8 }

		-- 1.3.6.1.4.1.3807.2.1619.2.3.1.9
	    wriPimNeighborTBit  OBJECT-TYPE
	    	 SYNTAX     TruthValue
    		 MAX-ACCESS read-only
    		 STATUS     current
  			 DESCRIPTION
           		 "Evaluates to TRUE if this neighbor is using the DR Priority
            	 option."
    		 ::= { wriPimNeighborEntry 9 }    
    		 
        -- 1.3.6.1.4.1.3807.2.1619.2.3.1.10
		wriPimNeighborLanPruneDelayPresent OBJECT-TYPE
    		SYNTAX     TruthValue
   			MAX-ACCESS read-only
    		STATUS     current
    		DESCRIPTION
            	"Evaluates to TRUE if this neighbor is using the LAN Prune
           		 Delay option."
   			 ::= { wriPimNeighborEntry 10 }
	                                          
	    -- 1.3.6.1.4.1.3807.2.1619.2.3.1.11                                      
		wriPimNeighborPropagationDelay  OBJECT-TYPE
			SYNTAX INTEGER
			MAX-ACCESS read-only
			STATUS current
			DESCRIPTION
				""
			::= { wriPimNeighborEntry 11 }
       
       	-- 1.3.6.1.4.1.3807.2.1619.2.3.1.12
		wriPimNeighborOverrideInterval  OBJECT-TYPE
    		SYNTAX     INTEGER (0..65535)
    		MAX-ACCESS read-only
    		STATUS     current
    		DESCRIPTION
            	"The value of the Override_Interval field of the LAN Prune
            	Delay option received from this neighbor.  This object is
            	always zero if pimNeighborLanPruneDelayPresent is FALSE."
    		::= { wriPimNeighborEntry 12 }
        
        -- 1.3.6.1.4.1.3807.2.1619.2.3.1.13
		wriPimNeighborJoinPruneCount OBJECT-TYPE
			SYNTAX Counter32
			MAX-ACCESS read-only
			STATUS current
			DESCRIPTION
				""
			::= { wriPimNeighborEntry 13 }
	
		--xf add 2015-5-20
		wriPimNeighborBfdState  OBJECT-TYPE
			SYNTAX INTEGER
			{
				down(1),
				up(2)
			}
			MAX-ACCESS read-only
			STATUS current
			DESCRIPTION
				""
			::= { wriPimNeighborEntry 14 }
		
		-- 1.3.6.1.4.1.3807.2.1619.2.4
		wriPimIpMRouteTable OBJECT-TYPE
			SYNTAX SEQUENCE OF WriPimIpMRouteEntry
			MAX-ACCESS not-accessible
			STATUS current
			DESCRIPTION
				"The (conceptual) table listing PIM multicast routing information"
			::= { wriPimTables 4 }

		
		-- 1.3.6.1.4.1.3807.2.1619.2.4.1
		wriPimIpMRouteEntry OBJECT-TYPE
			SYNTAX WriPimIpMRouteEntry
			MAX-ACCESS not-accessible
			STATUS current
			DESCRIPTION
				"An entry (conceptual row) in the pimIpMRouteTable.	 There
				is one entry for each incoming interface running PIM"
			INDEX { wriPimIpMRouteInstance,wriPimIpMRouteType,wriPimIpMRouteGroup, wriPimIpMRouteSource, wriPimIpMRouteSourceMask }
			::= { wriPimIpMRouteTable 1 }

		
		WriPimIpMRouteEntry ::=
			SEQUENCE {  
				wriPimIpMRouteInstance	
					INTEGER,
				wriPimIpMRouteType
					INTEGER,
	         	wriPimIpMRouteGroup
					IpAddress,
				wriPimIpMRouteSource
					IpAddress,
				wriPimIpMRouteSourceMask
					INTEGER,
				wriPimIpMRouteUpstreamNeighbor
					IpAddress,
				wriPimIpMRouteInIfIndex
					INTEGER,
				wriPimIpMRouteUpTime
					Unsigned32,
				wriPimIpMRouteExpiryTime
					Unsigned32,
				wriPimIpMRouteFwdPkts
					Counter32,
				wriPimIpMRouteAssertTimerExpiryTime
					Unsigned32,
				wriPimIpMRouteAssertMetric
					Integer32,
				wriPimIpMRouteAssertMetricPref
					Integer32,
				wriPimIpMRouteAssertRPTBit
					TruthValue,
				wriPimIpMRouteTimerFlags
					INTEGER,
				wriPimIpMRouteFlags
					INTEGER,
				wriPimIpMRouteAcceptDataStatus
					Integer32,
				wriPimIpMRouteRpfNbrAddress
				   	IpAddress,
				wriPimIpMRouteRegstOptLimit
				    INTEGER,
				wriPimIpMRoutePendingJoinFlag
				    INTEGER,
				wriPimIpMRouteJpSupressTimer
				    INTEGER,
				wriPimIpMRouteRegSupressTimer
				    INTEGER,     
				wriPimIpMRouteRouteTimer
					INTEGER,
				wriPimIpMRouteAssertTimer
					INTEGER,
				wriPimIpMRouteJoinDelayTimer
					INTEGER,
				wriPimIpMRouteAssertLimitTimer
					INTEGER,
				wriPimIpMRouteOutIfNumber
					INTEGER,
				wriPimIpMRouteState
					INTEGER	
		}    
		
		-- 1.3.6.1.4.1.3807.2.1619.2.4.1.1
       	wriPimIpMRouteInstance  OBJECT-TYPE
			SYNTAX INTEGER
			MAX-ACCESS read-only
			STATUS current
			DESCRIPTION
				"vpn instance id"
			::= { wriPimIpMRouteEntry 1 }

		-- 1.3.6.1.4.1.3807.2.1619.2.4.1.2
		wriPimIpMRouteType OBJECT-TYPE
			SYNTAX INTEGER
			MAX-ACCESS read-only
			STATUS current
			DESCRIPTION
				"This object describes the route entry type,such as SG,*G.
				1     (S,G)  Entry 
				2     (S,G) RPT Bit Entry
				3     (*,G) entry
				4     (*,*,RP) entry
				5     Invalid entry"
			::= { wriPimIpMRouteEntry 2 }

		
		-- 1.3.6.1.4.1.3807.2.1619.2.4.1.3
		wriPimIpMRouteGroup OBJECT-TYPE
			SYNTAX IpAddress
			MAX-ACCESS read-only
			STATUS current
			DESCRIPTION
				"The IP multicast group address for which this entry
				contains multicast routing information."
			::= { wriPimIpMRouteEntry 3 }

		
		-- 1.3.6.1.4.1.3807.2.1619.2.4.1.4
		wriPimIpMRouteSource OBJECT-TYPE
			SYNTAX IpAddress
			MAX-ACCESS read-only
			STATUS current
			DESCRIPTION
				"The network address which when combined with the
				corresponding value of ipMRouteSourceMask identifies the
				sources for which this entry contains multicast routing
				information."
			::= { wriPimIpMRouteEntry 4 }

		
		-- 1.3.6.1.4.1.3807.2.1619.2.4.1.5
		wriPimIpMRouteSourceMask OBJECT-TYPE
			SYNTAX INTEGER
			MAX-ACCESS read-only
			STATUS current
			DESCRIPTION
				"The network mask which when combined with the corresponding
				value of ipMRouteSource identifies the sources for which
				this entry contains multicast routing information."
			::= { wriPimIpMRouteEntry 5 }

		
		-- 1.3.6.1.4.1.3807.2.1619.2.4.1.6
		wriPimIpMRouteUpstreamNeighbor OBJECT-TYPE
			SYNTAX IpAddress
			MAX-ACCESS read-only
			STATUS current
			DESCRIPTION
				"The address of the upstream neighbor (e.g., RPF neighbor)
				from which IP datagrams from these sources to this multicast
				address are received."
			::= { wriPimIpMRouteEntry 6 }

		
		-- 1.3.6.1.4.1.3807.2.1619.2.4.1.7
		wriPimIpMRouteInIfIndex OBJECT-TYPE
			SYNTAX INTEGER
			MAX-ACCESS read-only
			STATUS current
			DESCRIPTION
				"The value of ifIndex for the interface on which IP
				datagrams sent by these sources to this multicast address
				are received."
			::= { wriPimIpMRouteEntry 7 }

		
		-- 1.3.6.1.4.1.3807.2.1619.2.4.1.8
		wriPimIpMRouteUpTime OBJECT-TYPE
			SYNTAX Unsigned32
			MAX-ACCESS read-only
			STATUS current
			DESCRIPTION
				"The time since the multicast routing information
				represented by this entry was learned by the router."
			::= { wriPimIpMRouteEntry 8 }

		
		-- 1.3.6.1.4.1.3807.2.1619.2.4.1.9
		wriPimIpMRouteExpiryTime OBJECT-TYPE
			SYNTAX Unsigned32
			MAX-ACCESS read-only
			STATUS current
			DESCRIPTION
				"The minimum amount of time remaining before this entry will
				be aged out.  The value 0 indicates that the entry is not
				subject to aging."
			::= { wriPimIpMRouteEntry 9 }

		
		-- 1.3.6.1.4.1.3807.2.1619.2.4.1.10
		wriPimIpMRouteFwdPkts OBJECT-TYPE
			SYNTAX Counter32
			MAX-ACCESS read-only
			STATUS current
			DESCRIPTION
				"The number of packets which this router has received from
				these sources and addressed to this multicast group
				address."
			::= { wriPimIpMRouteEntry 10 }

		
		-- 1.3.6.1.4.1.3807.2.1619.2.4.1.11
		wriPimIpMRouteAssertTimerExpiryTime OBJECT-TYPE
			SYNTAX Unsigned32
			MAX-ACCESS read-only
			STATUS current
			DESCRIPTION
				"The time remaining before the router changes its upstream
				neighbor back to its RPF neighbor.	This timer is called the
				Assert timer in the PIM Sparse and Dense mode specification.
				A value of 0 indicates that no Assert has changed the
				upstream neighbor away from the RPF neighbor."
			::= { wriPimIpMRouteEntry 11 }

		
		-- 1.3.6.1.4.1.3807.2.1619.2.4.1.12
		wriPimIpMRouteAssertMetric OBJECT-TYPE
			SYNTAX Integer32
			MAX-ACCESS read-only
			STATUS current
			DESCRIPTION
				"The metric advertised by the assert winner on the upstream
				interface, or 0 if no such assert is in received."
			::= { wriPimIpMRouteEntry 12 }

		
		-- 1.3.6.1.4.1.3807.2.1619.2.4.1.13
		wriPimIpMRouteAssertMetricPref OBJECT-TYPE
			SYNTAX Integer32
			MAX-ACCESS read-only
			STATUS current
			DESCRIPTION
				"The preference advertised by the assert winner on the
				upstream interface, or 0 if no such assert is in effect."
			::= { wriPimIpMRouteEntry 13 }

		
		-- 1.3.6.1.4.1.3807.2.1619.2.4.1.14
		wriPimIpMRouteAssertRPTBit OBJECT-TYPE
			SYNTAX TruthValue
			MAX-ACCESS read-only
			STATUS current
			DESCRIPTION
				"The value of the RPT-bit advertised by the assert winner on
				the upstream interface, or false if no such assert is in
				effect."
			::= { wriPimIpMRouteEntry 14 }

		
		-- 1.3.6.1.4.1.3807.2.1619.2.4.1.15
		wriPimIpMRouteTimerFlags OBJECT-TYPE
			SYNTAX INTEGER
			MAX-ACCESS read-only
			STATUS current
			DESCRIPTION
				"This object describes PIM-specific Timer flags related to a
				Multicast Route Entry. If the bit is 1 indicates that timer 
				       is started for that entry.  The bits corresponding to the 
				       timers are as follows:
				       0 - JP Suppression Timer, 1 - Oif Timer, 2 - Entry Timer,
				       3 - Reg Suppression Timer, 4 - Assert Timer, 
				       5 - RandomDelayJoin Timer.
				       For example, If this object value is 3 (0000 0011), then
				       it means that JPSuppression timer and  Oif timer are running.
				       This is for both SM and DM. The bits which are not applicable 
				       to DM/SM will be filled with 0 "
			::= { wriPimIpMRouteEntry 15 }

		
		-- 1.3.6.1.4.1.3807.2.1619.2.4.1.16
		wriPimIpMRouteFlags OBJECT-TYPE
			SYNTAX INTEGER
			MAX-ACCESS read-only
			STATUS current
			DESCRIPTION
				"This object describes PIM-specific flags related to a
				multicast state entry.  See the PIM Sparse Mode
				specification for the meaning of the RPT and SPT bits.
				0th bit set indicates RPT bit set
				   1st bit set indicates WC  bit set
				   2nd bit set indicates SPT bit set"
			::= { wriPimIpMRouteEntry 16 }

		
		-- 1.3.6.1.4.1.3807.2.1619.2.4.1.17
		wriPimIpMRouteAcceptDataStatus OBJECT-TYPE
			SYNTAX Integer32
			MAX-ACCESS read-write
			STATUS current
			DESCRIPTION
				"Description."
			::= { wriPimIpMRouteEntry 17 }

		-- 1.3.6.1.4.1.3807.2.1619.2.4.1.18
		wriPimIpMRouteRpfNbrAddress  OBJECT-TYPE
			SYNTAX IpAddress
			MAX-ACCESS read-only
			STATUS current
			DESCRIPTION
				"Description."
			::= { wriPimIpMRouteEntry 18 }

		
		-- 1.3.6.1.4.1.3807.2.1619.2.4.1.19		 
	    wriPimIpMRouteRegstOptLimit OBJECT-TYPE
			SYNTAX INTEGER
			MAX-ACCESS read-only
			STATUS current
			DESCRIPTION
				"Description."
			::= { wriPimIpMRouteEntry 19 }
                                           
        -- 1.3.6.1.4.1.3807.2.1619.2.4.1.20                                   
		wriPimIpMRoutePendingJoinFlag OBJECT-TYPE
			SYNTAX INTEGER
			MAX-ACCESS read-only
			STATUS current
			DESCRIPTION
				"Description."
			::= { wriPimIpMRouteEntry 20 }
			                               
		-- 1.3.6.1.4.1.3807.2.1619.2.4.1.21	                               
		wriPimIpMRouteJpSupressTimer OBJECT-TYPE
			SYNTAX INTEGER
			MAX-ACCESS read-only
			STATUS current
			DESCRIPTION
				"Description."
			::= { wriPimIpMRouteEntry 21 }
			                               
		-- 1.3.6.1.4.1.3807.2.1619.2.4.1.22	                               
		wriPimIpMRouteRegSupressTimer OBJECT-TYPE
			SYNTAX INTEGER
			MAX-ACCESS read-only
			STATUS current
			DESCRIPTION
				"Description."
			::= { wriPimIpMRouteEntry 22 }
			                               
		-- 1.3.6.1.4.1.3807.2.1619.2.4.1.23	                               
		wriPimIpMRouteRouteTimer  OBJECT-TYPE
			SYNTAX INTEGER
			MAX-ACCESS read-only
			STATUS current
			DESCRIPTION
				"Description."
			::= { wriPimIpMRouteEntry 23 }
			                               
		-- 1.3.6.1.4.1.3807.2.1619.2.4.1.24	                               
		wriPimIpMRouteAssertTimer  OBJECT-TYPE
			SYNTAX INTEGER
			MAX-ACCESS read-only
			STATUS current
			DESCRIPTION
				"Description."
			::= { wriPimIpMRouteEntry 24 }
			                               
			                               
		-- 1.3.6.1.4.1.3807.2.1619.2.4.1.25	                               
		wriPimIpMRouteJoinDelayTimer  OBJECT-TYPE
			SYNTAX INTEGER
			MAX-ACCESS read-only
			STATUS current
			DESCRIPTION
				"Description."
			::= { wriPimIpMRouteEntry 25 }
			                               
			                               
		-- 1.3.6.1.4.1.3807.2.1619.2.4.1.26	                               
		wriPimIpMRouteAssertLimitTimer  OBJECT-TYPE
			SYNTAX INTEGER
			MAX-ACCESS read-only
			STATUS current
			DESCRIPTION
				"Description."
			::= { wriPimIpMRouteEntry 26 }
			                               
		-- 1.3.6.1.4.1.3807.2.1619.2.4.1.27	                               
		wriPimIpMRouteOutIfNumber OBJECT-TYPE
			SYNTAX INTEGER
			MAX-ACCESS read-only
			STATUS current
			DESCRIPTION
				"Description."
			::= { wriPimIpMRouteEntry 27 }
					                       
					                       
		-- 1.3.6.1.4.1.3807.2.1619.2.4.1.28			                       
		wriPimIpMRouteState OBJECT-TYPE
			SYNTAX INTEGER
			MAX-ACCESS read-only
			STATUS current
			DESCRIPTION
				"This object describes the route entry state,such as forward.
				1    Forwarding State    
				   2    Null State          
				   3    Negative Cache State  "
			::= { wriPimIpMRouteEntry 28 }
	
		
		
		-- 1.3.6.1.4.1.3807.2.1619.2.5
		wriPimIpMRouteNextHopTable OBJECT-TYPE
			SYNTAX SEQUENCE OF WriPimIpMRouteNextHopEntry
			MAX-ACCESS not-accessible
			STATUS current
			DESCRIPTION
				"The (conceptual) table listing PIM information on the next hops
				on outgoing interfaces for forwarding multicast datagrams"
			::= { wriPimTables 5 }

		
		-- 1.3.6.1.4.1.3807.2.1619.2.5.1
		wriPimIpMRouteNextHopEntry OBJECT-TYPE
			SYNTAX WriPimIpMRouteNextHopEntry
			MAX-ACCESS not-accessible
			STATUS current
			DESCRIPTION
				"An entry (conceptual row) in the pimIpMRouteNextHopTable.
				There is one entry per entry in the ipMRouteNextHopTable
				whose interface is running PIM and whose
				pimIpMRouteNextHopState is pruned(1)."                                                                                             
			INDEX { wriPimIpMRouteNextHopInstance,wriPimIpMRouteNextHopRouteType,wriPimIpMRouteNextHopGroup, wriPimIpMRouteNextHopSource,
					 wriPimIpMRouteNextHopSourceMask,wriPimIpMRouteNextHopOIfIndex, wriPimIpMRouteNextHopAddress}
			::= { wriPimIpMRouteNextHopTable 1 }

		
		WriPimIpMRouteNextHopEntry ::=
			SEQUENCE { 
				wriPimIpMRouteNextHopInstance
					INTEGER,
				wriPimIpMRouteNextHopRouteType
					INTEGER,		
				wriPimIpMRouteNextHopGroup
					IpAddress,
				wriPimIpMRouteNextHopSource
					IpAddress,
				wriPimIpMRouteNextHopSourceMask
					INTEGER,
				wriPimIpMRouteNextHopOIfIndex
					Integer32,
				wriPimIpMRouteNextHopAddress
					IpAddress,
				wriPimIpMRouteNextHopPruneReason
					INTEGER,
				wriPimIpMRouteNextHopOifState
					INTEGER,
				wriPimIpMRouteNextHopOifUpTime
					Integer32,
				wriPimIpMRouteNextHopOifExpiryTime
					Integer32,
				wriPimIpMRouteNextHopOifAsserWinnerFlag
					TruthValue,
				wriPimIpMRouteNextHopJoinReason
				   	 INTEGER,
				wriPimIpMRouteNextHopFirstUpTime
					 INTEGER,
				wriPimIpMRouteNextHopDelDelayTime
					 INTEGER,
				wriPimIpMRouteNextHopCurrentFwdState
				     INTEGER,  
				wriPimIpMRouteNextHopAssertStartExpireTime
				     INTEGER,
				wriPimIpMRouteNextHopAssertWinnerPref       
                     INTEGER,
                wriPimIpMRouteNextHopAssertWinnerMetric
                     INTEGER,      
				wriPimIpMRouteNextHopNbrPruneReason     	    	 
			         INTEGER,
			    wriPimIpMRouteNextHopAssertState
			    	 INTEGER,
			   wriPimIpMRouteNextHopNextHop
			    	 IpAddress
            }     
            
		-- 1.3.6.1.4.1.3807.2.1619.2.5.1.1
		wriPimIpMRouteNextHopInstance  OBJECT-TYPE
			SYNTAX INTEGER
			MAX-ACCESS read-only
			STATUS current
			DESCRIPTION
				"vpn instance id."
			::= { wriPimIpMRouteNextHopEntry 1 }
			
			
		-- 1.3.6.1.4.1.3807.2.1619.2.5.1.2
		wriPimIpMRouteNextHopRouteType   OBJECT-TYPE
			SYNTAX INTEGER
			MAX-ACCESS read-only
			STATUS current
			DESCRIPTION
				"route type."
			::= { wriPimIpMRouteNextHopEntry 2 }  
			
			
		-- 1.3.6.1.4.1.3807.2.1619.2.5.1.3
		wriPimIpMRouteNextHopGroup OBJECT-TYPE
			SYNTAX IpAddress
			MAX-ACCESS read-only
			STATUS current
			DESCRIPTION
				"The IP multicast group for which this entry specifies a
				next-hop on an outgoing interface."
			::= { wriPimIpMRouteNextHopEntry 3 }

		
		-- 1.3.6.1.4.1.3807.2.1619.2.5.1.4
		wriPimIpMRouteNextHopSource OBJECT-TYPE
			SYNTAX IpAddress
			MAX-ACCESS read-only
			STATUS current
			DESCRIPTION
				"The network address which when combined with the
				corresponding value of pimIpMRouteNextHopSourceMask identifies
				the sources for which this entry specifies a next-hop on an
				outgoing interface."
			::= { wriPimIpMRouteNextHopEntry 4 }

		
		-- 1.3.6.1.4.1.3807.2.1619.2.5.1.5
		wriPimIpMRouteNextHopSourceMask OBJECT-TYPE
			SYNTAX INTEGER
			MAX-ACCESS read-only
			STATUS current
			DESCRIPTION
				"The network mask which when combined with the corresponding
				value of pimIpMRouteNextHopSource identifies the sources for
				which this entry specifies a next-hop on an outgoing interface"
			::= { wriPimIpMRouteNextHopEntry 5 }

		
		-- 1.3.6.1.4.1.3807.2.1619.2.5.1.6
		wriPimIpMRouteNextHopOIfIndex OBJECT-TYPE
			SYNTAX Integer32 (1..65535)
			MAX-ACCESS read-only
			STATUS current
			DESCRIPTION
				"The ifIndex value of the interface for the outgoing
				interface for this next-hop."
			::= { wriPimIpMRouteNextHopEntry 6 }

		
		-- 1.3.6.1.4.1.3807.2.1619.2.5.1.7
		wriPimIpMRouteNextHopAddress OBJECT-TYPE
			SYNTAX IpAddress
			MAX-ACCESS read-only
			STATUS current
			DESCRIPTION
				"The address of the next-hop specific to this entry.  For
				most interfaces, this is identical to pimIpMRouteNextHopGroup.
				NBMA interfaces, however, may have multiple next-hop
				addresses out a single outgoing interface."
			::= { wriPimIpMRouteNextHopEntry 7 }

		
		-- 1.3.6.1.4.1.3807.2.1619.2.5.1.8
		wriPimIpMRouteNextHopPruneReason OBJECT-TYPE
			SYNTAX INTEGER
				{
				other(1),
				prune(2),
				assert(3),
				join(4)
				}
			MAX-ACCESS read-only
			STATUS current
			DESCRIPTION
				"This object indicates why the downstream interface was
				pruned, whether in response to a PIM prune message or due to
				PIM Assert processing."
			::= { wriPimIpMRouteNextHopEntry 8 }

		
		-- 1.3.6.1.4.1.3807.2.1619.2.5.1.9
		wriPimIpMRouteNextHopOifState OBJECT-TYPE
			SYNTAX INTEGER
				{
				pruned(1),
				forwarding(2)
				}
			MAX-ACCESS read-only
			STATUS current
			DESCRIPTION
				"This object indicates the state of the output interface ."
			::= { wriPimIpMRouteNextHopEntry 9 }

		
		-- 1.3.6.1.4.1.3807.2.1619.2.5.1.10
		wriPimIpMRouteNextHopOifUpTime OBJECT-TYPE
			SYNTAX Integer32
			MAX-ACCESS read-only
			STATUS current
			DESCRIPTION
				"This object indicates the time value since the interface become the 
				output interface of the entry."
			::= { wriPimIpMRouteNextHopEntry 10 }

		
		-- 1.3.6.1.4.1.3807.2.1619.2.5.1.11
		wriPimIpMRouteNextHopOifExpiryTime OBJECT-TYPE
			SYNTAX Integer32
			MAX-ACCESS read-only
			STATUS current
			DESCRIPTION
				"This object indicates the time value before the interface timeout."
			::= { wriPimIpMRouteNextHopEntry 11 }

		
		-- 1.3.6.1.4.1.3807.2.1619.2.5.1.12
		wriPimIpMRouteNextHopOifAsserWinnerFlag OBJECT-TYPE
			SYNTAX TruthValue
			MAX-ACCESS read-only
			STATUS current
			DESCRIPTION
				"This object indicates wether the interface is a winner of assert process."
			::= { wriPimIpMRouteNextHopEntry 12 }     
			
			
		-- 1.3.6.1.4.1.3807.2.1619.2.5.1.13	
		wriPimIpMRouteNextHopJoinReason  OBJECT-TYPE
			SYNTAX INTEGER
			MAX-ACCESS read-only
			STATUS current
			DESCRIPTION
				""
			::= { wriPimIpMRouteNextHopEntry 13 }    
			
			
		-- 1.3.6.1.4.1.3807.2.1619.2.5.1.14	
		wriPimIpMRouteNextHopFirstUpTime OBJECT-TYPE
			SYNTAX INTEGER
			MAX-ACCESS read-only
			STATUS current
			DESCRIPTION
				""
			::= { wriPimIpMRouteNextHopEntry 14} 
			                                         
			                                         
		-- 1.3.6.1.4.1.3807.2.1619.2.5.1.15	                                         
		wriPimIpMRouteNextHopDelDelayTime  OBJECT-TYPE
			SYNTAX INTEGER
			MAX-ACCESS read-only
			STATUS current
			DESCRIPTION
				""
			::= { wriPimIpMRouteNextHopEntry 15 }  
			
			
		-- 1.3.6.1.4.1.3807.2.1619.2.5.1.16	
		wriPimIpMRouteNextHopCurrentFwdState  OBJECT-TYPE
			SYNTAX INTEGER
			MAX-ACCESS read-only
			STATUS current
			DESCRIPTION
				""
			::= { wriPimIpMRouteNextHopEntry 16 } 
			
			                                      
		-- 1.3.6.1.4.1.3807.2.1619.2.5.1.17	                                      
		wriPimIpMRouteNextHopAssertStartExpireTime OBJECT-TYPE
			SYNTAX INTEGER
			MAX-ACCESS read-only
			STATUS current
			DESCRIPTION
				""
			::= { wriPimIpMRouteNextHopEntry 17 }    
			
			
		-- 1.3.6.1.4.1.3807.2.1619.2.5.1.18	
		wriPimIpMRouteNextHopAssertWinnerPref OBJECT-TYPE
			SYNTAX INTEGER
			MAX-ACCESS read-only
			STATUS current
			DESCRIPTION
				""
			::= { wriPimIpMRouteNextHopEntry 18 }    
			
			
		-- 1.3.6.1.4.1.3807.2.1619.2.5.1.19	      
        wriPimIpMRouteNextHopAssertWinnerMetric   OBJECT-TYPE
			SYNTAX INTEGER
			MAX-ACCESS read-only
			STATUS current
			DESCRIPTION
				""
			::= { wriPimIpMRouteNextHopEntry 19 }  
			
			
		-- 1.3.6.1.4.1.3807.2.1619.2.5.1.20	
		wriPimIpMRouteNextHopNbrPruneReason  OBJECT-TYPE
			SYNTAX INTEGER
			MAX-ACCESS read-only
			STATUS current
			DESCRIPTION
				""
			::= { wriPimIpMRouteNextHopEntry 20 }  
			
			
		-- 1.3.6.1.4.1.3807.2.1619.2.5.1.21	   	    	 
	    wriPimIpMRouteNextHopAssertState  OBJECT-TYPE
			SYNTAX INTEGER
			MAX-ACCESS read-only
			STATUS current
			DESCRIPTION
				""
			::= { wriPimIpMRouteNextHopEntry 21 }     
			
			
		-- 1.3.6.1.4.1.3807.2.1619.2.5.1.22	
        wriPimIpMRouteNextHopNextHop   OBJECT-TYPE
			SYNTAX IpAddress
			MAX-ACCESS read-only
			STATUS current
			DESCRIPTION
				""
			::= { wriPimIpMRouteNextHopEntry 22 } 
		
			

		
		-- 1.3.6.1.4.1.3807.2.1619.2.6
		wriPimRPSetTable OBJECT-TYPE
			SYNTAX SEQUENCE OF WriPimRPSetEntry
			MAX-ACCESS not-accessible
			STATUS current
			DESCRIPTION
				"The (conceptual) table listing PIM information for
				candidate Rendezvous Points (RPs) for IP multicast groups.
				When the local router is the BSR, this information is
				obtained from received Candidate-RP-Advertisements.	 When
				the local router is not the BSR, this information is
				obtained from received RP-Set messages."
			::= { wriPimTables 6 }

		
		-- 1.3.6.1.4.1.3807.2.1619.2.6.1
		wriPimRPSetEntry OBJECT-TYPE
			SYNTAX WriPimRPSetEntry
			MAX-ACCESS not-accessible
			STATUS current
			DESCRIPTION
				"An entry (conceptual row) in the pimRPSetTable."
			INDEX { wriPimRPSetInstance, wriPimRPSetGroupAddress, wriPimRPSetGroupMask, wriPimRPSetAddress }
			::= { wriPimRPSetTable 1 }

		
		WriPimRPSetEntry ::=
			SEQUENCE {    
				wriPimRPSetInstance
					INTEGER,
				wriPimRPSetGroupAddress
					IpAddress,
				wriPimRPSetGroupMask
					INTEGER,
				wriPimRPSetAddress
					IpAddress,
				wriPimRPSetHoldTime
					Integer32,
				wriPimRPSetExpiryTime
					Unsigned32,
				wriPimRPSetBestRp
					IpAddress,
				wriPimRPSetPriority
					Integer32,
				wriPimRPSetStatus
					RowStatus,
				wriPimRPSetStaticState
					TruthValue	
			 }
        -- 1.3.6.1.4.1.3807.2.1619.2.6.1.1
       	wriPimRPSetInstance OBJECT-TYPE
			SYNTAX INTEGER
			MAX-ACCESS read-only
			STATUS current
			DESCRIPTION
				"Vpn instance id"
			::= { wriPimRPSetEntry 1 }
       	
		-- 1.3.6.1.4.1.3807.2.1619.2.6.1.2
		wriPimRPSetGroupAddress OBJECT-TYPE
			SYNTAX IpAddress
			MAX-ACCESS read-only
			STATUS current
			DESCRIPTION
				"The IP multicast group address which, when combined with
				pimRPSetGroupMask, gives the group prefix for which this
				entry contains information about the Candidate-RP."
			::= { wriPimRPSetEntry 2 }

		
		-- 1.3.6.1.4.1.3807.2.1619.2.6.1.3
		wriPimRPSetGroupMask OBJECT-TYPE
			SYNTAX INTEGER
			MAX-ACCESS read-only
			STATUS current
			DESCRIPTION
				"The multicast group address mask which, when combined with
				pimRPSetGroupAddress, gives the group prefix for which this
				entry contains information about the Candidate-RP."
			::= { wriPimRPSetEntry 3 }

		
		-- 1.3.6.1.4.1.3807.2.1619.2.6.1.4
		wriPimRPSetAddress OBJECT-TYPE
			SYNTAX IpAddress
			MAX-ACCESS read-only
			STATUS current
			DESCRIPTION
				"The IP address of the Candidate-RP."
			::= { wriPimRPSetEntry 4}

		
		-- 1.3.6.1.4.1.3807.2.1619.2.6.1.5
		wriPimRPSetHoldTime OBJECT-TYPE
			SYNTAX Integer32 (0..255)
			UNITS "seconds"
			MAX-ACCESS read-only
			STATUS current
			DESCRIPTION
				"The holdtime of a Candidate-RP.  If the local router is not
				the BSR, this value is 0."
			::= { wriPimRPSetEntry 5 }

		
		-- 1.3.6.1.4.1.3807.2.1619.2.6.1.6
		wriPimRPSetExpiryTime OBJECT-TYPE
			SYNTAX Unsigned32
			MAX-ACCESS read-only
			STATUS current
			DESCRIPTION
				"The minimum time remaining before the Candidate-RP will be
				declared down.  If the local router is not the BSR, this
				value is 0."
			::= { wriPimRPSetEntry 6 }

		
		-- 1.3.6.1.4.1.3807.2.1619.2.6.1.7
		wriPimRPSetBestRp OBJECT-TYPE
			SYNTAX IpAddress 
			MAX-ACCESS read-only
			STATUS current
			DESCRIPTION
				" ."
			::= { wriPimRPSetEntry 7}

         
		
		-- 1.3.6.1.4.1.3807.2.1619.2.6.1.8
		wriPimRPSetPriority OBJECT-TYPE
			SYNTAX Integer32 (1..255)
			MAX-ACCESS read-only
			STATUS current
			DESCRIPTION
				" The RP priority value used to select RP for a group."
			::= { wriPimRPSetEntry 8 }

		
		-- 1.3.6.1.4.1.3807.2.1619.2.6.1.9
		wriPimRPSetStatus OBJECT-TYPE
			SYNTAX RowStatus
			MAX-ACCESS read-create
			STATUS current
			DESCRIPTION
				"The status of this entry."
			::= { wriPimRPSetEntry 9 }
        
        -- 1.3.6.1.4.1.3807.2.1619.2.6.1.10            
		wriPimRPSetStaticState   OBJECT-TYPE
			SYNTAX TruthValue
			MAX-ACCESS read-create
			STATUS current
			DESCRIPTION
				"whether this entry is a Static."
			::= { wriPimRPSetEntry 10 }

		-- 1.3.6.1.4.1.3807.2.1619.2.7
		wriPimCandidateRPTable OBJECT-TYPE
			SYNTAX SEQUENCE OF WriPimCandidateRPEntry
			MAX-ACCESS not-accessible
			STATUS current
			DESCRIPTION
				"The (conceptual) table listing the IP multicast groups for
				which the local router is to advertise itself as a
				Candidate-RP when the value of pimComponentCRPHoldTime is
				non-zero.  If this table is empty, then the local router
				will advertise itself as a Candidate-RP for all groups
				(providing the value of pimComponentCRPHoldTime is non-
				zero)."
			::= { wriPimTables 7 }

		
		-- 1.3.6.1.4.1.3807.2.1619.2.7.1
		wriPimCandidateRPEntry OBJECT-TYPE
			SYNTAX WriPimCandidateRPEntry
			MAX-ACCESS not-accessible
			STATUS current
			DESCRIPTION
				"An entry (conceptual row) in the pimCandidateRPTable."
			INDEX { wriPimCandidateInstance,wriPimCandidateRPGroupAddress, wriPimCandidateRPGroupMask }
			::= { wriPimCandidateRPTable 1 }

		
		WriPimCandidateRPEntry ::=
			SEQUENCE {  
				wriPimCandidateInstance
					INTEGER,
				wriPimCandidateRPGroupAddress
					IpAddress,
				wriPimCandidateRPGroupMask
					INTEGER,
				wriPimCandidateRPAddress
					IpAddress,
				wriPimCandidateRPRowStatus
					RowStatus,
				wriPimCandidateRPHoldTime
					INTEGER,
				wriPimCandidateRPPriority
					INTEGER,
				wriPimCandidateRPNextAdvTime
					Unsigned32
			 }
         
        wriPimCandidateInstance  OBJECT-TYPE
			SYNTAX INTEGER
			MAX-ACCESS read-only
			STATUS current
			DESCRIPTION
				"vpn instace id"
			::= { wriPimCandidateRPEntry 1 }


		-- 1.3.6.1.4.1.3807.2.1619.2.7.1.1
		wriPimCandidateRPGroupAddress OBJECT-TYPE
			SYNTAX IpAddress
			MAX-ACCESS read-only
			STATUS current
			DESCRIPTION
				"The IP multicast group address which, when combined with
				pimCandidateRPGroupMask, identifies a group prefix for which
				the local router will advertise itself as a Candidate-RP."
			::= { wriPimCandidateRPEntry 2 }

		
		-- 1.3.6.1.4.1.3807.2.1619.2.7.1.2
		wriPimCandidateRPGroupMask OBJECT-TYPE
			SYNTAX INTEGER
			MAX-ACCESS read-only
			STATUS current
			DESCRIPTION
				"The multicast group address mask which, when combined with
				pimCandidateRPGroupMask, identifies a group prefix for which
				the local router will advertise itself as a Candidate-RP."
			::= { wriPimCandidateRPEntry 3 }

		
		-- 1.3.6.1.4.1.3807.2.1619.2.7.1.3
		wriPimCandidateRPAddress OBJECT-TYPE
			SYNTAX IpAddress
			MAX-ACCESS read-write
			STATUS current
			DESCRIPTION
				"The (unicast) address of the interface which will be
				advertised as a Candidate-RP."
			::= { wriPimCandidateRPEntry 4 }

		
		-- 1.3.6.1.4.1.3807.2.1619.2.7.1.4
		wriPimCandidateRPRowStatus OBJECT-TYPE
			SYNTAX RowStatus
			MAX-ACCESS read-create
			STATUS current
			DESCRIPTION
				"The status of this row, by which new entries may be
				created, or old entries deleted from this table."
			::= { wriPimCandidateRPEntry 5 }

		
		-- 1.3.6.1.4.1.3807.2.1619.2.7.1.5
		wriPimCandidateRPHoldTime OBJECT-TYPE
			SYNTAX INTEGER
			MAX-ACCESS read-write
			STATUS current
			DESCRIPTION
				"The holdtime for this candidate RP while send CRP message to BSR."
			::= { wriPimCandidateRPEntry 6 }

		
		-- 1.3.6.1.4.1.3807.2.1619.2.7.1.6
		wriPimCandidateRPPriority OBJECT-TYPE
			SYNTAX INTEGER (0..255)
			MAX-ACCESS read-write
			STATUS current
			DESCRIPTION
				"The RP priority for this candidate RP while send CRP message to BSR."
			::= { wriPimCandidateRPEntry 7 }

		
		-- 1.3.6.1.4.1.3807.2.1619.2.7.1.7
		wriPimCandidateRPNextAdvTime OBJECT-TYPE
			SYNTAX Unsigned32
			MAX-ACCESS read-only
			STATUS current
			DESCRIPTION
				"The time remaining before the system send CRP message to BSR."
			::= { wriPimCandidateRPEntry 8 }

		
		-- 1.3.6.1.4.1.3807.2.1619.2.8
		wriPimComponentTable OBJECT-TYPE
			SYNTAX SEQUENCE OF WriPimComponentEntry
			MAX-ACCESS not-accessible
			STATUS current
			DESCRIPTION
				"The (conceptual) table containing objects specific to a PIM
				domain.  One row exists for each domain to which the router
				is connected.  A PIM-SM domain is defined as an area of the
				network over which Bootstrap messages are forwarded.
				Typically, a PIM-SM router will be a member of exactly one
				domain.  This table also supports, however, routers which
				may form a border between two PIM-SM domains and do not
				forward Bootstrap messages between them."
			::= { wriPimTables 8 }

		
		-- 1.3.6.1.4.1.3807.2.1619.2.8.1
		wriPimComponentEntry OBJECT-TYPE
			SYNTAX WriPimComponentEntry
			MAX-ACCESS not-accessible
			STATUS current
			DESCRIPTION
				"An entry (conceptual row) in the pimComponentTable."
			INDEX { wriPimComponentInstance,wriPimComponentScopeGroup, wriPimComponentScopeMasklen}
			::= { wriPimComponentTable 1 }

		
		WriPimComponentEntry ::=
			SEQUENCE { 
				wriPimComponentInstance
				    INTEGER,
				wriPimComponentScopeGroup
					Integer32,
				wriPimComponentScopeMasklen
					Integer32,
				wriPimComponentId
					Integer32,
				wriPimComponentElectedBSRAddress
					IpAddress,
				wriPimComponentElectedBSRPriority
					INTEGER,
				wriPimComponentElectedBSRHashMaskLen
					INTEGER,
				wriPimComponentBSRExpiryTime
					Unsigned32,
				wriPimComponentStatus
					RowStatus,
				wriPimComponentCandidateBSRAddress
					IpAddress,
				wriPimComponentCandidateBSRPriority
					INTEGER,
				wriPimComponentCandidateBSRHashMaskLen
					INTEGER,
				wriPimComponentCandidateBSRState
					TruthValue,
				wriPimComponentBSRUpdateTime
					INTEGER,  
				wriPimComponentElectedBSRFragmentTag
					INTEGER,  	
				wriPimComponentElectedBSRState	
					TruthValue					
			 }     
			 
		-- 1.3.6.1.4.1.3807.2.1619.2.8.1.1	 
   		wriPimComponentInstance OBJECT-TYPE
			SYNTAX INTEGER 
			MAX-ACCESS read-only
			STATUS current
			DESCRIPTION
				"vpn instance id"
			::= { wriPimComponentEntry 1 }
   			
		-- 1.3.6.1.4.1.3807.2.1619.2.8.1.2
		wriPimComponentScopeGroup OBJECT-TYPE
			SYNTAX Integer32 (1..255)
			MAX-ACCESS read-only
			STATUS current
			DESCRIPTION
				"A number uniquely identifying the component.  Each protocol
				instance connected to a separate domain should have a
				different index value.  Routers that only support membership
				in a single PIM-SM domain should use a pimComponentIndex
				value of 1."
			::= { wriPimComponentEntry 2 }

		
		-- 1.3.6.1.4.1.3807.2.1619.2.8.1.3
		wriPimComponentScopeMasklen OBJECT-TYPE
			SYNTAX Integer32
			MAX-ACCESS read-only
			STATUS current
			DESCRIPTION
				"Description."
			::= { wriPimComponentEntry 3}

		
		-- 1.3.6.1.4.1.3807.2.1619.2.8.1.4
		wriPimComponentId OBJECT-TYPE
			SYNTAX Integer32
			MAX-ACCESS read-only
			STATUS current
			DESCRIPTION
				"Description."
			::= { wriPimComponentEntry 4 }

		
		-- 1.3.6.1.4.1.3807.2.1619.2.8.1.5
		wriPimComponentElectedBSRAddress OBJECT-TYPE
			SYNTAX IpAddress
			MAX-ACCESS read-only
			STATUS current
			DESCRIPTION
				"The IP address of the bootstrap router (BSR) for the local
				PIM region."
			::= { wriPimComponentEntry 5 }

		
		-- 1.3.6.1.4.1.3807.2.1619.2.8.1.6
		wriPimComponentElectedBSRPriority OBJECT-TYPE
			SYNTAX INTEGER (0..255)
			MAX-ACCESS read-only
			STATUS current
			DESCRIPTION
				"The BSR priority of elected bsr."
			::= { wriPimComponentEntry 6 }

		
		-- 1.3.6.1.4.1.3807.2.1619.2.8.1.7
		wriPimComponentElectedBSRHashMaskLen OBJECT-TYPE
			SYNTAX INTEGER (1..32)
			MAX-ACCESS read-only
	        STATUS current
			DESCRIPTION
				"The BSR hash mask lenth  of elected bsr,the hash mask 
				lenth used to find rp for a group."
			::= { wriPimComponentEntry 7}

		
		-- 1.3.6.1.4.1.3807.2.1619.2.8.1.8
		wriPimComponentBSRExpiryTime OBJECT-TYPE
			SYNTAX Unsigned32
			MAX-ACCESS read-only
			STATUS current
			DESCRIPTION
				"The minimum time remaining before the bootstrap router in
				the local domain will be declared down.  For candidate BSRs,
				this is the time until the component sends an RP-Set
				message.  For other routers, this is the time until it may
				accept an RP-Set message from a lower candidate BSR."
			::= { wriPimComponentEntry 8 }

		
		-- 1.3.6.1.4.1.3807.2.1619.2.8.1.9
		wriPimComponentStatus OBJECT-TYPE
			SYNTAX RowStatus
			MAX-ACCESS read-create
			STATUS current
			DESCRIPTION
				"The status of this entry.	Creating the entry creates
				another protocol instance; destroying the entry disables a
				protocol instance."
			::= { wriPimComponentEntry 9 }

		
		-- 1.3.6.1.4.1.3807.2.1619.2.8.1.10
		wriPimComponentCandidateBSRAddress OBJECT-TYPE
			SYNTAX IpAddress
			MAX-ACCESS read-create
			STATUS current
			DESCRIPTION
				"The IP address of the candidate bootstrap router (BSR) for the local
				PIM region."
			::= { wriPimComponentEntry 10 }

		
		-- 1.3.6.1.4.1.3807.2.1619.2.8.1.11
		wriPimComponentCandidateBSRPriority OBJECT-TYPE
			SYNTAX INTEGER (0..255)
			MAX-ACCESS read-create
			STATUS current
			DESCRIPTION
				"The BSR priority of candidate local bsr."
			::= { wriPimComponentEntry 11 }

		
		-- 1.3.6.1.4.1.3807.2.1619.2.8.1.12
		wriPimComponentCandidateBSRHashMaskLen OBJECT-TYPE
			SYNTAX INTEGER (1..32)
			MAX-ACCESS read-create
			STATUS current
			DESCRIPTION
				"The BSR hash mask lenth  of local candidate bsr,the hash mask 
				lenth used to find rp for a group."
			::= { wriPimComponentEntry 12 }

		
		-- 1.3.6.1.4.1.3807.2.1619.2.8.1.13
		wriPimComponentCandidateBSRState OBJECT-TYPE
			SYNTAX TruthValue
			MAX-ACCESS read-write
			STATUS current
			DESCRIPTION
				"Description."
			::= { wriPimComponentEntry 13 }
         
        -- 1.3.6.1.4.1.3807.2.1619.2.8.1.14 
		wriPimComponentBSRUpdateTime OBJECT-TYPE
			SYNTAX INTEGER
			MAX-ACCESS read-write
			STATUS current
			DESCRIPTION
				"Description."
			::= { wriPimComponentEntry 14 }

		-- 1.3.6.1.4.1.3807.2.1619.2.8.1.15
		wriPimComponentElectedBSRFragmentTag OBJECT-TYPE
			SYNTAX INTEGER
			MAX-ACCESS read-write
			STATUS current
			DESCRIPTION
				"Description."
			::= { wriPimComponentEntry 15 }

        -- 1.3.6.1.4.1.3807.2.1619.2.8.1.16                                   
		wriPimComponentElectedBSRState	OBJECT-TYPE
			SYNTAX TruthValue
			MAX-ACCESS read-write
			STATUS current
			DESCRIPTION
				"Description."
			::= { wriPimComponentEntry 16 }
											
		-- 1.3.6.1.4.1.3807.2.1619.2.9
		wriPimIgmpMemberTable OBJECT-TYPE
			SYNTAX SEQUENCE OF WriPimIgmpMemberEntry
			MAX-ACCESS not-accessible
			STATUS current
			DESCRIPTION
				"Description."
			::= { wriPimTables 9 }

		
		-- 1.3.6.1.4.1.3807.2.1619.2.9.1
		wriPimIgmpMemberEntry OBJECT-TYPE
			SYNTAX WriPimIgmpMemberEntry
			MAX-ACCESS not-accessible
			STATUS current
			DESCRIPTION
				"Description."
			INDEX { wriPimIgmpMemberIfAddress, wriPimIgmpMemberGroup, wriPimIgmpMemberSource, wriPimIgmpMemberPort }
			::= { wriPimIgmpMemberTable 1 }

		
		WriPimIgmpMemberEntry ::=
			SEQUENCE { 
				wriPimIgmpMemberIfAddress
					IpAddress,
				wriPimIgmpMemberGroup
					IpAddress,
				wriPimIgmpMemberSource
					IpAddress,
				wriPimIgmpMemberPort
					INTEGER,
				wriPimIgmpMemberStatus
					RowStatus
			 }

		-- 1.3.6.1.4.1.3807.2.1619.2.9.1.1
		wriPimIgmpMemberIfAddress OBJECT-TYPE
			SYNTAX IpAddress
			MAX-ACCESS read-only
			STATUS current
			DESCRIPTION
				"Description."
			::= { wriPimIgmpMemberEntry 1 }

		
		-- 1.3.6.1.4.1.3807.2.1619.2.9.1.2
		wriPimIgmpMemberGroup OBJECT-TYPE
			SYNTAX IpAddress
			MAX-ACCESS read-only
			STATUS current
			DESCRIPTION
				"Description."
			::= { wriPimIgmpMemberEntry 2 }

		
		-- 1.3.6.1.4.1.3807.2.1619.2.9.1.3
		wriPimIgmpMemberSource OBJECT-TYPE
			SYNTAX IpAddress
			MAX-ACCESS read-only
			STATUS current
			DESCRIPTION
				"Description."
			::= { wriPimIgmpMemberEntry 3 }

		
		-- 1.3.6.1.4.1.3807.2.1619.2.9.1.4
		wriPimIgmpMemberPort OBJECT-TYPE
			SYNTAX INTEGER (1..65535)
			MAX-ACCESS read-only
			STATUS current
			DESCRIPTION
				"Description."
			::= { wriPimIgmpMemberEntry 4 }

		
		-- 1.3.6.1.4.1.3807.2.1619.2.9.1.5
		wriPimIgmpMemberStatus OBJECT-TYPE
			SYNTAX RowStatus
			MAX-ACCESS read-create
			STATUS current
			DESCRIPTION
				"Description."
			::= { wriPimIgmpMemberEntry 5 }

		
		-- 1.3.6.1.4.1.3807.2.1619.3
		wriPimTraps OBJECT IDENTIFIER ::= { pimMIB 3 }

		
		-- 1.3.6.1.4.1.3807.2.1619.3.1
		wriPimNeighborLoss NOTIFICATION-TYPE
			OBJECTS { wriPimNeighborIfIndex }
			STATUS current
			DESCRIPTION 
				"A pimNeighborLoss trap signifies the loss of an adjacency
				with a neighbor.  This trap should be generated when the
				neighbor timer expires, and the router has no other
				neighbors on the same interface with a lower IP address than
				itself."
			::= { wriPimTraps 1 }

		
	
	END

--
-- wriPim.mib
--
