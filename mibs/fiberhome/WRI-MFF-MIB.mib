--
-- mff.mib
-- MIB generated by MG-SOFT Visual MIB Builder Version 6.0  Build 88
-- Monday, December 13, 2011 at 15:25:54
--

	WRI-MFF-MIB DEFINITIONS ::= BEGIN
 
		IMPORTS
			mib-2, Integer32, Unsigned32, OBJECT-TYPE, MODULE-IDENTITY,NOTIFICATION-TYPE	
				FROM SNMPv2-SMI					
			TEXTUAL-CONVENTION, TruthValue, TimeInterval,RowStatus,
				MacAddress,PhysAddress		FROM SNMPv2-TC
			InetAddressPrefixLength,InetAddressType,
				InetPortNumber,InetAddress			FROM INET-ADDRESS-MIB
			SnmpAdminString							FROM SNMP-FRAMEWORK-MIB
    		InterfaceIndex							FROM IF-MIB
			wriProtocol			
				FROM WRI-SMI;
	

		wriMff MODULE-IDENTITY 
			LAST-UPDATED "201107211500Z"		-- July 21, 2011 at 15:00 GMT
			ORGANIZATION 
				"FiberHome Networks Systems, Inc."
			CONTACT-INFO 
				"http://www.fhn.com.cn"
			DESCRIPTION 
				" The configure of Mac-Forced Forwarding."
			::= { wriProtocol 1330 }

		

--
-- Textual conventions
--
	
--  Textual Conventions
		DisplayString ::=   OCTET STRING
		EntryStatus ::= TEXTUAL-CONVENTION
			STATUS current
			DESCRIPTION 
				"entry status."
			SYNTAX INTEGER
				{
				valid(1),
				createRequest(2),
				underCreation(3),
				invalid(4)
				}


--
-- Node definitions
--
		mffGeneral OBJECT IDENTIFIER ::= { wriMff 1 }
		mffGenStatus  OBJECT-TYPE
			SYNTAX INTEGER 
			MAX-ACCESS read-write
			STATUS current
			DESCRIPTION
				"The status of mff."
			::= { mffGeneral 1 }
			
		mffVlanInfoTable OBJECT-TYPE
			SYNTAX SEQUENCE OF MffVlanInfoEntry
			MAX-ACCESS not-accessible
			STATUS current
			DESCRIPTION
				"The table of mff on vlan."
			::= { wriMff 2 }
		
		mffVlanInfoEntry OBJECT-TYPE
			SYNTAX MffVlanInfoEntry
			MAX-ACCESS not-accessible
			STATUS current
			DESCRIPTION
				"The entry of mff on vlan."
			INDEX { mffVlanIndex   }
			::= { mffVlanInfoTable 1 }

		
		MffVlanInfoEntry ::=
			SEQUENCE { 
				mffVlanIndex 
					Integer32,
				mffVlanStatus  
					INTEGER,
				mffVlanGateDetectStatus 
					INTEGER,
				mffVlanStaticGateIpV4Addr  
					InetAddress,
				mffVlanStaticGateIpV6Addr
					InetAddress,
				mffVlanNetworkPort
					OCTET STRING,
				mffVlanFlush
				    INTEGER
				    
			 }

		mffVlanIndex OBJECT-TYPE
			SYNTAX Integer32
			MAX-ACCESS read-only
			STATUS current
			DESCRIPTION
				"The index of vid."
			::= { mffVlanInfoEntry 1 }

		mffVlanStatus OBJECT-TYPE
			SYNTAX INTEGER
			{
				enable(1),
				disable(2)
			}
			MAX-ACCESS read-write
			STATUS current
			DESCRIPTION
				"The status of mff."
			::= { mffVlanInfoEntry 2 }

		mffVlanGateDetectStatus OBJECT-TYPE
			SYNTAX INTEGER	
			{
				enable(1),
				disable(2)
			}
			MAX-ACCESS read-write
			STATUS current
			DESCRIPTION
				"The status of gateway detect mff."
			::= { mffVlanInfoEntry 3 }

		mffVlanStaticGateIpV4Addr OBJECT-TYPE
			SYNTAX InetAddress
			MAX-ACCESS read-write
			STATUS current
			DESCRIPTION
				"The static gateway ipv4 address."
			::= { mffVlanInfoEntry 4 }

		mffVlanStaticGateIpV6Addr OBJECT-TYPE
			SYNTAX InetAddress
			MAX-ACCESS read-write
			STATUS current
			DESCRIPTION
				"The static gateway ipv6 address."
			::= { mffVlanInfoEntry 5 }
		
		mffVlanNetworkPort OBJECT-TYPE
			SYNTAX OCTET STRING (SIZE(0..1024))
			MAX-ACCESS read-only
			STATUS current
			DESCRIPTION
				"The all network port of mff on vlan."
			::= { mffVlanInfoEntry 6 }
		
		mffVlanFlush OBJECT-TYPE
			SYNTAX  INTEGER
			MAX-ACCESS read-write
			STATUS current
			DESCRIPTION
				"Flush all the mff info on vlan ."
			::= { mffVlanInfoEntry 7 }
			
		mffHostInfoTable OBJECT-TYPE
			SYNTAX SEQUENCE OF MffHostInfoEntry
			MAX-ACCESS not-accessible
			STATUS current
			DESCRIPTION
				"The host table of mff."
			::= { wriMff 3 }
		
		mffHostInfoEntry OBJECT-TYPE
			SYNTAX MffHostInfoEntry
			MAX-ACCESS not-accessible
			STATUS current
			DESCRIPTION
				"The entry of host mff."
			INDEX { mffHostIpType,mffHostIpAddr}
			::= { mffHostInfoTable 1 }

		MffHostInfoEntry ::=
			SEQUENCE { 
				mffHostIpType  
					InetAddressType,
				mffHostIpAddr  
					InetAddress,
				mffHostGateIpAddr  
					OCTET STRING,
				mffHostGateMacAddr  
					MacAddress,
				mffHostUserMacAddr
					MacAddress
			 }

		mffHostIpType OBJECT-TYPE
			SYNTAX InetAddressType
			MAX-ACCESS read-only
			STATUS current
			DESCRIPTION
				"The ip type of mff host."
			::= { mffHostInfoEntry 1 }
		
		mffHostIpAddr OBJECT-TYPE
			SYNTAX InetAddress
			MAX-ACCESS read-only
			STATUS current
			DESCRIPTION
				"The ip address of mff host."
			::= { mffHostInfoEntry 2 }
			
		mffHostGateIpAddr OBJECT-TYPE
			SYNTAX OCTET STRING (SIZE(0..1024))
			MAX-ACCESS read-only
			STATUS current
			DESCRIPTION
				"The gateway ip address of mff host."
			::= { mffHostInfoEntry 3 }
			
		mffHostGateMacAddr OBJECT-TYPE
			SYNTAX MacAddress
			MAX-ACCESS read-only
			STATUS current
			DESCRIPTION
				"The gateway mac address of mff host."
			::= { mffHostInfoEntry 4 }
			
		mffHostUserMacAddr OBJECT-TYPE
			SYNTAX MacAddress
			MAX-ACCESS read-only
			STATUS current
			DESCRIPTION
				"The user mac address of mff host."
			::= { mffHostInfoEntry 5 }
			
		
		mffServerIpTable OBJECT-TYPE
			SYNTAX SEQUENCE OF MffServerIpEntry
			MAX-ACCESS not-accessible
			STATUS current
			DESCRIPTION
				"The server ip address table of mff."
			::= { wriMff 4 }
		
		mffServerIpEntry OBJECT-TYPE
			SYNTAX MffServerIpEntry
			MAX-ACCESS not-accessible
			STATUS current
			DESCRIPTION
				"The entry of server ip address table mff."
			INDEX { mffserverVlanIndex,mffserverIpType,mffserverIpAddr}
			::= { mffServerIpTable 1 }

		MffServerIpEntry ::=
			SEQUENCE { 
				mffserverVlanIndex  
					Integer32,
				mffserverIpType  
					InetAddressType,
				mffserverIpAddr  
					InetAddress,
				mffServerEntryStatus  
					EntryStatus
			 }

		mffserverVlanIndex OBJECT-TYPE
			SYNTAX Integer32
			MAX-ACCESS read-only
			STATUS current
			DESCRIPTION
				"The vlan index of mff."
			::= { mffServerIpEntry 1 }
			
		mffserverIpType OBJECT-TYPE
			SYNTAX InetAddressType
			MAX-ACCESS read-only
			STATUS current
			DESCRIPTION
				"The server ip type of mff."
			::= { mffServerIpEntry 2 }
			
		mffserverIpAddr OBJECT-TYPE
			SYNTAX InetAddress
			MAX-ACCESS read-only
			STATUS current
			DESCRIPTION
				"The server ip  address of mff."
			::= { mffServerIpEntry 3 }
		
		mffServerEntryStatus OBJECT-TYPE
			SYNTAX EntryStatus
			MAX-ACCESS read-write
			STATUS current
			DESCRIPTION
				"The entry status of server ip table ."
			::= { mffServerIpEntry 4 }
	END

--
-- mff.mib
--
