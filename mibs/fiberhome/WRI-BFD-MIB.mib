--
-- wriBfd.mib
-- MIB generated by MG-SOFT Visual MIB Builder Version 4.0 Build 349
-- Friday, June 08, 2012 at 11:17:09
--

--  wriBfd.mib
-- MIB generated by MG-SOFT Visual MIB Builder Version 4.0 Build 349
-- Thursday, May 24, 2012 at 15:15:41
-- 
--  wriBfd.mib
-- MIB generated by MG-SOFT Visual MIB Builder Version 4.0 Build 349
-- Thursday, March 15, 2012 at 09:46:24
-- 
--  wriBfd.mib
-- MIB generated by MG-SOFT Visual MIB Builder Version 4.0 Build 349
-- Tuesday, August 31, 2010 at 10:19:51
-- 

	WRI-BFD-MIB DEFINITIONS ::= BEGIN
 
		IMPORTS
			InetAddressType, InetAddress			
				FROM INET-ADDRESS-MIB			
			OBJECT-GROUP, MODULE-COMPLIANCE, NOTIFICATION-GROUP			
				FROM SNMPv2-CONF			
			mib-2, Integer32, Unsigned32, Counter32, Counter64, 
			OBJECT-TYPE, MODULE-IDENTITY, NOTIFICATION-TYPE			
				FROM SNMPv2-SMI			
			TruthValue, StorageType, RowStatus, TimeStamp, TEXTUAL-CONVENTION			
				FROM SNMPv2-TC			
			wriProtocol			
				FROM WRI-SMI;
	
	
--    1.3.6.1.4.1.3807.2.240
-- June 26, 2009 at 12:00 GMT
-- 1.3.6.1.4.1.3807.2.240
-- June 26, 2009 at 12:00 GMT
-- June 26, 2009 at 12:00 GMT
		wriBfd MODULE-IDENTITY 
			LAST-UPDATED "200906261200Z"		-- June 26, 2009 at 12:00 GMT
			ORGANIZATION 
				"FiberHome Networks Systems, Inc."
			CONTACT-INFO 
				"http://www.fhn.com.cn"
			DESCRIPTION 
				"Bidirectional Forwarding Management Information Base."
			::= { wriProtocol 240 }

		
	
--
-- Textual conventions
--
	
--  Textual conventions
-- 
-- Textual conventions
-- 
-- Textual conventions
-- 
		BfdSessIndexTC ::= TEXTUAL-CONVENTION
			DISPLAY-HINT 
				"d"
			STATUS current
			DESCRIPTION 
				"An index used to uniquely identify BFD sessions."
			SYNTAX Unsigned32 (1..255)

		BfdDiag ::= TEXTUAL-CONVENTION
			STATUS current
			DESCRIPTION 
				"A common BFD diagnostic code."
			SYNTAX INTEGER
				{
				noDiagnostic(0),
				controlDetectionTimeExpired(1),
				echoFunctionFailed(2),
				neighborSignaledSessionDown(3),
				forwardingPlaneReset(4),
				pathDown(5),
				concatenatedPathDown(6),
				administrativelyDown(7),
				reverseConcatenatedPathDown(8)
				}

		BfdMultiplier ::= TEXTUAL-CONVENTION
			DISPLAY-HINT 
				"d"
			STATUS current
			DESCRIPTION 
				"The BFD failure detection multiplier."
			SYNTAX Unsigned32 (3..50)

	
--
-- Node definitions
--
	
--  Node definitions
-- 
-- Node definitions
-- 
-- Node definitions
-- 
-- 1.3.6.1.4.1.3807.2.240.0
-- 1.3.6.1.4.1.3807.2.240.0
		bfdNotifications OBJECT IDENTIFIER ::= { wriBfd 0 }

		
--    1.3.6.1.4.1.3807.2.240.0.1
-- 1.3.6.1.4.1.3807.2.240.0.1
		bfdSessUp NOTIFICATION-TYPE
			OBJECTS { bfdSessDiag, bfdSessDiag }
			STATUS current
			DESCRIPTION 
				"This notification is generated when the
				bfdSessState object for one or more contiguous
				entries in bfdSessTable are about to enter the up(4)
				state from some other state. The included values of
				bfdSessDiag MUST both be set equal to this
				new state (i.e: up(4)).  The two instances of
				bfdSessDiag in this notification indicate the range
				of indexes that are affected.  Note that all the indexes
				of the two ends of the range can be derived from the
				instance identifiers of these two objects.  For the
				cases where a contiguous range of sessions
				have transitioned into the up(4) state at roughly
				the same time, the device SHOULD issue a single
				notification for each range of contiguous indexes in
				an effort to minimize the emission of a large number
				of notifications.  If a notification has to be
				issued for just a single bfdSessEntry, then
				the instance identifier (and values) of the two
				bfdSessDiag objects MUST be the identical."
			::= { bfdNotifications 1 }

		
--    1.3.6.1.4.1.3807.2.240.0.2
-- 1.3.6.1.4.1.3807.2.240.0.2
		bfdSessDown NOTIFICATION-TYPE
			OBJECTS { bfdSessDiag, bfdSessDiag }
			STATUS current
			DESCRIPTION 
				"This notification is generated when the
				bfdSessState object for one or more contiguous
				entries in bfdSessTable are about to enter the down(2)
				or adminDown(1) states from some other state. The included
				values of bfdSessDiag MUST both be set equal to this new
				state (i.e: down(2) or adminDown(1)).  The two instances
				of bfdSessDiag in this notification indicate the range
				of indexes that are affected.  Note that all the indexes
				of the two ends of the range can be derived from the
				instance identifiers of these two objects.  For
				cases where a contiguous range of sessions
				have transitioned into the down(2) or adminDown(1) states
				at roughly the same time, the device SHOULD issue a single
				notification for each range of contiguous indexes in
				an effort to minimize the emission of a large number
				of notifications.  If a notification has to be
				issued for just a single bfdSessEntry, then
				the instance identifier (and values) of the two
				bfdSessDiag objects MUST be the identical."
			::= { bfdNotifications 2 }

		
--    1.3.6.1.4.1.3807.2.240.1
-- 1.3.6.1.4.1.3807.2.240.1
		bfdObjects OBJECT IDENTIFIER ::= { wriBfd 1 }

		
--    1.3.6.1.4.1.3807.2.240.1.1
-- 1.3.6.1.4.1.3807.2.240.1.1
		bfdScalarObjects OBJECT IDENTIFIER ::= { bfdObjects 1 }

		
--    1.3.6.1.4.1.3807.2.240.1.1.1
-- 1.3.6.1.4.1.3807.2.240.1.1.1
		bfdAdminStatus OBJECT-TYPE
			SYNTAX INTEGER
				{
				enabled(1),
				disabled(2)
				}
			MAX-ACCESS read-write
			STATUS current
			DESCRIPTION
				"The global administrative status of BFD in this router.
				The value 'enabled' denotes that the BFD Process is
				active on at least one interface; 'disabled' disables
				it on all interfaces."
			DEFVAL { enabled }
			::= { bfdScalarObjects 1 }

		
--    1.3.6.1.4.1.3807.2.240.1.1.2
-- 1.3.6.1.4.1.3807.2.240.1.1.2
		bfdVersionNumber OBJECT-TYPE
			SYNTAX Unsigned32
			MAX-ACCESS read-only
			STATUS current
			DESCRIPTION
				"The current version number of the BFD protocol."
			REFERENCE
				"BFD Version 0 (draft-katz-ward-bfd-02.txt)"
			DEFVAL { 1 }
			::= { bfdScalarObjects 2 }

		
--    1.3.6.1.4.1.3807.2.240.1.1.3
-- 1.3.6.1.4.1.3807.2.240.1.1.3
		bfdTrapEnable OBJECT-TYPE
			SYNTAX INTEGER
				{
				enable(1),
				disable(2)
				}
			MAX-ACCESS read-write
			STATUS current
			DESCRIPTION
				"Enable or disable bfd session up|down trap"
			::= { bfdScalarObjects 3 }

--    1.3.6.1.4.1.3807.2.240.1.1.4
-- 1.3.6.1.4.1.3807.2.240.1.1.4
		bfdProcessStatus OBJECT-TYPE
			SYNTAX INTEGER
				{
				enable(1),
				disable(2)
				}
			MAX-ACCESS read-write
			STATUS current
			DESCRIPTION
				"Enable or disable process interface status"
			::= { bfdScalarObjects 4 }

		
--    1.3.6.1.4.1.3807.2.240.1.2
-- 1.3.6.1.4.1.3807.2.240.1.2
		bfdSessTable OBJECT-TYPE
			SYNTAX SEQUENCE OF BfdSessEntry
			MAX-ACCESS not-accessible
			STATUS current
			DESCRIPTION
				"The BFD Session Table describes the BFD sessions."
			REFERENCE
				"BFD Version 0 (draft-katz-ward-bfd-02.txt) and
				BFD Version 1 (draft-ietf-bfd-base-08.txt)"
			::= { bfdObjects 2 }

		
--    1.3.6.1.4.1.3807.2.240.1.2.1
-- 1.3.6.1.4.1.3807.2.240.1.2.1
		bfdSessEntry OBJECT-TYPE
			SYNTAX BfdSessEntry
			MAX-ACCESS not-accessible
			STATUS current
			DESCRIPTION
				"The BFD Session Entry describes BFD session."
			INDEX { bfdSessIndex }
			::= { bfdSessTable 1 }

		
		BfdSessEntry ::=
			SEQUENCE { 
				bfdSessIndex
					BfdSessIndexTC,
				bfdSessType
					INTEGER,
				bfdSessRole
					INTEGER,
				bfdSessDiscriminator
					Unsigned32,
				bfdSessRemoteDiscr
					Unsigned32,
				bfdSessUdpPort
					INTEGER,
				bfdSessAdminStatus
					INTEGER,
				bfdSessState
					INTEGER,
				bfdSessRemoteHeardFlag
					TruthValue,
				bfdSessDiag
					BfdDiag,
				bfdSessOperMode
					INTEGER,
				bfdSessDemandModeDesiredFlag
					TruthValue,
				bfdSessEchoFuncModeDesiredFlag
					TruthValue,
				bfdSessControlPlaneIndepFlag
					TruthValue,
				bfdSessInterface
					Unsigned32,
				bfdSessAddrType
					InetAddressType,
				bfdSessAddr
					InetAddress,
				bfdSessDesiredMinTxInterval
					Unsigned32,
				bfdSessReqMinRxInterval
					Unsigned32,
				bfdSessReqMinEchoRxInterval
					Unsigned32,
				bfdSessDetectMult
					BfdMultiplier,
				bfdSessAuthPresFlag
					TruthValue,
				bfdSessAuthenticationType
					INTEGER,
				bfdSessAuthenticationKeyID
					Integer32,
				bfdSessAuthenticationKey
					OCTET STRING,
				bfdSessStorType
					StorageType,
				bfdSessRowStatus
					RowStatus,
				bfdSessVersionNumber
					Unsigned32,
				bfdSessRemoteAddr
					InetAddress,
				bfdSessNegotiateInterval
					Integer32,
				bfdSessNegotiateEchoInterval
					Integer32,
				bfdSessNegotiateMultiplier
					Integer32
			 }

--    1.3.6.1.4.1.3807.2.240.1.2.1.1
-- 1.3.6.1.4.1.3807.2.240.1.2.1.1
		bfdSessIndex OBJECT-TYPE
			SYNTAX BfdSessIndexTC
			MAX-ACCESS read-only
			STATUS current
			DESCRIPTION
				"This object contains an index used to represent a
				unique BFD session on this device."
			::= { bfdSessEntry 1 }

		
--    1.3.6.1.4.1.3807.2.240.1.2.1.2
-- 1.3.6.1.4.1.3807.2.240.1.2.1.2
		bfdSessType OBJECT-TYPE
			SYNTAX INTEGER
				{
				singleHop(1),
				multiHop(2)
				}
			MAX-ACCESS read-only
			STATUS current
			DESCRIPTION
				"The type of this BFD session."
			DEFVAL { singleHop }
			::= { bfdSessEntry 2 }

		
--    1.3.6.1.4.1.3807.2.240.1.2.1.3
-- 1.3.6.1.4.1.3807.2.240.1.2.1.3
		bfdSessRole OBJECT-TYPE
			SYNTAX INTEGER
				{
				none(1),
				active(2),
				passive(3)
				}
			MAX-ACCESS read-only
			STATUS current
			DESCRIPTION
				"For bfdSessType, this object specifies whether 
				this BFD session is running in active(1) mode or 
				passive(2) mode."
			::= { bfdSessEntry 3 }

		
--    1.3.6.1.4.1.3807.2.240.1.2.1.4
-- 1.3.6.1.4.1.3807.2.240.1.2.1.4
		bfdSessDiscriminator OBJECT-TYPE
			SYNTAX Unsigned32 (1..4294967295)
			MAX-ACCESS read-only
			STATUS current
			DESCRIPTION
				"This object specifies the local discriminator for this BFD
				session, used to uniquely identify it."
			::= { bfdSessEntry 4 }

		
--    1.3.6.1.4.1.3807.2.240.1.2.1.5
-- 1.3.6.1.4.1.3807.2.240.1.2.1.5
		bfdSessRemoteDiscr OBJECT-TYPE
			SYNTAX Unsigned32 (1..4294967295)
			MAX-ACCESS read-only
			STATUS current
			DESCRIPTION
				"This object specifies the session discriminator chosen
				by the remote system for this BFD session.  The value may
				be zero(0) if the remote discriminator is not yet known
				or if the session is in the down or adminDown(1) state."
			REFERENCE
				"draft-ietf-bfd-base-08, Section 6.8.6."
			::= { bfdSessEntry 5 }

		
--    1.3.6.1.4.1.3807.2.240.1.2.1.6
-- 1.3.6.1.4.1.3807.2.240.1.2.1.6
		bfdSessUdpPort OBJECT-TYPE
			SYNTAX INTEGER
			MAX-ACCESS read-only
			STATUS current
			DESCRIPTION
				"The destination UDP Port for BFD."
			REFERENCE
				"Port 3784 (draft-ietf-bfd-v4v6-1hop-08),
				Port 3785 (draft-ietf-bfd-v4v6-1hop-08), and
				Port 4784 (draft-ietf-bfd-multihop-06)"
			DEFVAL { 0 }
			::= { bfdSessEntry 6 }

		
--    1.3.6.1.4.1.3807.2.240.1.2.1.7
-- 1.3.6.1.4.1.3807.2.240.1.2.1.7
		bfdSessAdminStatus OBJECT-TYPE
			SYNTAX INTEGER
				{
				stop(1),
				start(2)
				}
			MAX-ACCESS read-only
			STATUS current
			DESCRIPTION
				"A transition from 'stop' to 'start' will start
				the BFD state machine for the session. The state
				machine will have an initial state of down.
				A transition from 'start' to 'stop' will cause
				the BFD sesssion to be brought down to
				adminDown(1). Care should be used in providing
				write access to this object without adequate
				authentication."
			DEFVAL { 2 }
			::= { bfdSessEntry 7 }

		
--    1.3.6.1.4.1.3807.2.240.1.2.1.8
-- 1.3.6.1.4.1.3807.2.240.1.2.1.8
		bfdSessState OBJECT-TYPE
			SYNTAX INTEGER
				{
				adminDown(1),
				down(2),
				init(3),
				up(4),
				failing(5)
				}
			MAX-ACCESS read-only
			STATUS current
			DESCRIPTION
				"The perceived state of the BFD session.
				BFD State failing(5) is only applicable if this BFD
				session is running version 0.
				Upon creation of a new BFD session via this MIB, the
				suggested initial state is down(2)."
			DEFVAL { 2 }
			::= { bfdSessEntry 8 }

		
--    1.3.6.1.4.1.3807.2.240.1.2.1.9
-- 1.3.6.1.4.1.3807.2.240.1.2.1.9
		bfdSessRemoteHeardFlag OBJECT-TYPE
			SYNTAX TruthValue
			MAX-ACCESS read-only
			STATUS current
			DESCRIPTION
				"This object specifies status of BFD packet reception from
				the remote system. Specifically, it is set to true(1) if
				the local system is actively receiving BFD packets from the
				remote system, and is set to false(2) if the local system
				has not received BFD packets recently (within the detection
				time) or if the local system is attempting to tear down
				the BFD session."
			REFERENCE
				"BFD Version 0 (draft-katz-ward-bfd-02.txt) and
				BFD Version 1 (draft-ietf-bfd-base-08.txt)"
			DEFVAL { false }
			::= { bfdSessEntry 9 }

		
--    1.3.6.1.4.1.3807.2.240.1.2.1.10
-- 1.3.6.1.4.1.3807.2.240.1.2.1.10
		bfdSessDiag OBJECT-TYPE
			SYNTAX BfdDiag
			MAX-ACCESS read-only
			STATUS current
			DESCRIPTION
				"A diagnostic code specifying the local system's reason
				for the last transition of the session from up(4)
				to some other state."
			::= { bfdSessEntry 10 }

		
--    1.3.6.1.4.1.3807.2.240.1.2.1.11
-- 1.3.6.1.4.1.3807.2.240.1.2.1.11
		bfdSessOperMode OBJECT-TYPE
			SYNTAX INTEGER
				{
				asyncWithEcho(1),
				asyncWithoutEcho(2),
				demandWithEcho(3),
				demandWithoutEcho(4)
				}
			MAX-ACCESS read-only
			STATUS current
			DESCRIPTION
				"This object specifies current operating mode that BFD
				session is operating in."
			::= { bfdSessEntry 11 }

		
--    1.3.6.1.4.1.3807.2.240.1.2.1.12
-- 1.3.6.1.4.1.3807.2.240.1.2.1.12
		bfdSessDemandModeDesiredFlag OBJECT-TYPE
			SYNTAX TruthValue
			MAX-ACCESS read-only
			STATUS current
			DESCRIPTION
				"This object indicates that the local system's
				desire to use Demand mode. Specifically, it is set
				to true(1) if the local system wishes to use
				Demand mode or false(2) if not"
			DEFVAL { false }
			::= { bfdSessEntry 12 }

		
--    1.3.6.1.4.1.3807.2.240.1.2.1.13
-- 1.3.6.1.4.1.3807.2.240.1.2.1.13
		bfdSessEchoFuncModeDesiredFlag OBJECT-TYPE
			SYNTAX TruthValue
			MAX-ACCESS read-only
			STATUS current
			DESCRIPTION
				"This object indicates that the local system's
				desire to use Echo mode. Specifically, it is set  
				to true(1) if the local system wishes to use  
				Echo mode or false(2) if not"
			DEFVAL { false }
			::= { bfdSessEntry 13 }

		
--    1.3.6.1.4.1.3807.2.240.1.2.1.14
-- 1.3.6.1.4.1.3807.2.240.1.2.1.14
		bfdSessControlPlaneIndepFlag OBJECT-TYPE
			SYNTAX TruthValue
			MAX-ACCESS read-only
			STATUS current
			DESCRIPTION
				"This object indicates that the local system's
				ability to continue to function through a disruption of
				the control plane. Specifically, it is set
				to true(1) if the local system BFD implementation is
				independent of the control plane. Otherwise, the
				value is set to false(2)"
			DEFVAL { false }
			::= { bfdSessEntry 14 }

		
--    1.3.6.1.4.1.3807.2.240.1.2.1.15
-- 1.3.6.1.4.1.3807.2.240.1.2.1.15
		bfdSessInterface OBJECT-TYPE
			SYNTAX Unsigned32
			MAX-ACCESS read-only
			STATUS current
			DESCRIPTION
				"This object contains an interface index used to indicate
				the interface which this BFD session is running on. This
				value can be zero if there is no interface associated
				with this BFD session."
			::= { bfdSessEntry 15 }

		
--    1.3.6.1.4.1.3807.2.240.1.2.1.16
-- 1.3.6.1.4.1.3807.2.240.1.2.1.16
		bfdSessAddrType OBJECT-TYPE
			SYNTAX InetAddressType
			MAX-ACCESS read-only
			STATUS current
			DESCRIPTION
				"This object specifies IP address type of the neighboring IP
				address which is being monitored with this BFD session.
				
				Only values unknown(0), ipv4(1), ipv6(2), or ipv6z(4)
				have to be supported.
				
				A value of unknown(0) is allowed only when
				the outgoing interface is of type point-to-point, or
				when the BFD session is not associated with a specific
				interface.
				
				If any other unsupported values are attempted in a set
				operation, the agent MUST return an inconsistentValue
				error."
			::= { bfdSessEntry 16 }

		
--    1.3.6.1.4.1.3807.2.240.1.2.1.17
-- 1.3.6.1.4.1.3807.2.240.1.2.1.17
		bfdSessAddr OBJECT-TYPE
			SYNTAX InetAddress
			MAX-ACCESS read-only
			STATUS current
			DESCRIPTION
				"This object specifies the neighboring IP address which is
				being monitored with this BFD session.
				It can also be used to enabled BFD on a specific
				interface. The value is set to zero when BFD session is not
				associated with a specific interface."
			::= { bfdSessEntry 17 }

		
--    1.3.6.1.4.1.3807.2.240.1.2.1.18
-- 1.3.6.1.4.1.3807.2.240.1.2.1.18
		bfdSessDesiredMinTxInterval OBJECT-TYPE
			SYNTAX Unsigned32 (50..999)
			MAX-ACCESS read-only
			STATUS current
			DESCRIPTION
				"This object specifies the minimum interval, in
				microseconds, that the local system would like to use when
				transmitting BFD Control packets."
			::= { bfdSessEntry 18 }

		
--    1.3.6.1.4.1.3807.2.240.1.2.1.19
-- 1.3.6.1.4.1.3807.2.240.1.2.1.19
		bfdSessReqMinRxInterval OBJECT-TYPE
			SYNTAX Unsigned32 (1..999)
			MAX-ACCESS read-only
			STATUS current
			DESCRIPTION
				"This object specifies the minimum interval, in
				microseconds, between received  BFD Control packets the
				local system is capable of supporting."
			::= { bfdSessEntry 19 }

		
--    1.3.6.1.4.1.3807.2.240.1.2.1.20
-- 1.3.6.1.4.1.3807.2.240.1.2.1.20
		bfdSessReqMinEchoRxInterval OBJECT-TYPE
			SYNTAX Unsigned32 (0..999)
			MAX-ACCESS read-only
			STATUS current
			DESCRIPTION
				"This object specifies the minimum interval, in
				microseconds, between received BFD Echo packets that this
				system is capable of supporting."
			::= { bfdSessEntry 20 }

		
--    1.3.6.1.4.1.3807.2.240.1.2.1.21
-- 1.3.6.1.4.1.3807.2.240.1.2.1.21
		bfdSessDetectMult OBJECT-TYPE
			SYNTAX BfdMultiplier
			MAX-ACCESS read-only
			STATUS current
			DESCRIPTION
				"This object specifies the Detect time multiplier."
			::= { bfdSessEntry 21 }

		
--    1.3.6.1.4.1.3807.2.240.1.2.1.22
-- 1.3.6.1.4.1.3807.2.240.1.2.1.22
		bfdSessAuthPresFlag OBJECT-TYPE
			SYNTAX TruthValue
			MAX-ACCESS read-only
			STATUS current
			DESCRIPTION
				"This object indicates that the local system's
				desire to use Authentication. Specifically, it is set
				to true(1) if the local system wishes the session
				to be authenticated or false(2) if not."
			REFERENCE
				"draft-ietf-bfd-base-08, Sections 4.2 - 4.4"
			DEFVAL { false }
			::= { bfdSessEntry 22 }

		
--    1.3.6.1.4.1.3807.2.240.1.2.1.23
-- 1.3.6.1.4.1.3807.2.240.1.2.1.23
		bfdSessAuthenticationType OBJECT-TYPE
			SYNTAX INTEGER
				{
				reserved(0),
				simplePassword(1),
				keyedMD5(2),
				meticulousKeyedMD5(3),
				keyedSHA1(4),
				meticulousKeyedSHA1(5)
				}
			MAX-ACCESS read-only
			STATUS current
			DESCRIPTION
				"The Authentication Type used for this BFD session.
				This field is valid only when the Authentication
				Present bit is set."
			REFERENCE
				"draft-ietf-bfd-base-08, Sections 4.2 - 4.4"
			::= { bfdSessEntry 23 }

		
--    1.3.6.1.4.1.3807.2.240.1.2.1.24
-- 1.3.6.1.4.1.3807.2.240.1.2.1.24
		bfdSessAuthenticationKeyID OBJECT-TYPE
			SYNTAX Integer32 (-1 | 0..255)
			MAX-ACCESS read-only
			STATUS current
			DESCRIPTION
				"The authentication key ID in use for this session.  This
				object permits multiple keys to be active simultaneously.
				
				When bfdSessAuthPresFlag is false(2), then the value
				of this object MUST be -1.  The value -1 indicates that
				no Authentication Key ID will be present in the optional
				BFD Authentication Section."
			REFERENCE
				"draft-ietf-bfd-base-08, Sections 4.2 - 4.4"
			DEFVAL { -1 }
			::= { bfdSessEntry 24 }

		
--    1.3.6.1.4.1.3807.2.240.1.2.1.25
-- 1.3.6.1.4.1.3807.2.240.1.2.1.25
		bfdSessAuthenticationKey OBJECT-TYPE
			SYNTAX OCTET STRING
			MAX-ACCESS read-only
			STATUS current
			DESCRIPTION
				"The authentication key.  When the
				bfdSessAuthenticationType is simplePassword(1), the value
				of this object is the password present in the BFD packets.
				
				When the bfdSessAuthentication type is one of the keyed
				authentication types, this value is used in the
				computation of the key present in the BFD authentication
				packet."
			REFERENCE
				"draft-ietf-bfd-base-08, Sections 4.2 - 4.4"
			::= { bfdSessEntry 25 }

		
--    1.3.6.1.4.1.3807.2.240.1.2.1.26
-- 1.3.6.1.4.1.3807.2.240.1.2.1.26
		bfdSessStorType OBJECT-TYPE
			SYNTAX StorageType
			MAX-ACCESS read-only
			STATUS current
			DESCRIPTION
				"This variable indicates the storage type for this
				object. Conceptual rows having the value
				'permanent' need not allow write-access to any
				columnar objects in the row."
			::= { bfdSessEntry 26 }

		
--    1.3.6.1.4.1.3807.2.240.1.2.1.27
-- 1.3.6.1.4.1.3807.2.240.1.2.1.27
		bfdSessRowStatus OBJECT-TYPE
			SYNTAX RowStatus
			MAX-ACCESS read-write
			STATUS current
			DESCRIPTION
				"This variable is used to create, modify, and/or
				delete a row in this table. When a row in this
				table has a row in the active(1) state, no
				objects in this row can be modified except the
				bfdSessRowStatus and bfdSessStorageType.
				-- by setting this object to createAndGo(4) -- and 
				suspension of an active conceptual row is not
				supported.  Consequently, setting this object to
				createAndWait(5) or notInService(2) SHALL fail.
				
				Setting this object to destroy(6) SHALL fail if the
				corresponding Spanning Tree instance has one or more
				FIDs allocated.
				
				Refer to the RowStatus convention for further details on 
				the behavior of this object."
			::= { bfdSessEntry 27 }

		
--    1.3.6.1.4.1.3807.2.240.1.2.1.28
-- 1.3.6.1.4.1.3807.2.240.1.2.1.28
		bfdSessVersionNumber OBJECT-TYPE
			SYNTAX Unsigned32
			MAX-ACCESS read-only
			STATUS current
			DESCRIPTION
				"The current version number of the BFD protocol."
			REFERENCE
				"BFD Version 0 (draft-katz-ward-bfd-02.txt)"
			DEFVAL { 1 }
			::= { bfdSessEntry 28 }

		
		-- 1.3.6.1.4.1.3807.2.240.1.2.1.29
		bfdSessRemoteAddr OBJECT-TYPE
			SYNTAX InetAddress
			MAX-ACCESS read-only
			STATUS current
			DESCRIPTION
				"Description."
			::= { bfdSessEntry 29 }

		
		-- 1.3.6.1.4.1.3807.2.240.1.2.1.30
		bfdSessNegotiateInterval OBJECT-TYPE
			SYNTAX Integer32
			MAX-ACCESS read-create
			STATUS current
			DESCRIPTION
				"Description."
			::= { bfdSessEntry 30 }

		
		-- 1.3.6.1.4.1.3807.2.240.1.2.1.31
		bfdSessNegotiateEchoInterval OBJECT-TYPE
			SYNTAX Integer32
			MAX-ACCESS read-only
			STATUS current
			DESCRIPTION
				"Description."
			::= { bfdSessEntry 31 }

		
		-- 1.3.6.1.4.1.3807.2.240.1.2.1.32
		bfdSessNegotiateMultiplier OBJECT-TYPE
			SYNTAX Integer32
			MAX-ACCESS read-only
			STATUS current
			DESCRIPTION
				"Description."
			::= { bfdSessEntry 32 }
-- 1.3.6.1.4.1.3807.2.240.1.3
		bfdSessPerfTable OBJECT-TYPE
			SYNTAX SEQUENCE OF BfdSessPerfEntry
			MAX-ACCESS not-accessible
			STATUS current
			DESCRIPTION
				"This table specifies BFD Session performance counters."
			::= { bfdObjects 3 }

		
--    1.3.6.1.4.1.3807.2.240.1.3.1
-- 1.3.6.1.4.1.3807.2.240.1.3.1
		bfdSessPerfEntry OBJECT-TYPE
			SYNTAX BfdSessPerfEntry
			MAX-ACCESS not-accessible
			STATUS current
			DESCRIPTION
				"An entry in this table is created by a BFD-enabled node for
				every BFD Session. bfdCounterDiscontinuityTime is used to
				indicate potential discontinuity for all counter objects
				in this table."
			AUGMENTS { bfdSessEntry }
			::= { bfdSessPerfTable 1 }

		
		BfdSessPerfEntry ::=
			SEQUENCE { 
				bfdSessPerfPktIn
					Counter32,
				bfdSessPerfPktOut
					Counter32,
				bfdSessUpTime
					TimeStamp,
				bfdSessPerfLastSessDownTime
					TimeStamp,
				bfdSessPerfLastCommLostDiag
					BfdDiag,
				bfdSessPerfSessUpCount
					Counter32,
				bfdSessPerfDiscTime
					TimeStamp,
				bfdSessPerfPktInHC
					Counter64,
				bfdSessPerfPktOutHC
					Counter64
			 }

--    1.3.6.1.4.1.3807.2.240.1.3.1.1
-- 1.3.6.1.4.1.3807.2.240.1.3.1.1
		bfdSessPerfPktIn OBJECT-TYPE
			SYNTAX Counter32
			MAX-ACCESS read-only
			STATUS current
			DESCRIPTION
				"The total number of BFD messages received for this BFD
				session."
			::= { bfdSessPerfEntry 1 }

		
--    1.3.6.1.4.1.3807.2.240.1.3.1.2
-- 1.3.6.1.4.1.3807.2.240.1.3.1.2
		bfdSessPerfPktOut OBJECT-TYPE
			SYNTAX Counter32
			MAX-ACCESS read-only
			STATUS current
			DESCRIPTION
				"The total number of BFD messages sent for this BFD
				session."
			::= { bfdSessPerfEntry 2 }

		
--    1.3.6.1.4.1.3807.2.240.1.3.1.3
-- 1.3.6.1.4.1.3807.2.240.1.3.1.3
		bfdSessUpTime OBJECT-TYPE
			SYNTAX TimeStamp
			MAX-ACCESS read-only
			STATUS current
			DESCRIPTION
				"The value of sysUpTime on the most recent occasion at which
				the session came up. If no such up event exists this object
				contains a zero value."
			::= { bfdSessPerfEntry 3 }

		
--    1.3.6.1.4.1.3807.2.240.1.3.1.4
-- 1.3.6.1.4.1.3807.2.240.1.3.1.4
		bfdSessPerfLastSessDownTime OBJECT-TYPE
			SYNTAX TimeStamp
			MAX-ACCESS read-only
			STATUS current
			DESCRIPTION
				"The value of sysUpTime on the most recent occasion at
				which the last time communication was lost with the
				neighbor. If no such down event exist this object
				contains a zero value."
			::= { bfdSessPerfEntry 4 }

		
--    1.3.6.1.4.1.3807.2.240.1.3.1.5
-- 1.3.6.1.4.1.3807.2.240.1.3.1.5
		bfdSessPerfLastCommLostDiag OBJECT-TYPE
			SYNTAX BfdDiag
			MAX-ACCESS read-only
			STATUS current
			DESCRIPTION
				"The BFD diag code for the last time communication was lost
				with the neighbor. If no such down event exists this object
				contains a zero value."
			::= { bfdSessPerfEntry 5 }

		
--    1.3.6.1.4.1.3807.2.240.1.3.1.6
-- 1.3.6.1.4.1.3807.2.240.1.3.1.6
		bfdSessPerfSessUpCount OBJECT-TYPE
			SYNTAX Counter32
			MAX-ACCESS read-only
			STATUS current
			DESCRIPTION
				"The number of times this session has gone into the Up
				state since the system last rebooted."
			::= { bfdSessPerfEntry 6 }

		
--    1.3.6.1.4.1.3807.2.240.1.3.1.7
-- 1.3.6.1.4.1.3807.2.240.1.3.1.7
		bfdSessPerfDiscTime OBJECT-TYPE
			SYNTAX TimeStamp
			MAX-ACCESS read-only
			STATUS current
			DESCRIPTION
				"The value of sysUpTime on the most recent occasion at
				which any one or more of the session counters suffered
				a discontinuity.
				The relevant counters are the specific instances associated
				with this BFD session of any Counter32 object contained in
				the BfdSessPerfTable. If no such discontinuities have
				occurred since the last re-initialization of the local
				management subsystem, then this object contains a zero
				value."
			::= { bfdSessPerfEntry 7 }

		
--    1.3.6.1.4.1.3807.2.240.1.3.1.8
-- 1.3.6.1.4.1.3807.2.240.1.3.1.8
		bfdSessPerfPktInHC OBJECT-TYPE
			SYNTAX Counter64
			MAX-ACCESS read-only
			STATUS current
			DESCRIPTION
				"This value represents the total number of BFD messages
				received for this BFD session. It MUST be equal to the
				least significant 32 bits of bfdSessPerfPktIn
				if bfdSessPerfPktInHC is supported according to
				the rules spelled out in RFC2863."
			::= { bfdSessPerfEntry 8 }

		
--    1.3.6.1.4.1.3807.2.240.1.3.1.9
-- 1.3.6.1.4.1.3807.2.240.1.3.1.9
		bfdSessPerfPktOutHC OBJECT-TYPE
			SYNTAX Counter64
			MAX-ACCESS read-only
			STATUS current
			DESCRIPTION
				"This value represents the total number of
				total number of BFD messages transmitted for this
				BFD session. It MUST be equal to the
				least significant 32 bits of bfdSessPerfPktIn
				if bfdSessPerfPktOutHC is supported according to
				the rules spelled out in RFC2863."
			::= { bfdSessPerfEntry 9 }

		
--    1.3.6.1.4.1.3807.2.240.1.4
-- 1.3.6.1.4.1.3807.2.240.1.4
		bfdSessDiscMapTable OBJECT-TYPE
			SYNTAX SEQUENCE OF BfdSessDiscMapEntry
			MAX-ACCESS not-accessible
			STATUS current
			DESCRIPTION
				"The BFD Session Discriminator Mapping Table maps a
				local discriminator value to associated BFD sessions'
				BfdSessIndexTC used in the bfdSessionTable."
			::= { bfdObjects 4 }

		
--    1.3.6.1.4.1.3807.2.240.1.4.1
-- 1.3.6.1.4.1.3807.2.240.1.4.1
		bfdSessDiscMapEntry OBJECT-TYPE
			SYNTAX BfdSessDiscMapEntry
			MAX-ACCESS not-accessible
			STATUS current
			DESCRIPTION
				"The BFD Session Discriminator Map Entry describes
				BFD session that is mapped to this BfdSessIndexTC."
			INDEX { bfdSessDiscriminator }
			::= { bfdSessDiscMapTable 1 }

		
		BfdSessDiscMapEntry ::=
			SEQUENCE { 
				bfdSessDiscMapIndex
					BfdSessIndexTC
			 }

--    1.3.6.1.4.1.3807.2.240.1.4.1.1
-- 1.3.6.1.4.1.3807.2.240.1.4.1.1
		bfdSessDiscMapIndex OBJECT-TYPE
			SYNTAX BfdSessIndexTC
			MAX-ACCESS read-only
			STATUS current
			DESCRIPTION
				"This object specifies the BfdIndex referred to by
				the indexes of this row. In essence, a mapping is
				provided between these indexes and the BfdSessTable."
			::= { bfdSessDiscMapEntry 1 }

		
--    1.3.6.1.4.1.3807.2.240.1.5
-- 1.3.6.1.4.1.3807.2.240.1.5
		bfdSessIpMapTable OBJECT-TYPE
			SYNTAX SEQUENCE OF BfdSessIpMapEntry
			MAX-ACCESS not-accessible
			STATUS current
			DESCRIPTION
				"The BFD Session IP Mapping Table maps given
				bfdSessInterface, bfdSessAddrType, and bfdSessAddr
				to an associated BFD sessions' BfdSessIndexTC used in
				the bfdSessionTable. This table SHOULD contains those
				BFD sessions of singleHop(1) type."
			::= { bfdObjects 5 }

		
--    1.3.6.1.4.1.3807.2.240.1.5.1
-- 1.3.6.1.4.1.3807.2.240.1.5.1
		bfdSessIpMapEntry OBJECT-TYPE
			SYNTAX BfdSessIpMapEntry
			MAX-ACCESS not-accessible
			STATUS current
			DESCRIPTION
				"The BFD Session IP Map Entry describes
				BFD session that is mapped to this BfdSessIndexTC."
			INDEX { bfdSessInterface, bfdSessAddrType, bfdSessAddr }
			::= { bfdSessIpMapTable 1 }

		
		BfdSessIpMapEntry ::=
			SEQUENCE { 
				bfdSessIpMapIndex
					BfdSessIndexTC
			 }

--    1.3.6.1.4.1.3807.2.240.1.5.1.1
-- 1.3.6.1.4.1.3807.2.240.1.5.1.1
		bfdSessIpMapIndex OBJECT-TYPE
			SYNTAX BfdSessIndexTC
			MAX-ACCESS read-only
			STATUS current
			DESCRIPTION
				"This object specifies the BfdIndex referred to by
				the indexes of this row. In essence, a mapping is
				provided between these indexes and the BfdSessTable."
			::= { bfdSessIpMapEntry 1 }

		
--    1.3.6.1.4.1.3807.2.240.1.6
-- 1.3.6.1.4.1.3807.2.240.1.6
		bfdIfTable OBJECT-TYPE
			SYNTAX SEQUENCE OF BfdIfEntry
			MAX-ACCESS not-accessible
			STATUS current
			DESCRIPTION
				"The BFD Interface Table describes the BFD sessions interface."
			REFERENCE
				"BFD Version 0 (draft-katz-ward-bfd-02.txt) and
				BFD Version 1 (draft-ietf-bfd-base-08.txt)"
			::= { bfdObjects 6 }

		
--    1.3.6.1.4.1.3807.2.240.1.6.1
-- 1.3.6.1.4.1.3807.2.240.1.6.1
		bfdIfEntry OBJECT-TYPE
			SYNTAX BfdIfEntry
			MAX-ACCESS not-accessible
			STATUS current
			DESCRIPTION
				"The BFD Interface Entry describes BFD session interface."
			INDEX { bfdIfIndex }
			::= { bfdIfTable 1 }

		
		BfdIfEntry ::=
			SEQUENCE { 
				bfdIfIndex
					Unsigned32,
				bfdIfRole
					INTEGER,
				bfdIfDemandModeDesiredFlag
					INTEGER,
				bfdIfEchoFuncModeDesiredFlag
					TruthValue,
				bfdIfDesiredMinTxInterval
					Unsigned32,
				bfdIfReqMinRxInterval
					Unsigned32,
				bfdIfReqMinEchoRxInterval
					Unsigned32,
				bfdIfDetectMult
					BfdMultiplier,
				bfdIfAuthPresFlag
					TruthValue,
				bfdIfAuthenticationType
					INTEGER,
				bfdIfAuthenticationKeyID
					Integer32,
				bfdIfAuthenticationKey
					OCTET STRING,
				bfdIfVersionNumber
					Unsigned32,
				bfdIfEnable
					INTEGER
			 }

--    1.3.6.1.4.1.3807.2.240.1.6.1.1
-- 1.3.6.1.4.1.3807.2.240.1.6.1.1
		bfdIfIndex OBJECT-TYPE
			SYNTAX Unsigned32
			MAX-ACCESS read-only
			STATUS current
			DESCRIPTION
				"This object contains an index used to represent a
				unique BFD session on this device."
			::= { bfdIfEntry 1 }

		
--    1.3.6.1.4.1.3807.2.240.1.6.1.2
-- 1.3.6.1.4.1.3807.2.240.1.6.1.2
		bfdIfRole OBJECT-TYPE
			SYNTAX INTEGER
				{
				none(1),
				active(2),
				passive(3)
				}
			MAX-ACCESS read-write
			STATUS current
			DESCRIPTION
				"For bfdSessType, this object specifies whether 
				this BFD session is running in active(1) mode or 
				passive(2) mode."
			::= { bfdIfEntry 2 }

		
--    1.3.6.1.4.1.3807.2.240.1.6.1.3
-- 1.3.6.1.4.1.3807.2.240.1.6.1.3
		bfdIfDemandModeDesiredFlag OBJECT-TYPE
			SYNTAX INTEGER
				{
				asynchronous(1),
				demand(2)
				}
			MAX-ACCESS read-create
			STATUS current
			DESCRIPTION
				"This object indicates that the local system's
				desire to use Demand mode. Specifically, it is set
				to true(1) if the local system wishes to use
				Demand mode or false(2) if the local system wishes to use the asych mode."
			::= { bfdIfEntry 3 }

		
--    1.3.6.1.4.1.3807.2.240.1.6.1.4
-- 1.3.6.1.4.1.3807.2.240.1.6.1.4
		bfdIfEchoFuncModeDesiredFlag OBJECT-TYPE
			SYNTAX TruthValue
			MAX-ACCESS read-create
			STATUS current
			DESCRIPTION
				"This object indicates that the local system's
				desire to use Echo mode. Specifically, it is set  
				to true(1) if the local system wishes to use  
				Echo mode or false(2) if not"
			DEFVAL { false }
			::= { bfdIfEntry 4 }

		
--    1.3.6.1.4.1.3807.2.240.1.6.1.5
-- 1.3.6.1.4.1.3807.2.240.1.6.1.5
		bfdIfDesiredMinTxInterval OBJECT-TYPE
			SYNTAX Unsigned32 (5..999)
			MAX-ACCESS read-create
			STATUS current
			DESCRIPTION
				"This object specifies the minimum interval, in
				microseconds, that the local system would like to use when
				transmitting BFD Control packets."
			::= { bfdIfEntry 5 }

		
--    1.3.6.1.4.1.3807.2.240.1.6.1.6
-- 1.3.6.1.4.1.3807.2.240.1.6.1.6
		bfdIfReqMinRxInterval OBJECT-TYPE
			SYNTAX Unsigned32 (1..999)
			MAX-ACCESS read-create
			STATUS current
			DESCRIPTION
				"This object specifies the minimum interval, in
				microseconds, between received  BFD Control packets the
				local system is capable of supporting."
			::= { bfdIfEntry 6 }

		
--    1.3.6.1.4.1.3807.2.240.1.6.1.7
-- 1.3.6.1.4.1.3807.2.240.1.6.1.7
		bfdIfReqMinEchoRxInterval OBJECT-TYPE
			SYNTAX Unsigned32 (0..999)
			MAX-ACCESS read-create
			STATUS current
			DESCRIPTION
				"This object specifies the minimum interval, in
				microseconds, between received BFD Echo packets that this
				system is capable of supporting."
			::= { bfdIfEntry 7 }

		
--    1.3.6.1.4.1.3807.2.240.1.6.1.8
-- 1.3.6.1.4.1.3807.2.240.1.6.1.8
		bfdIfDetectMult OBJECT-TYPE
			SYNTAX BfdMultiplier
			MAX-ACCESS read-create
			STATUS current
			DESCRIPTION
				"This object specifies the Detect time multiplier."
			::= { bfdIfEntry 8 }

		
--    1.3.6.1.4.1.3807.2.240.1.6.1.9
-- 1.3.6.1.4.1.3807.2.240.1.6.1.9
		bfdIfAuthPresFlag OBJECT-TYPE
			SYNTAX TruthValue
			MAX-ACCESS read-create
			STATUS current
			DESCRIPTION
				"This object indicates that the local system's
				desire to use Authentication. Specifically, it is set
				to true(1) if the local system wishes the session
				to be authenticated or false(2) if not."
			REFERENCE
				"draft-ietf-bfd-base-08, Sections 4.2 - 4.4"
			DEFVAL { false }
			::= { bfdIfEntry 9 }

		
--    1.3.6.1.4.1.3807.2.240.1.6.1.10
-- 1.3.6.1.4.1.3807.2.240.1.6.1.10
		bfdIfAuthenticationType OBJECT-TYPE
			SYNTAX INTEGER
				{
				reserved(0),
				simplePassword(1),
				keyedMD5(2),
				meticulousKeyedMD5(3),
				keyedSHA1(4),
				meticulousKeyedSHA1(5)
				}
			MAX-ACCESS read-create
			STATUS current
			DESCRIPTION
				"The Authentication Type used for this BFD session.
				This field is valid only when the Authentication
				Present bit is set."
			REFERENCE
				"draft-ietf-bfd-base-08, Sections 4.2 - 4.4"
			::= { bfdIfEntry 10 }

		
--    1.3.6.1.4.1.3807.2.240.1.6.1.11
-- 1.3.6.1.4.1.3807.2.240.1.6.1.11
		bfdIfAuthenticationKeyID OBJECT-TYPE
			SYNTAX Integer32 (-1 | 0..255)
			MAX-ACCESS read-create
			STATUS current
			DESCRIPTION
				"The authentication key ID in use for this session.  This
				object permits multiple keys to be active simultaneously.
				
				When bfdSessAuthPresFlag is false(2), then the value
				of this object MUST be -1.  The value -1 indicates that
				no Authentication Key ID will be present in the optional
				BFD Authentication Section."
			REFERENCE
				"draft-ietf-bfd-base-08, Sections 4.2 - 4.4"
			DEFVAL { -1 }
			::= { bfdIfEntry 11 }

		
--    1.3.6.1.4.1.3807.2.240.1.6.1.12
-- 1.3.6.1.4.1.3807.2.240.1.6.1.12
		bfdIfAuthenticationKey OBJECT-TYPE
			SYNTAX OCTET STRING
			MAX-ACCESS read-create
			STATUS current
			DESCRIPTION
				"The authentication key.  When the
				bfdSessAuthenticationType is simplePassword(1), the value
				of this object is the password present in the BFD packets.
				
				When the bfdSessAuthentication type is one of the keyed
				authentication types, this value is used in the
				computation of the key present in the BFD authentication
				packet."
			REFERENCE
				"draft-ietf-bfd-base-08, Sections 4.2 - 4.4"
			::= { bfdIfEntry 12 }

		
--    1.3.6.1.4.1.3807.2.240.1.6.1.13
-- 1.3.6.1.4.1.3807.2.240.1.6.1.13
		bfdIfVersionNumber OBJECT-TYPE
			SYNTAX Unsigned32
			MAX-ACCESS read-write
			STATUS current
			DESCRIPTION
				"The current version number of the BFD protocol."
			REFERENCE
				"BFD Version 0 (draft-katz-ward-bfd-02.txt)"
			DEFVAL { 1 }
			::= { bfdIfEntry 13 }

		
--    1.3.6.1.4.1.3807.2.240.1.6.1.14
-- 1.3.6.1.4.1.3807.2.240.1.6.1.14
		bfdIfEnable OBJECT-TYPE
			SYNTAX INTEGER
				{
				enable(1),
				diable(2)
				}
			MAX-ACCESS read-write
			STATUS current
			DESCRIPTION
				"enble or diable bfd session interface."
			DEFVAL { enable }
			::= { bfdIfEntry 14 }

		
--    1.3.6.1.4.1.3807.2.240.1.7
-- 1.3.6.1.4.1.3807.2.240.1.7
		bfdTrackTable OBJECT-TYPE
			SYNTAX SEQUENCE OF BfdTrackEntry
			MAX-ACCESS not-accessible
			STATUS current
			DESCRIPTION
				"Description."
			::= { bfdObjects 7 }

		
--    1.3.6.1.4.1.3807.2.240.1.7.1
-- 1.3.6.1.4.1.3807.2.240.1.7.1
		bfdTrackEntry OBJECT-TYPE
			SYNTAX BfdTrackEntry
			MAX-ACCESS not-accessible
			STATUS current
			DESCRIPTION
				"Description."
			INDEX { bfdTrackIndex }
			::= { bfdTrackTable 1 }

		
		BfdTrackEntry ::=
			SEQUENCE { 
				bfdTrackIndex
					Integer32,
				bfdTrackInterface
					Integer32,
				bfdTrackAddrType
					Integer32,
				bfdTrackAddr
					OCTET STRING,
				bfdTrackRemoteAddr
					OCTET STRING,
				bfdTrackSessionDiscr
					Integer32,
				bfdTrackSessionState
					Integer32,
				bfdTrackRowstatus
					Integer32,
				bfdTrackVpnId
					Integer32,
				bfdTrackOneArmEcho
					INTEGER
			 }

--    1.3.6.1.4.1.3807.2.240.1.7.1.1
-- 1.3.6.1.4.1.3807.2.240.1.7.1.1
		bfdTrackIndex OBJECT-TYPE
			SYNTAX Integer32
			MAX-ACCESS read-only
			STATUS current
			DESCRIPTION
				"Description."
			::= { bfdTrackEntry 1 }

		
--    1.3.6.1.4.1.3807.2.240.1.7.1.2
-- 1.3.6.1.4.1.3807.2.240.1.7.1.2
		bfdTrackInterface OBJECT-TYPE
			SYNTAX Integer32
			MAX-ACCESS read-write
			STATUS current
			DESCRIPTION
				"Description."
			::= { bfdTrackEntry 2 }

		
--    1.3.6.1.4.1.3807.2.240.1.7.1.3
-- 1.3.6.1.4.1.3807.2.240.1.7.1.3
		bfdTrackAddrType OBJECT-TYPE
			SYNTAX Integer32
			MAX-ACCESS read-write
			STATUS current
			DESCRIPTION
				"Description."
			::= { bfdTrackEntry 3 }

		
--    1.3.6.1.4.1.3807.2.240.1.7.1.4
-- 1.3.6.1.4.1.3807.2.240.1.7.1.4
		bfdTrackAddr OBJECT-TYPE
			SYNTAX OCTET STRING
			MAX-ACCESS read-write
			STATUS current
			DESCRIPTION
				"Description."
			::= { bfdTrackEntry 4 }

		
--    1.3.6.1.4.1.3807.2.240.1.7.1.5
-- 1.3.6.1.4.1.3807.2.240.1.7.1.5
		bfdTrackRemoteAddr OBJECT-TYPE
			SYNTAX OCTET STRING
			MAX-ACCESS read-write
			STATUS current
			DESCRIPTION
				"Description."
			::= { bfdTrackEntry 5 }

		
--    1.3.6.1.4.1.3807.2.240.1.7.1.6
-- 1.3.6.1.4.1.3807.2.240.1.7.1.6
		bfdTrackSessionDiscr OBJECT-TYPE
			SYNTAX Integer32
			MAX-ACCESS read-only
			STATUS current
			DESCRIPTION
				"Description."
			::= { bfdTrackEntry 6 }

		
--    1.3.6.1.4.1.3807.2.240.1.7.1.7
-- 1.3.6.1.4.1.3807.2.240.1.7.1.7
		bfdTrackSessionState OBJECT-TYPE
			SYNTAX Integer32
			MAX-ACCESS read-only
			STATUS current
			DESCRIPTION
				"Description."
			::= { bfdTrackEntry 7 }

		
--    1.3.6.1.4.1.3807.2.240.1.7.1.8
-- 1.3.6.1.4.1.3807.2.240.1.7.1.8
		bfdTrackRowstatus OBJECT-TYPE
			SYNTAX Integer32
			MAX-ACCESS read-write
			STATUS current
			DESCRIPTION
				"Description."
			::= { bfdTrackEntry 8 }

		
--   1.3.6.1.4.1.3807.2.240.1.7.1.9
		bfdTrackVpnId OBJECT-TYPE
			SYNTAX Integer32
			MAX-ACCESS read-write
			STATUS current
			DESCRIPTION
				"Description."
			::= { bfdTrackEntry 9 }
			
--   1.3.6.1.4.1.3807.2.240.1.7.1.9
		bfdTrackOneArmEcho OBJECT-TYPE
			SYNTAX INTEGER
				{
				enable(1),
				diable(2)
				}
			MAX-ACCESS read-write
			STATUS current
			DESCRIPTION
				"enble or diable bfd track one arm echo."
			DEFVAL { disable }
			::= { bfdTrackEntry 10 }
		
--    1.3.6.1.4.1.3807.2.240.2
-- 1.3.6.1.4.1.3807.2.240.2
		bfdConformance OBJECT IDENTIFIER ::= { wriBfd 2 }

		
--    1.3.6.1.4.1.3807.2.240.2.1
-- 1.3.6.1.4.1.3807.2.240.2.1
		bfdGroups OBJECT IDENTIFIER ::= { bfdConformance 1 }

		
--    1.3.6.1.4.1.3807.2.240.2.1.1
-- 1.3.6.1.4.1.3807.2.240.2.1.1
		bfdSessionGroup OBJECT-GROUP
			OBJECTS { bfdAdminStatus, bfdVersionNumber, bfdSessRole, bfdSessAdminStatus, bfdSessDiag, 
				bfdSessDemandModeDesiredFlag, bfdSessEchoFuncModeDesiredFlag, bfdSessControlPlaneIndepFlag, bfdSessInterface, bfdSessAddrType, 
				bfdSessAddr, bfdSessDesiredMinTxInterval, bfdSessReqMinRxInterval, bfdSessReqMinEchoRxInterval, bfdSessAuthenticationType, 
				bfdSessAuthenticationKeyID, bfdSessAuthenticationKey, bfdSessDetectMult, bfdSessStorType, bfdSessRowStatus
				 }
			STATUS current
			DESCRIPTION 
				"Collection of objects needed for BFD sessions."
			::= { bfdGroups 1 }

		
--    1.3.6.1.4.1.3807.2.240.2.1.2
-- 1.3.6.1.4.1.3807.2.240.2.1.2
		bfdSessionReadOnlyGroup OBJECT-GROUP
			OBJECTS { bfdSessType, bfdSessDiscriminator, bfdSessRemoteDiscr, bfdSessUdpPort, bfdSessState, 
				bfdSessRemoteHeardFlag, bfdSessOperMode, bfdSessAuthPresFlag, bfdSessDiscMapIndex, bfdSessIpMapIndex
				 }
			STATUS current
			DESCRIPTION 
				"Collection of read-only objects needed for BFD sessions."
			::= { bfdGroups 2 }

		
--    1.3.6.1.4.1.3807.2.240.2.1.3
-- 1.3.6.1.4.1.3807.2.240.2.1.3
		bfdSessionPerfGroup OBJECT-GROUP
			OBJECTS { bfdSessPerfPktIn, bfdSessPerfPktOut, bfdSessUpTime, bfdSessPerfLastSessDownTime, bfdSessPerfLastCommLostDiag, 
				bfdSessPerfSessUpCount, bfdSessPerfDiscTime }
			STATUS current
			DESCRIPTION 
				"Collection of objects needed to monitor the
				performance of BFD sessions."
			::= { bfdGroups 3 }

		
--    1.3.6.1.4.1.3807.2.240.2.1.4
-- 1.3.6.1.4.1.3807.2.240.2.1.4
		bfdSessionPerfHCGroup OBJECT-GROUP
			OBJECTS { bfdSessPerfPktInHC, bfdSessPerfPktOutHC }
			STATUS current
			DESCRIPTION 
				"Collection of objects needed to monitor the
				performance of BFD sessions for which the
				values of bfdSessPerfPktIn, bfdSessPerfPktOut
				wrap around too quickly."
			::= { bfdGroups 4 }

		
--    1.3.6.1.4.1.3807.2.240.2.1.5
-- 1.3.6.1.4.1.3807.2.240.2.1.5
		bfdNotificationGroup NOTIFICATION-GROUP
			NOTIFICATIONS { bfdSessUp, bfdSessDown }
			STATUS current
			DESCRIPTION 
				"Set of notifications implemented in this
				module."
			::= { bfdGroups 5 }

		
--    1.3.6.1.4.1.3807.2.240.2.2
-- 1.3.6.1.4.1.3807.2.240.2.2
		bfdCompliances OBJECT IDENTIFIER ::= { bfdConformance 2 }

		
--    1.3.6.1.4.1.3807.2.240.2.2.1
-- this module
-- 1.3.6.1.4.1.3807.2.240.2.2.1
-- this module
-- this module
		bfdModuleFullCompliance MODULE-COMPLIANCE
			STATUS current
			DESCRIPTION 
				"Compliance statement for agents that provide full
				support for BFD-MIB. Such devices can
				then be monitored and also be configured using
				this MIB module."
			MODULE -- this module
				MANDATORY-GROUPS { bfdSessionGroup, bfdSessionReadOnlyGroup, bfdSessionPerfGroup, bfdSessionPerfHCGroup, bfdNotificationGroup
					 }
				GROUP bfdSessionPerfHCGroup
					DESCRIPTION 
						"This group is mandatory for those bfdPerfTable
						entries for which any of the objects
						bfdSessPerfPktInHC or bfdSessPerfPktOutHC
						wraps around too quickly
						based on the criteria specified in RFC 2863 for
						high-capacity counters."
				GROUP bfdNotificationGroup
					DESCRIPTION 
						"This group is only mandatory for those
						implementations which can efficiently implement
						the notifications contained in this group."
				OBJECT bfdSessAddrType
					SYNTAX InetAddressType
						{
						unknown(0),
						ipv4(1),
						ipv6(2),
						ipv6z(4)
						}
					DESCRIPTION 
						"Only unknown(0), ipv4(1), ipv6(2) and ipv6z(4)
						support are required."
				OBJECT bfdSessAddr
					SYNTAX InetAddress (SIZE (0 | 4 | 16 | 20))
					DESCRIPTION 
						"An implementation is only required to support
						unknown(0), ipv4(1), ipv6(2) and ipv6z(4) sizes."
			::= { bfdCompliances 1 }

		
	
	END

--
-- wriBfd.mib
--
