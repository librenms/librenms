--
-- WRI-RFC2544-MIB.mib
-- MIB generated by MG-SOFT Visual MIB Builder Version 6.0  Build 88
-- Monday, July 09, 2012 at 16:31:56
--

	WRI-RFC2544-MIB DEFINITIONS ::= BEGIN
 
		IMPORTS
			mib-2			
				FROM RFC1213-MIB			
			enterprises, Integer32, TimeTicks, OBJECT-TYPE, MODULE-IDENTITY, Counter32			
				FROM SNMPv2-SMI			
			PhysAddress, RowStatus,TEXTUAL-CONVENTION			
				FROM SNMPv2-TC
	        InetAddress, InetAddressType
          		FROM INET-ADDRESS-MIB; 
	
		wri MODULE-IDENTITY 
			LAST-UPDATED "201208081500Z"		   --
			ORGANIZATION 
				"FiberHome Networks Systems, Inc."
			CONTACT-INFO 
				"http://www.fhn.com.cn"
			DESCRIPTION 
				"The Structure of Management Information for the FHN enterprise."
			::= { enterprises 3807 }

		
	
--
-- Node definitions
--
	
		wriProtocol OBJECT IDENTIFIER ::= { wri 2 }

		
		wriRfc2544 OBJECT IDENTIFIER ::= { wriProtocol 1815 }  
		         
		
		rfc2544Common OBJECT IDENTIFIER ::= { wriRfc2544 1 }  
		
		rfc2544IpType OBJECT-TYPE
			SYNTAX InetAddressType
			MAX-ACCESS read-write
			STATUS current
			DESCRIPTION
				""
			::= { rfc2544Common 1 }
		
		rfc2544Generator OBJECT IDENTIFIER ::= { wriRfc2544 2 }
                                                                       
                                                               
		generatorConfig OBJECT IDENTIFIER ::= { rfc2544Generator 1 }
		
		
		generatorConfigTable OBJECT-TYPE
		   SYNTAX SEQUENCE OF GeneratorConfigEntry
		   MAX-ACCESS not-accessible
		   STATUS current
		   DESCRIPTION
		       ""
		   ::= { generatorConfig 1 }
                                       
                                                   
		generatorConfigEntry OBJECT-TYPE
		    SYNTAX GeneratorConfigEntry
		    MAX-ACCESS not-accessible
		    STATUS current
		    DESCRIPTION
		       ""
		    INDEX { generatorIndex }
		    ::= { generatorConfigTable 1 }

        
		GeneratorConfigEntry ::=
		    SEQUENCE {                      
		    	   generatorIndex					Integer32,
		           generatorConfigState				INTEGER,
		           generatorDescription          	OCTET STRING,
		           generatorTestStartedTime 		TimeTicks,
		           generatorTestStopedTime    		TimeTicks, 
		           generatorBindPort    			Integer32,
		           generatorRunState				INTEGER,
		           generatorReset    				Integer32
		             }				                                                         


		generatorIndex OBJECT-TYPE
			SYNTAX Integer32
			MAX-ACCESS read-only
			STATUS current
			DESCRIPTION
				""
			::= { generatorConfigEntry 1 }


		generatorConfigState OBJECT-TYPE
			SYNTAX INTEGER
				{
				stop(2),
				start(1)
				}
			MAX-ACCESS read-write
			STATUS current
			DESCRIPTION
				""
			::= { generatorConfigEntry 2 }

				                                                         
		generatorDescription OBJECT-TYPE
			SYNTAX OCTET STRING
			MAX-ACCESS read-write
			STATUS current
			DESCRIPTION
				""
			::= { generatorConfigEntry 3 }

		
		
		generatorTestStartedTime OBJECT-TYPE
			SYNTAX TimeTicks
			MAX-ACCESS read-only
			STATUS current
			DESCRIPTION
				""
			::= { generatorConfigEntry 4 }
			

		generatorTestStopedTime OBJECT-TYPE
			SYNTAX TimeTicks
			MAX-ACCESS read-only
			STATUS current
			DESCRIPTION
				""
			::= { generatorConfigEntry 5 }   
		
		generatorBindPort OBJECT-TYPE
			SYNTAX Integer32
			MAX-ACCESS read-write
			STATUS current
			DESCRIPTION
				""
			::= { generatorConfigEntry 6 }  
			
		generatorRunState OBJECT-TYPE
			SYNTAX INTEGER
				{
				idle(0),
				running(1),
				fail(2),
				success(3)
				}
			MAX-ACCESS read-only
			STATUS current
			DESCRIPTION
				""
			::= { generatorConfigEntry 7 }  
			
		generatorReset OBJECT-TYPE
			SYNTAX Integer32
			MAX-ACCESS read-write
			STATUS current
			DESCRIPTION
				""
			::= { generatorConfigEntry 8 }

                                                                                            
                                                        
		generatorPacketFlow OBJECT IDENTIFIER ::= { generatorConfig 2 }

		                                                        
		generatorPacketFlowTable OBJECT-TYPE
		   SYNTAX SEQUENCE OF GeneratorPacketFlowEntry
		   MAX-ACCESS not-accessible
		   STATUS current
		   DESCRIPTION
		       ""
		   ::= { generatorPacketFlow 1 }
                                       
                                                   
		generatorPacketFlowEntry OBJECT-TYPE
		    SYNTAX GeneratorPacketFlowEntry
		    MAX-ACCESS not-accessible
		    STATUS current
		    DESCRIPTION
		       ""
		    INDEX { generatorConfigIndex, generatorPHFPIndex }
		    ::= { generatorPacketFlowTable 1 }

        
		GeneratorPacketFlowEntry ::=
		    SEQUENCE { 
		    	   generatorConfigIndex			Integer32,
		           generatorPHFPIndex			Integer32,
		           generatorPacketType          INTEGER,
		           generatorPacketSrcMac           PhysAddress, 
		           generatorPacketDstMac           PhysAddress,
		           generatorPacketOAMLevel      Integer32,
		           generatorPacketEthType       Integer32,
		           generatorPacketQoSType      	INTEGER,
		           generatorPacketDSCP      	Integer32,
		           generatorPacketTos       	Integer32, 
		           generatorPacketDstIp      	InetAddress,
		           generatorPacketSrcIp      	InetAddress,  
		           generatorPacketDstPort       Integer32, 
		           generatorPacketSrcPort       Integer32,
		           generatorPacketL4Type        INTEGER,		 
		           generatorPacketMep        	Integer32,
		           generatorPacketCvlanState        	INTEGER,
		           generatorPacketCvlanPriority    	    Integer32,
		           generatorPacketCvlanCFI          	Integer32,
		           generatorPacketCvlanID           	Integer32, 
		           generatorPacketCvlanTPID          	Integer32,
		           generatorPacketSvlanState        	INTEGER,
		           generatorPacketSvlanPriority    	    Integer32,
		           generatorPacketSvlanCFI         		Integer32,
		           generatorPacketSvlanID          		Integer32,
		           generatorPacketSvlanTPID          	Integer32,
		           generatorFlowState               	INTEGER,
		           generatorFlowType          			INTEGER,
		           generatorFlowRegulator     			Integer32,
		           generatorFlowName      				OCTET STRING,
		           generatorFlowDescription				OCTET STRING,  
		           generatorFlowTrafficType    			INTEGER,
		           generatorFlowBitRate            		Integer32,
		           generatorFlowPacketsPerBurst    	 	Integer32,
		           generatorFlowInterBurstGap      	 	Integer32,
		           generatorFlowSizeType           		INTEGER,
		           generatorFlowFixedSize          		Integer32,
		           generatorFlowPayloadType             INTEGER,
		           generatorFlowFixedPattern            Integer32,
		           generatorFlowIncrementalPattern      INTEGER,
		           generatorFlowRandomPattern           INTEGER,
		           generatorFlowDurationType            INTEGER,
		           generatorFlowDurationSeconds         Integer32,  
		           generatorFlowDurationBytes           Integer32,
		           generatorFlowDurationPackets         Integer32,
		           generatorFlowBindPort    			Integer32,
		           generatorFlowReset    				Integer32
		             }
                                                                                    
		generatorConfigIndex OBJECT-TYPE
			SYNTAX Integer32
			MAX-ACCESS read-only
			STATUS current
			DESCRIPTION
				""
			::= { generatorPacketFlowEntry 1 }
			         
		generatorPHFPIndex OBJECT-TYPE
			SYNTAX Integer32
			MAX-ACCESS read-only
			STATUS current
			DESCRIPTION
				""
			::= { generatorPacketFlowEntry 2 }
		                                              
		
		generatorPacketType OBJECT-TYPE
			SYNTAX INTEGER
				{
				unknown(0),		
				layer2(1),      
				layer3(2)		
				}
			MAX-ACCESS read-write
			STATUS current
			DESCRIPTION
				""
			::= { generatorPacketFlowEntry 3 }


		generatorPacketSrcMac OBJECT-TYPE
			SYNTAX PhysAddress
			MAX-ACCESS read-write
			STATUS current
			DESCRIPTION
				""
			::= { generatorPacketFlowEntry 4 } 
			
		generatorPacketDstMac OBJECT-TYPE
			SYNTAX PhysAddress
			MAX-ACCESS read-write
			STATUS current
			DESCRIPTION
				""
			::= { generatorPacketFlowEntry 5 }
			

		generatorPacketOAMLevel OBJECT-TYPE
			SYNTAX Integer32
			MAX-ACCESS read-write
			STATUS current
			DESCRIPTION
				""
			::= { generatorPacketFlowEntry 6 }     
			
		generatorPacketEthType OBJECT-TYPE
			SYNTAX Integer32
			MAX-ACCESS read-write
			STATUS current
			DESCRIPTION
				""
			::= { generatorPacketFlowEntry 7 }
			
		generatorPacketQoSType OBJECT-TYPE
			SYNTAX INTEGER
				{
				dscp(1),		
				tos(2)      		
				}
			MAX-ACCESS read-write
			STATUS current
			DESCRIPTION
				""
			::= { generatorPacketFlowEntry 8 }
			
		generatorPacketDSCP OBJECT-TYPE
			SYNTAX Integer32
			MAX-ACCESS read-write
			STATUS current
			DESCRIPTION
				""
			::= { generatorPacketFlowEntry 9 }
			
		generatorPacketTos OBJECT-TYPE
			SYNTAX Integer32
			MAX-ACCESS read-write
			STATUS current
			DESCRIPTION
				""
			::= { generatorPacketFlowEntry 10 }    
			                                   
					                                   
		generatorPacketDstIp OBJECT-TYPE
			SYNTAX InetAddress
			MAX-ACCESS read-write
			STATUS current
			DESCRIPTION
				""
			::= { generatorPacketFlowEntry 11 } 
			
		generatorPacketSrcIp OBJECT-TYPE
			SYNTAX InetAddress
			MAX-ACCESS read-write
			STATUS current
			DESCRIPTION
				""
			::= { generatorPacketFlowEntry 12 }    
			
		generatorPacketDstPort OBJECT-TYPE
			SYNTAX Integer32
			MAX-ACCESS read-write
			STATUS current
			DESCRIPTION
				""
			::= { generatorPacketFlowEntry 13 }
			
		generatorPacketSrcPort OBJECT-TYPE
			SYNTAX Integer32
			MAX-ACCESS read-write
			STATUS current
			DESCRIPTION
				""
			::= { generatorPacketFlowEntry 14 } 
			
		generatorPacketL4Type OBJECT-TYPE
			SYNTAX INTEGER
				{
				tcp(6),		
				udp(17)      		
				}
			MAX-ACCESS read-only
			STATUS current
			DESCRIPTION
				""
			::= { generatorPacketFlowEntry 15 }  
			
			
		generatorPacketMep OBJECT-TYPE
			SYNTAX Integer32
			MAX-ACCESS read-write
			STATUS current
			DESCRIPTION
				""
			::= { generatorPacketFlowEntry 16 }

		            		                                                 
		generatorPacketCvlanState OBJECT-TYPE
			SYNTAX INTEGER
				{
				disable(2),
				enable(1)
				}
			MAX-ACCESS read-write
			STATUS current
			DESCRIPTION
				""
			::= { generatorPacketFlowEntry 17 }
		    
		    
		generatorPacketCvlanPriority OBJECT-TYPE
			SYNTAX Integer32
			MAX-ACCESS read-write
			STATUS current
			DESCRIPTION
				""
			::= { generatorPacketFlowEntry 18 }
		    

		generatorPacketCvlanCFI OBJECT-TYPE
			SYNTAX Integer32
			MAX-ACCESS read-write
			STATUS current
			DESCRIPTION
				""
			::= { generatorPacketFlowEntry 19 }


		generatorPacketCvlanID OBJECT-TYPE
			SYNTAX Integer32
			MAX-ACCESS read-write
			STATUS current
			DESCRIPTION
				""
			::= { generatorPacketFlowEntry 20 }
			
		generatorPacketCvlanTPID OBJECT-TYPE
			SYNTAX Integer32
			MAX-ACCESS read-write
			STATUS current
			DESCRIPTION
				""
			::= { generatorPacketFlowEntry 21 }
			
		generatorPacketSvlanState OBJECT-TYPE
			SYNTAX INTEGER
				{
				disable(2),
				enable(1)
				}
			MAX-ACCESS read-write
			STATUS current
			DESCRIPTION
				""
			::= { generatorPacketFlowEntry 22 }
		    
		    
		generatorPacketSvlanPriority OBJECT-TYPE
			SYNTAX Integer32
			MAX-ACCESS read-write
			STATUS current
			DESCRIPTION
				""
			::= { generatorPacketFlowEntry 23 }
		    

		generatorPacketSvlanCFI OBJECT-TYPE
			SYNTAX Integer32
			MAX-ACCESS read-write
			STATUS current
			DESCRIPTION
				""
			::= { generatorPacketFlowEntry 24 }


		generatorPacketSvlanID OBJECT-TYPE
			SYNTAX Integer32
			MAX-ACCESS read-write
			STATUS current
			DESCRIPTION
				""
			::= { generatorPacketFlowEntry 25 }
			
		generatorPacketSvlanTPID OBJECT-TYPE
			SYNTAX Integer32
			MAX-ACCESS read-write
			STATUS current
			DESCRIPTION
				""
			::= { generatorPacketFlowEntry 26 }
                                                       

		generatorFlowState OBJECT-TYPE
			SYNTAX INTEGER
				{
				disable(2),
				enable(1)
				}
			MAX-ACCESS read-write
			STATUS current
			DESCRIPTION
				""
			::= { generatorPacketFlowEntry 27 }
                                                                        

		generatorFlowType OBJECT-TYPE
			SYNTAX INTEGER
				{
				outofservice(2),
				inservice(1)
				}
			MAX-ACCESS read-write
			STATUS current
			DESCRIPTION
				""
			::= { generatorPacketFlowEntry 28 }
                                            

		generatorFlowRegulator OBJECT-TYPE
			SYNTAX Integer32
			MAX-ACCESS read-write
			STATUS current
			DESCRIPTION
				""
			::= { generatorPacketFlowEntry 29 }


		generatorFlowName OBJECT-TYPE
			SYNTAX OCTET STRING
			MAX-ACCESS read-write
			STATUS current
			DESCRIPTION
				""
			::= { generatorPacketFlowEntry 30 }


		generatorFlowDescription OBJECT-TYPE
			SYNTAX OCTET STRING
			MAX-ACCESS read-write             
			STATUS current
			DESCRIPTION
				""
			::= { generatorPacketFlowEntry 31 }


		generatorFlowTrafficType OBJECT-TYPE
			SYNTAX INTEGER
				{
				constant(1),
				burst(2)
				}
			MAX-ACCESS read-write
			STATUS current
			DESCRIPTION
				""
			::= { generatorPacketFlowEntry 32 }
                                                   

		generatorFlowBitRate OBJECT-TYPE
			SYNTAX Integer32
			MAX-ACCESS read-write
			STATUS current
			DESCRIPTION
				""
			::= { generatorPacketFlowEntry 33 }
                                                   

		generatorFlowPacketsPerBurst OBJECT-TYPE
			SYNTAX Integer32
			MAX-ACCESS read-write
			STATUS current
			DESCRIPTION
				""
			::= { generatorPacketFlowEntry 34 }
			
			
		generatorFlowInterBurstGap OBJECT-TYPE
			SYNTAX Integer32
			MAX-ACCESS read-write
			STATUS current
			DESCRIPTION
				""
			::= { generatorPacketFlowEntry 35 }
                                          
                                          
		generatorFlowSizeType OBJECT-TYPE
			SYNTAX INTEGER
				{
				fixed(1),
				random(2)
				}
			MAX-ACCESS read-write
			STATUS current
			DESCRIPTION
				""
			::= { generatorPacketFlowEntry 36 }


		generatorFlowFixedSize OBJECT-TYPE
			SYNTAX Integer32
			MAX-ACCESS read-write
			STATUS current
			DESCRIPTION
				""
			::= { generatorPacketFlowEntry 37 }


		generatorFlowPayloadType OBJECT-TYPE
			SYNTAX INTEGER
				{
				fixed(1),
				incremental(2),
				random(3)
				}
			MAX-ACCESS read-write
			STATUS current
			DESCRIPTION
				""
			::= { generatorPacketFlowEntry 38 }


		generatorFlowFixedPattern OBJECT-TYPE
			SYNTAX Integer32
			MAX-ACCESS read-write
			STATUS current
			DESCRIPTION
				""
			::= { generatorPacketFlowEntry 39 }
                                               

		generatorFlowIncrementalPattern OBJECT-TYPE
			SYNTAX INTEGER
				{
				bytes(1),
				words(2)
				}
			MAX-ACCESS read-write
			STATUS current
			DESCRIPTION
				""
			::= { generatorPacketFlowEntry 40 }
                                                         

		generatorFlowRandomPattern OBJECT-TYPE
			SYNTAX INTEGER
				{
				pattern2e11(0),
				pattern2e15(1), 
				pattern2e11inv(2),
				pattern2e15inv(3),
				patternother(4)
				}
			MAX-ACCESS read-write
			STATUS current
			DESCRIPTION
				""
			::= { generatorPacketFlowEntry 41 }
                                            
                                            
		generatorFlowDurationType OBJECT-TYPE
			SYNTAX INTEGER
				{
				continuous(1),
				seconds(2), 
				bytes(3),
				packets(4)
				}
			MAX-ACCESS read-write
			STATUS current
			DESCRIPTION
				""
			::= { generatorPacketFlowEntry 42 }     
			
			
		generatorFlowDurationSeconds OBJECT-TYPE
			SYNTAX Integer32
			MAX-ACCESS read-write
			STATUS current
			DESCRIPTION
				""
			::= { generatorPacketFlowEntry 43 }     
			

		generatorFlowDurationBytes OBJECT-TYPE
			SYNTAX Integer32
			MAX-ACCESS read-write
			STATUS current
			DESCRIPTION
				""
			::= { generatorPacketFlowEntry 44 }     
                                                                        

		generatorFlowDurationPackets OBJECT-TYPE
			SYNTAX Integer32
			MAX-ACCESS read-write
			STATUS current
			DESCRIPTION
				""
			::= { generatorPacketFlowEntry 45 }       
			
		generatorFlowBindPort OBJECT-TYPE
			SYNTAX Integer32
			MAX-ACCESS read-write
			STATUS current
			DESCRIPTION
				""
			::= { generatorPacketFlowEntry 46 }


		generatorFlowReset OBJECT-TYPE
			SYNTAX Integer32
			MAX-ACCESS read-write
			STATUS current
			DESCRIPTION
				""
			::= { generatorPacketFlowEntry 47 }

                                            
                                            
		generatorResultTable OBJECT-TYPE
		   SYNTAX SEQUENCE OF GeneratorResultEntry
		   MAX-ACCESS not-accessible
		   STATUS current
		   DESCRIPTION
		       ""
		   ::= { rfc2544Generator 2 }
                                       
                                                   
		generatorResultEntry OBJECT-TYPE
		    SYNTAX GeneratorResultEntry
		    MAX-ACCESS not-accessible
		    STATUS current
		    DESCRIPTION
		       ""
		    INDEX { generatorResultIndex, generatorResultPHFPIndex }
		    ::= { generatorResultTable 1 }

        
		GeneratorResultEntry ::=
		    SEQUENCE {   
		    	   generatorResultIndex         			Integer32,
		    	   generatorResultPHFPIndex     			Integer32,
		           generatorResultFlowTransPackets          Counter32,
		           generatorResultFlowTransBytes     		Counter32,
		           generatorResultFlowTransRate      		Counter32, 
		           generatorResultFlowRecvPackets    		Counter32,
		           generatorResultFlowRecvBytes            	Counter32,
		           generatorResultFlowRecvRate     			Counter32,
		           generatorResultFlowOOODuplicates       	Counter32,
		           generatorResultFlowNumberOfGaps          Counter32,
		           generatorResultFlowMaxGap           		Counter32,
		           generatorResultFlowTwoWayDelayInstant    Counter32,
		           generatorResultFlowTwoWayDelayAverage    Counter32,
		           generatorResultFlowTwoWayDelayMin        Counter32,
		           generatorResultFlowTwoWayDelayMax        Counter32,
		           generatorResultFlowTwoWayDelayVarInstant Counter32,
		           generatorResultFlowTwoWayDelayVarAverage Counter32,
		           generatorResultFlowTwoWayDelayVarMin    	Counter32,
		           generatorResultFlowTwoWayDelayVarMax    	Counter32
		          		             }
		
		generatorResultIndex OBJECT-TYPE
			SYNTAX Integer32
			MAX-ACCESS read-only
			STATUS current
			DESCRIPTION
				""
			::= { generatorResultEntry 1 }
			         
		generatorResultPHFPIndex OBJECT-TYPE
			SYNTAX Integer32
			MAX-ACCESS read-only
			STATUS current
			DESCRIPTION
				""
			::= { generatorResultEntry 2 }
		    
				                                                         
		generatorResultFlowTransPackets OBJECT-TYPE
			SYNTAX Counter32
			MAX-ACCESS read-only
			STATUS current
			DESCRIPTION
				""
			::= { generatorResultEntry 3 }
			                         

		generatorResultFlowTransBytes OBJECT-TYPE
			SYNTAX Counter32
			MAX-ACCESS read-only
			STATUS current
			DESCRIPTION
				""
			::= { generatorResultEntry 4 }


		generatorResultFlowTransRate OBJECT-TYPE
			SYNTAX Counter32
			MAX-ACCESS read-only
			STATUS current
			DESCRIPTION
				""
			::= { generatorResultEntry 5 }


		generatorResultFlowRecvPackets OBJECT-TYPE
			SYNTAX Counter32
			MAX-ACCESS read-only
			STATUS current
			DESCRIPTION
				""
			::= { generatorResultEntry 6 }
			                         

		generatorResultFlowRecvBytes OBJECT-TYPE
			SYNTAX Counter32
			MAX-ACCESS read-only
			STATUS current
			DESCRIPTION
				""
			::= { generatorResultEntry 7 }


		generatorResultFlowRecvRate OBJECT-TYPE
			SYNTAX Counter32
			MAX-ACCESS read-only
			STATUS current
			DESCRIPTION
				""
			::= { generatorResultEntry 8 }
			                             

		generatorResultFlowOOODuplicates OBJECT-TYPE
			SYNTAX Counter32
			MAX-ACCESS read-only
			STATUS current
			DESCRIPTION
				""
			::= { generatorResultEntry 9 }


		generatorResultFlowNumberOfGaps OBJECT-TYPE
			SYNTAX Counter32
			MAX-ACCESS read-only
			STATUS current
			DESCRIPTION
				""
			::= { generatorResultEntry 10 }
			
			
		generatorResultFlowMaxGap OBJECT-TYPE
			SYNTAX Counter32
			MAX-ACCESS read-only
			STATUS current
			DESCRIPTION
				""
			::= { generatorResultEntry 11 }
			

		generatorResultFlowTwoWayDelayInstant OBJECT-TYPE
			SYNTAX Counter32
			MAX-ACCESS read-only
			STATUS current
			DESCRIPTION
				""
			::= { generatorResultEntry 12 }


		generatorResultFlowTwoWayDelayAverage OBJECT-TYPE
			SYNTAX Counter32
			MAX-ACCESS read-only
			STATUS current
			DESCRIPTION
				""
			::= { generatorResultEntry 13 }


		generatorResultFlowTwoWayDelayMin OBJECT-TYPE
			SYNTAX Counter32
			MAX-ACCESS read-only
			STATUS current
			DESCRIPTION
				""
			::= { generatorResultEntry 14 }


		generatorResultFlowTwoWayDelayMax OBJECT-TYPE
			SYNTAX Counter32
			MAX-ACCESS read-only
			STATUS current
			DESCRIPTION
				""
			::= { generatorResultEntry 15 }            
			
			
		generatorResultFlowTwoWayDelayVarInstant OBJECT-TYPE
			SYNTAX Counter32
			MAX-ACCESS read-only
			STATUS current
			DESCRIPTION
				""
			::= { generatorResultEntry 16 }


		generatorResultFlowTwoWayDelayVarAverage OBJECT-TYPE
			SYNTAX Counter32
			MAX-ACCESS read-only
			STATUS current
			DESCRIPTION
				""
			::= { generatorResultEntry 17 }


		generatorResultFlowTwoWayDelayVarMin OBJECT-TYPE
			SYNTAX Counter32
			MAX-ACCESS read-only
			STATUS current
			DESCRIPTION
				""
			::= { generatorResultEntry 18 }


		generatorResultFlowTwoWayDelayVarMax OBJECT-TYPE
			SYNTAX Counter32
			MAX-ACCESS read-only
			STATUS current
			DESCRIPTION
				""
			::= { generatorResultEntry 19 }            
			

		rfc2544Monitor OBJECT IDENTIFIER ::= { wriRfc2544 3 }
                                                   
		monitorConfig OBJECT IDENTIFIER ::= { rfc2544Monitor 1 }
		                                                                                                                                      
		monitorConfigTable OBJECT-TYPE
		   SYNTAX SEQUENCE OF MonitorConfigEntry
		   MAX-ACCESS not-accessible
		   STATUS current
		   DESCRIPTION
		       ""
		   ::= { monitorConfig 1 }
                                       
                                                   
		monitorConfigEntry OBJECT-TYPE
		    SYNTAX MonitorConfigEntry
		    MAX-ACCESS not-accessible
		    STATUS current
		    DESCRIPTION
		       ""
		    INDEX { monitorIndex }
		    ::= { monitorConfigTable 1 }

        
		MonitorConfigEntry ::=
		    SEQUENCE { 
		           monitorIndex               		Integer32,
		           monitorConfigState          		INTEGER,
		           monitorName             			OCTET STRING,
		           monitorDescription      			OCTET STRING,            
		           monitorMode			   			INTEGER,
		           monitorBindPort			   		Integer32,
		           monitorRunState            		INTEGER ,
		           monitorPacketType        		INTEGER,
		           monitorPacketSrcMac         		PhysAddress, 
		           monitorPacketDstMac         		PhysAddress,
		           monitorPacketSrcMacMask         	PhysAddress, 
		           monitorPacketDstMacMask         	PhysAddress,
		           monitorPacketOAMLevel    		Integer32, 
		           monitorPacketEthType    	    	Integer32, 
		           monitorPacketQoSType    	   		INTEGER,
		           monitorPacketDSCPType      					INTEGER,
		           monitorPacketDSCPFixedValue      			Integer32,
		           monitorPacketDSCPRandomMinValue      		Integer32,
		           monitorPacketDSCPRandomMaxValue      		Integer32,
		           monitorPacketTosType      					INTEGER,
		           monitorPacketTosFixedValue      				Integer32, 
		           monitorPacketTosRandomMinValue      			Integer32,
                   monitorPacketTosRandomMaxValue      			Integer32,        
		           monitorPacketDstIp      	    				InetAddress,
		           monitorPacketSrcIp      						InetAddress,
		           monitorPacketDstIpMask         	            InetAddress,
		           monitorPacketSrcIpMask         	            InetAddress,  
		           monitorPacketDstPort     					Integer32, 
		           monitorPacketSrcPort     					Integer32,
		           monitorPacketL4Type              			INTEGER,    
		           monitorPacketMep     						Integer32,
		           monitorPacketCvlanState        				INTEGER,
		           monitorPacketCvlanPriType    				INTEGER,
		           monitorPacketCvlanPriFixedValue      		Integer32,
		           monitorPacketCvlanPriRandomMinValue      	Integer32,
		           monitorPacketCvlanPriRandomMaxValue      	Integer32,
		           monitorPacketCvlanCFI         	            Integer32,
		           monitorPacketCvlanIDType    					INTEGER,
		           monitorPacketCvlanIDFixedValue      			Integer32,
		           monitorPacketCvlanIDRandomMinValue      		Integer32,
		           monitorPacketCvlanIDRandomMaxValue      		Integer32,
		           monitorPacketCvlanTPID                   	Integer32, 
		           monitorPacketSvlanState        	            INTEGER,
		           monitorPacketSvlanPriType    	            INTEGER,
		           monitorPacketSvlanPriFixedValue      		Integer32,
		           monitorPacketSvlanPriRandomMinValue      	Integer32,
		           monitorPacketSvlanPriRandomMaxValue      	Integer32,
		           monitorPacketSvlanCFI         				Integer32,
		           monitorPacketSvlanIDType    					INTEGER,
		           monitorPacketSvlanIDFixedValue      			Integer32,
		           monitorPacketSvlanIDRandomMinValue      		Integer32,
		           monitorPacketSvlanIDRandomMaxValue      		Integer32, 
		           monitorPacketSvlanTPID          				Integer32,
		           monitorPacketReset    						Integer32,
		           monitorDirection                             INTEGER
		             }
                                                                                    
			
		monitorIndex OBJECT-TYPE
			SYNTAX Integer32
			MAX-ACCESS read-only
			STATUS current
			DESCRIPTION
				""
			::= { monitorConfigEntry 1 }


		monitorConfigState OBJECT-TYPE
			SYNTAX INTEGER
				{
				disable(2),
				enable(1)
				}
			MAX-ACCESS read-write
			STATUS current
			DESCRIPTION
				""
			::= { monitorConfigEntry 2 }


		monitorName OBJECT-TYPE
			SYNTAX OCTET STRING
			MAX-ACCESS read-write
			STATUS current
			DESCRIPTION
				""
			::= { monitorConfigEntry 3 }

				
		monitorDescription OBJECT-TYPE
			SYNTAX OCTET STRING
			MAX-ACCESS read-write
			STATUS current
			DESCRIPTION
				""
			::= { monitorConfigEntry 4 }

		
		monitorMode OBJECT-TYPE
			SYNTAX INTEGER
				{
				terminal(1),
				bypass(2)
				}
			MAX-ACCESS read-write
			STATUS current
			DESCRIPTION
				""
			::= { monitorConfigEntry 5 }     
			
		monitorBindPort OBJECT-TYPE
			SYNTAX Integer32
			MAX-ACCESS read-write
			STATUS current
			DESCRIPTION
				""
			::= { monitorConfigEntry 6 }  
			
		monitorRunState OBJECT-TYPE
			SYNTAX INTEGER
			{
				idle(0),
				running(1),
				fail(2),
				success(3)
			}
			MAX-ACCESS read-write
			STATUS current
			DESCRIPTION
				""
			::= { monitorConfigEntry 7 }


		monitorPacketType OBJECT-TYPE
			SYNTAX INTEGER
				{ 
				unknown(0),
				layer2(1),      
				layer3(2)
				}
			MAX-ACCESS read-write
			STATUS current
			DESCRIPTION
				""
			::= { monitorConfigEntry 8 }


		monitorPacketSrcMac OBJECT-TYPE
			SYNTAX PhysAddress
			MAX-ACCESS read-write
			STATUS current
			DESCRIPTION
				""
			::= { monitorConfigEntry 9 }    
			
		monitorPacketDstMac OBJECT-TYPE
			SYNTAX PhysAddress
			MAX-ACCESS read-write
			STATUS current
			DESCRIPTION
				""
			::= { monitorConfigEntry 10 } 
			
		monitorPacketSrcMacMask OBJECT-TYPE
			SYNTAX PhysAddress
			MAX-ACCESS read-write
			STATUS current
			DESCRIPTION
				""
			::= { monitorConfigEntry 11 }    
			
		monitorPacketDstMacMask OBJECT-TYPE
			SYNTAX PhysAddress
			MAX-ACCESS read-write
			STATUS current
			DESCRIPTION
				""
			::= { monitorConfigEntry 12 }
			

		monitorPacketOAMLevel OBJECT-TYPE
			SYNTAX Integer32
			MAX-ACCESS read-write
			STATUS current
			DESCRIPTION
				""
			::= { monitorConfigEntry 13 } 
			
		monitorPacketEthType OBJECT-TYPE
			SYNTAX Integer32
			MAX-ACCESS read-write
			STATUS current
			DESCRIPTION
				""
			::= { monitorConfigEntry 14 }
			
		monitorPacketQoSType OBJECT-TYPE
			SYNTAX INTEGER
			{
				dscp(1),		
				tos(2)      		
			}
			MAX-ACCESS read-write
			STATUS current
			DESCRIPTION
				""
			::= { monitorConfigEntry 15 }
			
		monitorPacketDSCPType OBJECT-TYPE
			SYNTAX INTEGER
				{
				fixed(1),
				random(2)
				}		
			MAX-ACCESS read-write
			STATUS current
			DESCRIPTION
				""
			::= { monitorConfigEntry 16 }
			
		monitorPacketDSCPFixedValue OBJECT-TYPE
			SYNTAX Integer32		
			MAX-ACCESS read-write
			STATUS current
			DESCRIPTION
				""
			::= { monitorConfigEntry 17 } 
			
		monitorPacketDSCPRandomMinValue OBJECT-TYPE
			SYNTAX Integer32		
			MAX-ACCESS read-write
			STATUS current
			DESCRIPTION
				""
			::= { monitorConfigEntry 18 } 
			
		monitorPacketDSCPRandomMaxValue OBJECT-TYPE
			SYNTAX Integer32		
			MAX-ACCESS read-write
			STATUS current
			DESCRIPTION
				""
			::= { monitorConfigEntry 19 }   
			
		monitorPacketTosType OBJECT-TYPE
			SYNTAX INTEGER
				{
				fixed(1),
				random(2)
				}		
			MAX-ACCESS read-write
			STATUS current
			DESCRIPTION
				""
			::= { monitorConfigEntry 20 }
			
		monitorPacketTosFixedValue OBJECT-TYPE
			SYNTAX Integer32		
			MAX-ACCESS read-write
			STATUS current
			DESCRIPTION
				""
			::= { monitorConfigEntry 21 } 
			
		monitorPacketTosRandomMinValue OBJECT-TYPE
			SYNTAX Integer32		
			MAX-ACCESS read-write
			STATUS current
			DESCRIPTION
				""
			::= { monitorConfigEntry 22 } 
			
		monitorPacketTosRandomMaxValue OBJECT-TYPE
			SYNTAX Integer32		
			MAX-ACCESS read-write
			STATUS current
			DESCRIPTION
				""
			::= { monitorConfigEntry 23 }   
	
			
		monitorPacketDstIp OBJECT-TYPE
			SYNTAX InetAddress
			MAX-ACCESS read-write
			STATUS current
			DESCRIPTION
				""
			::= { monitorConfigEntry 24 } 
			
		monitorPacketSrcIp OBJECT-TYPE
			SYNTAX InetAddress
			MAX-ACCESS read-write
			STATUS current
			DESCRIPTION
				""
			::= { monitorConfigEntry 25 }
			
		monitorPacketDstIpMask OBJECT-TYPE
			SYNTAX InetAddress
			MAX-ACCESS read-write
			STATUS current
			DESCRIPTION
				""
			::= { monitorConfigEntry 26 } 
			
		monitorPacketSrcIpMask OBJECT-TYPE
			SYNTAX InetAddress
			MAX-ACCESS read-write
			STATUS current
			DESCRIPTION
				""
			::= { monitorConfigEntry 27 }    
			
		monitorPacketDstPort OBJECT-TYPE
			SYNTAX Integer32
			MAX-ACCESS read-write
			STATUS current
			DESCRIPTION
				""
			::= { monitorConfigEntry 28 }
			
		monitorPacketSrcPort OBJECT-TYPE
			SYNTAX Integer32
			MAX-ACCESS read-write
			STATUS current
			DESCRIPTION
				""
			::= { monitorConfigEntry 29 } 
			                                  
		monitorPacketL4Type OBJECT-TYPE
			SYNTAX INTEGER  
				{
				tcp(6),		
				udp(17)      		
				}
			MAX-ACCESS read-only
			STATUS current
			DESCRIPTION
				""
			::= { monitorConfigEntry 30 } 
			
				
		monitorPacketMep OBJECT-TYPE
			SYNTAX Integer32
			MAX-ACCESS read-write
			STATUS current
			DESCRIPTION
				""
			::= { monitorConfigEntry 31 }				


		monitorPacketCvlanState OBJECT-TYPE
			SYNTAX INTEGER
				{
				disable(2),
				enable(1)
				}
			MAX-ACCESS read-write
			STATUS current
			DESCRIPTION
				""
			::= { monitorConfigEntry 32 }
					
		monitorPacketCvlanPriType OBJECT-TYPE
			SYNTAX INTEGER
				{
				fixed(1),
				random(2)
				}		
			MAX-ACCESS read-write
			STATUS current
			DESCRIPTION
				""
			::= { monitorConfigEntry 33 }
			
		monitorPacketCvlanPriFixedValue OBJECT-TYPE
			SYNTAX Integer32		
			MAX-ACCESS read-write
			STATUS current
			DESCRIPTION
				""
			::= { monitorConfigEntry 34 } 
			
		monitorPacketCvlanPriRandomMinValue OBJECT-TYPE
			SYNTAX Integer32		
			MAX-ACCESS read-write
			STATUS current
			DESCRIPTION
				""
			::= { monitorConfigEntry 35 } 
			
		monitorPacketCvlanPriRandomMaxValue OBJECT-TYPE
			SYNTAX Integer32		
			MAX-ACCESS read-write
			STATUS current
			DESCRIPTION
				""
			::= { monitorConfigEntry 36 } 
		    

		monitorPacketCvlanCFI OBJECT-TYPE
			SYNTAX Integer32
			MAX-ACCESS read-write
			STATUS current
			DESCRIPTION
				""
			::= { monitorConfigEntry 37 }


		monitorPacketCvlanIDType OBJECT-TYPE
			SYNTAX INTEGER
				{
				fixed(1),
				random(2)
				}		
			MAX-ACCESS read-write
			STATUS current
			DESCRIPTION
				""
			::= { monitorConfigEntry 38 }
			
		monitorPacketCvlanIDFixedValue OBJECT-TYPE
			SYNTAX Integer32		
			MAX-ACCESS read-write
			STATUS current
			DESCRIPTION
				""
			::= { monitorConfigEntry 39 } 
			
		monitorPacketCvlanIDRandomMinValue OBJECT-TYPE
			SYNTAX Integer32		
			MAX-ACCESS read-write
			STATUS current
			DESCRIPTION
				""
			::= { monitorConfigEntry 40 } 
			
		monitorPacketCvlanIDRandomMaxValue OBJECT-TYPE
			SYNTAX Integer32		
			MAX-ACCESS read-write
			STATUS current
			DESCRIPTION
				""
			::= { monitorConfigEntry 41 } 
			
		monitorPacketCvlanTPID OBJECT-TYPE
			SYNTAX Integer32		
			MAX-ACCESS read-write
			STATUS current
			DESCRIPTION
				""
			::= { monitorConfigEntry 42 }   
			
		monitorPacketSvlanState OBJECT-TYPE
			SYNTAX INTEGER
				{
				disable(2),
				enable(1)
				}
			MAX-ACCESS read-write
			STATUS current
			DESCRIPTION
				""
			::= { monitorConfigEntry 43 }

		    
		monitorPacketSvlanPriType OBJECT-TYPE
			SYNTAX INTEGER
				{
				fixed(1),
				random(2)
				}		
			MAX-ACCESS read-write
			STATUS current
			DESCRIPTION
				""
			::= { monitorConfigEntry 44 }
			
		monitorPacketSvlanPriFixedValue OBJECT-TYPE
			SYNTAX Integer32		
			MAX-ACCESS read-write
			STATUS current
			DESCRIPTION
				""
			::= { monitorConfigEntry 45 } 
			
		monitorPacketSvlanPriRandomMinValue OBJECT-TYPE
			SYNTAX Integer32		
			MAX-ACCESS read-write
			STATUS current
			DESCRIPTION
				""
			::= { monitorConfigEntry 46 } 
			
		monitorPacketSvlanPriRandomMaxValue OBJECT-TYPE
			SYNTAX Integer32		
			MAX-ACCESS read-write
			STATUS current
			DESCRIPTION
				""
			::= { monitorConfigEntry 47 }		    

		monitorPacketSvlanCFI OBJECT-TYPE
			SYNTAX Integer32
			MAX-ACCESS read-write
			STATUS current
			DESCRIPTION
				""
			::= { monitorConfigEntry 48 }


		monitorPacketSvlanIDType OBJECT-TYPE
			SYNTAX INTEGER
				{
				fixed(1),
				random(2)
				}		
			MAX-ACCESS read-write
			STATUS current
			DESCRIPTION
				""
			::= { monitorConfigEntry 49 }
			
		monitorPacketSvlanIDFixedValue OBJECT-TYPE
			SYNTAX Integer32		
			MAX-ACCESS read-write
			STATUS current
			DESCRIPTION
				""
			::= { monitorConfigEntry 50 } 
			
		monitorPacketSvlanIDRandomMinValue OBJECT-TYPE
			SYNTAX Integer32		
			MAX-ACCESS read-write
			STATUS current
			DESCRIPTION
				""
			::= { monitorConfigEntry 51 } 
			
		monitorPacketSvlanIDRandomMaxValue OBJECT-TYPE
			SYNTAX Integer32		
			MAX-ACCESS read-write
			STATUS current
			DESCRIPTION
				""
			::= { monitorConfigEntry 52 } 
			
		monitorPacketSvlanTPID OBJECT-TYPE
			SYNTAX Integer32		
			MAX-ACCESS read-write
			STATUS current
			DESCRIPTION
				""
			::= { monitorConfigEntry 53 }  
          
        monitorPacketReset OBJECT-TYPE
			SYNTAX Integer32		
			MAX-ACCESS read-write
			STATUS current
			DESCRIPTION
				""
			::= { monitorConfigEntry 54 }
			
		 monitorDirection OBJECT-TYPE
			SYNTAX INTEGER
			{
				uni(1),
				bi(2)
				}		
			MAX-ACCESS read-write
			STATUS current
			DESCRIPTION
				""
			::= { monitorConfigEntry 55 }                                             

		monitorResultTable OBJECT-TYPE
		   SYNTAX SEQUENCE OF MonitorResultEntry
		   MAX-ACCESS not-accessible
		   STATUS current
		   DESCRIPTION
		       ""
		   ::= { rfc2544Monitor 2 }
                                       
                                                   
		monitorResultEntry OBJECT-TYPE
		    SYNTAX MonitorResultEntry
		    MAX-ACCESS not-accessible
		    STATUS current
		    DESCRIPTION
		       ""
		    INDEX { monitorResultIndex }
		    ::= { monitorResultTable 1 }

        
		MonitorResultEntry ::=
		    SEQUENCE {                                      
		    	   monitorResultIndex                       Integer32,
		           monitorResultRecvPackets					Counter32,
		           monitorResultRecvBytes          			Counter32,
		           monitorResultRecvRate      				Counter32,
		           monitorResultOOODuplicates       	    Counter32,
		           monitorResultNumberOfGaps                Counter32,
		           monitorResultMaxGap           		    Counter32,
		           monitorResultOneWayDelayInstant          Counter32,
		           monitorResultOneWayDelayAverage          Counter32,
		           monitorResultOneWayDelayMin              Counter32,
		           monitorResultOneWayDelayMax              Counter32,
		           monitorResultOneWayDelayVarInstant       Counter32,
		           monitorResultOneWayDelayVarAverage       Counter32,
		           monitorResultOneWayDelayVarMin       	Counter32,
		           monitorResultOneWayDelayVarMax       	Counter32,
		           monitorResultReset      					Integer32          
		           		             }
                          
                          
        monitorResultIndex OBJECT-TYPE
			SYNTAX Integer32
			MAX-ACCESS read-only
			STATUS current
			DESCRIPTION
				""
			::= { monitorResultEntry 1 }                                                          
			
		monitorResultRecvPackets OBJECT-TYPE
			SYNTAX Counter32
			MAX-ACCESS read-only
			STATUS current
			DESCRIPTION
				""
			::= { monitorResultEntry 2 }
			                         

		monitorResultRecvBytes OBJECT-TYPE
			SYNTAX Counter32
			MAX-ACCESS read-only
			STATUS current
			DESCRIPTION
				""
			::= { monitorResultEntry 3 }


		monitorResultRecvRate OBJECT-TYPE
			SYNTAX Counter32
			MAX-ACCESS read-only
			STATUS current
			DESCRIPTION
				""
			::= { monitorResultEntry 4 }  
			
		monitorResultOOODuplicates OBJECT-TYPE
			SYNTAX Counter32
			MAX-ACCESS read-only
			STATUS current
			DESCRIPTION
				""
			::= { monitorResultEntry 5 }


		monitorResultNumberOfGaps OBJECT-TYPE
			SYNTAX Counter32
			MAX-ACCESS read-only
			STATUS current
			DESCRIPTION
				""
			::= { monitorResultEntry 6 }
			
			
		monitorResultMaxGap OBJECT-TYPE
			SYNTAX Counter32
			MAX-ACCESS read-only
			STATUS current
			DESCRIPTION
				""
			::= { monitorResultEntry 7 }
			

		monitorResultOneWayDelayInstant OBJECT-TYPE
			SYNTAX Counter32
			MAX-ACCESS read-only
			STATUS current
			DESCRIPTION
				""
			::= { monitorResultEntry 8 }


		monitorResultOneWayDelayAverage OBJECT-TYPE
			SYNTAX Counter32
			MAX-ACCESS read-only
			STATUS current
			DESCRIPTION
				""
			::= { monitorResultEntry 9 }


		monitorResultOneWayDelayMin OBJECT-TYPE
			SYNTAX Counter32
			MAX-ACCESS read-only
			STATUS current
			DESCRIPTION
				""
			::= { monitorResultEntry 10 }


		monitorResultOneWayDelayMax OBJECT-TYPE
			SYNTAX Counter32
			MAX-ACCESS read-only
			STATUS current
			DESCRIPTION
				""
			::= { monitorResultEntry 11 }            
			
			
		monitorResultOneWayDelayVarInstant OBJECT-TYPE
			SYNTAX Counter32
			MAX-ACCESS read-only
			STATUS current
			DESCRIPTION
				""
			::= { monitorResultEntry 12 }


		monitorResultOneWayDelayVarAverage OBJECT-TYPE
			SYNTAX Counter32
			MAX-ACCESS read-only
			STATUS current
			DESCRIPTION
				""
			::= { monitorResultEntry 13 }


		monitorResultOneWayDelayVarMin OBJECT-TYPE
			SYNTAX Counter32
			MAX-ACCESS read-only
			STATUS current
			DESCRIPTION
				""
			::= { monitorResultEntry 14 }


		monitorResultOneWayDelayVarMax OBJECT-TYPE
			SYNTAX Counter32
			MAX-ACCESS read-only
			STATUS current
			DESCRIPTION
				""
			::= { monitorResultEntry 15 }    
			
		monitorResultReset OBJECT-TYPE
			SYNTAX Integer32
			MAX-ACCESS read-write
			STATUS current
			DESCRIPTION
				""
			::= { monitorResultEntry 16 } 		
			                             

		rfc2544Testsuite OBJECT IDENTIFIER ::= { wriRfc2544 4 }
                                                   
		testsuiteConfig OBJECT IDENTIFIER ::= { rfc2544Testsuite 1 }
		                                                                                                                                      
		testsuiteConfigTable OBJECT-TYPE
		   SYNTAX SEQUENCE OF TestsuiteConfigEntry
		   MAX-ACCESS not-accessible
		   STATUS current
		   DESCRIPTION
		       ""
		   ::= { testsuiteConfig 1 }
                                       
                                                   
		testsuiteConfigEntry OBJECT-TYPE
		    SYNTAX TestsuiteConfigEntry
		    MAX-ACCESS not-accessible
		    STATUS current
		    DESCRIPTION
		       ""
		    INDEX { testsuiteIndex }
		    ::= { testsuiteConfigTable 1 }

        
		TestsuiteConfigEntry ::=
		    SEQUENCE { 
		           testsuiteIndex             	Integer32,
		           testsuiteName				OCTET STRING,
		           testsuiteDescription         OCTET STRING,
		           testsuiteJumboFrameSize      Integer32,
		           testsuiteBinaryDuration      Integer32,
		           testsuiteStrictFailureState  INTEGER,
		           testsuiteVerboseReportState  INTEGER, 
		           testsuiteThroughputState  	INTEGER,
		           testsuiteFrameLossState      INTEGER,
		           testsuiteDelayState  		INTEGER,
		           testsuiteBackToBackState  	INTEGER, 
		           testsuiteBindPort  			Integer32,
		           testsuiteConfigState  		INTEGER,
		           testsuiteRunState  			INTEGER,
		           testsuiteRowstatus           RowStatus,
		           testsuitePeerType        	INTEGER,
		           testsuitePeerSrcMac         	PhysAddress,
		           testsuitePeerDstMac         	PhysAddress,
		           testsuitePeerOAMLevel    	Integer32,
		           testsuitePeerEthType    	    Integer32,
		           testsuitePeerQoSType  		INTEGER, 
		           testsuitePeerDSCP     		Integer32,
		           testsuitePeerTos      		Integer32,
		           testsuitePeerDstIp      	    InetAddress,
		           testsuitePeerSrcIp      		InetAddress,  
		           testsuitePeerDstPort     	Integer32, 
		           testsuitePeerSrcPort     	Integer32,
		           testsuitePeerL4Type        	INTEGER,
		           testsuitePeerMep     		Integer32,
		           testsuitePeerCvlanState        	INTEGER,
			       testsuitePeerCvlanPriority    	Integer32,
		           testsuitePeerCvlanCFI         	Integer32,
		           testsuitePeerCvlanID          	Integer32,
		           testsuitePeerCvlanTPID          	Integer32,
		           testsuitePeerSvlanState        	INTEGER,
			       testsuitePeerSvlanPriority    	Integer32,
		           testsuitePeerSvlanCFI         	Integer32,
		           testsuitePeerSvlanID          	Integer32, 
		           testsuitePeerSvlanTPID          	Integer32,		
		           testsuiteThroughputTrialDuration     Integer32,
		           testsuiteThroughputStepSize          Integer32,
		           testsuiteThroughputUseFineStepping   INTEGER,
		           testsuiteThroughputMaxRate  			Integer32,            
		           testsuiteThroughputMinRate  			Integer32,            
		           testsuiteThroughputFrameLoss 		Integer32,
		           testsuiteThroughputFrameSizeBitList   	INTEGER,
		           testsuiteDelayTrialDuration     		Integer32,
		           testsuiteDelayFrameLoss 				Integer32,
		           testsuiteDelayFrameSizeBitList   		INTEGER,
		           testsuiteFrameLossTrialDuration     	Integer32,
		           testsuiteFrameLossStepSize 			Integer32,
		           testsuiteFrameLossFrameSizeBitList   	INTEGER, 
		           testsuiteBackToBackTrialDuration 	Integer32,
		           testsuiteBackToBackRepeat 			Integer32,
		           testsuiteBackToBackFrameSizeBitList   	INTEGER,
		           testsuiteReset     				Integer32,
		           testsuiteReceivePort     		Integer32,
		           testsuiteRole     				Integer32
		             }
                                                                                    
		testsuiteIndex OBJECT-TYPE
			SYNTAX Integer32
			MAX-ACCESS read-only
			STATUS current
			DESCRIPTION
				""
			::= { testsuiteConfigEntry 1 }


		testsuiteName OBJECT-TYPE
			SYNTAX OCTET STRING
			MAX-ACCESS read-write
			STATUS current
			DESCRIPTION
				""
			::= { testsuiteConfigEntry 2 }


		testsuiteDescription OBJECT-TYPE
			SYNTAX OCTET STRING
			MAX-ACCESS read-write
			STATUS current
			DESCRIPTION
				""
			::= { testsuiteConfigEntry 3 }
                                    

		testsuiteJumboFrameSize OBJECT-TYPE
			SYNTAX Integer32
			MAX-ACCESS read-only
			STATUS current
			DESCRIPTION
				""
			::= { testsuiteConfigEntry 4 }


		testsuiteBinaryDuration OBJECT-TYPE
			SYNTAX Integer32
			MAX-ACCESS read-only
			STATUS current
			DESCRIPTION
				""
			::= { testsuiteConfigEntry 5 }
                                       

		testsuiteStrictFailureState OBJECT-TYPE
			SYNTAX INTEGER
				{
				disable(2),
				enable(1)
				}
			MAX-ACCESS read-write
			STATUS current
			DESCRIPTION
				""
			::= { testsuiteConfigEntry 6 }


		testsuiteVerboseReportState OBJECT-TYPE
			SYNTAX INTEGER
				{
				disable(2),
				enable(1)
				}
			MAX-ACCESS read-write
			STATUS current
			DESCRIPTION
				""
			::= { testsuiteConfigEntry 7 }


		testsuiteThroughputState OBJECT-TYPE
			SYNTAX INTEGER
				{
				disable(2),
				enable(1)
				}
			MAX-ACCESS read-write
			STATUS current
			DESCRIPTION
				""
			::= { testsuiteConfigEntry 8 }
			

		testsuiteFrameLossState OBJECT-TYPE
			SYNTAX INTEGER
				{
				disable(2),
				enable(1)
				}
			MAX-ACCESS read-write
			STATUS current
			DESCRIPTION
				""
			::= { testsuiteConfigEntry 9 }
			

		testsuiteDelayState OBJECT-TYPE
			SYNTAX INTEGER
				{
				disable(2),
				enable(1)
				}
			MAX-ACCESS read-write
			STATUS current
			DESCRIPTION
				""
			::= { testsuiteConfigEntry 10 }


		testsuiteBackToBackState OBJECT-TYPE
			SYNTAX INTEGER
				{
				disable(2),
				enable(1)
				}
			MAX-ACCESS read-write
			STATUS current
			DESCRIPTION
				""
			::= { testsuiteConfigEntry 11 }  
			
		testsuiteBindPort OBJECT-TYPE
			SYNTAX Integer32
			MAX-ACCESS read-write
			STATUS current
			DESCRIPTION
				""
			::= { testsuiteConfigEntry 12 }  
			
		testsuiteConfigState OBJECT-TYPE
			SYNTAX INTEGER
				{
				stop(2),
				start(1)
				}
			MAX-ACCESS read-write
			STATUS current
			DESCRIPTION
				""
			::= { testsuiteConfigEntry 13 }   
			
		testsuiteRunState OBJECT-TYPE
			SYNTAX INTEGER
				{
				idle(0),
				running(1),
				fail(2),
				success(3)
				}
			MAX-ACCESS read-write
			STATUS current
			DESCRIPTION
				""
			::= { testsuiteConfigEntry 14 } 
			
		testsuiteRowstatus OBJECT-TYPE
			SYNTAX RowStatus
			MAX-ACCESS read-write
			STATUS current
			DESCRIPTION
				""
			::= { testsuiteConfigEntry 15 }

		
		testsuitePeerType OBJECT-TYPE
			SYNTAX INTEGER
				{ 
				unknown(0),
				layer2(1),      
				layer3(2)				
				}
			MAX-ACCESS read-write
			STATUS current
			DESCRIPTION
				""
			::= { testsuiteConfigEntry 16 }


		testsuitePeerSrcMac OBJECT-TYPE
			SYNTAX PhysAddress
			MAX-ACCESS read-write
			STATUS current
			DESCRIPTION
				""
			::= { testsuiteConfigEntry 17 } 
			
		testsuitePeerDstMac OBJECT-TYPE
			SYNTAX PhysAddress
			MAX-ACCESS read-write
			STATUS current
			DESCRIPTION
				""
			::= { testsuiteConfigEntry 18 }
			

		testsuitePeerOAMLevel OBJECT-TYPE
			SYNTAX Integer32
			MAX-ACCESS read-write
			STATUS current
			DESCRIPTION
				""
			::= { testsuiteConfigEntry 19 }
			
		testsuitePeerEthType OBJECT-TYPE
			SYNTAX Integer32
			MAX-ACCESS read-write
			STATUS current
			DESCRIPTION
				""
			::= { testsuiteConfigEntry 20 }
			
		testsuitePeerQoSType OBJECT-TYPE
			SYNTAX INTEGER 
			{
			 dscp(1),
			 tos(2)
			}
			MAX-ACCESS read-write
			STATUS current
			DESCRIPTION
				""
			::= { testsuiteConfigEntry 21 }
			 
		testsuitePeerDSCP OBJECT-TYPE
			SYNTAX Integer32
			MAX-ACCESS read-write
			STATUS current
			DESCRIPTION
				""
			::= { testsuiteConfigEntry 22 }
			
		testsuitePeerTos OBJECT-TYPE
			SYNTAX Integer32
			MAX-ACCESS read-write
			STATUS current
			DESCRIPTION
				""
			::= { testsuiteConfigEntry 23 } 		
			
		testsuitePeerDstIp OBJECT-TYPE
			SYNTAX InetAddress
			MAX-ACCESS read-write
			STATUS current
			DESCRIPTION
				""
			::= { testsuiteConfigEntry 24 } 
			
		testsuitePeerSrcIp OBJECT-TYPE
			SYNTAX InetAddress
			MAX-ACCESS read-write
			STATUS current
			DESCRIPTION
				""
			::= { testsuiteConfigEntry 25 }    
			
		testsuitePeerDstPort OBJECT-TYPE
			SYNTAX Integer32
			MAX-ACCESS read-write
			STATUS current
			DESCRIPTION
				""
			::= { testsuiteConfigEntry 26 }
			
		testsuitePeerSrcPort OBJECT-TYPE
			SYNTAX Integer32
			MAX-ACCESS read-write
			STATUS current
			DESCRIPTION
				""
			::= { testsuiteConfigEntry 27 }
			
		testsuitePeerL4Type OBJECT-TYPE
			SYNTAX INTEGER
				{
				tcp(6),
				udp(17)
				}
			MAX-ACCESS read-only
			STATUS current
			DESCRIPTION
				""
			::= { testsuiteConfigEntry 28 } 
			
			
		testsuitePeerMep OBJECT-TYPE
			SYNTAX Integer32
			MAX-ACCESS read-write
			STATUS current
			DESCRIPTION
				""
			::= { testsuiteConfigEntry 29 }                                      
						
			                                                  
		testsuitePeerCvlanState OBJECT-TYPE
			SYNTAX INTEGER
				{
				disable(2),
				enable(1)
				}
			MAX-ACCESS read-write
			STATUS current
			DESCRIPTION
				""
			::= { testsuiteConfigEntry 30 }

		testsuitePeerCvlanPriority OBJECT-TYPE
			SYNTAX Integer32
			MAX-ACCESS read-write
			STATUS current
			DESCRIPTION
				""
			::= { testsuiteConfigEntry 31 }
		    

		testsuitePeerCvlanCFI OBJECT-TYPE
			SYNTAX Integer32
			MAX-ACCESS read-write
			STATUS current
			DESCRIPTION
				""
			::= { testsuiteConfigEntry 32 }


		testsuitePeerCvlanID OBJECT-TYPE
			SYNTAX Integer32
			MAX-ACCESS read-write
			STATUS current
			DESCRIPTION
				""
			::= { testsuiteConfigEntry 33 }
			
		testsuitePeerCvlanTPID OBJECT-TYPE
			SYNTAX Integer32
			MAX-ACCESS read-write
			STATUS current
			DESCRIPTION
				""
			::= { testsuiteConfigEntry 34 }  
			
		testsuitePeerSvlanState OBJECT-TYPE
			SYNTAX INTEGER
				{
				disable(2),
				enable(1)
				}
			MAX-ACCESS read-write
			STATUS current
			DESCRIPTION
				""
			::= { testsuiteConfigEntry 35 }

		testsuitePeerSvlanPriority OBJECT-TYPE
			SYNTAX Integer32
			MAX-ACCESS read-write
			STATUS current
			DESCRIPTION
				""
			::= { testsuiteConfigEntry 36 }
		    

		testsuitePeerSvlanCFI OBJECT-TYPE
			SYNTAX Integer32
			MAX-ACCESS read-write
			STATUS current
			DESCRIPTION
				""
			::= { testsuiteConfigEntry 37 }


		testsuitePeerSvlanID OBJECT-TYPE
			SYNTAX Integer32
			MAX-ACCESS read-write
			STATUS current
			DESCRIPTION
				""
			::= { testsuiteConfigEntry 38 } 
			
		testsuitePeerSvlanTPID OBJECT-TYPE
			SYNTAX Integer32
			MAX-ACCESS read-write
			STATUS current
			DESCRIPTION
				""
			::= { testsuiteConfigEntry 39 }
                                                       
    						                      
		testsuiteThroughputTrialDuration OBJECT-TYPE
			SYNTAX Integer32
			MAX-ACCESS read-write
			STATUS current
			DESCRIPTION
				""
			::= { testsuiteConfigEntry 40 }
                                                       

		testsuiteThroughputStepSize OBJECT-TYPE
			SYNTAX Integer32
			MAX-ACCESS read-write
			STATUS current
			DESCRIPTION
				""
			::= { testsuiteConfigEntry 41 }


		testsuiteThroughputUseFineStepping OBJECT-TYPE
			SYNTAX INTEGER
				{
				selected(1),
				unselected(2)
				}
			MAX-ACCESS read-write
			STATUS current
			DESCRIPTION
				""
			::= { testsuiteConfigEntry 42 }
						                      
						                      
		testsuiteThroughputMaxRate OBJECT-TYPE
			SYNTAX Integer32
			MAX-ACCESS read-write
			STATUS current
			DESCRIPTION
				""
			::= { testsuiteConfigEntry 43 }
                                                       

		testsuiteThroughputMinRate OBJECT-TYPE
			SYNTAX Integer32
			MAX-ACCESS read-write
			STATUS current
			DESCRIPTION
				""
			::= { testsuiteConfigEntry 44 }


		testsuiteThroughputFrameLoss OBJECT-TYPE	
			SYNTAX Integer32
			MAX-ACCESS read-write
			STATUS current
			DESCRIPTION
				""
			::= { testsuiteConfigEntry 45 }


		testsuiteThroughputFrameSizeBitList OBJECT-TYPE
			SYNTAX INTEGER
			MAX-ACCESS read-write
			STATUS current
			DESCRIPTION
				""
			::= { testsuiteConfigEntry 46 }
				
						                      
		testsuiteDelayTrialDuration OBJECT-TYPE
			SYNTAX Integer32
			MAX-ACCESS read-write
			STATUS current
			DESCRIPTION
				""
			::= { testsuiteConfigEntry 47 }
                                                       

		testsuiteDelayFrameLoss OBJECT-TYPE
			SYNTAX Integer32
			MAX-ACCESS read-write
			STATUS current
			DESCRIPTION
				""
			::= { testsuiteConfigEntry 48 }


		testsuiteDelayFrameSizeBitList OBJECT-TYPE
			SYNTAX INTEGER
			MAX-ACCESS read-write
			STATUS current
			DESCRIPTION
				""
			::= { testsuiteConfigEntry 49 }

						                      
		testsuiteFrameLossTrialDuration OBJECT-TYPE
			SYNTAX Integer32
			MAX-ACCESS read-write
			STATUS current
			DESCRIPTION
				""
			::= { testsuiteConfigEntry 50 }
                                                       

		testsuiteFrameLossStepSize OBJECT-TYPE
			SYNTAX Integer32
			MAX-ACCESS read-write
			STATUS current
			DESCRIPTION
				""
			::= { testsuiteConfigEntry 51 }


		testsuiteFrameLossFrameSizeBitList OBJECT-TYPE
			SYNTAX INTEGER
			MAX-ACCESS read-write
			STATUS current
			DESCRIPTION
				""
			::= { testsuiteConfigEntry 52 }


		testsuiteBackToBackTrialDuration OBJECT-TYPE
			SYNTAX Integer32
			MAX-ACCESS read-write
			STATUS current
			DESCRIPTION
				""
			::= { testsuiteConfigEntry 53 }
                                                       

		testsuiteBackToBackRepeat OBJECT-TYPE
			SYNTAX Integer32
			MAX-ACCESS read-write
			STATUS current
			DESCRIPTION
				""
			::= { testsuiteConfigEntry 54 }


		testsuiteBackToBackFrameSizeBitList OBJECT-TYPE
			SYNTAX INTEGER
			MAX-ACCESS read-write
			STATUS current
			DESCRIPTION
				""
			::= { testsuiteConfigEntry 55 }  
			
		testsuiteReset OBJECT-TYPE
			SYNTAX Integer32
			MAX-ACCESS read-write
			STATUS current
			DESCRIPTION
				""
			::= { testsuiteConfigEntry 56 }          
			
		testsuiteReceivePort OBJECT-TYPE
			SYNTAX Integer32
			MAX-ACCESS read-write
			STATUS current
			DESCRIPTION
				""
			::= { testsuiteConfigEntry 57 }
			
		testsuiteRole OBJECT-TYPE
			SYNTAX Integer32
			MAX-ACCESS read-write
			STATUS current
			DESCRIPTION
				""
			::= { testsuiteConfigEntry 58 }


	-- 1.3.6.1.4.1.3807.2.1815.3.2
		testsuiteReport OBJECT IDENTIFIER ::= { rfc2544Testsuite 2 }
		
		-- 1.3.6.1.4.1.3807.2.1815.3.1.1
		testsuiteReportTable OBJECT-TYPE
			SYNTAX SEQUENCE OF TestsuiteReportEntry
			MAX-ACCESS not-accessible
			STATUS current
			DESCRIPTION	" "
			::= { testsuiteReport 1 }

		testsuiteReportEntry OBJECT-TYPE
		    SYNTAX TestsuiteReportEntry
		    MAX-ACCESS not-accessible
		    STATUS current
		    DESCRIPTION
		       ""
		    INDEX { testsuiteIndex ,testsuiteReportIndex}
		    ::= { testsuiteReportTable 1 } 
		    
		 TestsuiteReportEntry ::=
		    SEQUENCE { 
		           testsuiteReportIndex 	Integer32,
		           testsuiteReportBindSuit 			Integer32,
		           testsuiteReportFileName   	OCTET STRING,
		           testsuiteReportDescription   	OCTET STRING,
		           testsuiteReportTechnicalName   	OCTET STRING,
		           testsuiteReportNote   			OCTET STRING,
		           testsuiteReportRowstatus   		RowStatus, 
		           testsuiteReportUpload            INTEGER,
		           testsuiteReportFpRecvRate64            Counter32, 
		           testsuiteReportFpRecvRate128            Counter32,
		           testsuiteReportFpRecvRate256            Counter32,
		           testsuiteReportFpRecvRate512            Counter32,
		           testsuiteReportFpRecvRate1024           Counter32,
		           testsuiteReportFpRecvRate1280           Counter32,    
		           testsuiteReportFpRecvRate1518           Counter32,
		           testsuiteReportFpRecvRateJumbo          Counter32,
		           testsuiteReportFpSendRate64             Counter32, 
		           testsuiteReportFpSendRate128            Counter32,
		           testsuiteReportFpSendRate256            Counter32,
		           testsuiteReportFpSendRate512            Counter32,
		           testsuiteReportFpSendRate1024           Counter32,
		           testsuiteReportFpSendRate1280           Counter32,    
		           testsuiteReportFpSendRate1518           Counter32,
		           testsuiteReportFpSendRateJumbo          Counter32,
		           testsuiteReportDelayResult64            Counter32, 
		           testsuiteReportDelayResult128           Counter32,
		           testsuiteReportDelayResult256           Counter32,
		           testsuiteReportDelayResult512           Counter32,
		           testsuiteReportDelayResult1024          Counter32,
		           testsuiteReportDelayResult1280          Counter32,    
		           testsuiteReportDelayResult1518          Counter32,
		           testsuiteReportDelayResultJumbo         Counter32, 
		           testsuiteReportFlResult64              Counter32, 
		           testsuiteReportFlResult128             Counter32,
		           testsuiteReportFlResult256             Counter32,
		           testsuiteReportFlResult512             Counter32,
		           testsuiteReportFlResult1024            Counter32,
		           testsuiteReportFlResult1280            Counter32,    
		           testsuiteReportFlResult1518            Counter32,
		           testsuiteReportFlResultJumbo           Counter32,
		           testsuiteReportB2BResult64             Counter32, 
		           testsuiteReportB2BResult128            Counter32,
		           testsuiteReportB2BResult256            Counter32,
		           testsuiteReportB2BResult512            Counter32,
		           testsuiteReportB2BResult1024           Counter32,
		           testsuiteReportB2BResult1280           Counter32,    
		           testsuiteReportB2BResult1518           Counter32,
		           testsuiteReportB2BResultJumbo          Counter32,
		           testsuiteReportStartedTime 		TimeTicks, 
		           testsuiteReportStopedTime 		TimeTicks
		           }		       		  
		       		     
		testsuiteReportIndex OBJECT-TYPE
			SYNTAX Integer32
			MAX-ACCESS read-only
			STATUS current
			DESCRIPTION
				""
			::= { testsuiteReportEntry 1 }
			
		testsuiteReportBindSuit OBJECT-TYPE
			SYNTAX Integer32
			MAX-ACCESS read-write
			STATUS current
			DESCRIPTION
				""
			::= { testsuiteReportEntry 2 }
			
		testsuiteReportFileName OBJECT-TYPE
			SYNTAX OCTET STRING
			MAX-ACCESS read-write
			STATUS current
			DESCRIPTION
				""
			::= { testsuiteReportEntry 3 } 
			
		testsuiteReportDescription OBJECT-TYPE
			SYNTAX OCTET STRING
			MAX-ACCESS read-write
			STATUS current
			DESCRIPTION
				""
			::= { testsuiteReportEntry 4 }
			
		testsuiteReportTechnicalName OBJECT-TYPE
			SYNTAX OCTET STRING
			MAX-ACCESS read-write
			STATUS current
			DESCRIPTION
				""
			::= { testsuiteReportEntry 5 }
			
		testsuiteReportNote OBJECT-TYPE
			SYNTAX OCTET STRING
			MAX-ACCESS read-write
			STATUS current
			DESCRIPTION
				""
			::= { testsuiteReportEntry 6 }  
			
		testsuiteReportRowstatus OBJECT-TYPE
			SYNTAX RowStatus     
			MAX-ACCESS read-write
			STATUS current
			DESCRIPTION
				""
			::= { testsuiteReportEntry 7 }
			
		testsuiteReportUpload OBJECT-TYPE
			SYNTAX INTEGER
			MAX-ACCESS read-write
			STATUS current
			DESCRIPTION
				""
			::= { testsuiteReportEntry 8 } 
			
		testsuiteReportFpRecvRate64 OBJECT-TYPE
			SYNTAX Counter32
			MAX-ACCESS read-only
			STATUS current
			DESCRIPTION
				""
			::= { testsuiteReportEntry 9 }  
			
		testsuiteReportFpRecvRate128 OBJECT-TYPE
			SYNTAX Counter32
			MAX-ACCESS read-only
			STATUS current
			DESCRIPTION
				""
			::= { testsuiteReportEntry 10 }
			
		testsuiteReportFpRecvRate256 OBJECT-TYPE
			SYNTAX Counter32
			MAX-ACCESS read-only
			STATUS current
			DESCRIPTION
				""
			::= { testsuiteReportEntry 11 }
			
		testsuiteReportFpRecvRate512 OBJECT-TYPE
			SYNTAX Counter32
			MAX-ACCESS read-only
			STATUS current
			DESCRIPTION
				""
			::= { testsuiteReportEntry 12 } 
			
		testsuiteReportFpRecvRate1024 OBJECT-TYPE
			SYNTAX Counter32
			MAX-ACCESS read-only
			STATUS current
			DESCRIPTION
				""
			::= { testsuiteReportEntry 13 }
			
		testsuiteReportFpRecvRate1280 OBJECT-TYPE
			SYNTAX Counter32
			MAX-ACCESS read-only
			STATUS current
			DESCRIPTION
				""
			::= { testsuiteReportEntry 14 } 
			
		testsuiteReportFpRecvRate1518 OBJECT-TYPE
			SYNTAX Counter32
			MAX-ACCESS read-only
			STATUS current
			DESCRIPTION
				""
			::= { testsuiteReportEntry 15 }
			
		testsuiteReportFpRecvRateJumbo OBJECT-TYPE
			SYNTAX Counter32
			MAX-ACCESS read-only
			STATUS current
			DESCRIPTION
				""
			::= { testsuiteReportEntry 16 } 
			
		testsuiteReportFpSendRate64 OBJECT-TYPE
			SYNTAX Counter32
			MAX-ACCESS read-only
			STATUS current
			DESCRIPTION
				""
			::= { testsuiteReportEntry 17 }  
			
		testsuiteReportFpSendRate128 OBJECT-TYPE
			SYNTAX Counter32
			MAX-ACCESS read-only
			STATUS current
			DESCRIPTION
				""
			::= { testsuiteReportEntry 18 }
			
		testsuiteReportFpSendRate256 OBJECT-TYPE
			SYNTAX Counter32
			MAX-ACCESS read-only
			STATUS current
			DESCRIPTION
				""
			::= { testsuiteReportEntry 19 }
			
		testsuiteReportFpSendRate512 OBJECT-TYPE
			SYNTAX Counter32
			MAX-ACCESS read-only
			STATUS current
			DESCRIPTION
				""
			::= { testsuiteReportEntry 20 } 
			
		testsuiteReportFpSendRate1024 OBJECT-TYPE
			SYNTAX Counter32
			MAX-ACCESS read-only
			STATUS current
			DESCRIPTION
				""
			::= { testsuiteReportEntry 21 }
			
		testsuiteReportFpSendRate1280 OBJECT-TYPE
			SYNTAX Counter32
			MAX-ACCESS read-only
			STATUS current
			DESCRIPTION
				""
			::= { testsuiteReportEntry 22 } 
			
		testsuiteReportFpSendRate1518 OBJECT-TYPE
			SYNTAX Counter32
			MAX-ACCESS read-only
			STATUS current
			DESCRIPTION
				""
			::= { testsuiteReportEntry 23 }
			
		testsuiteReportFpSendRateJumbo OBJECT-TYPE
			SYNTAX Counter32
			MAX-ACCESS read-only
			STATUS current
			DESCRIPTION
				""
			::= { testsuiteReportEntry 24 }
			
		testsuiteReportDelayResult64 OBJECT-TYPE
			SYNTAX Counter32
			MAX-ACCESS read-only
			STATUS current
			DESCRIPTION
				""
			::= { testsuiteReportEntry 25 }	
		
		testsuiteReportDelayResult128 OBJECT-TYPE
			SYNTAX Counter32
			MAX-ACCESS read-only
			STATUS current
			DESCRIPTION
				""
			::= { testsuiteReportEntry 26 }
			
		testsuiteReportDelayResult256 OBJECT-TYPE
			SYNTAX Counter32
			MAX-ACCESS read-only
			STATUS current
			DESCRIPTION
				""
			::= { testsuiteReportEntry 27 }	
			
		testsuiteReportDelayResult512 OBJECT-TYPE
			SYNTAX Counter32
			MAX-ACCESS read-only
			STATUS current
			DESCRIPTION
				""
			::= { testsuiteReportEntry 28 }	
			
		testsuiteReportDelayResult1024 OBJECT-TYPE
			SYNTAX Counter32
			MAX-ACCESS read-only
			STATUS current
			DESCRIPTION
				""
			::= { testsuiteReportEntry 29 }	
			
		testsuiteReportDelayResult1280 OBJECT-TYPE
			SYNTAX Counter32
			MAX-ACCESS read-only
			STATUS current
			DESCRIPTION
				""
			::= { testsuiteReportEntry 30 }
			
		testsuiteReportDelayResult1518 OBJECT-TYPE
			SYNTAX Counter32
			MAX-ACCESS read-only
			STATUS current
			DESCRIPTION
				""
			::= { testsuiteReportEntry 31 }	
			
		testsuiteReportDelayResultJumbo OBJECT-TYPE
			SYNTAX Counter32
			MAX-ACCESS read-only
			STATUS current
			DESCRIPTION
				""
			::= { testsuiteReportEntry 32 }	
			
		testsuiteReportFlResult64 OBJECT-TYPE
			SYNTAX Counter32
			MAX-ACCESS read-only
			STATUS current
			DESCRIPTION
				""
			::= { testsuiteReportEntry 33 }	
		
		testsuiteReportFlResult128 OBJECT-TYPE
			SYNTAX Counter32
			MAX-ACCESS read-only
			STATUS current
			DESCRIPTION
				""
			::= { testsuiteReportEntry 34 }
			
		testsuiteReportFlResult256 OBJECT-TYPE
			SYNTAX Counter32
			MAX-ACCESS read-only
			STATUS current
			DESCRIPTION
				""
			::= { testsuiteReportEntry 35 }	
			
		testsuiteReportFlResult512 OBJECT-TYPE
			SYNTAX Counter32
			MAX-ACCESS read-only
			STATUS current
			DESCRIPTION
				""
			::= { testsuiteReportEntry 36 }	
			
		testsuiteReportFlResult1024 OBJECT-TYPE
			SYNTAX Counter32
			MAX-ACCESS read-only
			STATUS current
			DESCRIPTION
				""
			::= { testsuiteReportEntry 37 }	
			
		testsuiteReportFlResult1280 OBJECT-TYPE
			SYNTAX Counter32
			MAX-ACCESS read-only
			STATUS current
			DESCRIPTION
				""
			::= { testsuiteReportEntry 38 }
			
		testsuiteReportFlResult1518 OBJECT-TYPE
			SYNTAX Counter32
			MAX-ACCESS read-only
			STATUS current
			DESCRIPTION
				""
			::= { testsuiteReportEntry 39 }	
			
		testsuiteReportFlResultJumbo OBJECT-TYPE
			SYNTAX Counter32
			MAX-ACCESS read-only
			STATUS current
			DESCRIPTION
				""
			::= { testsuiteReportEntry 40 }
			                                  
		testsuiteReportB2BResult64 OBJECT-TYPE
			SYNTAX Counter32
			MAX-ACCESS read-only
			STATUS current
			DESCRIPTION
				""
			::= { testsuiteReportEntry 41 }	
		
		testsuiteReportB2BResult128 OBJECT-TYPE
			SYNTAX Counter32
			MAX-ACCESS read-only
			STATUS current
			DESCRIPTION
				""
			::= { testsuiteReportEntry 42 }
			
		testsuiteReportB2BResult256 OBJECT-TYPE
			SYNTAX Counter32
			MAX-ACCESS read-only
			STATUS current
			DESCRIPTION
				""
			::= { testsuiteReportEntry 43 }	
			
		testsuiteReportB2BResult512 OBJECT-TYPE
			SYNTAX Counter32
			MAX-ACCESS read-only
			STATUS current
			DESCRIPTION
				""
			::= { testsuiteReportEntry 44 }	
			
		testsuiteReportB2BResult1024 OBJECT-TYPE
			SYNTAX Counter32
			MAX-ACCESS read-only
			STATUS current
			DESCRIPTION
				""
			::= { testsuiteReportEntry 45 }	
			
		testsuiteReportB2BResult1280 OBJECT-TYPE
			SYNTAX Counter32
			MAX-ACCESS read-only
			STATUS current
			DESCRIPTION
				""
			::= { testsuiteReportEntry 46 }
			
		testsuiteReportB2BResult1518 OBJECT-TYPE
			SYNTAX Counter32
			MAX-ACCESS read-only
			STATUS current
			DESCRIPTION
				""
			::= { testsuiteReportEntry 47 }	
			
		testsuiteReportB2BResultJumbo OBJECT-TYPE
			SYNTAX Counter32
			MAX-ACCESS read-only
			STATUS current
			DESCRIPTION
				""
			::= { testsuiteReportEntry 48 }
			                                
		 testsuiteReportStartedTime OBJECT-TYPE
			SYNTAX TimeTicks
			MAX-ACCESS read-only
			STATUS current
			DESCRIPTION
				""
			::= { testsuiteReportEntry 49 }

     	 testsuiteReportStopedTime OBJECT-TYPE
			SYNTAX TimeTicks
			MAX-ACCESS read-only
			STATUS current
			DESCRIPTION
				""
			::= { testsuiteReportEntry 50 }
		                                  
	
	END

--
-- WRI-RFC2544-MIB.mib
--
