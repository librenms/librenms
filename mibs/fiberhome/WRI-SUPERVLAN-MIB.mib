--
-- supervlan.mib
-- MIB generated by MG-SOFT Visual MIB Builder Version 4.0 Build 349
-- Monday, June 07, 2010 at 07:38:22



	WRI-SUPERVLAN-MIB DEFINITIONS ::= BEGIN
 
		IMPORTS
			Integer32, OBJECT-TYPE			
				FROM SNMPv2-SMI			
			TEXTUAL-CONVENTION, RowStatus	FROM SNMPv2-TC	
			wriProtocol			
				FROM WRI-SMI;

--
-- Node definitions
--
	
--  Node definitions
-- 
-- 1.3.6.1.4.1.3807.2.1911
		superVlan OBJECT IDENTIFIER ::= { wriProtocol 1911 }

		superVlanTable OBJECT-TYPE
			SYNTAX SEQUENCE OF SuperVlanEntry
			MAX-ACCESS not-accessible
			STATUS current
			DESCRIPTION
				"Description."
			::= { superVlan 1 }

		superVlanEntry OBJECT-TYPE
			SYNTAX SuperVlanEntry
			MAX-ACCESS not-accessible
			STATUS current
			DESCRIPTION
				"Description."
			INDEX { superVlanIndex }
			::= { superVlanTable 1 }

		SuperVlanEntry ::=
			SEQUENCE { 
				superVlanIndex									Integer32,
				superVlanAddsubvlanList							OCTET STRING,
				superVlanDelsubvlanList							OCTET STRING,
				superVlanMode									INTEGER
			 }

		superVlanIndex OBJECT-TYPE
			SYNTAX Integer32
			MAX-ACCESS read-only
			STATUS current
			DESCRIPTION
				"super vlan index.."
			::= { superVlanEntry 1 }
		
		superVlanAddsubvlanList OBJECT-TYPE
			SYNTAX OCTET STRING
			MAX-ACCESS read-write
			STATUS current
			DESCRIPTION
				"Add sub vlanlist to supervlan."
			::= { superVlanEntry 2 }

		superVlanDelsubvlanList OBJECT-TYPE
			SYNTAX OCTET STRING
			MAX-ACCESS read-write
			STATUS current
			DESCRIPTION
				"Delete sub vlanlist to supervlan."
			::= { superVlanEntry 3 }
	
		superVlanMode OBJECT-TYPE
			SYNTAX INTEGER
			 {
			 	primary(0),
				secondary(1)
	    }
			MAX-ACCESS read-write
			STATUS current
			DESCRIPTION
				"create/destroy supervlan."
			::= { superVlanEntry 4 }	
	
	END

--
-- supervlan.mib
--
