--
-- privatevlan.mib
-- MIB generated by MG-SOFT Visual MIB Builder Version 4.0 Build 349
-- Wednesday, January 12, 2011 at 13:43:25
--

	WRI-PRIVATEVLAN-MIB DEFINITIONS ::= BEGIN
 
		IMPORTS
			Integer32, OBJECT-TYPE			
				FROM SNMPv2-SMI			
			wriProtocol			
				FROM WRI-SMI;
	
	
--
-- Node definitions
--
	
		-- 1.3.6.1.4.1.3807.2.1610
		privateVlan OBJECT IDENTIFIER ::= { wriProtocol 1610 }

		
		-- 1.3.6.1.4.1.3807.2.1610.1
		privateVlanTable OBJECT-TYPE
			SYNTAX SEQUENCE OF PrivateVlanEntry
			MAX-ACCESS not-accessible
			STATUS current
			DESCRIPTION
				"Description."
			::= { privateVlan 1 }

		
		-- 1.3.6.1.4.1.3807.2.1610.1.1
		privateVlanEntry OBJECT-TYPE
			SYNTAX PrivateVlanEntry
			MAX-ACCESS not-accessible
			STATUS current
			DESCRIPTION
				"Description."
			INDEX { privateVlanIndex }
			::= { privateVlanTable 1 }

		
		PrivateVlanEntry ::=
			SEQUENCE { 
				privateVlanIndex
					Integer32,
				privateVlanAddVlanList
					OCTET STRING,
				privateVlanDelVlanList
					OCTET STRING,
				privateVlanSecondVlanList
					OCTET STRING,
				privateVlanMode
					INTEGER,
				privateVlanDelAllVlan
					INTEGER
			 }

		-- 1.3.6.1.4.1.3807.2.1610.1.1.1
		privateVlanIndex OBJECT-TYPE
			SYNTAX Integer32
			MAX-ACCESS read-only
			STATUS current
			DESCRIPTION
				"Description."
			::= { privateVlanEntry 1 }

		
		-- 1.3.6.1.4.1.3807.2.1610.1.1.2
		privateVlanAddVlanList OBJECT-TYPE
			SYNTAX OCTET STRING
			MAX-ACCESS read-write
			STATUS current
			DESCRIPTION
				"add association secondary vlan to primary vlan"
			::= { privateVlanEntry 2 }

		
		-- 1.3.6.1.4.1.3807.2.1610.1.1.3
		privateVlanDelVlanList OBJECT-TYPE
			SYNTAX OCTET STRING
			MAX-ACCESS read-write
			STATUS current
			DESCRIPTION
				"delete association secondary vlan to primary vlan"
			::= { privateVlanEntry 3 }

		
		-- 1.3.6.1.4.1.3807.2.1610.1.1.4
		privateVlanSecondVlanList OBJECT-TYPE
			SYNTAX OCTET STRING
			MAX-ACCESS read-only
			STATUS current
			DESCRIPTION
				"the association secondary vlan of primary vlan"
			::= { privateVlanEntry 4 }

		
		-- 1.3.6.1.4.1.3807.2.1610.1.1.5
		privateVlanMode OBJECT-TYPE
			SYNTAX INTEGER
				{
				primary(0), 
				community(1),
				isolated(2)
				}
			MAX-ACCESS read-write
			STATUS current
			DESCRIPTION
				"The mode of pvlan"
			::= { privateVlanEntry 5 }

		
		-- 1.3.6.1.4.1.3807.2.1610.1.1.6
		privateVlanDelAllVlan OBJECT-TYPE
			SYNTAX INTEGER
			MAX-ACCESS read-write
			STATUS current
			DESCRIPTION
				"Delete all secondary vlanlist .
				set 0"
			::= { privateVlanEntry 6 }

		
		-- 1.3.6.1.4.1.3807.2.1610.2
		privateVlanIfTable OBJECT-TYPE
			SYNTAX SEQUENCE OF PrivateVlanIfEntry
			MAX-ACCESS not-accessible
			STATUS current
			DESCRIPTION
				"Description."
			::= { privateVlan 2 }

		
		-- 1.3.6.1.4.1.3807.2.1610.2.1
		privateVlanIfEntry OBJECT-TYPE
			SYNTAX PrivateVlanIfEntry
			MAX-ACCESS not-accessible
			STATUS current
			DESCRIPTION
				"Description."
			INDEX { privateVlanIfIndex }
			::= { privateVlanIfTable 1 }

		
		PrivateVlanIfEntry ::=
			SEQUENCE { 
				privateVlanIfIndex
					Integer32,
				privateVlanIfMode
					INTEGER,
				privateVlanIfAddVlanList
					OCTET STRING,
				privateVlanIfDelVlanList
					OCTET STRING,
				privateVlanIfVlanList
					OCTET STRING
			 }

		-- 1.3.6.1.4.1.3807.2.1610.2.1.1
		privateVlanIfIndex OBJECT-TYPE
			SYNTAX Integer32
			MAX-ACCESS read-only
			STATUS current
			DESCRIPTION
				"Description."
			::= { privateVlanIfEntry 1 }

		
		-- 1.3.6.1.4.1.3807.2.1610.2.1.2
		privateVlanIfMode OBJECT-TYPE
			SYNTAX INTEGER
			MAX-ACCESS read-write
			STATUS current
			DESCRIPTION
				"The private vlan mode of interface"
			::= { privateVlanIfEntry 2 }

		
		-- 1.3.6.1.4.1.3807.2.1610.2.1.3
		privateVlanIfAddVlanList OBJECT-TYPE
			SYNTAX OCTET STRING
			MAX-ACCESS read-write
			STATUS current
			DESCRIPTION
				"add private vlan to interface"
			::= { privateVlanIfEntry 3 }

		
		-- 1.3.6.1.4.1.3807.2.1610.2.1.4
		privateVlanIfDelVlanList OBJECT-TYPE
			SYNTAX OCTET STRING
			MAX-ACCESS read-write
			STATUS current
			DESCRIPTION
				"add private vlan to interface"
			::= { privateVlanIfEntry 4 }

		
		-- 1.3.6.1.4.1.3807.2.1610.2.1.5
		privateVlanIfVlanList OBJECT-TYPE
			SYNTAX OCTET STRING
			MAX-ACCESS read-only
			STATUS current
			DESCRIPTION
				"the private vlan of interface"
			::= { privateVlanIfEntry 5 }

		
	
	END

--
-- privatevlan.mib
--
