--
-- rip.mib
-- MIB generated by MG-SOFT Visual MIB Builder Version 4.0 Build 349
-- Friday, May 04, 2012 at 11:26:34
--

--  rip.mib
-- MIB generated by MG-SOFT Visual MIB Builder Version 4.0 Build 349
-- Thursday, April 26, 2012 at 15:07:08
-- 
--  rip.mib
-- MIB generated by MG-SOFT Visual MIB Builder Version 4.0 Build 349
-- Wednesday, April 18, 2012 at 15:03:29
-- 
--  rip.mib
-- MIB generated by MG-SOFT Visual MIB Builder Version 4.0 Build 349
-- Tuesday, March 27, 2012 at 14:55:28
-- 
--  rip.mib
-- MIB generated by MG-SOFT Visual MIB Builder Version 4.0 Build 349
-- Monday, March 26, 2012 at 18:29:19
-- 
--  rip.mib
-- MIB generated by MG-SOFT Visual MIB Builder Version 4.0 Build 349
-- Monday, March 26, 2012 at 13:51:14
-- 
--  rip.mib
-- MIB generated by MG-SOFT Visual MIB Builder Version 4.0 Build 349
-- Tuesday, March 06, 2012 at 10:45:24
-- 
--  rip.mib
-- MIB generated by MG-SOFT Visual MIB Builder Version 4.0 Build 349
-- Friday, February 24, 2012 at 16:54:26
-- 
--  rip.mib
-- MIB generated by MG-SOFT Visual MIB Builder Version 4.0 Build 349
-- Wednesday, November 23, 2011 at 19:38:34
-- 

	WRI-RIP-MIB DEFINITIONS ::= BEGIN
 
		IMPORTS
			TimeTicks, IpAddress, Integer32, Counter32, OBJECT-TYPE			
				FROM SNMPv2-SMI			
			RowStatus, TEXTUAL-CONVENTION			
				FROM SNMPv2-TC			
			wri        FROM WRI-SMI ; 	
	
-- Type definitions
-- 
		DisplayString ::= OCTET STRING

	
-- Textual conventions
-- 
		RouteTag ::= TEXTUAL-CONVENTION
			STATUS current
			DESCRIPTION 
				"the RouteTag type represents the contents of the Route Domain
				field in the packet header or route entry"
			SYNTAX OCTET STRING (SIZE (2))

		EntryStatus ::= TEXTUAL-CONVENTION
			STATUS current
			DESCRIPTION 
				"entry status."
			SYNTAX INTEGER
				{
				valid(1),
				createRequest(2),
				underCreation(3),
				invalid(4)
				}

	
-- Node definitions
		-- 1.3.6.1.4.1.3807.2
		wriProtocol OBJECT IDENTIFIER ::= { wri 2 }

		
		-- 1.3.6.1.4.1.3807.2.1812
		wriRip OBJECT IDENTIFIER ::= { wriProtocol 1812 }

		-- 1.3.6.1.4.1.3807.2.1812.1
		ripGlobals OBJECT IDENTIFIER ::= { wriRip 1 }

		-- 1.3.6.1.4.1.3807.2.1812.1.1
		ripGlobalProcessMaxNum OBJECT-TYPE
			SYNTAX Counter32
			MAX-ACCESS read-only
			STATUS current
			DESCRIPTION
				"The number of route changes made to the IP Route
				Database by RIP.  This does not include the refresh
				of a route's age."
			::= { ripGlobals 1 }

		
		-- 1.3.6.1.4.1.3807.2.1812.1.2
		ripGlobalProcessCurrentNum OBJECT-TYPE
			SYNTAX Counter32
			MAX-ACCESS read-only
			STATUS current
			DESCRIPTION
				"The number of responses sent to RIP queries
				from other systems."
			::= { ripGlobals 2 }

		
		-- 1.3.6.1.4.1.3807.2.1812.1.3
		ripGlobalRouteCurrentNum OBJECT-TYPE
			SYNTAX Integer32
			MAX-ACCESS read-only
			STATUS current
			DESCRIPTION
				"Description."
			::= { ripGlobals 3 }

		
		-- 1.3.6.1.4.1.3807.2.1812.1.4
		ripGlobalRouteMaxNum OBJECT-TYPE
			SYNTAX Integer32
			MAX-ACCESS read-only
			STATUS current
			DESCRIPTION
				"Description."
			::= { ripGlobals 4 }


		-- 1.3.6.1.4.1.3807.2.1812.1.5
		ripGlobalIfCurrentNum OBJECT-TYPE
			SYNTAX Integer32
			MAX-ACCESS read-only
			STATUS current
			DESCRIPTION
				"Description."
			::= { ripGlobals 5 }

		
		-- 1.3.6.1.4.1.3807.2.1812.1.6
		ripGlobalIfMaxNum OBJECT-TYPE
			SYNTAX Integer32
			MAX-ACCESS read-only
			STATUS current
			DESCRIPTION
				"Description."
			::= { ripGlobals 6 }

		
		-- 1.3.6.1.4.1.3807.2.1812.1.7
		ripGlobalPeerMaxNum OBJECT-TYPE
			SYNTAX Integer32
			MAX-ACCESS read-only
			STATUS current
			DESCRIPTION
				"Description."
			::= { ripGlobals 7 }

		-- 1.3.6.1.4.1.3807.2.1812.1.8
		ripGlobalPeerCurrentNum OBJECT-TYPE
			SYNTAX Integer32
			MAX-ACCESS read-only
			STATUS current
			DESCRIPTION
				"Description."
			::= { ripGlobals 8 }

		
		-- 1.3.6.1.4.1.3807.2.1812.1.9
		ripGlobalNexthopMaxNum OBJECT-TYPE
			SYNTAX Integer32
			MAX-ACCESS read-only
			STATUS current
			DESCRIPTION
				"Description."
			::= { ripGlobals 9 }

		
		-- 1.3.6.1.4.1.3807.2.1812.1.10
		ripGlobalNexthopCurrentNum OBJECT-TYPE
			SYNTAX Integer32
			MAX-ACCESS read-only
			STATUS current
			DESCRIPTION
				"Description."
			::= { ripGlobals 10 }


		-- 1.3.6.1.4.1.3807.2.1812.2
		ripIfStatTable OBJECT-TYPE
			SYNTAX SEQUENCE OF RipIfStatEntry
			MAX-ACCESS not-accessible
			STATUS current
			DESCRIPTION
				"A list of subnets which require separate
				status monitoring in RIP."
			::= { wriRip 2 }

		
		-- 1.3.6.1.4.1.3807.2.1812.2.1
		ripIfStatEntry OBJECT-TYPE
			SYNTAX RipIfStatEntry
			MAX-ACCESS not-accessible
			STATUS current
			DESCRIPTION
				"A Single Routing Domain in a single Subnet."
			INDEX { ripIfStatProcessId, ripIfStatAddress }
			::= { ripIfStatTable 1 }

		
		RipIfStatEntry ::=
			SEQUENCE { 
				ripIfStatProcessId
					Integer32,
				ripIfStatAddress
					IpAddress,
				ripIfStatRcvBadPackets
					Counter32,
				ripIfStatRcvBadRoutes
					Counter32,
				ripIfStatSentUpdates
					Counter32,
				ripIfStatStatus
					RowStatus,
				ripIfStatRcvPackets	
					Counter32
			 }
		-- 1.3.6.1.4.1.3807.2.1812.2.1.1
		ripIfStatProcessId OBJECT-TYPE
			SYNTAX Integer32
			MAX-ACCESS read-only
			STATUS current
			DESCRIPTION
				"Description."
			::= { ripIfStatEntry 1 }

		
		-- 1.3.6.1.4.1.3807.2.1812.2.1.2
		ripIfStatAddress OBJECT-TYPE
			SYNTAX IpAddress
			MAX-ACCESS read-only
			STATUS current
			DESCRIPTION
				"The IP Address of this system on the indicated
				subnet. For unnumbered interfaces, the value 0.0.0.N,
				where the least significant 24 bits (N) is the ifIndex
				for the IP Interface in network byte order."
			::= { ripIfStatEntry 2 }

		
		-- 1.3.6.1.4.1.3807.2.1812.2.1.3
		ripIfStatRcvBadPackets OBJECT-TYPE
			SYNTAX Counter32
			MAX-ACCESS read-only
			STATUS current
			DESCRIPTION
				"The number of RIP response packets received by
				the RIP process which were subsequently discarded
				for any reason (e.g. a version 0 packet, or an
				unknown command type)."
			::= { ripIfStatEntry 3 }

		
		-- 1.3.6.1.4.1.3807.2.1812.2.1.4
		ripIfStatRcvBadRoutes OBJECT-TYPE
			SYNTAX Counter32
			MAX-ACCESS read-only
			STATUS current
			DESCRIPTION
				"The number of routes, in valid RIP packets,
				which were ignored for any reason (e.g. unknown
				address family, or invalid metric)."
			::= { ripIfStatEntry 4 }
    
    
		-- 1.3.6.1.4.1.3807.2.1812.2.1.5
		ripIfStatSentUpdates OBJECT-TYPE
			SYNTAX Counter32
			MAX-ACCESS read-only
			STATUS current
			DESCRIPTION
				"The number of triggered RIP updates actually
				sent on this interface.  This explicitly does
				NOT include full updates sent containing new
				information."
			::= { ripIfStatEntry 5 }

		
		-- 1.3.6.1.4.1.3807.2.1812.2.1.6
		ripIfStatStatus OBJECT-TYPE
			SYNTAX RowStatus
			MAX-ACCESS read-create
			STATUS current
			DESCRIPTION
				"Writing invalid has the effect of deleting
				this interface."
			::= { ripIfStatEntry 6 }
        
        -- 1.3.6.1.4.1.3807.2.1812.2.1.7
		ripIfStatRcvPackets   OBJECT-TYPE
			SYNTAX Counter32
			MAX-ACCESS read-only
			STATUS current
			DESCRIPTION
				"The number of receive packets."
			::= { ripIfStatEntry 7 }
			
		-- 1.3.6.1.4.1.3807.2.1812.3
		ripIfConfTable OBJECT-TYPE
			SYNTAX SEQUENCE OF RipIfConfEntry
			MAX-ACCESS not-accessible
			STATUS current
			DESCRIPTION
				"A list of subnets which require separate
				configuration in RIP."
			::= { wriRip 3 }

		
		-- 1.3.6.1.4.1.3807.2.1812.3.1
		ripIfConfEntry OBJECT-TYPE
			SYNTAX RipIfConfEntry
			MAX-ACCESS not-accessible
			STATUS current
			DESCRIPTION
				"A Single Routing Domain in a single Subnet."
			INDEX { ripIfConfProcessId, ripIfConfAddress }
			::= { ripIfConfTable 1 }

		
		RipIfConfEntry ::=
			SEQUENCE { 
				ripIfConfProcessId
					Integer32,
				ripIfConfAddress
					IpAddress,
				ripIfConfDomain
					RouteTag,
				ripIfConfAuthType
					INTEGER,
				ripIfConfAuthKey
					OCTET STRING,
				ripIfConfSend
					INTEGER,
				ripIfConfReceive
					INTEGER,
				ripIfConfDefaultMetric
					INTEGER,
				ripIfConfStatus
					RowStatus,
				ripIfConfSrcAddress
					IpAddress,
				ripIfConfAuthMd5KeyId
					INTEGER,
				ripIfConfPassiveMode
					INTEGER,
				ripIfConfNetmask
					Integer32,
				ripIfConfState
					Integer32,
				ripIfConfUnit
					Integer32,
				ripIfConfLastSendSeq
					Integer32,
				ripIfConfMetricIn
					Integer32,
				ripIfConfMetricOut
					Integer32,
				ripIfConfFilterIn
					Integer32,
				ripIfConfFilterOut
					Integer32,
				ripIfConfBfd
					Integer32,
				ripIfConfMD5CompatibleMode
					INTEGER,
				ripIfConfTransInterval
					INTEGER,
				ripIfConfTransPktNum							
					Counter32
			 }

		-- 1.3.6.1.4.1.3807.2.1812.3.1.1
		ripIfConfProcessId OBJECT-TYPE
			SYNTAX Integer32
			MAX-ACCESS read-only
			STATUS current
			DESCRIPTION
				"Description."
			::= { ripIfConfEntry 1 }

		-- 1.3.6.1.4.1.3807.2.1812.3.1.2
		ripIfConfAddress OBJECT-TYPE
			SYNTAX IpAddress
			MAX-ACCESS read-only
			STATUS current
			DESCRIPTION
				"The IP Address of this system on the indicated
				subnet.  For unnumbered interfaces, the value 0.0.0.N,
				where the least significant 24 bits (N) is the ifIndex
				for the IP Interface in network byte order."
			::= { ripIfConfEntry 2 }

		
		-- 1.3.6.1.4.1.3807.2.1812.3.1.3
		ripIfConfDomain OBJECT-TYPE
			SYNTAX RouteTag
			MAX-ACCESS read-create
			STATUS obsolete
			DESCRIPTION
				"Value inserted into the Routing Domain field
				of all RIP packets sent on this interface."
			DEFVAL { '0000'h }
			::= { ripIfConfEntry 3 }

		
		-- 1.3.6.1.4.1.3807.2.1812.3.1.4
		ripIfConfAuthType OBJECT-TYPE
			SYNTAX INTEGER
				{
				noAuthentication(1),
				simplePassword(2),
				md5(3)
				}
			MAX-ACCESS read-create
			STATUS current
			DESCRIPTION
				"The type of Authentication used on this
				interface."
			DEFVAL { noAuthentication }
			::= { ripIfConfEntry 4 }
                                        
                                        
		-- 1.3.6.1.4.1.3807.2.1812.3.1.5
		ripIfConfAuthKey OBJECT-TYPE
			SYNTAX OCTET STRING (SIZE (0..16))
			MAX-ACCESS read-create
			STATUS current
			DESCRIPTION
				"The value to be used as the Authentication Key
				whenever the corresponding instance of
				rip2IfConfAuthType has a value other than
				noAuthentication.  A modification of the corresponding
				instance of rip2IfConfAuthType does not modify
				the rip2IfConfAuthKey value.  If a string shorter
				than 16 octets is supplied, it will be left-
				justified and padded to 16 octets, on the right,
				with nulls (0x00).
				
				Reading this object always results in an  OCTET
				STRING of length zero; authentication may not
				be bypassed by reading the MIB object."
			DEFVAL { ''h }
			::= { ripIfConfEntry 5 }

		
		-- 1.3.6.1.4.1.3807.2.1812.3.1.6
		ripIfConfSend OBJECT-TYPE
			SYNTAX INTEGER
				{
				doNotSend(1),
				ripVersion1(2),
				rip1Compatible(3),
				ripVersion2(4),
				ripV1Demand(5),
				ripV2Demand(6)
				}
			MAX-ACCESS read-create
			STATUS current
			DESCRIPTION
				"What the router sends on this interface.
				ripVersion1 implies sending RIP updates compliant
				with  RFC  1058.   rip1Compatible implies
				broadcasting RIP-2 updates using RFC 1058 route
				subsumption rules.  ripVersion2 implies
				multicasting RIP-2 updates.  ripV1Demand indicates
				the use of Demand RIP on a WAN interface under RIP
				Version 1 rules.  ripV2Demand indicates the use of
				
				Demand RIP on a WAN interface under Version 2 rules."
			DEFVAL { rip1Compatible }
			::= { ripIfConfEntry 6 }

		
		-- 1.3.6.1.4.1.3807.2.1812.3.1.7
		ripIfConfReceive OBJECT-TYPE
			SYNTAX INTEGER
				{
				rip1(1),
				rip2(2),
				rip1OrRip2(3),
				doNotRecieve(4)
				}
			MAX-ACCESS read-create
			STATUS current
			DESCRIPTION
				"This indicates which version of RIP updates
				are to be accepted.  Note that rip2 and
				rip1OrRip2 implies reception of multicast
				packets."
			DEFVAL { rip1OrRip2 }
			::= { ripIfConfEntry 7 }

		
		-- 1.3.6.1.4.1.3807.2.1812.3.1.8
		ripIfConfDefaultMetric OBJECT-TYPE
			SYNTAX INTEGER (0..15)
			MAX-ACCESS read-create
			STATUS current
			DESCRIPTION
				"This variable indicates the metric that is to
				be used for the default route entry in RIP updates
				originated on this interface.  A value of zero
				indicates that no default route should be
				originated; in this case, a default route via
				another router may be propagated."
			::= { ripIfConfEntry 8 }

		
		-- 1.3.6.1.4.1.3807.2.1812.3.1.9
		ripIfConfStatus OBJECT-TYPE
			SYNTAX RowStatus
			MAX-ACCESS read-create
			STATUS current
			DESCRIPTION
				"Writing invalid has  the  effect  of  deleting
				this interface."
			::= { ripIfConfEntry 9 }

		
		-- 1.3.6.1.4.1.3807.2.1812.3.1.10
		ripIfConfSrcAddress OBJECT-TYPE
			SYNTAX IpAddress
			MAX-ACCESS read-create
			STATUS current
			DESCRIPTION
				"The IP Address this system will use as a source
				address on this interface.  If it is a numbered
				interface, this MUST be the same value as
				rip2IfConfAddress.  On unnumbered interfaces,
				it must be the value of rip2IfConfAddress for
				some interface on the system."
			::= { ripIfConfEntry 10 }

		

		-- 1.3.6.1.4.1.3807.2.1812.3.1.11
		ripIfConfAuthMd5KeyId OBJECT-TYPE
			SYNTAX INTEGER
			MAX-ACCESS read-create
			STATUS current
			DESCRIPTION
				"The key id of md5 authentication."
			DEFVAL { 0 }
			::= { ripIfConfEntry 11 }

		
		-- 1.3.6.1.4.1.3807.2.1812.3.1.12
		ripIfConfPassiveMode OBJECT-TYPE
			SYNTAX INTEGER
				{
				enable(1),
				disable(2)
				}
			MAX-ACCESS read-create
			STATUS current
			DESCRIPTION
				"The passive mode enable."
			DEFVAL { 1 }
			::= { ripIfConfEntry 12 }

		
		-- 1.3.6.1.4.1.3807.2.1812.3.1.13
		ripIfConfNetmask OBJECT-TYPE
			SYNTAX Integer32
			MAX-ACCESS read-only
			STATUS current
			DESCRIPTION
				"Description."
			::= { ripIfConfEntry 13 }

		
		-- 1.3.6.1.4.1.3807.2.1812.3.1.14
		ripIfConfState OBJECT-TYPE
			SYNTAX Integer32
			MAX-ACCESS read-only
			STATUS current
			DESCRIPTION
				"Description."
			::= { ripIfConfEntry 14 }

		
		-- 1.3.6.1.4.1.3807.2.1812.3.1.15
		ripIfConfUnit OBJECT-TYPE
			SYNTAX Integer32
			MAX-ACCESS read-only
			STATUS current
			DESCRIPTION
				"Description."
			::= { ripIfConfEntry 15 }

		
		-- 1.3.6.1.4.1.3807.2.1812.3.1.16
		ripIfConfLastSendSeq OBJECT-TYPE
			SYNTAX Integer32
			MAX-ACCESS read-only
			STATUS current
			DESCRIPTION
				"Description."
			::= { ripIfConfEntry 16 }

		
		-- 1.3.6.1.4.1.3807.2.1812.3.1.17
		ripIfConfMetricIn OBJECT-TYPE
			SYNTAX Integer32 (0..15)
			MAX-ACCESS read-write
			STATUS current
			DESCRIPTION
				"Description."
			::= { ripIfConfEntry 17 }

		

		-- 1.3.6.1.4.1.3807.2.1812.3.1.18
		ripIfConfMetricOut OBJECT-TYPE
			SYNTAX Integer32 (0..15)
			MAX-ACCESS read-write
			STATUS current
			DESCRIPTION
				"Description."
			::= { ripIfConfEntry 18 }

		
		-- 1.3.6.1.4.1.3807.2.1812.3.1.19
		ripIfConfFilterIn OBJECT-TYPE
			SYNTAX Integer32
			MAX-ACCESS read-write
			STATUS current
			DESCRIPTION
				"Description."
			::= { ripIfConfEntry 19 }

		
		-- 1.3.6.1.4.1.3807.2.1812.3.1.20
		ripIfConfFilterOut OBJECT-TYPE
			SYNTAX Integer32
			MAX-ACCESS read-write
			STATUS current
			DESCRIPTION
				"Description."
			::= { ripIfConfEntry 20 }

		
		-- 1.3.6.1.4.1.3807.2.1812.3.1.21
		ripIfConfBfd OBJECT-TYPE
			SYNTAX Integer32
			MAX-ACCESS read-write
			STATUS current
			DESCRIPTION
				"Description."
			::= { ripIfConfEntry 21 }    
			
        -- 1.3.6.1.4.1.3807.2.1812.3.1.22
		ripIfConfMD5CompatibleMode OBJECT-TYPE
			SYNTAX INTEGER{enbale(1),disable(2)}
			MAX-ACCESS read-write
			STATUS current
			DESCRIPTION
				"Description."
			::= { ripIfConfEntry 22 }
					                     				
		-- 1.3.6.1.4.1.3807.2.1812.3.1.23		
		ripIfConfTransInterval OBJECT-TYPE
			SYNTAX INTEGER
			MAX-ACCESS read-write
			STATUS current
			DESCRIPTION
				"Description."
			::= { ripIfConfEntry 23}
		
		-- 1.3.6.1.4.1.3807.2.1812.3.1.24				
		ripIfConfTransPktNum   OBJECT-TYPE
			SYNTAX Counter32
			MAX-ACCESS read-write
			STATUS current
			DESCRIPTION
				"Description."
			::= { ripIfConfEntry 24 }							
					
			
		-- 1.3.6.1.4.1.3807.2.1812.4
		ripPeerTable OBJECT-TYPE
			SYNTAX SEQUENCE OF RipPeerEntry
			MAX-ACCESS not-accessible
			STATUS current
			DESCRIPTION
				"A list of RIP Peers."
			::= { wriRip 4 }

		
		-- 1.3.6.1.4.1.3807.2.1812.4.1
		ripPeerEntry OBJECT-TYPE
			SYNTAX RipPeerEntry
			MAX-ACCESS not-accessible
			STATUS current
			DESCRIPTION
				"Information regarding a single routing peer."
			INDEX { ripPeerProcessId, ripPeerAddress }
			::= { ripPeerTable 1 }

		
		RipPeerEntry ::=
			SEQUENCE { 
				ripPeerProcessId
					Integer32,
				ripPeerAddress
					IpAddress,
				ripPeerDomain
					RouteTag,
				ripPeerLastUpdate
					TimeTicks,
				ripPeerVersion
					INTEGER,
				ripPeerRcvBadPackets
					Counter32,
				ripPeerRcvBadRoutes
					Counter32,
				ripPeerKeyLastSeq
					Integer32,
				ripPeerInterface
					INTEGER,
				ripPeerLastSentTime
					INTEGER,
				ripPeerEntryStatus
					EntryStatus,
				ripPeerBfdSession
					INTEGER					
			 }

		-- 1.3.6.1.4.1.3807.2.1812.4.1.1
		ripPeerProcessId OBJECT-TYPE
			SYNTAX Integer32
			MAX-ACCESS read-only
			STATUS current
			DESCRIPTION
				"Description."
			::= { ripPeerEntry 1 }

		-- 1.3.6.1.4.1.3807.2.1812.4.1.2
		ripPeerAddress OBJECT-TYPE
			SYNTAX IpAddress
			MAX-ACCESS read-only
			STATUS current
			DESCRIPTION
				"The IP Address that the peer is using as its source
				address.  Note that on an unnumbered link, this may
				not be a member of any subnet on the system."
			::= { ripPeerEntry 2 }

		
		-- 1.3.6.1.4.1.3807.2.1812.4.1.3
		ripPeerDomain OBJECT-TYPE
			SYNTAX RouteTag
			MAX-ACCESS read-only
			STATUS current
			DESCRIPTION
				"The value in the Routing Domain field  in  RIP
				packets received from the peer.  As domain suuport
				is deprecated, this must be zero."
			::= { ripPeerEntry 3 }
                                  
                                  
		-- 1.3.6.1.4.1.3807.2.1812.4.1.4
		ripPeerLastUpdate OBJECT-TYPE
			SYNTAX TimeTicks
			MAX-ACCESS read-only
			STATUS current
			DESCRIPTION
				"The value of sysUpTime when the most recent
				RIP update was received from this system."
			::= { ripPeerEntry 4 }

		
		-- 1.3.6.1.4.1.3807.2.1812.4.1.5
		ripPeerVersion OBJECT-TYPE
			SYNTAX INTEGER (0..255)
			MAX-ACCESS read-only
			STATUS current
			DESCRIPTION
				"The RIP version number in the header of the
				last RIP packet received."
			::= { ripPeerEntry 5 }

		
		-- 1.3.6.1.4.1.3807.2.1812.4.1.6
		ripPeerRcvBadPackets OBJECT-TYPE
			SYNTAX Counter32
			MAX-ACCESS read-only
			STATUS current
			DESCRIPTION
				"The number of RIP response packets from this
				peer discarded as invalid."
			::= { ripPeerEntry 6 }

		
		-- 1.3.6.1.4.1.3807.2.1812.4.1.7
		ripPeerRcvBadRoutes OBJECT-TYPE
			SYNTAX Counter32
			MAX-ACCESS read-only
			STATUS current
			DESCRIPTION
				"The number of routes from this peer that were
				ignored because the entry format was invalid."
			::= { ripPeerEntry 7 }

		
		-- 1.3.6.1.4.1.3807.2.1812.4.1.8
		ripPeerKeyLastSeq OBJECT-TYPE
			SYNTAX Integer32
			MAX-ACCESS read-only
			STATUS current
			DESCRIPTION
				"Description."
			::= { ripPeerEntry 8 }
        
        -- 1.3.6.1.4.1.3807.2.1812.4.1.9
		ripPeerInterface  OBJECT-TYPE
			SYNTAX INTEGER
			MAX-ACCESS read-only
			STATUS current
			DESCRIPTION
				"Description."
			::= { ripPeerEntry 9 }

		-- 1.3.6.1.4.1.3807.2.1812.4.1.10	
		ripPeerLastSentTime  OBJECT-TYPE
			SYNTAX INTEGER
			MAX-ACCESS read-only
			STATUS current
			DESCRIPTION
				"last send packet time in second."
			::= { ripPeerEntry 10 }
					            
		-- 1.3.6.1.4.1.3807.2.1812.4.1.11			            
		ripPeerEntryStatus   OBJECT-TYPE
			SYNTAX EntryStatus
			MAX-ACCESS read-write
			STATUS current
			DESCRIPTION
				"Description."
			::= { ripPeerEntry 11 }
	
		ripPeerBfdSession OBJECT-TYPE
			SYNTAX INTEGER
			MAX-ACCESS read-only
			STATUS current
			DESCRIPTION
				"bfd session ."
			::= { ripPeerEntry 12 }
					
		-- 1.3.6.1.4.1.3807.2.1812.5
		ripProcessTable OBJECT-TYPE
			SYNTAX SEQUENCE OF RipProcessEntry
			MAX-ACCESS not-accessible
			STATUS current
			DESCRIPTION
				"Description."
			::= { wriRip 5 }

		
		-- 1.3.6.1.4.1.3807.2.1812.5.1
		ripProcessEntry OBJECT-TYPE
			SYNTAX RipProcessEntry
			MAX-ACCESS not-accessible
			STATUS current
			DESCRIPTION
				"Description."
			INDEX { ripProcessId }
			::= { ripProcessTable 1 }

		
		RipProcessEntry ::=
			SEQUENCE { 
				ripProcessId
					Integer32,
				ripProcessRouteChanges
					Integer32,
				ripProcessQueries
					Integer32,
				ripProcessRouteCurNum
					Integer32,
				ripProcessSplithorizenOnOff
					INTEGER,
				ripProcessRedistributeStatic
					INTEGER,
				ripProcessRedistributeStaticCost
					Integer32,
				ripProcessRedistributeStaticPolicy
					Integer32,
				ripProcessRedistributeOspf
					INTEGER,
				ripProcessRedistributeOspfCost
					Integer32,
				ripProcessRedistributeOspfPolicy
					Integer32,
				ripProcessRedistributeConnect
					INTEGER,
				ripProcessRedistributeConnectCost
					Integer32,
				ripProcessRedistributeConnectPolicy
					Integer32,
				ripProcessRedistributeBgp
					INTEGER,
				ripProcessRedistributeBgpCost
					Integer32,
				ripProcessRedistributeBgpPolicy
					Integer32,
				ripProcessRedistributeIsis
					INTEGER,
				ripProcessRedistributeIsisCost
					Integer32,
				ripProcessRedistributeIsisPolicy
					Integer32,
				ripProcessEntryStatus
					EntryStatus,
				ripProcessStaticFilterPolicy
					Integer32,
				ripProcessConnectFilterPolicy
					Integer32,
				ripProcessOspfFilterPolicy
					Integer32,
				ripProcessBgpFilterPolicy
					Integer32,
				ripProcessIsisFilterPolicy
					Integer32,
				ripProcessUpdateTime
					Integer32,
				ripProcessExpired
					Integer32,
				ripProcessGarbAge
					Integer32,
				ripProcessRouteDefault
					Integer32,
				ripProcessCheckZero
					INTEGER,
				ripProcessValidateSource
					INTEGER,
				ripProcessHostRoute
					INTEGER,
				ripProcessDefaultMetric
					Integer32,
				ripProcessFilterIn
					Integer32,
				ripProcessFilterOut
					Integer32,
				ripProcessVpnId
					Integer32,
				ripProcessDefaultRouteState
					INTEGER,
				ripProcessPoisonReverse
				    INTEGER,
				ripProcessSummaryState
					INTEGER,
				ripProcessFrrState	    				
					INTEGER
			 }

		-- 1.3.6.1.4.1.3807.2.1812.5.1.1
		ripProcessId OBJECT-TYPE
			SYNTAX Integer32
			MAX-ACCESS read-only
			STATUS current
			DESCRIPTION
				"Description."
			::= { ripProcessEntry 1 }

		
		-- 1.3.6.1.4.1.3807.2.1812.5.1.2
		ripProcessRouteChanges OBJECT-TYPE
			SYNTAX Integer32
			MAX-ACCESS read-only
			STATUS current
			DESCRIPTION
				"Description."
			::= { ripProcessEntry 2 }

		

		-- 1.3.6.1.4.1.3807.2.1812.5.1.3
		ripProcessQueries OBJECT-TYPE
			SYNTAX Integer32
			MAX-ACCESS read-only
			STATUS current
			DESCRIPTION
				"Description."
			::= { ripProcessEntry 3 }

		
		-- 1.3.6.1.4.1.3807.2.1812.5.1.4
		ripProcessRouteCurNum OBJECT-TYPE
			SYNTAX Integer32
			MAX-ACCESS read-only
			STATUS current
			DESCRIPTION
				"Description."
			::= { ripProcessEntry 4 }

		
		-- 1.3.6.1.4.1.3807.2.1812.5.1.5
		ripProcessSplithorizenOnOff OBJECT-TYPE
			SYNTAX INTEGER
				{
				enable(1),
				disable(2)
				}
			MAX-ACCESS read-write
			STATUS current
			DESCRIPTION
				"Description."
			::= { ripProcessEntry 5 }

		
		-- 1.3.6.1.4.1.3807.2.1812.5.1.6
		ripProcessRedistributeStatic OBJECT-TYPE
			SYNTAX INTEGER
				{
				enable(1),
				disable(2)
				}
			MAX-ACCESS read-write
			STATUS current
			DESCRIPTION
				"Description."
			::= { ripProcessEntry 6 }

		
		-- 1.3.6.1.4.1.3807.2.1812.5.1.7
		ripProcessRedistributeStaticCost OBJECT-TYPE
			SYNTAX Integer32 (0..15)
			MAX-ACCESS read-write
			STATUS current
			DESCRIPTION
				"Description."
			::= { ripProcessEntry 7 }

		
		-- 1.3.6.1.4.1.3807.2.1812.5.1.8
		ripProcessRedistributeStaticPolicy OBJECT-TYPE
			SYNTAX Integer32
			MAX-ACCESS read-write
			STATUS current
			DESCRIPTION
				"Description."
			::= { ripProcessEntry 8 }

		
		-- 1.3.6.1.4.1.3807.2.1812.5.1.9
		ripProcessRedistributeOspf OBJECT-TYPE
			SYNTAX INTEGER
				{
				enable(1),
				disable(2)
				}
			MAX-ACCESS read-write
			STATUS current
			DESCRIPTION
				"Description."
			::= { ripProcessEntry 9 }

		
		-- 1.3.6.1.4.1.3807.2.1812.5.1.10
		ripProcessRedistributeOspfCost OBJECT-TYPE
			SYNTAX Integer32 (0..15)
			MAX-ACCESS read-write
			STATUS current
			DESCRIPTION
				"Description."
			::= { ripProcessEntry 10 }

		

		-- 1.3.6.1.4.1.3807.2.1812.5.1.11
		ripProcessRedistributeOspfPolicy OBJECT-TYPE
			SYNTAX Integer32
			MAX-ACCESS read-write
			STATUS current
			DESCRIPTION
				"Description."
			::= { ripProcessEntry 11 }

		
		-- 1.3.6.1.4.1.3807.2.1812.5.1.12
		ripProcessRedistributeConnect OBJECT-TYPE
			SYNTAX INTEGER
				{
				enable(1),
				disable(2)
				}
			MAX-ACCESS read-write
			STATUS current
			DESCRIPTION
				"Description."
			::= { ripProcessEntry 12 }

		
		-- 1.3.6.1.4.1.3807.2.1812.5.1.13
		ripProcessRedistributeConnectCost OBJECT-TYPE
			SYNTAX Integer32 (0..15)
			MAX-ACCESS read-write
			STATUS current
			DESCRIPTION
				"Description."
			::= { ripProcessEntry 13 }

		
		-- 1.3.6.1.4.1.3807.2.1812.5.1.14
		ripProcessRedistributeConnectPolicy OBJECT-TYPE
			SYNTAX Integer32
			MAX-ACCESS read-write
			STATUS current
			DESCRIPTION
				"Description."
			::= { ripProcessEntry 14 }

		
		-- 1.3.6.1.4.1.3807.2.1812.5.1.15
		ripProcessRedistributeBgp OBJECT-TYPE
			SYNTAX INTEGER
				{
				enable(1),
				disable(2)
				}
			MAX-ACCESS read-write
			STATUS current
			DESCRIPTION
				"Description."
			::= { ripProcessEntry 15 }

		
		-- 1.3.6.1.4.1.3807.2.1812.5.1.16
		ripProcessRedistributeBgpCost OBJECT-TYPE
			SYNTAX Integer32 (0..15)
			MAX-ACCESS read-write
			STATUS current
			DESCRIPTION
				"Description."
			::= { ripProcessEntry 16 }

		
		-- 1.3.6.1.4.1.3807.2.1812.5.1.17
		ripProcessRedistributeBgpPolicy OBJECT-TYPE
			SYNTAX Integer32
			MAX-ACCESS read-write
			STATUS current
			DESCRIPTION
				"Description."
			::= { ripProcessEntry 17 }

		
		-- 1.3.6.1.4.1.3807.2.1812.5.1.18
		ripProcessRedistributeIsis OBJECT-TYPE
			SYNTAX INTEGER
				{
				enable(1),
				disable(2)
				}
			MAX-ACCESS read-write
			STATUS current
			DESCRIPTION
				"Description."
			::= { ripProcessEntry 18 }

		
		-- 1.3.6.1.4.1.3807.2.1812.5.1.19
		ripProcessRedistributeIsisCost OBJECT-TYPE
			SYNTAX Integer32 (0..15)
			MAX-ACCESS read-write
			STATUS current
			DESCRIPTION
				"Description."
			::= { ripProcessEntry 19 }

		
		-- 1.3.6.1.4.1.3807.2.1812.5.1.20
		ripProcessRedistributeIsisPolicy OBJECT-TYPE
			SYNTAX Integer32
			MAX-ACCESS read-write
			STATUS current
			DESCRIPTION
				"Description."
			::= { ripProcessEntry 20 }

		
		-- 1.3.6.1.4.1.3807.2.1812.5.1.21
		ripProcessEntryStatus OBJECT-TYPE
			SYNTAX EntryStatus
			MAX-ACCESS read-write
			STATUS current
			DESCRIPTION
				"Description."
			::= { ripProcessEntry 21 }

		
		-- 1.3.6.1.4.1.3807.2.1812.5.1.22
		ripProcessStaticFilterPolicy OBJECT-TYPE
			SYNTAX Integer32
			MAX-ACCESS read-write
			STATUS current
			DESCRIPTION
				"Description."
			::= { ripProcessEntry 22 }

		
		-- 1.3.6.1.4.1.3807.2.1812.5.1.23
		ripProcessConnectFilterPolicy OBJECT-TYPE
			SYNTAX Integer32
			MAX-ACCESS read-write
			STATUS current
			DESCRIPTION
				"Description."
			::= { ripProcessEntry 23 }

		
		-- 1.3.6.1.4.1.3807.2.1812.5.1.24
		ripProcessOspfFilterPolicy OBJECT-TYPE
			SYNTAX Integer32
			MAX-ACCESS read-write
			STATUS current
			DESCRIPTION
				"Description."
			::= { ripProcessEntry 24 }

		
		-- 1.3.6.1.4.1.3807.2.1812.5.1.25
		ripProcessBgpFilterPolicy OBJECT-TYPE
			SYNTAX Integer32
			MAX-ACCESS read-write
			STATUS current
			DESCRIPTION
				"Description."
			::= { ripProcessEntry 25 }

		
		-- 1.3.6.1.4.1.3807.2.1812.5.1.26
		ripProcessIsisFilterPolicy OBJECT-TYPE
			SYNTAX Integer32
			MAX-ACCESS read-write
			STATUS current
			DESCRIPTION
				"Description."
			::= { ripProcessEntry 26 }


		-- 1.3.6.1.4.1.3807.2.1812.5.1.27
		ripProcessUpdateTime OBJECT-TYPE
			SYNTAX Integer32
			MAX-ACCESS read-write
			STATUS current
			DESCRIPTION
				"Description."
			::= { ripProcessEntry 27 }

		
		-- 1.3.6.1.4.1.3807.2.1812.5.1.28
		ripProcessExpired OBJECT-TYPE
			SYNTAX Integer32
			MAX-ACCESS read-write
			STATUS current
			DESCRIPTION
				"Description."
			::= { ripProcessEntry 28 }

		
		-- 1.3.6.1.4.1.3807.2.1812.5.1.29
		ripProcessGarbAge OBJECT-TYPE
			SYNTAX Integer32
			MAX-ACCESS read-write
			STATUS current
			DESCRIPTION
				"Description."
			::= { ripProcessEntry 29 }

		
		-- 1.3.6.1.4.1.3807.2.1812.5.1.30
		ripProcessRouteDefault OBJECT-TYPE
			SYNTAX Integer32
			MAX-ACCESS read-write
			STATUS current
			DESCRIPTION
				"Description."
			::= { ripProcessEntry 30 }

		
		-- 1.3.6.1.4.1.3807.2.1812.5.1.31
		ripProcessCheckZero OBJECT-TYPE
			SYNTAX INTEGER
				{
				enable(1),
				disable(2)
				}
			MAX-ACCESS read-write
			STATUS current
			DESCRIPTION
				"Description."
			::= { ripProcessEntry 31 }


		-- 1.3.6.1.4.1.3807.2.1812.5.1.32
		ripProcessValidateSource OBJECT-TYPE
			SYNTAX INTEGER
				{
				enable(1),
				disable(2)
				}
			MAX-ACCESS read-write
			STATUS current
			DESCRIPTION
				"Description."
			::= { ripProcessEntry 32 }

		
		-- 1.3.6.1.4.1.3807.2.1812.5.1.33
		ripProcessHostRoute OBJECT-TYPE
			SYNTAX INTEGER
				{
				enable(1),
				disable(2)
				}
			MAX-ACCESS read-write
			STATUS current
			DESCRIPTION
				"Description."
			::= { ripProcessEntry 33 }

		
		-- 1.3.6.1.4.1.3807.2.1812.5.1.34
		ripProcessDefaultMetric OBJECT-TYPE
			SYNTAX Integer32 (0..15)
			MAX-ACCESS read-write
			STATUS current
			DESCRIPTION
				"Description."
			::= { ripProcessEntry 34 }

		
		-- 1.3.6.1.4.1.3807.2.1812.5.1.35
		ripProcessFilterIn OBJECT-TYPE
			SYNTAX Integer32
			MAX-ACCESS read-write
			STATUS current
			DESCRIPTION
				"Description."
			::= { ripProcessEntry 35 }

		
		-- 1.3.6.1.4.1.3807.2.1812.5.1.36
		ripProcessFilterOut OBJECT-TYPE
			SYNTAX Integer32
			MAX-ACCESS read-write
			STATUS current
			DESCRIPTION
				"Description."
			::= { ripProcessEntry 36 }

		
		-- 1.3.6.1.4.1.3807.2.1812.5.1.37
		ripProcessVpnId OBJECT-TYPE
			SYNTAX Integer32
			MAX-ACCESS read-write
			STATUS current
			DESCRIPTION
				"Description."
			::= { ripProcessEntry 37 }

		-- 1.3.6.1.4.1.3807.2.1812.5.1.38
		ripProcessDefaultRouteState  OBJECT-TYPE
			SYNTAX INTEGER
				{
				enable(1),
				disable(2)
				}
			MAX-ACCESS read-write
			STATUS current
			DESCRIPTION
				"Description ."
			::= { ripProcessEntry 38 }

		ripProcessPoisonReverse    OBJECT-TYPE
			SYNTAX INTEGER
				{
				enable(1),
				disable(2)
				}
			MAX-ACCESS read-write
			STATUS current
			DESCRIPTION
				"Description ."
			::= { ripProcessEntry 39 }
			
		ripProcessSummaryState	OBJECT-TYPE
			SYNTAX INTEGER
				{
				enable(1),
				disable(2)
				}
			MAX-ACCESS read-write
			STATUS current
			DESCRIPTION
				"Description ."
			::= { ripProcessEntry 40 }

		ripProcessFrrState 	OBJECT-TYPE
			SYNTAX INTEGER
				{
				enable(1),
				disable(2)
				}
			MAX-ACCESS read-write
			STATUS current
			DESCRIPTION
				"Description ."
			::= { ripProcessEntry 41 }
				
		-- 1.3.6.1.4.1.3807.2.1812.6
		ripRouteTable OBJECT-TYPE
			SYNTAX SEQUENCE OF RipRouteEntry
			MAX-ACCESS not-accessible
			STATUS current
			DESCRIPTION
				"Description."
			::= { wriRip 6 }

		
		-- 1.3.6.1.4.1.3807.2.1812.6.1
		ripRouteEntry OBJECT-TYPE
			SYNTAX RipRouteEntry
			MAX-ACCESS not-accessible
			STATUS current
			DESCRIPTION
				"Description."
			INDEX { ripRouteProcessId, ripRouteDst, ripRouteGateway, ripRouteNetmask, ripRouteProto
				 }
			::= { ripRouteTable 1 }

		
		RipRouteEntry ::=
			SEQUENCE { 
				ripRouteProcessId
					Integer32,
				ripRouteDst
					IpAddress,
				ripRouteGateway
					IpAddress,
				ripRouteNetmask
					IpAddress,
				ripRouteProto
					Integer32,
				ripRouteMetric
					Integer32,
				ripRouteAg
					Integer32,
				ripRouteTag
					Integer32,
				ripRouteFlag
					Integer32
			 }

		-- 1.3.6.1.4.1.3807.2.1812.6.1.1
		ripRouteProcessId OBJECT-TYPE
			SYNTAX Integer32
			MAX-ACCESS read-only
			STATUS current
			DESCRIPTION
				"Description."
			::= { ripRouteEntry 1 }

		
		-- 1.3.6.1.4.1.3807.2.1812.6.1.2
		ripRouteDst OBJECT-TYPE
			SYNTAX IpAddress
			MAX-ACCESS read-only
			STATUS current
			DESCRIPTION
				"Description."
			::= { ripRouteEntry 2 }

		
		-- 1.3.6.1.4.1.3807.2.1812.6.1.3
		ripRouteGateway OBJECT-TYPE
			SYNTAX IpAddress
			MAX-ACCESS read-only
			STATUS current
			DESCRIPTION
				"Description."
			::= { ripRouteEntry 3 }

		
		-- 1.3.6.1.4.1.3807.2.1812.6.1.4
		ripRouteNetmask OBJECT-TYPE
			SYNTAX IpAddress
			MAX-ACCESS read-only
			STATUS current
			DESCRIPTION
				"Description."
			::= { ripRouteEntry 4 }

		

		-- 1.3.6.1.4.1.3807.2.1812.6.1.5
		ripRouteProto OBJECT-TYPE
			SYNTAX Integer32
			MAX-ACCESS read-only
			STATUS current
			DESCRIPTION
				"Description."
			::= { ripRouteEntry 5 }

		
		-- 1.3.6.1.4.1.3807.2.1812.6.1.6
		ripRouteMetric OBJECT-TYPE
			SYNTAX Integer32
			MAX-ACCESS read-only
			STATUS current
			DESCRIPTION
				"Description."
			::= { ripRouteEntry 6 }


		-- 1.3.6.1.4.1.3807.2.1812.6.1.7
		ripRouteAg OBJECT-TYPE
			SYNTAX Integer32
			MAX-ACCESS read-only
			STATUS current
			DESCRIPTION
				"Description."
			::= { ripRouteEntry 7 }

		
		-- 1.3.6.1.4.1.3807.2.1812.6.1.8
		ripRouteTag OBJECT-TYPE
			SYNTAX Integer32
			MAX-ACCESS read-only
			STATUS current
			DESCRIPTION
				"Description."
			::= { ripRouteEntry 8 }

		
		-- 1.3.6.1.4.1.3807.2.1812.6.1.9
		ripRouteFlag OBJECT-TYPE
			SYNTAX Integer32
			MAX-ACCESS read-only
			STATUS current
			DESCRIPTION
				"Description."
			::= { ripRouteEntry 9 }

		-- 1.3.6.1.4.1.3807.2.1812.7
		ripNetWorkTable OBJECT-TYPE
			SYNTAX SEQUENCE OF RipNetWorkEntry
			MAX-ACCESS not-accessible
			STATUS current
			DESCRIPTION
				"Description."
			::= { wriRip 7 }

		
		-- 1.3.6.1.4.1.3807.2.1812.7.1
		ripNetWorkEntry OBJECT-TYPE
			SYNTAX RipNetWorkEntry
			MAX-ACCESS not-accessible
			STATUS current
			DESCRIPTION
				"Description."
			INDEX { ripNetWorkProcessId, ripNetWorkAddress}
			::= { ripNetWorkTable 1 }

		
		RipNetWorkEntry ::=
			SEQUENCE { 
				ripNetWorkProcessId
					Integer32,
				ripNetWorkAddress
					IpAddress,
				ripNetWorkStatus
					EntryStatus
				 }

		-- 1.3.6.1.4.1.3807.2.1812.7.1.1
		ripNetWorkProcessId OBJECT-TYPE
			SYNTAX Integer32
			MAX-ACCESS read-only
			STATUS current
			DESCRIPTION
				"Description."
			::= { ripNetWorkEntry 1 }

		
		-- 1.3.6.1.4.1.3807.2.1812.7.1.2
		ripNetWorkAddress OBJECT-TYPE
			SYNTAX IpAddress
			MAX-ACCESS read-only
			STATUS current
			DESCRIPTION
				"Description."
			::= { ripNetWorkEntry 2 }

		
		-- 1.3.6.1.4.1.3807.2.1812.7.1.3
		ripNetWorkStatus OBJECT-TYPE
			SYNTAX EntryStatus
			MAX-ACCESS read-write
			STATUS current
			DESCRIPTION
				"Description."
			::= { ripNetWorkEntry 3 }			  
			
			
			
	-- 1.3.6.1.4.1.3807.2.1812.8
		ripSummaryTable OBJECT-TYPE
			SYNTAX SEQUENCE OF RipSummaryEntry
			MAX-ACCESS not-accessible
			STATUS current
			DESCRIPTION
				"Description."
			::= { wriRip 8 }

		
		-- 1.3.6.1.4.1.3807.2.1812.8.1
		ripSummaryEntry OBJECT-TYPE
			SYNTAX RipSummaryEntry
			MAX-ACCESS not-accessible
			STATUS current
			DESCRIPTION
				"Description."
			INDEX { ripSummaryProcessId, ripSummaryIfAddress,ripSummaryAddress,ripSummaryMask}
			::= { ripSummaryTable 1 }

		
		RipSummaryEntry ::=
			SEQUENCE { 
				ripSummaryProcessId
					Integer32,
				ripSummaryIfAddress
					IpAddress, 
				ripSummaryAddress
					IpAddress, 
				ripSummaryMask
					IpAddress, 				
				ripSummaryStatus
					EntryStatus,
				ripSummaryAvoidFeedBack	
					INTEGER	
				 }

		-- 1.3.6.1.4.1.3807.2.1812.8.1.1
		ripSummaryProcessId OBJECT-TYPE
			SYNTAX Integer32
			MAX-ACCESS read-only
			STATUS current
			DESCRIPTION
				"Description."
			::= { ripSummaryEntry 1 }

		
		-- 1.3.6.1.4.1.3807.2.1812.8.1.2
		ripSummaryIfAddress OBJECT-TYPE
			SYNTAX IpAddress
			MAX-ACCESS read-only
			STATUS current
			DESCRIPTION
				"Description."
			::= { ripSummaryEntry 2 }

		    
		-- 1.3.6.1.4.1.3807.2.1812.8.1.3
		ripSummaryAddress OBJECT-TYPE
			SYNTAX IpAddress
			MAX-ACCESS read-only
			STATUS current
			DESCRIPTION
				"Description."
			::= { ripSummaryEntry 3 }
	    
		 
		 -- 1.3.6.1.4.1.3807.2.1812.8.1.4
		ripSummaryMask OBJECT-TYPE
			SYNTAX IpAddress
			MAX-ACCESS read-only
			STATUS current
			DESCRIPTION
				"Description."
			::= { ripSummaryEntry 4 }

		    
		-- 1.3.6.1.4.1.3807.2.1812.8.1.5
		ripSummaryStatus OBJECT-TYPE
			SYNTAX EntryStatus
			MAX-ACCESS read-write
			STATUS current
			DESCRIPTION
				"Description."
			::= { ripSummaryEntry 5 }			
		
	    
	    -- 1.3.6.1.4.1.3807.2.1812.8.1.6
		ripSummaryAvoidFeedBack OBJECT-TYPE
			SYNTAX INTEGER{enable(1),disable(2)}
			MAX-ACCESS read-write
			STATUS current
			DESCRIPTION
				"Description."
			::= { ripSummaryEntry 6 }
	END

--
-- rip.mib
--
