--
-- netflow.mib
-- MIB generated by MG-SOFT Visual MIB Builder Version 4.0 Build 349
-- Thursday, August 22, 2013 at 16:24:02
--

	WRI-NETFLOW-MIB DEFINITIONS ::= BEGIN
 
		IMPORTS
			Integer32, Unsigned32, Counter64, OBJECT-TYPE			
				FROM SNMPv2-SMI			
			TEXTUAL-CONVENTION			
				FROM SNMPv2-TC			
			wriProducts, wriProtocol			
				FROM WRI-SMI;
	
	
--
-- Type definitions
--
	
		DisplayString ::= OCTET STRING

	
--
-- Textual conventions
--
	
		EntryStatus ::= TEXTUAL-CONVENTION
			STATUS current
			DESCRIPTION 
				"entry status."
			SYNTAX INTEGER
				{
				valid(1),
				createRequest(2),
				underCreation(3),
				invalid(4)
				}

	
--
-- Node definitions
--
	
		-- 1.3.6.1.4.1.3807.2.1403
		netflow OBJECT IDENTIFIER ::= { wriProtocol 1403 }

		
		-- 1.3.6.1.4.1.3807.2.1403.1
		netflowGlobal OBJECT IDENTIFIER ::= { netflow 1 }

		
		-- 1.3.6.1.4.1.3807.2.1403.1.1
		netflowSampleMaxSize OBJECT-TYPE
			SYNTAX Integer32
			MAX-ACCESS read-only
			STATUS current
			DESCRIPTION
				"Description."
			::= { netflowGlobal 1 }

		
		-- 1.3.6.1.4.1.3807.2.1403.1.2
		netflowRecordMaxSize OBJECT-TYPE
			SYNTAX Integer32
			MAX-ACCESS read-only
			STATUS current
			DESCRIPTION
				"Description."
			::= { netflowGlobal 2 }

		
		-- 1.3.6.1.4.1.3807.2.1403.1.3
		netflowExporterMaxSize OBJECT-TYPE
			SYNTAX Integer32
			MAX-ACCESS read-only
			STATUS current
			DESCRIPTION
				"Description."
			::= { netflowGlobal 3 }

		
		-- 1.3.6.1.4.1.3807.2.1403.1.4
		netflowMonitorMaxSize OBJECT-TYPE
			SYNTAX Integer32
			MAX-ACCESS read-only
			STATUS current
			DESCRIPTION
				"Description."
			::= { netflowGlobal 4 }

		
		-- 1.3.6.1.4.1.3807.2.1403.1.5
		netflowIfMaxSize OBJECT-TYPE
			SYNTAX Integer32
			MAX-ACCESS read-only
			STATUS current
			DESCRIPTION
				"Description."
			::= { netflowGlobal 5 }

		
		-- 1.3.6.1.4.1.3807.2.1403.1.6
		netflowSamplerFreeIdx OBJECT-TYPE
			SYNTAX Integer32
			MAX-ACCESS read-only
			STATUS current
			DESCRIPTION
				"Description."
			::= { netflowGlobal 6 }

		
		-- 1.3.6.1.4.1.3807.2.1403.1.7
		netflowRecordFreeIdx OBJECT-TYPE
			SYNTAX Integer32
			MAX-ACCESS read-only
			STATUS current
			DESCRIPTION
				"Description."
			::= { netflowGlobal 7 }

		
		-- 1.3.6.1.4.1.3807.2.1403.1.8
		netflowExporterFreeIdx OBJECT-TYPE
			SYNTAX Integer32
			MAX-ACCESS read-only
			STATUS current
			DESCRIPTION
				"Description."
			::= { netflowGlobal 8 }

		
		-- 1.3.6.1.4.1.3807.2.1403.1.9
		netflowMonitorFreeIdx OBJECT-TYPE
			SYNTAX Integer32
			MAX-ACCESS read-only
			STATUS current
			DESCRIPTION
				"Description."
			::= { netflowGlobal 9 }

		
		-- 1.3.6.1.4.1.3807.2.1403.1.10
		netflowIfUsedSize OBJECT-TYPE
			SYNTAX Integer32
			MAX-ACCESS read-only
			STATUS current
			DESCRIPTION
				"Description."
			::= { netflowGlobal 10 }

		
		-- 1.3.6.1.4.1.3807.2.1403.1.11
		netflowSamplerUsedSize OBJECT-TYPE
			SYNTAX Integer32
			MAX-ACCESS read-only
			STATUS current
			DESCRIPTION
				"Description."
			::= { netflowGlobal 11 }

		
		-- 1.3.6.1.4.1.3807.2.1403.1.12
		netflowRecordUsedSize OBJECT-TYPE
			SYNTAX Integer32
			MAX-ACCESS read-only
			STATUS current
			DESCRIPTION
				"Description."
			::= { netflowGlobal 12 }

		
		-- 1.3.6.1.4.1.3807.2.1403.1.13
		netflowExporterUsedSize OBJECT-TYPE
			SYNTAX Integer32
			MAX-ACCESS read-only
			STATUS current
			DESCRIPTION
				"Description."
			::= { netflowGlobal 13 }

		
		-- 1.3.6.1.4.1.3807.2.1403.1.14
		netflowMonitorUsedSize OBJECT-TYPE
			SYNTAX Integer32
			MAX-ACCESS read-only
			STATUS current
			DESCRIPTION
				"Description."
			::= { netflowGlobal 14 }

		
		-- 1.3.6.1.4.1.3807.2.1403.2
		netflowSamplerTable OBJECT-TYPE
			SYNTAX SEQUENCE OF NetflowSamplerEntry
			MAX-ACCESS not-accessible
			STATUS current
			DESCRIPTION
				"Description."
			::= { netflow 2 }

		
		-- 1.3.6.1.4.1.3807.2.1403.2.1
		netflowSamplerEntry OBJECT-TYPE
			SYNTAX NetflowSamplerEntry
			MAX-ACCESS not-accessible
			STATUS current
			DESCRIPTION
				"Description."
			INDEX { netflowSamplerIdx }
			::= { netflowSamplerTable 1 }

		
		NetflowSamplerEntry ::=
			SEQUENCE { 
				netflowSamplerIdx
					Integer32,
				netflowSamplerEntryStatus
					Integer32,
				netflowSamplerName
					DisplayString,
				netflowSamplerType
					Integer32,
				netflowSamplerRate
					Integer32,
				netflowSamplerDescription
					DisplayString,
				netflowSamplerInterval
					Integer32,
				netflowSamplerRefCnt
					Integer32
			 }

		-- 1.3.6.1.4.1.3807.2.1403.2.1.1
		netflowSamplerIdx OBJECT-TYPE
			SYNTAX Integer32
			MAX-ACCESS read-only
			STATUS current
			DESCRIPTION
				"Description."
			::= { netflowSamplerEntry 1 }

		
		-- 1.3.6.1.4.1.3807.2.1403.2.1.2
		netflowSamplerEntryStatus OBJECT-TYPE
			SYNTAX Integer32
			MAX-ACCESS read-write
			STATUS current
			DESCRIPTION
				"Description."
			::= { netflowSamplerEntry 2 }

		
		-- 1.3.6.1.4.1.3807.2.1403.2.1.3
		netflowSamplerName OBJECT-TYPE
			SYNTAX DisplayString (SIZE (0..32))
			MAX-ACCESS read-write
			STATUS current
			DESCRIPTION
				"Description."
			::= { netflowSamplerEntry 3 }

		
		-- 1.3.6.1.4.1.3807.2.1403.2.1.4
		netflowSamplerType OBJECT-TYPE
			SYNTAX Integer32
			MAX-ACCESS read-write
			STATUS current
			DESCRIPTION
				"Description."
			::= { netflowSamplerEntry 4 }

		
		-- 1.3.6.1.4.1.3807.2.1403.2.1.5
		netflowSamplerRate OBJECT-TYPE
			SYNTAX Integer32
			MAX-ACCESS read-write
			STATUS current
			DESCRIPTION
				"Description."
			::= { netflowSamplerEntry 5 }

		
		-- 1.3.6.1.4.1.3807.2.1403.2.1.6
		netflowSamplerDescription OBJECT-TYPE
			SYNTAX DisplayString (SIZE (0..128))
			MAX-ACCESS read-write
			STATUS current
			DESCRIPTION
				"Description."
			::= { netflowSamplerEntry 6 }

		
		-- 1.3.6.1.4.1.3807.2.1403.2.1.7
		netflowSamplerInterval OBJECT-TYPE
			SYNTAX Integer32
			MAX-ACCESS read-write
			STATUS current
			DESCRIPTION
				"Description."
			::= { netflowSamplerEntry 7 }

		
		-- 1.3.6.1.4.1.3807.2.1403.2.1.8
		netflowSamplerRefCnt OBJECT-TYPE
			SYNTAX Integer32
			MAX-ACCESS read-only
			STATUS current
			DESCRIPTION
				"Description."
			::= { netflowSamplerEntry 8 }

		
		-- 1.3.6.1.4.1.3807.2.1403.3
		netflowRecordTable OBJECT-TYPE
			SYNTAX SEQUENCE OF NetflowRecordEntry
			MAX-ACCESS not-accessible
			STATUS current
			DESCRIPTION
				"Description."
			::= { netflow 3 }

		
		-- 1.3.6.1.4.1.3807.2.1403.3.1
		netflowRecordEntry OBJECT-TYPE
			SYNTAX NetflowRecordEntry
			MAX-ACCESS not-accessible
			STATUS current
			DESCRIPTION
				"Description."
			INDEX { netflowRecordIdx }
			::= { netflowRecordTable 1 }

		
		NetflowRecordEntry ::=
			SEQUENCE { 
				netflowRecordIdx
					Integer32,
				netflowRecordEntryStatus
					Integer32,
				netflowRecordName
					DisplayString,
				netflowRecordMatchField
					OCTET STRING,
				netflowRecordCollectField
					OCTET STRING,
				netflowRecordDescription
					DisplayString,
				netflowRecordRefCnt
					Integer32
			 }

		-- 1.3.6.1.4.1.3807.2.1403.3.1.1
		netflowRecordIdx OBJECT-TYPE
			SYNTAX Integer32
			MAX-ACCESS read-only
			STATUS current
			DESCRIPTION
				"Description."
			::= { netflowRecordEntry 1 }

		
		-- 1.3.6.1.4.1.3807.2.1403.3.1.2
		netflowRecordEntryStatus OBJECT-TYPE
			SYNTAX Integer32
			MAX-ACCESS read-write
			STATUS current
			DESCRIPTION
				"Description."
			::= { netflowRecordEntry 2 }

		
		-- 1.3.6.1.4.1.3807.2.1403.3.1.3
		netflowRecordName OBJECT-TYPE
			SYNTAX DisplayString (SIZE (0..32))
			MAX-ACCESS read-write
			STATUS current
			DESCRIPTION
				"Description."
			::= { netflowRecordEntry 3 }

		
		-- 1.3.6.1.4.1.3807.2.1403.3.1.4
		netflowRecordMatchField OBJECT-TYPE
			SYNTAX OCTET STRING (SIZE (0..16))
			MAX-ACCESS read-write
			STATUS current
			DESCRIPTION
				"Description."
			::= { netflowRecordEntry 4 }

		
		-- 1.3.6.1.4.1.3807.2.1403.3.1.5
		netflowRecordCollectField OBJECT-TYPE
			SYNTAX OCTET STRING (SIZE (0..16))
			MAX-ACCESS read-write
			STATUS current
			DESCRIPTION
				"Description."
			::= { netflowRecordEntry 5 }

		
		-- 1.3.6.1.4.1.3807.2.1403.3.1.6
		netflowRecordDescription OBJECT-TYPE
			SYNTAX DisplayString (SIZE (0..128))
			MAX-ACCESS read-write
			STATUS current
			DESCRIPTION
				"Description."
			::= { netflowRecordEntry 6 }

		
		-- 1.3.6.1.4.1.3807.2.1403.3.1.7
		netflowRecordRefCnt OBJECT-TYPE
			SYNTAX Integer32
			MAX-ACCESS read-only
			STATUS current
			DESCRIPTION
				"Description."
			::= { netflowRecordEntry 7 }

		
		-- 1.3.6.1.4.1.3807.2.1403.4
		netflowExporterTable OBJECT-TYPE
			SYNTAX SEQUENCE OF NetflowExporterEntry
			MAX-ACCESS not-accessible
			STATUS current
			DESCRIPTION
				"Description."
			::= { netflow 4 }

		
		-- 1.3.6.1.4.1.3807.2.1403.4.1
		netflowExporterEntry OBJECT-TYPE
			SYNTAX NetflowExporterEntry
			MAX-ACCESS not-accessible
			STATUS current
			DESCRIPTION
				"Description."
			INDEX { netflowExporterIdx }
			::= { netflowExporterTable 1 }

		
		NetflowExporterEntry ::=
			SEQUENCE { 
				netflowExporterIdx
					Integer32,
				netflowExporterEntryStatus
					Integer32,
				netflowExporterName
					DisplayString,
				netflowExporterVersion
					Integer32,
				netflowExporterTransProtocol
					Integer32,
				netflowExporterDstIpAddrType
					Integer32,
				netflowExporterDstIpAddr
					OCTET STRING,
				netflowExporterHostName
					DisplayString,
				netflowExporterSrcIf
					Integer32,
				netflowExporterUdpPort
					Integer32,
				netflowExporterTTL
					Integer32,
				netflowExporterDescription
					DisplayString,
				netflowExporterTemUpdateTimeout
					Integer32,
				netflowExporterRefCnt
					Integer32,
				netflowExporterDstIpVrid
					Integer32
			 }

		-- 1.3.6.1.4.1.3807.2.1403.4.1.1
		netflowExporterIdx OBJECT-TYPE
			SYNTAX Integer32
			MAX-ACCESS read-only
			STATUS current
			DESCRIPTION
				"Description."
			::= { netflowExporterEntry 1 }

		
		-- 1.3.6.1.4.1.3807.2.1403.4.1.2
		netflowExporterEntryStatus OBJECT-TYPE
			SYNTAX Integer32
			MAX-ACCESS read-write
			STATUS current
			DESCRIPTION
				"Description."
			::= { netflowExporterEntry 2 }

		
		-- 1.3.6.1.4.1.3807.2.1403.4.1.3
		netflowExporterName OBJECT-TYPE
			SYNTAX DisplayString (SIZE (0..32))
			MAX-ACCESS read-write
			STATUS current
			DESCRIPTION
				"Description."
			::= { netflowExporterEntry 3 }

		
		-- 1.3.6.1.4.1.3807.2.1403.4.1.4
		netflowExporterVersion OBJECT-TYPE
			SYNTAX Integer32
			MAX-ACCESS read-write
			STATUS current
			DESCRIPTION
				"Description."
			::= { netflowExporterEntry 4 }

		
		-- 1.3.6.1.4.1.3807.2.1403.4.1.5
		netflowExporterTransProtocol OBJECT-TYPE
			SYNTAX Integer32
			MAX-ACCESS read-write
			STATUS current
			DESCRIPTION
				"Description."
			::= { netflowExporterEntry 5 }

		
		-- 1.3.6.1.4.1.3807.2.1403.4.1.6
		netflowExporterDstIpAddrType OBJECT-TYPE
			SYNTAX Integer32
			MAX-ACCESS read-write
			STATUS current
			DESCRIPTION
				"Description."
			::= { netflowExporterEntry 6 }

		
		-- 1.3.6.1.4.1.3807.2.1403.4.1.7
		netflowExporterDstIpAddr OBJECT-TYPE
			SYNTAX OCTET STRING
			MAX-ACCESS read-write
			STATUS current
			DESCRIPTION
				"Description."
			::= { netflowExporterEntry 7 }

		
		-- 1.3.6.1.4.1.3807.2.1403.4.1.8
		netflowExporterHostName OBJECT-TYPE
			SYNTAX DisplayString (SIZE (0..32))
			MAX-ACCESS read-write
			STATUS current
			DESCRIPTION
				"Description."
			::= { netflowExporterEntry 8 }

		
		-- 1.3.6.1.4.1.3807.2.1403.4.1.9
		netflowExporterSrcIf OBJECT-TYPE
			SYNTAX Integer32
			MAX-ACCESS read-write
			STATUS current
			DESCRIPTION
				"Description."
			::= { netflowExporterEntry 9 }

		
		-- 1.3.6.1.4.1.3807.2.1403.4.1.10
		netflowExporterUdpPort OBJECT-TYPE
			SYNTAX Integer32
			MAX-ACCESS read-write
			STATUS current
			DESCRIPTION
				"Description."
			::= { netflowExporterEntry 10 }

		
		-- 1.3.6.1.4.1.3807.2.1403.4.1.11
		netflowExporterTTL OBJECT-TYPE
			SYNTAX Integer32
			MAX-ACCESS read-write
			STATUS current
			DESCRIPTION
				"Description."
			::= { netflowExporterEntry 11 }

		
		-- 1.3.6.1.4.1.3807.2.1403.4.1.12
		netflowExporterDescription OBJECT-TYPE
			SYNTAX DisplayString (SIZE (0..128))
			MAX-ACCESS read-write
			STATUS current
			DESCRIPTION
				"Description."
			::= { netflowExporterEntry 12 }

		
		-- 1.3.6.1.4.1.3807.2.1403.4.1.13
		netflowExporterTemUpdateTimeout OBJECT-TYPE
			SYNTAX Integer32
			MAX-ACCESS read-write
			STATUS current
			DESCRIPTION
				"Description."
			::= { netflowExporterEntry 13 }

		
		-- 1.3.6.1.4.1.3807.2.1403.4.1.14
		netflowExporterRefCnt OBJECT-TYPE
			SYNTAX Integer32
			MAX-ACCESS read-only
			STATUS current
			DESCRIPTION
				"Description."
			::= { netflowExporterEntry 14 }

		
		-- 1.3.6.1.4.1.3807.2.1403.4.1.15
		netflowExporterDstIpVrid OBJECT-TYPE
			SYNTAX Integer32
			MAX-ACCESS read-write
			STATUS current
			DESCRIPTION
				"Description."
			::= { netflowExporterEntry 15 }

		
		-- 1.3.6.1.4.1.3807.2.1403.5
		netflowMonitorTable OBJECT-TYPE
			SYNTAX SEQUENCE OF NetflowMonitorEntry
			MAX-ACCESS not-accessible
			STATUS current
			DESCRIPTION
				"Description."
			::= { netflow 5 }

		
		-- 1.3.6.1.4.1.3807.2.1403.5.1
		netflowMonitorEntry OBJECT-TYPE
			SYNTAX NetflowMonitorEntry
			MAX-ACCESS not-accessible
			STATUS current
			DESCRIPTION
				"Description."
			INDEX { netflowMonitorIdx }
			::= { netflowMonitorTable 1 }

		
		NetflowMonitorEntry ::=
			SEQUENCE { 
				netflowMonitorIdx
					Integer32,
				netflowMonitorEntryStatus
					Integer32,
				netflowMonitorName
					DisplayString,
				netflowMonitorRecordId
					Integer32,
				netflowMonitorExporterId
					OCTET STRING,
				netflowMonitorExporterIdDel
					Integer32,
				netflowMonitorCacheSize
					Integer32,
				netflowMonitorCacheType
					Integer32,
				netflowMonitorActiveTimeout
					Integer32,
				netflowMonitorInactiveTimeout
					Integer32,
				netflowMonitorUpdateTimeout
					Integer32,
				netflowMonitorCurCacheSize
					Integer32,
				netflowMonitorAddedFlow
					Integer32,
				netflowMonitorActiveAgedFlow
					Integer32,
				netflowMonitorInactiveAgedFlow
					Integer32,
				netflowMonitorEventAgedFlow
					Integer32,
				netflowMonitorEmergAgedFlow
					Integer32,
				netflowMonitorDescription
					DisplayString,
				netflowMonitorRefCnt
					Integer32,
				netflowMonitorClear
					Integer32
			 }

		-- 1.3.6.1.4.1.3807.2.1403.5.1.1
		netflowMonitorIdx OBJECT-TYPE
			SYNTAX Integer32
			MAX-ACCESS read-only
			STATUS current
			DESCRIPTION
				"Description."
			::= { netflowMonitorEntry 1 }

		
		-- 1.3.6.1.4.1.3807.2.1403.5.1.2
		netflowMonitorEntryStatus OBJECT-TYPE
			SYNTAX Integer32
			MAX-ACCESS read-write
			STATUS current
			DESCRIPTION
				"Description."
			::= { netflowMonitorEntry 2 }

		
		-- 1.3.6.1.4.1.3807.2.1403.5.1.3
		netflowMonitorName OBJECT-TYPE
			SYNTAX DisplayString (SIZE (0..32))
			MAX-ACCESS read-write
			STATUS current
			DESCRIPTION
				"Description."
			::= { netflowMonitorEntry 3 }

		
		-- 1.3.6.1.4.1.3807.2.1403.5.1.4
		netflowMonitorRecordId OBJECT-TYPE
			SYNTAX Integer32
			MAX-ACCESS read-write
			STATUS current
			DESCRIPTION
				"Description."
			::= { netflowMonitorEntry 4 }

		
		-- 1.3.6.1.4.1.3807.2.1403.5.1.5
		netflowMonitorExporterId OBJECT-TYPE
			SYNTAX OCTET STRING
			MAX-ACCESS read-write
			STATUS current
			DESCRIPTION
				"Description."
			::= { netflowMonitorEntry 5 }

		
		-- 1.3.6.1.4.1.3807.2.1403.5.1.6
		netflowMonitorExporterIdDel OBJECT-TYPE
			SYNTAX Integer32
			MAX-ACCESS read-write
			STATUS current
			DESCRIPTION
				"Description."
			::= { netflowMonitorEntry 6 }

		
		-- 1.3.6.1.4.1.3807.2.1403.5.1.7
		netflowMonitorCacheSize OBJECT-TYPE
			SYNTAX Integer32
			MAX-ACCESS read-write
			STATUS current
			DESCRIPTION
				"Description."
			::= { netflowMonitorEntry 7 }

		
		-- 1.3.6.1.4.1.3807.2.1403.5.1.8
		netflowMonitorCacheType OBJECT-TYPE
			SYNTAX Integer32
			MAX-ACCESS read-write
			STATUS current
			DESCRIPTION
				"Description."
			::= { netflowMonitorEntry 8 }

		
		-- 1.3.6.1.4.1.3807.2.1403.5.1.9
		netflowMonitorActiveTimeout OBJECT-TYPE
			SYNTAX Integer32
			MAX-ACCESS read-write
			STATUS current
			DESCRIPTION
				"Description."
			::= { netflowMonitorEntry 9 }

		
		-- 1.3.6.1.4.1.3807.2.1403.5.1.10
		netflowMonitorInactiveTimeout OBJECT-TYPE
			SYNTAX Integer32
			MAX-ACCESS read-write
			STATUS current
			DESCRIPTION
				"Description."
			::= { netflowMonitorEntry 10 }

		
		-- 1.3.6.1.4.1.3807.2.1403.5.1.11
		netflowMonitorUpdateTimeout OBJECT-TYPE
			SYNTAX Integer32
			MAX-ACCESS read-write
			STATUS current
			DESCRIPTION
				"Description."
			::= { netflowMonitorEntry 11 }

		
		-- 1.3.6.1.4.1.3807.2.1403.5.1.12
		netflowMonitorCurCacheSize OBJECT-TYPE
			SYNTAX Integer32
			MAX-ACCESS read-only
			STATUS current
			DESCRIPTION
				"Description."
			::= { netflowMonitorEntry 12 }

		
		-- 1.3.6.1.4.1.3807.2.1403.5.1.13
		netflowMonitorAddedFlow OBJECT-TYPE
			SYNTAX Integer32
			MAX-ACCESS read-only
			STATUS current
			DESCRIPTION
				"Description."
			::= { netflowMonitorEntry 13 }

		
		-- 1.3.6.1.4.1.3807.2.1403.5.1.14
		netflowMonitorActiveAgedFlow OBJECT-TYPE
			SYNTAX Integer32
			MAX-ACCESS read-only
			STATUS current
			DESCRIPTION
				"Description."
			::= { netflowMonitorEntry 14 }

		
		-- 1.3.6.1.4.1.3807.2.1403.5.1.15
		netflowMonitorInactiveAgedFlow OBJECT-TYPE
			SYNTAX Integer32
			MAX-ACCESS read-only
			STATUS current
			DESCRIPTION
				"Description."
			::= { netflowMonitorEntry 15 }

		
		-- 1.3.6.1.4.1.3807.2.1403.5.1.16
		netflowMonitorEventAgedFlow OBJECT-TYPE
			SYNTAX Integer32
			MAX-ACCESS read-only
			STATUS current
			DESCRIPTION
				"Description."
			::= { netflowMonitorEntry 16 }

		
		-- 1.3.6.1.4.1.3807.2.1403.5.1.17
		netflowMonitorEmergAgedFlow OBJECT-TYPE
			SYNTAX Integer32
			MAX-ACCESS read-only
			STATUS current
			DESCRIPTION
				"Description."
			::= { netflowMonitorEntry 17 }

		
		-- 1.3.6.1.4.1.3807.2.1403.5.1.18
		netflowMonitorDescription OBJECT-TYPE
			SYNTAX DisplayString (SIZE (0..128))
			MAX-ACCESS read-write
			STATUS current
			DESCRIPTION
				"Description."
			::= { netflowMonitorEntry 18 }

		
		-- 1.3.6.1.4.1.3807.2.1403.5.1.19
		netflowMonitorRefCnt OBJECT-TYPE
			SYNTAX Integer32
			MAX-ACCESS read-only
			STATUS current
			DESCRIPTION
				"Description."
			::= { netflowMonitorEntry 19 }

		
		-- 1.3.6.1.4.1.3807.2.1403.5.1.20
		netflowMonitorClear OBJECT-TYPE
			SYNTAX Integer32
			MAX-ACCESS read-write
			STATUS current
			DESCRIPTION
				"Description."
			::= { netflowMonitorEntry 20 }

		
		-- 1.3.6.1.4.1.3807.2.1403.6
		netflowIfTable OBJECT-TYPE
			SYNTAX SEQUENCE OF NetflowIfEntry
			MAX-ACCESS not-accessible
			STATUS current
			DESCRIPTION
				"Description."
			::= { netflow 6 }

		
		-- 1.3.6.1.4.1.3807.2.1403.6.1
		netflowIfEntry OBJECT-TYPE
			SYNTAX NetflowIfEntry
			MAX-ACCESS not-accessible
			STATUS current
			DESCRIPTION
				"Description."
			INDEX { netflowIfIndex }
			::= { netflowIfTable 1 }

		
		NetflowIfEntry ::=
			SEQUENCE { 
				netflowIfIndex
					Unsigned32,
				netflowIfEntryStatus
					Integer32,
				netflowIfIpv4InSamplerId
					Integer32,
				netflowIfIpv4OutSamplerId
					Integer32,
				netflowIfIpv6InSamplerId
					Integer32,
				netflowIfIpv6OutSamplerId
					Integer32,
				netflowIfL2InSamplerId
					Integer32,
				netflowIfL2OutSamplerId
					Integer32,
				netflowIfIpv4InMonId
					Integer32,
				netflowIfIpv4OutMonId
					Integer32,
				netflowIfIpv6InMonId
					Integer32,
				netflowIfIpv6OutMonId
					Integer32,
				netflowIfL2InMonId
					Integer32,
				netflowIfL2OutMonId
					Integer32,
				netflowIfIpv4InBind
					Integer32,
				netflowIfIpv4OutBind
					Integer32,
				netflowIfIpv6InBind
					Integer32,
				netflowIfIpv6OutBind
					Integer32,
				netflowIfL2InBind
					Integer32,
				netflowIfL2OutBind
					Integer32,
				netflowIfCast
					Integer32,
				netflowIfIpv4InSampledPkts
					Counter64,
				netflowIfIpv4OutSampledPkts
					Counter64,
				netflowIfIpv6InSampledPkts
					Counter64,
				netflowIfIpv6OutSampledPkts
					Counter64,
				netflowIfL2InSampledPkts
					Counter64,
				netflowIfL2OutSampledPkts
					Counter64,
				netflowIfIpv4InMatchedPkts
					Counter64,
				netflowIfIpv4OutMatchedPkts
					Counter64,
				netflowIfIpv6InMatchedPkts
					Counter64,
				netflowIfIpv6OutMatchedPkts
					Counter64,
				netflowIfL2InMatchedPkts
					Counter64,
				netflowIfL2OutMatchedPkts
					Counter64,
				netflowIfIpv4InTime
					Integer32,
				netflowIfIpv4OutTime
					Integer32,
				netflowIfIpv6InTime
					Integer32,
				netflowIfIpv6OutTime
					Integer32,
				netflowIfL2InTime
					Integer32,
				netflowIfL2OutTime
					Integer32,
				netflowIfMplsInSamplerId
					Integer32,
				netflowIfMplsOutSamplerId
					Integer32,
				netflowIfMplsInMonId
					Integer32,
				netflowIfMplsOutMonId
					Integer32,
				netflowIfMplsInBind
					Integer32,
				netflowIfMplsOutBind
					Integer32,
				netflowIfMplsInSampledPkts
					Counter64,
				netflowIfMplsOutSampledPkts
					Counter64,
				netflowIfMplsInMatchedPkts
					Counter64,
				netflowIfMplsOutMatchedPkts
					Counter64,
				netflowIfMplsInTime
					Integer32,
				netflowIfMplsOutTime
					Integer32
			 }

		-- 1.3.6.1.4.1.3807.2.1403.6.1.1
		netflowIfIndex OBJECT-TYPE
			SYNTAX Unsigned32
			MAX-ACCESS read-only
			STATUS current
			DESCRIPTION
				"Description."
			::= { netflowIfEntry 1 }

		
		-- 1.3.6.1.4.1.3807.2.1403.6.1.2
		netflowIfEntryStatus OBJECT-TYPE
			SYNTAX Integer32
			MAX-ACCESS read-write
			STATUS current
			DESCRIPTION
				"Description."
			::= { netflowIfEntry 2 }

		
		-- 1.3.6.1.4.1.3807.2.1403.6.1.3
		netflowIfIpv4InSamplerId OBJECT-TYPE
			SYNTAX Integer32
			MAX-ACCESS read-write
			STATUS current
			DESCRIPTION
				"Description."
			::= { netflowIfEntry 3 }

		
		-- 1.3.6.1.4.1.3807.2.1403.6.1.4
		netflowIfIpv4OutSamplerId OBJECT-TYPE
			SYNTAX Integer32
			MAX-ACCESS read-write
			STATUS current
			DESCRIPTION
				"Description."
			::= { netflowIfEntry 4 }

		
		-- 1.3.6.1.4.1.3807.2.1403.6.1.5
		netflowIfIpv6InSamplerId OBJECT-TYPE
			SYNTAX Integer32
			MAX-ACCESS read-write
			STATUS current
			DESCRIPTION
				"Description."
			::= { netflowIfEntry 5 }

		
		-- 1.3.6.1.4.1.3807.2.1403.6.1.6
		netflowIfIpv6OutSamplerId OBJECT-TYPE
			SYNTAX Integer32
			MAX-ACCESS read-write
			STATUS current
			DESCRIPTION
				"Description."
			::= { netflowIfEntry 6 }

		
		-- 1.3.6.1.4.1.3807.2.1403.6.1.7
		netflowIfL2InSamplerId OBJECT-TYPE
			SYNTAX Integer32
			MAX-ACCESS read-write
			STATUS current
			DESCRIPTION
				"Description."
			::= { netflowIfEntry 7 }

		
		-- 1.3.6.1.4.1.3807.2.1403.6.1.8
		netflowIfL2OutSamplerId OBJECT-TYPE
			SYNTAX Integer32
			MAX-ACCESS read-write
			STATUS current
			DESCRIPTION
				"Description."
			::= { netflowIfEntry 8 }

		
		-- 1.3.6.1.4.1.3807.2.1403.6.1.9
		netflowIfIpv4InMonId OBJECT-TYPE
			SYNTAX Integer32
			MAX-ACCESS read-write
			STATUS current
			DESCRIPTION
				"Description."
			::= { netflowIfEntry 9 }

		
		-- 1.3.6.1.4.1.3807.2.1403.6.1.10
		netflowIfIpv4OutMonId OBJECT-TYPE
			SYNTAX Integer32
			MAX-ACCESS read-write
			STATUS current
			DESCRIPTION
				"Description."
			::= { netflowIfEntry 10 }

		
		-- 1.3.6.1.4.1.3807.2.1403.6.1.11
		netflowIfIpv6InMonId OBJECT-TYPE
			SYNTAX Integer32
			MAX-ACCESS read-write
			STATUS current
			DESCRIPTION
				"Description."
			::= { netflowIfEntry 11 }

		
		-- 1.3.6.1.4.1.3807.2.1403.6.1.12
		netflowIfIpv6OutMonId OBJECT-TYPE
			SYNTAX Integer32
			MAX-ACCESS read-write
			STATUS current
			DESCRIPTION
				"Description."
			::= { netflowIfEntry 12 }

		
		-- 1.3.6.1.4.1.3807.2.1403.6.1.13
		netflowIfL2InMonId OBJECT-TYPE
			SYNTAX Integer32
			MAX-ACCESS read-write
			STATUS current
			DESCRIPTION
				"Description."
			::= { netflowIfEntry 13 }

		
		-- 1.3.6.1.4.1.3807.2.1403.6.1.14
		netflowIfL2OutMonId OBJECT-TYPE
			SYNTAX Integer32
			MAX-ACCESS read-write
			STATUS current
			DESCRIPTION
				"Description."
			::= { netflowIfEntry 14 }

		
		-- 1.3.6.1.4.1.3807.2.1403.6.1.15
		netflowIfIpv4InBind OBJECT-TYPE
			SYNTAX Integer32
			MAX-ACCESS read-write
			STATUS current
			DESCRIPTION
				"Description."
			::= { netflowIfEntry 15 }

		
		-- 1.3.6.1.4.1.3807.2.1403.6.1.16
		netflowIfIpv4OutBind OBJECT-TYPE
			SYNTAX Integer32
			MAX-ACCESS read-write
			STATUS current
			DESCRIPTION
				"Description."
			::= { netflowIfEntry 16 }

		
		-- 1.3.6.1.4.1.3807.2.1403.6.1.17
		netflowIfIpv6InBind OBJECT-TYPE
			SYNTAX Integer32
			MAX-ACCESS read-write
			STATUS current
			DESCRIPTION
				"Description."
			::= { netflowIfEntry 17 }

		
		-- 1.3.6.1.4.1.3807.2.1403.6.1.18
		netflowIfIpv6OutBind OBJECT-TYPE
			SYNTAX Integer32
			MAX-ACCESS read-write
			STATUS current
			DESCRIPTION
				"Description."
			::= { netflowIfEntry 18 }

		
		-- 1.3.6.1.4.1.3807.2.1403.6.1.19
		netflowIfL2InBind OBJECT-TYPE
			SYNTAX Integer32
			MAX-ACCESS read-write
			STATUS current
			DESCRIPTION
				"Description."
			::= { netflowIfEntry 19 }

		
		-- 1.3.6.1.4.1.3807.2.1403.6.1.20
		netflowIfL2OutBind OBJECT-TYPE
			SYNTAX Integer32
			MAX-ACCESS read-write
			STATUS current
			DESCRIPTION
				"Description."
			::= { netflowIfEntry 20 }

		
		-- 1.3.6.1.4.1.3807.2.1403.6.1.21
		netflowIfCast OBJECT-TYPE
			SYNTAX Integer32
			MAX-ACCESS read-write
			STATUS current
			DESCRIPTION
				"Description."
			::= { netflowIfEntry 21 }

		
		-- 1.3.6.1.4.1.3807.2.1403.6.1.22
		netflowIfIpv4InSampledPkts OBJECT-TYPE
			SYNTAX Counter64
			MAX-ACCESS read-only
			STATUS current
			DESCRIPTION
				"Description."
			::= { netflowIfEntry 22 }

		
		-- 1.3.6.1.4.1.3807.2.1403.6.1.23
		netflowIfIpv4OutSampledPkts OBJECT-TYPE
			SYNTAX Counter64
			MAX-ACCESS read-only
			STATUS current
			DESCRIPTION
				"Description."
			::= { netflowIfEntry 23 }

		
		-- 1.3.6.1.4.1.3807.2.1403.6.1.24
		netflowIfIpv6InSampledPkts OBJECT-TYPE
			SYNTAX Counter64
			MAX-ACCESS read-only
			STATUS current
			DESCRIPTION
				"Description."
			::= { netflowIfEntry 24 }

		
		-- 1.3.6.1.4.1.3807.2.1403.6.1.25
		netflowIfIpv6OutSampledPkts OBJECT-TYPE
			SYNTAX Counter64
			MAX-ACCESS read-only
			STATUS current
			DESCRIPTION
				"Description."
			::= { netflowIfEntry 25 }

		
		-- 1.3.6.1.4.1.3807.2.1403.6.1.26
		netflowIfL2InSampledPkts OBJECT-TYPE
			SYNTAX Counter64
			MAX-ACCESS read-only
			STATUS current
			DESCRIPTION
				"Description."
			::= { netflowIfEntry 26 }

		
		-- 1.3.6.1.4.1.3807.2.1403.6.1.27
		netflowIfL2OutSampledPkts OBJECT-TYPE
			SYNTAX Counter64
			MAX-ACCESS read-only
			STATUS current
			DESCRIPTION
				"Description."
			::= { netflowIfEntry 27 }

		
		-- 1.3.6.1.4.1.3807.2.1403.6.1.28
		netflowIfIpv4InMatchedPkts OBJECT-TYPE
			SYNTAX Counter64
			MAX-ACCESS read-only
			STATUS current
			DESCRIPTION
				"Description."
			::= { netflowIfEntry 28 }

		
		-- 1.3.6.1.4.1.3807.2.1403.6.1.29
		netflowIfIpv4OutMatchedPkts OBJECT-TYPE
			SYNTAX Counter64
			MAX-ACCESS read-only
			STATUS current
			DESCRIPTION
				"Description."
			::= { netflowIfEntry 29 }

		
		-- 1.3.6.1.4.1.3807.2.1403.6.1.30
		netflowIfIpv6InMatchedPkts OBJECT-TYPE
			SYNTAX Counter64
			MAX-ACCESS read-only
			STATUS current
			DESCRIPTION
				"Description."
			::= { netflowIfEntry 30 }

		
		-- 1.3.6.1.4.1.3807.2.1403.6.1.31
		netflowIfIpv6OutMatchedPkts OBJECT-TYPE
			SYNTAX Counter64
			MAX-ACCESS read-only
			STATUS current
			DESCRIPTION
				"Description."
			::= { netflowIfEntry 31 }

		
		-- 1.3.6.1.4.1.3807.2.1403.6.1.32
		netflowIfL2InMatchedPkts OBJECT-TYPE
			SYNTAX Counter64
			MAX-ACCESS read-only
			STATUS current
			DESCRIPTION
				"Description."
			::= { netflowIfEntry 32 }

		
		-- 1.3.6.1.4.1.3807.2.1403.6.1.33
		netflowIfL2OutMatchedPkts OBJECT-TYPE
			SYNTAX Counter64
			MAX-ACCESS read-only
			STATUS current
			DESCRIPTION
				"Description."
			::= { netflowIfEntry 33 }

		
		-- 1.3.6.1.4.1.3807.2.1403.6.1.34
		netflowIfIpv4InTime OBJECT-TYPE
			SYNTAX Integer32
			MAX-ACCESS read-only
			STATUS current
			DESCRIPTION
				"Description."
			::= { netflowIfEntry 34 }

		
		-- 1.3.6.1.4.1.3807.2.1403.6.1.35
		netflowIfIpv4OutTime OBJECT-TYPE
			SYNTAX Integer32
			MAX-ACCESS read-only
			STATUS current
			DESCRIPTION
				"Description."
			::= { netflowIfEntry 35 }

		
		-- 1.3.6.1.4.1.3807.2.1403.6.1.36
		netflowIfIpv6InTime OBJECT-TYPE
			SYNTAX Integer32
			MAX-ACCESS read-only
			STATUS current
			DESCRIPTION
				"Description."
			::= { netflowIfEntry 36 }

		
		-- 1.3.6.1.4.1.3807.2.1403.6.1.37
		netflowIfIpv6OutTime OBJECT-TYPE
			SYNTAX Integer32
			MAX-ACCESS read-only
			STATUS current
			DESCRIPTION
				"Description."
			::= { netflowIfEntry 37 }

		
		-- 1.3.6.1.4.1.3807.2.1403.6.1.38
		netflowIfL2InTime OBJECT-TYPE
			SYNTAX Integer32
			MAX-ACCESS read-only
			STATUS current
			DESCRIPTION
				"Description."
			::= { netflowIfEntry 38 }

		
		-- 1.3.6.1.4.1.3807.2.1403.6.1.39
		netflowIfL2OutTime OBJECT-TYPE
			SYNTAX Integer32
			MAX-ACCESS read-only
			STATUS current
			DESCRIPTION
				"Description."
			::= { netflowIfEntry 39 }

		
		-- 1.3.6.1.4.1.3807.2.1403.6.1.40
		netflowIfMplsInSamplerId OBJECT-TYPE
			SYNTAX Integer32
			MAX-ACCESS read-write
			STATUS current
			DESCRIPTION
				"Description."
			::= { netflowIfEntry 40 }

		
		-- 1.3.6.1.4.1.3807.2.1403.6.1.41
		netflowIfMplsOutSamplerId OBJECT-TYPE
			SYNTAX Integer32
			MAX-ACCESS read-write
			STATUS current
			DESCRIPTION
				"Description."
			::= { netflowIfEntry 41 }

		
		-- 1.3.6.1.4.1.3807.2.1403.6.1.42
		netflowIfMplsInMonId OBJECT-TYPE
			SYNTAX Integer32
			MAX-ACCESS read-write
			STATUS current
			DESCRIPTION
				"Description."
			::= { netflowIfEntry 42 }

		
		-- 1.3.6.1.4.1.3807.2.1403.6.1.43
		netflowIfMplsOutMonId OBJECT-TYPE
			SYNTAX Integer32
			MAX-ACCESS read-write
			STATUS current
			DESCRIPTION
				"Description."
			::= { netflowIfEntry 43 }

		
		-- 1.3.6.1.4.1.3807.2.1403.6.1.44
		netflowIfMplsInBind OBJECT-TYPE
			SYNTAX Integer32
			MAX-ACCESS read-write
			STATUS current
			DESCRIPTION
				"Description."
			::= { netflowIfEntry 44 }

		
		-- 1.3.6.1.4.1.3807.2.1403.6.1.45
		netflowIfMplsOutBind OBJECT-TYPE
			SYNTAX Integer32
			MAX-ACCESS read-write
			STATUS current
			DESCRIPTION
				"Description."
			::= { netflowIfEntry 45 }

		
		-- 1.3.6.1.4.1.3807.2.1403.6.1.46
		netflowIfMplsInSampledPkts OBJECT-TYPE
			SYNTAX Counter64
			MAX-ACCESS read-only
			STATUS current
			DESCRIPTION
				"Description."
			::= { netflowIfEntry 46 }

		
		-- 1.3.6.1.4.1.3807.2.1403.6.1.47
		netflowIfMplsOutSampledPkts OBJECT-TYPE
			SYNTAX Counter64
			MAX-ACCESS read-only
			STATUS current
			DESCRIPTION
				"Description."
			::= { netflowIfEntry 47 }

		
		-- 1.3.6.1.4.1.3807.2.1403.6.1.48
		netflowIfMplsInMatchedPkts OBJECT-TYPE
			SYNTAX Counter64
			MAX-ACCESS read-only
			STATUS current
			DESCRIPTION
				"Description."
			::= { netflowIfEntry 48 }

		
		-- 1.3.6.1.4.1.3807.2.1403.6.1.49
		netflowIfMplsOutMatchedPkts OBJECT-TYPE
			SYNTAX Counter64
			MAX-ACCESS read-only
			STATUS current
			DESCRIPTION
				"Description."
			::= { netflowIfEntry 49 }

		
		-- 1.3.6.1.4.1.3807.2.1403.6.1.50
		netflowIfMplsInTime OBJECT-TYPE
			SYNTAX Integer32
			MAX-ACCESS read-only
			STATUS current
			DESCRIPTION
				"Description."
			::= { netflowIfEntry 50 }

		
		-- 1.3.6.1.4.1.3807.2.1403.6.1.51
		netflowIfMplsOutTime OBJECT-TYPE
			SYNTAX Integer32
			MAX-ACCESS read-only
			STATUS current
			DESCRIPTION
				"Description."
			::= { netflowIfEntry 51 }

		
		-- 1.3.6.1.4.1.3807.2.1403.7
		netflowTable OBJECT-TYPE
			SYNTAX SEQUENCE OF NetflowEntry
			MAX-ACCESS not-accessible
			STATUS current
			DESCRIPTION
				"Description."
			::= { netflow 7 }

		
		-- 1.3.6.1.4.1.3807.2.1403.7.1
		netflowEntry OBJECT-TYPE
			SYNTAX NetflowEntry
			MAX-ACCESS not-accessible
			STATUS current
			DESCRIPTION
				"Description."
			INDEX { netflowMonitorIndex, netflowIndex }
			::= { netflowTable 1 }

		
		NetflowEntry ::=
			SEQUENCE { 
				netflowMonitorIndex
					Integer32,
				netflowIndex
					Integer32,
				netflowStatus
					Integer32,
				netflowInPkts
					Counter64,
				netflowInBytes
					Counter64,
				netflownOutPkts
					Counter64,
				netflowOutBytes
					Counter64,
				netflowStartTime
					Integer32,
				netflowEndTime
					Integer32,
				netflowIpv4SrcAddr
					OCTET STRING,
				netflowIpv4DstAddr
					OCTET STRING,
				netflowIpv6SrcAddr
					OCTET STRING,
				netflowIpv6DstAddr
					OCTET STRING,
				netflowSrcPort
					Integer32,
				netflowDstPort
					Integer32,
				netflowL2Protocol
					Integer32,
				netflowTos
					Integer32,
				netflowDscp
					Integer32,
				netflowIpv4HeaderLen
					Integer32,
				netflowIpv4NextHop
					OCTET STRING,
				netflowIpv6NextHop
					OCTET STRING,
				netflowSrcAs
					Integer32,
				netflowDstAs
					Integer32,
				netflowTcpFlag
					Integer32,
				netflowIpv4L4Protocol
					Integer32,
				netflowIpv6L4Protocol
					Integer32,
				netflowIpv4SrcMask
					Integer32,
				netflowIpv4DstMask
					Integer32,
				netflowIpv6SrcMask
					Integer32,
				netflowIpv6DstMask
					Integer32,
				netflowInputVlan
					Integer32,
				netflowOutputVlan
					Integer32,
				netflowIpv4SrcPrefix
					Integer32,
				netflowIpv4DstPrefix
					Integer32,
				netflowIpv6SrcPrefix
					Integer32,
				netflowIpv6DstPrefix
					Integer32,
				netflowInputSrcMac
					OCTET STRING,
				netflowInputDstMac
					OCTET STRING,
				netflowOutputSrcMac
					OCTET STRING,
				netflowOutputDstMac
					OCTET STRING,
				netflowIpv4Id
					Integer32,
				netflowIpv6Flowlabel
					Integer32,
				netflowDirection
					Integer32,
				netflowflowInIfIndex
					Integer32,
				netflowflowOutIfIndex
					Integer32,
				netflowTTL
					Integer32,
				netflowIpv4IcmpType
					Integer32,
				netflowIpv4IcmpCode
					Integer32,
				netflowIpv6IcmpType
					Integer32,
				netflowIpv6IcmpCode
					Integer32,
				netflowIpv4FragFlag
					Integer32,
				netflownIpv4FragOffset
					Integer32,
				netflowIpv4Len
					Integer32,
				netflowIpv6Payloadlen
					Integer32,
				netflowTcpSeq
					Integer32,
				netflowTcpAck
					Integer32,
				netflowTcpHeaderLen
					Integer32,
				netflowTcpWindow
					Integer32,
				netflowTcpUrp
					Integer32,
				netflowUdpLen
					Integer32,
				netflowBits
					OCTET STRING,
				netflowTcpFlagUrg
					Integer32,
				netflowTcpFlagAck
					Integer32,
				netflowTcpFlagPsh
					Integer32,
				netflowTcpFlagRst
					Integer32,
				netflowFlagSyn
					Integer32,
				netflowFlagFin
					Integer32,
				netflowIpv6Nexthead
					Integer32,
				netflowMplsTopLabelType
					Integer32,
				netflowMplsTopLabelTtl
					Integer32,
				netflowMplsTopLabelExp
					Integer32,
				netflowMplsLabelStackLength
					Integer32,
				netflowMplsLabelStackDepth
					Integer32,
				netflowMplsTopLabelStackSection
					Integer32,
				netflowMplsLabelStackSection2
					Integer32,
				netflowMplsLabelStackSection3
					Integer32,
				netflowMplsPayloadLength
					Integer32
			 }

		-- 1.3.6.1.4.1.3807.2.1403.7.1.1
		netflowMonitorIndex OBJECT-TYPE
			SYNTAX Integer32
			MAX-ACCESS read-only
			STATUS current
			DESCRIPTION
				"Description."
			::= { netflowEntry 1 }

		
		-- 1.3.6.1.4.1.3807.2.1403.7.1.2
		netflowIndex OBJECT-TYPE
			SYNTAX Integer32
			MAX-ACCESS read-only
			STATUS current
			DESCRIPTION
				"Description."
			::= { netflowEntry 2 }

		
		-- 1.3.6.1.4.1.3807.2.1403.7.1.3
		netflowStatus OBJECT-TYPE
			SYNTAX Integer32
			MAX-ACCESS read-write
			STATUS current
			DESCRIPTION
				"Description."
			::= { netflowEntry 3 }

		
		-- 1.3.6.1.4.1.3807.2.1403.7.1.4
		netflowInPkts OBJECT-TYPE
			SYNTAX Counter64
			MAX-ACCESS read-only
			STATUS current
			DESCRIPTION
				"Description."
			::= { netflowEntry 4 }

		
		-- 1.3.6.1.4.1.3807.2.1403.7.1.5
		netflowInBytes OBJECT-TYPE
			SYNTAX Counter64
			MAX-ACCESS read-only
			STATUS current
			DESCRIPTION
				"Description."
			::= { netflowEntry 5 }

		
		-- 1.3.6.1.4.1.3807.2.1403.7.1.6
		netflownOutPkts OBJECT-TYPE
			SYNTAX Counter64
			MAX-ACCESS read-only
			STATUS current
			DESCRIPTION
				"Description."
			::= { netflowEntry 6 }

		
		-- 1.3.6.1.4.1.3807.2.1403.7.1.7
		netflowOutBytes OBJECT-TYPE
			SYNTAX Counter64
			MAX-ACCESS read-only
			STATUS current
			DESCRIPTION
				"Description."
			::= { netflowEntry 7 }

		
		-- 1.3.6.1.4.1.3807.2.1403.7.1.8
		netflowStartTime OBJECT-TYPE
			SYNTAX Integer32
			MAX-ACCESS read-only
			STATUS current
			DESCRIPTION
				"Description."
			::= { netflowEntry 8 }

		
		-- 1.3.6.1.4.1.3807.2.1403.7.1.9
		netflowEndTime OBJECT-TYPE
			SYNTAX Integer32
			MAX-ACCESS read-only
			STATUS current
			DESCRIPTION
				"Description."
			::= { netflowEntry 9 }

		
		-- 1.3.6.1.4.1.3807.2.1403.7.1.10
		netflowIpv4SrcAddr OBJECT-TYPE
			SYNTAX OCTET STRING
			MAX-ACCESS read-only
			STATUS current
			DESCRIPTION
				"Description."
			::= { netflowEntry 10 }

		
		-- 1.3.6.1.4.1.3807.2.1403.7.1.11
		netflowIpv4DstAddr OBJECT-TYPE
			SYNTAX OCTET STRING
			MAX-ACCESS read-only
			STATUS current
			DESCRIPTION
				"Description."
			::= { netflowEntry 11 }

		
		-- 1.3.6.1.4.1.3807.2.1403.7.1.12
		netflowIpv6SrcAddr OBJECT-TYPE
			SYNTAX OCTET STRING
			MAX-ACCESS read-only
			STATUS current
			DESCRIPTION
				"Description."
			::= { netflowEntry 12 }

		
		-- 1.3.6.1.4.1.3807.2.1403.7.1.13
		netflowIpv6DstAddr OBJECT-TYPE
			SYNTAX OCTET STRING
			MAX-ACCESS read-only
			STATUS current
			DESCRIPTION
				"Description."
			::= { netflowEntry 13 }

		
		-- 1.3.6.1.4.1.3807.2.1403.7.1.14
		netflowSrcPort OBJECT-TYPE
			SYNTAX Integer32
			MAX-ACCESS read-only
			STATUS current
			DESCRIPTION
				"Description."
			::= { netflowEntry 14 }

		
		-- 1.3.6.1.4.1.3807.2.1403.7.1.15
		netflowDstPort OBJECT-TYPE
			SYNTAX Integer32
			MAX-ACCESS read-only
			STATUS current
			DESCRIPTION
				"Description."
			::= { netflowEntry 15 }

		
		-- 1.3.6.1.4.1.3807.2.1403.7.1.16
		netflowL2Protocol OBJECT-TYPE
			SYNTAX Integer32
			MAX-ACCESS read-only
			STATUS current
			DESCRIPTION
				"Description."
			::= { netflowEntry 16 }

		
		-- 1.3.6.1.4.1.3807.2.1403.7.1.17
		netflowTos OBJECT-TYPE
			SYNTAX Integer32
			MAX-ACCESS read-only
			STATUS current
			DESCRIPTION
				"Description."
			::= { netflowEntry 17 }

		
		-- 1.3.6.1.4.1.3807.2.1403.7.1.18
		netflowDscp OBJECT-TYPE
			SYNTAX Integer32
			MAX-ACCESS read-only
			STATUS current
			DESCRIPTION
				"Description."
			::= { netflowEntry 18 }

		
		-- 1.3.6.1.4.1.3807.2.1403.7.1.19
		netflowIpv4HeaderLen OBJECT-TYPE
			SYNTAX Integer32
			MAX-ACCESS read-only
			STATUS current
			DESCRIPTION
				"Description."
			::= { netflowEntry 19 }

		
		-- 1.3.6.1.4.1.3807.2.1403.7.1.20
		netflowIpv4NextHop OBJECT-TYPE
			SYNTAX OCTET STRING
			MAX-ACCESS read-only
			STATUS current
			DESCRIPTION
				"Description."
			::= { netflowEntry 20 }

		
		-- 1.3.6.1.4.1.3807.2.1403.7.1.21
		netflowIpv6NextHop OBJECT-TYPE
			SYNTAX OCTET STRING
			MAX-ACCESS read-only
			STATUS current
			DESCRIPTION
				"Description."
			::= { netflowEntry 21 }

		
		-- 1.3.6.1.4.1.3807.2.1403.7.1.22
		netflowSrcAs OBJECT-TYPE
			SYNTAX Integer32
			MAX-ACCESS read-only
			STATUS current
			DESCRIPTION
				"Description."
			::= { netflowEntry 22 }

		
		-- 1.3.6.1.4.1.3807.2.1403.7.1.23
		netflowDstAs OBJECT-TYPE
			SYNTAX Integer32
			MAX-ACCESS read-only
			STATUS current
			DESCRIPTION
				"Description."
			::= { netflowEntry 23 }

		
		-- 1.3.6.1.4.1.3807.2.1403.7.1.24
		netflowTcpFlag OBJECT-TYPE
			SYNTAX Integer32
			MAX-ACCESS read-only
			STATUS current
			DESCRIPTION
				"Description."
			::= { netflowEntry 24 }

		
		-- 1.3.6.1.4.1.3807.2.1403.7.1.25
		netflowIpv4L4Protocol OBJECT-TYPE
			SYNTAX Integer32
			MAX-ACCESS read-only
			STATUS current
			DESCRIPTION
				"Description."
			::= { netflowEntry 25 }

		
		-- 1.3.6.1.4.1.3807.2.1403.7.1.26
		netflowIpv6L4Protocol OBJECT-TYPE
			SYNTAX Integer32
			MAX-ACCESS read-only
			STATUS current
			DESCRIPTION
				"Description."
			::= { netflowEntry 26 }

		
		-- 1.3.6.1.4.1.3807.2.1403.7.1.27
		netflowIpv4SrcMask OBJECT-TYPE
			SYNTAX Integer32
			MAX-ACCESS read-only
			STATUS current
			DESCRIPTION
				"Description."
			::= { netflowEntry 27 }

		
		-- 1.3.6.1.4.1.3807.2.1403.7.1.28
		netflowIpv4DstMask OBJECT-TYPE
			SYNTAX Integer32
			MAX-ACCESS read-only
			STATUS current
			DESCRIPTION
				"Description."
			::= { netflowEntry 28 }

		
		-- 1.3.6.1.4.1.3807.2.1403.7.1.29
		netflowIpv6SrcMask OBJECT-TYPE
			SYNTAX Integer32
			MAX-ACCESS read-only
			STATUS current
			DESCRIPTION
				"Description."
			::= { netflowEntry 29 }

		
		-- 1.3.6.1.4.1.3807.2.1403.7.1.30
		netflowIpv6DstMask OBJECT-TYPE
			SYNTAX Integer32
			MAX-ACCESS read-only
			STATUS current
			DESCRIPTION
				"Description."
			::= { netflowEntry 30 }

		
		-- 1.3.6.1.4.1.3807.2.1403.7.1.31
		netflowInputVlan OBJECT-TYPE
			SYNTAX Integer32
			MAX-ACCESS read-only
			STATUS current
			DESCRIPTION
				"Description."
			::= { netflowEntry 31 }

		
		-- 1.3.6.1.4.1.3807.2.1403.7.1.32
		netflowOutputVlan OBJECT-TYPE
			SYNTAX Integer32
			MAX-ACCESS read-only
			STATUS current
			DESCRIPTION
				"Description."
			::= { netflowEntry 32 }

		
		-- 1.3.6.1.4.1.3807.2.1403.7.1.33
		netflowIpv4SrcPrefix OBJECT-TYPE
			SYNTAX Integer32
			MAX-ACCESS read-only
			STATUS current
			DESCRIPTION
				"Description."
			::= { netflowEntry 33 }

		
		-- 1.3.6.1.4.1.3807.2.1403.7.1.34
		netflowIpv4DstPrefix OBJECT-TYPE
			SYNTAX Integer32
			MAX-ACCESS read-only
			STATUS current
			DESCRIPTION
				"Description."
			::= { netflowEntry 34 }

		
		-- 1.3.6.1.4.1.3807.2.1403.7.1.35
		netflowIpv6SrcPrefix OBJECT-TYPE
			SYNTAX Integer32
			MAX-ACCESS read-only
			STATUS current
			DESCRIPTION
				"Description."
			::= { netflowEntry 35 }

		
		-- 1.3.6.1.4.1.3807.2.1403.7.1.36
		netflowIpv6DstPrefix OBJECT-TYPE
			SYNTAX Integer32
			MAX-ACCESS read-only
			STATUS current
			DESCRIPTION
				"Description."
			::= { netflowEntry 36 }

		
		-- 1.3.6.1.4.1.3807.2.1403.7.1.37
		netflowInputSrcMac OBJECT-TYPE
			SYNTAX OCTET STRING
			MAX-ACCESS read-only
			STATUS current
			DESCRIPTION
				"Description."
			::= { netflowEntry 37 }

		
		-- 1.3.6.1.4.1.3807.2.1403.7.1.38
		netflowInputDstMac OBJECT-TYPE
			SYNTAX OCTET STRING
			MAX-ACCESS read-only
			STATUS current
			DESCRIPTION
				"Description."
			::= { netflowEntry 38 }

		
		-- 1.3.6.1.4.1.3807.2.1403.7.1.39
		netflowOutputSrcMac OBJECT-TYPE
			SYNTAX OCTET STRING
			MAX-ACCESS read-only
			STATUS current
			DESCRIPTION
				"Description."
			::= { netflowEntry 39 }

		
		-- 1.3.6.1.4.1.3807.2.1403.7.1.40
		netflowOutputDstMac OBJECT-TYPE
			SYNTAX OCTET STRING
			MAX-ACCESS read-only
			STATUS current
			DESCRIPTION
				"Description."
			::= { netflowEntry 40 }

		
		-- 1.3.6.1.4.1.3807.2.1403.7.1.41
		netflowIpv4Id OBJECT-TYPE
			SYNTAX Integer32
			MAX-ACCESS read-only
			STATUS current
			DESCRIPTION
				"Description."
			::= { netflowEntry 41 }

		
		-- 1.3.6.1.4.1.3807.2.1403.7.1.42
		netflowIpv6Flowlabel OBJECT-TYPE
			SYNTAX Integer32
			MAX-ACCESS read-only
			STATUS current
			DESCRIPTION
				"Description."
			::= { netflowEntry 42 }

		
		-- 1.3.6.1.4.1.3807.2.1403.7.1.43
		netflowDirection OBJECT-TYPE
			SYNTAX Integer32
			MAX-ACCESS read-only
			STATUS current
			DESCRIPTION
				"Description."
			::= { netflowEntry 43 }

		
		-- 1.3.6.1.4.1.3807.2.1403.7.1.44
		netflowflowInIfIndex OBJECT-TYPE
			SYNTAX Integer32
			MAX-ACCESS read-only
			STATUS current
			DESCRIPTION
				"Description."
			::= { netflowEntry 44 }

		
		-- 1.3.6.1.4.1.3807.2.1403.7.1.45
		netflowflowOutIfIndex OBJECT-TYPE
			SYNTAX Integer32
			MAX-ACCESS read-only
			STATUS current
			DESCRIPTION
				"Description."
			::= { netflowEntry 45 }

		
		-- 1.3.6.1.4.1.3807.2.1403.7.1.46
		netflowTTL OBJECT-TYPE
			SYNTAX Integer32
			MAX-ACCESS read-only
			STATUS current
			DESCRIPTION
				"Description."
			::= { netflowEntry 46 }

		
		-- 1.3.6.1.4.1.3807.2.1403.7.1.47
		netflowIpv4IcmpType OBJECT-TYPE
			SYNTAX Integer32
			MAX-ACCESS read-only
			STATUS current
			DESCRIPTION
				"Description."
			::= { netflowEntry 47 }

		
		-- 1.3.6.1.4.1.3807.2.1403.7.1.48
		netflowIpv4IcmpCode OBJECT-TYPE
			SYNTAX Integer32
			MAX-ACCESS read-only
			STATUS current
			DESCRIPTION
				"Description."
			::= { netflowEntry 48 }

		
		-- 1.3.6.1.4.1.3807.2.1403.7.1.49
		netflowIpv6IcmpType OBJECT-TYPE
			SYNTAX Integer32
			MAX-ACCESS read-only
			STATUS current
			DESCRIPTION
				"Description."
			::= { netflowEntry 49 }

		
		-- 1.3.6.1.4.1.3807.2.1403.7.1.50
		netflowIpv6IcmpCode OBJECT-TYPE
			SYNTAX Integer32
			MAX-ACCESS read-only
			STATUS current
			DESCRIPTION
				"Description."
			::= { netflowEntry 50 }

		
		-- 1.3.6.1.4.1.3807.2.1403.7.1.51
		netflowIpv4FragFlag OBJECT-TYPE
			SYNTAX Integer32
			MAX-ACCESS read-only
			STATUS current
			DESCRIPTION
				"Description."
			::= { netflowEntry 51 }

		
		-- 1.3.6.1.4.1.3807.2.1403.7.1.52
		netflownIpv4FragOffset OBJECT-TYPE
			SYNTAX Integer32
			MAX-ACCESS read-only
			STATUS current
			DESCRIPTION
				"Description."
			::= { netflowEntry 52 }

		
		-- 1.3.6.1.4.1.3807.2.1403.7.1.53
		netflowIpv4Len OBJECT-TYPE
			SYNTAX Integer32
			MAX-ACCESS read-only
			STATUS current
			DESCRIPTION
				"Description."
			::= { netflowEntry 53 }

		
		-- 1.3.6.1.4.1.3807.2.1403.7.1.54
		netflowIpv6Payloadlen OBJECT-TYPE
			SYNTAX Integer32
			MAX-ACCESS read-only
			STATUS current
			DESCRIPTION
				"Description."
			::= { netflowEntry 54 }

		
		-- 1.3.6.1.4.1.3807.2.1403.7.1.55
		netflowTcpSeq OBJECT-TYPE
			SYNTAX Integer32
			MAX-ACCESS read-only
			STATUS current
			DESCRIPTION
				"Description."
			::= { netflowEntry 55 }

		
		-- 1.3.6.1.4.1.3807.2.1403.7.1.56
		netflowTcpAck OBJECT-TYPE
			SYNTAX Integer32
			MAX-ACCESS read-only
			STATUS current
			DESCRIPTION
				"Description."
			::= { netflowEntry 56 }

		
		-- 1.3.6.1.4.1.3807.2.1403.7.1.57
		netflowTcpHeaderLen OBJECT-TYPE
			SYNTAX Integer32
			MAX-ACCESS read-only
			STATUS current
			DESCRIPTION
				"Description."
			::= { netflowEntry 57 }

		
		-- 1.3.6.1.4.1.3807.2.1403.7.1.58
		netflowTcpWindow OBJECT-TYPE
			SYNTAX Integer32
			MAX-ACCESS read-only
			STATUS current
			DESCRIPTION
				"Description."
			::= { netflowEntry 58 }

		
		-- 1.3.6.1.4.1.3807.2.1403.7.1.59
		netflowTcpUrp OBJECT-TYPE
			SYNTAX Integer32
			MAX-ACCESS read-only
			STATUS current
			DESCRIPTION
				"Description."
			::= { netflowEntry 59 }

		
		-- 1.3.6.1.4.1.3807.2.1403.7.1.60
		netflowUdpLen OBJECT-TYPE
			SYNTAX Integer32
			MAX-ACCESS read-only
			STATUS current
			DESCRIPTION
				"Description."
			::= { netflowEntry 60 }

		
		-- 1.3.6.1.4.1.3807.2.1403.7.1.61
		netflowBits OBJECT-TYPE
			SYNTAX OCTET STRING
			MAX-ACCESS read-only
			STATUS current
			DESCRIPTION
				"Description."
			::= { netflowEntry 61 }

		
		-- 1.3.6.1.4.1.3807.2.1403.7.1.62
		netflowTcpFlagUrg OBJECT-TYPE
			SYNTAX Integer32
			MAX-ACCESS read-only
			STATUS current
			DESCRIPTION
				"Description."
			::= { netflowEntry 62 }

		
		-- 1.3.6.1.4.1.3807.2.1403.7.1.63
		netflowTcpFlagAck OBJECT-TYPE
			SYNTAX Integer32
			MAX-ACCESS read-only
			STATUS current
			DESCRIPTION
				"Description."
			::= { netflowEntry 63 }

		
		-- 1.3.6.1.4.1.3807.2.1403.7.1.64
		netflowTcpFlagPsh OBJECT-TYPE
			SYNTAX Integer32
			MAX-ACCESS read-only
			STATUS current
			DESCRIPTION
				"Description."
			::= { netflowEntry 64 }

		
		-- 1.3.6.1.4.1.3807.2.1403.7.1.65
		netflowTcpFlagRst OBJECT-TYPE
			SYNTAX Integer32
			MAX-ACCESS read-only
			STATUS current
			DESCRIPTION
				"Description."
			::= { netflowEntry 65 }

		
		-- 1.3.6.1.4.1.3807.2.1403.7.1.66
		netflowFlagSyn OBJECT-TYPE
			SYNTAX Integer32
			MAX-ACCESS read-only
			STATUS current
			DESCRIPTION
				"Description."
			::= { netflowEntry 66 }

		
		-- 1.3.6.1.4.1.3807.2.1403.7.1.67
		netflowFlagFin OBJECT-TYPE
			SYNTAX Integer32
			MAX-ACCESS read-only
			STATUS current
			DESCRIPTION
				"Description."
			::= { netflowEntry 67 }

		
		-- 1.3.6.1.4.1.3807.2.1403.7.1.68
		netflowIpv6Nexthead OBJECT-TYPE
			SYNTAX Integer32
			MAX-ACCESS read-only
			STATUS current
			DESCRIPTION
				"Description."
			::= { netflowEntry 68 }

		
		-- 1.3.6.1.4.1.3807.2.1403.7.1.69
		netflowMplsTopLabelType OBJECT-TYPE
			SYNTAX Integer32
			MAX-ACCESS read-only
			STATUS current
			DESCRIPTION
				"Description."
			::= { netflowEntry 69 }

		
		-- 1.3.6.1.4.1.3807.2.1403.7.1.70
		netflowMplsTopLabelTtl OBJECT-TYPE
			SYNTAX Integer32
			MAX-ACCESS read-only
			STATUS current
			DESCRIPTION
				"Description."
			::= { netflowEntry 70 }

		
		-- 1.3.6.1.4.1.3807.2.1403.7.1.71
		netflowMplsTopLabelExp OBJECT-TYPE
			SYNTAX Integer32
			MAX-ACCESS read-only
			STATUS current
			DESCRIPTION
				"Description."
			::= { netflowEntry 71 }

		
		-- 1.3.6.1.4.1.3807.2.1403.7.1.72
		netflowMplsLabelStackLength OBJECT-TYPE
			SYNTAX Integer32
			MAX-ACCESS read-only
			STATUS current
			DESCRIPTION
				"Description."
			::= { netflowEntry 72 }

		
		-- 1.3.6.1.4.1.3807.2.1403.7.1.73
		netflowMplsLabelStackDepth OBJECT-TYPE
			SYNTAX Integer32
			MAX-ACCESS read-only
			STATUS current
			DESCRIPTION
				"Description."
			::= { netflowEntry 73 }

		
		-- 1.3.6.1.4.1.3807.2.1403.7.1.74
		netflowMplsTopLabelStackSection OBJECT-TYPE
			SYNTAX Integer32
			MAX-ACCESS read-only
			STATUS current
			DESCRIPTION
				"Description."
			::= { netflowEntry 74 }

		
		-- 1.3.6.1.4.1.3807.2.1403.7.1.75
		netflowMplsLabelStackSection2 OBJECT-TYPE
			SYNTAX Integer32
			MAX-ACCESS read-only
			STATUS current
			DESCRIPTION
				"Description."
			::= { netflowEntry 75 }

		
		-- 1.3.6.1.4.1.3807.2.1403.7.1.76
		netflowMplsLabelStackSection3 OBJECT-TYPE
			SYNTAX Integer32
			MAX-ACCESS read-only
			STATUS current
			DESCRIPTION
				"Description."
			::= { netflowEntry 76 }

		
		-- 1.3.6.1.4.1.3807.2.1403.7.1.77
		netflowMplsPayloadLength OBJECT-TYPE
			SYNTAX Integer32
			MAX-ACCESS read-only
			STATUS current
			DESCRIPTION
				"Description."
			::= { netflowEntry 77 }

		
	
	END

--
-- netflow.mib
--
