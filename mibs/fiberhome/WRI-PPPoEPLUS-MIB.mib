--
-- WRI-PPPoEPLUS-MIB.mib
-- MIB generated by MG-SOFT Visual MIB Builder Version 6.0  Build 88
-- Friday, April 11, 2014 at 13:33:25
--

	WRI-PPPoEPLUS-MIB DEFINITIONS ::= BEGIN
 
		IMPORTS
			IpAddress, Integer32, Unsigned32, OBJECT-TYPE			
				FROM SNMPv2-SMI			
			MacAddress			
				FROM SNMPv2-TC			
			wriProducts, wriProtocol			
				FROM WRI-SMI;
	
	
	
--
-- Node definitions
--
	
		-- 1.3.6.1.4.1.3807.2.1615
		pppoePlus OBJECT IDENTIFIER ::= { wriProtocol 1615 }

		
		-- 1.3.6.1.4.1.3807.2.1615.1
		pppoePlusGeneral OBJECT IDENTIFIER ::= { pppoePlus 1 }

		
		-- 1.3.6.1.4.1.3807.2.1615.1.1
		pppoePlusGenAction OBJECT-TYPE
			SYNTAX INTEGER
				{
				keep(1),
				drop(2),
				replace(3)
				}
			MAX-ACCESS read-write
			STATUS current
			DESCRIPTION
				"The general action of pppoeplus."
			::= { pppoePlusGeneral 1 }

		
		-- 1.3.6.1.4.1.3807.2.1615.1.2
		pppoePlusGenVenderId OBJECT-TYPE
			SYNTAX Integer32
			MAX-ACCESS read-write
			STATUS current
			DESCRIPTION
				"The general vender id of pppoeplus."
			::= { pppoePlusGeneral 2 }

		
		-- 1.3.6.1.4.1.3807.2.1615.1.3
		pppoePlusGenEnable OBJECT-TYPE
			SYNTAX INTEGER
				{
				enable(1),
				disable(2)
				}
			MAX-ACCESS read-write
			STATUS current
			DESCRIPTION
				"The switch of enable or disable pppoeplus."
			::= { pppoePlusGeneral 3 }

		
		-- 1.3.6.1.4.1.3807.2.1615.1.4
		pppoePlusGenRemoteidType OBJECT-TYPE
			SYNTAX INTEGER
				{
				switchCommon(1),
				switchCustom(2),
				ponCommon(3),
				ponCustom(4),
				ponCtc(5),
				ponCnc(6)
				}
			MAX-ACCESS read-write
			STATUS current
			DESCRIPTION
				" "
			::= { pppoePlusGeneral 4 }

		
		-- 1.3.6.1.4.1.3807.2.1615.1.5
		pppoePlusGenRemoteidFormat OBJECT-TYPE
			SYNTAX OCTET STRING
			MAX-ACCESS read-write
			STATUS current
			DESCRIPTION
				" "
			::= { pppoePlusGeneral 5 }

		
		-- 1.3.6.1.4.1.3807.2.1615.1.6
		pppoePlusGenCircuitidType OBJECT-TYPE
			SYNTAX INTEGER
				{
				switchCommon(1),
				switchCustom(2),
				ponCommon(3),
				ponCustom(4),
				ponCtc(5),
				ponCnc(6)
				}
			MAX-ACCESS read-write
			STATUS current
			DESCRIPTION
				" "
			::= { pppoePlusGeneral 6 }

		
		-- 1.3.6.1.4.1.3807.2.1615.1.7
		pppoePlusGenCircuitidFormat OBJECT-TYPE
			SYNTAX OCTET STRING
			MAX-ACCESS read-write
			STATUS current
			DESCRIPTION
				" "
			::= { pppoePlusGeneral 7 }

		
		-- 1.3.6.1.4.1.3807.2.1615.2
		pppoePlusIfTable OBJECT-TYPE
			SYNTAX SEQUENCE OF PppoePlusIfEntry
			MAX-ACCESS not-accessible
			STATUS current
			DESCRIPTION
				"The pppoeplus interface table."
			::= { pppoePlus 2 }

		
		-- 1.3.6.1.4.1.3807.2.1615.2.1
		pppoePlusIfEntry OBJECT-TYPE
			SYNTAX PppoePlusIfEntry
			MAX-ACCESS not-accessible
			STATUS current
			DESCRIPTION
				"The pppoeplus interface table."
			INDEX { pppoePlusIfIndex }
			::= { pppoePlusIfTable 1 }

		
		PppoePlusIfEntry ::=
			SEQUENCE { 
				pppoePlusIfIndex
					Integer32,
				pppoePlusIfTrust
					INTEGER,
				pppoePlusIfAction
					INTEGER,
				pppoePlusIfEnable
					INTEGER,
				pppoePlusIfUplink
					INTEGER,
				pppoePlusIfCircuitidType
					INTEGER,
				pppoePlusIfCircuitidFormat
					OCTET STRING,
				pppoePlusIfRemoteidType
					INTEGER,
				pppoePlusIfRemoteidFormat
					OCTET STRING
			 }

		-- 1.3.6.1.4.1.3807.2.1615.2.1.1
		pppoePlusIfIndex OBJECT-TYPE
			SYNTAX Integer32 (0..1024)
			MAX-ACCESS read-only
			STATUS current
			DESCRIPTION
				"Pppoe interface index."
			::= { pppoePlusIfEntry 1 }

		
		-- 1.3.6.1.4.1.3807.2.1615.2.1.2
		pppoePlusIfTrust OBJECT-TYPE
			SYNTAX INTEGER
				{
				trust(1),
				untrust(2)
				}
			MAX-ACCESS read-write
			STATUS current
			DESCRIPTION
				"The trust status of interface."
			::= { pppoePlusIfEntry 2 }

		
		-- 1.3.6.1.4.1.3807.2.1615.2.1.3
		pppoePlusIfAction OBJECT-TYPE
			SYNTAX INTEGER
				{
				none(0),
				keep(1),
				drop(2),
				replace(3)
				}
			MAX-ACCESS read-write
			STATUS current
			DESCRIPTION
				"The action of interface.."
			::= { pppoePlusIfEntry 3 }

		
		-- 1.3.6.1.4.1.3807.2.1615.2.1.4
		pppoePlusIfEnable OBJECT-TYPE
			SYNTAX INTEGER
				{
				enable(1),
				disable(2)
				}
			MAX-ACCESS read-write
			STATUS current
			DESCRIPTION
				"The status of interface.."
			::= { pppoePlusIfEntry 4 }

		
		-- 1.3.6.1.4.1.3807.2.1615.2.1.5
		pppoePlusIfUplink OBJECT-TYPE
			SYNTAX INTEGER
				{
				uplink(1),
				downlink(2)
				}
			MAX-ACCESS read-write
			STATUS current
			DESCRIPTION
				" "
			::= { pppoePlusIfEntry 5 }

		
		-- 1.3.6.1.4.1.3807.2.1615.2.1.6
		pppoePlusIfCircuitidType OBJECT-TYPE
			SYNTAX INTEGER
				{
				none(0),
				switchCommon(1),
				switchCustom(2),
				ponCommon(3),
				ponCustom(4),
				ponCtc(5),
				ponCnc(6)
				}
			MAX-ACCESS read-write
			STATUS current
			DESCRIPTION
				" "
			::= { pppoePlusIfEntry 6 }

		
		-- 1.3.6.1.4.1.3807.2.1615.2.1.7
		pppoePlusIfCircuitidFormat OBJECT-TYPE
			SYNTAX OCTET STRING
			MAX-ACCESS read-write
			STATUS current
			DESCRIPTION
				" "
			::= { pppoePlusIfEntry 7 }

		
		-- 1.3.6.1.4.1.3807.2.1615.2.1.8
		pppoePlusIfRemoteidType OBJECT-TYPE
			SYNTAX INTEGER
				{
				none(0),
				switchCommon(1),
				switchCustom(2),
				ponCommon(3),
				ponCustom(4),
				ponCtc(5),
				ponCnc(6)
				}
			MAX-ACCESS read-write
			STATUS current
			DESCRIPTION
				" "
			::= { pppoePlusIfEntry 8 }

		
		-- 1.3.6.1.4.1.3807.2.1615.2.1.9
		pppoePlusIfRemoteidFormat OBJECT-TYPE
			SYNTAX OCTET STRING
			MAX-ACCESS read-write
			STATUS current
			DESCRIPTION
				" "
			::= { pppoePlusIfEntry 9 }

		
		-- 1.3.6.1.4.1.3807.2.1615.3
		pppoePlusAddressTable OBJECT-TYPE
			SYNTAX SEQUENCE OF PppoePlusAddressEntry
			MAX-ACCESS not-accessible
			STATUS current
			DESCRIPTION
				"Description."
			::= { pppoePlus 3 }

		
		-- 1.3.6.1.4.1.3807.2.1615.3.1
		pppoePlusAddressEntry OBJECT-TYPE
			SYNTAX PppoePlusAddressEntry
			MAX-ACCESS not-accessible
			STATUS current
			DESCRIPTION
				"Description."
			INDEX { pppoePlusAddressMacAddress }
			::= { pppoePlusAddressTable 1 }

		
		PppoePlusAddressEntry ::=
			SEQUENCE { 
				pppoePlusAddressMacAddress
					MacAddress,
				pppoePlusAddressIPAddress
					IpAddress,
				pppoePlusAddressIfIndex
					Unsigned32,
				pppoePlusAddressVlan
					Integer32,
				pppoePlusAddressState
					INTEGER
			 }

		-- 1.3.6.1.4.1.3807.2.1615.3.1.1
		pppoePlusAddressMacAddress OBJECT-TYPE
			SYNTAX MacAddress
			MAX-ACCESS read-only
			STATUS current
			DESCRIPTION
				"Description."
			::= { pppoePlusAddressEntry 1 }

		
		-- 1.3.6.1.4.1.3807.2.1615.3.1.2
		pppoePlusAddressIPAddress OBJECT-TYPE
			SYNTAX IpAddress
			MAX-ACCESS read-only
			STATUS current
			DESCRIPTION
				"Description."
			::= { pppoePlusAddressEntry 2 }

		
		-- 1.3.6.1.4.1.3807.2.1615.3.1.3
		pppoePlusAddressIfIndex OBJECT-TYPE
			SYNTAX Unsigned32
			MAX-ACCESS read-only
			STATUS current
			DESCRIPTION
				"Description."
			::= { pppoePlusAddressEntry 3 }

		
		-- 1.3.6.1.4.1.3807.2.1615.3.1.4
		pppoePlusAddressVlan OBJECT-TYPE
			SYNTAX Integer32
			MAX-ACCESS read-only
			STATUS current
			DESCRIPTION
				"Description."
			::= { pppoePlusAddressEntry 4 }

		
		-- 1.3.6.1.4.1.3807.2.1615.3.1.5
		pppoePlusAddressState OBJECT-TYPE
			SYNTAX INTEGER
				{
				invalid(0),
				valid(1)
				}
			MAX-ACCESS read-only
			STATUS current
			DESCRIPTION
				"Description."
			::= { pppoePlusAddressEntry 5 }

		
	
	END

--
-- WRI-PPPoEPLUS-MIB.mib
--
