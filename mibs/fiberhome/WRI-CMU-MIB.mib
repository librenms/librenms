--
-- cmu.mib
-- MIB generated by MG-SOFT Visual MIB Builder Version 6.0  Build 88
-- Monday, December 13, 2010 at 15:25:54
--

	WRI-CMU-MIB DEFINITIONS ::= BEGIN
 
		IMPORTS
			mib-2, Integer32, Unsigned32, OBJECT-TYPE, MODULE-IDENTITY,Counter64,NOTIFICATION-TYPE	
				FROM SNMPv2-SMI			
			TEXTUAL-CONVENTION			
				FROM SNMPv2-TC			
			wriProtocol,wriMgmt			
				FROM WRI-SMI;
	
	
--  23 September 2009 12:00:00 EST
		cmu MODULE-IDENTITY 
			LAST-UPDATED "201103131500Z"		-- March 13, 2011 at 15:00 GMT
			ORGANIZATION 
				"FiberHome Networks Systems, Inc."
			CONTACT-INFO 
				"http://www.fhn.com.cn"
			DESCRIPTION 
				"Cmu info  ."
			::= { wriMgmt 304 }

--
-- Textual conventions
--
	
--  Textual Conventions
		EntryStatus ::= TEXTUAL-CONVENTION
			STATUS current
			DESCRIPTION 
				"entry status."
			SYNTAX INTEGER
				{
				valid(1),
				createRequest(2),
				underCreation(3),
				invalid(4)
				}

	
--
-- Node definitions
--
		cmuGeneral OBJECT IDENTIFIER ::= { cmu 1 }

		fanGenLevel OBJECT-TYPE
			SYNTAX Integer32 (0..255)
			MAX-ACCESS read-write
			STATUS current
			DESCRIPTION
				"The level of fan-speed."			
			::= { cmuGeneral 1 }
			
		fanMonitorEnable OBJECT-TYPE
				SYNTAX  INTEGER{
					enable(1),
					disable(2)
				}
				MAX-ACCESS  read-write
				STATUS  current
				DESCRIPTION
						"Enable fan monitor or not."
				::= { cmuGeneral 2 }              
				
		cmuCardTrapEnable OBJECT-TYPE
			SYNTAX  INTEGER{
				enable(1),
				disable(2)
			}
			MAX-ACCESS  read-write
			STATUS  current
			DESCRIPTION
					"Trap enable or not for cmu card."
			::= { cmuGeneral 3 }					

		cmuPowerTrapEnable OBJECT-TYPE
			SYNTAX  INTEGER{
				enable(1),
				disable(2)
			}
			MAX-ACCESS  read-write
			STATUS  current
			DESCRIPTION
					"Trap enable or not for power."
			::= { cmuGeneral 4 }					

		cmuVoltageTrapEnable OBJECT-TYPE
			SYNTAX  INTEGER{
				enable(1),
				disable(2)
			}
			MAX-ACCESS  read-write
			STATUS  current
			DESCRIPTION
					"Trap enable or not for voltage."
			::= { cmuGeneral 5 }					
			                              
	--fan table

		fanInfoTable OBJECT-TYPE
			SYNTAX SEQUENCE OF FanInfoEntry
			MAX-ACCESS not-accessible
			STATUS current
			DESCRIPTION
				"The fan info of cmu module."
			::= { cmu 2 }

		fanInfoEntry OBJECT-TYPE
			SYNTAX FanInfoEntry
			MAX-ACCESS not-accessible
			STATUS current
			DESCRIPTION
				"The fan info of cmu module ."
			INDEX { fanIndex }
			::= { fanInfoTable 1 }

		FanInfoEntry ::=
			SEQUENCE { 
				fanIndex				Integer32,
				fanSpeed				Integer32,
				fanPercent			    Integer32,
				fanLThreshold           Integer32,
				fanHThreshold           Integer32,
				fanTrapEnable      		INTEGER,
				fanState 				INTEGER,
				fanSerial 				OCTET STRING,
				fanDescr 				OCTET STRING,
				fanType  				INTEGER,
				fanMode  				INTEGER,
				fanAllSetting		OCTET STRING
			 }
			 
		fanIndex OBJECT-TYPE
			SYNTAX Integer32
			MAX-ACCESS read-only
			STATUS current
			DESCRIPTION
				"The index of fan table ."
			::= { fanInfoEntry 1 }

		fanSpeed OBJECT-TYPE
			SYNTAX Integer32
			MAX-ACCESS read-only
			STATUS current
			DESCRIPTION
				"The speed of fan ."
			::= { fanInfoEntry 2 }

		fanPercent OBJECT-TYPE
			SYNTAX Integer32
			MAX-ACCESS read-write
			STATUS current
			DESCRIPTION
				"The percent speed of fan  ."
			::= { fanInfoEntry 3 }

		fanLThreshold OBJECT-TYPE
			SYNTAX Integer32
			MAX-ACCESS read-write
			STATUS current
			DESCRIPTION
				"The lower speed of fan ."
			::= { fanInfoEntry 4 }
			
		fanHThreshold OBJECT-TYPE
			SYNTAX Integer32
			MAX-ACCESS read-write
			STATUS current
			DESCRIPTION
				"The high speed of fan  ."
			::= { fanInfoEntry 5 }
			
		fanTrapEnable OBJECT-TYPE
			SYNTAX  INTEGER{
				enable(1),
				disable(2)
			}
			MAX-ACCESS  read-write
			STATUS  current
			DESCRIPTION
					"Trap enable or not for the fan."
			::= { fanInfoEntry 6 }	
			
		fanState OBJECT-TYPE
			SYNTAX  INTEGER{     
				normal(0),
				highoverflow(1),
				lowunderflow(2),  
				counteroverflow(4)
			}
			MAX-ACCESS  read-only
			STATUS  current
			DESCRIPTION
					"States for the fan controller."
			::= { fanInfoEntry 7 } 
		
		fanSerial OBJECT-TYPE
			SYNTAX  OCTET STRING
			MAX-ACCESS  read-only
			STATUS  current
			DESCRIPTION
					"Serial for the fan controller."
			::= { fanInfoEntry 8 }   
				
		fanDescr OBJECT-TYPE
			SYNTAX  OCTET STRING
			MAX-ACCESS  read-write
			STATUS  current
			DESCRIPTION
					"Description for the fan controller."
			::= { fanInfoEntry 9 } 
				
		fanType OBJECT-TYPE
			SYNTAX  INTEGER{
				dc(0),
				reserved(1)
			}
			MAX-ACCESS  read-only
			STATUS  current
			DESCRIPTION
					"Type for the fan controller."
			::= { fanInfoEntry 10 }		
				
		fanMode OBJECT-TYPE
			SYNTAX  INTEGER{
			   fixedspeed(1),
			   temperatureControl(2),
			   temperatureControlEx(3)
			}
			MAX-ACCESS  read-write
			STATUS  current
			DESCRIPTION
					"Mode for the fan controller."
			::= { fanInfoEntry 11 }  
			
		fanAllSetting OBJECT-TYPE
			SYNTAX  OCTET STRING
			MAX-ACCESS  read-write
			STATUS  current
			DESCRIPTION
					"All parameter operation for the fan controller."
			::= { fanInfoEntry 12 }   
				 
	--power table
	
		powerInfoTable OBJECT-TYPE
			SYNTAX SEQUENCE OF PowerInfoEntry
			MAX-ACCESS not-accessible
			STATUS current
			DESCRIPTION
				"The power info of cmu module."
			::= { cmu 3 }

		powerInfoEntry OBJECT-TYPE
			SYNTAX PowerInfoEntry
			MAX-ACCESS not-accessible
			STATUS current
			DESCRIPTION
				"The power info of cmu module."
			INDEX { powerIndex }
			::= { powerInfoTable 1 }

		PowerInfoEntry ::=
			SEQUENCE { 
						powerIndex      	Integer32,
						powerMode 		INTEGER,	
						powerElectricity        Counter64,
						powerVoltage 		Counter64,
						powerValue  		Counter64,
						powerInputState		Integer32,
						powerVoltageState	Integer32,
						powerlightningProtect   Integer32,
						powerState		INTEGER,
						powerDescr      OCTET STRING
			 }

		powerIndex OBJECT-TYPE
			SYNTAX Integer32
			MAX-ACCESS read-only
			STATUS current
			DESCRIPTION
				"The index of power table ."
			::= { powerInfoEntry 1 }

		powerMode OBJECT-TYPE
			SYNTAX INTEGER
			MAX-ACCESS read-only
			STATUS current
			DESCRIPTION
				"The mode of  power  ."
			::= { powerInfoEntry 2 }
			
		powerElectricity OBJECT-TYPE
			SYNTAX Counter64
			MAX-ACCESS read-only
			STATUS current
			DESCRIPTION
				"The electricity vlan of power ."
			::= { powerInfoEntry 3 }
			
		powerVoltage OBJECT-TYPE
			SYNTAX Counter64
			MAX-ACCESS read-only
			STATUS current
			DESCRIPTION
				"The voltage of power  ."
			::= { powerInfoEntry 4 }
			
		powerValue OBJECT-TYPE
			SYNTAX Counter64
			MAX-ACCESS read-only
			STATUS current
			DESCRIPTION
				"The power value of power ."
			::= { powerInfoEntry 5 }
		
		powerInputState OBJECT-TYPE
			SYNTAX Integer32
			MAX-ACCESS read-only
			STATUS current
			DESCRIPTION
				"The input state of power table ."
			::= { powerInfoEntry 6 }
			
		powerVoltageState OBJECT-TYPE
			SYNTAX Integer32
			MAX-ACCESS read-only
			STATUS current
			DESCRIPTION
				"The voltage state of power table ."
			::= { powerInfoEntry 7 }
			
		powerlightningProtect OBJECT-TYPE
			SYNTAX Integer32
			MAX-ACCESS read-only
			STATUS current
			DESCRIPTION
				"The ightningProtect info of power table ."
			::= { powerInfoEntry 8 }
			
		powerState OBJECT-TYPE
			SYNTAX INTEGER
			{
			   up(1) ,
			   down(2)
			}
			MAX-ACCESS read-only
			STATUS current
			DESCRIPTION
				"The state of power table ."
			::= { powerInfoEntry 9 }

		powerDescr OBJECT-TYPE
			SYNTAX  OCTET STRING
			MAX-ACCESS  read-write
			STATUS  current
			DESCRIPTION
					"Description for the power."
			::= { powerInfoEntry 10 } 
		
		-- voltage table
		voltageInfoTable OBJECT-TYPE
			SYNTAX SEQUENCE OF VoltageInfoEntry
			MAX-ACCESS not-accessible
			STATUS current
			DESCRIPTION
				"The voltage info of cmu module."
			::= { cmu 4 }

		
		voltageInfoEntry OBJECT-TYPE
			SYNTAX VoltageInfoEntry
			MAX-ACCESS not-accessible
			STATUS current
			DESCRIPTION
				"The voltage info of cmu module."
			INDEX { voltageSlotIndex,voltageId }
			::= { voltageInfoTable 1 }

		
		VoltageInfoEntry ::=
			SEQUENCE { 
						voltageSlotIndex      Integer32,
						voltageId    		  Integer32,
						voltageCardType  	  INTEGER,
						voltageName 		  OCTET STRING,
						voltageValue  		  Counter64,
						voltageLThreshold 	  Counter64,
						voltageHThreshold	  Counter64,
						voltageState          INTEGER
			 }

		voltageSlotIndex OBJECT-TYPE
			SYNTAX Integer32
			MAX-ACCESS read-only
			STATUS current
			DESCRIPTION
				"The slot id."
			::= { voltageInfoEntry 1}

		voltageId OBJECT-TYPE
			SYNTAX Integer32
			MAX-ACCESS read-only
			STATUS current
			DESCRIPTION
				"The voltage id."
			::= { voltageInfoEntry 2}
			
		voltageCardType OBJECT-TYPE
			SYNTAX INTEGER
			MAX-ACCESS read-only
			STATUS current
			DESCRIPTION
				"The card type ."
			::= { voltageInfoEntry 3}

		voltageName OBJECT-TYPE
			SYNTAX OCTET STRING (SIZE(0..64))
			MAX-ACCESS read-only
			STATUS current
			DESCRIPTION
				"The voltage name  ."
			::= { voltageInfoEntry 4 }
			
		voltageValue OBJECT-TYPE
			SYNTAX Counter64
			MAX-ACCESS read-only
			STATUS current
			DESCRIPTION
				"The voltage value."
			::= { voltageInfoEntry 5 }

	
		voltageLThreshold OBJECT-TYPE
			SYNTAX Counter64
			MAX-ACCESS read-only
			STATUS current
			DESCRIPTION
				"The lower voltage value ."
			::= { voltageInfoEntry 6 }
			
		voltageHThreshold OBJECT-TYPE
			SYNTAX Counter64
			MAX-ACCESS read-only
			STATUS current
			DESCRIPTION
				"The high voltage value ."
			::= { voltageInfoEntry 7 }
			
		voltageState OBJECT-TYPE
			SYNTAX INTEGER
			{
				normal(0),
				abnormal(1)
			}
			MAX-ACCESS read-only
			STATUS current
			DESCRIPTION
				"The voltage state ."
			::= { voltageInfoEntry 8 }

		cmuInfoTable OBJECT-TYPE
			SYNTAX SEQUENCE OF CmuInfoEntry
			MAX-ACCESS not-accessible
			STATUS current
			DESCRIPTION
				"The cmu info."
			::= { cmu 5 }

		cmuInfoEntry OBJECT-TYPE
			SYNTAX CmuInfoEntry
			MAX-ACCESS not-accessible
			STATUS current
			DESCRIPTION
				"The cmu info ."
			INDEX { cmuIndex }
			::= { cmuInfoTable 1 }

		CmuInfoEntry ::=
			SEQUENCE { 
				cmuIndex				Integer32,
				cmuSwVer 				OCTET STRING,
				cmuHwver 				OCTET STRING,
				cmuCompliedTime				OCTET STRING,
				cmuPrimary				INTEGER,
				cmuState				INTEGER
			 }
			 
		cmuIndex OBJECT-TYPE
			SYNTAX Integer32
			MAX-ACCESS read-only
			STATUS current
			DESCRIPTION
				"The index of fan table ."
			::= { cmuInfoEntry 1 }

		cmuSwVer OBJECT-TYPE
			SYNTAX OCTET STRING (SIZE(0..64))
			MAX-ACCESS read-only
			STATUS current
			DESCRIPTION
				"Software version of the slot."
			::= { cmuInfoEntry 2 }
			
		cmuHwver OBJECT-TYPE
			SYNTAX OCTET STRING (SIZE(0..64))
			MAX-ACCESS read-only
			STATUS current
			DESCRIPTION
				"Hardware version of the slot."
			::= { cmuInfoEntry 3 }
			
		cmuCompliedTime OBJECT-TYPE
			SYNTAX  OCTET STRING (SIZE(0..64))
			MAX-ACCESS  read-only
			STATUS  current
			DESCRIPTION
					"The compile time."
			::= { cmuInfoEntry 4 }
			
		cmuPrimary OBJECT-TYPE
			SYNTAX INTEGER
			{
					master(1),
					slave(2)
			}
			MAX-ACCESS read-only
			STATUS current
			DESCRIPTION
				"The status of cmu:master\slave."
			::= { cmuInfoEntry 5 }
			
		cmuState OBJECT-TYPE
			SYNTAX INTEGER
			{
					up(1),
					down(2)
			}
			MAX-ACCESS read-only
			STATUS current
			DESCRIPTION
				"The state of cmu."
			::= { cmuInfoEntry 6 }
		
		cmuFanTrap			OBJECT IDENTIFIER ::=   {cmu 6}
		
		cmuFanUp NOTIFICATION-TYPE
       		OBJECTS {fanState}
       		STATUS  current
       		DESCRIPTION
               	"mspp cmu fan up trap."
			::= { cmuFanTrap 1}
		
		cmuFanDown NOTIFICATION-TYPE
	       	OBJECTS {fanState}
       		STATUS  current
       		DESCRIPTION
               	"mspp cmu fan down trap"
			::= { cmuFanTrap 2}
		
		cmuFanFault NOTIFICATION-TYPE
       		OBJECTS {fanState}
       		STATUS  current
       		DESCRIPTION            
               	"mspp cmu fan fault trap.fanState==1,overflow, fanState==2 tooslow"
			::= { cmuFanTrap 3}
		
		cmuFanOk NOTIFICATION-TYPE
	       	OBJECTS {fanState}
       		STATUS  current
       		DESCRIPTION
       		"mspp cmu fan ok trap."             
			::= { cmuFanTrap 4}
		
		
		
		cmuVoltageTrap			OBJECT IDENTIFIER ::=   {cmu 7}
		
		
		cmuvoltageNormal NOTIFICATION-TYPE
       		OBJECTS {voltageValue,voltageLThreshold,voltageHThreshold}
       		STATUS  current
       		DESCRIPTION
               	"cmu voltage normal."
			::= { cmuVoltageTrap 1}
		
		cmuvoltageAbnormal NOTIFICATION-TYPE
	       	OBJECTS {voltageValue,voltageLThreshold,voltageHThreshold}
       		STATUS  current
       		DESCRIPTION
               	"cmu voltage abnormal"
			::= { cmuVoltageTrap 2}
			
			
		cmuPowerTrap			OBJECT IDENTIFIER ::=   {cmu 8}

		cmuPowerUp NOTIFICATION-TYPE
       		OBJECTS {powerState}
       		STATUS  current
       		DESCRIPTION
               	"power up trap."
			::= { cmuPowerTrap 1}
		
		
		cmuPowerDown NOTIFICATION-TYPE
	       	OBJECTS {powerState}
       		STATUS  current
       		DESCRIPTION
               	"power down trap."
			::= { cmuPowerTrap 2}
			
		cmuTrap			OBJECT IDENTIFIER ::=   {cmu 9}

		cmuUp NOTIFICATION-TYPE
       		OBJECTS {cmuState}
       		STATUS  current
       		DESCRIPTION
               	"cmu up trap."
			::= { cmuTrap 1}
		
		
		cmuDown NOTIFICATION-TYPE
	       	OBJECTS {cmuState}
       		STATUS  current
       		DESCRIPTION
               	"cmu down trap."
			::= { cmuTrap 2}
			
			
		
			
	END

--
-- cmu.mib
--
