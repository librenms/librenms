WRI-DHCPSNOOP-MIB DEFINITIONS ::= BEGIN
 
    IMPORTS
        TimeTicks, IpAddress, Unsigned32, Counter32,OBJECT-TYPE,MODULE-IDENTITY
            FROM SNMPv2-SMI            
        MacAddress, RowStatus, TEXTUAL-CONVENTION            
            FROM SNMPv2-TC
        enterprises	FROM RFC1155-SMI
        InetAddressType,InetAddress			FROM INET-ADDRESS-MIB
        wri,wriProtocol,wriProducts				FROM WRI-SMI;
            	
    -- 1.3.6.1.4.1.3807.2.403
		wriDhcpSnoop OBJECT IDENTIFIER ::= { wriProtocol 418 }
     
		-- 1.3.6.1.4.1.3807.2.403.1
		dhcpSnoopCommon OBJECT IDENTIFIER ::= { wriDhcpSnoop 1 }
        
          
-- WRI DhcpSnoop Common Information	
		-- 1.3.6.1.4.1.3807.2.403.1.1
		dhcpSnoopStatus OBJECT-TYPE
			SYNTAX INTEGER
				{
				start(1),
				stop(0)
				}
			MAX-ACCESS read-write
			STATUS current
			DESCRIPTION
				"The dhcp snoop protocol common status enabled to start the protocol,
				disabled to stop the protocol."
			::= { dhcpSnoopCommon 1 } 
		
	  -- 1.3.6.1.4.1.3807.2.403.1.2
    dhcpSnoopUserNumber OBJECT-TYPE
        SYNTAX INTEGER
        MAX-ACCESS read-only
        STATUS current
        DESCRIPTION
            "The number of dhcpsnoop user. "
        ::= { dhcpSnoopCommon 2 }
        
    -- 1.3.6.1.4.1.3807.2.403.1.3
    dhcpSnoopServerDetect OBJECT-TYPE
        SYNTAX INTEGER
        {
				  enable(1),
				  disable(0)
				}
        MAX-ACCESS read-write
        STATUS current
        DESCRIPTION
            "Enable or disable the server detect function "
        ::= { dhcpSnoopCommon 3 }
        
    -- 1.3.6.1.4.1.3807.2.403.1.4
    dhcpSnoopResetStatistics OBJECT-TYPE
        SYNTAX INTEGER
        MAX-ACCESS read-write
        STATUS current
        DESCRIPTION
            "Reset the statistics. "
        ::= { dhcpSnoopCommon 4 }
        
   
                                                             
  -- 1.3.6.1.4.1.3807.2.403.2                      
     dhcpSnoopIfTable OBJECT-TYPE
        SYNTAX SEQUENCE OF DhcpSnoopIfEntry
        MAX-ACCESS not-accessible
        STATUS current
        DESCRIPTION
            "The dhcpsnoop interface table. "
        ::= { wriDhcpSnoop 2 }
                                       
                                                   
     -- 1.3.6.1.4.1.3807.2.403.2.1                                                   
     dhcpSnoopIfEntry OBJECT-TYPE
         SYNTAX DhcpSnoopIfEntry
         MAX-ACCESS not-accessible
         STATUS current
         DESCRIPTION
            "The dhcpsnoop interface table. "
         INDEX { dhcpSnoopIfIndex }
         ::= { dhcpSnoopIfTable 1 }

        
     DhcpSnoopIfEntry ::=
         SEQUENCE { 
                dhcpSnoopIfIndex               INTEGER,
                dhcpSnoopIfStatus              INTEGER,
                dhcpSnoopIfVersion             INTEGER,
                dhcpSnoopIfTrust               INTEGER,            
                dhcpSnoopIfOption82Strategy    INTEGER,
                dhcpSnoopIfOption82Status      INTEGER, 
                dhcpSnoopIfOption82Circuitid   OCTET STRING,
                dhcpSnoopIfOption82Remoteid    OCTET STRING,
                dhcpSnoopIfOption82Sub9        OCTET STRING,
                dhcpSnoopIfSub9Status          INTEGER,
                dhcpSnoopIfOption18Status      INTEGER,
                dhcpSnoopIfOption18            OCTET STRING,
                dhcpSnoopIfOption37Status      INTEGER,
                dhcpSnoopIfOption37            OCTET STRING,
                dhcpSnoopIfMacAddressCheck       INTEGER,
                dhcpSnoopIfUserBindCheck         INTEGER,
                dhcpSnoopIfMaxUserNum            INTEGER,
                dhcpSnoopIfRateCheckEnable       INTEGER,
                dhcpSnoopIfRateCheck             INTEGER,
                dhcpSnoopIfResetStatistics          INTEGER,
                dhcpSnoopIfMacMismatchPkt        Counter32,
                dhcpSnoopIfBindMismatchPkt       Counter32,
                dhcpSnoopIfUntrustReplyPkt       Counter32,
                dhcpSnoopIfDiscordArpPkt         Counter32,
                dhcpSnoopIfDiscordIpPkt          Counter32,
                dhcpSnoopIfDiscordDhcpPkt        Counter32,
                dhcpSnoopIfPvid                   Unsigned32,
                dhcpSnoopIfCurUserNum                   Unsigned32       
              }
                                                                                    
        -- 1.3.6.1.4.1.3807.2.403.2.1.1
        dhcpSnoopIfIndex OBJECT-TYPE
            SYNTAX INTEGER (1..65535)
            MAX-ACCESS read-only
            STATUS current
            DESCRIPTION
                "interface index. "
            ::= { dhcpSnoopIfEntry 1 }
                                       
                                       
        -- 1.3.6.1.4.1.3807.2.403.2.1.2
        dhcpSnoopIfStatus OBJECT-TYPE
			      SYNTAX INTEGER
						{
							enable(1),
							disable(0)
						}
					  MAX-ACCESS read-write
					  STATUS current
				  	DESCRIPTION
							 "The dhcpsnoop status of interface. "
					  ::= { dhcpSnoopIfEntry 2 }
				
				-- 1.3.6.1.4.1.3807.2.403.2.1.3
        dhcpSnoopIfVersion OBJECT-TYPE
			      SYNTAX INTEGER
						{
							v4(1),
							v6(2),
							all(3)
						}
					  MAX-ACCESS read-write
					  STATUS current
					  DESCRIPTION
							  "The version of dhcpsnoop. "
					  ::= { dhcpSnoopIfEntry 3 }
					
				-- 1.3.6.1.4.1.3807.2.403.2.1.4
        dhcpSnoopIfTrust OBJECT-TYPE
			      SYNTAX INTEGER
						{
							trust(1),
							untrust(0)
						}
					  MAX-ACCESS read-write
					  STATUS current
					  DESCRIPTION
							"The trust status of interface. "
					  ::= { dhcpSnoopIfEntry 4 }
					  				
				-- 1.3.6.1.4.1.3807.2.403.2.1.5
        dhcpSnoopIfOption82Strategy OBJECT-TYPE
			      SYNTAX INTEGER
						 {
							drop(1),
							keep(2),
							append(3)
						 }
					  MAX-ACCESS read-write
					  STATUS current
					  DESCRIPTION
							"The dhcpsnoop option82 strategy of interface. "
					  ::= { dhcpSnoopIfEntry 5 }
					
				-- 1.3.6.1.4.1.3807.2.403.2.1.6
        dhcpSnoopIfOption82Status OBJECT-TYPE
			      SYNTAX INTEGER
						 {
							enable(1),
							disable(0)
						 }
					  MAX-ACCESS read-write
					  STATUS current
					  DESCRIPTION
							"The dhcpsnoop option82 status of interface. "
					  ::= { dhcpSnoopIfEntry 6 }
					  
				-- 1.3.6.1.4.1.3807.2.403.2.1.7
        dhcpSnoopIfOption82Circuitid OBJECT-TYPE
			      SYNTAX  OCTET STRING
					  MAX-ACCESS read-write
					  STATUS current
					  DESCRIPTION
							"The dhcpsnoop option82 circuit id of interface. "
					  ::= { dhcpSnoopIfEntry 7 }
					  
				-- 1.3.6.1.4.1.3807.2.403.2.1.8
        dhcpSnoopIfOption82Remoteid OBJECT-TYPE
			      SYNTAX  OCTET STRING
					  MAX-ACCESS read-write
					  STATUS current
					  DESCRIPTION
							"The dhcpsnoop option82 remote id of interface "
					  ::= { dhcpSnoopIfEntry 8 }
					  
				-- 1.3.6.1.4.1.3807.2.403.2.1.9
        dhcpSnoopIfOption82Sub9 OBJECT-TYPE
			      SYNTAX  OCTET STRING
					  MAX-ACCESS read-write
					  STATUS current
					  DESCRIPTION
							"The dhcpsnoop option82 sub-option9 of interface. "
					  ::= { dhcpSnoopIfEntry 9 }  
					  
				-- 1.3.6.1.4.1.3807.2.403.2.1.10
        dhcpSnoopIfSub9Status OBJECT-TYPE
			      SYNTAX INTEGER
			      {
			      		enable(1),
			      		disable(0)
			      }
					  MAX-ACCESS read-write
					  STATUS current
					  DESCRIPTION
							"The dhcpsnoop option82 sub-option9 status of interface. "
					  ::= { dhcpSnoopIfEntry 10 }  
				
				-- 1.3.6.1.4.1.3807.2.404.2.1.11
			  dhcpSnoopIfOption18Status OBJECT-TYPE
			      SYNTAX INTEGER
				    {
				       enable(1),
				       disable(0)
				    }
			      MAX-ACCESS read-write
			      STATUS current
			      DESCRIPTION
				       "The status of option18,enable or disable."
			      ::= { dhcpSnoopIfEntry 11 } 
			      
			  -- 1.3.6.1.4.1.3807.2.404.2.1.12
			  dhcpSnoopIfOption18 OBJECT-TYPE
			      SYNTAX OCTET STRING
			      MAX-ACCESS read-write
			      STATUS current
			      DESCRIPTION
				       "The information of optoion18."
			      ::= { dhcpSnoopIfEntry 12 }
			      
			  -- 1.3.6.1.4.1.3807.2.404.2.1.13
			  dhcpSnoopIfOption37Status OBJECT-TYPE
			      SYNTAX INTEGER
				    {
				       enable(1),
				       disable(0)
				    }
			      MAX-ACCESS read-write
			      STATUS current
			      DESCRIPTION
				       "The status of option37,enable or disable."
			      ::= { dhcpSnoopIfEntry 13 }   
			  
			  -- 1.3.6.1.4.1.3807.2.404.2.1.14
			  dhcpSnoopIfOption37 OBJECT-TYPE
			      SYNTAX OCTET STRING
			      MAX-ACCESS read-write
			      STATUS current
			      DESCRIPTION
				       "The information of option37."
			      ::= { dhcpSnoopIfEntry 14 }
			      
			 -- 1.3.6.1.4.1.3807.2.404.2.1.15
			  dhcpSnoopIfMacAddressCheck OBJECT-TYPE
			      SYNTAX INTEGER
			      {
			          enable(1),
			          disable(0)
			      }
			      MAX-ACCESS read-write
			      STATUS current
			      DESCRIPTION
				       ""
			      ::= { dhcpSnoopIfEntry 15 }
			      
			 -- 1.3.6.1.4.1.3807.2.404.2.1.16
			  dhcpSnoopIfUserBindCheck OBJECT-TYPE
			      SYNTAX INTEGER
			      {
			          enable(1),
			          disable(0)
			      }
			      MAX-ACCESS read-write
			      STATUS current
			      DESCRIPTION
				       ""
			      ::= { dhcpSnoopIfEntry 16 }
			      
			      
			 -- 1.3.6.1.4.1.3807.2.404.2.1.17
			  dhcpSnoopIfMaxUserNum OBJECT-TYPE
			      SYNTAX INTEGER
			      MAX-ACCESS read-write
			      STATUS current
			      DESCRIPTION
				       ""
			      ::= { dhcpSnoopIfEntry 17 }
			      
			      
			  -- 1.3.6.1.4.1.3807.2.404.2.1.18
			  dhcpSnoopIfRateCheckEnable OBJECT-TYPE
			      SYNTAX INTEGER
			      {
			          enable(1),
			          disable(0)
			      }
			      MAX-ACCESS read-write
			      STATUS current
			      DESCRIPTION
				       ""
			      ::= { dhcpSnoopIfEntry 18 }   
			 
			 
			  -- 1.3.6.1.4.1.3807.2.404.2.1.19
			  dhcpSnoopIfRateCheck OBJECT-TYPE
			      SYNTAX INTEGER
			      MAX-ACCESS read-write
			      STATUS current
			      DESCRIPTION
				       ""
			      ::= { dhcpSnoopIfEntry 19 } 
			      
			 -- 1.3.6.1.4.1.3807.2.404.2.1.20
			  dhcpSnoopIfResetStatistics OBJECT-TYPE
			      SYNTAX INTEGER
			      MAX-ACCESS read-write
			      STATUS current
			      DESCRIPTION
				       ""
			      ::= { dhcpSnoopIfEntry 20 } 
			      
			 -- 1.3.6.1.4.1.3807.2.404.2.1.21
			  dhcpSnoopIfMacMismatchPkt OBJECT-TYPE
			      SYNTAX Counter32
			      MAX-ACCESS read-only
			      STATUS current
			      DESCRIPTION
				       ""
			      ::= { dhcpSnoopIfEntry 21 }
			      
			  -- 1.3.6.1.4.1.3807.2.404.2.1.22
			  dhcpSnoopIfBindMismatchPkt OBJECT-TYPE
			      SYNTAX Counter32
			      MAX-ACCESS read-only
			      STATUS current
			      DESCRIPTION
				       ""
			      ::= { dhcpSnoopIfEntry 22 }
			      
			  -- 1.3.6.1.4.1.3807.2.404.2.1.23
			  dhcpSnoopIfUntrustReplyPkt OBJECT-TYPE
			      SYNTAX Counter32
			      MAX-ACCESS read-only
			      STATUS current
			      DESCRIPTION
				       ""
			      ::= { dhcpSnoopIfEntry 23 }
			      
			  -- 1.3.6.1.4.1.3807.2.404.2.1.24
			  dhcpSnoopIfDiscordArpPkt OBJECT-TYPE
			      SYNTAX Counter32
			      MAX-ACCESS read-only
			      STATUS current
			      DESCRIPTION
				       ""
			      ::= { dhcpSnoopIfEntry 24 }
			      
			  -- 1.3.6.1.4.1.3807.2.404.2.1.25
			  dhcpSnoopIfDiscordIpPkt OBJECT-TYPE
			      SYNTAX Counter32
			      MAX-ACCESS read-only
			      STATUS current
			      DESCRIPTION
				       ""
			      ::= { dhcpSnoopIfEntry 25 }
			      
			  -- 1.3.6.1.4.1.3807.2.404.2.1.26
			  dhcpSnoopIfDiscordDhcpPkt OBJECT-TYPE
			      SYNTAX Counter32
			      MAX-ACCESS read-only
			      STATUS current
			      DESCRIPTION
				       ""
			      ::= { dhcpSnoopIfEntry 26 } 
			      
			  -- 1.3.6.1.4.1.3807.2.404.2.1.27
			  dhcpSnoopIfPvid OBJECT-TYPE
			      SYNTAX Unsigned32
			      MAX-ACCESS read-only
			      STATUS current
			      DESCRIPTION
				       ""
			      ::= { dhcpSnoopIfEntry 27 }  
			      
			  -- 1.3.6.1.4.1.3807.2.404.2.1.28
			  dhcpSnoopIfCurUserNum OBJECT-TYPE
			      SYNTAX Unsigned32
			      MAX-ACCESS read-only
			      STATUS current
			      DESCRIPTION
				       ""
			      ::= { dhcpSnoopIfEntry 28 }  			  
			 
									                                                                          
     -- 1.3.6.1.4.1.3807.2.403.3
     dhcpSnoopUserInfoTable OBJECT-TYPE
         SYNTAX SEQUENCE OF DhcpSnoopUserInfoEntry
         MAX-ACCESS not-accessible
         STATUS current
         DESCRIPTION
              "dhcpsnoop user information table. "
          ::= { wriDhcpSnoop 3 }
                                   
                                   
     -- 1.3.6.1.4.1.3807.2.403.3.1
     dhcpSnoopUserInfoEntry OBJECT-TYPE
         SYNTAX DhcpSnoopUserInfoEntry
         MAX-ACCESS not-accessible
         STATUS current
         DESCRIPTION
              "dhcpsnoop user information table. "
         INDEX { dhcpSnoopUserInfoIpAddrType,dhcpSnoopUserInfoIpAddr }
         ::= { dhcpSnoopUserInfoTable 1 }

        
        DhcpSnoopUserInfoEntry ::=
            SEQUENCE {
            		dhcpSnoopUserInfoIpAddrType     InetAddressType,
            		dhcpSnoopUserInfoIpAddr         InetAddress,
                dhcpSnoopUserInfoMac		        MacAddress,          
								dhcpSnoopUserInfoVid            INTEGER,                
								dhcpSnoopUserInfoIfIndex      	INTEGER,			
				   			dhcpSnoopUserInfoTime           INTEGER,
				   			dhcpSnoopUserInfoState          INTEGER,
				   			dhcpSnoopUserInfoRowStatus      RowStatus,
				   			dhcpSnoopUserInfoCurTime          INTEGER           	
             }
             
        -- 1.3.6.1.4.1.3807.2.403.3.1.1 
        dhcpSnoopUserInfoIpAddrType OBJECT-TYPE
				    SYNTAX  InetAddressType
				    MAX-ACCESS  read-only
				    STATUS  current
				    DESCRIPTION
						   "ipv4 address:1,ipv6 address:2."
				    ::= { dhcpSnoopUserInfoEntry 1 }  
        
        -- 1.3.6.1.4.1.3807.2.403.3.1.2                                       
        dhcpSnoopUserInfoIpAddr OBJECT-TYPE
            SYNTAX InetAddress
            MAX-ACCESS read-only
            STATUS current
            DESCRIPTION
                "The ip address of dhcpsnoop user. "
            ::= { dhcpSnoopUserInfoEntry 2 }
        
        -- 1.3.6.1.4.1.3807.2.403.3.1.3
        dhcpSnoopUserInfoMac OBJECT-TYPE
            SYNTAX MacAddress
            MAX-ACCESS read-write
            STATUS current
            DESCRIPTION
                "The mac address of dhcpsnoop user. "
            ::= { dhcpSnoopUserInfoEntry 3 }
                                                                                                     
       -- 1.3.6.1.4.1.3807.2.403.3.1.4
        dhcpSnoopUserInfoVid OBJECT-TYPE
            SYNTAX INTEGER
            MAX-ACCESS read-write
            STATUS current
            DESCRIPTION
                "The vlan id of dhcpsnoop user. "
            ::= { dhcpSnoopUserInfoEntry 4 }
                                             
        -- 1.3.6.1.4.1.3807.2.403.3.1.5
        dhcpSnoopUserInfoIfIndex OBJECT-TYPE
            SYNTAX INTEGER
            MAX-ACCESS read-write
            STATUS current
            DESCRIPTION
                "The interface index of dhcpsnoop user. "
            ::= { dhcpSnoopUserInfoEntry 5 }                                                                          			
            
        -- 1.3.6.1.4.1.3807.2.403.3.1.6
        dhcpSnoopUserInfoTime OBJECT-TYPE
            SYNTAX INTEGER
            MAX-ACCESS read-only
            STATUS current
            DESCRIPTION
                "The rent time of dhcpsnoop user. "
            ::= { dhcpSnoopUserInfoEntry 6 }
            
        -- 1.3.6.1.4.1.3807.2.403.3.1.7
        dhcpSnoopUserInfoState OBJECT-TYPE
            SYNTAX INTEGER
              {
                 static(2),
                 dynamic(1)
              }
            MAX-ACCESS read-only
            STATUS current
            DESCRIPTION
                "The state of dhcpsnoop user:dynamic learning or static configure."
            ::= { dhcpSnoopUserInfoEntry 7 }
            
        -- 1.3.6.1.4.1.3807.2.403.3.1.8
        dhcpSnoopUserInfoRowStatus OBJECT-TYPE
            SYNTAX RowStatus
            MAX-ACCESS read-write
            STATUS current
            DESCRIPTION
                "Add or delete one dhcpsnoop user. active 1,notInService 2,notReady 3,createAndGo 4
								createAndWait 5,destroy 6"
            ::= { dhcpSnoopUserInfoEntry 8 }
            
         -- 1.3.6.1.4.1.3807.2.403.3.1.9
        dhcpSnoopUserInfoCurTime OBJECT-TYPE
            SYNTAX INTEGER
            MAX-ACCESS read-only
            STATUS current
            DESCRIPTION
                "The current time of dhcpsnoop user. "
            ::= { dhcpSnoopUserInfoEntry 9 }
            
-- 1.3.6.1.4.1.3807.2.403.4                      
     dhcpSnoopVlanIfTable OBJECT-TYPE
        SYNTAX SEQUENCE OF DhcpSnoopVlanIfEntry
        MAX-ACCESS not-accessible
        STATUS current
        DESCRIPTION
            "The dhcpsnoop vlan interface table. "
        ::= { wriDhcpSnoop 4 }
                                       
                                                   
     -- 1.3.6.1.4.1.3807.2.403.4.1                                                   
     dhcpSnoopVlanIfEntry OBJECT-TYPE
         SYNTAX DhcpSnoopVlanIfEntry
         MAX-ACCESS not-accessible
         STATUS current
         DESCRIPTION
            "The dhcpsnoop vlan interface table. "
         INDEX { dhcpSnoopVlanIfIndex }
         ::= { dhcpSnoopVlanIfTable 1 }

        
     DhcpSnoopVlanIfEntry ::=
         SEQUENCE { 
                dhcpSnoopVlanIfIndex               INTEGER,
                dhcpSnoopVlanIfMaxUserNum              INTEGER,
                dhcpSnoopVlanIfUserCnt             INTEGER
              }
                                                                                    
        -- 1.3.6.1.4.1.3807.2.403.4.1.1
        dhcpSnoopVlanIfIndex OBJECT-TYPE
            SYNTAX INTEGER (1..4094)
            MAX-ACCESS read-only
            STATUS current
            DESCRIPTION
                "interface index. "
            ::= { dhcpSnoopVlanIfEntry 1 }

				-- 1.3.6.1.4.1.3807.2.403.4.1.2
        dhcpSnoopVlanIfMaxUserNum OBJECT-TYPE
            SYNTAX INTEGER
            MAX-ACCESS read-write
            STATUS current
            DESCRIPTION
                ""
            ::= { dhcpSnoopVlanIfEntry 2 }
        
        -- 1.3.6.1.4.1.3807.2.403.4.1.3
        dhcpSnoopVlanIfUserCnt OBJECT-TYPE
            SYNTAX INTEGER
            MAX-ACCESS read-only
            STATUS current
            DESCRIPTION
                "interface index. "
            ::= { dhcpSnoopVlanIfEntry 3 }    
                                        
    END
