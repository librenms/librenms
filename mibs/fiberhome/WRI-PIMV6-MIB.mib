--
-- wriPimv6.mib
-- MIB generated by MG-SOFT Visual MIB Builder Version 4.0 Build 349
-- Thursday, January 06, 2011 at 09:56:54
--

	WRI-PIMV6-PRIVATE-MIB DEFINITIONS ::= BEGIN
 
		IMPORTS
			mib-2			
				FROM RFC1213-MIB			
			TimeTicks, IpAddress, Integer32, Gauge32, Counter32,Unsigned32,
			OBJECT-TYPE, MODULE-IDENTITY, NOTIFICATION-TYPE			
				FROM SNMPv2-SMI	
			 Ipv6Address                   
			    FROM IPV6-TC		
			DisplayString, RowStatus, TruthValue			
				FROM SNMPv2-TC			
			wriProtocol			
				FROM WRI-SMI;
	
	
		-- 1.3.6.1.4.1.3807.2.1620
		pimv6MIB MODULE-IDENTITY 
			LAST-UPDATED "200208211830Z"		-- August 21, 2002 at 18:30 GMT
			ORGANIZATION 
				"Fiberhomenetworks software group"
			CONTACT-INFO 
				"postal :-
				Fiberhomenetworks Ltd.,
				88,youkeyuan road,wuhan
				china
				Phone 
				EMail: "
			DESCRIPTION 
				"The MIB module for management of PIMv6 Routers
				Initial Version"
			::= { wriProtocol 1620 }

		
	
	
--
-- Node definitions
--	
		-- 1.3.6.1.4.1.3807.2.1620.1
		wriPimv6Scalars OBJECT IDENTIFIER ::= { pimv6MIB 1 }

		
		-- 1.3.6.1.4.1.3807.2.1620.1.1
		wriPimv6VersionString OBJECT-TYPE
			SYNTAX DisplayString
			MAX-ACCESS read-only
			STATUS current
			DESCRIPTION
				"The version number of the PIM protocol in the router"
			::= { wriPimv6Scalars 1 }	
	
		-- 1.3.6.1.4.1.3807.2.1620.1.2
		wriPimv6Enable OBJECT-TYPE
			SYNTAX INTEGER
				{
				enable(1),
				disable(2)
				}
			MAX-ACCESS read-write
			STATUS current
			DESCRIPTION
				"wriPimv6Enable."
			::= { wriPimv6Scalars 2 }
       
       -- 1.3.6.1.4.1.3807.2.1620.1.3
      wriPimv6CurrentTime OBJECT-TYPE
			SYNTAX INTEGER
			MAX-ACCESS read-only
			STATUS current
			DESCRIPTION
				"wriPimv6Enable."
			::= { wriPimv6Scalars 3 }  
			
		-- 1.3.6.1.4.1.3807.2.1620.2
		wriPimv6Tables OBJECT IDENTIFIER ::= { pimv6MIB 2 }

				
        -- 1.3.6.1.4.1.3807.2.1620.2.1
		wriPimv6InstanceTable OBJECT-TYPE
			SYNTAX SEQUENCE OF WriPimv6InstanceEntry
			MAX-ACCESS not-accessible
			STATUS current
			DESCRIPTION
				"The (conceptual) table listing the router's PIM instance				
				table."
			::= { wriPimv6Tables 1 }

		
		-- 1.3.6.1.4.1.3807.2.1620.2.1
		wriPimv6InstanceEntry OBJECT-TYPE
			SYNTAX WriPimv6InstanceEntry       
			MAX-ACCESS not-accessible
			STATUS current
			DESCRIPTION
				"An entry (conceptual row) in the pimInstanceTable."
			INDEX { wriPimv6Instance }
			::= { wriPimv6InstanceTable 1 }

		
		WriPimv6InstanceEntry ::=
			SEQUENCE {  
				wriPimv6Instance
					INTEGER,
				wriPimv6InstanceJoinPruneInterval
					Integer32,
				wriPimv6InstanceSPTGroupThreshold
					INTEGER,
				wriPimv6InstanceEnableFastfowardMcastPkt
					INTEGER,
				wriPimv6InstanceEnableNeighborLossTrap
					INTEGER,
				wriPimv6InstanceIpMRouteEntryCount
					Gauge32,    
				wriPimv6InstanceIpMemeryAllocatedCount
					Gauge32,				
				wriPimv6InstanceRegisterFragment
					INTEGER,
				wriPimv6InstanceRegisterMtu
					INTEGER,
				wriPimv6InstanceAcceptUnkownRp
					INTEGER,
				wriPimv6InstanceExternsionChecksum
					INTEGER,
				wriPimv6InstanceRegisterThreshold												
			        INTEGER,
			    wriPimv6InstanceScopeStatus												
			        INTEGER, 
			    wriPimv6InstanceIfCount												
			        Gauge32, 
                wriPimv6InstanceCrpGrpCount												
			        Gauge32, 
			    wriPimv6InstanceIsCrp												
			        INTEGER,    
			 	wriPimv6InstanceStatus	 		
					RowStatus,
				wriPimv6InstanceMrouteFlush
					INTEGER ,
				wriPimv6InstanceEmbeddedRp
					INTEGER,				    		 		
				wriPimv6InstanceStateFlashInterval
					INTEGER,		
				wriPimv6InstanceStateFlashRateLimit
					INTEGER,			                         				
				wriPimv6InstanceStateFlashTtl
					INTEGER,
				wriPimv6InstanceMode
					INTEGER			
            }

  		-- 1.3.6.1.4.1.3807.2.1620.2.1.1
		wriPimv6Instance   OBJECT-TYPE
			SYNTAX INTEGER
			MAX-ACCESS read-only
			STATUS current
			DESCRIPTION
				"The vpn instance id ."
			::= { wriPimv6InstanceEntry 1 }

						
		-- 1.3.6.1.4.1.3807.2.1620.2.1.2
		wriPimv6InstanceJoinPruneInterval OBJECT-TYPE
			SYNTAX Integer32 (1..65535)
			UNITS "seconds"
			MAX-ACCESS read-write
			STATUS current
			DESCRIPTION
				"The default interval at which periodic PIM-SM Join/Prune
				messages are to be sent."
			DEFVAL { 60 }
			::= { wriPimv6InstanceEntry 2 }

		
		-- 1.3.6.1.4.1.3807.2.1620.2.1.3
		wriPimv6InstanceSPTGroupThreshold OBJECT-TYPE
			SYNTAX INTEGER (1..2147483647)
			MAX-ACCESS read-write
			STATUS current
			DESCRIPTION
				"The threshold of data rate for any group when exceeded,
				source specific counters are initiated for that particular group
				It is based on number of bits per sec.
				To initiate SPT switching counter, this threshold MUST be
				configured"
			::= { wriPimv6InstanceEntry 3 }

		
		-- 1.3.6.1.4.1.3807.2.1620.2.1.4
		wriPimv6InstanceEnableFastfowardMcastPkt OBJECT-TYPE
			SYNTAX INTEGER
				{
				enable(1),
				disable(2)
				}
			MAX-ACCESS read-write
			STATUS current
			DESCRIPTION
				"The threshold of data rate for any group when exceeded,
				source specific counters are initiated for that particular group
				It is based on number of bits per sec.
				To initiate SPT switching counter, this threshold MUST be
				configured"
			::= { wriPimv6InstanceEntry 4 }

		
		-- 1.3.6.1.4.1.3807.2.1620.2.1.5
		wriPimv6InstanceEnableNeighborLossTrap OBJECT-TYPE
			SYNTAX INTEGER
				{
				enable(1),
				disable(2)
				}
			MAX-ACCESS read-write
			STATUS current
			DESCRIPTION
				"The threshold of data rate for any group when exceeded,
				source specific counters are initiated for that particular group
				It is based on number of bits per sec.
				To initiate SPT switching counter, this threshold MUST be
				configured"
			::= { wriPimv6InstanceEntry 5 }

		
		-- 1.3.6.1.4.1.3807.2.1620.2.1.6
		wriPimv6InstanceIpMRouteEntryCount OBJECT-TYPE
			SYNTAX Gauge32
			MAX-ACCESS read-only
			STATUS current
			DESCRIPTION
				"The number of rows in the pimIpMRouteTable. This can be used
				to monitor the multicast routing table size."
			::= { wriPimv6InstanceEntry 6 }

		
		-- 1.3.6.1.4.1.3807.2.1620.2.1.7
		wriPimv6InstanceIpMemeryAllocatedCount OBJECT-TYPE
			SYNTAX Gauge32
			MAX-ACCESS read-only
			STATUS current
			DESCRIPTION
				"This attributes holds the memory allocated for the PIM in Bytes."
			::= { wriPimv6InstanceEntry 7 }

		
				
		-- 1.3.6.1.4.1.3807.2.1620.2.1.8
		wriPimv6InstanceRegisterFragment OBJECT-TYPE
			SYNTAX INTEGER
				{
				no(0),
				fragment(1)
				}
			MAX-ACCESS read-write
			STATUS current
			DESCRIPTION
				"Description."
			::= { wriPimv6InstanceEntry 8 }

		
		-- 1.3.6.1.4.1.3807.2.1620.2.1.9
		wriPimv6InstanceRegisterMtu OBJECT-TYPE
			SYNTAX INTEGER (750..1600)
			MAX-ACCESS read-write
			STATUS current
			DESCRIPTION
				"Description."
			::= { wriPimv6InstanceEntry 9 }

		
		-- 1.3.6.1.4.1.3807.2.1620.2.1.10
		wriPimv6InstanceAcceptUnkownRp OBJECT-TYPE
			SYNTAX INTEGER
				{
				no(0),
				unkownRp(1)
				}
			MAX-ACCESS read-write
			STATUS current
			DESCRIPTION
				"Description."
			::= { wriPimv6InstanceEntry 10 }

		
		-- 1.3.6.1.4.1.3807.2.1620.2.1.11
		wriPimv6InstanceExternsionChecksum OBJECT-TYPE
			SYNTAX INTEGER
				{
				no(0),
				checksum(1)
				}
			MAX-ACCESS read-write
			STATUS current
			DESCRIPTION
				"Description."
			::= { wriPimv6InstanceEntry 11 }

		
		-- 1.3.6.1.4.1.3807.2.1620.2.1.12
		wriPimv6InstanceRegisterThreshold OBJECT-TYPE
			SYNTAX INTEGER (1..2147483647)
			MAX-ACCESS read-write
			STATUS current
			DESCRIPTION
				"Description."
			::= { wriPimv6InstanceEntry 12 }

		
		-- 1.3.6.1.4.1.3807.2.1620.2.1.13
		wriPimv6InstanceScopeStatus OBJECT-TYPE
			SYNTAX INTEGER
			MAX-ACCESS read-write
			STATUS current
			DESCRIPTION
				"Description."
			::= { wriPimv6InstanceEntry 13 }
       
       -- 1.3.6.1.4.1.3807.2.1620.2.1.14
       wriPimv6InstanceIfCount OBJECT-TYPE
			SYNTAX Gauge32
			MAX-ACCESS read-only
			STATUS current
			DESCRIPTION
				"Description."
			::= { wriPimv6InstanceEntry 14 }
			
	   -- 1.3.6.1.4.1.3807.2.1620.2.1.15
       wriPimv6InstanceCrpGrpCount OBJECT-TYPE
			SYNTAX Gauge32
			MAX-ACCESS read-only
			STATUS current
			DESCRIPTION
				"Description."
			::= { wriPimv6InstanceEntry 15 }
					
     
      -- 1.3.6.1.4.1.3807.2.1620.2.1.16
      wriPimv6InstanceIsCrp OBJECT-TYPE
			SYNTAX INTEGER
			MAX-ACCESS read-only
			STATUS current
			DESCRIPTION
				"Description."
			::= { wriPimv6InstanceEntry 16 }
  	
  	  -- 1.3.6.1.4.1.3807.2.1620.2.1.17
      wriPimv6InstanceStatus OBJECT-TYPE
			SYNTAX RowStatus
			MAX-ACCESS read-write
			STATUS current
			DESCRIPTION
				"Description."
			::= { wriPimv6InstanceEntry 17 }

      wriPimv6InstanceMrouteFlush  OBJECT-TYPE
			SYNTAX INTEGER
			MAX-ACCESS read-write
			STATUS current
			DESCRIPTION
				"Description."
			::= { wriPimv6InstanceEntry 18 }

    wriPimv6InstanceEmbeddedRp  OBJECT-TYPE
			SYNTAX INTEGER
			MAX-ACCESS read-write
			STATUS current
			DESCRIPTION
				"Description."
			::= { wriPimv6InstanceEntry 19 }  
			
     wriPimv6InstanceStateFlashInterval  OBJECT-TYPE
			SYNTAX INTEGER(1..65535)
			MAX-ACCESS read-write
			STATUS current
			DESCRIPTION
				"Description."
			::= { wriPimv6InstanceEntry 20 }
				
				
	   wriPimv6InstanceStateFlashRateLimit  OBJECT-TYPE
			SYNTAX INTEGER(1..65535)
			MAX-ACCESS read-write
			STATUS current
			DESCRIPTION
				"Description."
			::= { wriPimv6InstanceEntry 21 }
			
							                         				
	   wriPimv6InstanceStateFlashTtl OBJECT-TYPE
			SYNTAX INTEGER(1..255)
			MAX-ACCESS read-write
			STATUS current
			DESCRIPTION
				"Description."
			::= { wriPimv6InstanceEntry 22 }
                  
       wriPimv6InstanceMode  OBJECT-TYPE
			SYNTAX INTEGER{sm(1),dm(2)}
			MAX-ACCESS read-only
			STATUS current
			DESCRIPTION
				"The instance mode of pimv6."
			::= { wriPimv6InstanceEntry 23 } 

		-- 1.3.6.1.4.1.3807.2.1620.2.2
		wriPimv6InterfaceTable OBJECT-TYPE
			SYNTAX SEQUENCE OF WriPimv6InterfaceEntry
			MAX-ACCESS not-accessible
			STATUS current
			DESCRIPTION
				"The (conceptual) table listing the router's PIM interfaces.
				IGMP and PIM are enabled on all interfaces listed in this
				table."
			::= { wriPimv6Tables 2 }

		
		-- 1.3.6.1.4.1.3807.2.1620.2.2.1
		wriPimv6InterfaceEntry OBJECT-TYPE
			SYNTAX WriPimv6InterfaceEntry       
			MAX-ACCESS not-accessible
			STATUS current
			DESCRIPTION
				"An entry (conceptual row) in the pimInterfaceTable."
			INDEX { wriPimv6InterfaceIfIndex }
			::= { wriPimv6InterfaceTable 1 }

		
		WriPimv6InterfaceEntry ::=
			SEQUENCE { 
				wriPimv6InterfaceIfIndex
					Integer32,
				wriPimv6InterfaceName
					OCTET STRING,
				wriPimv6InterfaceLocalOverrideTime
					INTEGER,
				wriPimv6InterfaceLanPruneDelayTime
					INTEGER,
				wriPimv6InterfaceAddress
					Ipv6Address,
				wriPimv6InterfaceNetMask
					INTEGER,
				wriPimv6InterfaceSMMode
					INTEGER,    
				wriPimv6InterfaceDMMode
					INTEGER,	
				wriPimv6InterfaceGenerationId
					Integer32,
				wriPimv6InterfaceDR
					Ipv6Address,
				wriPimv6InterfaceDRPriority
					Integer32,
				wriPimv6InterfaceHelloInterval
					Integer32,
				wriPimv6InterfaceState
					INTEGER,
				wriPimv6InterfaceJoinPruneInterval
					Integer32,
				wriPimv6InterfaceCBSRPreference
					Integer32,
				wriPimv6InterfaceLocalDRPriority
					Integer32,
				wriPimv6InterfaceDRFlag
					INTEGER,
				wriPimv6InterfaceTimerFlags
					INTEGER,
				wriPimv6InterfaceNeighborCnt
					INTEGER,
				wriPimv6InterfaceLocalPruneDelay
					INTEGER,
				wriPimv6InterfaceOverrideInterval
					INTEGER,
				wriPimv6InterfaceDomainBorder
					TruthValue,	
				wriPimv6InterfaceHelloTimer
					INTEGER,
				wriPimv6InterfaceMldTimer
					INTEGER,	
				wriPimv6InterfaceJoinPruneTimer
					INTEGER,
				wriPimv6InterfaceNbrListCount
				    Gauge32,
				wriPimv6InterfaceMNbrListCount
				    Gauge32,
				wriPimv6InterfaceLinkState
				    INTEGER,
				wriPimv6InterfaceInBadPacket
				    Counter32,
				wriPimv6InterfaceInPacket
				    Counter32, 
				wriPimv6InterfaceOutPacket
				    Counter32, 
				wriPimv6InterfaceJoinPruneInPacket
				    Counter32,  
				wriPimv6InterfaceJoinPruneOutPacket
				    Counter32,
				wriPimv6InterfaceLanDelayEnabled
					TruthValue,
				wriPimv6InterfacePruneDelay
					INTEGER,  
				wriPimv6InterfaceStateFlashCapable
					INTEGER,
				wriPimv6InterfaceGraftRetryInterval
					INTEGER		
			}			
		-- 1.3.6.1.4.1.3807.2.1620.2.2.1.1
		wriPimv6InterfaceIfIndex OBJECT-TYPE
			SYNTAX Integer32 (1..65535)
			MAX-ACCESS read-only
			STATUS current
			DESCRIPTION
				"The ifIndex value of this PIM interface."
			::= { wriPimv6InterfaceEntry 1 }

		
		-- 1.3.6.1.4.1.3807.2.1620.2.2.1.2
		wriPimv6InterfaceName OBJECT-TYPE
			SYNTAX OCTET STRING
			MAX-ACCESS read-only
			STATUS current
			DESCRIPTION
				"The interface name."
			::= { wriPimv6InterfaceEntry 2 }

		
		-- 1.3.6.1.4.1.3807.2.1620.2.2.1.3
		wriPimv6InterfaceLocalOverrideTime OBJECT-TYPE
			SYNTAX INTEGER 
			MAX-ACCESS read-only
			STATUS current
			DESCRIPTION
				"."
			::= { wriPimv6InterfaceEntry 3 }

		
		-- 1.3.6.1.4.1.3807.2.1620.2.2.1.4
		wriPimv6InterfaceLanPruneDelayTime OBJECT-TYPE
			SYNTAX INTEGER 
			MAX-ACCESS read-write
			STATUS current
			DESCRIPTION
				""
			::= { wriPimv6InterfaceEntry 4 }

		
	  -- 1.3.6.1.4.1.3807.2.1620.2.2.1.5
		wriPimv6InterfaceAddress OBJECT-TYPE
			SYNTAX Ipv6Address
			MAX-ACCESS read-only
			STATUS current
			DESCRIPTION
				"The IP address of the PIM interface."
			::= { wriPimv6InterfaceEntry 5 }

		
		-- 1.3.6.1.4.1.3807.2.1620.2.2.1.6
		wriPimv6InterfaceNetMask OBJECT-TYPE
			SYNTAX INTEGER
			MAX-ACCESS read-only
			STATUS current
			DESCRIPTION
				"The network mask for the IP address of the PIM interface."
			::= { wriPimv6InterfaceEntry 6 }

		
		-- 1.3.6.1.4.1.3807.2.1620.2.2.1.7
		wriPimv6InterfaceSMMode OBJECT-TYPE
			SYNTAX INTEGER
				{
				enable(1),	
				disable(2)				
				}
			MAX-ACCESS read-write
			STATUS current
			DESCRIPTION
				"The configured mode sparse of this PIM interface."
			::= { wriPimv6InterfaceEntry 7 }

		-- 1.3.6.1.4.1.3807.2.1620.2.2.1.8	
		wriPimv6InterfaceDMMode   OBJECT-TYPE
			SYNTAX INTEGER
				{
				enable(1),	
				disable(2)				
				}
			MAX-ACCESS read-write
			STATUS current
			DESCRIPTION
				"The configured mode Dense of this PIM interface."
			::= { wriPimv6InterfaceEntry 8 }
		
		-- 1.3.6.1.4.1.3807.2.1620.2.2.1.9
		wriPimv6InterfaceGenerationId OBJECT-TYPE
			SYNTAX Integer32
			MAX-ACCESS read-only
			STATUS current
			DESCRIPTION
				"The Generation identifier of this interface. This is used to inform
				neighbour routers to quickly detect the change of itself"
			::= { wriPimv6InterfaceEntry 9 }

		
		-- 1.3.6.1.4.1.3807.2.1620.2.2.1.10
		wriPimv6InterfaceDR OBJECT-TYPE
			SYNTAX Ipv6Address
			MAX-ACCESS read-only
			STATUS current
			DESCRIPTION
				"The Designated Router on this PIM interface.  For point-to-
				point interfaces, this object has the value 0.0.0.0."
			::= { wriPimv6InterfaceEntry 10 }

		
		-- 1.3.6.1.4.1.3807.2.1620.2.2.1.11
		wriPimv6InterfaceDRPriority OBJECT-TYPE
			SYNTAX Integer32
			MAX-ACCESS read-only
			STATUS current
			DESCRIPTION
				"The priority of the DR on this interface. "
			::= { wriPimv6InterfaceEntry 11 }

		
		-- 1.3.6.1.4.1.3807.2.1620.2.2.1.12
		wriPimv6InterfaceHelloInterval OBJECT-TYPE
			SYNTAX Integer32
			UNITS "seconds"
			MAX-ACCESS read-create
			STATUS current
			DESCRIPTION
				"The frequency at which PIM Hello messages are transmitted
				on this interface."
			DEFVAL { 30 }
			::= { wriPimv6InterfaceEntry 12 }

		
		-- 1.3.6.1.4.1.3807.2.1620.2.2.1.13
		wriPimv6InterfaceState OBJECT-TYPE
			SYNTAX INTEGER
				{
				enable(1),	
				disable(2)				
				}
			MAX-ACCESS read-only
			STATUS current
			DESCRIPTION
				"The state of this this interface"
			::= { wriPimv6InterfaceEntry 13 }

		
		-- 1.3.6.1.4.1.3807.2.1620.2.2.1.14
		wriPimv6InterfaceJoinPruneInterval OBJECT-TYPE
			SYNTAX Integer32
			UNITS "seconds"
			MAX-ACCESS read-create
			STATUS current
			DESCRIPTION
				"The frequency at which PIM Join/Prune messages are
				transmitted on this PIM interface.	The default value of
				this object is the pimJoinPruneInterval."
			DEFVAL { 60 }
			::= { wriPimv6InterfaceEntry 14 }

		
		-- 1.3.6.1.4.1.3807.2.1620.2.2.1.15
		wriPimv6InterfaceCBSRPreference OBJECT-TYPE
			SYNTAX Integer32 (-1..255)
			MAX-ACCESS read-create
			STATUS current
			DESCRIPTION
				"The preference value for the local interface as a candidate
				bootstrap router.  The value of -1 is used to indicate that
				the local interface is not a candidate BSR interface."
			DEFVAL { -1 }
			::= { wriPimv6InterfaceEntry 15 }

		
		-- 1.3.6.1.4.1.3807.2.1620.2.2.1.16
		wriPimv6InterfaceLocalDRPriority OBJECT-TYPE
			SYNTAX Integer32
			MAX-ACCESS read-create
			STATUS current
			DESCRIPTION
				"The DR priority of this interface. "
			::= { wriPimv6InterfaceEntry 16 }

		
		-- 1.3.6.1.4.1.3807.2.1620.2.2.1.17
		wriPimv6InterfaceDRFlag OBJECT-TYPE
			SYNTAX INTEGER
			MAX-ACCESS read-only
			STATUS current
			DESCRIPTION
				"The flag indicate wether the interface is DR or not.
				1  PIM_LOCAL_RTR_IS_DR
				2  PIM_LOCAL_RTR_IS_NON_DR
				3  PIM_DR_TRANSITION_TO_NONDR
				4  PIM_NONDR_TRANSITION_TO_DR"
			::= { wriPimv6InterfaceEntry 17 }

		
		-- 1.3.6.1.4.1.3807.2.1620.2.2.1.18
		wriPimv6InterfaceTimerFlags OBJECT-TYPE
			SYNTAX INTEGER
			MAX-ACCESS read-only
			STATUS current
			DESCRIPTION
				"This object describes PIM-specific Timer flags related to a
				Interface. Bits setting in this objects correspond to the 
				       starting of a interface specific timer. The bits corresponding
				       to the timers are as follows:
				       0 - Hello Timer, 1 - JP Timer.
				       For example, If this object value is 3 (0000 0011), then
				       it means that Hello timer and JP timer are running.
				This is for both SM and DM. The bits which are not applicable 
				       to DM/SM will be filled with 0 "
			::= { wriPimv6InterfaceEntry 18 }

		
		-- 1.3.6.1.4.1.3807.2.1620.2.2.1.19
		wriPimv6InterfaceNeighborCnt OBJECT-TYPE
			SYNTAX INTEGER
			MAX-ACCESS read-only
			STATUS current
			DESCRIPTION
				"This object indicates how many pim neighbor on this interface. "
			::= { wriPimv6InterfaceEntry 19 }

		
		-- 1.3.6.1.4.1.3807.2.1620.2.2.1.20
		wriPimv6InterfaceLocalPruneDelay OBJECT-TYPE
			SYNTAX INTEGER (0..65535)
			MAX-ACCESS read-write
			STATUS current
			DESCRIPTION
				"Description."
			::= { wriPimv6InterfaceEntry 20 }

		
		-- 1.3.6.1.4.1.3807.2.1620.2.2.1.21
		wriPimv6InterfaceOverrideInterval OBJECT-TYPE
			SYNTAX INTEGER (0..65535)
			MAX-ACCESS read-write
			STATUS current
			DESCRIPTION
				"Description."
			::= { wriPimv6InterfaceEntry 21 }

		
		-- 1.3.6.1.4.1.3807.2.1620.2.2.1.22
		wriPimv6InterfaceDomainBorder OBJECT-TYPE
			SYNTAX TruthValue
			MAX-ACCESS read-write
			STATUS current
			DESCRIPTION
				"Description."
			::= { wriPimv6InterfaceEntry 22 }
                                           
		-- 1.3.6.1.4.1.3807.2.1620.2.2.1.23                                           
        wriPimv6InterfaceHelloTimer OBJECT-TYPE
			SYNTAX INTEGER
			MAX-ACCESS read-write
			STATUS current
			DESCRIPTION
				"Description."
			::= { wriPimv6InterfaceEntry 23 }
       
       -- 1.3.6.1.4.1.3807.2.1620.2.2.1.24
        wriPimv6InterfaceMldTimer OBJECT-TYPE
			SYNTAX INTEGER
			MAX-ACCESS read-write
			STATUS current
			DESCRIPTION
				"Description."
			::= { wriPimv6InterfaceEntry 24 }
			
       -- 1.3.6.1.4.1.3807.2.1620.2.2.1.25
        wriPimv6InterfaceJoinPruneTimer  OBJECT-TYPE
			SYNTAX INTEGER
			MAX-ACCESS read-write
			STATUS current
			DESCRIPTION
				"Description."
			::= { wriPimv6InterfaceEntry 25 }
			
        -- 1.3.6.1.4.1.3807.2.1620.2.2.1.26
		wriPimv6InterfaceNbrListCount  OBJECT-TYPE
			SYNTAX Gauge32
			MAX-ACCESS read-only
			STATUS current
			DESCRIPTION
				"Description."
			::= { wriPimv6InterfaceEntry 26 }
       
       -- 1.3.6.1.4.1.3807.2.1620.2.2.1.27   
        wriPimv6InterfaceMNbrListCount OBJECT-TYPE
			SYNTAX Gauge32
			MAX-ACCESS read-only
			STATUS current
			DESCRIPTION
				"Description."
			::= { wriPimv6InterfaceEntry 27 }

		-- 1.3.6.1.4.1.3807.2.1620.2.2.1.28			
		wriPimv6InterfaceLinkState OBJECT-TYPE
			SYNTAX INTEGER
			MAX-ACCESS read-only
			STATUS current
			DESCRIPTION
				"Description."
			::= { wriPimv6InterfaceEntry 28 }	
			                               
		-- 1.3.6.1.4.1.3807.2.1620.2.2.1.29	                               
		wriPimv6InterfaceInBadPacket 	OBJECT-TYPE
			SYNTAX Counter32
			MAX-ACCESS read-only
			STATUS current
			DESCRIPTION
				"Description."
			::= { wriPimv6InterfaceEntry 29 }			
			                               
		-- 1.3.6.1.4.1.3807.2.1620.2.2.1.30	                               
	   wriPimv6InterfaceInPacket  OBJECT-TYPE
			SYNTAX Counter32
			MAX-ACCESS read-only
			STATUS current
			DESCRIPTION
				"Description."
			::= { wriPimv6InterfaceEntry 30 }	 
			
	                                       
	    -- 1.3.6.1.4.1.3807.2.1620.2.2.1.31                                   
		wriPimv6InterfaceOutPacket OBJECT-TYPE
			SYNTAX Counter32
			MAX-ACCESS read-only
			STATUS current
			DESCRIPTION
				"Description."
			::= { wriPimv6InterfaceEntry 31 }	 	
		
		
		-- 1.3.6.1.4.1.3807.2.1620.2.2.1.32     
		wriPimv6InterfaceJoinPruneInPacket OBJECT-TYPE
			SYNTAX Counter32
			MAX-ACCESS read-only
			STATUS current
			DESCRIPTION
				"Description."
			::= { wriPimv6InterfaceEntry 32 }	     
		                                   
		                                   
		-- 1.3.6.1.4.1.3807.2.1620.2.2.1.33                                      
		wriPimv6InterfaceJoinPruneOutPacket  OBJECT-TYPE
			SYNTAX Counter32
			MAX-ACCESS read-only
			STATUS current
			DESCRIPTION
				"Description."
			::= { wriPimv6InterfaceEntry 33 }
		                                   
		                                   
		-- 1.3.6.1.4.1.3807.2.1620.2.2.1.34                                   
		wriPimv6InterfaceLanDelayEnabled OBJECT-TYPE
			SYNTAX TruthValue
			MAX-ACCESS read-only
			STATUS current
			DESCRIPTION
				"Description."
			::= { wriPimv6InterfaceEntry 34 }
                                           
                                           
      -- 1.3.6.1.4.1.3807.2.1620.2.2.1.35                                     
	  wriPimv6InterfacePruneDelay	 OBJECT-TYPE
			SYNTAX INTEGER
			MAX-ACCESS read-only
			STATUS current
			DESCRIPTION
				"Description."
			::= { wriPimv6InterfaceEntry 35 }
      
     -- 1.3.6.1.4.1.3807.2.1620.2.2.1.36 
      wriPimv6InterfaceStateFlashCapable OBJECT-TYPE
			SYNTAX INTEGER{ enable(1),disable(2)}
			MAX-ACCESS read-write
			STATUS current
			DESCRIPTION
				"Description."
			::= { wriPimv6InterfaceEntry 36 }
					
					
	  -- 1.3.6.1.4.1.3807.2.1620.2.2.1.37 				
	   wriPimv6InterfaceGraftRetryInterval OBJECT-TYPE
			SYNTAX INTEGER(1..65535)
			MAX-ACCESS read-write
			STATUS current
			DESCRIPTION
				"Description."
			::= { wriPimv6InterfaceEntry 37 }
	                              
		                                      
		-- 1.3.6.1.4.1.3807.2.1620.2.3
		wriPimv6NeighborTable OBJECT-TYPE
			SYNTAX SEQUENCE OF WriPimv6NeighborEntry
			MAX-ACCESS not-accessible
			STATUS current
			DESCRIPTION
				"The (conceptual) table listing the router's PIM neighbors."
			::= { wriPimv6Tables 3 }

		
		-- 1.3.6.1.4.1.3807.2.1620.2.3.1
		wriPimv6NeighborEntry OBJECT-TYPE
			SYNTAX WriPimv6NeighborEntry
			MAX-ACCESS not-accessible
			STATUS current
			DESCRIPTION
				"An entry (conceptual row) in the pimNeighborTable."
			INDEX { wriPimv6NeighborIfIndex,wriPimv6NeighborAddress }
			::= { wriPimv6NeighborTable 1 }

		
		WriPimv6NeighborEntry ::=
			SEQUENCE { 
				wriPimv6NeighborAddress
					Ipv6Address,
				wriPimv6NeighborIfIndex
					INTEGER,
				wriPimv6NeighborUpTime
					Unsigned32,
				wriPimv6NeighborExpiryTime
					Unsigned32,
				wriPimv6NeighborMode
					INTEGER,
				wriPimv6NeighborGenerationId
					Integer32,
				wriPimv6NeighborDRPriority
					Integer32,
				wriPimv6NeighborDRState
					INTEGER,
				wriPimv6NeighborTBit
					TruthValue,  
				wriPimv6NeighborLanPruneDelayPresent	
		            TruthValue,
		        wriPimv6NeighborPropagationDelay
		        	 INTEGER,
		        wriPimv6NeighborOverrideInterval
		           	 INTEGER,  
		        wriPimv6NeighborJoinPruneCount
		        	 Counter32  	 		           	    				
			 }

	   -- 1.3.6.1.4.1.3807.2.1620.2.3.1.1
			wriPimv6NeighborAddress OBJECT-TYPE
			SYNTAX Ipv6Address
			MAX-ACCESS read-only
			STATUS current
			DESCRIPTION
				"The IP address of the PIM neighbor for which this entry
				contains information."
			::= { wriPimv6NeighborEntry 1 }

		
	   -- 1.3.6.1.4.1.3807.2.1620.2.3.1.2
		wriPimv6NeighborIfIndex OBJECT-TYPE
			SYNTAX INTEGER
			MAX-ACCESS read-only
			STATUS current
			DESCRIPTION
				"The value of ifIndex for the interface used to reach this
				PIM neighbor."
			::= { wriPimv6NeighborEntry 2 }

		
		-- 1.3.6.1.4.1.3807.2.1620.2.3.1.3
		wriPimv6NeighborUpTime OBJECT-TYPE
			SYNTAX Unsigned32
			MAX-ACCESS read-only
			STATUS current
			DESCRIPTION
				"The time since this PIM neighbor (last) became a neighbor
				of the local router."
			::= { wriPimv6NeighborEntry 3 }

		
		-- 1.3.6.1.4.1.3807.2.1620.2.3.1.4
		wriPimv6NeighborExpiryTime OBJECT-TYPE
			SYNTAX Unsigned32
			MAX-ACCESS read-only
			STATUS current
			DESCRIPTION
				"The minimum time remaining before this PIM neighbor will be
				aged out."
			::= { wriPimv6NeighborEntry 4 }

		
		-- 1.3.6.1.4.1.3807.2.1620.2.3.1.5
		wriPimv6NeighborMode OBJECT-TYPE
			SYNTAX INTEGER
				{ 
				sparse(1),
				dense(2)
				}
			MAX-ACCESS read-only
			STATUS deprecated
			DESCRIPTION
				"The active PIM mode of this neighbor.  This object is
				deprecated for PIMv2 routers since all neighbors on the
				interface must be either dense or sparse as determined by
				the protocol running on the interface."
			::= { wriPimv6NeighborEntry 5 }

		
		-- 1.3.6.1.4.1.3807.2.1620.2.3.1.6
		wriPimv6NeighborGenerationId OBJECT-TYPE
			SYNTAX Integer32
			MAX-ACCESS read-only
			STATUS current
			DESCRIPTION
				"The Generation identifier of the router. This is used by
				neighbour routers to quickly detect router reboot and synchronize
				RP-Set information and forwarding states by triggering Bootstrap
				and Join/Prune messages to the rebooted router"
			::= { wriPimv6NeighborEntry 6 }

		
		-- 1.3.6.1.4.1.3807.2.1620.2.3.1.7
		wriPimv6NeighborDRPriority OBJECT-TYPE
			SYNTAX Integer32
			MAX-ACCESS read-only
			STATUS current
			DESCRIPTION
				"The DR priority used to elect DR of the neighbor"
			::= { wriPimv6NeighborEntry 7 }

		
		-- 1.3.6.1.4.1.3807.2.1620.2.3.1.8
		wriPimv6NeighborDRState OBJECT-TYPE
			SYNTAX INTEGER
				{
				yes(1),
				no(2)
				}
			MAX-ACCESS read-only
			STATUS current
			DESCRIPTION
				"It to indicate whether the neighbor is DR or not."
			::= { wriPimv6NeighborEntry 8 }

		-- 1.3.6.1.4.1.3807.2.1620.2.3.1.9
	    wriPimv6NeighborTBit  OBJECT-TYPE
	    	 SYNTAX     TruthValue
    		 MAX-ACCESS read-only
    		 STATUS     current
  			 DESCRIPTION
           		 "Evaluates to TRUE if this neighbor is using the DR Priority
            	 option."
    		 ::= { wriPimv6NeighborEntry 9 }    
    		 
        -- 1.3.6.1.4.1.3807.2.1620.2.3.1.10
		wriPimv6NeighborLanPruneDelayPresent OBJECT-TYPE
    		SYNTAX     TruthValue
   			MAX-ACCESS read-only
    		STATUS     current
    		DESCRIPTION
            	"Evaluates to TRUE if this neighbor is using the LAN Prune
           		 Delay option."
   			 ::= { wriPimv6NeighborEntry 10 }
	                                          
	    -- 1.3.6.1.4.1.3807.2.1620.2.3.1.11                                      
		wriPimv6NeighborPropagationDelay  OBJECT-TYPE
			SYNTAX INTEGER
			MAX-ACCESS read-only
			STATUS current
			DESCRIPTION
				""
			::= { wriPimv6NeighborEntry 11 }
       
       	-- 1.3.6.1.4.1.3807.2.1620.2.3.1.12
		wriPimv6NeighborOverrideInterval  OBJECT-TYPE
    		SYNTAX     INTEGER (0..65535)
    		MAX-ACCESS read-only
    		STATUS     current
    		DESCRIPTION
            	"The value of the Override_Interval field of the LAN Prune
            	Delay option received from this neighbor.  This object is
            	always zero if pimNeighborLanPruneDelayPresent is FALSE."
    		::= { wriPimv6NeighborEntry 12 }
        
        -- 1.3.6.1.4.1.3807.2.1620.2.3.1.13
		wriPimv6NeighborJoinPruneCount OBJECT-TYPE
			SYNTAX Counter32
			MAX-ACCESS read-only
			STATUS current
			DESCRIPTION
				""
			::= { wriPimv6NeighborEntry 13 }

		
		-- 1.3.6.1.4.1.3807.2.1620.2.4
		wriPimv6IpMRouteTable OBJECT-TYPE
			SYNTAX SEQUENCE OF WriPimv6IpMRouteEntry
			MAX-ACCESS not-accessible
			STATUS current
			DESCRIPTION
				"The (conceptual) table listing PIM multicast routing information"
			::= { wriPimv6Tables 4 }

		
		-- 1.3.6.1.4.1.3807.2.1620.2.4.1
		wriPimv6IpMRouteEntry OBJECT-TYPE
			SYNTAX WriPimv6IpMRouteEntry
			MAX-ACCESS not-accessible
			STATUS current
			DESCRIPTION
				"An entry (conceptual row) in the pimIpMRouteTable.	 There
				is one entry for each incoming interface running PIM"
			INDEX { wriPimv6IpMRouteInstance,wriPimv6IpMRouteType,wriPimv6IpMRouteGroup, wriPimv6IpMRouteSource, wriPimv6IpMRouteSourceMask }
			::= { wriPimv6IpMRouteTable 1 }

		
		WriPimv6IpMRouteEntry ::=
			SEQUENCE {  
				wriPimv6IpMRouteInstance	
					INTEGER,
				wriPimv6IpMRouteType
					INTEGER,
	         	wriPimv6IpMRouteGroup
					Ipv6Address,
				wriPimv6IpMRouteSource
					Ipv6Address,
				wriPimv6IpMRouteSourceMask
					INTEGER,
				wriPimv6IpMRouteUpstreamNeighbor
					Ipv6Address,
				wriPimv6IpMRouteInIfIndex
					INTEGER,
				wriPimv6IpMRouteUpTime
					Unsigned32,
				wriPimv6IpMRouteExpiryTime
					Unsigned32,
				wriPimv6IpMRouteFwdPkts
					Counter32,
				wriPimv6IpMRouteAssertTimerExpiryTime
					Unsigned32,
				wriPimv6IpMRouteAssertMetric
					Integer32,
				wriPimv6IpMRouteAssertMetricPref
					Integer32,
				wriPimv6IpMRouteAssertRPTBit
					TruthValue,
				wriPimv6IpMRouteTimerFlags
					INTEGER,
				wriPimv6IpMRouteFlags
					INTEGER,
				wriPimv6IpMRouteAcceptDataStatus
					Integer32,
				wriPimv6IpMRouteRpfNbrAddress
				   	Ipv6Address,
				wriPimv6IpMRouteRegstOptLimit
				    INTEGER,
				wriPimv6IpMRoutePendingJoinFlag
				    INTEGER,
				wriPimv6IpMRouteJpSupressTimer
				    INTEGER,
				wriPimv6IpMRouteRegSupressTimer
				    INTEGER,     
				wriPimv6IpMRouteRouteTimer
					INTEGER,
				wriPimv6IpMRouteAssertTimer
					INTEGER,
				wriPimv6IpMRouteJoinDelayTimer
					INTEGER,
				wriPimv6IpMRouteAssertLimitTimer
					INTEGER,
				wriPimv6IpMRouteOutIfNumber
					INTEGER,
				wriPimv6IpMRouteState
					INTEGER	
		}    
		
		-- 1.3.6.1.4.1.3807.2.1620.2.4.1.1
       	wriPimv6IpMRouteInstance  OBJECT-TYPE
			SYNTAX INTEGER
			MAX-ACCESS read-only
			STATUS current
			DESCRIPTION
				"vpn instance id"
			::= { wriPimv6IpMRouteEntry 1 }

		-- 1.3.6.1.4.1.3807.2.1620.2.4.1.2
		wriPimv6IpMRouteType OBJECT-TYPE
			SYNTAX INTEGER
			MAX-ACCESS read-only
			STATUS current
			DESCRIPTION
				"This object describes the route entry type,such as SG,*G.
				1     (S,G)  Entry 
				2     (S,G) RPT Bit Entry
				3     (*,G) entry
				4     (*,*,RP) entry
				5     Invalid entry"
			::= { wriPimv6IpMRouteEntry 2 }

		
		-- 1.3.6.1.4.1.3807.2.1620.2.4.1.3
		wriPimv6IpMRouteGroup OBJECT-TYPE
			SYNTAX Ipv6Address
			MAX-ACCESS read-only
			STATUS current
			DESCRIPTION
				"The IP multicast group address for which this entry
				contains multicast routing information."
			::= { wriPimv6IpMRouteEntry 3 }

		
		-- 1.3.6.1.4.1.3807.2.1620.2.4.1.4
		wriPimv6IpMRouteSource OBJECT-TYPE
			SYNTAX Ipv6Address
			MAX-ACCESS read-only
			STATUS current
			DESCRIPTION
				"The network address which when combined with the
				corresponding value of ipMRouteSourceMask identifies the
				sources for which this entry contains multicast routing
				information."
			::= { wriPimv6IpMRouteEntry 4 }

		
		-- 1.3.6.1.4.1.3807.2.1620.2.4.1.5
		wriPimv6IpMRouteSourceMask OBJECT-TYPE
			SYNTAX INTEGER
			MAX-ACCESS read-only
			STATUS current
			DESCRIPTION
				"The network mask which when combined with the corresponding
				value of ipMRouteSource identifies the sources for which
				this entry contains multicast routing information."
			::= { wriPimv6IpMRouteEntry 5 }

		
		-- 1.3.6.1.4.1.3807.2.1620.2.4.1.6
		wriPimv6IpMRouteUpstreamNeighbor OBJECT-TYPE
			SYNTAX Ipv6Address
			MAX-ACCESS read-only
			STATUS current
			DESCRIPTION
				"The address of the upstream neighbor (e.g., RPF neighbor)
				from which IP datagrams from these sources to this multicast
				address are received."
			::= { wriPimv6IpMRouteEntry 6 }

		
		-- 1.3.6.1.4.1.3807.2.1620.2.4.1.7
		wriPimv6IpMRouteInIfIndex OBJECT-TYPE
			SYNTAX INTEGER
			MAX-ACCESS read-only
			STATUS current
			DESCRIPTION
				"The value of ifIndex for the interface on which IP
				datagrams sent by these sources to this multicast address
				are received."
			::= { wriPimv6IpMRouteEntry 7 }

		
		-- 1.3.6.1.4.1.3807.2.1620.2.4.1.8
		wriPimv6IpMRouteUpTime OBJECT-TYPE
			SYNTAX Unsigned32
			MAX-ACCESS read-only
			STATUS current
			DESCRIPTION
				"The time since the multicast routing information
				represented by this entry was learned by the router."
			::= { wriPimv6IpMRouteEntry 8 }

		
		-- 1.3.6.1.4.1.3807.2.1620.2.4.1.9
		wriPimv6IpMRouteExpiryTime OBJECT-TYPE
			SYNTAX Unsigned32
			MAX-ACCESS read-only
			STATUS current
			DESCRIPTION
				"The minimum amount of time remaining before this entry will
				be aged out.  The value 0 indicates that the entry is not
				subject to aging."
			::= { wriPimv6IpMRouteEntry 9 }

		
		-- 1.3.6.1.4.1.3807.2.1620.2.4.1.10
		wriPimv6IpMRouteFwdPkts OBJECT-TYPE
			SYNTAX Counter32
			MAX-ACCESS read-only
			STATUS current
			DESCRIPTION
				"The number of packets which this router has received from
				these sources and addressed to this multicast group
				address."
			::= { wriPimv6IpMRouteEntry 10 }

		
		-- 1.3.6.1.4.1.3807.2.1620.2.4.1.11
		wriPimv6IpMRouteAssertTimerExpiryTime OBJECT-TYPE
			SYNTAX Unsigned32
			MAX-ACCESS read-only
			STATUS current
			DESCRIPTION
				"The time remaining before the router changes its upstream
				neighbor back to its RPF neighbor.	This timer is called the
				Assert timer in the PIM Sparse and Dense mode specification.
				A value of 0 indicates that no Assert has changed the
				upstream neighbor away from the RPF neighbor."
			::= { wriPimv6IpMRouteEntry 11 }

		
		-- 1.3.6.1.4.1.3807.2.1620.2.4.1.12
		wriPimv6IpMRouteAssertMetric OBJECT-TYPE
			SYNTAX Integer32
			MAX-ACCESS read-only
			STATUS current
			DESCRIPTION
				"The metric advertised by the assert winner on the upstream
				interface, or 0 if no such assert is in received."
			::= { wriPimv6IpMRouteEntry 12 }

		
		-- 1.3.6.1.4.1.3807.2.1620.2.4.1.13
		wriPimv6IpMRouteAssertMetricPref OBJECT-TYPE
			SYNTAX Integer32
			MAX-ACCESS read-only
			STATUS current
			DESCRIPTION
				"The preference advertised by the assert winner on the
				upstream interface, or 0 if no such assert is in effect."
			::= { wriPimv6IpMRouteEntry 13 }

		
		-- 1.3.6.1.4.1.3807.2.1620.2.4.1.14
		wriPimv6IpMRouteAssertRPTBit OBJECT-TYPE
			SYNTAX TruthValue
			MAX-ACCESS read-only
			STATUS current
			DESCRIPTION
				"The value of the RPT-bit advertised by the assert winner on
				the upstream interface, or false if no such assert is in
				effect."
			::= { wriPimv6IpMRouteEntry 14 }

		
		-- 1.3.6.1.4.1.3807.2.1620.2.4.1.15
		wriPimv6IpMRouteTimerFlags OBJECT-TYPE
			SYNTAX INTEGER
			MAX-ACCESS read-only
			STATUS current
			DESCRIPTION
				"This object describes PIM-specific Timer flags related to a
				Multicast Route Entry. If the bit is 1 indicates that timer 
				       is started for that entry.  The bits corresponding to the 
				       timers are as follows:
				       0 - JP Suppression Timer, 1 - Oif Timer, 2 - Entry Timer,
				       3 - Reg Suppression Timer, 4 - Assert Timer, 
				       5 - RandomDelayJoin Timer.
				       For example, If this object value is 3 (0000 0011), then
				       it means that JPSuppression timer and  Oif timer are running.
				       This is for both SM and DM. The bits which are not applicable 
				       to DM/SM will be filled with 0 "
			::= { wriPimv6IpMRouteEntry 15 }

		
		-- 1.3.6.1.4.1.3807.2.1620.2.4.1.16
		wriPimv6IpMRouteFlags OBJECT-TYPE
			SYNTAX INTEGER
			MAX-ACCESS read-only
			STATUS current
			DESCRIPTION
				"This object describes PIM-specific flags related to a
				multicast state entry.  See the PIM Sparse Mode
				specification for the meaning of the RPT and SPT bits.
				0th bit set indicates RPT bit set
				   1st bit set indicates WC  bit set
				   2nd bit set indicates SPT bit set"
			::= { wriPimv6IpMRouteEntry 16 }

		
		-- 1.3.6.1.4.1.3807.2.1620.2.4.1.17
		wriPimv6IpMRouteAcceptDataStatus OBJECT-TYPE
			SYNTAX Integer32
			MAX-ACCESS read-write
			STATUS current
			DESCRIPTION
				"Description."
			::= { wriPimv6IpMRouteEntry 17 }

		-- 1.3.6.1.4.1.3807.2.1620.2.4.1.18
		wriPimv6IpMRouteRpfNbrAddress  OBJECT-TYPE
			SYNTAX Ipv6Address
			MAX-ACCESS read-only
			STATUS current
			DESCRIPTION
				"Description."
			::= { wriPimv6IpMRouteEntry 18 }

		
		-- 1.3.6.1.4.1.3807.2.1620.2.4.1.19		 
	    wriPimv6IpMRouteRegstOptLimit OBJECT-TYPE
			SYNTAX INTEGER
			MAX-ACCESS read-only
			STATUS current
			DESCRIPTION
				"Description."
			::= { wriPimv6IpMRouteEntry 19 }
                                           
        -- 1.3.6.1.4.1.3807.2.1620.2.4.1.20                                   
		wriPimv6IpMRoutePendingJoinFlag OBJECT-TYPE
			SYNTAX INTEGER
			MAX-ACCESS read-only
			STATUS current
			DESCRIPTION
				"Description."
			::= { wriPimv6IpMRouteEntry 20 }
			                               
		-- 1.3.6.1.4.1.3807.2.1620.2.4.1.21	                               
		wriPimv6IpMRouteJpSupressTimer OBJECT-TYPE
			SYNTAX INTEGER
			MAX-ACCESS read-only
			STATUS current
			DESCRIPTION
				"Description."
			::= { wriPimv6IpMRouteEntry 21 }
			                               
		-- 1.3.6.1.4.1.3807.2.1620.2.4.1.22	                               
		wriPimv6IpMRouteRegSupressTimer OBJECT-TYPE
			SYNTAX INTEGER
			MAX-ACCESS read-only
			STATUS current
			DESCRIPTION
				"Description."
			::= { wriPimv6IpMRouteEntry 22 }
			                               
		-- 1.3.6.1.4.1.3807.2.1620.2.4.1.23	                               
		wriPimv6IpMRouteRouteTimer  OBJECT-TYPE
			SYNTAX INTEGER
			MAX-ACCESS read-only
			STATUS current
			DESCRIPTION
				"Description."
			::= { wriPimv6IpMRouteEntry 23 }
			                               
		-- 1.3.6.1.4.1.3807.2.1620.2.4.1.24	                               
		wriPimv6IpMRouteAssertTimer  OBJECT-TYPE
			SYNTAX INTEGER
			MAX-ACCESS read-only
			STATUS current
			DESCRIPTION
				"Description."
			::= { wriPimv6IpMRouteEntry 24 }
			                               
			                               
		-- 1.3.6.1.4.1.3807.2.1620.2.4.1.25	                               
		wriPimv6IpMRouteJoinDelayTimer  OBJECT-TYPE
			SYNTAX INTEGER
			MAX-ACCESS read-only
			STATUS current
			DESCRIPTION
				"Description."
			::= { wriPimv6IpMRouteEntry 25 }
			                               
			                               
		-- 1.3.6.1.4.1.3807.2.1620.2.4.1.26	                               
		wriPimv6IpMRouteAssertLimitTimer  OBJECT-TYPE
			SYNTAX INTEGER
			MAX-ACCESS read-only
			STATUS current
			DESCRIPTION
				"Description."
			::= { wriPimv6IpMRouteEntry 26 }
			                               
		-- 1.3.6.1.4.1.3807.2.1620.2.4.1.27	                               
		wriPimv6IpMRouteOutIfNumber OBJECT-TYPE
			SYNTAX INTEGER
			MAX-ACCESS read-only
			STATUS current
			DESCRIPTION
				"Description."
			::= { wriPimv6IpMRouteEntry 27 }
					                       
					                       
		-- 1.3.6.1.4.1.3807.2.1620.2.4.1.28			                       
		wriPimv6IpMRouteState OBJECT-TYPE
			SYNTAX INTEGER
			MAX-ACCESS read-only
			STATUS current
			DESCRIPTION
				"This object describes the route entry state,such as forward.
				1    Forwarding State    
				   2    Null State          
				   3    Negative Cache State  "
			::= { wriPimv6IpMRouteEntry 28 }
	
		
		
		-- 1.3.6.1.4.1.3807.2.1620.2.5
		wriPimv6IpMRouteNextHopTable OBJECT-TYPE
			SYNTAX SEQUENCE OF WriPimv6IpMRouteNextHopEntry
			MAX-ACCESS not-accessible
			STATUS current
			DESCRIPTION
				"The (conceptual) table listing PIM information on the next hops
				on outgoing interfaces for forwarding multicast datagrams"
			::= { wriPimv6Tables 5 }

		
		-- 1.3.6.1.4.1.3807.2.1620.2.5.1
		wriPimv6IpMRouteNextHopEntry OBJECT-TYPE
			SYNTAX WriPimv6IpMRouteNextHopEntry
			MAX-ACCESS not-accessible
			STATUS current
			DESCRIPTION
				"An entry (conceptual row) in the pimIpMRouteNextHopTable.
				There is one entry per entry in the ipMRouteNextHopTable
				whose interface is running PIM and whose
				pimIpMRouteNextHopState is pruned(1)."                                                                                             
			INDEX { wriPimv6IpMRouteNextHopInstance,wriPimv6IpMRouteNextHopRouteType,wriPimv6IpMRouteNextHopGroup, wriPimv6IpMRouteNextHopSource,
					 wriPimv6IpMRouteNextHopSourceMask,wriPimv6IpMRouteNextHopOIfIndex, wriPimv6IpMRouteNextHopAddress}
			::= { wriPimv6IpMRouteNextHopTable 1 }

		
		WriPimv6IpMRouteNextHopEntry ::=
			SEQUENCE { 
				wriPimv6IpMRouteNextHopInstance
					INTEGER,
				wriPimv6IpMRouteNextHopRouteType
					INTEGER,		
				wriPimv6IpMRouteNextHopGroup
					Ipv6Address,
				wriPimv6IpMRouteNextHopSource
					Ipv6Address,
				wriPimv6IpMRouteNextHopSourceMask
					INTEGER,
				wriPimv6IpMRouteNextHopOIfIndex
					Integer32,
				wriPimv6IpMRouteNextHopAddress
					Ipv6Address,
				wriPimv6IpMRouteNextHopPruneReason
					INTEGER,
				wriPimv6IpMRouteNextHopOifState
					INTEGER,
				wriPimv6IpMRouteNextHopOifUpTime
					Integer32,
				wriPimv6IpMRouteNextHopOifExpiryTime
					Integer32,
				wriPimv6IpMRouteNextHopOifAsserWinnerFlag
					TruthValue,
				wriPimv6IpMRouteNextHopJoinReason
				   	 INTEGER,
				wriPimv6IpMRouteNextHopFirstUpTime
					 INTEGER,
				wriPimv6IpMRouteNextHopDelDelayTime
					 INTEGER,
				wriPimv6IpMRouteNextHopCurrentFwdState
				     INTEGER,  
				wriPimv6IpMRouteNextHopAssertStartExpireTime
				     INTEGER,
				wriPimv6IpMRouteNextHopAssertWinnerPref       
                     INTEGER,
                wriPimv6IpMRouteNextHopAssertWinnerMetric
                     INTEGER,      
				wriPimv6IpMRouteNextHopNbrPruneReason     	    	 
			         INTEGER,
			    wriPimv6IpMRouteNextHopAssertState
			    	 INTEGER,
			   wriPimv6IpMRouteNextHopNextHop
			    	 Ipv6Address
            }     
            
		-- 1.3.6.1.4.1.3807.2.1620.2.5.1.1
		wriPimv6IpMRouteNextHopInstance  OBJECT-TYPE
			SYNTAX INTEGER
			MAX-ACCESS read-only
			STATUS current
			DESCRIPTION
				"vpn instance id."
			::= { wriPimv6IpMRouteNextHopEntry 1 }
			
			
		-- 1.3.6.1.4.1.3807.2.1620.2.5.1.2
		wriPimv6IpMRouteNextHopRouteType   OBJECT-TYPE
			SYNTAX INTEGER
			MAX-ACCESS read-only
			STATUS current
			DESCRIPTION
				"route type."
			::= { wriPimv6IpMRouteNextHopEntry 2 }  
			
			
		-- 1.3.6.1.4.1.3807.2.1620.2.5.1.3
		wriPimv6IpMRouteNextHopGroup OBJECT-TYPE
			SYNTAX Ipv6Address
			MAX-ACCESS read-only
			STATUS current
			DESCRIPTION
				"The IP multicast group for which this entry specifies a
				next-hop on an outgoing interface."
			::= { wriPimv6IpMRouteNextHopEntry 3 }

		
		-- 1.3.6.1.4.1.3807.2.1620.2.5.1.4
		wriPimv6IpMRouteNextHopSource OBJECT-TYPE
			SYNTAX Ipv6Address
			MAX-ACCESS read-only
			STATUS current
			DESCRIPTION
				"The network address which when combined with the
				corresponding value of pimIpMRouteNextHopSourceMask identifies
				the sources for which this entry specifies a next-hop on an
				outgoing interface."
			::= { wriPimv6IpMRouteNextHopEntry 4 }

		
		-- 1.3.6.1.4.1.3807.2.1620.2.5.1.5
		wriPimv6IpMRouteNextHopSourceMask OBJECT-TYPE
			SYNTAX INTEGER
			MAX-ACCESS read-only
			STATUS current
			DESCRIPTION
				"The network mask which when combined with the corresponding
				value of pimIpMRouteNextHopSource identifies the sources for
				which this entry specifies a next-hop on an outgoing interface"
			::= { wriPimv6IpMRouteNextHopEntry 5 }

		
		-- 1.3.6.1.4.1.3807.2.1620.2.5.1.6
		wriPimv6IpMRouteNextHopOIfIndex OBJECT-TYPE
			SYNTAX Integer32 (1..65535)
			MAX-ACCESS read-only
			STATUS current
			DESCRIPTION
				"The ifIndex value of the interface for the outgoing
				interface for this next-hop."
			::= { wriPimv6IpMRouteNextHopEntry 6 }

		
		-- 1.3.6.1.4.1.3807.2.1620.2.5.1.7
		wriPimv6IpMRouteNextHopAddress OBJECT-TYPE
			SYNTAX Ipv6Address
			MAX-ACCESS read-only
			STATUS current
			DESCRIPTION
				"The address of the next-hop specific to this entry.  For
				most interfaces, this is identical to pimIpMRouteNextHopGroup.
				NBMA interfaces, however, may have multiple next-hop
				addresses out a single outgoing interface."
			::= { wriPimv6IpMRouteNextHopEntry 7 }

		
		-- 1.3.6.1.4.1.3807.2.1620.2.5.1.8
		wriPimv6IpMRouteNextHopPruneReason OBJECT-TYPE
			SYNTAX INTEGER
				{
				other(1),
				prune(2),
				assert(3),
				join(4)
				}
			MAX-ACCESS read-only
			STATUS current
			DESCRIPTION
				"This object indicates why the downstream interface was
				pruned, whether in response to a PIM prune message or due to
				PIM Assert processing."
			::= { wriPimv6IpMRouteNextHopEntry 8 }

		
		-- 1.3.6.1.4.1.3807.2.1620.2.5.1.9
		wriPimv6IpMRouteNextHopOifState OBJECT-TYPE
			SYNTAX INTEGER
				{
				pruned(1),
				forwarding(2)
				}
			MAX-ACCESS read-only
			STATUS current
			DESCRIPTION
				"This object indicates the state of the output interface ."
			::= { wriPimv6IpMRouteNextHopEntry 9 }

		
		-- 1.3.6.1.4.1.3807.2.1620.2.5.1.10
		wriPimv6IpMRouteNextHopOifUpTime OBJECT-TYPE
			SYNTAX Integer32
			MAX-ACCESS read-only
			STATUS current
			DESCRIPTION
				"This object indicates the time value since the interface become the 
				output interface of the entry."
			::= { wriPimv6IpMRouteNextHopEntry 10 }

		
		-- 1.3.6.1.4.1.3807.2.1620.2.5.1.11
		wriPimv6IpMRouteNextHopOifExpiryTime OBJECT-TYPE
			SYNTAX Integer32
			MAX-ACCESS read-only
			STATUS current
			DESCRIPTION
				"This object indicates the time value before the interface timeout."
			::= { wriPimv6IpMRouteNextHopEntry 11 }

		
		-- 1.3.6.1.4.1.3807.2.1620.2.5.1.12
		wriPimv6IpMRouteNextHopOifAsserWinnerFlag OBJECT-TYPE
			SYNTAX TruthValue
			MAX-ACCESS read-only
			STATUS current
			DESCRIPTION
				"This object indicates wether the interface is a winner of assert process."
			::= { wriPimv6IpMRouteNextHopEntry 12 }     
			
			
		-- 1.3.6.1.4.1.3807.2.1620.2.5.1.13	
		wriPimv6IpMRouteNextHopJoinReason  OBJECT-TYPE
			SYNTAX INTEGER
			MAX-ACCESS read-only
			STATUS current
			DESCRIPTION
				""
			::= { wriPimv6IpMRouteNextHopEntry 13 }    
			
			
		-- 1.3.6.1.4.1.3807.2.1620.2.5.1.14	
		wriPimv6IpMRouteNextHopFirstUpTime OBJECT-TYPE
			SYNTAX INTEGER
			MAX-ACCESS read-only
			STATUS current
			DESCRIPTION
				""
			::= { wriPimv6IpMRouteNextHopEntry 14} 
			                                         
			                                         
		-- 1.3.6.1.4.1.3807.2.1620.2.5.1.15	                                         
		wriPimv6IpMRouteNextHopDelDelayTime  OBJECT-TYPE
			SYNTAX INTEGER
			MAX-ACCESS read-only
			STATUS current
			DESCRIPTION
				""
			::= { wriPimv6IpMRouteNextHopEntry 15 }  
			
			
		-- 1.3.6.1.4.1.3807.2.1620.2.5.1.16	
		wriPimv6IpMRouteNextHopCurrentFwdState  OBJECT-TYPE
			SYNTAX INTEGER
			MAX-ACCESS read-only
			STATUS current
			DESCRIPTION
				""
			::= { wriPimv6IpMRouteNextHopEntry 16 } 
			
			                                      
		-- 1.3.6.1.4.1.3807.2.1620.2.5.1.17	                                      
		wriPimv6IpMRouteNextHopAssertStartExpireTime OBJECT-TYPE
			SYNTAX INTEGER
			MAX-ACCESS read-only
			STATUS current
			DESCRIPTION
				""
			::= { wriPimv6IpMRouteNextHopEntry 17 }    
			
			
		-- 1.3.6.1.4.1.3807.2.1620.2.5.1.18	
		wriPimv6IpMRouteNextHopAssertWinnerPref OBJECT-TYPE
			SYNTAX INTEGER
			MAX-ACCESS read-only
			STATUS current
			DESCRIPTION
				""
			::= { wriPimv6IpMRouteNextHopEntry 18 }    
			
			
		-- 1.3.6.1.4.1.3807.2.1620.2.5.1.19	      
        wriPimv6IpMRouteNextHopAssertWinnerMetric   OBJECT-TYPE
			SYNTAX INTEGER
			MAX-ACCESS read-only
			STATUS current
			DESCRIPTION
				""
			::= { wriPimv6IpMRouteNextHopEntry 19 }  
			
			
		-- 1.3.6.1.4.1.3807.2.1620.2.5.1.20	
		wriPimv6IpMRouteNextHopNbrPruneReason  OBJECT-TYPE
			SYNTAX INTEGER
			MAX-ACCESS read-only
			STATUS current
			DESCRIPTION
				""
			::= { wriPimv6IpMRouteNextHopEntry 20 }  
			
			
		-- 1.3.6.1.4.1.3807.2.1620.2.5.1.21	   	    	 
	    wriPimv6IpMRouteNextHopAssertState  OBJECT-TYPE
			SYNTAX INTEGER
			MAX-ACCESS read-only
			STATUS current
			DESCRIPTION
				""
			::= { wriPimv6IpMRouteNextHopEntry 21 }     
			
			
		-- 1.3.6.1.4.1.3807.2.1620.2.5.1.22	
        wriPimv6IpMRouteNextHopNextHop   OBJECT-TYPE
			SYNTAX Ipv6Address
			MAX-ACCESS read-only
			STATUS current
			DESCRIPTION
				""
			::= { wriPimv6IpMRouteNextHopEntry 22 } 
		
			

		
		-- 1.3.6.1.4.1.3807.2.1620.2.6
		wriPimv6RPSetTable OBJECT-TYPE
			SYNTAX SEQUENCE OF WriPimv6RPSetEntry
			MAX-ACCESS not-accessible
			STATUS current
			DESCRIPTION
				"The (conceptual) table listing PIM information for
				candidate Rendezvous Points (RPs) for IP multicast groups.
				When the local router is the BSR, this information is
				obtained from received Candidate-RP-Advertisements.	 When
				the local router is not the BSR, this information is
				obtained from received RP-Set messages."
			::= { wriPimv6Tables 6 }

		
		-- 1.3.6.1.4.1.3807.2.1620.2.6.1
		wriPimv6RPSetEntry OBJECT-TYPE
			SYNTAX WriPimv6RPSetEntry
			MAX-ACCESS not-accessible
			STATUS current
			DESCRIPTION
				"An entry (conceptual row) in the pimRPSetTable."
			INDEX { wriPimv6RPSetInstance, wriPimv6RPSetGroupAddress, wriPimv6RPSetGroupMask, wriPimv6RPSetAddress }
			::= { wriPimv6RPSetTable 1 }

		
		WriPimv6RPSetEntry ::=
			SEQUENCE {    
				wriPimv6RPSetInstance
					INTEGER,
				wriPimv6RPSetGroupAddress
					Ipv6Address,
				wriPimv6RPSetGroupMask
					INTEGER,
				wriPimv6RPSetAddress
					Ipv6Address,
				wriPimv6RPSetHoldTime
					Integer32,
				wriPimv6RPSetExpiryTime
					Unsigned32,
				wriPimv6RPSetBestRp
					Ipv6Address,
				wriPimv6RPSetPriority
					Integer32,
				wriPimv6RPSetStatus
					RowStatus,
				wriPimv6RPSetStaticState
					TruthValue	
			 }
        -- 1.3.6.1.4.1.3807.2.1620.2.6.1.1
       	wriPimv6RPSetInstance OBJECT-TYPE
			SYNTAX INTEGER
			MAX-ACCESS read-only
			STATUS current
			DESCRIPTION
				"Vpn instance id"
			::= { wriPimv6RPSetEntry 1 }
       	
		-- 1.3.6.1.4.1.3807.2.1620.2.6.1.2
		wriPimv6RPSetGroupAddress OBJECT-TYPE
			SYNTAX Ipv6Address
			MAX-ACCESS read-only
			STATUS current
			DESCRIPTION
				"The IP multicast group address which, when combined with
				pimRPSetGroupMask, gives the group prefix for which this
				entry contains information about the Candidate-RP."
			::= { wriPimv6RPSetEntry 2 }

		
		-- 1.3.6.1.4.1.3807.2.1620.2.6.1.3
		wriPimv6RPSetGroupMask OBJECT-TYPE
			SYNTAX INTEGER
			MAX-ACCESS read-only
			STATUS current
			DESCRIPTION
				"The multicast group address mask which, when combined with
				pimRPSetGroupAddress, gives the group prefix for which this
				entry contains information about the Candidate-RP."
			::= { wriPimv6RPSetEntry 3 }

		
		-- 1.3.6.1.4.1.3807.2.1620.2.6.1.4
		wriPimv6RPSetAddress OBJECT-TYPE
			SYNTAX Ipv6Address
			MAX-ACCESS read-only
			STATUS current
			DESCRIPTION
				"The IP address of the Candidate-RP."
			::= { wriPimv6RPSetEntry 4}

		
		-- 1.3.6.1.4.1.3807.2.1620.2.6.1.5
		wriPimv6RPSetHoldTime OBJECT-TYPE
			SYNTAX Integer32 (0..255)
			UNITS "seconds"
			MAX-ACCESS read-only
			STATUS current
			DESCRIPTION
				"The holdtime of a Candidate-RP.  If the local router is not
				the BSR, this value is 0."
			::= { wriPimv6RPSetEntry 5 }

		
		-- 1.3.6.1.4.1.3807.2.1620.2.6.1.6
		wriPimv6RPSetExpiryTime OBJECT-TYPE
			SYNTAX Unsigned32
			MAX-ACCESS read-only
			STATUS current
			DESCRIPTION
				"The minimum time remaining before the Candidate-RP will be
				declared down.  If the local router is not the BSR, this
				value is 0."
			::= { wriPimv6RPSetEntry 6 }

		
		-- 1.3.6.1.4.1.3807.2.1620.2.6.1.7
		wriPimv6RPSetBestRp OBJECT-TYPE
			SYNTAX Ipv6Address 
			MAX-ACCESS read-only
			STATUS current
			DESCRIPTION
				" ."
			::= { wriPimv6RPSetEntry 7}

         
		
		-- 1.3.6.1.4.1.3807.2.1620.2.6.1.8
		wriPimv6RPSetPriority OBJECT-TYPE
			SYNTAX Integer32 (1..255)
			MAX-ACCESS read-only
			STATUS current
			DESCRIPTION
				" The RP priority value used to select RP for a group."
			::= { wriPimv6RPSetEntry 8 }

		
		-- 1.3.6.1.4.1.3807.2.1620.2.6.1.9
		wriPimv6RPSetStatus OBJECT-TYPE
			SYNTAX RowStatus
			MAX-ACCESS read-create
			STATUS current
			DESCRIPTION
				"The status of this entry."
			::= { wriPimv6RPSetEntry 9 }
        
        -- 1.3.6.1.4.1.3807.2.1620.2.6.1.10            
		wriPimv6RPSetStaticState   OBJECT-TYPE
			SYNTAX TruthValue
			MAX-ACCESS read-create
			STATUS current
			DESCRIPTION
				"whether this entry is a Static."
			::= { wriPimv6RPSetEntry 10 }

		-- 1.3.6.1.4.1.3807.2.1620.2.7
		wriPimv6CandidateRPTable OBJECT-TYPE
			SYNTAX SEQUENCE OF WriPimv6CandidateRPEntry
			MAX-ACCESS not-accessible
			STATUS current
			DESCRIPTION
				"The (conceptual) table listing the IP multicast groups for
				which the local router is to advertise itself as a
				Candidate-RP when the value of pimComponentCRPHoldTime is
				non-zero.  If this table is empty, then the local router
				will advertise itself as a Candidate-RP for all groups
				(providing the value of pimComponentCRPHoldTime is non-
				zero)."
			::= { wriPimv6Tables 7 }

		
		-- 1.3.6.1.4.1.3807.2.1620.2.7.1
		wriPimv6CandidateRPEntry OBJECT-TYPE
			SYNTAX WriPimv6CandidateRPEntry
			MAX-ACCESS not-accessible
			STATUS current
			DESCRIPTION
				"An entry (conceptual row) in the pimCandidateRPTable."
			INDEX { wriPimv6CandidateInstance,wriPimv6CandidateRPGroupAddress, wriPimv6CandidateRPGroupMask }
			::= { wriPimv6CandidateRPTable 1 }

		
		WriPimv6CandidateRPEntry ::=
			SEQUENCE {  
				wriPimv6CandidateInstance
					INTEGER,
				wriPimv6CandidateRPGroupAddress
					Ipv6Address,
				wriPimv6CandidateRPGroupMask
					INTEGER,
				wriPimv6CandidateRPAddress
					Ipv6Address,
				wriPimv6CandidateRPRowStatus
					RowStatus,
				wriPimv6CandidateRPHoldTime
					INTEGER,
				wriPimv6CandidateRPPriority
					INTEGER,
				wriPimv6CandidateRPNextAdvTime
					Unsigned32
			 }
         
        wriPimv6CandidateInstance  OBJECT-TYPE
			SYNTAX INTEGER
			MAX-ACCESS read-only
			STATUS current
			DESCRIPTION
				"vpn instace id"
			::= { wriPimv6CandidateRPEntry 1 }


		-- 1.3.6.1.4.1.3807.2.1620.2.7.1.1
		wriPimv6CandidateRPGroupAddress OBJECT-TYPE
			SYNTAX Ipv6Address
			MAX-ACCESS read-only
			STATUS current
			DESCRIPTION
				"The IP multicast group address which, when combined with
				pimCandidateRPGroupMask, identifies a group prefix for which
				the local router will advertise itself as a Candidate-RP."
			::= { wriPimv6CandidateRPEntry 2 }

		
		-- 1.3.6.1.4.1.3807.2.1620.2.7.1.2
		wriPimv6CandidateRPGroupMask OBJECT-TYPE
			SYNTAX INTEGER
			MAX-ACCESS read-only
			STATUS current
			DESCRIPTION
				"The multicast group address mask which, when combined with
				pimCandidateRPGroupMask, identifies a group prefix for which
				the local router will advertise itself as a Candidate-RP."
			::= { wriPimv6CandidateRPEntry 3 }

		
		-- 1.3.6.1.4.1.3807.2.1620.2.7.1.3
		wriPimv6CandidateRPAddress OBJECT-TYPE
			SYNTAX Ipv6Address
			MAX-ACCESS read-write
			STATUS current
			DESCRIPTION
				"The (unicast) address of the interface which will be
				advertised as a Candidate-RP."
			::= { wriPimv6CandidateRPEntry 4 }

		
		-- 1.3.6.1.4.1.3807.2.1620.2.7.1.4
		wriPimv6CandidateRPRowStatus OBJECT-TYPE
			SYNTAX RowStatus
			MAX-ACCESS read-create
			STATUS current
			DESCRIPTION
				"The status of this row, by which new entries may be
				created, or old entries deleted from this table."
			::= { wriPimv6CandidateRPEntry 5 }

		
		-- 1.3.6.1.4.1.3807.2.1620.2.7.1.5
		wriPimv6CandidateRPHoldTime OBJECT-TYPE
			SYNTAX INTEGER
			MAX-ACCESS read-only
			STATUS current
			DESCRIPTION
				"The holdtime for this candidate RP while send CRP message to BSR."
			::= { wriPimv6CandidateRPEntry 6 }

		
		-- 1.3.6.1.4.1.3807.2.1620.2.7.1.6
		wriPimv6CandidateRPPriority OBJECT-TYPE
			SYNTAX INTEGER (0..255)
			MAX-ACCESS read-write
			STATUS current
			DESCRIPTION
				"The RP priority for this candidate RP while send CRP message to BSR."
			::= { wriPimv6CandidateRPEntry 7 }

		
		-- 1.3.6.1.4.1.3807.2.1620.2.7.1.7
		wriPimv6CandidateRPNextAdvTime OBJECT-TYPE
			SYNTAX Unsigned32
			MAX-ACCESS read-only
			STATUS current
			DESCRIPTION
				"The time remaining before the system send CRP message to BSR."
			::= { wriPimv6CandidateRPEntry 8 }

		
		-- 1.3.6.1.4.1.3807.2.1620.2.8
		wriPimv6ComponentTable OBJECT-TYPE
			SYNTAX SEQUENCE OF WriPimv6ComponentEntry
			MAX-ACCESS not-accessible
			STATUS current
			DESCRIPTION
				"The (conceptual) table containing objects specific to a PIM
				domain.  One row exists for each domain to which the router
				is connected.  A PIM-SM domain is defined as an area of the
				network over which Bootstrap messages are forwarded.
				Typically, a PIM-SM router will be a member of exactly one
				domain.  This table also supports, however, routers which
				may form a border between two PIM-SM domains and do not
				forward Bootstrap messages between them."
			::= { wriPimv6Tables 8 }

		
		-- 1.3.6.1.4.1.3807.2.1620.2.8.1
		wriPimv6ComponentEntry OBJECT-TYPE
			SYNTAX WriPimv6ComponentEntry
			MAX-ACCESS not-accessible
			STATUS current
			DESCRIPTION
				"An entry (conceptual row) in the pimComponentTable."
			INDEX { wriPimv6ComponentInstance,wriPimv6ComponentScopeId}
			::= { wriPimv6ComponentTable 1 }

		
		WriPimv6ComponentEntry ::=
			SEQUENCE { 
				wriPimv6ComponentInstance
				    INTEGER,
				wriPimv6ComponentScopeId
					Integer32,
				wriPimv6ComponentElectedBSRAddress
					Ipv6Address,
				wriPimv6ComponentElectedBSRPriority
					INTEGER,
				wriPimv6ComponentElectedBSRHashMaskLen
					INTEGER,
				wriPimv6ComponentBSRExpiryTime
					Unsigned32,
				wriPimv6ComponentStatus
					RowStatus,
				wriPimv6ComponentCandidateBSRAddress
					Ipv6Address,
				wriPimv6ComponentCandidateBSRPriority
					INTEGER,
				wriPimv6ComponentCandidateBSRHashMaskLen
					INTEGER,
				wriPimv6ComponentCandidateBSRState
					TruthValue,
				wriPimv6ComponentBSRUpdateTime
					INTEGER,  
				wriPimv6ComponentElectedBSRFragmentTag
					INTEGER,  	
				wriPimv6ComponentElectedBSRState	
					TruthValue					
			 }     
			 
		-- 1.3.6.1.4.1.3807.2.1620.2.8.1.1	 
   		wriPimv6ComponentInstance OBJECT-TYPE
			SYNTAX INTEGER 
			MAX-ACCESS read-only
			STATUS current
			DESCRIPTION
				"vpn instance id"
			::= { wriPimv6ComponentEntry 1 }
   			
		-- 1.3.6.1.4.1.3807.2.1620.2.8.1.2
		
		
		-- 1.3.6.1.4.1.3807.2.1620.2.8.1.4
		wriPimv6ComponentScopeId OBJECT-TYPE
			SYNTAX Integer32
			MAX-ACCESS read-only
			STATUS current
			DESCRIPTION
				"Description."
			::= { wriPimv6ComponentEntry 2 }

		
		-- 1.3.6.1.4.1.3807.2.1620.2.8.1.5
		wriPimv6ComponentElectedBSRAddress OBJECT-TYPE
			SYNTAX Ipv6Address
			MAX-ACCESS read-only
			STATUS current
			DESCRIPTION
				"The IP address of the bootstrap router (BSR) for the local
				PIM region."
			::= { wriPimv6ComponentEntry 3 }

		
		-- 1.3.6.1.4.1.3807.2.1620.2.8.1.6
		wriPimv6ComponentElectedBSRPriority OBJECT-TYPE
			SYNTAX INTEGER (0..255)
			MAX-ACCESS read-only
			STATUS current
			DESCRIPTION
				"The BSR priority of elected bsr."
			::= { wriPimv6ComponentEntry 4 }

		
		-- 1.3.6.1.4.1.3807.2.1620.2.8.1.7
		wriPimv6ComponentElectedBSRHashMaskLen OBJECT-TYPE
			SYNTAX INTEGER (1..32)
			MAX-ACCESS read-only
	        STATUS current
			DESCRIPTION
				"The BSR hash mask lenth  of elected bsr,the hash mask 
				lenth used to find rp for a group."
			::= { wriPimv6ComponentEntry 5}

		
		-- 1.3.6.1.4.1.3807.2.1620.2.8.1.8
		wriPimv6ComponentBSRExpiryTime OBJECT-TYPE
			SYNTAX Unsigned32
			MAX-ACCESS read-only
			STATUS current
			DESCRIPTION
				"The minimum time remaining before the bootstrap router in
				the local domain will be declared down.  For candidate BSRs,
				this is the time until the component sends an RP-Set
				message.  For other routers, this is the time until it may
				accept an RP-Set message from a lower candidate BSR."
			::= { wriPimv6ComponentEntry 6 }

		
		-- 1.3.6.1.4.1.3807.2.1620.2.8.1.9
		wriPimv6ComponentStatus OBJECT-TYPE
			SYNTAX RowStatus
			MAX-ACCESS read-create
			STATUS current
			DESCRIPTION
				"The status of this entry.	Creating the entry creates
				another protocol instance; destroying the entry disables a
				protocol instance."
			::= { wriPimv6ComponentEntry 7 }

		
		-- 1.3.6.1.4.1.3807.2.1620.2.8.1.10
		wriPimv6ComponentCandidateBSRAddress OBJECT-TYPE
			SYNTAX Ipv6Address
			MAX-ACCESS read-create
			STATUS current
			DESCRIPTION
				"The IP address of the candidate bootstrap router (BSR) for the local
				PIM region."
			::= { wriPimv6ComponentEntry 8 }

		
		-- 1.3.6.1.4.1.3807.2.1620.2.8.1.11
		wriPimv6ComponentCandidateBSRPriority OBJECT-TYPE
			SYNTAX INTEGER (0..255)
			MAX-ACCESS read-create
			STATUS current
			DESCRIPTION
				"The BSR priority of candidate local bsr."
			::= { wriPimv6ComponentEntry 9 }

		
		-- 1.3.6.1.4.1.3807.2.1620.2.8.1.12
		wriPimv6ComponentCandidateBSRHashMaskLen OBJECT-TYPE
			SYNTAX INTEGER (1..32)
			MAX-ACCESS read-create
			STATUS current
			DESCRIPTION
				"The BSR hash mask lenth  of local candidate bsr,the hash mask 
				lenth used to find rp for a group."
			::= { wriPimv6ComponentEntry 10 }

		
		-- 1.3.6.1.4.1.3807.2.1620.2.8.1.13
		wriPimv6ComponentCandidateBSRState OBJECT-TYPE
			SYNTAX TruthValue
			MAX-ACCESS read-write
			STATUS current
			DESCRIPTION
				"Description."
			::= { wriPimv6ComponentEntry 11 }
         
        -- 1.3.6.1.4.1.3807.2.1620.2.8.1.14 
		wriPimv6ComponentBSRUpdateTime OBJECT-TYPE
			SYNTAX INTEGER
			MAX-ACCESS read-write
			STATUS current
			DESCRIPTION
				"Description."
			::= { wriPimv6ComponentEntry 12 }

		-- 1.3.6.1.4.1.3807.2.1620.2.8.1.15
		wriPimv6ComponentElectedBSRFragmentTag OBJECT-TYPE
			SYNTAX INTEGER
			MAX-ACCESS read-write
			STATUS current
			DESCRIPTION
				"Description."
			::= { wriPimv6ComponentEntry 13 }

        -- 1.3.6.1.4.1.3807.2.1620.2.8.1.16                                   
		wriPimv6ComponentElectedBSRState	OBJECT-TYPE
			SYNTAX TruthValue
			MAX-ACCESS read-write
			STATUS current
			DESCRIPTION
				"Description."
			::= { wriPimv6ComponentEntry 14 }
											
		-- 1.3.6.1.4.1.3807.2.1620.2.9
		wriPimv6IgmpMemberTable OBJECT-TYPE
			SYNTAX SEQUENCE OF WriPimv6IgmpMemberEntry
			MAX-ACCESS not-accessible
			STATUS current
			DESCRIPTION
				"Description."
			::= { wriPimv6Tables 9 }

		
		-- 1.3.6.1.4.1.3807.2.1620.2.9.1
		wriPimv6IgmpMemberEntry OBJECT-TYPE
			SYNTAX WriPimv6IgmpMemberEntry
			MAX-ACCESS not-accessible
			STATUS current
			DESCRIPTION
				"Description."
			INDEX { wriPimv6IgmpMemberIfAddress, wriPimv6IgmpMemberGroup, wriPimv6IgmpMemberSource, wriPimv6IgmpMemberPort }
			::= { wriPimv6IgmpMemberTable 1 }

		
		WriPimv6IgmpMemberEntry ::=
			SEQUENCE { 
				wriPimv6IgmpMemberIfAddress
					Ipv6Address,
				wriPimv6IgmpMemberGroup
					Ipv6Address,
				wriPimv6IgmpMemberSource
					Ipv6Address,
				wriPimv6IgmpMemberPort
					INTEGER,
				wriPimv6IgmpMemberStatus
					RowStatus
			 }

		-- 1.3.6.1.4.1.3807.2.1620.2.9.1.1
		wriPimv6IgmpMemberIfAddress OBJECT-TYPE
			SYNTAX Ipv6Address
			MAX-ACCESS read-only
			STATUS current
			DESCRIPTION
				"Description."
			::= { wriPimv6IgmpMemberEntry 1 }

		
		-- 1.3.6.1.4.1.3807.2.1620.2.9.1.2
		wriPimv6IgmpMemberGroup OBJECT-TYPE
			SYNTAX Ipv6Address
			MAX-ACCESS read-only
			STATUS current
			DESCRIPTION
				"Description."
			::= { wriPimv6IgmpMemberEntry 2 }

		
		-- 1.3.6.1.4.1.3807.2.1620.2.9.1.3
		wriPimv6IgmpMemberSource OBJECT-TYPE
			SYNTAX Ipv6Address
			MAX-ACCESS read-only
			STATUS current
			DESCRIPTION
				"Description."
			::= { wriPimv6IgmpMemberEntry 3 }

		
		-- 1.3.6.1.4.1.3807.2.1620.2.9.1.4
		wriPimv6IgmpMemberPort OBJECT-TYPE
			SYNTAX INTEGER (1..65535)
			MAX-ACCESS read-only
			STATUS current
			DESCRIPTION
				"Description."
			::= { wriPimv6IgmpMemberEntry 4 }

		
		-- 1.3.6.1.4.1.3807.2.1620.2.9.1.5
		wriPimv6IgmpMemberStatus OBJECT-TYPE
			SYNTAX RowStatus
			MAX-ACCESS read-create
			STATUS current
			DESCRIPTION
				"Description."
			::= { wriPimv6IgmpMemberEntry 5 }

		
		-- 1.3.6.1.4.1.3807.2.1620.3
		wriPimv6Traps OBJECT IDENTIFIER ::= { pimv6MIB 3 }

		
		-- 1.3.6.1.4.1.3807.2.1620.3.1
		wriPimv6NeighborLoss NOTIFICATION-TYPE
			OBJECTS { wriPimv6NeighborIfIndex }
			STATUS current
			DESCRIPTION 
				"A pimNeighborLoss trap signifies the loss of an adjacency
				with a neighbor.  This trap should be generated when the
				neighbor timer expires, and the router has no other
				neighbors on the same interface with a lower IP address than
				itself."
			::= { wriPimv6Traps 1 }

		
	
	END

--
-- wriPimv6.mib
--
