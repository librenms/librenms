--
-- macLimit.mib
-- MIB generated by MG-SOFT Visual MIB Builder Version 6.0  Build 88
-- Monday, December 13, 2010 at 15:25:54
--

	WRI-MACLIMIT-MIB DEFINITIONS ::= BEGIN
 
		IMPORTS
			mib-2, Integer32, Unsigned32, OBJECT-TYPE, MODULE-IDENTITY,NOTIFICATION-TYPE	
				FROM SNMPv2-SMI
			MacAddress,TEXTUAL-CONVENTION			
				FROM SNMPv2-TC			
			wriProtocol			
				FROM WRI-SMI;
	
	
--  23 September 2009 12:00:00 EST
		-- 1.3.6.1.4.1.3807.2.1321
		wriMacLimit MODULE-IDENTITY 
			LAST-UPDATED "201012131500Z"		-- December 13, 2010 at 15:00 GMT
			ORGANIZATION 
				"FiberHome Networks Systems, Inc."
			CONTACT-INFO 
				"http://www.fhn.com.cn"
			DESCRIPTION 
				" The configure of Mac Limit Num ."
			::= { wriProtocol 1321 }

		
	
--
-- Textual conventions
--
	
--  Textual Conventions
		EntryStatus ::= TEXTUAL-CONVENTION
			STATUS current
			DESCRIPTION 
				"entry status."
			SYNTAX INTEGER
				{
				valid(1),
				createRequest(2),
				underCreation(3),
				invalid(4)
				}

	
--
-- Node definitions
--
	

		-- 1.3.6.1.4.1.3807.2.1321.1
		macLimitGeneral OBJECT IDENTIFIER ::= { wriMacLimit 1 }

		
		-- 1.3.6.1.4.1.3807.2.1321.1.1
		macLimitNum OBJECT-TYPE
			SYNTAX Integer32 (0..32767)
			MAX-ACCESS read-write
			STATUS current
			DESCRIPTION
				"mac limit num,default is 0."
			::= { macLimitGeneral 1 }

		-- 1.3.6.1.4.1.3807.2.1321.1.2
		macLimitAction OBJECT-TYPE
			SYNTAX INTEGER
				{    
				drop(1),
				forward (2)}
			MAX-ACCESS read-write
			STATUS current
			DESCRIPTION
				"mac limit action:default is forward."
			::= { macLimitGeneral 2 }
		
		-- 1.3.6.1.4.1.3807.2.1321.1.3
		macLimitUsedCount OBJECT-TYPE
			SYNTAX Integer32
			MAX-ACCESS read-only
			STATUS current
			DESCRIPTION
				"mac limit used count,default is 0."
			::= { macLimitGeneral 3 }

		-- 1.3.6.1.4.1.3807.2.1321.1.4
		macLimitAlarmStatus OBJECT-TYPE
			SYNTAX INTEGER
				{
				enable(1),
				disable(2)
				}
			MAX-ACCESS read-write
			STATUS current
			DESCRIPTION
				"mac limit alarm enable or disable,the default is disable."
			::= { macLimitGeneral 4 }
        
        -- 1.3.6.1.4.1.3807.2.1321.1.5
		macLimitAlarmSrcMac OBJECT-TYPE
			SYNTAX MacAddress
			MAX-ACCESS read-write
			STATUS current
			DESCRIPTION
				"the source mac of the learning mac address that is going beyond the limit."
			::= { macLimitGeneral 5 }

		
		-- 1.3.6.1.4.1.3807.2.1321.2
		macLimitSlotTable OBJECT-TYPE
			SYNTAX SEQUENCE OF MacLimitSlotEntry
			MAX-ACCESS not-accessible
			STATUS current
			DESCRIPTION
				"The table of mac limit about slot ."
			::= { wriMacLimit 2 }

		
		-- 1.3.6.1.4.1.3807.2.1321.2.1
		macLimitSlotEntry OBJECT-TYPE
			SYNTAX MacLimitSlotEntry
			MAX-ACCESS not-accessible
			STATUS current
			DESCRIPTION
				"The entry of mac limit about slot ."
			INDEX { macLimitSlotSysIndex,macLimitSlotIndex }
			::= { macLimitSlotTable 1 }

		
		MacLimitSlotEntry ::=
			SEQUENCE { 
				macLimitSlotSysIndex
					Unsigned32,
				macLimitSlotIndex
					Unsigned32,
				macLimitSlotNum
					Integer32,
				macLimitSlotAction
					INTEGER,
				macLimitSlotUsedCount
					Integer32,
				macLimitSlotAlarmStatus
					INTEGER
			 }
		
		-- 1.3.6.1.4.1.3807.2.1321.2.1.1
		macLimitSlotSysIndex OBJECT-TYPE
			SYNTAX Unsigned32
			MAX-ACCESS read-only
			STATUS current
			DESCRIPTION
				"The system index of mac limit about slot ."
			::= { macLimitSlotEntry 1 }
			
		-- 1.3.6.1.4.1.3807.2.1321.2.1.2
		macLimitSlotIndex OBJECT-TYPE
			SYNTAX Unsigned32
			MAX-ACCESS read-only
			STATUS current
			DESCRIPTION
				"The index of mac limit about slot ."
			::= { macLimitSlotEntry 2 }

		
		-- 1.3.6.1.4.1.3807.2.1321.2.1.3
		macLimitSlotNum OBJECT-TYPE
			SYNTAX Integer32 (0..32767)
			MAX-ACCESS read-write
			STATUS current
			DESCRIPTION
				"The num of mac limit about slot,default is 0."
			::= { macLimitSlotEntry 3 }

		
		-- 1.3.6.1.4.1.3807.2.1321.2.1.4
		macLimitSlotAction OBJECT-TYPE
			SYNTAX INTEGER
				{    
					drop(1),
					forward (2)
				}
			MAX-ACCESS read-write
			STATUS current
			DESCRIPTION
				"The action of mac limit about slot,default is forward."
			DEFVAL { forward }
			::= { macLimitSlotEntry 4 }

		
		-- 1.3.6.1.4.1.3807.2.1321.2.1.5
		macLimitSlotUsedCount OBJECT-TYPE
			SYNTAX Integer32
			MAX-ACCESS read-only
			STATUS current
			DESCRIPTION
				"The used count of mac limit about slot,default is 0."
			DEFVAL { 0 }
			::= { macLimitSlotEntry 5 }

		
		-- 1.3.6.1.4.1.3807.2.1321.2.1.6
		macLimitSlotAlarmStatus OBJECT-TYPE
			SYNTAX INTEGER
				{
					enable(1),
					disable(2)
				}
			MAX-ACCESS read-write
			STATUS current
			DESCRIPTION
				"The status  of mac limit alarm about slot,default is disable."
			DEFVAL { disable }
			::= { macLimitSlotEntry 6 }

		
			
		-- 1.3.6.1.4.1.3807.2.1321.3
		macLimitVlanTable OBJECT-TYPE
			SYNTAX SEQUENCE OF MacLimitVlanEntry
			MAX-ACCESS not-accessible
			STATUS current
			DESCRIPTION
				"The table of mac limit about vlan."
			::= { wriMacLimit 3 }

		
		-- 1.3.6.1.4.1.3807.2.1321.3.1
		macLimitVlanEntry OBJECT-TYPE
			SYNTAX MacLimitVlanEntry
			MAX-ACCESS not-accessible
			STATUS current
			DESCRIPTION
				"The entry of mac limit about vlan ."
			INDEX { macLimitVlanIndex }
			::= { macLimitVlanTable 1 }

		
		MacLimitVlanEntry ::=
			SEQUENCE { 
				macLimitVlanIndex
					Unsigned32,
				macLimitVlanNum
					Integer32,
				macLimitVlanAction
					INTEGER,
				macLimitVlanUsedCount
					Integer32,
				macLimitVlanAlarmStatus
					INTEGER
			 }

		-- 1.3.6.1.4.1.3807.2.1321.3.1.1
		macLimitVlanIndex OBJECT-TYPE
			SYNTAX Unsigned32
			MAX-ACCESS read-only
			STATUS current
			DESCRIPTION
				"The index of mac limit about vlan ."
			::= { macLimitVlanEntry 1 }

		
		-- 1.3.6.1.4.1.3807.2.1321.3.1.2
		macLimitVlanNum OBJECT-TYPE
			SYNTAX Integer32 (0..32767)
			MAX-ACCESS read-write
			STATUS current
			DESCRIPTION
				"The count of mac limit about vlan,default is 0."
			DEFVAL { 0 }
			::= { macLimitVlanEntry 2 }

		
		-- 1.3.6.1.4.1.3807.2.1321.3.1.3
		macLimitVlanAction OBJECT-TYPE
			SYNTAX INTEGER
			{    
				drop(1),
				forward (2)}
			MAX-ACCESS read-write
			STATUS current
			DESCRIPTION
				"The action of mac limit about vlan."
			DEFVAL { forward }
			::= { macLimitVlanEntry 3 }

		
		-- 1.3.6.1.4.1.3807.2.1321.3.1.4
		macLimitVlanUsedCount OBJECT-TYPE
			SYNTAX Integer32
			MAX-ACCESS read-only
			STATUS current
			DESCRIPTION
				"The count used of mac limit about vlan ."
			DEFVAL { 0 }
			::= { macLimitVlanEntry 4 }

		
		-- 1.3.6.1.4.1.3807.2.1321.3.1.5
		macLimitVlanAlarmStatus OBJECT-TYPE
			SYNTAX INTEGER
				{
				enable(1),
				disable(2)
				}
			MAX-ACCESS read-write
			STATUS current
			DESCRIPTION
				"The status of mac limit alarm about vlan ."
			DEFVAL { disable }
			::= { macLimitVlanEntry 5 }

		
		
		-- 1.3.6.1.4.1.3807.2.1321.4
		macLimitIfTable OBJECT-TYPE
			SYNTAX SEQUENCE OF MacLimitIfEntry
			MAX-ACCESS not-accessible
			STATUS current
			DESCRIPTION
				"The table of mac limit about port."
			::= { wriMacLimit 4 }

		
		-- 1.3.6.1.4.1.3807.2.1321.4.1
		macLimitIfEntry OBJECT-TYPE
			SYNTAX MacLimitIfEntry
			MAX-ACCESS not-accessible
			STATUS current
			DESCRIPTION
				"The entry of mac limit about port."
			INDEX { macLimitIfIndex }
			::= { macLimitIfTable 1 }

		
		MacLimitIfEntry ::=
			SEQUENCE { 
				macLimitIfIndex
					Unsigned32,
				macLimitIfNum
					Integer32,
				macLimitIfAction
					INTEGER,
				macLimitIfUsedCount
					Integer32,
				macLimitIfAlarmStatus
					INTEGER
			 }

		-- 1.3.6.1.4.1.3807.2.1321.4.1.1
		macLimitIfIndex OBJECT-TYPE
			SYNTAX Unsigned32
			MAX-ACCESS read-only
			STATUS current
			DESCRIPTION
				"The index of mac limit about port."
			::= { macLimitIfEntry 1 }

		
		-- 1.3.6.1.4.1.3807.2.1321.4.1.2
		macLimitIfNum OBJECT-TYPE
			SYNTAX Integer32 (0..32767)
			MAX-ACCESS read-write
			STATUS current
			DESCRIPTION
				"The count of mac limit about port."
			DEFVAL { 0 }
			::= { macLimitIfEntry 2 }

		
		-- 1.3.6.1.4.1.3807.2.1321.4.1.3
		macLimitIfAction OBJECT-TYPE
			SYNTAX INTEGER
			{    
				drop(1),
				forward (2)}
			MAX-ACCESS read-write
			STATUS current
			DESCRIPTION
				"The action of mac limit about port."
			DEFVAL { forward }
			::= { macLimitIfEntry 3 }

		
		-- 1.3.6.1.4.1.3807.2.1321.4.1.4
		macLimitIfUsedCount OBJECT-TYPE
			SYNTAX Integer32 (0..32767)
			MAX-ACCESS read-only
			STATUS current
			DESCRIPTION
				"The count used of mac limit about port."
			DEFVAL { 0 }
			::= { macLimitIfEntry 4 }

		
		-- 1.3.6.1.4.1.3807.2.1321.4.1.5
		macLimitIfAlarmStatus OBJECT-TYPE
			SYNTAX INTEGER
				{
				enable(1),
				disable(2)
				}
			MAX-ACCESS read-write
			STATUS current
			DESCRIPTION
				"The status of mac limit alarm about port."
			DEFVAL { disable }
			::= { macLimitIfEntry 5 }

		
		--mac limit trap
		macLimitTraps  OBJECT IDENTIFIER ::=   {wriMacLimit 5}

   macLimitAlarmTrap NOTIFICATION-TYPE
       	OBJECTS {macLimitNum,macLimitUsedCount}
       	STATUS  current
       	DESCRIPTION
               "the mac limit alarm trap about the system ."
		::= { macLimitTraps 1}

   macLimitSlotAlarmTrap NOTIFICATION-TYPE
       	OBJECTS {macLimitSlotIndex,macLimitSlotNum,macLimitSlotUsedCount}
       	STATUS  current
       	DESCRIPTION
               "the mac limit  alarm  trap about some slot ."
		::= { macLimitTraps 2}
    
  macLimitVlanAlarmTrap NOTIFICATION-TYPE
       	OBJECTS {macLimitVlanIndex,macLimitVlanNum,macLimitVlanUsedCount}
       	STATUS  current
       	DESCRIPTION
               "the mac limit  alarm  trap about some vlan."
		::= { macLimitTraps 3}
  
   macLimitIfAlarmTrap NOTIFICATION-TYPE
       	OBJECTS {macLimitIfIndex,macLimitIfNum,macLimitIfUsedCount}
       	STATUS  current
       	DESCRIPTION
               "the mac limit  alarm  trap about some port."
		::= { macLimitTraps 4}
	
	END

--
-- macLimit.mib
--
