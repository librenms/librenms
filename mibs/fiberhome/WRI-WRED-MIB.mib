--
-- wred.mib
-- MIB generated by MG-SOFT Visual MIB Builder Version 6.0  Build 88
--

	WRI-WRED-MIB DEFINITIONS ::= BEGIN
 
		IMPORTS
			mib-2, Integer32, Unsigned32, OBJECT-TYPE, MODULE-IDENTITY,NOTIFICATION-TYPE	
				FROM SNMPv2-SMI			
			TEXTUAL-CONVENTION			
				FROM SNMPv2-TC			
			wriProtocol			
				FROM WRI-SMI;
	

		wred MODULE-IDENTITY 
			LAST-UPDATED "201301211500Z"		-- Jan 21, 2013 at 15:00 GMT
			ORGANIZATION 
				"FiberHome Networks Systems, Inc."
			CONTACT-INFO 
				"http://www.fhn.com.cn"
			DESCRIPTION 
				" The configure of wred."
			::= { wriProtocol 2301 }

		
	
--
-- Textual conventions
--
	
--  Textual Conventions
		DisplayString ::=   OCTET STRING
		EntryStatus ::= TEXTUAL-CONVENTION
			STATUS current
			DESCRIPTION 
				"entry status."
			SYNTAX INTEGER
				{
				valid(1),
				createRequest(2),
				underCreation(3),
				invalid(4)
				}

	
--
-- Node definitions
--
	

		wredGeneral OBJECT IDENTIFIER ::= { wred 1 }

		wredFreeIndex OBJECT-TYPE
			SYNTAX Unsigned32 (0..32767)
			MAX-ACCESS read-only
			STATUS current
			DESCRIPTION
				"The free wred index."
			::= { wredGeneral 1 }

		wredUsedNum OBJECT-TYPE
			SYNTAX Integer32 (0..32767)
			MAX-ACCESS read-only
			STATUS current
			DESCRIPTION
				"The used num of wred."
			::= { wredGeneral 2 }
		
		wredMaxNum OBJECT-TYPE
			SYNTAX Integer32 (0..32767)
			MAX-ACCESS read-only
			STATUS current
			DESCRIPTION
				"The max num of wred."
			::= { wredGeneral 3 }

	
		wredDropProfileInfoTable OBJECT-TYPE
			SYNTAX SEQUENCE OF WredDropProfileInfoEntry
			MAX-ACCESS not-accessible
			STATUS current
			DESCRIPTION
				"The table of wred drop profile."
			::= { wred 2 }

		
		wredDropProfileInfoEntry OBJECT-TYPE
			SYNTAX WredDropProfileInfoEntry
			MAX-ACCESS not-accessible
			STATUS current
			DESCRIPTION
				"The entry of wred drop profile."
			INDEX { wredDropProfileIndex  }
			::= { wredDropProfileInfoTable 1 }

		
		WredDropProfileInfoEntry ::=
			SEQUENCE { 
				wredDropProfileIndex
					Integer32,
				wredDropProfileName
					OCTET STRING,
				wredDropProfileRedHPercent 
					Integer32,
				wredDropProfileRedLPercent 
					Integer32,
				wredDropProfileRedDiscardPercent 
					Integer32,
				wredDropProfileGreenHPercent
					Integer32,
				wredDropProfileGreenLPercent 
					Integer32,
				wredDropProfileGreenDiscardPercent 
					Integer32,
				wredDropProfileYellowHPercent 
					Integer32,
				wredDropProfileYellowLPercent 
					Integer32,
				wredDropProfileYellowDiscardPercent 
					Integer32,
				wredDropProfileNoTcpHPercent 
					Integer32,
				wredDropProfileNoTcpLPercent 
					Integer32,
				wredDropProfileNoTcpDiscardPercent 
					Integer32,
				wredDropProfileEntryStatus  
					EntryStatus,
				wredDropProfileRefCnt
					Integer32
			 }

		wredDropProfileIndex OBJECT-TYPE
			SYNTAX Integer32
			MAX-ACCESS read-only
			STATUS current
			DESCRIPTION
				"The index of wred drop profile."
			::= { wredDropProfileInfoEntry 1 }

		wredDropProfileName OBJECT-TYPE
			SYNTAX OCTET STRING
			MAX-ACCESS read-write
			STATUS current
			DESCRIPTION
				"The name of wred drop profile."
			::= { wredDropProfileInfoEntry 2 }

		wredDropProfileRedHPercent OBJECT-TYPE
			SYNTAX Integer32
			MAX-ACCESS read-write
			STATUS current
			DESCRIPTION
				"The high percentage of red packet."
			::= { wredDropProfileInfoEntry 3 }
		
		wredDropProfileRedLPercent OBJECT-TYPE
			SYNTAX Integer32
			MAX-ACCESS read-write
			STATUS current
			DESCRIPTION
				"The low percentage of red packet."
			::= { wredDropProfileInfoEntry 4 }
			
		wredDropProfileRedDiscardPercent OBJECT-TYPE
			SYNTAX Integer32
			MAX-ACCESS read-write
			STATUS current
			DESCRIPTION
				"The discard percentage of red packet."
			::= { wredDropProfileInfoEntry 5 }
			
		wredDropProfileGreenHPercent OBJECT-TYPE
			SYNTAX Integer32
			MAX-ACCESS read-write
			STATUS current
			DESCRIPTION
				"The high percentage of green packet."
			::= { wredDropProfileInfoEntry 6 }
		
		wredDropProfileGreenLPercent OBJECT-TYPE
			SYNTAX Integer32
			MAX-ACCESS read-write
			STATUS current
			DESCRIPTION
				"The low percentage of green packet."
			::= { wredDropProfileInfoEntry 7 }
			
		wredDropProfileGreenDiscardPercent OBJECT-TYPE
			SYNTAX Integer32
			MAX-ACCESS read-write
			STATUS current
			DESCRIPTION
				"The discard percentage of green packet."
			::= { wredDropProfileInfoEntry 8 }
			
		wredDropProfileYellowHPercent OBJECT-TYPE
			SYNTAX Integer32
			MAX-ACCESS read-write
			STATUS current
			DESCRIPTION
				"The high percentage of yellow packet."
			::= { wredDropProfileInfoEntry 9 }
		
		wredDropProfileYellowLPercent OBJECT-TYPE
			SYNTAX Integer32
			MAX-ACCESS read-write
			STATUS current
			DESCRIPTION
				"The low percentage of yellow packet."
			::= { wredDropProfileInfoEntry 10 }
			
		wredDropProfileYellowDiscardPercent OBJECT-TYPE
			SYNTAX Integer32
			MAX-ACCESS read-write
			STATUS current
			DESCRIPTION
				"The discard percentage of yellow packet."
			::= { wredDropProfileInfoEntry 11 }
			
		wredDropProfileNoTcpHPercent OBJECT-TYPE
			SYNTAX Integer32
			MAX-ACCESS read-write
			STATUS current
			DESCRIPTION
				"The high percentage of non-tcp packet."
			::= { wredDropProfileInfoEntry 12 }
		
		wredDropProfileNoTcpLPercent OBJECT-TYPE
			SYNTAX Integer32
			MAX-ACCESS read-write
			STATUS current
			DESCRIPTION
				"The low percentage of non-tcp packet."
			::= { wredDropProfileInfoEntry 13 }
			
		wredDropProfileNoTcpDiscardPercent OBJECT-TYPE
			SYNTAX Integer32
			MAX-ACCESS read-write
			STATUS current
			DESCRIPTION
				"The discard percentage of non-tcp packet."
			::= { wredDropProfileInfoEntry 14 }
			
		wredDropProfileEntryStatus OBJECT-TYPE
			SYNTAX EntryStatus
			MAX-ACCESS read-write
			STATUS current
			DESCRIPTION
				"The status of wred drop profile ."
			::= { wredDropProfileInfoEntry 15 }
			
		wredDropProfileRefCnt OBJECT-TYPE
			SYNTAX Integer32
			MAX-ACCESS read-only
			STATUS current
			DESCRIPTION
				"The reference count of drop profile ."
			::= { wredDropProfileInfoEntry 16 }
		
		wredDropProfilePortTable OBJECT-TYPE
			SYNTAX SEQUENCE OF WredDropProfilePortEntry
			MAX-ACCESS not-accessible
			STATUS current
			DESCRIPTION
				"The table of wred drop profile interface info."
			::= { wred 3 }

		
		wredDropProfilePortEntry OBJECT-TYPE
			SYNTAX WredDropProfilePortEntry
			MAX-ACCESS not-accessible
			STATUS current
			DESCRIPTION
				"The entry of wred drop profile interface info."
			INDEX {  wredDropProfileIfIndex }
			::= { wredDropProfilePortTable 1 }

		
		WredDropProfilePortEntry ::=
			SEQUENCE { 
				wredDropProfileIfIndex
					Integer32,
				wredDropProfileId
					Integer32,
				wredDropProfileState 
					INTEGER
			 }

		wredDropProfileIfIndex OBJECT-TYPE
			SYNTAX Integer32
			MAX-ACCESS read-only
			STATUS current
			DESCRIPTION
				"The unit of interface."
			::= { wredDropProfilePortEntry 1 }

		wredDropProfileId OBJECT-TYPE
			SYNTAX Integer32
			MAX-ACCESS read-write
			STATUS current
			DESCRIPTION
				"The index of wred drop profile."
			::= { wredDropProfilePortEntry 2 }

		wredDropProfileState OBJECT-TYPE
			SYNTAX INTEGER
				{
				  enable(1),
				  disable(2)
				}
			MAX-ACCESS read-write
			STATUS current
			DESCRIPTION
				"The state of wred drop profile on interface."
			::= { wredDropProfilePortEntry 3 }


		wredDropProfilePortQueueTable OBJECT-TYPE
			SYNTAX SEQUENCE OF WredDropProfilePortQueueEntry
			MAX-ACCESS not-accessible
			STATUS current
			DESCRIPTION
				"The table of wred drop profile interface and queue."
			::= { wred 4 }

		
		wredDropProfilePortQueueEntry OBJECT-TYPE
			SYNTAX WredDropProfilePortQueueEntry
			MAX-ACCESS not-accessible
			STATUS current
			DESCRIPTION
				"The entry of wred drop profile interface and queue."
			INDEX { wredDropProfileQueueIfIndex,wredDropProfileQueueId }
			::= { wredDropProfilePortQueueTable 1 }

		
		WredDropProfilePortQueueEntry ::=
			SEQUENCE { 
				wredDropProfileQueueIfIndex
					Integer32,
				wredDropProfileQueueId
					Integer32,
				wredDropProfileQueueIndex
					Integer32,
				wredDropProfileQueueState 
					INTEGER
			 }

		wredDropProfileQueueIfIndex OBJECT-TYPE
			SYNTAX Integer32
			MAX-ACCESS read-only
			STATUS current
			DESCRIPTION
				"The unit of interface."
			::= { wredDropProfilePortQueueEntry 1 }

		wredDropProfileQueueId OBJECT-TYPE
			SYNTAX Integer32
			MAX-ACCESS read-only
			STATUS current
			DESCRIPTION
				"The queue id."
			::= { wredDropProfilePortQueueEntry 2 }

		wredDropProfileQueueIndex OBJECT-TYPE
			SYNTAX Integer32
			MAX-ACCESS read-write
			STATUS current
			DESCRIPTION
				"The index of wred drop profile."
			::= { wredDropProfilePortQueueEntry 3 }

		wredDropProfileQueueState OBJECT-TYPE
			SYNTAX INTEGER
				{
				  enable(1),
				  disable(2)
				}
			MAX-ACCESS read-write
			STATUS current
			DESCRIPTION
				"The state of wred drop profile about interface and queue."
			::= { wredDropProfilePortQueueEntry 4 }

	END

--
-- macLimit.mib
--
