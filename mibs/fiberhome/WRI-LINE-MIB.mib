--
-- wriLine.mib
-- MIB generated by MG-SOFT Visual MIB Builder Version 4.0 Build 349
-- Monday, April 09, 2012 at 15:09:08
--

-- ----------------------------------------------------------------------------
-- ----------------------------------------------------------------------------
--   WRI Line MIB
-- 
-- ----------------------------------------------------------------------------
-- ----------------------------------------------------------------------------

	WRI-LINE-MIB DEFINITIONS ::= BEGIN
 
		IMPORTS
			Integer32, OBJECT-TYPE			
				FROM SNMPv2-SMI			
			DisplayString			
				FROM SNMPv2-TC			
			wri, wriProtocol			
				FROM WRI-SMI;
	
	
	
--
-- Node definitions
--
	
--  assigned by IANA
		-- 1.3.6.1.4.1.3807.3
		wriMgmt OBJECT IDENTIFIER ::= { wri 3 }

		
		-- 1.3.6.1.4.1.3807.3.5
		wriLine OBJECT IDENTIFIER ::= { wriMgmt 5 }

		
-- line configuration
		-- 1.3.6.1.4.1.3807.3.5.1
		wriLineCommon OBJECT IDENTIFIER ::= { wriLine 1 }

		
		-- 1.3.6.1.4.1.3807.3.5.1.1
		wriLineVtyNum OBJECT-TYPE
			SYNTAX INTEGER
			MAX-ACCESS read-write
			STATUS current
			DESCRIPTION
				"configure maximum line number."
			::= { wriLineCommon 1 }

		
		-- 1.3.6.1.4.1.3807.3.5.1.2
		wriLineUser OBJECT-TYPE
			SYNTAX OCTET STRING (SIZE (0..128))
			MAX-ACCESS read-create
			STATUS current
			DESCRIPTION
				"add or delete a user."
			DEFVAL { ''h }
			::= { wriLineCommon 2 }

		
		-- 1.3.6.1.4.1.3807.3.5.1.3
		wriLineEnablePassword OBJECT-TYPE
			SYNTAX OCTET STRING (SIZE (0..64))
			MAX-ACCESS read-create
			STATUS current
			DESCRIPTION
				"configure enable password."
			DEFVAL { ''h }
			::= { wriLineCommon 3 }

		
-- line vty table                                  
		-- 1.3.6.1.4.1.3807.3.5.2
		wriLineVtyTable OBJECT-TYPE
			SYNTAX SEQUENCE OF WriLineVtyEntry
			MAX-ACCESS not-accessible
			STATUS current
			DESCRIPTION
				"line vty configure table."
			::= { wriLine 2 }

		
		-- 1.3.6.1.4.1.3807.3.5.2.1
		wriLineVtyEntry OBJECT-TYPE
			SYNTAX WriLineVtyEntry
			MAX-ACCESS not-accessible
			STATUS current
			DESCRIPTION
				"line vty configure entry."
			INDEX { wriLineVtyIndex }
			::= { wriLineVtyTable 1 }

		
		WriLineVtyEntry ::=
			SEQUENCE { 
				wriLineVtyIndex
					INTEGER,
				wriLineVtyType
					INTEGER,
				wriLineVtyPassword
					OCTET STRING,
				wriLineVtyTimeout
					INTEGER,
				wriLineVtyPrivilege
					INTEGER,
				wriLineVtyTerminalLen
					INTEGER,
				wriLineVtyLoginType
					INTEGER,
				wriLineVtyMonitor
					Integer32,
				wriLineVtyColorUsed
					Integer32,
				wriLineVtyColor
					Integer32,
				wriLineVtyLanguage
					Integer32,
				wriLineVtyStatus
					Integer32,
				wriLineVtyNode
					Integer32,
				wriLineVtyUsed
					Integer32,
				wriLineVtyLastChange
					Integer32,
				wriLineVtyUser
					DisplayString,
				wriLineVtyAddress
					OCTET STRING,
				wriLineVtyCanclose
					Integer32
			 }

		-- 1.3.6.1.4.1.3807.3.5.2.1.1
		wriLineVtyIndex OBJECT-TYPE
			SYNTAX INTEGER
			MAX-ACCESS read-only
			STATUS current
			DESCRIPTION
				"line vty index."
			::= { wriLineVtyEntry 1 }

		
		-- 1.3.6.1.4.1.3807.3.5.2.1.2
		wriLineVtyType OBJECT-TYPE
			SYNTAX INTEGER
				{
				unknown(0),
				console(1),
				telnet(2),
				aux(3)
				}
			MAX-ACCESS read-only
			STATUS current
			DESCRIPTION
				"line vty index."
			::= { wriLineVtyEntry 2 }

		
		-- 1.3.6.1.4.1.3807.3.5.2.1.3
		wriLineVtyPassword OBJECT-TYPE
			SYNTAX OCTET STRING (SIZE (0..64))
			MAX-ACCESS read-write
			STATUS current
			DESCRIPTION
				"line vty password"
			::= { wriLineVtyEntry 3 }

		
		-- 1.3.6.1.4.1.3807.3.5.2.1.4
		wriLineVtyTimeout OBJECT-TYPE
			SYNTAX INTEGER
			MAX-ACCESS read-write
			STATUS current
			DESCRIPTION
				"The timeout of line vty."
			::= { wriLineVtyEntry 4 }

		
		-- 1.3.6.1.4.1.3807.3.5.2.1.5
		wriLineVtyPrivilege OBJECT-TYPE
			SYNTAX INTEGER
			MAX-ACCESS read-write
			STATUS current
			DESCRIPTION
				"The privilege of line vty."
			::= { wriLineVtyEntry 5 }

		
		-- 1.3.6.1.4.1.3807.3.5.2.1.6
		wriLineVtyTerminalLen OBJECT-TYPE
			SYNTAX INTEGER
			MAX-ACCESS read-write
			STATUS current
			DESCRIPTION
				"The terminal length of line vty."
			::= { wriLineVtyEntry 6 }

		
		-- 1.3.6.1.4.1.3807.3.5.2.1.7
		wriLineVtyLoginType OBJECT-TYPE
			SYNTAX INTEGER
				{
				logindisable(0),
				loginlocal(1),
				loginremote(2)
				}
			MAX-ACCESS read-write
			STATUS current
			DESCRIPTION
				"line vty login local"
			::= { wriLineVtyEntry 7 }

		
		-- 1.3.6.1.4.1.3807.3.5.2.1.8
		wriLineVtyMonitor OBJECT-TYPE
			SYNTAX Integer32
			MAX-ACCESS read-write
			STATUS current
			DESCRIPTION
				"Description."
			::= { wriLineVtyEntry 8 }

		
		-- 1.3.6.1.4.1.3807.3.5.2.1.9
		wriLineVtyColorUsed OBJECT-TYPE
			SYNTAX Integer32
			MAX-ACCESS read-write
			STATUS current
			DESCRIPTION
				"Description."
			::= { wriLineVtyEntry 9 }

		
		-- 1.3.6.1.4.1.3807.3.5.2.1.10
		wriLineVtyColor OBJECT-TYPE
			SYNTAX Integer32
			MAX-ACCESS read-write
			STATUS current
			DESCRIPTION
				"Description."
			::= { wriLineVtyEntry 10 }

		
		-- 1.3.6.1.4.1.3807.3.5.2.1.11
		wriLineVtyLanguage OBJECT-TYPE
			SYNTAX Integer32
			MAX-ACCESS read-write
			STATUS current
			DESCRIPTION
				"Description."
			::= { wriLineVtyEntry 11 }

		
		-- 1.3.6.1.4.1.3807.3.5.2.1.12
		wriLineVtyStatus OBJECT-TYPE
			SYNTAX Integer32
			MAX-ACCESS read-write
			STATUS current
			DESCRIPTION
				"Description."
			::= { wriLineVtyEntry 12 }

		
		-- 1.3.6.1.4.1.3807.3.5.2.1.13
		wriLineVtyNode OBJECT-TYPE
			SYNTAX Integer32
			MAX-ACCESS read-write
			STATUS current
			DESCRIPTION
				"Description."
			::= { wriLineVtyEntry 13 }

		
		-- 1.3.6.1.4.1.3807.3.5.2.1.14
		wriLineVtyUsed OBJECT-TYPE
			SYNTAX Integer32
			MAX-ACCESS read-only
			STATUS current
			DESCRIPTION
				"Description."
			::= { wriLineVtyEntry 14 }

		
		-- 1.3.6.1.4.1.3807.3.5.2.1.15
		wriLineVtyLastChange OBJECT-TYPE
			SYNTAX Integer32
			MAX-ACCESS read-only
			STATUS current
			DESCRIPTION
				"Description."
			::= { wriLineVtyEntry 15 }

		
		-- 1.3.6.1.4.1.3807.3.5.2.1.16
		wriLineVtyUser OBJECT-TYPE
			SYNTAX DisplayString
			MAX-ACCESS read-only
			STATUS current
			DESCRIPTION
				"Description."
			::= { wriLineVtyEntry 16 }

		
		-- 1.3.6.1.4.1.3807.3.5.2.1.17
		wriLineVtyAddress OBJECT-TYPE
			SYNTAX OCTET STRING
			MAX-ACCESS read-only
			STATUS current
			DESCRIPTION
				"Description."
			::= { wriLineVtyEntry 17 }

		
		-- 1.3.6.1.4.1.3807.3.5.2.1.18
		wriLineVtyCanclose OBJECT-TYPE
			SYNTAX Integer32
			MAX-ACCESS read-only
			STATUS current
			DESCRIPTION
				"Description."
			::= { wriLineVtyEntry 18 }

		
-- line user table                                  
		-- 1.3.6.1.4.1.3807.3.5.3
		wriLineUserTable OBJECT-TYPE
			SYNTAX SEQUENCE OF WriLineUserEntry
			MAX-ACCESS not-accessible
			STATUS current
			DESCRIPTION
				"line vty configure table."
			::= { wriLine 3 }

		
		-- 1.3.6.1.4.1.3807.3.5.3.1
		wriLineUserEntry OBJECT-TYPE
			SYNTAX WriLineUserEntry
			MAX-ACCESS not-accessible
			STATUS current
			DESCRIPTION
				"line vty configure entry."
			INDEX { wriLineUserIndex }
			::= { wriLineUserTable 1 }

		
		WriLineUserEntry ::=
			SEQUENCE { 
				wriLineUserIndex
					INTEGER,
				wriLineUserName
					OCTET STRING,
				wriLineUserPassword
					OCTET STRING,
				wriLineUserPrivilege
					INTEGER
			 }

		-- 1.3.6.1.4.1.3807.3.5.3.1.1
		wriLineUserIndex OBJECT-TYPE
			SYNTAX INTEGER
			MAX-ACCESS read-only
			STATUS current
			DESCRIPTION
				"line user index."
			::= { wriLineUserEntry 1 }

		
		-- 1.3.6.1.4.1.3807.3.5.3.1.2
		wriLineUserName OBJECT-TYPE
			SYNTAX OCTET STRING (SIZE (0..64))
			MAX-ACCESS read-write
			STATUS current
			DESCRIPTION
				"line user name"
			::= { wriLineUserEntry 2 }

		
		-- 1.3.6.1.4.1.3807.3.5.3.1.3
		wriLineUserPassword OBJECT-TYPE
			SYNTAX OCTET STRING (SIZE (0..64))
			MAX-ACCESS read-write
			STATUS current
			DESCRIPTION
				"line user password"
			::= { wriLineUserEntry 3 }

		
		-- 1.3.6.1.4.1.3807.3.5.3.1.4
		wriLineUserPrivilege OBJECT-TYPE
			SYNTAX INTEGER
			MAX-ACCESS read-write
			STATUS current
			DESCRIPTION
				"The privilege of line user."
			::= { wriLineUserEntry 4 }

		
	
	END

--
-- wriLine.mib
--
