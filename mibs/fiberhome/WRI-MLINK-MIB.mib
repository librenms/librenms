--
-- wriMlink.mib
-- MIB generated by MG-SOFT Visual MIB Builder Version 4.0 Build 349
-- Friday, January 14, 2011 at 15:12:47
-- 

	WRI-MLINK-MIB DEFINITIONS ::= BEGIN
 
		IMPORTS
			Integer32, OBJECT-TYPE,NOTIFICATION-TYPE
				FROM SNMPv2-SMI			
			wriProtocol			
				FROM WRI-SMI;
	
--
-- Node definitions
--
	
		wriMlink OBJECT IDENTIFIER ::= { wriProtocol 1332 }
		wriMlinkGeneral OBJECT IDENTIFIER ::= { wriMlink 1 }
		
		wriMlinkGeneralIfCount OBJECT-TYPE
			SYNTAX Integer32
			MAX-ACCESS read-only
			STATUS current
			DESCRIPTION
				"Mlink max interface number."
			::= { wriMlinkGeneral 1 }

		wriMlinkGeneralIfFreeCount OBJECT-TYPE
			SYNTAX Integer32
			MAX-ACCESS read-only
			STATUS current
			DESCRIPTION
				"Mlink free interface number."
			::= { wriMlinkGeneral 2 }

		wriMlinkGeneralGroupCount OBJECT-TYPE
			SYNTAX Integer32
			MAX-ACCESS read-only
			STATUS current
			DESCRIPTION
				"Mlink max group number."
			::= { wriMlinkGeneral 3 }

		wrMlinkGeneralGroupFreeCount OBJECT-TYPE
			SYNTAX Integer32
			MAX-ACCESS read-only
			STATUS current
			DESCRIPTION
				"Mlink free group number."
			::= { wriMlinkGeneral 4 }

		wriMlinkGeneralMemberCount OBJECT-TYPE
			SYNTAX Integer32
			MAX-ACCESS read-only
			STATUS current
			DESCRIPTION
				"Mlink max member number."
			::= { wriMlinkGeneral 5 }

		wriMlinkGeneralMemberFreeCount OBJECT-TYPE
			SYNTAX Integer32
			MAX-ACCESS read-only
			STATUS current
			DESCRIPTION
				"Mlink free member number."
			::= { wriMlinkGeneral 6 }	

		wriMlinkGroupTable OBJECT-TYPE
			SYNTAX SEQUENCE OF WriMlinkGroupEntry
			MAX-ACCESS not-accessible
			STATUS current
			DESCRIPTION
				"Description."
			::= { wriMlink 2 }

		wriMlinkGroupEntry OBJECT-TYPE
			SYNTAX WriMlinkGroupEntry
			MAX-ACCESS not-accessible
			STATUS current
			DESCRIPTION
				"Description."
			INDEX { wriMlinkGroupIndex }
			::= { wriMlinkGroupTable 1 }
		
		WriMlinkGroupEntry ::=
			SEQUENCE { 
				wriMlinkGroupIndex
					Integer32,
				wriMlinkGroupEntryStatus
					INTEGER,
				wriMlinkGroupTrapEnable
				  INTEGER
			 }

		wriMlinkGroupIndex OBJECT-TYPE
			SYNTAX Integer32
			MAX-ACCESS read-only
			STATUS current
			DESCRIPTION
				"Group index of this entry."
			::= { wriMlinkGroupEntry 1 }
		
		wriMlinkGroupEntryStatus OBJECT-TYPE
			SYNTAX INTEGER
				{
				valid(1),
				createRequest(2),
				underCreation(3),
				invalid(4)
				}
			MAX-ACCESS read-write
			STATUS current
			DESCRIPTION
				"Group entry-status."
			::= { wriMlinkGroupEntry 2 }

		wriMlinkGroupTrapEnable OBJECT-TYPE
			SYNTAX INTEGER
				{
				enable(1),
				disable(0)
				}
			MAX-ACCESS read-write
			STATUS current
			DESCRIPTION
				"Whether or not enable trap."
			::= { wriMlinkGroupEntry 3 }

		wriMlinkIfTable OBJECT-TYPE
			SYNTAX SEQUENCE OF WriMlinkIfEntry
			MAX-ACCESS not-accessible
			STATUS current
			DESCRIPTION
				"Description."
			::= { wriMlink 3 }

		wriMlinkIfEntry OBJECT-TYPE
			SYNTAX WriMlinkIfEntry
			MAX-ACCESS not-accessible
			STATUS current
			DESCRIPTION
				"Description."
			INDEX { wriMlinkIfIndex }
			::= { wriMlinkIfTable 1 }
		
		WriMlinkIfEntry ::=
			SEQUENCE { 
				wriMlinkIfIndex
					Integer32,
				wriMlinkIfLinkState
					INTEGER
			 }

		wriMlinkIfIndex OBJECT-TYPE
			SYNTAX Integer32
			MAX-ACCESS read-only
			STATUS current
			DESCRIPTION
				"Interface index."
			::= { wriMlinkIfEntry 1 }
		
		wriMlinkIfLinkState OBJECT-TYPE
			SYNTAX INTEGER
				{
				up(1),
				down(2)
				}
			MAX-ACCESS read-only
			STATUS current
			DESCRIPTION
				"Mlink interface link state."
			::= { wriMlinkIfEntry 2 }

		wriMlinkMemberTable OBJECT-TYPE
			SYNTAX SEQUENCE OF WriMlinkMemberEntry
			MAX-ACCESS not-accessible
			STATUS current
			DESCRIPTION
				"Description."
			::= { wriMlink 4 }

		wriMlinkMemberEntry OBJECT-TYPE
			SYNTAX WriMlinkMemberEntry
			MAX-ACCESS not-accessible
			STATUS current
			DESCRIPTION
				"Description."
			INDEX { wriMlinkMemberIfIndex, wriMlinkMemberGroupIndex }
			::= { wriMlinkMemberTable 1 }

		
		WriMlinkMemberEntry ::=
			SEQUENCE { 
				wriMlinkMemberIfIndex
					Integer32,
				wriMlinkMemberGroupIndex
					Integer32,
				wriMlinkMemberEntryStatus
					INTEGER,
				wriMlinkMemberRole
					INTEGER,
				wriMlinkMemberState
					INTEGER
			 }

		wriMlinkMemberIfIndex OBJECT-TYPE
			SYNTAX Integer32
			MAX-ACCESS read-only
			STATUS current
			DESCRIPTION
				"Mlink member interface index."
			::= { wriMlinkMemberEntry 1 }

		wriMlinkMemberGroupIndex OBJECT-TYPE
			SYNTAX Integer32
			MAX-ACCESS read-only
			STATUS current
			DESCRIPTION
				"Mlink member group index"
			::= { wriMlinkMemberEntry 2 }

		wriMlinkMemberEntryStatus OBJECT-TYPE
			SYNTAX INTEGER
				{
				valid(1),
				createRequest(2),
				underCreation(3),
				invalid(4)
				}
			MAX-ACCESS read-write
			STATUS current
			DESCRIPTION
				"Mlink member entry-status."
			::= { wriMlinkMemberEntry 3 }

		wriMlinkMemberRole OBJECT-TYPE
			SYNTAX INTEGER
				{
				uplink(0),
				downlink(1)
				}
			MAX-ACCESS read-write
			STATUS current
			DESCRIPTION
				"Mlink member role."
			::= { wriMlinkMemberEntry 4 }

		wriMlinkMemberState OBJECT-TYPE
			SYNTAX INTEGER
				{
				forward(1),
				block(2)
				}
			MAX-ACCESS read-only
			STATUS current
			DESCRIPTION
				"Mlink member state."
			::= { wriMlinkMemberEntry 5 }

		mlinkTrap			OBJECT IDENTIFIER ::=   {wriMlink 5}

		mlinkMemStateChangeTrap NOTIFICATION-TYPE
       		OBJECTS {wriMlinkMemberGroupIndex,wriMlinkMemberRole}
       		STATUS  current
       		DESCRIPTION
               	"mlink group uplinks state change."          
			::= { mlinkTrap 1}
	
	END

--
-- wriMlink.mib
--
