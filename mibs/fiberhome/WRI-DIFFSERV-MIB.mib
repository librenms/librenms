--
-- macLimit.mib
-- MIB generated by MG-SOFT Visual MIB Builder Version 6.0  Build 88
-- Monday, December 13, 2010 at 15:25:54
--

	WRI-DIFFSERV-MIB DEFINITIONS ::= BEGIN
 
		IMPORTS
			mib-2, Integer32, Unsigned32, OBJECT-TYPE, MODULE-IDENTITY,NOTIFICATION-TYPE	
				FROM SNMPv2-SMI			
			TEXTUAL-CONVENTION			
				FROM SNMPv2-TC			
			wriProtocol			
				FROM WRI-SMI;
	

		diffserv MODULE-IDENTITY 
			LAST-UPDATED "201107211500Z"		-- July 21, 2011 at 15:00 GMT
			ORGANIZATION 
				"FiberHome Networks Systems, Inc."
			CONTACT-INFO 
				"http://www.fhn.com.cn"
			DESCRIPTION 
				" The configure of diffserv domain."
			::= { wriProtocol 412 }

		
	
--
-- Textual conventions
--
	
--  Textual Conventions
		DisplayString ::=   OCTET STRING
		EntryStatus ::= TEXTUAL-CONVENTION
			STATUS current
			DESCRIPTION 
				"entry status."
			SYNTAX INTEGER
				{
				valid(1),
				createRequest(2),
				underCreation(3),
				invalid(4)
				}

	
--
-- Node definitions
--
	

		diffservGeneral OBJECT IDENTIFIER ::= { diffserv 1 }

		diffservFreeIndex OBJECT-TYPE
			SYNTAX Unsigned32 (0..32767)
			MAX-ACCESS read-only
			STATUS current
			DESCRIPTION
				"The free diffserv index."
			::= { diffservGeneral 1 }

		diffservDomainSize OBJECT-TYPE
			SYNTAX Integer32 (0..32767)
			MAX-ACCESS read-only
			STATUS current
			DESCRIPTION
				"The max index of diffserv."
			::= { diffservGeneral 2 }

		diffservDomainUsedSize OBJECT-TYPE
			SYNTAX Integer32 (0..32767)
			MAX-ACCESS read-only
			STATUS current
			DESCRIPTION
				"The used size of diffserv index."
			::= { diffservGeneral 3 }

	
		diffservInfoTable OBJECT-TYPE
			SYNTAX SEQUENCE OF DiffservInfoEntry
			MAX-ACCESS not-accessible
			STATUS current
			DESCRIPTION
				"The table of diffserv."
			::= { diffserv 2 }

		
		diffservInfoEntry OBJECT-TYPE
			SYNTAX DiffservInfoEntry
			MAX-ACCESS not-accessible
			STATUS current
			DESCRIPTION
				"The entry of diffserv."
			INDEX { dsDomainIndex  }
			::= { diffservInfoTable 1 }

		
		DiffservInfoEntry ::=
			SEQUENCE { 
				dsDomainIndex
					Integer32,
				dsDomainName
					OCTET STRING,
				dsDomainRefCnt 
					Integer32,
				dsDomainEntryStatus  
					EntryStatus,
				dsDomain8021pInDefault
					Integer32,
				dsDomain8021pOutDefault
					Integer32,
				dsDomainDscpInDefault
					Integer32,
				dsDomainDscpOutDefault
					Integer32,
				dsDomainExpInDefault
					Integer32,
				dsDomainExpOutDefault
					Integer32
			 }

		dsDomainIndex OBJECT-TYPE
			SYNTAX Integer32
			MAX-ACCESS read-only
			STATUS current
			DESCRIPTION
				"The index of diffserv."
			::= { diffservInfoEntry 1 }


		dsDomainName OBJECT-TYPE
			SYNTAX OCTET STRING
			MAX-ACCESS read-write
			STATUS current
			DESCRIPTION
				"The name of diffserv."
			::= { diffservInfoEntry 2 }

		dsDomainRefCnt OBJECT-TYPE
			SYNTAX Integer32			
			MAX-ACCESS read-only
			STATUS current
			DESCRIPTION
				"The refcnt of diffserv."
			::= { diffservInfoEntry 3 }

		dsDomainEntryStatus OBJECT-TYPE
			SYNTAX EntryStatus
			MAX-ACCESS read-write
			STATUS current
			DESCRIPTION
				"The status of diffserv ."
			::= { diffservInfoEntry 4 }
			
		dsDomain8021pInDefault OBJECT-TYPE
			SYNTAX Integer32			
			MAX-ACCESS read-write
			STATUS current
			DESCRIPTION
				"Configure 8021p inbound default info."
			::= { diffservInfoEntry 5 }
			
		dsDomain8021pOutDefault OBJECT-TYPE
			SYNTAX Integer32			
			MAX-ACCESS read-write
			STATUS current
			DESCRIPTION
				"Configure 8021p outbound default info."
			::= { diffservInfoEntry 6 }
		
		dsDomainDscpInDefault OBJECT-TYPE
			SYNTAX Integer32			
			MAX-ACCESS read-write
			STATUS current
			DESCRIPTION
				"Configure dscp inbound default info."
			::= { diffservInfoEntry 7 }
			
		dsDomainDscpOutDefault OBJECT-TYPE
			SYNTAX Integer32			
			MAX-ACCESS read-write
			STATUS current
			DESCRIPTION
				"Configure dscp outbound default info."
			::= { diffservInfoEntry 8 }
			
		dsDomainExpInDefault OBJECT-TYPE
			SYNTAX Integer32			
			MAX-ACCESS read-write
			STATUS current
			DESCRIPTION
				"Configure exp inbound default info."
			::= { diffservInfoEntry 9 }
			
		dsDomainExpOutDefault OBJECT-TYPE
			SYNTAX Integer32			
			MAX-ACCESS read-write
			STATUS current
			DESCRIPTION
				"Configure exp outbound default info."
			::= { diffservInfoEntry 10 }

		ds8021pInboundTable OBJECT-TYPE
			SYNTAX SEQUENCE OF Ds8021pInboundEntry
			MAX-ACCESS not-accessible
			STATUS current
			DESCRIPTION
				"The table of 8021p inbound info."
			::= { diffserv 3 }

		
		ds8021pInboundEntry OBJECT-TYPE
			SYNTAX Ds8021pInboundEntry
			MAX-ACCESS not-accessible
			STATUS current
			DESCRIPTION
				"The entry of 8021p inbound info."
			INDEX { dsInDomainIndex,dsInDot1pIndex  }
			::= { ds8021pInboundTable 1 }

		
		Ds8021pInboundEntry ::=
			SEQUENCE { 
				dsInDomainIndex
					Integer32,
				dsInDot1pIndex
					Integer32,
				ds8021pInPhb 
					INTEGER,
				ds8021pInColor
					INTEGER
			 }

		dsInDomainIndex OBJECT-TYPE
			SYNTAX Integer32
			MAX-ACCESS read-only
			STATUS current
			DESCRIPTION
				"The index of diffserv."
			::= { ds8021pInboundEntry 1 }

		
		dsInDot1pIndex OBJECT-TYPE
			SYNTAX Integer32
			MAX-ACCESS read-only
			STATUS current
			DESCRIPTION
				"The 802.1p priority of vlan packet."
			::= { ds8021pInboundEntry 2 }

		
		ds8021pInPhb OBJECT-TYPE
			SYNTAX INTEGER
				{
				  be(0),
				  af1(1),
				  af2(2),
				  af3(3),
				  af4(4),
				  ef(5),
				  cs6(6),
				  cs7(7),
				  default(8)
				}
			MAX-ACCESS read-write
			STATUS current
			DESCRIPTION
				"The phb action of 8021p inbound."
			::= { ds8021pInboundEntry 3 }


		ds8021pInColor OBJECT-TYPE
			SYNTAX INTEGER
				{
				  green(0),
				  yellow(1),
				  red(2)
				}
			MAX-ACCESS read-write
			STATUS current
			DESCRIPTION
				"The color of 8021p inbound."
			::= { ds8021pInboundEntry 4 }


		ds8021pOutnboundTable OBJECT-TYPE
			SYNTAX SEQUENCE OF Ds8021pOutnboundEntry
			MAX-ACCESS not-accessible
			STATUS current
			DESCRIPTION
				"The table of 8021p outbound."
			::= { diffserv 4 }

		
		ds8021pOutnboundEntry OBJECT-TYPE
			SYNTAX Ds8021pOutnboundEntry
			MAX-ACCESS not-accessible
			STATUS current
			DESCRIPTION
				"The entry of 8021p outbound."
			INDEX { dsOutDomainIndex,ds8021pOutPhb,ds8021pOutColor }
			::= { ds8021pOutnboundTable 1 }

		
		Ds8021pOutnboundEntry ::=
			SEQUENCE { 
				dsOutDomainIndex
					Integer32,
				ds8021pOutPhb
					INTEGER,
				ds8021pOutColor
					INTEGER,
				dsOutDot1pIndex 
					Integer32
			 }

		dsOutDomainIndex OBJECT-TYPE
			SYNTAX Integer32
			MAX-ACCESS read-only
			STATUS current
			DESCRIPTION
				"The index of diffserv."
			::= { ds8021pOutnboundEntry 1 }

		
		ds8021pOutPhb OBJECT-TYPE
			SYNTAX INTEGER
			{	  
				  be(0),
				  af1(1),
				  af2(2),
				  af3(3),
				  af4(4),
				  ef(5),
				  cs6(6),
				  cs7(7)
				}
			MAX-ACCESS read-only
			STATUS current
			DESCRIPTION
				"The phb action  of 8021p outbound."
			::= { ds8021pOutnboundEntry 2 }


		ds8021pOutColor OBJECT-TYPE
			SYNTAX INTEGER
				{
				  green(0),
				  yellow(1),
				  red(2)
				}
			MAX-ACCESS read-only
			STATUS current
			DESCRIPTION
				"The color of 8021p outbound."
			::= { ds8021pOutnboundEntry 3 }

		
		dsOutDot1pIndex OBJECT-TYPE
			SYNTAX Integer32
			MAX-ACCESS read-write
			STATUS current
			DESCRIPTION
				"The 802.1p priority of vlan packet."
			::= { ds8021pOutnboundEntry 4 }


		dsIpDscpInboundTable OBJECT-TYPE
			SYNTAX SEQUENCE OF DsIpDscpInboundEntry
			MAX-ACCESS not-accessible
			STATUS current
			DESCRIPTION
				"The table of ip dscp info."
			::= { diffserv 5 }

		
		dsIpDscpInboundEntry OBJECT-TYPE
			SYNTAX DsIpDscpInboundEntry
			MAX-ACCESS not-accessible
			STATUS current
			DESCRIPTION
				"The entry of ip dscp inbound info."
			INDEX { dsDscpInDomainIndex,dsDscpInIndex  }
			::= { dsIpDscpInboundTable 1 }

		
		DsIpDscpInboundEntry ::=
			SEQUENCE { 
				dsDscpInDomainIndex
					Integer32,
				dsDscpInIndex
					Integer32,
				dsIpDscpInPhb
					INTEGER,
				dsIpDscpInColor
					INTEGER
			 }

		dsDscpInDomainIndex OBJECT-TYPE
			SYNTAX Integer32
			MAX-ACCESS read-only
			STATUS current
			DESCRIPTION
				"The index of diffserv."
			::= { dsIpDscpInboundEntry 1 }

		
		dsDscpInIndex OBJECT-TYPE
			SYNTAX Integer32
			MAX-ACCESS read-only
			STATUS current
			DESCRIPTION
				"The dscp priority of ip packet."
			::= { dsIpDscpInboundEntry 2 }

		
		dsIpDscpInPhb OBJECT-TYPE
			SYNTAX INTEGER
				{
				  be(0),
				  af1(1),
				  af2(2),
				  af3(3),
				  af4(4),
				  ef(5),
				  cs6(6),
				  cs7(7),
				  default(8)
				}
			MAX-ACCESS read-write
			STATUS current
			DESCRIPTION
				"The phb action of ip packet inbound."
			::= { dsIpDscpInboundEntry 3 }


		dsIpDscpInColor OBJECT-TYPE
			SYNTAX INTEGER
				{
				  green(0),
				  yellow(1),
				  red(2)
				}
			MAX-ACCESS read-write
			STATUS current
			DESCRIPTION
				"The color of ip packet inbound."
			::= { dsIpDscpInboundEntry 4 }


		dsIpDscpOutTable OBJECT-TYPE
			SYNTAX SEQUENCE OF DsIpDscpOutEntry
			MAX-ACCESS not-accessible
			STATUS current
			DESCRIPTION
				"The table of ip dscp inboun."
			::= { diffserv 6 }

		
		dsIpDscpOutEntry OBJECT-TYPE
			SYNTAX DsIpDscpOutEntry
			MAX-ACCESS not-accessible
			STATUS current
			DESCRIPTION
				"The entry of ip dscp inboun."
			INDEX { dsDscpOutDomainIndex,dsIpDscpOutPhb,dsIpDscpOutColor }
			::= { dsIpDscpOutTable 1 }

		
		DsIpDscpOutEntry ::=
			SEQUENCE { 
				dsDscpOutDomainIndex
					Integer32,
				dsIpDscpOutPhb
					INTEGER,
				dsIpDscpOutColor
					INTEGER,
				dsIpDscpOut 
					Integer32
			 }

		dsDscpOutDomainIndex OBJECT-TYPE
			SYNTAX Integer32
			MAX-ACCESS read-only
			STATUS current
			DESCRIPTION
				"The index of diffserv."
			::= { dsIpDscpOutEntry 1 }

		
		dsIpDscpOutPhb OBJECT-TYPE
			SYNTAX INTEGER
			{
				  be(0),
				  af1(1),
				  af2(2),
				  af3(3),
				  af4(4),
				  ef(5),
				  cs6(6),
				  cs7(7)
				}
			MAX-ACCESS read-only
			STATUS current
			DESCRIPTION
				"The phb action of ip dscp inbound."
			::= { dsIpDscpOutEntry 2 }


		dsIpDscpOutColor OBJECT-TYPE
			SYNTAX INTEGER
				{
					green(0),
				  yellow(1),
				  red(2)
				}
			MAX-ACCESS read-only
			STATUS current
			DESCRIPTION
				"The color of ip dscp inbound."
			::= { dsIpDscpOutEntry 3 }

		
		dsIpDscpOut OBJECT-TYPE
			SYNTAX Integer32
			MAX-ACCESS read-write
			STATUS current
			DESCRIPTION
				"The dscp priority of ip packet."
			::= { dsIpDscpOutEntry 4 }


		diffservIfTable OBJECT-TYPE
			SYNTAX SEQUENCE OF DiffservIfEntry
			MAX-ACCESS not-accessible
			STATUS current
			DESCRIPTION
				"The table of diffserv on interface."
			::= { diffserv 7 }

		
		diffservIfEntry OBJECT-TYPE
			SYNTAX DiffservIfEntry
			MAX-ACCESS not-accessible
			STATUS current
			DESCRIPTION
				"The entry of diffserv on interface."
			INDEX { diffservIfIndex}
			::= { diffservIfTable 1 }

		
		DiffservIfEntry ::=
			SEQUENCE { 
				diffservIfIndex
					Integer32,
				diffservIfDomainIndex 
					Integer32,
				diffservIfMode
					INTEGER
			 }

		diffservIfIndex OBJECT-TYPE
			SYNTAX Integer32
			MAX-ACCESS read-only
			STATUS current
			DESCRIPTION
				"The interface index."
			::= { diffservIfEntry 1 }

		
		diffservIfDomainIndex OBJECT-TYPE
			SYNTAX Integer32
			MAX-ACCESS read-write
			STATUS current
			DESCRIPTION
				"The index of diffserv."
			::= { diffservIfEntry 2 }


		diffservIfMode OBJECT-TYPE
			SYNTAX INTEGER
				{ 
					no-trust(0),
					inner-8021p(1),
					outer-8021p(2),
					dscp(3)
	
				}
			MAX-ACCESS read-write
			STATUS current
			DESCRIPTION
				"The trust mode of diffserv on interface."
			::= { diffservIfEntry 3 }

		
		dsMplsExpInboundTable OBJECT-TYPE
			SYNTAX SEQUENCE OF DsMplsExpInboundEntry
			MAX-ACCESS not-accessible
			STATUS current
			DESCRIPTION
				"The table of mpls exp inbound info."
			::= { diffserv 8 }

		
		dsMplsExpInboundEntry OBJECT-TYPE
			SYNTAX DsMplsExpInboundEntry
			MAX-ACCESS not-accessible
			STATUS current
			DESCRIPTION
				"The entry of mpls exp inbound info."
			INDEX { dsMplsExpInDomainIndex,dsMplsExpInIndex  }
			::= { dsMplsExpInboundTable 1 }

		
		DsMplsExpInboundEntry ::=
			SEQUENCE { 
				dsMplsExpInDomainIndex
					Integer32,
				dsMplsExpInIndex
					Integer32,
				dsMplsExpInPhb 
					INTEGER,
				dsMplsExpInColor
					INTEGER
			 }

		dsMplsExpInDomainIndex OBJECT-TYPE
			SYNTAX Integer32
			MAX-ACCESS read-only
			STATUS current
			DESCRIPTION
				"The index of diffserv."
			::= { dsMplsExpInboundEntry 1 }

		
		dsMplsExpInIndex OBJECT-TYPE
			SYNTAX Integer32
			MAX-ACCESS read-only
			STATUS current
			DESCRIPTION
				"The mpls exp priority of vlan packet."
			::= { dsMplsExpInboundEntry 2 }

		
		dsMplsExpInPhb OBJECT-TYPE
			SYNTAX INTEGER
				{
				  be(0),
				  af1(1),
				  af2(2),
				  af3(3),
				  af4(4),
				  ef(5),
				  cs6(6),
				  cs7(7),
				  default(8)
				}
			MAX-ACCESS read-write
			STATUS current
			DESCRIPTION
				"The phb action of mpls exp inbound."
			::= { dsMplsExpInboundEntry 3 }


		dsMplsExpInColor OBJECT-TYPE
			SYNTAX INTEGER
				{
				  green(0),
				  yellow(1),
				  red(2)
				}
			MAX-ACCESS read-write
			STATUS current
			DESCRIPTION
				"The color of mpls exp inbound."
			::= { dsMplsExpInboundEntry 4 }


		dsMplsExpOutboundTable OBJECT-TYPE
			SYNTAX SEQUENCE OF DsMplsExpOutboundEntry
			MAX-ACCESS not-accessible
			STATUS current
			DESCRIPTION
				"The table of mpls exp outbound."
			::= { diffserv 9 }

		
		dsMplsExpOutboundEntry OBJECT-TYPE
			SYNTAX DsMplsExpOutboundEntry
			MAX-ACCESS not-accessible
			STATUS current
			DESCRIPTION
				"The entry of mpls exp outbound."
			INDEX { dsMplsExpOutDomainIndex,dsMplsExpOutPhb,dsMplsExpOutColor }
			::= { dsMplsExpOutboundTable 1 }

		
		DsMplsExpOutboundEntry ::=
			SEQUENCE { 
				dsMplsExpOutDomainIndex
					Integer32,
				dsMplsExpOutPhb
					INTEGER,
				dsMplsExpOutColor
					INTEGER,
				dsMplsExpOutIndex 
					Integer32
			 }

		dsMplsExpOutDomainIndex OBJECT-TYPE
			SYNTAX Integer32
			MAX-ACCESS read-only
			STATUS current
			DESCRIPTION
				"The index of diffserv."
			::= { dsMplsExpOutboundEntry 1 }

		
		dsMplsExpOutPhb OBJECT-TYPE
			SYNTAX INTEGER
			{	  
				  be(0),
				  af1(1),
				  af2(2),
				  af3(3),
				  af4(4),
				  ef(5),
				  cs6(6),
				  cs7(7)
				}
			MAX-ACCESS read-only
			STATUS current
			DESCRIPTION
				"The phb action  of mpls exp outbound."
			::= { dsMplsExpOutboundEntry 2 }


		dsMplsExpOutColor OBJECT-TYPE
			SYNTAX INTEGER
				{
				  green(0),
				  yellow(1),
				  red(2)
				}
			MAX-ACCESS read-only
			STATUS current
			DESCRIPTION
				"The color of mpls exp outbound."
			::= { dsMplsExpOutboundEntry 3 }

		
		dsMplsExpOutIndex OBJECT-TYPE
			SYNTAX Integer32
			MAX-ACCESS read-write
			STATUS current
			DESCRIPTION
				"The mpls exp priority of vlan packet."
			::= { dsMplsExpOutboundEntry 4 }
	END

--
-- macLimit.mib
--
