--
-- tunnel.mib
-- MIB generated by MG-SOFT Visual MIB Builder Version 6.0  Build 88
-- Monday, December 13, 2011 at 15:25:54
--

	WRI-TUNNEL-MIB DEFINITIONS ::= BEGIN
 
		IMPORTS
			mib-2, Integer32, Unsigned32, OBJECT-TYPE, MODULE-IDENTITY,NOTIFICATION-TYPE	
				FROM SNMPv2-SMI					
			TEXTUAL-CONVENTION, TruthValue, TimeInterval,RowStatus,
				MacAddress,PhysAddress		FROM SNMPv2-TC
			InetAddressPrefixLength,InetAddressType,
				InetPortNumber,InetAddress			FROM INET-ADDRESS-MIB
			SnmpAdminString							FROM SNMP-FRAMEWORK-MIB
    		InterfaceIndex							FROM IF-MIB
			wriProtocol			
				FROM WRI-SMI;
	

		tunnel MODULE-IDENTITY 
			LAST-UPDATED "201107211500Z"		-- July 21, 2011 at 15:00 GMT
			ORGANIZATION 
				"FiberHome Networks Systems, Inc."
			CONTACT-INFO 
				"http://www.fhn.com.cn"
			DESCRIPTION 
				" The configure of tunnel domain."
			::= { wriProtocol 2004 }

--
-- Textual conventions
--
	
--  Textual Conventions
		DisplayString ::=   OCTET STRING
		EntryStatus ::= TEXTUAL-CONVENTION
			STATUS current
			DESCRIPTION 
				"entry status."
			SYNTAX INTEGER
				{
				valid(1),
				createRequest(2),
				underCreation(3),
				invalid(4)
				}
--
-- Node definitions
--
		tunnelInfoTable OBJECT-TYPE
			SYNTAX SEQUENCE OF TunnelInfoEntry
			MAX-ACCESS not-accessible
			STATUS current
			DESCRIPTION
				"The table of tunnel."
			::= { tunnel 1 }

		
		tunnelInfoEntry OBJECT-TYPE
			SYNTAX TunnelInfoEntry
			MAX-ACCESS not-accessible
			STATUS current
			DESCRIPTION
				"The entry of tunnel."
			INDEX { tunnelIndex   }
			::= { tunnelInfoTable 1 }

		
		TunnelInfoEntry ::=
			SEQUENCE { 
				tunnelIndex 
					Integer32,
				tunnelEncapsMethod 
					INTEGER,
				tunnelIpType 
					InetAddressType,
				tunnelSourceAddr  
					InetAddress,
				tunnelDestAddr
					InetAddress,
				tunnelVpnName
					OCTET STRING,
				tunnelEncapsulationlimit
					Integer32,
				tunnelFlowLabel 
					Unsigned32,
				tunnelTrafficClass
					Integer32,
				tunnelHopLimit
					Integer32,
				tunnelIpAddress
				    OCTET STRING,
				tunnel6rdV6PrefixAddress
					OCTET STRING,
				tunnel6rdBrV4Address
					OCTET STRING,
				tunnel6rdV6PrefixLength
					Integer32,
				tunnel6rdV4PrefixLength
					Integer32,
				tunnelSourceIfindex
					Integer32,
				tunnelMplsTeId
					Integer32,
				tunnelAdminStatus
					Integer32,
				tunnelMtu
					Integer32,
				tunnelInterfaceRowStatus
					Integer32
			 }

		tunnelIndex OBJECT-TYPE
			SYNTAX Integer32
			MAX-ACCESS read-only
			STATUS current
			DESCRIPTION
				"The index of tunnel."
			::= { tunnelInfoEntry 1 }

		tunnelEncapsMethod OBJECT-TYPE
			SYNTAX INTEGER
			{
				other(1),        
                direct(2),      
                gre(3),          
                minimal(4),      
                l2tp(5),         
                pptp(6),         
                l2f(7),          
                udp(8),          
                atmp(9),        
                msdp(10),        
                sixToFour(11),  
                sixOverFour(12), 
                isatap(13),
				teredo(14),
				iphttps(15),
				ipinip(100),
				sixToFoursecure(101),
				pimsmdr1(102),
				pimsmdr2(103)
			}
			MAX-ACCESS read-write
			STATUS current
			DESCRIPTION
				"The encaps method of tunnel."
			::= { tunnelInfoEntry 2 }

		tunnelIpType OBJECT-TYPE
			SYNTAX InetAddressType			
			MAX-ACCESS read-write
			STATUS current
			DESCRIPTION
				"The type of source ip address."
			::= { tunnelInfoEntry 3 }

		tunnelSourceAddr OBJECT-TYPE
			SYNTAX InetAddress
			MAX-ACCESS read-write
			STATUS current
			DESCRIPTION
				"The source ip address."
			::= { tunnelInfoEntry 4 }

		tunnelDestAddr OBJECT-TYPE
			SYNTAX InetAddress
			MAX-ACCESS read-write
			STATUS current
			DESCRIPTION
				"The destination ip address."
			::= { tunnelInfoEntry 5 }
		
		tunnelVpnName OBJECT-TYPE
			SYNTAX OCTET STRING
			MAX-ACCESS read-write
			STATUS current
			DESCRIPTION
				"The vpn name of tunnel."
			::= { tunnelInfoEntry 6 }
			
		tunnelEncapsulationlimit OBJECT-TYPE
			SYNTAX Integer32 (0..255)
			MAX-ACCESS read-write
			STATUS current
			DESCRIPTION
				"The encapsulation limit value of tunnel."			
			DEFVAL {4}
			::= { tunnelInfoEntry 7 }

		tunnelFlowLabel  OBJECT-TYPE 
			SYNTAX Unsigned32 
			MAX-ACCESS read-write
			STATUS current
			DESCRIPTION
				"The flow label value of tunnel."
			::= { tunnelInfoEntry 8 }

		tunnelTrafficClass OBJECT-TYPE
			SYNTAX Integer32 
			MAX-ACCESS read-write
			STATUS current
			DESCRIPTION
				"The traffic class value of tunnel."
			DEFVAL {0}
			::= { tunnelInfoEntry 9 }

		tunnelHopLimit OBJECT-TYPE
			SYNTAX Integer32 (1..255)
			MAX-ACCESS read-write
			STATUS current
			DESCRIPTION
				"The hop limit value of tunnel."
			DEFVAL {0}
			::= { tunnelInfoEntry 10 }
			
		tunnelIpAddress OBJECT-TYPE
			SYNTAX OCTET STRING
			MAX-ACCESS read-write
			STATUS current
			DESCRIPTION
				"The ip address of tunnel interface."
			::= { tunnelInfoEntry 11}
			
		tunnel6rdV6PrefixAddress OBJECT-TYPE
			SYNTAX OCTET STRING
			MAX-ACCESS read-write
			STATUS current
			DESCRIPTION
				"The 6rd v6 address of tunnel interface."
			::= { tunnelInfoEntry 12}
			
		tunnel6rdBrV4Address OBJECT-TYPE
			SYNTAX OCTET STRING
			MAX-ACCESS read-write
			STATUS current
			DESCRIPTION
				"The 6rd br address of tunnel interface."
			::= { tunnelInfoEntry 13}
			
		tunnel6rdV6PrefixLength OBJECT-TYPE
			SYNTAX Integer32 (0..255)
			MAX-ACCESS read-write
			STATUS current
			DESCRIPTION
				"The 6rd v6 prefix length of tunnel."
			::= { tunnelInfoEntry 14 }
			
		tunnel6rdV4PrefixLength OBJECT-TYPE
			SYNTAX Integer32 (0..255)
			MAX-ACCESS read-write
			STATUS current
			DESCRIPTION
				"The 6rd v4 prefix length of tunnel."
			::= { tunnelInfoEntry 15 }
		
		tunnelSourceIfindex OBJECT-TYPE
			SYNTAX Integer32 (0..255)
			MAX-ACCESS read-write
			STATUS current
			DESCRIPTION
				"The source ifindex of tunnel."
			::= { tunnelInfoEntry 16 }
			
		tunnelMplsTeId	OBJECT-TYPE
			SYNTAX Integer32 (0..255)
			MAX-ACCESS read-write
			STATUS current
			DESCRIPTION
				"The mpls te id."
			::= { tunnelInfoEntry 17 }
			
		tunnelAdminStatus OBJECT-TYPE
			SYNTAX Integer32 
			MAX-ACCESS read-write
			STATUS current
			DESCRIPTION
				"The admin status."
			::= { tunnelInfoEntry 18 }
			
		tunnelMtu OBJECT-TYPE
			SYNTAX Integer32 
			MAX-ACCESS read-write
			STATUS current
			DESCRIPTION
				"Mtu."
			::= { tunnelInfoEntry 19 }
		
		tunnelInterfaceRowStatus OBJECT-TYPE
			SYNTAX Integer32 
			MAX-ACCESS read-write
			STATUS current
			DESCRIPTION
				"Row Status."
			::= { tunnelInfoEntry 20 }
		
	
	END

--
-- macLimit.mib
--
