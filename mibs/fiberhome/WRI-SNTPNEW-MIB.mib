--
-- wriSntpNew.mib
-- MIB generated by MG-SOFT Visual MIB Builder Version 4.0 Build 349
-- Tuesday, April 20, 2010 at 09:13:40
--

--  wriSntpNew.mib
-- MIB generated by MG-SOFT Visual MIB Builder Version 4.0 Build 349
-- Thursday, April 15, 2010 at 15:12:33
-- 
--  wriSntpNew.mib
-- MIB generated by MG-SOFT Visual MIB Builder Version 4.0 Build 349
-- Friday, April 09, 2010 at 11:01:14
-- 
--  wriSntpNew.mib
-- MIB generated by MG-SOFT Visual MIB Builder Version 4.0 Build 349
-- Thursday, April 08, 2010 at 14:56:03
-- 

	WRI-SNTPNEW-MIB DEFINITIONS ::= BEGIN
 
		IMPORTS
			OBJECT-TYPE			
				FROM SNMPv2-SMI			
			wriProtocol			
				FROM WRI-SMI;
	
	
--
-- Node definitions
--
	
--  Node definitions
-- 
-- Node definitions
-- 
-- Node definitions
-- 
-- 1.3.6.1.4.1.3807.2.1910
-- 1.3.6.1.4.1.3807.2.1910
-- 1.3.6.1.4.1.3807.2.1910
		-- 1.3.6.1.4.1.3807.2.1910
		wriSntpNew OBJECT IDENTIFIER ::= { wriProtocol 1910 }

		
--    1.3.6.1.4.1.3807.2.1910.1
-- 1.3.6.1.4.1.3807.2.1910.1
-- 1.3.6.1.4.1.3807.2.1910.1
		-- 1.3.6.1.4.1.3807.2.1910.1
		sntpClientCommon OBJECT IDENTIFIER ::= { wriSntpNew 1 }

		
--    1.3.6.1.4.1.3807.2.1910.1.1
-- 1.3.6.1.4.1.3807.2.1910.1.1
-- 1.3.6.1.4.1.3807.2.1910.1.1
		-- 1.3.6.1.4.1.3807.2.1910.1.1
		sntpClientTimeFlag OBJECT-TYPE
			SYNTAX INTEGER
				{
				plus(1),
				minus(2)
				}
			MAX-ACCESS read-write
			STATUS current
			DESCRIPTION
				"Description."
			::= { sntpClientCommon 1 }

		
--    1.3.6.1.4.1.3807.2.1910.1.2
-- 1.3.6.1.4.1.3807.2.1910.1.2
-- 1.3.6.1.4.1.3807.2.1910.1.2
		-- 1.3.6.1.4.1.3807.2.1910.1.2
		sntpClientTimeOffset OBJECT-TYPE
			SYNTAX INTEGER
			MAX-ACCESS read-write
			STATUS current
			DESCRIPTION
				"Description."
			::= { sntpClientCommon 2 }

		
--    1.3.6.1.4.1.3807.2.1910.1.3
-- 1.3.6.1.4.1.3807.2.1910.1.3
-- 1.3.6.1.4.1.3807.2.1910.1.3
		-- 1.3.6.1.4.1.3807.2.1910.1.3
		sntpClientNotifyTime OBJECT-TYPE
			SYNTAX INTEGER
			MAX-ACCESS read-write
			STATUS current
			DESCRIPTION
				"Description."
			::= { sntpClientCommon 3 }

		
--    1.3.6.1.4.1.3807.2.1910.2
-- 1.3.6.1.4.1.3807.2.1910.2
-- 1.3.6.1.4.1.3807.2.1910.2
		-- 1.3.6.1.4.1.3807.2.1910.2
		sntpClientTable OBJECT-TYPE
			SYNTAX SEQUENCE OF SntpClientEntry
			MAX-ACCESS not-accessible
			STATUS current
			DESCRIPTION
				"Description."
			::= { wriSntpNew 2 }

		
--    1.3.6.1.4.1.3807.2.1910.2.1
-- 1.3.6.1.4.1.3807.2.1910.2.1
-- 1.3.6.1.4.1.3807.2.1910.2.1
		-- 1.3.6.1.4.1.3807.2.1910.2.1
		sntpClientEntry OBJECT-TYPE
			SYNTAX SntpClientEntry
			MAX-ACCESS not-accessible
			STATUS current
			DESCRIPTION
				"Description."
			INDEX { sntpClientIpType, sntpClientIpAddr }
			::= { sntpClientTable 1 }

		
		SntpClientEntry ::=
			SEQUENCE { 
				sntpClientIpType
					INTEGER,
				sntpClientIpAddr
					OCTET STRING,
				sntpClientWorkMode
					INTEGER,
				sntpClientServerIp
					OCTET STRING,
				sntpClientServerPort
					INTEGER,
				sntpClientServerIp2
					OCTET STRING,
				sntpClientServePort2
					INTEGER,
				sntpClientPort
					INTEGER,
				sntpClientVersion
					INTEGER,
				sntpClientRowstatus
					INTEGER
			 }

--    1.3.6.1.4.1.3807.2.1910.2.1.1
-- 1.3.6.1.4.1.3807.2.1910.2.1.1
-- 1.3.6.1.4.1.3807.2.1910.2.1.1
		-- 1.3.6.1.4.1.3807.2.1910.2.1.1
		sntpClientIpType OBJECT-TYPE
			SYNTAX INTEGER
			MAX-ACCESS read-only
			STATUS current
			DESCRIPTION
				"Description."
			::= { sntpClientEntry 1 }

		
--    1.3.6.1.4.1.3807.2.1910.2.1.2
-- 1.3.6.1.4.1.3807.2.1910.2.1.2
-- 1.3.6.1.4.1.3807.2.1910.2.1.2
		-- 1.3.6.1.4.1.3807.2.1910.2.1.2
		sntpClientIpAddr OBJECT-TYPE
			SYNTAX OCTET STRING
			MAX-ACCESS read-only
			STATUS current
			DESCRIPTION
				"Description."
			::= { sntpClientEntry 2 }

		
--    1.3.6.1.4.1.3807.2.1910.2.1.3
-- 1.3.6.1.4.1.3807.2.1910.2.1.3
-- 1.3.6.1.4.1.3807.2.1910.2.1.3
		-- 1.3.6.1.4.1.3807.2.1910.2.1.3
		sntpClientWorkMode OBJECT-TYPE
			SYNTAX INTEGER
			MAX-ACCESS read-write
			STATUS current
			DESCRIPTION
				"Description."
			::= { sntpClientEntry 3 }

		
--    1.3.6.1.4.1.3807.2.1910.2.1.4
-- 1.3.6.1.4.1.3807.2.1910.2.1.4
-- 1.3.6.1.4.1.3807.2.1910.2.1.4
		-- 1.3.6.1.4.1.3807.2.1910.2.1.4
		sntpClientServerIp OBJECT-TYPE
			SYNTAX OCTET STRING
			MAX-ACCESS read-write
			STATUS current
			DESCRIPTION
				"Description."
			::= { sntpClientEntry 4 }

		
		-- 1.3.6.1.4.1.3807.2.1910.2.1.5
		sntpClientServerPort OBJECT-TYPE
			SYNTAX INTEGER
			MAX-ACCESS read-write
			STATUS current
			DESCRIPTION
				"Description."
			::= { sntpClientEntry 5 }

		
--  1.3.6.1.4.1.3807.2.1910.2.1.5
		-- 1.3.6.1.4.1.3807.2.1910.2.1.6
		sntpClientServerIp2 OBJECT-TYPE
			SYNTAX OCTET STRING
			MAX-ACCESS read-write
			STATUS current
			DESCRIPTION
				"Description."
			::= { sntpClientEntry 6 }

		
		-- 1.3.6.1.4.1.3807.2.1910.2.1.7
		sntpClientServePort2 OBJECT-TYPE
			SYNTAX INTEGER
			MAX-ACCESS read-write
			STATUS current
			DESCRIPTION
				"Description."
			::= { sntpClientEntry 7 }

		
--    1.3.6.1.4.1.3807.2.1910.2.1.5
-- 1.3.6.1.4.1.3807.2.1910.2.1.5
-- 1.3.6.1.4.1.3807.2.1910.2.1.6
		-- 1.3.6.1.4.1.3807.2.1910.2.1.8
		sntpClientPort OBJECT-TYPE
			SYNTAX INTEGER
			MAX-ACCESS read-write
			STATUS current
			DESCRIPTION
				"Description."
			::= { sntpClientEntry 8 }

		
--   1.3.6.1.4.1.3807.2.1910.2.1.6
-- 1.3.6.1.4.1.3807.2.1910.2.1.7
		-- 1.3.6.1.4.1.3807.2.1910.2.1.9
		sntpClientVersion OBJECT-TYPE
			SYNTAX INTEGER
			MAX-ACCESS read-write
			STATUS current
			DESCRIPTION
				"Description."
			::= { sntpClientEntry 9 }

		
--    1.3.6.1.4.1.3807.2.1910.2.1.6
-- 1.3.6.1.4.1.3807.2.1910.2.1.7
-- 1.3.6.1.4.1.3807.2.1910.2.1.8
		-- 1.3.6.1.4.1.3807.2.1910.2.1.10
		sntpClientRowstatus OBJECT-TYPE
			SYNTAX INTEGER
			MAX-ACCESS read-write
			STATUS current
			DESCRIPTION
				"Description."
			::= { sntpClientEntry 10 }

		
--  1.3.6.1.4.1.3807.2.1910.3
		-- 1.3.6.1.4.1.3807.2.1910.3
		sntpServerCommon OBJECT IDENTIFIER ::= { wriSntpNew 3 }

		
--  1.3.6.1.4.1.3807.2.1910.3.1
		-- 1.3.6.1.4.1.3807.2.1910.3.1
		sntpServerNotifyTime OBJECT-TYPE
			SYNTAX INTEGER
			MAX-ACCESS read-write
			STATUS current
			DESCRIPTION
				"Description."
			::= { sntpServerCommon 1 }

		
--    1.3.6.1.4.1.3807.2.1910.3
-- 1.3.6.1.4.1.3807.2.1910.3
-- 1.3.6.1.4.1.3807.2.1910.4
		-- 1.3.6.1.4.1.3807.2.1910.4
		sntpServerTable OBJECT-TYPE
			SYNTAX SEQUENCE OF SntpServerEntry
			MAX-ACCESS not-accessible
			STATUS current
			DESCRIPTION
				"Description."
			::= { wriSntpNew 4 }

		
--    1.3.6.1.4.1.3807.2.1910.3.1
-- 1.3.6.1.4.1.3807.2.1910.3.1
-- 1.3.6.1.4.1.3807.2.1910.4.1
		-- 1.3.6.1.4.1.3807.2.1910.4.1
		sntpServerEntry OBJECT-TYPE
			SYNTAX SntpServerEntry
			MAX-ACCESS not-accessible
			STATUS current
			DESCRIPTION
				"Description."
			INDEX { sntpServerIpType, sntpServerIpAddr }
			::= { sntpServerTable 1 }

		
		SntpServerEntry ::=
			SEQUENCE { 
				sntpServerIpType
					INTEGER,
				sntpServerIpAddr
					OCTET STRING,
				sntpServerWorkMode
					INTEGER,
				sntpServerPort
					INTEGER,
				sntpServerVersion
					INTEGER,
				sntpServerRowstatus
					INTEGER
			 }

--    1.3.6.1.4.1.3807.2.1910.3.1.1
-- 1.3.6.1.4.1.3807.2.1910.3.1.1
-- 1.3.6.1.4.1.3807.2.1910.4.1.1
		-- 1.3.6.1.4.1.3807.2.1910.4.1.1
		sntpServerIpType OBJECT-TYPE
			SYNTAX INTEGER
			MAX-ACCESS read-only
			STATUS current
			DESCRIPTION
				"Description."
			::= { sntpServerEntry 1 }

		
--    1.3.6.1.4.1.3807.2.1910.3.1.2
-- 1.3.6.1.4.1.3807.2.1910.3.1.2
-- 1.3.6.1.4.1.3807.2.1910.4.1.2
		-- 1.3.6.1.4.1.3807.2.1910.4.1.2
		sntpServerIpAddr OBJECT-TYPE
			SYNTAX OCTET STRING
			MAX-ACCESS read-only
			STATUS current
			DESCRIPTION
				"Description."
			::= { sntpServerEntry 2 }

		
--    1.3.6.1.4.1.3807.2.1910.3.1.3
-- 1.3.6.1.4.1.3807.2.1910.3.1.3
-- 1.3.6.1.4.1.3807.2.1910.4.1.3
		-- 1.3.6.1.4.1.3807.2.1910.4.1.3
		sntpServerWorkMode OBJECT-TYPE
			SYNTAX INTEGER
			MAX-ACCESS read-write
			STATUS current
			DESCRIPTION
				"Description."
			::= { sntpServerEntry 3 }

		
--    1.3.6.1.4.1.3807.2.1910.3.1.4
-- 1.3.6.1.4.1.3807.2.1910.3.1.4
-- 1.3.6.1.4.1.3807.2.1910.4.1.4
		-- 1.3.6.1.4.1.3807.2.1910.4.1.4
		sntpServerPort OBJECT-TYPE
			SYNTAX INTEGER
			MAX-ACCESS read-write
			STATUS current
			DESCRIPTION
				"Description."
			::= { sntpServerEntry 4 }

		
--   1.3.6.1.4.1.3807.2.1910.3.1.6
-- 1.3.6.1.4.1.3807.2.1910.4.1.5
		-- 1.3.6.1.4.1.3807.2.1910.4.1.5
		sntpServerVersion OBJECT-TYPE
			SYNTAX INTEGER
			MAX-ACCESS read-write
			STATUS current
			DESCRIPTION
				"Description."
			::= { sntpServerEntry 5 }

		
--    1.3.6.1.4.1.3807.2.1910.3.1.6
-- 1.3.6.1.4.1.3807.2.1910.3.1.7
-- 1.3.6.1.4.1.3807.2.1910.4.1.6
		-- 1.3.6.1.4.1.3807.2.1910.4.1.6
		sntpServerRowstatus OBJECT-TYPE
			SYNTAX INTEGER
			MAX-ACCESS read-write
			STATUS current
			DESCRIPTION
				"Description."
			::= { sntpServerEntry 6 }

		
	
	END

--
-- wriSntpNew.mib
--
