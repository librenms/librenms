--
-- WRI-ARP-MIB.mib
-- MIB generated by MG-SOFT Visual MIB Builder Version 6.0  Build 88
-- Tuesday, January 04, 2011 at 10:15:53
--

	WRI-ARP-MIB DEFINITIONS ::= BEGIN
 
		IMPORTS
			mib-2, Integer32, Unsigned32, OBJECT-TYPE, MODULE-IDENTITY,NOTIFICATION-TYPE	
				FROM SNMPv2-SMI		
			TEXTUAL-CONVENTION, TruthValue, TimeInterval,
				MacAddress,PhysAddress			
				FROM SNMPv2-TC		
			InetAddressPrefixLength,InetAddressType,
				InetPortNumber,InetAddress			FROM INET-ADDRESS-MIB	
			wriProducts, wriProtocol			
				FROM WRI-SMI;
	
	-- 1.3.6.1.4.1.3807.2.110
		wriArp MODULE-IDENTITY 
			LAST-UPDATED "201101041500Z"		-- January 4, 2011 at 15:00 GMT
			ORGANIZATION 
				"FiberHome Networks Systems, Inc."
			CONTACT-INFO 
				"http://www.fhn.com.cn"
			DESCRIPTION 
				" The arp info."
		::= { wriProtocol 110 }
--
-- Textual conventions
--
	
		EntryStatus ::= TEXTUAL-CONVENTION
			STATUS current
			DESCRIPTION 
				"entry status."
			SYNTAX INTEGER
				{
				valid(1),
				createRequest(2),
				underCreation(3),
				invalid(4)
				}

		DisplayString ::= TEXTUAL-CONVENTION
			STATUS current
			DESCRIPTION 
				"8 bit octet."
			SYNTAX OCTET STRING
		
		-- 1.3.6.1.4.1.3807.2.110.1
		arpGeneral OBJECT IDENTIFIER ::= { wriArp 1 }

		-- 1.3.6.1.4.1.3807.2.110.1.1
		arpSpeedLimitMaxnum OBJECT-TYPE
			SYNTAX Integer32
			MAX-ACCESS read-write
			STATUS current
			DESCRIPTION
				"The max num of arp speed-limit on global."
			::= { arpGeneral 1 }
		
		-- 1.3.6.1.4.1.3807.2.110.1.1
		arpLearingStrict OBJECT-TYPE
			SYNTAX INTEGER
			{
				enable(1),
				disable(2)
			}
			MAX-ACCESS read-write
			STATUS current
			DESCRIPTION
				"The config of arp learning strict on global."
			::= { arpGeneral 2 }

		-- 1.3.6.1.4.1.3807.2.110.1.2
		arpLearingStrictIPType OBJECT-TYPE
			SYNTAX InetAddressType
			MAX-ACCESS read-only
			STATUS current
			DESCRIPTION
				"The ip type of arp learning strict on global."
			::= { arpGeneral 3 }
			
		-- 1.3.6.1.4.1.3807.2.110.1.3
		arpLearingStrictIPAddr OBJECT-TYPE
			SYNTAX InetAddress
			MAX-ACCESS read-only
			STATUS current
			DESCRIPTION
				"The ip address of arp learning strict on global."
			::= { arpGeneral 4 }
			
		-- 1.3.6.1.4.1.3807.2.110.1.4
		arpAgingTime OBJECT-TYPE
			SYNTAX Integer32
			MAX-ACCESS read-write
			STATUS current
			DESCRIPTION
				"The ip arp aging time on global."
			::= { arpGeneral 5 }     
			
      	-- 1.3.6.1.4.1.3807.2.110.1.6
		arpErrorType OBJECT-TYPE
			SYNTAX INTEGER
			MAX-ACCESS read-only
			STATUS current
			DESCRIPTION
				"The ip arp error type."
			::= { arpGeneral 6 }

	    -- 1.3.6.1.4.1.3807.2.110.1.7
		arpProbeState OBJECT-TYPE
			SYNTAX INTEGER{enable(1),disable(2)}
			MAX-ACCESS read-write
			STATUS current
			DESCRIPTION
				"The ip arp error type."
			::= { arpGeneral 7 }
			
		arpDetectTime OBJECT-TYPE
			SYNTAX Integer32
			MAX-ACCESS read-write
			STATUS current
			DESCRIPTION
				"The ip arp detect times."
			::= { arpGeneral 8 }
		
		-- 1.3.6.1.4.1.3807.2.110.2
		arpSpeedLimitTable OBJECT-TYPE
			SYNTAX SEQUENCE OF ArpSpeedLimitEntry
			MAX-ACCESS not-accessible
			STATUS current
			DESCRIPTION
				"Arp speed-limit table."
			::= { wriArp 2 }

		
		-- 1.3.6.1.4.1.3807.2.110.2.1
		arpSpeedLimitEntry OBJECT-TYPE
			SYNTAX ArpSpeedLimitEntry
			MAX-ACCESS not-accessible
			STATUS current
			DESCRIPTION
				"Arp speed-limit entry."
			INDEX { arpSpeedLimitSourceIPType, arpSpeedLimitSourceIPAddr }
			::= { arpSpeedLimitTable 1 }

		
		ArpSpeedLimitEntry ::=
			SEQUENCE { 
				arpSpeedLimitSourceIPType
					InetAddressType,
				arpSpeedLimitSourceIPAddr
					InetAddress,
				arpSpeedLimitSourceMaxnum
					Integer32,
				arpSpeedLimitEntryStatus
					EntryStatus
			 }

--  The following section describes the components of the
-- table.
		-- 1.3.6.1.4.1.3807.2.110.2.1.1
		arpSpeedLimitSourceIPType OBJECT-TYPE
			SYNTAX InetAddressType
			MAX-ACCESS read-only
			STATUS current
			DESCRIPTION
				"Ip address type,ipv4 address:1,ipv6 address:2."
			::= { arpSpeedLimitEntry 1 }

		
		-- 1.3.6.1.4.1.3807.2.110.2.1.2
		arpSpeedLimitSourceIPAddr OBJECT-TYPE
			SYNTAX InetAddress
			MAX-ACCESS read-only
			STATUS current
			DESCRIPTION
				"Arp source ip address."
			::= { arpSpeedLimitEntry 2 }

		
		-- 1.3.6.1.4.1.3807.2.110.2.1.3
		arpSpeedLimitSourceMaxnum OBJECT-TYPE
			SYNTAX Integer32
			MAX-ACCESS read-write
			STATUS current
			DESCRIPTION
				"The max num of arp speed-limit."
			::= { arpSpeedLimitEntry 3 }

		
		-- 1.3.6.1.4.1.3807.2.110.2.1.4
		arpSpeedLimitEntryStatus OBJECT-TYPE
			SYNTAX EntryStatus
			MAX-ACCESS read-write
			STATUS current
			DESCRIPTION
				"Entry status.."
			::= { arpSpeedLimitEntry 4 }

		
		-- 1.3.6.1.4.1.3807.2.110.3
		arpMaxNumTable OBJECT-TYPE
			SYNTAX SEQUENCE OF ArpMaxNumEntry
			MAX-ACCESS not-accessible
			STATUS current
			DESCRIPTION
				"The arp num table."
			::= { wriArp 3 }

		-- 1.3.6.1.4.1.3807.2.110.3.1
		arpMaxNumEntry OBJECT-TYPE
			SYNTAX ArpMaxNumEntry
			MAX-ACCESS not-accessible
			STATUS current
			DESCRIPTION
				"The arp num entry."
			INDEX { arpMaxNumIfIndex,arpMaxNumVLanId}
			::= { arpMaxNumTable 1 }

		
		ArpMaxNumEntry ::=
			SEQUENCE { 
				arpMaxNumIfIndex
					Integer32,
				arpMaxNumVLanId
					Integer32,
				arpMaxNum
					Integer32,
				arpLearnedNum
				  Integer32,
				arpMaxNumStatus
					INTEGER
			 }

		-- 1.3.6.1.4.1.3807.2.110.3.1.1
		arpMaxNumIfIndex OBJECT-TYPE
			SYNTAX Integer32
			MAX-ACCESS read-only
			STATUS current
			DESCRIPTION
				"Ifindex."
			::= { arpMaxNumEntry 1 }

		-- 1.3.6.1.4.1.3807.2.110.3.1.2
		arpMaxNumVLanId OBJECT-TYPE
			SYNTAX Integer32
			MAX-ACCESS read-only
			STATUS current
			DESCRIPTION
				"vid."
			::= { arpMaxNumEntry 2 }
			
		-- 1.3.6.1.4.1.3807.2.110.3.1.3
		arpMaxNum OBJECT-TYPE
			SYNTAX Integer32 (0..32767)
			MAX-ACCESS read-write
			STATUS current
			DESCRIPTION
				"The max arp num ."
			::= { arpMaxNumEntry 3 }

		-- 1.3.6.1.4.1.3807.2.110.3.1.4
		arpLearnedNum OBJECT-TYPE
			SYNTAX Integer32
			MAX-ACCESS read-only
			STATUS current
			DESCRIPTION
				"The learned arp num."
			::= { arpMaxNumEntry 4 }

			
		-- 1.3.6.1.4.1.3807.2.110.3.1.5
		arpMaxNumStatus OBJECT-TYPE
			SYNTAX INTEGER{
			 enable(1),
			 disable(2)
			}
			MAX-ACCESS read-write
			STATUS current
			DESCRIPTION
				"Enable or disable arp num ."
			::= { arpMaxNumEntry 5 }

	-- 1.3.6.1.4.1.3807.2.110.4
		arpMaxNumVlanTable OBJECT-TYPE
			SYNTAX SEQUENCE OF ArpMaxNumVlanEntry
			MAX-ACCESS not-accessible
			STATUS current
			DESCRIPTION
				"The arp num table on vlan."
			::= { wriArp 4 }

		-- 1.3.6.1.4.1.3807.2.110.4.1
		arpMaxNumVlanEntry OBJECT-TYPE
			SYNTAX ArpMaxNumVlanEntry
			MAX-ACCESS not-accessible
			STATUS current
			DESCRIPTION
				"The arp num entry on vlan."
			INDEX {arpMaxNumVLanIndex }
			::= { arpMaxNumVlanTable 1 }

		ArpMaxNumVlanEntry ::=
			SEQUENCE { 
				arpMaxNumVLanIndex
					Integer32,
				arpVlanMaxNum
					Integer32,
				arpVlanLearnedNum
					Integer32
			 }

		-- 1.3.6.1.4.1.3807.2.110.4.1.1
		arpMaxNumVLanIndex OBJECT-TYPE
			SYNTAX Integer32
			MAX-ACCESS read-only
			STATUS current
			DESCRIPTION
				"Vid."
			::= { arpMaxNumVlanEntry 1 }

		-- 1.3.6.1.4.1.3807.2.110.4.1.2
		arpVlanMaxNum OBJECT-TYPE
			SYNTAX Integer32 (0..32767)
			MAX-ACCESS read-write
			STATUS current
			DESCRIPTION
				"The max arp num of vlan."
			::= { arpMaxNumVlanEntry 2 }
			
		-- 1.3.6.1.4.1.3807.2.110.4.1.3
		arpVlanLearnedNum OBJECT-TYPE
			SYNTAX Integer32
			MAX-ACCESS read-only
			STATUS current
			DESCRIPTION
				"The learned max arp num of vlan."
			::= { arpMaxNumVlanEntry 3 }
			
	
		
		arpLearingStrictTrap		OBJECT IDENTIFIER ::=   {wriArp 5}
		
		arpLearingStrictIp NOTIFICATION-TYPE
       		OBJECTS {arpLearingStrictIPType,arpLearingStrictIPAddr}
       		STATUS  current
       		DESCRIPTION
               	""
			::= { arpLearingStrictTrap 1} 	
	
	   arpUnknowHwAddress	NOTIFICATION-TYPE
       		OBJECTS {arpErrorType}
       		STATUS  current
       		DESCRIPTION
               	""
			::= { arpLearingStrictTrap 2}
			
		
	   arpUnknowProtocolAddress	NOTIFICATION-TYPE
       		OBJECTS {arpErrorType}
       		STATUS  current
       		DESCRIPTION
               	""
			::= { arpLearingStrictTrap 3} 
			
	
		
	   arpInvalidAddressLengh	NOTIFICATION-TYPE
       		OBJECTS {arpErrorType}
       		STATUS  current
       		DESCRIPTION
               	""
			::= { arpLearingStrictTrap 4} 
			
	
	   arpInvalidOperationCode	NOTIFICATION-TYPE
       		OBJECTS {arpErrorType}
       		STATUS  current
       		DESCRIPTION
               	""
			::= { arpLearingStrictTrap 5} 					 		
	   				
		
		
	END

--
-- WRI-ARP-MIB.mib
--
