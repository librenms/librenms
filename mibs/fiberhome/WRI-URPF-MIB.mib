--
-- urpf.mib
-- MIB generated by MG-SOFT Visual MIB Builder Version 6.0  Build 88
-- Monday, December 13, 2010 at 15:25:54
--

	WRI-URPF-MIB DEFINITIONS ::= BEGIN
 
		IMPORTS
			mib-2, Integer32, Unsigned32, OBJECT-TYPE, MODULE-IDENTITY,NOTIFICATION-TYPE	
				FROM SNMPv2-SMI			
			TEXTUAL-CONVENTION			
				FROM SNMPv2-TC			
			wriProtocol			
				FROM WRI-SMI;
	
		urpf MODULE-IDENTITY 
			LAST-UPDATED "201107211500Z"		-- July 21, 2011 at 15:00 GMT
			ORGANIZATION 
				"FiberHome Networks Systems, Inc."
			CONTACT-INFO 
				"http://www.fhn.com.cn"
			DESCRIPTION 
				" The configure of urpf."
			::= { wriProtocol 2102 }

--
-- Textual conventions
--
	
--  Textual Conventions
		DisplayString ::=   OCTET STRING
		EntryStatus ::= TEXTUAL-CONVENTION
			STATUS current
			DESCRIPTION 
				"entry status."
			SYNTAX INTEGER
				{
				valid(1),
				createRequest(2),
				underCreation(3),
				invalid(4)
				}

	
--
-- Node definitions
--
		
		urpfIfTable OBJECT-TYPE
			SYNTAX SEQUENCE OF UrpfIfEntry
			MAX-ACCESS not-accessible
			STATUS current
			DESCRIPTION
				"The table of urpf ."
			::= { urpf 1 }
			
		urpfIfEntry OBJECT-TYPE
			SYNTAX UrpfIfEntry
			MAX-ACCESS not-accessible
			STATUS current
			DESCRIPTION
				"The entry of diffserv."
			INDEX { urpfIfIndex  }
			::= { urpfIfTable 1 }

		UrpfIfEntry ::=
			SEQUENCE { 
				urpfIfIndex
					Integer32,
				urpfIfMode
					INTEGER,
				urpfIfRoute  
					Integer32
			 }

		urpfIfIndex OBJECT-TYPE
			SYNTAX Integer32
			MAX-ACCESS read-only
			STATUS current
			DESCRIPTION
				"The index of urpf."
			::= { urpfIfEntry 1 }

		urpfIfMode OBJECT-TYPE
			SYNTAX INTEGER
			{
				disable(0),
				loose(1),
				strict(2)
			}
			MAX-ACCESS read-write
			STATUS current
			DESCRIPTION
				"The mode of urpf."
			::= { urpfIfEntry 2 }

		urpfIfRoute OBJECT-TYPE
			SYNTAX Integer32			
			MAX-ACCESS read-write
			STATUS current
			DESCRIPTION
				"The default route configure of urpf."
			::= { urpfIfEntry 3 }

		
		
	END

--
-- urpf.mib
--
