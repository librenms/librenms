WRI-VLAN-MIB DEFINITIONS ::= BEGIN
	IMPORTS
			MODULE-IDENTITY, OBJECT-TYPE, Counter32, Gauge32,
			Integer32, TimeTicks, Counter64,Unsigned32,enterprises,
			NOTIFICATION-TYPE                        FROM SNMPv2-SMI
       
			TEXTUAL-CONVENTION, TruthValue, TimeInterval,
				MacAddress,PhysAddress		FROM SNMPv2-TC
			InetAddressPrefixLength,InetAddressType,
				InetPortNumber,InetAddress			FROM INET-ADDRESS-MIB
			SnmpAdminString							FROM SNMP-FRAMEWORK-MIB
    			InterfaceIndex							FROM IF-MIB
			wri,wriProducts,wriMgmt			FROM WRI-SMI;
	
	

	-- Multiple Services Ring (MSPP)

	
	mspp         	OBJECT IDENTIFIER ::= { wriProducts 8012 }
	msppLayer2		OBJECT IDENTIFIER ::=   {mspp 3}
	


	
	
	RerRingDir ::= TEXTUAL-CONVENTION
		STATUS      current
		DESCRIPTION
				"Indicates the ringlet on which the OAM action
				request/response is sent/replied."
		SYNTAX      INTEGER {
			west(0),
			east(1)
			}
	
	DisplayString ::= TEXTUAL-CONVENTION
		STATUS current
		DESCRIPTION
				"8 bit octet."
		SYNTAX OCTET STRING
	

	 EntryStatus ::= TEXTUAL-CONVENTION
		STATUS current
		DESCRIPTION
				"entry status."
		SYNTAX INTEGER 
			{
				valid(1),
				createRequest(2),
				underCreation(3),
				invalid(4)
			}
			
			

	PortList ::= OCTET STRING (SIZE(0..1024))

		
	VlanIndex ::= TEXTUAL-CONVENTION
		STATUS      current
		DESCRIPTION
				"A value used to index per-VLAN tables: values of 0 and
				4095 are not permitted; if the value is between 1 and
				4094 inclusive, it represents an IEEE 802.1Q VLAN-ID with
				global scope within a given bridged domain (see VlanId
				textual convention).  If the value is greater than 4095
				then it represents a VLAN with scope local to the
				particular agent, i.e. one without a global VLAN-ID
				assigned to it. Such VLANs are outside the scope of
				IEEE 802.1Q but it is convenient to be able to manage them
				in the same way using this MIB."
		SYNTAX      Unsigned32
		
	VlanId ::= TEXTUAL-CONVENTION
		STATUS      current
		DESCRIPTION
				"A 12-bit VLAN ID used in the VLAN Tag header."
		SYNTAX      INTEGER (1..4094)
	
	

	-- 802.1q
		portBasedVlan			OBJECT IDENTIFIER ::=   {msppLayer2 2}
		
		portBasedVlanGeneral		OBJECT IDENTIFIER ::=   {portBasedVlan 1}
		
		portBasedVlanVersionNumber OBJECT-TYPE
			SYNTAX      INTEGER {
					version1(1)
				}
			MAX-ACCESS  read-only
			STATUS      current
			DESCRIPTION
					"The version number of IEEE 802.1Q that this device
			        supports."
			REFERENCE
					"IEEE 802.1Q/D11 Section 12.10.1.1"
			::= { portBasedVlanGeneral 1 }
		
		portBasedVlanMaxVlanId OBJECT-TYPE
			SYNTAX      VlanId
			MAX-ACCESS  read-only
		   	STATUS      current
	    	DESCRIPTION
			        "The maximum IEEE 802.1Q VLAN ID that this device
			        supports."
    		REFERENCE
		    	    "IEEE 802.1Q/D11 Section 9.3.2.3"
    		::= { portBasedVlanGeneral 2 }
			
			
		portBasedVlanMaxSupportedVlans OBJECT-TYPE
			SYNTAX      Unsigned32
			MAX-ACCESS  read-only
			STATUS      current
			DESCRIPTION
					"The maximum number of IEEE 802.1Q VLANs that this
					device supports."
			REFERENCE
					"IEEE 802.1Q/D11 Section 12.10.1.1"
			::= { portBasedVlanGeneral 3 }			
		
		
		portBasedVlanNumVlans OBJECT-TYPE
			SYNTAX      Unsigned32
			MAX-ACCESS  read-only
			STATUS      current
			DESCRIPTION
					"The current number of IEEE 802.1Q VLANs that are
					configured in this device."
			REFERENCE
					"IEEE 802.1Q/D11 Section 12.7.1.1"
			::= { portBasedVlanGeneral 4 }
			
		portBasedVlanListStatus OBJECT-TYPE
			SYNTAX      DisplayString (SIZE (0..512)) 
			MAX-ACCESS  read-write
			STATUS      current
			DESCRIPTION
        			"The state of vlan."
			::= { portBasedVlanGeneral 6 }
		
		portBasedVlanExistList OBJECT-TYPE
			SYNTAX      DisplayString (SIZE (0..1024))
			MAX-ACCESS  read-only
			STATUS      current
			DESCRIPTION
					"The list of all the IEEE 802.1Q VLANs that are
					existed or not existed in this device."
			::= { portBasedVlanGeneral 7 }
		
		portBasedVlanSuperPrimaryList OBJECT-TYPE
			SYNTAX      DisplayString (SIZE (0..1024))
			MAX-ACCESS  read-only
			STATUS      current
			DESCRIPTION
					"The list of IEEE 802.1Q VLANs that are
					super-primary vlan ."
			::= { portBasedVlanGeneral 8 }
			
		portBasedVlanDelList OBJECT-TYPE
			SYNTAX      DisplayString (SIZE (0..1024))
			MAX-ACCESS  read-write
			STATUS      current
			DESCRIPTION
					"Delete the list of all the IEEE 802.1Q VLANs."
			::= { portBasedVlanGeneral 9 }
			
	portBasedVlanCurMaxVlanId OBJECT-TYPE
			SYNTAX      Unsigned32
			MAX-ACCESS  read-only
			STATUS      current
			DESCRIPTION
					"The current max number of IEEE 802.1Q VLANs that are
					configured in this device."
			::= { portBasedVlanGeneral 10}
			
	portBasedVlanMaxMacVlan	OBJECT-TYPE
			SYNTAX      Unsigned32
			MAX-ACCESS  read-only
			STATUS      current
			DESCRIPTION
					"The current max number of mac-vlan in this device."
			::= { portBasedVlanGeneral 11}
			
	portBasedVlanMaxIpSubNetVlan	OBJECT-TYPE
			SYNTAX      Unsigned32
			MAX-ACCESS  read-only
			STATUS      current
			DESCRIPTION
					"The current max number of ip-subnet-vlan in this device."
			::= { portBasedVlanGeneral 12}
        	
	portBasedVlanMaxProtolVlan	OBJECT-TYPE
			SYNTAX      Unsigned32
			MAX-ACCESS  read-only
			STATUS      current
			DESCRIPTION
					"The current max number of protocol-vlan in this device."
			::= { portBasedVlanGeneral 13}
			
	portBasedVlanNumDEL	OBJECT-TYPE
			SYNTAX      Unsigned32
			MAX-ACCESS  read-only
			STATUS      current
			DESCRIPTION
					"The number of vlan that deleted in this device."
			::= { portBasedVlanGeneral 14}
			
	portBasedVlanFreeIndex	OBJECT-TYPE
			SYNTAX      Unsigned32
			MAX-ACCESS  read-only
			STATUS      current
			DESCRIPTION
					"The free index of vlan in this device."
			::= { portBasedVlanGeneral 15}
			
	portBasedVlanExistStaticList OBJECT-TYPE
			SYNTAX      DisplayString (SIZE (0..1024))
			MAX-ACCESS  read-write
			STATUS      current
			DESCRIPTION
					"The list of all the IEEE 802.1Q static VLANs that are
					existed or not existed in this device."
			::= { portBasedVlanGeneral 16 }
			
		portBasedVlanCurrentTable OBJECT-TYPE
			SYNTAX      SEQUENCE OF PortBasedVlanCurrentEntry
			MAX-ACCESS  not-accessible
			STATUS      current
			DESCRIPTION
					"A table containing current configuration information
					for each VLAN currently configured into the device by
					(local or network) management, or dynamically created
					as a result of GVRP requests received."
			::= { portBasedVlan 2 }
	
		portBasedVlanCurrentEntry OBJECT-TYPE
			SYNTAX      PortBasedVlanCurrentEntry
			MAX-ACCESS  not-accessible
			STATUS      current
			DESCRIPTION
					"Information for a VLAN configured into the device by
					(local or network) management, or dynamically created
					as a result of GVRP requests received."
			INDEX   { portBasedVlanIndex }
			::= { portBasedVlanCurrentTable 1 }
	
		PortBasedVlanCurrentEntry ::=
			SEQUENCE {
				--portBasedVlanTimeMark				TimeFilter,
				portBasedVlanIndex					VlanIndex,
				--portBasedVlanFdbId				Unsigned32,
				portBasedVlanCurrentEgressPorts		PortList,
				portBasedVlanCurrentUntaggedPorts	PortList,
				portBasedVlanCurrentPortsNum		INTEGER,
				portBasedVlanStatus					INTEGER,
				portBasedVlanCreationTime			TimeTicks
			}
	
	
		--portBasedVlanTimeMark OBJECT-TYPE
			--SYNTAX      TimeFilter
			--MAX-ACCESS  not-accessible
			--STATUS      current
			--DESCRIPTION
						--"A TimeFilter for this entry.  See the TimeFilter
						--textual convention to see how this works."
			--::= { portBasedVlanCurrentEntry 2 }
	
		portBasedVlanIndex OBJECT-TYPE
			SYNTAX      VlanIndex
			MAX-ACCESS  read-only
			STATUS      current
			DESCRIPTION
					"The VLAN-ID or other identifier refering to this VLAN."
			::= { portBasedVlanCurrentEntry 1 }
	
		--portBasedVlanFdbId OBJECT-TYPE
			--SYNTAX      Unsigned32
			--MAX-ACCESS  read-only
			--STATUS      current
			--DESCRIPTION
					--"The Filtering Database used by this VLAN.  This is one
					--of the dot1qFdbId values in the dot1qFdbTable.  This
					--value is allocated automatically by the device whenever
					--the VLAN is created: either dynamically by GVRP, or by	
					--management, in portBasedVlanStaticTable.  Allocation of this
					--value follows the learning constraints defined for this
					--VLAN in dot1qLearningConstraintsTable."
			--::= { portBasedVlanCurrentEntry 2 }
	
		portBasedVlanCurrentEgressPorts OBJECT-TYPE
			SYNTAX      PortList (SIZE(0..1024))
			MAX-ACCESS  read-only
			STATUS      current
			DESCRIPTION
					"The set of ports which are transmitting traffic for
					this VLAN as either tagged or untagged frames."
			REFERENCE
					"IEEE 802.1Q/D11 Section 12.10.2.1"
			::= { portBasedVlanCurrentEntry 2 }
	
		portBasedVlanCurrentUntaggedPorts OBJECT-TYPE
			SYNTAX      PortList (SIZE(0..1024))
			MAX-ACCESS  read-only
			STATUS      current
			DESCRIPTION
					"The set of ports which are transmitting traffic for
					this VLAN as untagged frames."
			REFERENCE
					"IEEE 802.1Q/D11 Section 12.10.2.1"
			::= { portBasedVlanCurrentEntry 3 }
	
		portBasedVlanCurrentPortsNum OBJECT-TYPE
			SYNTAX      INTEGER
			MAX-ACCESS  read-only
			STATUS      current
			DESCRIPTION
					"port number"
			::= { portBasedVlanCurrentEntry 4 }
	
		portBasedVlanStatus OBJECT-TYPE
			SYNTAX      INTEGER {
	                    other(1),
	                    permanent(2),
	                    dynamicGvrp(3)
	                }
			MAX-ACCESS  read-write
			STATUS      current
			DESCRIPTION
					"This object indicates the status of this entry.
					other(1) - this entry is currently in use but the
						conditions under which it will remain so differ
						from the following values.
					permanent(2) - this entry, corresponding to an entry
						in dot1qVlanStaticTable, is currently in use and
						will remain so after the next reset of the
						device.  The port lists for this entry include
						ports from the equivalent dot1qVlanStaticTable
						entry and ports learnt dynamically.
					dynamicGvrp(3) - this entry is currently in use
						and will remain so until removed by GVRP.  There
						is no static entry for this VLAN and it will be
						removed when the last port leaves the VLAN."
			::= { portBasedVlanCurrentEntry 5 }
	
		portBasedVlanCreationTime OBJECT-TYPE
			SYNTAX      TimeTicks
			MAX-ACCESS  read-only
			STATUS      current
			DESCRIPTION
					"The value of sysUpTime when this VLAN was created."
			::= { portBasedVlanCurrentEntry 6 }
  
   
  

	-- -------------------------------------------------------------
	-- The Static VLAN Database
	-- -------------------------------------------------------------
	
		portBasedVlanStaticTable OBJECT-TYPE
	    	SYNTAX      SEQUENCE OF PortBasedVlanStaticEntry
			MAX-ACCESS  not-accessible
			STATUS      current
			DESCRIPTION
					"A table containing static configuration information for
					each VLAN configured into the device by (local or
					network) management.  All entries are permanent and will
					be restored after the device is reset."
			::= { portBasedVlan 3 }
	
		portBasedVlanStaticEntry OBJECT-TYPE
			SYNTAX      PortBasedVlanStaticEntry
			MAX-ACCESS  not-accessible
			STATUS      current
			DESCRIPTION
					"Static information for a VLAN configured into the
					device by (local or network) management."
			INDEX   { portBasedVlanIndex }
			::= { portBasedVlanStaticTable 1 }
	
		PortBasedVlanStaticEntry ::=
	    	SEQUENCE {
	        portBasedVlanStaticName							DisplayString,
	        portBasedVlanStaticPortBits						PortList,
	        portBasedVlanStaticUntaggedPortBits				PortList,
	        
	        portBasedVlanStaticPorts						PortList,
	        portBasedVlanStaticUntaggedPorts				PortList,
	        portBasedVlanStaticRemovePorts					PortList,
	        portBasedVlanStaticPortsNum						INTEGER,
	        portBasedVlanStaticIpAddressType				InetAddressType,
	        portBasedVlanStaticIpAddress					InetAddress,
	        portBasedVlanStaticIpAddressPrefixLength		InetAddressPrefixLength,
	        portBasedVlanUnknownMulticastDiscard			INTEGER,
	        portBasedVlanStaticEntryStatus					EntryStatus,
	        portBasedVlanUnknownUnicastDiscard				INTEGER,
	        portBasedVlanBroadcastDiscard					INTEGER,
	        portBasedVlanMacLearningEnable					INTEGER,
	        portBasedVlanMacLimitCtrl						INTEGER,
	        portBasedVlanMacLimitNum						INTEGER,
	        portBasedVlanStaticTaggedPorts       PortList,   
	        portBasedVlanStaticTaggedPortBits    PortList,
	        portBasedVlanStaticDesc            				DisplayString,
	        ---add by xiongfang 2010-12-24
			portBasedVlanStaticAdminStatus     				INTEGER,
			portBasedVlanStaticOperStatus      				INTEGER,
			portBasedVlanStaticStatus          				INTEGER,
			portBasedVlanStaticType            				INTEGER,
			portBasedVlanStaticArpProxy                  	INTEGER,
			portBasedVlanStaticInnerSubVlanArpProxy      	INTEGER,
			portBasedVlanStaticInterSubVlanArpProxy      	INTEGER,
			portBasedVlanStaticNdProxy                   	INTEGER,
			portBasedVlanStaticInnerSubVlanNdProxy       	INTEGER,
			portBasedVlanStaticInterSubVlanNdProxy       	INTEGER,
			portBasedVlanStaticReset                     	Integer32,
			portBasedVlanStaticArpLearing                	INTEGER,
			portBasedVlanStaticIcmpRedirect			   		INTEGER,
			portBasedVlanStaticIcmp6Redirect			    INTEGER,
			portBasedVlanStaticIpv4Num 				   		INTEGER,
			portBasedVlanStaticIpv6Num			       		INTEGER,
			portBasedVlanStaticMtu                          INTEGER,
			portBasedVlanStaticPmtu							INTEGER
	    }
	
		portBasedVlanStaticName OBJECT-TYPE
			SYNTAX      DisplayString (SIZE (0..32))
			MAX-ACCESS  read-write
			STATUS      current
			DESCRIPTION
					"An administratively assigned string, which may be used
					to identify the VLAN."
			REFERENCE
					"IEEE 802.1Q/D11 Section 12.10.2.1"
			::= { portBasedVlanStaticEntry 1 }
	
		portBasedVlanStaticPortBits OBJECT-TYPE
			SYNTAX      PortList (SIZE(0..1024))
			MAX-ACCESS  read-write
			STATUS      current
			DESCRIPTION
					"The set of ports which are permanently assigned to the
					egress list for this VLAN by management.  Changes to a
					bit in this object affect the per-port per-VLAN
					Registrar control for Registration Fixed for the
					relevant GVRP state machine on each port.  A port may
					not be added in this set if it is already a member of
					the set of ports in portBasedVlanForbiddenEgressPorts.  The
					default value of this object is a string of zeros of
					appropriate length, indicating not fixed."
			REFERENCE
					"IEEE 802.1Q/D11 Section 12.7.7.3, 11.2.3.2.3"
			::= { portBasedVlanStaticEntry 2 }
		
		portBasedVlanStaticUntaggedPortBits OBJECT-TYPE
			SYNTAX      PortList (SIZE(0..1024))
			MAX-ACCESS  read-write
			STATUS      current
			DESCRIPTION
					"The set of ports which should transmit egress packets
					for this VLAN as untagged.  The default value of this
					object for the default VLAN (dot1qVlanIndex = 1) is a string
					of appropriate length including all ports.  There is no
					specified default for other VLANs.  If a device agent cannot
					support the set of ports being set then it will reject the
					set operation with an error. An example might be if a
					manager attempts to set more than one VLAN to be untagged
					on egress where the device does not support this IEEE 802.1Q
					option."
			REFERENCE
					"IEEE 802.1Q/D11 Section 12.10.2.1"
			::= { portBasedVlanStaticEntry 3 }
	
		portBasedVlanStaticPorts OBJECT-TYPE
			SYNTAX      PortList (SIZE(0..1024))
			MAX-ACCESS  read-write
			STATUS      current
			DESCRIPTION
					"The set of ports which are permanently assigned to the
					egress list for this VLAN by management.  Changes to a
					bit in this object affect the per-port per-VLAN
					Registrar control for Registration Fixed for the
					relevant GVRP state machine on each port.  A port may
					not be added in this set if it is already a member of
					the set of ports in portBasedVlanForbiddenEgressPorts.  The
					default value of this object is a string of zeros of
					appropriate length, indicating not fixed."
			REFERENCE
					"IEEE 802.1Q/D11 Section 12.7.7.3, 11.2.3.2.3"
			::= { portBasedVlanStaticEntry 4 }
		
		portBasedVlanStaticUntaggedPorts OBJECT-TYPE
			SYNTAX      PortList (SIZE(0..1024))
			MAX-ACCESS  read-write
			STATUS      current
			DESCRIPTION
					"The set of ports which should transmit egress packets
					for this VLAN as untagged.  The default value of this
					object for the default VLAN (dot1qVlanIndex = 1) is a string
					of appropriate length including all ports.  There is no
					specified default for other VLANs.  If a device agent cannot
					support the set of ports being set then it will reject the
					set operation with an error. An example might be if a
					manager attempts to set more than one VLAN to be untagged
					on egress where the device does not support this IEEE 802.1Q
					option."
			REFERENCE
					"IEEE 802.1Q/D11 Section 12.10.2.1"
			::= { portBasedVlanStaticEntry 5 }
	
		portBasedVlanStaticRemovePorts OBJECT-TYPE
			SYNTAX      PortList (SIZE(0..1024))
			MAX-ACCESS  read-write
			STATUS      current
			DESCRIPTION
					"The set of ports which should transmit egress packets
					for this VLAN as untagged.  The default value of this
					object for the default VLAN (dot1qVlanIndex = 1) is a string
					of appropriate length including all ports.  There is no
					specified default for other VLANs.  If a device agent cannot
					support the set of ports being set then it will reject the
					set operation with an error. An example might be if a
					manager attempts to set more than one VLAN to be untagged
					on egress where the device does not support this IEEE 802.1Q
					option."
			REFERENCE
					"IEEE 802.1Q/D11 Section 12.10.2.1"
			::= { portBasedVlanStaticEntry 6 }
	
		portBasedVlanStaticPortsNum OBJECT-TYPE
			SYNTAX      INTEGER
			MAX-ACCESS  read-only
			STATUS      current
			DESCRIPTION
					"egress port number"
			::= { portBasedVlanStaticEntry 7 }
	
		portBasedVlanStaticIpAddressType OBJECT-TYPE
			SYNTAX      InetAddressType
			MAX-ACCESS  read-write
			STATUS      current
			DESCRIPTION
					"NULL."			
			::= { portBasedVlanStaticEntry 8 }
			
		portBasedVlanStaticIpAddress OBJECT-TYPE
			SYNTAX      InetAddress
			MAX-ACCESS  read-write
			STATUS      current
			DESCRIPTION
					"NULL."			
			::= { portBasedVlanStaticEntry 9 }
	
		portBasedVlanStaticIpAddressPrefixLength OBJECT-TYPE
			SYNTAX      InetAddressPrefixLength
			MAX-ACCESS  read-write
			STATUS      current
			DESCRIPTION
					"NULL."			
			::= { portBasedVlanStaticEntry 10 }
	
		portBasedVlanUnknownMulticastDiscard OBJECT-TYPE
			SYNTAX      INTEGER
			MAX-ACCESS  read-write
			STATUS      current
			DESCRIPTION
					"unregister multicast mac address"
			::= { portBasedVlanStaticEntry 11 }
	
		portBasedVlanStaticEntryStatus OBJECT-TYPE
			SYNTAX      EntryStatus
			MAX-ACCESS  read-create
			STATUS      current
			DESCRIPTION
					"This object indicates the status of this entry."
			::= { portBasedVlanStaticEntry 12 }
			
		portBasedVlanUnknownUnicastDiscard OBJECT-TYPE
			SYNTAX      INTEGER
			MAX-ACCESS  read-write
			STATUS      current
			DESCRIPTION
					"unregister multicast mac address"
			::= { portBasedVlanStaticEntry 13 }
			
		portBasedVlanBroadcastDiscard OBJECT-TYPE
			SYNTAX      INTEGER
			MAX-ACCESS  read-write
			STATUS      current
			DESCRIPTION
					"unregister multicast mac address"
			::= { portBasedVlanStaticEntry 14 }
			
		portBasedVlanMacLearningEnable OBJECT-TYPE
			SYNTAX      INTEGER
			MAX-ACCESS  read-write
			STATUS      current
			DESCRIPTION
					"unregister multicast mac address"
			::= { portBasedVlanStaticEntry 15 }
			
		portBasedVlanMacLimitCtrl OBJECT-TYPE
			SYNTAX      INTEGER
			MAX-ACCESS  read-write
			STATUS      current
			DESCRIPTION
					"enable or disable vlan mac limit"
			::= { portBasedVlanStaticEntry 16 }
		
		portBasedVlanMacLimitNum OBJECT-TYPE
			SYNTAX      INTEGER
			MAX-ACCESS  read-write
			STATUS      current
			DESCRIPTION
					"vlan mac limit number"
			::= { portBasedVlanStaticEntry 17 }
  
		portBasedVlanStaticTaggedPorts OBJECT-TYPE
			SYNTAX      PortList (SIZE(0..1024))
			MAX-ACCESS  read-write
			STATUS      current
			DESCRIPTION
					"The set of ports which should transmit egress packets
					for this VLAN as tagged.  The default value of this
					object for the default VLAN (dot1qVlanIndex = 1) is a string
					of appropriate length including all ports.  There is no
					specified default for other VLANs.  If a device agent cannot
					support the set of ports being set then it will reject the
					set operation with an error. An example might be if a
					manager attempts to set more than one VLAN to be tagged
					on egress where the device does not support this IEEE 802.1Q
					option."
			REFERENCE
					"IEEE 802.1Q/D11 Section 12.10.2.1"
			::= { portBasedVlanStaticEntry 18 }
			
		portBasedVlanStaticTaggedPortBits OBJECT-TYPE
			SYNTAX      PortList (SIZE(0..1024))
			MAX-ACCESS  read-write
			STATUS      current
			DESCRIPTION
					"The set of ports which should transmit egress packets
					for this VLAN as tagged.  The default value of this
					object for the default VLAN (dot1qVlanIndex = 1) is a string
					of appropriate length including all ports.  There is no
					specified default for other VLANs.  If a device agent cannot
					support the set of ports being set then it will reject the
					set operation with an error. An example might be if a
					manager attempts to set more than one VLAN to be tagged
					on egress where the device does not support this IEEE 802.1Q
					option."
			REFERENCE
					"IEEE 802.1Q/D11 Section 12.10.2.1"
			::= { portBasedVlanStaticEntry 19 }
	
	portBasedVlanStaticDesc OBJECT-TYPE
			SYNTAX      DisplayString (SIZE (0..1024))
			MAX-ACCESS  read-write
			STATUS      current
			DESCRIPTION
					"An administratively assigned string, which may be used
					to identify the VLAN."
			REFERENCE
					"IEEE 802.1Q/D11 Section 12.10.2.1"
			::= { portBasedVlanStaticEntry 20}
			
	--add by xiongfang 2010-12-24
				
	portBasedVlanStaticAdminStatus OBJECT-TYPE
			SYNTAX      INTEGER{                          
				up(1),       
				down(0)
			}
			MAX-ACCESS  read-write
			STATUS      current
			DESCRIPTION
					"vlan admin status ."
			::= { portBasedVlanStaticEntry 21}
			
	portBasedVlanStaticOperStatus OBJECT-TYPE
			SYNTAX      INTEGER{                          
				up(1),       
				down(0)
			}
			MAX-ACCESS  read-only
			STATUS      current
			DESCRIPTION
					"vlan oper status."
			::= { portBasedVlanStaticEntry 22 }
			
	portBasedVlanStaticStatus OBJECT-TYPE
			SYNTAX      INTEGER{
			enable(1),
			disable(2)
			}
			MAX-ACCESS  read-write
			STATUS      current
			DESCRIPTION
					"the statistic of vlan ."
			::= { portBasedVlanStaticEntry 23 }
			
	 portBasedVlanStaticType OBJECT-TYPE
			SYNTAX      INTEGER
			MAX-ACCESS  read-write
			STATUS      current
			DESCRIPTION
					"vlan type:normal\pvlan\supervlan."
			::= { portBasedVlanStaticEntry 24 }
			
  portBasedVlanStaticArpProxy OBJECT-TYPE
			SYNTAX INTEGER
		      {
			    enable(1),
			    disable(2)
			    }
			MAX-ACCESS  read-write
			STATUS   current
			DESCRIPTION
					"Enable or disable arp proxy."
			::= { portBasedVlanStaticEntry 25 }
			
	portBasedVlanStaticInnerSubVlanArpProxy OBJECT-TYPE
			SYNTAX INTEGER
		      {
			    enable(1),
			    disable(2)
			    }
			MAX-ACCESS  read-write
			STATUS   current
			DESCRIPTION
					"Enable or disable arp proxy inner sub vlan."
			::= { portBasedVlanStaticEntry 26 }
			
	portBasedVlanStaticInterSubVlanArpProxy OBJECT-TYPE
			SYNTAX INTEGER
		      {
			    enable(1),
			    disable(2)
			    }
			MAX-ACCESS  read-write
			STATUS   current
			DESCRIPTION
					"Enable or disable arp proxy inter sub vlan."
			::= { portBasedVlanStaticEntry 27 }
			
	portBasedVlanStaticNdProxy OBJECT-TYPE
			SYNTAX INTEGER
		      {
			    enable(1),
			    disable(2)
			    }
			MAX-ACCESS  read-write
			STATUS   current
			DESCRIPTION
					"Enable or disable nd proxy."
			::= { portBasedVlanStaticEntry 28 }	
			
	portBasedVlanStaticInnerSubVlanNdProxy OBJECT-TYPE
			SYNTAX INTEGER
		      {
			    enable(1),
			    disable(2)
			    }
			MAX-ACCESS  read-write
			STATUS   current
			DESCRIPTION
					"Enable or disable nd proxy inner sub vlan."
			::= { portBasedVlanStaticEntry 29 }	
			
	portBasedVlanStaticInterSubVlanNdProxy OBJECT-TYPE
			SYNTAX INTEGER
		      {
			    enable(1),
			    disable(2)
			    }
			MAX-ACCESS  read-write
			STATUS   current
			DESCRIPTION
					"Enable or disable nd proxy inter sub vlan."
			::= { portBasedVlanStaticEntry 30 }	
			
	portBasedVlanStaticReset	 OBJECT-TYPE	
			SYNTAX Integer32
			MAX-ACCESS  read-write
			STATUS   current
			DESCRIPTION
					"Reset vlan statistics info."
			::= { portBasedVlanStaticEntry 31 }	
		
	portBasedVlanStaticArpLearing	 OBJECT-TYPE	
			SYNTAX INTEGER
			MAX-ACCESS  read-write
			STATUS   current
			DESCRIPTION
					"Arp learning strict mode."
			::= { portBasedVlanStaticEntry 32 }	
		
		portBasedVlanStaticIcmpRedirect OBJECT-TYPE
			SYNTAX   INTEGER{
			    enable(1),
			    disable(2)
			}
			MAX-ACCESS   read-write
			STATUS       current
			DESCRIPTION
					"enable or disable the icmp redirect."
			::= { portBasedVlanStaticEntry 33 }
			
		portBasedVlanStaticIcmp6Redirect OBJECT-TYPE
			SYNTAX      INTEGER{
			    enable(1),
			    disable(2)
			}
			MAX-ACCESS   read-write
			STATUS       current
			DESCRIPTION
					"enable or disable the icmp6 redirect."
			::= { portBasedVlanStaticEntry 34 }
			
		--xf add 2013-6-3
		portBasedVlanStaticIpv4Num OBJECT-TYPE
			SYNTAX      INTEGER
			MAX-ACCESS   read-write
			STATUS       current
			DESCRIPTION
					"The count of ipv4 address on vlan ."
			::= { portBasedVlanStaticEntry 35 }
			
		portBasedVlanStaticIpv6Num OBJECT-TYPE
			SYNTAX      INTEGER
			MAX-ACCESS   read-write
			STATUS       current
			DESCRIPTION
					"The count of ipv6 address on vlan ."
			::= { portBasedVlanStaticEntry 36 }
			
		portBasedVlanStaticMtu OBJECT-TYPE
			SYNTAX      INTEGER
			MAX-ACCESS   read-write
			STATUS       current
			DESCRIPTION
					"The mtu."
			::= { portBasedVlanStaticEntry 37 }
			
		portBasedVlanStaticPmtu OBJECT-TYPE
			SYNTAX      INTEGER
			MAX-ACCESS   read-write
			STATUS       current
			DESCRIPTION
					"The pmtu ."
			::= { portBasedVlanStaticEntry 38 }
		--vlan interface
		portBasedVlanIfTable OBJECT-TYPE
	    	SYNTAX      SEQUENCE OF PortBasedVlanIfEntry
			MAX-ACCESS  not-accessible
			STATUS      current
			DESCRIPTION
					"A table containing static configuration information for
					each VLAN configured into the device by (local or
					network) management.  All entries are permanent and will
					be restored after the device is reset."
			::= { portBasedVlan 4 }
	
		portBasedVlanIfEntry OBJECT-TYPE
			SYNTAX      PortBasedVlanIfEntry
			MAX-ACCESS  not-accessible
			STATUS      current
			DESCRIPTION
					"Static information for a VLAN configured into the
					device by (local or network) management."
			INDEX   { portBasedVlanIfIndex }
			::= { portBasedVlanIfTable 1 }
	
		PortBasedVlanIfEntry ::=
	    	SEQUENCE {                              
				portBasedVlanIfIndex				Unsigned32,
	        	portBasedVlanIfGmrpEnable		INTEGER,
				portBasedVlanIfGvrpEnable		INTEGER,
				portBasedVlanIfVlanList			DisplayString,
				portBasedVlanIfUntaggedList		DisplayString,
				portBasedVlanIfVlansNum			INTEGER,
				portBasedVlanIfPVID				INTEGER,
				portBasedVlanIfTPID				INTEGER,
				portBasedVlanIfDTMode			INTEGER,
				portBasedVlanIfTPIDNum			INTEGER,
				portBasedVlanIfDelTPID			INTEGER,
				portBasedVlanIfTPIDList			DisplayString,
				portBasedVlanIfType         	INTEGER,
				portBasedVlanIfDelVlanList  	OCTET STRING,
				portBasedVlanIfInnerPvid 		INTEGER,
				portBasedVlanIfInnerPri 		INTEGER,
				portBasedVlanIfInnerTpid		INTEGER,
				portBasedVlanIfAllVlanList			DisplayString,
				portBasedVlanIfAllUntaggedList		DisplayString	
	    }
	
		portBasedVlanIfIndex OBJECT-TYPE
			SYNTAX   Unsigned32
			MAX-ACCESS   read-only
			STATUS   current
			DESCRIPTION
					"The state of access control list."
			::= { portBasedVlanIfEntry 1 }
			
		portBasedVlanIfGmrpEnable OBJECT-TYPE
			SYNTAX   INTEGER{
				enable(1),
                disable(0)
			}
			MAX-ACCESS   read-write
			STATUS   current
			DESCRIPTION
					"The state of access control list."
			DEFVAL {disable}
			::= { portBasedVlanIfEntry 2 }

		portBasedVlanIfGvrpEnable OBJECT-TYPE
			SYNTAX   INTEGER{
				enable(1),
                disable(0)
			}
			MAX-ACCESS   read-write
			STATUS   current
			DESCRIPTION
					"The state of access control list."
			DEFVAL {disable}
			::= { portBasedVlanIfEntry 3 }		

		portBasedVlanIfVlanList OBJECT-TYPE
			SYNTAX   DisplayString (SIZE(0..1024))
			MAX-ACCESS   read-write
			STATUS   current
			DESCRIPTION
					"all vlan list."
			::= { portBasedVlanIfEntry 4 }

		portBasedVlanIfUntaggedList OBJECT-TYPE
			SYNTAX   DisplayString (SIZE(0..1024))
			MAX-ACCESS   read-write
			STATUS   current
			DESCRIPTION
					"untagged vlan list."
			::= { portBasedVlanIfEntry 5 }
			
		portBasedVlanIfVlansNum OBJECT-TYPE
			SYNTAX   INTEGER
			MAX-ACCESS   read-only
			STATUS   current
			DESCRIPTION
					"vlan list number(all)."
			::= { portBasedVlanIfEntry 6 }

		portBasedVlanIfPVID OBJECT-TYPE
			SYNTAX   INTEGER
			MAX-ACCESS   read-write
			STATUS   current
			DESCRIPTION
					"Port vid."
			::= { portBasedVlanIfEntry 7 }

		portBasedVlanIfTPID OBJECT-TYPE
			SYNTAX   INTEGER
			MAX-ACCESS   read-write
			STATUS   current
			DESCRIPTION
					"Protocol ID.0x8100 for 802.1q in 802.1q,0x9100 for none 802.1q in 802.1q"
			::= { portBasedVlanIfEntry 8 }

		portBasedVlanIfDTMode OBJECT-TYPE
			SYNTAX   INTEGER{
					enable(1),
					disable(2)
					}
			MAX-ACCESS   read-write
			STATUS   current
			DESCRIPTION
					"double tagged."
			::= { portBasedVlanIfEntry 9 }
			
		portBasedVlanIfTPIDNum OBJECT-TYPE
			SYNTAX   INTEGER
			MAX-ACCESS   read-only
			STATUS   current
			DESCRIPTION
					"support Protocol ID number."
			::= { portBasedVlanIfEntry 10 }
			
		portBasedVlanIfDelTPID OBJECT-TYPE
			SYNTAX   INTEGER
			MAX-ACCESS   read-write
			STATUS   current
			DESCRIPTION
					"del Protocol ID."
			::= { portBasedVlanIfEntry 11 }
			
		portBasedVlanIfTPIDList OBJECT-TYPE
			SYNTAX   DisplayString (SIZE(0..1024))
			MAX-ACCESS   read-only
			STATUS   current
			DESCRIPTION
					"support Protocol ID number."
			::= { portBasedVlanIfEntry 12 }
			
		--add by xiongfang 2010-12-23			
			
			portBasedVlanIfType OBJECT-TYPE
			SYNTAX       INTEGER{
			    hybrid(0),
			    trunk(1),
			    access(2) 
			}
			MAX-ACCESS   read-write
			STATUS       current
			DESCRIPTION
					"port type:hybrid:0,trunk:1,access:2."
			::= { portBasedVlanIfEntry 13 }
			
			portBasedVlanIfDelVlanList OBJECT-TYPE
			SYNTAX      OCTET STRING (SIZE(0..1024))
			MAX-ACCESS   read-write
			STATUS       current
			DESCRIPTION
					"Delete the vlan list on the interface ."
			::= { portBasedVlanIfEntry 14 }
			
			portBasedVlanIfInnerPvid OBJECT-TYPE
			SYNTAX   INTEGER
			MAX-ACCESS   read-write
			STATUS   current
			DESCRIPTION
					"The inner pvid."
			::= { portBasedVlanIfEntry 15 }
			
			portBasedVlanIfInnerPri OBJECT-TYPE
			SYNTAX   INTEGER
			MAX-ACCESS   read-write
			STATUS   current
			DESCRIPTION
					"The inner priority ."
			::= { portBasedVlanIfEntry 16 }
			
			portBasedVlanIfInnerTpid OBJECT-TYPE
			SYNTAX   INTEGER
			MAX-ACCESS   read-write
			STATUS   current
			DESCRIPTION
					"The inner tpid."
			::= { portBasedVlanIfEntry 17 }   
			
			portBasedVlanIfAllVlanList	OBJECT-TYPE
			SYNTAX   DisplayString
			MAX-ACCESS   read-only
			STATUS   current
			DESCRIPTION
					"all tag vlan list."
			::= { portBasedVlanIfEntry 18 }		
				
			portBasedVlanIfAllUntaggedList	OBJECT-TYPE
			SYNTAX   DisplayString
			MAX-ACCESS   read-only
			STATUS   current
			DESCRIPTION
					"all untag vlan list."
			::= { portBasedVlanIfEntry 19 }	
			                            
		--mac base valn
		macBasedVlan			OBJECT IDENTIFIER ::=   {msppLayer2 3}
		macBasedVlanTable OBJECT-TYPE
			SYNTAX  SEQUENCE OF MacBasedVlanEntry
			MAX-ACCESS  not-accessible
			STATUS  current
			DESCRIPTION
					"A list of interface entries.  The number of
					entries is given by the value of ifNumber."
			::= { macBasedVlan 2 }
	
		macBasedVlanEntry OBJECT-TYPE
			SYNTAX  MacBasedVlanEntry
			MAX-ACCESS  not-accessible
			STATUS  current
			DESCRIPTION
					"An interface entry containing objects at the
					subnetwork layer and below for a particular
					interface."
			INDEX   { macBasedVlanMacAddr,macBasedVlanMacAddrPrefix }
			::= { macBasedVlanTable 1 }

		MacBasedVlanEntry ::=
			SEQUENCE {
				macBasedVlanMacAddr			      MacAddress,
				macBasedVlanMacAddrPrefix			INTEGER,
				macBasedVlanID		            Integer32,
				macBasedVlanPriority          Integer32,
				macBasedVlanState             INTEGER,
				macBasedVlanRowStatus         EntryStatus
			}		        
	
		macBasedVlanMacAddr	OBJECT-TYPE
		        SYNTAX MacAddress 
        		MAX-ACCESS read-only
        		STATUS current
        		DESCRIPTION
                	"mac address."
        	::= { macBasedVlanEntry 1 }
	
		macBasedVlanMacAddrPrefix	OBJECT-TYPE
        		SYNTAX  INTEGER
        		MAX-ACCESS read-only
        		STATUS current
        		DESCRIPTION
                	"mac address prefix."
        	::= { macBasedVlanEntry 2 }
        	
		macBasedVlanID	OBJECT-TYPE
	        	SYNTAX Integer32
        		MAX-ACCESS read-write
        		STATUS current
        		DESCRIPTION
                	"vlan id ."
        	::= { macBasedVlanEntry 3 }
        	
    macBasedVlanPriority	OBJECT-TYPE
	        	SYNTAX Integer32
        		MAX-ACCESS read-write
        		STATUS current
        		DESCRIPTION
                	"mac vlan priority ."
        	::= { macBasedVlanEntry 4 }
        	
   macBasedVlanState	OBJECT-TYPE
	        	SYNTAX INTEGER
        		MAX-ACCESS read-write
        		STATUS current
        		DESCRIPTION
                	"vlan state:static:0\dynamic:1."
        	::= { macBasedVlanEntry 5 }
        	
   macBasedVlanRowStatus	OBJECT-TYPE
	        	SYNTAX EntryStatus
        		MAX-ACCESS read-write
        		STATUS current
        		DESCRIPTION
                	"entry status."
        	::= { macBasedVlanEntry 6 }
        	
		
		--ip Based valn
		ipBasedVlan			OBJECT IDENTIFIER ::=   {msppLayer2 4}
		ipBasedVlanTable OBJECT-TYPE
			SYNTAX  SEQUENCE OF IpBasedVlanEntry
			MAX-ACCESS  not-accessible
			STATUS  current
			DESCRIPTION
					"A list of interface entries.  The number of
					entries is given by the value of ifNumber."
			::= { ipBasedVlan 2 }
	
		ipBasedVlanEntry OBJECT-TYPE
			SYNTAX  IpBasedVlanEntry
			MAX-ACCESS  not-accessible
			STATUS  current
			DESCRIPTION
					"An interface entry containing objects at the
					subnetwork layer and below for a particular
					interface."
			INDEX   { ipBasedVlanIpAddrType, ipBasedVlanIpAddr, ipBasedVlanIpPrefix}
			::= { ipBasedVlanTable 1 }

		IpBasedVlanEntry ::=
			SEQUENCE {
				ipBasedVlanIpAddrType		INTEGER,
				ipBasedVlanIpAddr			  InetAddress,
				ipBasedVlanIpPrefix			InetAddressPrefixLength,
				ipBasedVlanID           Integer32,
				ipBasedVlanIpPriority   Integer32,
				ipBasedVlanRowStatus		EntryStatus
			}		        
	
		ipBasedVlanIpAddrType	OBJECT-TYPE
	        	SYNTAX INTEGER 
        		MAX-ACCESS read-only
        		STATUS current
        		DESCRIPTION
                	"the ip address type."
        	::= { ipBasedVlanEntry 1 }
	
		ipBasedVlanIpAddr	OBJECT-TYPE
	        	SYNTAX InetAddress 
        		MAX-ACCESS read-only
        		STATUS current
        		DESCRIPTION
                	"the ip address."
        	::= { ipBasedVlanEntry 2 }
        	
    ipBasedVlanIpPrefix	OBJECT-TYPE
	        	SYNTAX InetAddressPrefixLength 
        		MAX-ACCESS read-only
        		STATUS current
        		DESCRIPTION
                	"the prefix of ip address."
        	::= { ipBasedVlanEntry 3 }
        	
    ipBasedVlanID	OBJECT-TYPE
	        	SYNTAX Integer32 
        		MAX-ACCESS read-write
        		STATUS current
        		DESCRIPTION
                	"vlan id ."
        	::= { ipBasedVlanEntry 4 }
        	
        	ipBasedVlanIpPriority	OBJECT-TYPE
	        	SYNTAX Integer32 
        		MAX-ACCESS read-write
        		STATUS current
        		DESCRIPTION
                	"the priority of vlan-ip."
        	::= { ipBasedVlanEntry 5 }
        	
    ipBasedVlanRowStatus	OBJECT-TYPE
		        SYNTAX EntryStatus
        		MAX-ACCESS read-write
        		STATUS current
        		DESCRIPTION
                	"table status."
        	::= { ipBasedVlanEntry 6 }
        	
        	
    --protocol Based valn
		protocolBasedVlan			OBJECT IDENTIFIER ::=   {msppLayer2 9}
		protocolBasedVlanTable OBJECT-TYPE
			SYNTAX  SEQUENCE OF ProtocolBasedVlanEntry
			MAX-ACCESS  not-accessible
			STATUS  current
			DESCRIPTION
					"A list of interface entries.  The number of
					entries is given by the value of ifNumber."
			::= { protocolBasedVlan 3 }
	
		protocolBasedVlanEntry OBJECT-TYPE
			SYNTAX  ProtocolBasedVlanEntry
			MAX-ACCESS  not-accessible
			STATUS  current
			DESCRIPTION
					"An interface entry containing objects at the
					subnetwork layer and below for a particular
					interface."
			INDEX   { protocolBasedVlanInstance}
			::= { protocolBasedVlanTable 1 }

		ProtocolBasedVlanEntry ::=
			SEQUENCE {
				protocolBasedVlanInstance			Integer32,
				protocolBasedVlanFrameType		INTEGER,
				protocolBasedVlanEthType		  INTEGER,
				protocolBasedVlanMatchUpper   Integer32,
				protocolBasedVlanMatchLower   Integer32,
				protocolBasedVlanRowStatus		EntryStatus
			}
	
		protocolBasedVlanInstance	OBJECT-TYPE
	        	SYNTAX Integer32 
        		MAX-ACCESS read-only
        		STATUS current
        		DESCRIPTION
                	"protocol-vlan instance ."
        	::= { protocolBasedVlanEntry 1 }
	
		protocolBasedVlanFrameType	OBJECT-TYPE
        		SYNTAX INTEGER 
        		MAX-ACCESS read-write
        		STATUS current
        		DESCRIPTION
                	"frame type."
        	::= { protocolBasedVlanEntry 2 }
        	
	  protocolBasedVlanEthType	OBJECT-TYPE
        		SYNTAX INTEGER 
        		MAX-ACCESS read-write
        		STATUS current
        		DESCRIPTION
                	"ethernet type."
        	::= { protocolBasedVlanEntry 3 }
        	
    protocolBasedVlanMatchUpper	OBJECT-TYPE
        		SYNTAX Integer32 
        		MAX-ACCESS read-write
        		STATUS current
        		DESCRIPTION
                	"the value of match upper."
        	::= { protocolBasedVlanEntry 4 }
        	
	  protocolBasedVlanMatchLower	OBJECT-TYPE
        		SYNTAX Integer32 
        		MAX-ACCESS read-write
        		STATUS current
        		DESCRIPTION
                	"the value of match lower."
        	::= { protocolBasedVlanEntry 5 }
        	
   protocolBasedVlanRowStatus	OBJECT-TYPE
		        SYNTAX EntryStatus
        		MAX-ACCESS read-write
        		STATUS current
        		DESCRIPTION
                	"table status."
        	::= { protocolBasedVlanEntry 6 }
        	
    
		protocolBasedVlanIfTable OBJECT-TYPE
			SYNTAX  SEQUENCE OF ProtocolBasedVlanIfEntry
			MAX-ACCESS  not-accessible
			STATUS  current
			DESCRIPTION
					"the inteface table of protocol-vlan."
			::= { protocolBasedVlan 2 }
	
		protocolBasedVlanIfEntry OBJECT-TYPE
			SYNTAX  ProtocolBasedVlanIfEntry
			MAX-ACCESS  not-accessible
			STATUS  current
			DESCRIPTION
					"the inteface table of protocol-vlan."
			INDEX   { protocolBasedVlanIfIndex,protocolBasedVlanIfInstance}
			::= { protocolBasedVlanIfTable 1 }
    
    ProtocolBasedVlanIfEntry ::=
			SEQUENCE {
				protocolBasedVlanIfIndex			Integer32,
				protocolBasedVlanIfInstance		Integer32,
				protocolBasedVlanIfVid		    Integer32,
				protocolBasedVlanIfPrio       Integer32,
				protocolBasedVlanIfRowStatus	EntryStatus
			}
	
		protocolBasedVlanIfIndex	OBJECT-TYPE
	        	SYNTAX Integer32 
        		MAX-ACCESS read-only
        		STATUS current
        		DESCRIPTION
                	"the interface index."
        	::= { protocolBasedVlanIfEntry 1 }
	
		protocolBasedVlanIfInstance	OBJECT-TYPE
        		SYNTAX Integer32 
        		MAX-ACCESS read-only
        		STATUS current
        		DESCRIPTION
                	"the instance of vlan ."
        	::= { protocolBasedVlanIfEntry 2 }
        	
	  protocolBasedVlanIfVid	OBJECT-TYPE
        		SYNTAX Integer32 
        		MAX-ACCESS read-write
        		STATUS current
        		DESCRIPTION
                	"vlan id."
        	::= { protocolBasedVlanIfEntry 3 }
        	
    protocolBasedVlanIfPrio	OBJECT-TYPE
        		SYNTAX Integer32 
        		MAX-ACCESS read-write
        		STATUS current
        		DESCRIPTION
                	"the priority of protocol-vlan."
        	::= { protocolBasedVlanIfEntry 4 }
        	
	  protocolBasedVlanIfRowStatus	OBJECT-TYPE
        		SYNTAX EntryStatus 
        		MAX-ACCESS read-write
        		STATUS current
        		DESCRIPTION
                	"entry status."
        	::= { protocolBasedVlanIfEntry 5 }
        	
  
        	
  -- add by xiongfang 2011-1-11 	
	wriVlanStatistic OBJECT IDENTIFIER ::=   {wriMgmt 300}
    	
		vlanStatisticTable OBJECT-TYPE
			SYNTAX  SEQUENCE OF VlanStatisticEntry
			MAX-ACCESS  not-accessible
			STATUS  current
			DESCRIPTION
					"the statistic info of vlan ."
			::= { wriVlanStatistic 1 }
	
		vlanStatisticEntry OBJECT-TYPE
			SYNTAX  VlanStatisticEntry
			MAX-ACCESS  not-accessible
			STATUS  current
			DESCRIPTION
					"the statistic info of vlan ."
			INDEX   { vlanStatisticVid,vlanStatisticSlotId}
			::= { vlanStatisticTable 1 }

		VlanStatisticEntry ::=
			SEQUENCE {
				vlanStatisticVid                    Integer32,
				vlanStatisticSlotId     			Integer32,
				vlanStatisticInPackets  			Counter64,
				vlanStatisticInBytes    			Counter64,
				vlanStatisticOutPackets 			Counter64,
				vlanStatisticOutBytes   			Counter64
			}

		vlanStatisticVid	OBJECT-TYPE
	        	SYNTAX Integer32
        		MAX-ACCESS read-only
        		STATUS current
        		DESCRIPTION
                	"vlan id."
        	::= { vlanStatisticEntry 1 }
	
		vlanStatisticSlotId	OBJECT-TYPE
        		SYNTAX Integer32 
        		MAX-ACCESS read-only
        		STATUS current
        		DESCRIPTION
                	"slot id."
        	::= { vlanStatisticEntry 2 }
        	
	 vlanStatisticInPackets	OBJECT-TYPE
        		SYNTAX Counter64 
        		MAX-ACCESS read-only
        		STATUS current
        		DESCRIPTION
                	"the input packets."
        	::= { vlanStatisticEntry 3 }
        	
   vlanStatisticInBytes	OBJECT-TYPE
		        SYNTAX Counter64
        		MAX-ACCESS read-only
        		STATUS current
        		DESCRIPTION
                	"the input bytes."
        	::= { vlanStatisticEntry 4 }
        	
    vlanStatisticOutPackets	OBJECT-TYPE
        		SYNTAX Counter64 
        		MAX-ACCESS read-only
        		STATUS current
        		DESCRIPTION
                	"the output packets."
        	::= { vlanStatisticEntry 5 }
        	
    vlanStatisticOutBytes	OBJECT-TYPE
		        SYNTAX Counter64
        		MAX-ACCESS read-only
        		STATUS current
        		DESCRIPTION
                	"the output bytes."
        	::= { vlanStatisticEntry 6 }
        	
END
