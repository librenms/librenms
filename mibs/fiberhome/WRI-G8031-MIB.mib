--
-- wriG8031.mib
-- MIB generated by MG-SOFT Visual MIB Builder Version 4.0 Build 349
-- Tuesday, February 19, 2013 at 14:50:27
--

--  wriG8031.mib
-- MIB generated by MG-SOFT Visual MIB Builder Version 4.0 Build 349
-- Tuesday, November 15, 2011 at 15:23:46
-- 

	WRI-G8031-MIB DEFINITIONS ::= BEGIN
 
		IMPORTS
			TimeTicks, Integer32, Unsigned32, OBJECT-TYPE, NOTIFICATION-TYPE			
				FROM SNMPv2-SMI			
			TEXTUAL-CONVENTION			
				FROM SNMPv2-TC			
			wriProducts, wriProtocol			
				FROM WRI-SMI;
	
	
--
-- Type definitions
--
	
--  Type definitions
-- 
		DisplayString ::= OCTET STRING

	
--
-- Textual conventions
--
	
--  Textual conventions
-- 
		EntryStatus ::= TEXTUAL-CONVENTION
			STATUS current
			DESCRIPTION 
				"entry status."
			SYNTAX INTEGER
				{
				valid(1),
				createRequest(2),
				underCreation(3),
				invalid(4)
				}

	
--
-- Node definitions
--
	
--  Node definitions
-- 
		-- 1.3.6.1.4.1.3807.2.701
		wriG8031 OBJECT IDENTIFIER ::= { wriProtocol 701 }

		
		-- 1.3.6.1.4.1.3807.2.701.1
		g8031General OBJECT IDENTIFIER ::= { wriG8031 1 }

		
		-- 1.3.6.1.4.1.3807.2.701.1.1
		g8031CcCheckTimer OBJECT-TYPE
			SYNTAX INTEGER
			MAX-ACCESS read-write
			STATUS current
			DESCRIPTION
				"cc check timer,unit is s"
			::= { g8031General 1 }

		
		-- 1.3.6.1.4.1.3807.2.701.1.2
		g8031TrapEnable OBJECT-TYPE
			SYNTAX INTEGER
				{
				enable(1),
				disable(2)
				}
			MAX-ACCESS read-write
			STATUS current
			DESCRIPTION
				"Description."
			::= { g8031General 2 }

		
		-- 1.3.6.1.4.1.3807.2.701.1.3
		g8031Y1731Auto OBJECT-TYPE
			SYNTAX INTEGER
				{
				enable(1),
				disable(2)
				}
			MAX-ACCESS read-write
			STATUS current
			DESCRIPTION
				"Description."
			::= { g8031General 3 }

		
		-- 1.3.6.1.4.1.3807.2.701.2
		g8031InstanceTable OBJECT-TYPE
			SYNTAX SEQUENCE OF G8031InstanceEntry
			MAX-ACCESS not-accessible
			STATUS current
			DESCRIPTION
				"The list of configured ethernet  protection  switching
				instances."
			::= { wriG8031 2 }

		
		-- 1.3.6.1.4.1.3807.2.701.2.1
		g8031InstanceEntry OBJECT-TYPE
			SYNTAX G8031InstanceEntry
			MAX-ACCESS not-accessible
			STATUS current
			DESCRIPTION
				"A table entry representing each ethernet  protection  switching
				instance."
			INDEX { g8031InstanceIndex }
			::= { g8031InstanceTable 1 }

		
		G8031InstanceEntry ::=
			SEQUENCE { 
				g8031InstanceIndex
					Unsigned32,
				g8031InstanceVlanList
					OCTET STRING,
				g8031InstanceVlanAdd
					OCTET STRING,
				g8031InstanceVlanDel
					OCTET STRING,
				g8031InstanceCtrlVlan
					INTEGER,
				g8031InstanceWTRTimer
					Unsigned32,
				g8031InstanceHoldOffTimer
					Unsigned32,
				g8031InstanceWorkPort
					INTEGER,
				g8031InstanceWorkPortForward
					INTEGER,
				g8031InstanceWorkPortOperate
					INTEGER,
				g8031InstanceWorkPortAction
					INTEGER,
				g8031InstanceProtectPort
					INTEGER,
				g8031InstanceProtectPortForward
					INTEGER,
				g8031InstanceProtectPortOperate
					INTEGER,
				g8031InstanceProtectPortAction
					INTEGER,
				g8031InstanceArch
					INTEGER,
				g8031InstanceDir
					INTEGER,
				g8031InstanceMode
					INTEGER,
				g8031InstanceCmdType
					INTEGER,
				g8031InstanceSMStatus
					INTEGER,
				g8031InstanceEntryStatus
					EntryStatus,
				g8031InstanceMel
					Integer32,
				g8031InstanceWtrReMain
					Integer32
			 }

		-- 1.3.6.1.4.1.3807.2.701.2.1.1
		g8031InstanceIndex OBJECT-TYPE
			SYNTAX Unsigned32
			MAX-ACCESS read-only
			STATUS current
			DESCRIPTION
				"The unique ID of this Ethernet  protection  switching instance.
				This value SHALL be between 1 and g8031MaxId 
				inclusively."
			::= { g8031InstanceEntry 1 }

		
		-- 1.3.6.1.4.1.3807.2.701.2.1.2
		g8031InstanceVlanList OBJECT-TYPE
			SYNTAX OCTET STRING
			MAX-ACCESS read-only
			STATUS current
			DESCRIPTION
				"Data vlan"
			::= { g8031InstanceEntry 2 }

		
		-- 1.3.6.1.4.1.3807.2.701.2.1.3
		g8031InstanceVlanAdd OBJECT-TYPE
			SYNTAX OCTET STRING
			MAX-ACCESS read-write
			STATUS current
			DESCRIPTION
				"add Data vlan"
			::= { g8031InstanceEntry 3 }

		
		-- 1.3.6.1.4.1.3807.2.701.2.1.4
		g8031InstanceVlanDel OBJECT-TYPE
			SYNTAX OCTET STRING
			MAX-ACCESS read-write
			STATUS current
			DESCRIPTION
				"delete Data vlan"
			::= { g8031InstanceEntry 4 }

		
		-- 1.3.6.1.4.1.3807.2.701.2.1.5
		g8031InstanceCtrlVlan OBJECT-TYPE
			SYNTAX INTEGER
			MAX-ACCESS read-write
			STATUS current
			DESCRIPTION
				"channel vlan Id"
			::= { g8031InstanceEntry 5 }

		
		-- 1.3.6.1.4.1.3807.2.701.2.1.6
		g8031InstanceWTRTimer OBJECT-TYPE
			SYNTAX Unsigned32
			MAX-ACCESS read-write
			STATUS current
			DESCRIPTION
				"wtr timer,unit is min"
			::= { g8031InstanceEntry 6 }

		
		-- 1.3.6.1.4.1.3807.2.701.2.1.7
		g8031InstanceHoldOffTimer OBJECT-TYPE
			SYNTAX Unsigned32
			MAX-ACCESS read-write
			STATUS current
			DESCRIPTION
				"hold off timer,unit is ms"
			::= { g8031InstanceEntry 7 }

		
		-- 1.3.6.1.4.1.3807.2.701.2.1.8
		g8031InstanceWorkPort OBJECT-TYPE
			SYNTAX INTEGER
			MAX-ACCESS read-write
			STATUS current
			DESCRIPTION
				"working port"
			REFERENCE
				"instance working port"
			::= { g8031InstanceEntry 8 }

		
		-- 1.3.6.1.4.1.3807.2.701.2.1.9
		g8031InstanceWorkPortForward OBJECT-TYPE
			SYNTAX INTEGER
			MAX-ACCESS read-only
			STATUS current
			DESCRIPTION
				"working port forwarding status"
			::= { g8031InstanceEntry 9 }

		
		-- 1.3.6.1.4.1.3807.2.701.2.1.10
		g8031InstanceWorkPortOperate OBJECT-TYPE
			SYNTAX INTEGER
			MAX-ACCESS read-only
			STATUS current
			DESCRIPTION
				"working port operation status"
			::= { g8031InstanceEntry 10 }

		
		-- 1.3.6.1.4.1.3807.2.701.2.1.11
		g8031InstanceWorkPortAction OBJECT-TYPE
			SYNTAX INTEGER
			MAX-ACCESS read-only
			STATUS current
			DESCRIPTION
				"working port action status"
			::= { g8031InstanceEntry 11 }

		
		-- 1.3.6.1.4.1.3807.2.701.2.1.12
		g8031InstanceProtectPort OBJECT-TYPE
			SYNTAX INTEGER
			MAX-ACCESS read-write
			STATUS current
			DESCRIPTION
				"protecting port"
			REFERENCE
				"instance protection port"
			::= { g8031InstanceEntry 12 }

		
		-- 1.3.6.1.4.1.3807.2.701.2.1.13
		g8031InstanceProtectPortForward OBJECT-TYPE
			SYNTAX INTEGER
			MAX-ACCESS read-only
			STATUS current
			DESCRIPTION
				"protecting port forward status"
			::= { g8031InstanceEntry 13 }

		
		-- 1.3.6.1.4.1.3807.2.701.2.1.14
		g8031InstanceProtectPortOperate OBJECT-TYPE
			SYNTAX INTEGER
			MAX-ACCESS read-only
			STATUS current
			DESCRIPTION
				"protecting port operate status"
			::= { g8031InstanceEntry 14 }

		
		-- 1.3.6.1.4.1.3807.2.701.2.1.15
		g8031InstanceProtectPortAction OBJECT-TYPE
			SYNTAX INTEGER
			MAX-ACCESS read-only
			STATUS current
			DESCRIPTION
				"protecting port action status"
			::= { g8031InstanceEntry 15 }

		
		-- 1.3.6.1.4.1.3807.2.701.2.1.16
		g8031InstanceArch OBJECT-TYPE
			SYNTAX INTEGER
				{
				oneversusone(1),
				oneplusone(2)
				}
			MAX-ACCESS read-write
			STATUS current
			DESCRIPTION
				"architectures of instance."
			::= { g8031InstanceEntry 16 }

		
		-- 1.3.6.1.4.1.3807.2.701.2.1.17
		g8031InstanceDir OBJECT-TYPE
			SYNTAX INTEGER
				{
				bidirection(1),
				unidirection(2)
				}
			MAX-ACCESS read-write
			STATUS current
			DESCRIPTION
				"Direction of instance. "
			::= { g8031InstanceEntry 17 }

		
		-- 1.3.6.1.4.1.3807.2.701.2.1.18
		g8031InstanceMode OBJECT-TYPE
			SYNTAX INTEGER
				{
				revertive(1),
				nonrever(2)
				}
			MAX-ACCESS read-write
			STATUS current
			DESCRIPTION
				"Revertive and non-revertive switching. "
			::= { g8031InstanceEntry 18 }

		
		-- 1.3.6.1.4.1.3807.2.701.2.1.19
		g8031InstanceCmdType OBJECT-TYPE
			SYNTAX INTEGER
				{
				lockout(1),
				ms(2),
				fs(3),
				exercise(4),
				clear(5)
				}
			MAX-ACCESS read-write
			STATUS current
			DESCRIPTION
				"set 1 to lockout for protection. "
			::= { g8031InstanceEntry 19 }

		
		-- 1.3.6.1.4.1.3807.2.701.2.1.20
		g8031InstanceSMStatus OBJECT-TYPE
			SYNTAX INTEGER
				{
				norequestworking(1),
				norequestprotection(2),
				lockout(3),
				forcedswitch(4),
				signalfailworking(5),
				signalfailprotection(6),
				manualswitch(7),
				waittorestore(8),
				exerciseworking(9),
				exerciseprotection(10),
				donotrevert(11),
				idle(12),
				error(13)
				}
			MAX-ACCESS read-only
			STATUS current
			DESCRIPTION
				"instance sm status"
			::= { g8031InstanceEntry 20 }

		
		-- 1.3.6.1.4.1.3807.2.701.2.1.21
		g8031InstanceEntryStatus OBJECT-TYPE
			SYNTAX EntryStatus
			MAX-ACCESS read-write
			STATUS current
			DESCRIPTION
				"1 snmp_valid
				2 snmp_createrequest
				3 snmp_undercreation
				4 snmp_invalid"
			::= { g8031InstanceEntry 21 }

		
		-- 1.3.6.1.4.1.3807.2.701.2.1.22
		g8031InstanceMel OBJECT-TYPE
			SYNTAX Integer32
			MAX-ACCESS read-write
			STATUS current
			DESCRIPTION
				"Description."
			::= { g8031InstanceEntry 22 }

		
		-- 1.3.6.1.4.1.3807.2.701.2.1.23
		g8031InstanceWtrReMain OBJECT-TYPE
			SYNTAX Integer32
			MAX-ACCESS read-only
			STATUS current
			DESCRIPTION
				"Description."
			::= { g8031InstanceEntry 23 }

		
		-- 1.3.6.1.4.1.3807.2.701.3
		g8031Trap OBJECT IDENTIFIER ::= { wriG8031 3 }

		
		-- 1.3.6.1.4.1.3807.2.701.3.1
		g8031StatusChange NOTIFICATION-TYPE
			OBJECTS { g8031InstanceSMStatus, g8031InstanceWorkPort, g8031InstanceProtectPort, g8031InstanceWorkPortForward, g8031InstanceProtectPortForward
				 }
			STATUS current
			DESCRIPTION 
				"status changed of instance."
			::= { g8031Trap 1 }

		
		-- 1.3.6.1.4.1.3807.2.701.4
		g8031InstancePortTable OBJECT-TYPE
			SYNTAX SEQUENCE OF G8031InstancePortEntry
			MAX-ACCESS not-accessible
			STATUS current
			DESCRIPTION
				"Description."
			::= { wriG8031 4 }

		
		-- 1.3.6.1.4.1.3807.2.701.4.1
		g8031InstancePortEntry OBJECT-TYPE
			SYNTAX G8031InstancePortEntry
			MAX-ACCESS not-accessible
			STATUS current
			DESCRIPTION
				"Description."
			INDEX { g8031InstancePortInsIdx, g8031InstancePortPortIdx }
			::= { g8031InstancePortTable 1 }

		
		G8031InstancePortEntry ::=
			SEQUENCE { 
				g8031InstancePortInsIdx
					Integer32,
				g8031InstancePortPortIdx
					Integer32,
				g8031InstancePortIfUnit
					Integer32,
				g8031InstancePortOperstate
					Integer32,
				g8031InstancePortFwdstate
					Integer32,
				g8031InstancePortAction
					Integer32,
				g8031InstancePortRxcount
					Integer32,
				g8031InstancePortTxcount
					Integer32,
				g8031InstancePortEntryStatus
					Integer32,
				g8031InstancePortRole
					Integer32
			 }

		-- 1.3.6.1.4.1.3807.2.701.4.1.1
		g8031InstancePortInsIdx OBJECT-TYPE
			SYNTAX Integer32
			MAX-ACCESS read-only
			STATUS current
			DESCRIPTION
				"Description."
			::= { g8031InstancePortEntry 1 }

		
		-- 1.3.6.1.4.1.3807.2.701.4.1.2
		g8031InstancePortPortIdx OBJECT-TYPE
			SYNTAX Integer32
			MAX-ACCESS read-only
			STATUS current
			DESCRIPTION
				"Description."
			::= { g8031InstancePortEntry 2 }

		
		-- 1.3.6.1.4.1.3807.2.701.4.1.3
		g8031InstancePortIfUnit OBJECT-TYPE
			SYNTAX Integer32
			MAX-ACCESS read-only
			STATUS current
			DESCRIPTION
				"Description."
			::= { g8031InstancePortEntry 3 }

		
		-- 1.3.6.1.4.1.3807.2.701.4.1.4
		g8031InstancePortOperstate OBJECT-TYPE
			SYNTAX Integer32
			MAX-ACCESS read-only
			STATUS current
			DESCRIPTION
				"Description."
			::= { g8031InstancePortEntry 4 }

		
		-- 1.3.6.1.4.1.3807.2.701.4.1.5
		g8031InstancePortFwdstate OBJECT-TYPE
			SYNTAX Integer32
			MAX-ACCESS read-only
			STATUS current
			DESCRIPTION
				"Description."
			::= { g8031InstancePortEntry 5 }

		
		-- 1.3.6.1.4.1.3807.2.701.4.1.6
		g8031InstancePortAction OBJECT-TYPE
			SYNTAX Integer32
			MAX-ACCESS read-only
			STATUS current
			DESCRIPTION
				"Description."
			::= { g8031InstancePortEntry 6 }

		
		-- 1.3.6.1.4.1.3807.2.701.4.1.7
		g8031InstancePortRxcount OBJECT-TYPE
			SYNTAX Integer32
			MAX-ACCESS read-only
			STATUS current
			DESCRIPTION
				"Description."
			::= { g8031InstancePortEntry 7 }

		
		-- 1.3.6.1.4.1.3807.2.701.4.1.8
		g8031InstancePortTxcount OBJECT-TYPE
			SYNTAX Integer32
			MAX-ACCESS read-only
			STATUS current
			DESCRIPTION
				"Description."
			::= { g8031InstancePortEntry 8 }

		
		-- 1.3.6.1.4.1.3807.2.701.4.1.9
		g8031InstancePortEntryStatus OBJECT-TYPE
			SYNTAX Integer32
			MAX-ACCESS read-write
			STATUS current
			DESCRIPTION
				"Description."
			::= { g8031InstancePortEntry 9 }

		
		-- 1.3.6.1.4.1.3807.2.701.4.1.10
		g8031InstancePortRole OBJECT-TYPE
			SYNTAX Integer32
			MAX-ACCESS read-write
			STATUS current
			DESCRIPTION
				"Description."
			::= { g8031InstancePortEntry 10 }

		
	
	END

--
-- wriG8031.mib
--
