--
-- WRI-PM-MIB.mib
-- MIB generated by MG-SOFT Visual MIB Builder Version 4.0 Build 349
-- Saturday, December 22, 2012 at 11:02:37
--

	WRI-PM-MIB DEFINITIONS ::= BEGIN
 
		IMPORTS
			TimeTicks, Unsigned32, Counter64, OBJECT-TYPE			
				FROM SNMPv2-SMI			
			TEXTUAL-CONVENTION			
				FROM SNMPv2-TC			
			wriProtocol			
				FROM WRI-SMI;
	
	
--
-- Textual conventions
--
	
		DisplayString ::= TEXTUAL-CONVENTION
			STATUS current
			DESCRIPTION 
				"8 bit octet."
			SYNTAX OCTET STRING

		EntryStatus ::= TEXTUAL-CONVENTION
			STATUS current
			DESCRIPTION 
				"entry status."
			SYNTAX INTEGER
				{
				valid(1),
				createRequest(2),
				underCreation(3),
				invalid(4)
				}

	
--
-- Node definitions
--
	
		pm OBJECT IDENTIFIER ::= { wriProtocol 1619 }

		
		pmIfPeriod OBJECT IDENTIFIER ::= { pm 1 }

		
		pmIfStatusTable OBJECT-TYPE
			SYNTAX SEQUENCE OF PmIfStatusEntry
			MAX-ACCESS not-accessible
			STATUS current
			DESCRIPTION
				"Description."
			::= { pmIfPeriod 1 }

		
		pmIfStatusEntry OBJECT-TYPE
			SYNTAX PmIfStatusEntry
			MAX-ACCESS not-accessible
			STATUS current
			DESCRIPTION
				"Description."
			INDEX { pmIfStatusIfUnit }
			::= { pmIfStatusTable 1 }

		
		PmIfStatusEntry ::=
			SEQUENCE { 
				pmIfStatusIfUnit
					INTEGER,
				pmIfStatus
					INTEGER,
				pmIfStatusStatClear
					INTEGER
			 }

		pmIfStatusIfUnit OBJECT-TYPE
			SYNTAX INTEGER (1..2147483647)
			MAX-ACCESS read-only
			STATUS current
			DESCRIPTION
				"Description."
			::= { pmIfStatusEntry 1 }

		
		pmIfStatus OBJECT-TYPE
			SYNTAX INTEGER
				{
				enable(1),
				disable(2)
				}
			MAX-ACCESS read-write
			STATUS current
			DESCRIPTION
				"Description."
			::= { pmIfStatusEntry 2 }

		
		pmIfStatusStatClear OBJECT-TYPE
			SYNTAX INTEGER
				{
				clearall(0),
				clear1m(1),
				clear5m(2),
				clear15m(3),
				clear24h(4),  
				clearUnTimed(5)				
				}
			MAX-ACCESS read-write
			STATUS current
			DESCRIPTION
				"Description."
			::= { pmIfStatusEntry 3 }

		
		pmIf1mStatTable OBJECT-TYPE
			SYNTAX SEQUENCE OF PmIf1mStatEntry
			MAX-ACCESS not-accessible
			STATUS current
			DESCRIPTION
				"Description."
			::= { pmIfPeriod 2 }

		
		pmIf1mStatEntry OBJECT-TYPE
			SYNTAX PmIf1mStatEntry
			MAX-ACCESS not-accessible
			STATUS current
			DESCRIPTION
				"Description."
			INDEX { pmIf1mStatIfUnit, pmIf1mStatTimeStamp }
			::= { pmIf1mStatTable 1 }

		
		PmIf1mStatEntry ::=
			SEQUENCE { 
				pmIf1mStatIfUnit
					INTEGER,
				pmIf1mStatTimeStamp
					Unsigned32,
				pmIf1mStatBinFlag
					INTEGER,
				pmIf1mStatTx5mPps
					Counter64,
				pmIf1mStatTx5mBps
					Counter64,
				pmIf1mStatRx5mPps
					Counter64,
				pmIf1mStatRx5mBps
					Counter64,
				pmIf1mStatTxBytes
					Counter64,
				pmIf1mStatRxBytes
					Counter64,
				pmIf1mStatJunbo
					Counter64,
				pmIf1mStatFcsErrs
					Counter64,
				pmIf1mStatCollisions
					Counter64,
				pmIf1mStatDropEvts
					Counter64,
				pmIf1mStatUndersize
					Counter64,
				pmIf1mStatFragments
					Counter64,
				pmIf1mStatTxPkts
					Counter64,
				pmIf1mStatTxPause
					Counter64,
				pmIf1mStatTxUnicast
					Counter64,
				pmIf1mStatTxMulticast
					Counter64,
				pmIf1mStatTxBroadcast
					Counter64,
				pmIf1mStatRxPkts
					Counter64,
				pmIf1mStatRxPause
					Counter64,
				pmIf1mStatRxUnicast
					Counter64,
				pmIf1mStatRxMulticast
					Counter64,
				pmIf1mStatRxBroadcast
					Counter64,
				pmIf1mStatDurPrdOperState
					INTEGER,
				pmIf1mStatEndPrdOperState
					INTEGER,
				pmIf1mStatDurPrdAdminState
					INTEGER,
				pmIf1mStatEndPrdAdminState
					INTEGER,
				pmIf1mStatOversize
					Counter64
			 }

		pmIf1mStatIfUnit OBJECT-TYPE
			SYNTAX INTEGER (1..2147483647)
			MAX-ACCESS read-only
			STATUS current
			DESCRIPTION
				"Description."
			::= { pmIf1mStatEntry 1 }

		
		pmIf1mStatTimeStamp OBJECT-TYPE
			SYNTAX Unsigned32
			MAX-ACCESS read-only
			STATUS current
			DESCRIPTION
				"PM_IF1MINSTAT_TIMESTAMP"
			::= { pmIf1mStatEntry 2 }

		
		pmIf1mStatBinFlag OBJECT-TYPE
			SYNTAX INTEGER
				{
				invalid(0),
				valid(1),
				partial(2)
				}
			MAX-ACCESS read-only
			STATUS current
			DESCRIPTION
				"PM_IF1MINSTAT_BINFLAG"
			::= { pmIf1mStatEntry 3 }

		
		pmIf1mStatTx5mPps OBJECT-TYPE
			SYNTAX Counter64
			MAX-ACCESS read-only
			STATUS current
			DESCRIPTION
				"PM_IF1MINSTAT_TX5MINPPS"
			::= { pmIf1mStatEntry 4 }

		
		pmIf1mStatTx5mBps OBJECT-TYPE
			SYNTAX Counter64
			MAX-ACCESS read-only
			STATUS current
			DESCRIPTION
				"PM_IF1MINSTAT_TX5MINBPS"
			::= { pmIf1mStatEntry 5 }

		
		pmIf1mStatRx5mPps OBJECT-TYPE
			SYNTAX Counter64
			MAX-ACCESS read-only
			STATUS current
			DESCRIPTION
				"PM_IF1MINSTAT_RX5MINPPS"
			::= { pmIf1mStatEntry 6 }

		
		pmIf1mStatRx5mBps OBJECT-TYPE
			SYNTAX Counter64
			MAX-ACCESS read-only
			STATUS current
			DESCRIPTION
				"PM_IF1MINSTAT_RX5MINBPS"
			::= { pmIf1mStatEntry 7 }

		
		pmIf1mStatTxBytes OBJECT-TYPE
			SYNTAX Counter64
			MAX-ACCESS read-only
			STATUS current
			DESCRIPTION
				"PM_IF1MINSTAT_TXBYTES"
			::= { pmIf1mStatEntry 8 }

		
		pmIf1mStatRxBytes OBJECT-TYPE
			SYNTAX Counter64
			MAX-ACCESS read-only
			STATUS current
			DESCRIPTION
				"PM_IF1MINSTAT_RXBYTES"
			::= { pmIf1mStatEntry 9 }

		
		pmIf1mStatJunbo OBJECT-TYPE
			SYNTAX Counter64
			MAX-ACCESS read-only
			STATUS current
			DESCRIPTION
				"PM_IF1MINSTAT_JUNBO"
			::= { pmIf1mStatEntry 10 }

		
		pmIf1mStatFcsErrs OBJECT-TYPE
			SYNTAX Counter64
			MAX-ACCESS read-only
			STATUS current
			DESCRIPTION
				"PM_IF1MINSTAT_FCSERRS"
			::= { pmIf1mStatEntry 11 }

		
		pmIf1mStatCollisions OBJECT-TYPE
			SYNTAX Counter64
			MAX-ACCESS read-only
			STATUS current
			DESCRIPTION
				"PM_IF1MINSTAT_COLLISIONS"
			::= { pmIf1mStatEntry 12 }

		
		pmIf1mStatDropEvts OBJECT-TYPE
			SYNTAX Counter64
			MAX-ACCESS read-only
			STATUS current
			DESCRIPTION
				"PM_IF1MINSTAT_DROPEVTS"
			::= { pmIf1mStatEntry 13 }

		
		pmIf1mStatUndersize OBJECT-TYPE
			SYNTAX Counter64
			MAX-ACCESS read-only
			STATUS current
			DESCRIPTION
				"PM_IF1MINSTAT_UNDERSIZE"
			::= { pmIf1mStatEntry 14 }

		
		pmIf1mStatFragments OBJECT-TYPE
			SYNTAX Counter64
			MAX-ACCESS read-only
			STATUS current
			DESCRIPTION
				"PM_IF1MINSTAT_FRAGMENTS"
			::= { pmIf1mStatEntry 15 }

		
		pmIf1mStatTxPkts OBJECT-TYPE
			SYNTAX Counter64
			MAX-ACCESS read-only
			STATUS current
			DESCRIPTION
				"PM_IF1MINSTAT_TXPKTS"
			::= { pmIf1mStatEntry 16 }

		
		pmIf1mStatTxPause OBJECT-TYPE
			SYNTAX Counter64
			MAX-ACCESS read-only
			STATUS current
			DESCRIPTION
				"PM_IF1MINSTAT_TXPAUSE"
			::= { pmIf1mStatEntry 17 }

		
		pmIf1mStatTxUnicast OBJECT-TYPE
			SYNTAX Counter64
			MAX-ACCESS read-only
			STATUS current
			DESCRIPTION
				"PM_IF1MINSTAT_TXUNICAST"
			::= { pmIf1mStatEntry 18 }

		
		pmIf1mStatTxMulticast OBJECT-TYPE
			SYNTAX Counter64
			MAX-ACCESS read-only
			STATUS current
			DESCRIPTION
				"PM_IF1MINSTAT_TXMULTICAST"
			::= { pmIf1mStatEntry 19 }

		
		pmIf1mStatTxBroadcast OBJECT-TYPE
			SYNTAX Counter64
			MAX-ACCESS read-only
			STATUS current
			DESCRIPTION
				"PM_IF1MINSTAT_TXBROADCAST"
			::= { pmIf1mStatEntry 20 }

		
		pmIf1mStatRxPkts OBJECT-TYPE
			SYNTAX Counter64
			MAX-ACCESS read-only
			STATUS current
			DESCRIPTION
				"PM_IF1MINSTAT_RXPKTS"
			::= { pmIf1mStatEntry 21 }

		
		pmIf1mStatRxPause OBJECT-TYPE
			SYNTAX Counter64
			MAX-ACCESS read-only
			STATUS current
			DESCRIPTION
				"PM_IF1MINSTAT_RXPAUSE"
			::= { pmIf1mStatEntry 22 }

		
		pmIf1mStatRxUnicast OBJECT-TYPE
			SYNTAX Counter64
			MAX-ACCESS read-only
			STATUS current
			DESCRIPTION
				"PM_IF1MINSTAT_RXUNICAST"
			::= { pmIf1mStatEntry 23 }

		
		pmIf1mStatRxMulticast OBJECT-TYPE
			SYNTAX Counter64
			MAX-ACCESS read-only
			STATUS current
			DESCRIPTION
				"PM_IF1MINSTAT_RXMULTICAST"
			::= { pmIf1mStatEntry 24 }

		
		pmIf1mStatRxBroadcast OBJECT-TYPE
			SYNTAX Counter64
			MAX-ACCESS read-only
			STATUS current
			DESCRIPTION
				"PM_IF1MINSTAT_RXBROADCAST"
			::= { pmIf1mStatEntry 25 }

		
		pmIf1mStatDurPrdOperState OBJECT-TYPE
			SYNTAX INTEGER
			MAX-ACCESS read-only
			STATUS current
			DESCRIPTION
				"PM_IF1MINSTAT_DURPRDOPERSTATE"
			::= { pmIf1mStatEntry 26 }

		
		pmIf1mStatEndPrdOperState OBJECT-TYPE
			SYNTAX INTEGER
			MAX-ACCESS read-only
			STATUS current
			DESCRIPTION
				"PM_IF1MINSTAT_ENDPRDOPERSTATE"
			::= { pmIf1mStatEntry 27 }

		
		pmIf1mStatDurPrdAdminState OBJECT-TYPE
			SYNTAX INTEGER
			MAX-ACCESS read-only
			STATUS current
			DESCRIPTION
				"PM_IF1MINSTAT_DURPRDADMINSTATE"
			::= { pmIf1mStatEntry 28 }

		
		pmIf1mStatEndPrdAdminState OBJECT-TYPE
			SYNTAX INTEGER
			MAX-ACCESS read-only
			STATUS current
			DESCRIPTION
				"PM_IF1MINSTAT_ENDPRDADMINSTATE"
			::= { pmIf1mStatEntry 29 }

		
		pmIf1mStatOversize OBJECT-TYPE
			SYNTAX Counter64
			MAX-ACCESS read-only
			STATUS current
			DESCRIPTION
				"PM_IF1MINSTAT_OVERSIZE"
			::= { pmIf1mStatEntry 30 }

		
		pmIf5mStatTable OBJECT-TYPE
			SYNTAX SEQUENCE OF PmIf5mStatEntry
			MAX-ACCESS not-accessible
			STATUS current
			DESCRIPTION
				"Description."
			::= { pmIfPeriod 3 }

		
		pmIf5mStatEntry OBJECT-TYPE
			SYNTAX PmIf5mStatEntry
			MAX-ACCESS not-accessible
			STATUS current
			DESCRIPTION
				"Description."
			INDEX { pmIf5mStatIfUnit, pmIf5mStatTimeStamp }
			::= { pmIf5mStatTable 1 }

		
		PmIf5mStatEntry ::=
			SEQUENCE { 
				pmIf5mStatIfUnit
					INTEGER,
				pmIf5mStatTimeStamp
					Unsigned32,
				pmIf5mStatBinFlag
					INTEGER,
				pmIf5mStatTx5mPps
					Counter64,
				pmIf5mStatTx5mBps
					Counter64,
				pmIf5mStatRx5mPps
					Counter64,
				pmIf5mStatRx5mBps
					Counter64,
				pmIf5mStatTxBytes
					Counter64,
				pmIf5mStatRxBytes
					Counter64,
				pmIf5mStatJunbo
					Counter64,
				pmIf5mStatFcsErrs
					Counter64,
				pmIf5mStatCollisions
					Counter64,
				pmIf5mStatDropEvts
					Counter64,
				pmIf5mStatUndersize
					Counter64,
				pmIf5mStatFragments
					Counter64,
				pmIf5mStatTxPkts
					Counter64,
				pmIf5mStatTxPause
					Counter64,
				pmIf5mStatTxUnicast
					Counter64,
				pmIf5mStatTxMulticast
					Counter64,
				pmIf5mStatTxBroadcast
					Counter64,
				pmIf5mStatRxPkts
					Counter64,
				pmIf5mStatRxPause
					Counter64,
				pmIf5mStatRxUnicast
					Counter64,
				pmIf5mStatRxMulticast
					Counter64,
				pmIf5mStatRxBroadcast
					Counter64,
				pmIf5mStatDurPrdOperState
					INTEGER,
				pmIf5mStatEndPrdOperState
					INTEGER,
				pmIf5mStatDurPrdAdminState
					INTEGER,
				pmIf5mStatEndPrdAdminState
					INTEGER,
				pmIf5mStatOversize
					Counter64
			 }

		pmIf5mStatIfUnit OBJECT-TYPE
			SYNTAX INTEGER (1..2147483647)
			MAX-ACCESS read-only
			STATUS current
			DESCRIPTION
				"Description."
			::= { pmIf5mStatEntry 1 }

		
		pmIf5mStatTimeStamp OBJECT-TYPE
			SYNTAX Unsigned32
			MAX-ACCESS read-only
			STATUS current
			DESCRIPTION
				"PM_IF5MINSTAT_TIMESTAMP"
			::= { pmIf5mStatEntry 2 }

		
		pmIf5mStatBinFlag OBJECT-TYPE
			SYNTAX INTEGER
				{
				invalid(0),
				valid(1),
				partial(2)
				}
			MAX-ACCESS read-only
			STATUS current
			DESCRIPTION
				"PM_IF5MINSTAT_BINFLAG"
			::= { pmIf5mStatEntry 3 }

		
		pmIf5mStatTx5mPps OBJECT-TYPE
			SYNTAX Counter64
			MAX-ACCESS read-only
			STATUS current
			DESCRIPTION
				"PM_IF5MINSTAT_TX5MINPPS"
			::= { pmIf5mStatEntry 4 }

		
		pmIf5mStatTx5mBps OBJECT-TYPE
			SYNTAX Counter64
			MAX-ACCESS read-only
			STATUS current
			DESCRIPTION
				"PM_IF5MINSTAT_TX5MINBPS"
			::= { pmIf5mStatEntry 5 }

		
		pmIf5mStatRx5mPps OBJECT-TYPE
			SYNTAX Counter64
			MAX-ACCESS read-only
			STATUS current
			DESCRIPTION
				"PM_IF5MINSTAT_RX5MINPPS"
			::= { pmIf5mStatEntry 6 }

		
		pmIf5mStatRx5mBps OBJECT-TYPE
			SYNTAX Counter64
			MAX-ACCESS read-only
			STATUS current
			DESCRIPTION
				"PM_IF5MINSTAT_RX5MINBPS"
			::= { pmIf5mStatEntry 7 }

		
		pmIf5mStatTxBytes OBJECT-TYPE
			SYNTAX Counter64
			MAX-ACCESS read-only
			STATUS current
			DESCRIPTION
				"PM_IF5MINSTAT_TXBYTES"
			::= { pmIf5mStatEntry 8 }

		
		pmIf5mStatRxBytes OBJECT-TYPE
			SYNTAX Counter64
			MAX-ACCESS read-only
			STATUS current
			DESCRIPTION
				"PM_IF5MINSTAT_RXBYTES"
			::= { pmIf5mStatEntry 9 }

		
		pmIf5mStatJunbo OBJECT-TYPE
			SYNTAX Counter64
			MAX-ACCESS read-only
			STATUS current
			DESCRIPTION
				"PM_IF5MINSTAT_JUNBO"
			::= { pmIf5mStatEntry 10 }

		
		pmIf5mStatFcsErrs OBJECT-TYPE
			SYNTAX Counter64
			MAX-ACCESS read-only
			STATUS current
			DESCRIPTION
				"PM_IF5MINSTAT_FCSERRS"
			::= { pmIf5mStatEntry 11 }

		
		pmIf5mStatCollisions OBJECT-TYPE
			SYNTAX Counter64
			MAX-ACCESS read-only
			STATUS current
			DESCRIPTION
				"PM_IF5MINSTAT_COLLISIONS"
			::= { pmIf5mStatEntry 12 }

		
		pmIf5mStatDropEvts OBJECT-TYPE
			SYNTAX Counter64
			MAX-ACCESS read-only
			STATUS current
			DESCRIPTION
				"PM_IF5MINSTAT_DROPEVTS"
			::= { pmIf5mStatEntry 13 }

		
		pmIf5mStatUndersize OBJECT-TYPE
			SYNTAX Counter64
			MAX-ACCESS read-only
			STATUS current
			DESCRIPTION
				"PM_IF5MINSTAT_UNDERSIZE"
			::= { pmIf5mStatEntry 14 }

		
		pmIf5mStatFragments OBJECT-TYPE
			SYNTAX Counter64
			MAX-ACCESS read-only
			STATUS current
			DESCRIPTION
				"PM_IF5MINSTAT_FRAGMENTS"
			::= { pmIf5mStatEntry 15 }

		
		pmIf5mStatTxPkts OBJECT-TYPE
			SYNTAX Counter64
			MAX-ACCESS read-only
			STATUS current
			DESCRIPTION
				"PM_IF5MINSTAT_TXPKTS"
			::= { pmIf5mStatEntry 16 }

		
		pmIf5mStatTxPause OBJECT-TYPE
			SYNTAX Counter64
			MAX-ACCESS read-only
			STATUS current
			DESCRIPTION
				"PM_IF5MINSTAT_TXPAUSE"
			::= { pmIf5mStatEntry 17 }

		
		pmIf5mStatTxUnicast OBJECT-TYPE
			SYNTAX Counter64
			MAX-ACCESS read-only
			STATUS current
			DESCRIPTION
				"PM_IF5MINSTAT_TXUNICAST"
			::= { pmIf5mStatEntry 18 }

		
		pmIf5mStatTxMulticast OBJECT-TYPE
			SYNTAX Counter64
			MAX-ACCESS read-only
			STATUS current
			DESCRIPTION
				"PM_IF5MINSTAT_TXMULTICAST"
			::= { pmIf5mStatEntry 19 }

		
		pmIf5mStatTxBroadcast OBJECT-TYPE
			SYNTAX Counter64
			MAX-ACCESS read-only
			STATUS current
			DESCRIPTION
				"PM_IF5MINSTAT_TXBROADCAST"
			::= { pmIf5mStatEntry 20 }

		
		pmIf5mStatRxPkts OBJECT-TYPE
			SYNTAX Counter64
			MAX-ACCESS read-only
			STATUS current
			DESCRIPTION
				"PM_IF5MINSTAT_RXPKTS"
			::= { pmIf5mStatEntry 21 }

		
		pmIf5mStatRxPause OBJECT-TYPE
			SYNTAX Counter64
			MAX-ACCESS read-only
			STATUS current
			DESCRIPTION
				"PM_IF5MINSTAT_RXPAUSE"
			::= { pmIf5mStatEntry 22 }

		
		pmIf5mStatRxUnicast OBJECT-TYPE
			SYNTAX Counter64
			MAX-ACCESS read-only
			STATUS current
			DESCRIPTION
				"PM_IF5MINSTAT_RXUNICAST"
			::= { pmIf5mStatEntry 23 }

		
		pmIf5mStatRxMulticast OBJECT-TYPE
			SYNTAX Counter64
			MAX-ACCESS read-only
			STATUS current
			DESCRIPTION
				"PM_IF5MINSTAT_RXMULTICAST"
			::= { pmIf5mStatEntry 24 }

		
		pmIf5mStatRxBroadcast OBJECT-TYPE
			SYNTAX Counter64
			MAX-ACCESS read-only
			STATUS current
			DESCRIPTION
				"PM_IF5MINSTAT_RXBROADCAST"
			::= { pmIf5mStatEntry 25 }

		
		pmIf5mStatDurPrdOperState OBJECT-TYPE
			SYNTAX INTEGER
			MAX-ACCESS read-only
			STATUS current
			DESCRIPTION
				"PM_IF5MINSTAT_DURPRDOPERSTATE"
			::= { pmIf5mStatEntry 26 }

		
		pmIf5mStatEndPrdOperState OBJECT-TYPE
			SYNTAX INTEGER
			MAX-ACCESS read-only
			STATUS current
			DESCRIPTION
				"PM_IF5MINSTAT_ENDPRDOPERSTATE"
			::= { pmIf5mStatEntry 27 }

		
		pmIf5mStatDurPrdAdminState OBJECT-TYPE
			SYNTAX INTEGER
			MAX-ACCESS read-only
			STATUS current
			DESCRIPTION
				"PM_IF5MINSTAT_DURPRDADMINSTATE"
			::= { pmIf5mStatEntry 28 }

		
		pmIf5mStatEndPrdAdminState OBJECT-TYPE
			SYNTAX INTEGER
			MAX-ACCESS read-only
			STATUS current
			DESCRIPTION
				"PM_IF5MINSTAT_ENDPRDADMINSTATE"
			::= { pmIf5mStatEntry 29 }

		
		pmIf5mStatOversize OBJECT-TYPE
			SYNTAX Counter64
			MAX-ACCESS read-only
			STATUS current
			DESCRIPTION
				"PM_IF5MINSTAT_OVERSIZE"
			::= { pmIf5mStatEntry 30 }

		
		pmIf15mStatTable OBJECT-TYPE
			SYNTAX SEQUENCE OF PmIf15mStatEntry
			MAX-ACCESS not-accessible
			STATUS current
			DESCRIPTION
				"Description."
			::= { pmIfPeriod 4 }

		
		pmIf15mStatEntry OBJECT-TYPE
			SYNTAX PmIf15mStatEntry
			MAX-ACCESS not-accessible
			STATUS current
			DESCRIPTION
				"Description."
			INDEX { pmIf15mStatIfUnit, pmIf15mStatTimeStamp }
			::= { pmIf15mStatTable 1 }

		
		PmIf15mStatEntry ::=
			SEQUENCE { 
				pmIf15mStatIfUnit
					INTEGER,
				pmIf15mStatTimeStamp
					Unsigned32,
				pmIf15mStatBinFlag
					INTEGER,
				pmIf15mStatTx5mPps
					Counter64,
				pmIf15mStatTx5mBps
					Counter64,
				pmIf15mStatRx5mPps
					Counter64,
				pmIf15mStatRx5mBps
					Counter64,
				pmIf15mStatTxBytes
					Counter64,
				pmIf15mStatRxBytes
					Counter64,
				pmIf15mStatJunbo
					Counter64,
				pmIf15mStatFcsErrs
					Counter64,
				pmIf15mStatCollisions
					Counter64,
				pmIf15mStatDropEvts
					Counter64,
				pmIf15mStatUndersize
					Counter64,
				pmIf15mStatFragments
					Counter64,
				pmIf15mStatTxPkts
					Counter64,
				pmIf15mStatTxPause
					Counter64,
				pmIf15mStatTxUnicast
					Counter64,
				pmIf15mStatTxMulticast
					Counter64,
				pmIf15mStatTxBroadcast
					Counter64,
				pmIf15mStatRxPkts
					Counter64,
				pmIf15mStatRxPause
					Counter64,
				pmIf15mStatRxUnicast
					Counter64,
				pmIf15mStatRxMulticast
					Counter64,
				pmIf15mStatRxBroadcast
					Counter64,
				pmIf15mStatDurPrdOperState
					INTEGER,
				pmIf15mStatEndPrdOperState
					INTEGER,
				pmIf15mStatDurPrdAdminState
					INTEGER,
				pmIf15mStatEndPrdAdminState
					INTEGER,
				pmIf15mStatOversize
					Counter64
			 }

		pmIf15mStatIfUnit OBJECT-TYPE
			SYNTAX INTEGER (1..2147483647)
			MAX-ACCESS read-only
			STATUS current
			DESCRIPTION
				"Description."
			::= { pmIf15mStatEntry 1 }

		
		pmIf15mStatTimeStamp OBJECT-TYPE
			SYNTAX Unsigned32
			MAX-ACCESS read-only
			STATUS current
			DESCRIPTION
				"PM_IF15MINSTAT_TIMESTAMP"
			::= { pmIf15mStatEntry 2 }

		
		pmIf15mStatBinFlag OBJECT-TYPE
			SYNTAX INTEGER
				{
				invalid(0),
				valid(1),
				partial(2)
				}
			MAX-ACCESS read-only
			STATUS current
			DESCRIPTION
				"PM_IF15MINSTAT_BINFLAG"
			::= { pmIf15mStatEntry 3 }

		
		pmIf15mStatTx5mPps OBJECT-TYPE
			SYNTAX Counter64
			MAX-ACCESS read-only
			STATUS current
			DESCRIPTION
				"PM_IF15MINSTAT_TX5MINPPS"
			::= { pmIf15mStatEntry 4 }

		
		pmIf15mStatTx5mBps OBJECT-TYPE
			SYNTAX Counter64
			MAX-ACCESS read-only
			STATUS current
			DESCRIPTION
				"PM_IF15MINSTAT_TX5MINBPS"
			::= { pmIf15mStatEntry 5 }

		
		pmIf15mStatRx5mPps OBJECT-TYPE
			SYNTAX Counter64
			MAX-ACCESS read-only
			STATUS current
			DESCRIPTION
				"PM_IF15MINSTAT_RX5MINPPS"
			::= { pmIf15mStatEntry 6 }

		
		pmIf15mStatRx5mBps OBJECT-TYPE
			SYNTAX Counter64
			MAX-ACCESS read-only
			STATUS current
			DESCRIPTION
				"PM_IF15MINSTAT_RX5MINBPS"
			::= { pmIf15mStatEntry 7 }

		
		pmIf15mStatTxBytes OBJECT-TYPE
			SYNTAX Counter64
			MAX-ACCESS read-only
			STATUS current
			DESCRIPTION
				"PM_IF15MINSTAT_TXBYTES"
			::= { pmIf15mStatEntry 8 }

		
		pmIf15mStatRxBytes OBJECT-TYPE
			SYNTAX Counter64
			MAX-ACCESS read-only
			STATUS current
			DESCRIPTION
				"PM_IF15MINSTAT_RXBYTES"
			::= { pmIf15mStatEntry 9 }

		
		pmIf15mStatJunbo OBJECT-TYPE
			SYNTAX Counter64
			MAX-ACCESS read-only
			STATUS current
			DESCRIPTION
				"PM_IF15MINSTAT_JUNBO"
			::= { pmIf15mStatEntry 10 }

		
		pmIf15mStatFcsErrs OBJECT-TYPE
			SYNTAX Counter64
			MAX-ACCESS read-only
			STATUS current
			DESCRIPTION
				"PM_IF15MINSTAT_FCSERRS"
			::= { pmIf15mStatEntry 11 }

		
		pmIf15mStatCollisions OBJECT-TYPE
			SYNTAX Counter64
			MAX-ACCESS read-only
			STATUS current
			DESCRIPTION
				"PM_IF15MINSTAT_COLLISIONS"
			::= { pmIf15mStatEntry 12 }

		
		pmIf15mStatDropEvts OBJECT-TYPE
			SYNTAX Counter64
			MAX-ACCESS read-only
			STATUS current
			DESCRIPTION
				"PM_IF15MINSTAT_DROPEVTS"
			::= { pmIf15mStatEntry 13 }

		
		pmIf15mStatUndersize OBJECT-TYPE
			SYNTAX Counter64
			MAX-ACCESS read-only
			STATUS current
			DESCRIPTION
				"PM_IF15MINSTAT_UNDERSIZE"
			::= { pmIf15mStatEntry 14 }

		
		pmIf15mStatFragments OBJECT-TYPE
			SYNTAX Counter64
			MAX-ACCESS read-only
			STATUS current
			DESCRIPTION
				"PM_IF15MINSTAT_FRAGMENTS"
			::= { pmIf15mStatEntry 15 }

		
		pmIf15mStatTxPkts OBJECT-TYPE
			SYNTAX Counter64
			MAX-ACCESS read-only
			STATUS current
			DESCRIPTION
				"PM_IF15MINSTAT_TXPKTS"
			::= { pmIf15mStatEntry 16 }

		
		pmIf15mStatTxPause OBJECT-TYPE
			SYNTAX Counter64
			MAX-ACCESS read-only
			STATUS current
			DESCRIPTION
				"PM_IF15MINSTAT_TXPAUSE"
			::= { pmIf15mStatEntry 17 }

		
		pmIf15mStatTxUnicast OBJECT-TYPE
			SYNTAX Counter64
			MAX-ACCESS read-only
			STATUS current
			DESCRIPTION
				"PM_IF15MINSTAT_TXUNICAST"
			::= { pmIf15mStatEntry 18 }

		
		pmIf15mStatTxMulticast OBJECT-TYPE
			SYNTAX Counter64
			MAX-ACCESS read-only
			STATUS current
			DESCRIPTION
				"PM_IF15MINSTAT_TXMULTICAST"
			::= { pmIf15mStatEntry 19 }

		
		pmIf15mStatTxBroadcast OBJECT-TYPE
			SYNTAX Counter64
			MAX-ACCESS read-only
			STATUS current
			DESCRIPTION
				"PM_IF15MINSTAT_TXBROADCAST"
			::= { pmIf15mStatEntry 20 }

		
		pmIf15mStatRxPkts OBJECT-TYPE
			SYNTAX Counter64
			MAX-ACCESS read-only
			STATUS current
			DESCRIPTION
				"PM_IF15MINSTAT_RXPKTS"
			::= { pmIf15mStatEntry 21 }

		
		pmIf15mStatRxPause OBJECT-TYPE
			SYNTAX Counter64
			MAX-ACCESS read-only
			STATUS current
			DESCRIPTION
				"PM_IF15MINSTAT_RXPAUSE"
			::= { pmIf15mStatEntry 22 }

		
		pmIf15mStatRxUnicast OBJECT-TYPE
			SYNTAX Counter64
			MAX-ACCESS read-only
			STATUS current
			DESCRIPTION
				"PM_IF15MINSTAT_RXUNICAST"
			::= { pmIf15mStatEntry 23 }

		
		pmIf15mStatRxMulticast OBJECT-TYPE
			SYNTAX Counter64
			MAX-ACCESS read-only
			STATUS current
			DESCRIPTION
				"PM_IF15MINSTAT_RXMULTICAST"
			::= { pmIf15mStatEntry 24 }

		
		pmIf15mStatRxBroadcast OBJECT-TYPE
			SYNTAX Counter64
			MAX-ACCESS read-only
			STATUS current
			DESCRIPTION
				"PM_IF15MINSTAT_RXBROADCAST"
			::= { pmIf15mStatEntry 25 }

		
		pmIf15mStatDurPrdOperState OBJECT-TYPE
			SYNTAX INTEGER
			MAX-ACCESS read-only
			STATUS current
			DESCRIPTION
				"PM_IF15MINSTAT_DURPRDOPERSTATE"
			::= { pmIf15mStatEntry 26 }

		
		pmIf15mStatEndPrdOperState OBJECT-TYPE
			SYNTAX INTEGER
			MAX-ACCESS read-only
			STATUS current
			DESCRIPTION
				"PM_IF15MINSTAT_ENDPRDOPERSTATE"
			::= { pmIf15mStatEntry 27 }

		
		pmIf15mStatDurPrdAdminState OBJECT-TYPE
			SYNTAX INTEGER
			MAX-ACCESS read-only
			STATUS current
			DESCRIPTION
				"PM_IF15MINSTAT_DURPRDADMINSTATE"
			::= { pmIf15mStatEntry 28 }

		
		pmIf15mStatEndPrdAdminState OBJECT-TYPE
			SYNTAX INTEGER
			MAX-ACCESS read-only
			STATUS current
			DESCRIPTION
				"PM_IF15MINSTAT_ENDPRDADMINSTATE"
			::= { pmIf15mStatEntry 29 }

		
		pmIf15mStatOversize OBJECT-TYPE
			SYNTAX Counter64
			MAX-ACCESS read-only
			STATUS current
			DESCRIPTION
				"PM_IF15MINSTAT_OVERSIZE"
			::= { pmIf15mStatEntry 30 }

		
		pmIf24hStatTable OBJECT-TYPE
			SYNTAX SEQUENCE OF PmIf24hStatEntry
			MAX-ACCESS not-accessible
			STATUS current
			DESCRIPTION
				"Description."
			::= { pmIfPeriod 5 }

		
		pmIf24hStatEntry OBJECT-TYPE
			SYNTAX PmIf24hStatEntry
			MAX-ACCESS not-accessible
			STATUS current
			DESCRIPTION
				"Description."
			INDEX { pmIf24hStatIfUnit, pmIf24hStatTimeStamp }
			::= { pmIf24hStatTable 1 }

		
		PmIf24hStatEntry ::=
			SEQUENCE { 
				pmIf24hStatIfUnit
					INTEGER,
				pmIf24hStatTimeStamp
					Unsigned32,
				pmIf24hStatBinFlag
					INTEGER,
				pmIf24hStatTx5mPps
					Counter64,
				pmIf24hStatTx5mBps
					Counter64,
				pmIf24hStatRx5mPps
					Counter64,
				pmIf24hStatRx5mBps
					Counter64,
				pmIf24hStatTxBytes
					Counter64,
				pmIf24hStatRxBytes
					Counter64,
				pmIf24hStatJunbo
					Counter64,
				pmIf24hStatFcsErrs
					Counter64,
				pmIf24hStatCollisions
					Counter64,
				pmIf24hStatDropEvts
					Counter64,
				pmIf24hStatUndersize
					Counter64,
				pmIf24hStatFragments
					Counter64,
				pmIf24hStatTxPkts
					Counter64,
				pmIf24hStatTxPause
					Counter64,
				pmIf24hStatTxUnicast
					Counter64,
				pmIf24hStatTxMulticast
					Counter64,
				pmIf24hStatTxBroadcast
					Counter64,
				pmIf24hStatRxPkts
					Counter64,
				pmIf24hStatRxPause
					Counter64,
				pmIf24hStatRxUnicast
					Counter64,
				pmIf24hStatRxMulticast
					Counter64,
				pmIf24hStatRxBroadcast
					Counter64,
				pmIf24hStatDurPrdOperState
					INTEGER,
				pmIf24hStatEndPrdOperState
					INTEGER,
				pmIf24hStatDurPrdAdminState
					INTEGER,
				pmIf24hStatEndPrdAdminState
					INTEGER,
				pmIf24hStatOversize
					Counter64
			 }

		pmIf24hStatIfUnit OBJECT-TYPE
			SYNTAX INTEGER (1..2147483647)
			MAX-ACCESS read-only
			STATUS current
			DESCRIPTION
				"Description."
			::= { pmIf24hStatEntry 1 }

		
		pmIf24hStatTimeStamp OBJECT-TYPE
			SYNTAX Unsigned32
			MAX-ACCESS read-only
			STATUS current
			DESCRIPTION
				"PM_IF24HOURSTAT_TIMESTAMP"
			::= { pmIf24hStatEntry 2 }

		
		pmIf24hStatBinFlag OBJECT-TYPE
			SYNTAX INTEGER
				{
				invalid(0),
				valid(1),
				partial(2)
				}
			MAX-ACCESS read-only
			STATUS current
			DESCRIPTION
				"PM_IF24HOURSTAT_BINFLAG"
			::= { pmIf24hStatEntry 3 }

		
		pmIf24hStatTx5mPps OBJECT-TYPE
			SYNTAX Counter64
			MAX-ACCESS read-only
			STATUS current
			DESCRIPTION
				"PM_IF24HOURSTAT_TX5MINPPS"
			::= { pmIf24hStatEntry 4 }

		
		pmIf24hStatTx5mBps OBJECT-TYPE
			SYNTAX Counter64
			MAX-ACCESS read-only
			STATUS current
			DESCRIPTION
				"PM_IF24HOURSTAT_TX5MINBPS"
			::= { pmIf24hStatEntry 5 }

		
		pmIf24hStatRx5mPps OBJECT-TYPE
			SYNTAX Counter64
			MAX-ACCESS read-only
			STATUS current
			DESCRIPTION
				"PM_IF24HOURSTAT_RX5MINPPS"
			::= { pmIf24hStatEntry 6 }

		
		pmIf24hStatRx5mBps OBJECT-TYPE
			SYNTAX Counter64
			MAX-ACCESS read-only
			STATUS current
			DESCRIPTION
				"PM_IF24HOURSTAT_RX5MINBPS"
			::= { pmIf24hStatEntry 7 }

		
		pmIf24hStatTxBytes OBJECT-TYPE
			SYNTAX Counter64
			MAX-ACCESS read-only
			STATUS current
			DESCRIPTION
				"PM_IF24HOURSTAT_TXBYTES"
			::= { pmIf24hStatEntry 8 }

		
		pmIf24hStatRxBytes OBJECT-TYPE
			SYNTAX Counter64
			MAX-ACCESS read-only
			STATUS current
			DESCRIPTION
				"PM_IF24HOURSTAT_RXBYTES"
			::= { pmIf24hStatEntry 9 }

		
		pmIf24hStatJunbo OBJECT-TYPE
			SYNTAX Counter64
			MAX-ACCESS read-only
			STATUS current
			DESCRIPTION
				"PM_IF24HOURSTAT_JUNBO"
			::= { pmIf24hStatEntry 10 }

		
		pmIf24hStatFcsErrs OBJECT-TYPE
			SYNTAX Counter64
			MAX-ACCESS read-only
			STATUS current
			DESCRIPTION
				"PM_IF24HOURSTAT_FCSERRS"
			::= { pmIf24hStatEntry 11 }

		
		pmIf24hStatCollisions OBJECT-TYPE
			SYNTAX Counter64
			MAX-ACCESS read-only
			STATUS current
			DESCRIPTION
				"PM_IF24HOURSTAT_COLLISIONS"
			::= { pmIf24hStatEntry 12 }

		
		pmIf24hStatDropEvts OBJECT-TYPE
			SYNTAX Counter64
			MAX-ACCESS read-only
			STATUS current
			DESCRIPTION
				"PM_IF24HOURSTAT_DROPEVTS"
			::= { pmIf24hStatEntry 13 }

		
		pmIf24hStatUndersize OBJECT-TYPE
			SYNTAX Counter64
			MAX-ACCESS read-only
			STATUS current
			DESCRIPTION
				"PM_IF24HOURSTAT_UNDERSIZE"
			::= { pmIf24hStatEntry 14 }

		
		pmIf24hStatFragments OBJECT-TYPE
			SYNTAX Counter64
			MAX-ACCESS read-only
			STATUS current
			DESCRIPTION
				"PM_IF24HOURSTAT_FRAGMENTS"
			::= { pmIf24hStatEntry 15 }

		
		pmIf24hStatTxPkts OBJECT-TYPE
			SYNTAX Counter64
			MAX-ACCESS read-only
			STATUS current
			DESCRIPTION
				"PM_IF24HOURSTAT_TXPKTS"
			::= { pmIf24hStatEntry 16 }

		
		pmIf24hStatTxPause OBJECT-TYPE
			SYNTAX Counter64
			MAX-ACCESS read-only
			STATUS current
			DESCRIPTION
				"PM_IF24HOURSTAT_TXPAUSE"
			::= { pmIf24hStatEntry 17 }

		
		pmIf24hStatTxUnicast OBJECT-TYPE
			SYNTAX Counter64
			MAX-ACCESS read-only
			STATUS current
			DESCRIPTION
				"PM_IF24HOURSTAT_TXUNICAST"
			::= { pmIf24hStatEntry 18 }

		
		pmIf24hStatTxMulticast OBJECT-TYPE
			SYNTAX Counter64
			MAX-ACCESS read-only
			STATUS current
			DESCRIPTION
				"PM_IF24HOURSTAT_TXMULTICAST"
			::= { pmIf24hStatEntry 19 }

		
		pmIf24hStatTxBroadcast OBJECT-TYPE
			SYNTAX Counter64
			MAX-ACCESS read-only
			STATUS current
			DESCRIPTION
				"PM_IF24HOURSTAT_TXBROADCAST"
			::= { pmIf24hStatEntry 20 }

		
		pmIf24hStatRxPkts OBJECT-TYPE
			SYNTAX Counter64
			MAX-ACCESS read-only
			STATUS current
			DESCRIPTION
				"PM_IF24HOURSTAT_RXPKTS"
			::= { pmIf24hStatEntry 21 }

		
		pmIf24hStatRxPause OBJECT-TYPE
			SYNTAX Counter64
			MAX-ACCESS read-only
			STATUS current
			DESCRIPTION
				"PM_IF24HOURSTAT_RXPAUSE"
			::= { pmIf24hStatEntry 22 }

		
		pmIf24hStatRxUnicast OBJECT-TYPE
			SYNTAX Counter64
			MAX-ACCESS read-only
			STATUS current
			DESCRIPTION
				"PM_IF24HOURSTAT_RXUNICAST"
			::= { pmIf24hStatEntry 23 }

		
		pmIf24hStatRxMulticast OBJECT-TYPE
			SYNTAX Counter64
			MAX-ACCESS read-only
			STATUS current
			DESCRIPTION
				"PM_IF24HOURSTAT_RXMULTICAST"
			::= { pmIf24hStatEntry 24 }

		
		pmIf24hStatRxBroadcast OBJECT-TYPE
			SYNTAX Counter64
			MAX-ACCESS read-only
			STATUS current
			DESCRIPTION
				"PM_IF24HOURSTAT_RXBROADCAST"
			::= { pmIf24hStatEntry 25 }

		
		pmIf24hStatDurPrdOperState OBJECT-TYPE
			SYNTAX INTEGER
			MAX-ACCESS read-only
			STATUS current
			DESCRIPTION
				"PM_IF24HOURSTAT_DURPRDOPERSTATE"
			::= { pmIf24hStatEntry 26 }

		
		pmIf24hStatEndPrdOperState OBJECT-TYPE
			SYNTAX INTEGER
			MAX-ACCESS read-only
			STATUS current
			DESCRIPTION
				"PM_IF24HOURSTAT_ENDPRDOPERSTATE"
			::= { pmIf24hStatEntry 27 }

		
		pmIf24hStatDurPrdAdminState OBJECT-TYPE
			SYNTAX INTEGER
			MAX-ACCESS read-only
			STATUS current
			DESCRIPTION
				"PM_IF24HOURSTAT_DURPRDADMINSTATE"
			::= { pmIf24hStatEntry 28 }

		
		pmIf24hStatEndPrdAdminState OBJECT-TYPE
			SYNTAX INTEGER
			MAX-ACCESS read-only
			STATUS current
			DESCRIPTION
				"PM_IF24HOURSTAT_ENDPRDADMINSTATE"
			::= { pmIf24hStatEntry 29 }

		
		pmIf24hStatOversize OBJECT-TYPE
			SYNTAX Counter64
			MAX-ACCESS read-only
			STATUS current
			DESCRIPTION
				"PM_IF24HOURSTAT_OVERSIZE"
			::= { pmIf24hStatEntry 30 }

		                                      
		pmIfCurrentTable OBJECT-TYPE
			SYNTAX SEQUENCE OF PmIfCurrentEntry
			MAX-ACCESS not-accessible
			STATUS current
			DESCRIPTION
				"Description."
			::= { pmIfPeriod 6 }

		
		pmIfCurrentEntry OBJECT-TYPE
			SYNTAX PmIfCurrentEntry
			MAX-ACCESS not-accessible
			STATUS current
			DESCRIPTION
				"Description."
			INDEX { pmIfCurrentIfUnit }
			::= { pmIfCurrentTable 1 }

		
		PmIfCurrentEntry ::=
			SEQUENCE { 
				pmIfCurrentIfUnit
					INTEGER,
				pmIfCurrentStartTime
					Unsigned32,
				pmIfCurrentEndTime
					Unsigned32,					
				pmIfCurrentBinFlag
					INTEGER,
				pmIfCurrentTx5mPps
					Counter64,
				pmIfCurrentTx5mBps
					Counter64,
				pmIfCurrentRx5mPps
					Counter64,
				pmIfCurrentRx5mBps
					Counter64,
				pmIfCurrentTxBytes
					Counter64,
				pmIfCurrentRxBytes
					Counter64,
				pmIfCurrentJunbo
					Counter64,
				pmIfCurrentFcsErrs
					Counter64,
				pmIfCurrentCollisions
					Counter64,
				pmIfCurrentDropEvts
					Counter64,
				pmIfCurrentUndersize
					Counter64,
				pmIfCurrentFragments
					Counter64,
				pmIfCurrentTxPkts
					Counter64,
				pmIfCurrentTxPause
					Counter64,
				pmIfCurrentTxUnicast
					Counter64,
				pmIfCurrentTxMulticast
					Counter64,
				pmIfCurrentTxBroadcast
					Counter64,
				pmIfCurrentRxPkts
					Counter64,
				pmIfCurrentRxPause
					Counter64,
				pmIfCurrentRxUnicast
					Counter64,
				pmIfCurrentRxMulticast
					Counter64,
				pmIfCurrentRxBroadcast
					Counter64,
				pmIfCurrentDurPrdOperState
					INTEGER,
				pmIfCurrentEndPrdOperState
					INTEGER,
				pmIfCurrentDurPrdAdminState
					INTEGER,
				pmIfCurrentEndPrdAdminState
					INTEGER,
				pmIfCurrentOversize
					Counter64
			 }

		pmIfCurrentIfUnit OBJECT-TYPE
			SYNTAX INTEGER (1..2147483647)
			MAX-ACCESS read-only
			STATUS current
			DESCRIPTION
				"Description."
			::= { pmIfCurrentEntry 1 }

		
		pmIfCurrentStartTime OBJECT-TYPE
			SYNTAX Unsigned32
			MAX-ACCESS read-only
			STATUS current
			DESCRIPTION
				"PM_IFCURRENT_STARTTIME"
			::= { pmIfCurrentEntry 2 }


		pmIfCurrentEndTime OBJECT-TYPE
			SYNTAX Unsigned32
			MAX-ACCESS read-only
			STATUS current
			DESCRIPTION
				"PM_IFCURRENT_ENDTIME"
			::= { pmIfCurrentEntry 3 }

		
		pmIfCurrentBinFlag OBJECT-TYPE
			SYNTAX INTEGER
				{
				invalid(0),
				valid(1),
				partial(2)
				}
			MAX-ACCESS read-only
			STATUS current
			DESCRIPTION
				"PM_IFCURRENT_BINFLAG"
			::= { pmIfCurrentEntry 4 }

		
		pmIfCurrentTx5mPps OBJECT-TYPE
			SYNTAX Counter64
			MAX-ACCESS read-only
			STATUS current
			DESCRIPTION
				"PM_IFCURRENT_TX5MINPPS"
			::= { pmIfCurrentEntry 5 }

		
		pmIfCurrentTx5mBps OBJECT-TYPE
			SYNTAX Counter64
			MAX-ACCESS read-only
			STATUS current
			DESCRIPTION
				"PM_IFCURRENT_TX5MINBPS"
			::= { pmIfCurrentEntry 6 }

		
		pmIfCurrentRx5mPps OBJECT-TYPE
			SYNTAX Counter64
			MAX-ACCESS read-only
			STATUS current
			DESCRIPTION
				"PM_IFCURRENT_RX5MINPPS"
			::= { pmIfCurrentEntry 7 }

		
		pmIfCurrentRx5mBps OBJECT-TYPE
			SYNTAX Counter64
			MAX-ACCESS read-only
			STATUS current
			DESCRIPTION
				"PM_IFCURRENT_RX5MINBPS"
			::= { pmIfCurrentEntry 8 }

		
		pmIfCurrentTxBytes OBJECT-TYPE
			SYNTAX Counter64
			MAX-ACCESS read-only
			STATUS current
			DESCRIPTION
				"PM_IFCURRENT_TXBYTES"
			::= { pmIfCurrentEntry 9 }

		
		pmIfCurrentRxBytes OBJECT-TYPE
			SYNTAX Counter64
			MAX-ACCESS read-only
			STATUS current
			DESCRIPTION
				"PM_IFCURRENT_RXBYTES"
			::= { pmIfCurrentEntry 10 }

		
		pmIfCurrentJunbo OBJECT-TYPE
			SYNTAX Counter64
			MAX-ACCESS read-only
			STATUS current
			DESCRIPTION
				"PM_IFCURRENT_JUNBO"
			::= { pmIfCurrentEntry 11 }

		
		pmIfCurrentFcsErrs OBJECT-TYPE
			SYNTAX Counter64
			MAX-ACCESS read-only
			STATUS current
			DESCRIPTION
				"PM_IFCURRENT_FCSERRS"
			::= { pmIfCurrentEntry 12 }

		
		pmIfCurrentCollisions OBJECT-TYPE
			SYNTAX Counter64
			MAX-ACCESS read-only
			STATUS current
			DESCRIPTION
				"PM_IFCURRENT_COLLISIONS"
			::= { pmIfCurrentEntry 13 }

		
		pmIfCurrentDropEvts OBJECT-TYPE
			SYNTAX Counter64
			MAX-ACCESS read-only
			STATUS current
			DESCRIPTION
				"PM_IFCURRENT_DROPEVTS"
			::= { pmIfCurrentEntry 14 }

		
		pmIfCurrentUndersize OBJECT-TYPE
			SYNTAX Counter64
			MAX-ACCESS read-only
			STATUS current
			DESCRIPTION
				"PM_IFCURRENT_UNDERSIZE"
			::= { pmIfCurrentEntry 15 }

		
		pmIfCurrentFragments OBJECT-TYPE
			SYNTAX Counter64
			MAX-ACCESS read-only
			STATUS current
			DESCRIPTION
				"PM_IFCURRENT_FRAGMENTS"
			::= { pmIfCurrentEntry 16 }

		
		pmIfCurrentTxPkts OBJECT-TYPE
			SYNTAX Counter64
			MAX-ACCESS read-only
			STATUS current
			DESCRIPTION
				"PM_IFCURRENT_TXPKTS"
			::= { pmIfCurrentEntry 17 }

		
		pmIfCurrentTxPause OBJECT-TYPE
			SYNTAX Counter64
			MAX-ACCESS read-only
			STATUS current
			DESCRIPTION
				"PM_IFCURRENT_TXPAUSE"
			::= { pmIfCurrentEntry 18 }

		
		pmIfCurrentTxUnicast OBJECT-TYPE
			SYNTAX Counter64
			MAX-ACCESS read-only
			STATUS current
			DESCRIPTION
				"PM_IFCURRENT_TXUNICAST"
			::= { pmIfCurrentEntry 19 }

		
		pmIfCurrentTxMulticast OBJECT-TYPE
			SYNTAX Counter64
			MAX-ACCESS read-only
			STATUS current
			DESCRIPTION
				"PM_IFCURRENT_TXMULTICAST"
			::= { pmIfCurrentEntry 20 }

		
		pmIfCurrentTxBroadcast OBJECT-TYPE
			SYNTAX Counter64
			MAX-ACCESS read-only
			STATUS current
			DESCRIPTION
				"PM_IFCURRENT_TXBROADCAST"
			::= { pmIfCurrentEntry 21 }

		
		pmIfCurrentRxPkts OBJECT-TYPE
			SYNTAX Counter64
			MAX-ACCESS read-only
			STATUS current
			DESCRIPTION
				"PM_IFCURRENT_RXPKTS"
			::= { pmIfCurrentEntry 22 }

		
		pmIfCurrentRxPause OBJECT-TYPE
			SYNTAX Counter64
			MAX-ACCESS read-only
			STATUS current
			DESCRIPTION
				"PM_IFCURRENT_RXPAUSE"
			::= { pmIfCurrentEntry 23 }

		
		pmIfCurrentRxUnicast OBJECT-TYPE
			SYNTAX Counter64
			MAX-ACCESS read-only
			STATUS current
			DESCRIPTION
				"PM_IFCURRENT_RXUNICAST"
			::= { pmIfCurrentEntry 24 }

		
		pmIfCurrentRxMulticast OBJECT-TYPE
			SYNTAX Counter64
			MAX-ACCESS read-only
			STATUS current
			DESCRIPTION
				"PM_IFCURRENT_RXMULTICAST"
			::= { pmIfCurrentEntry 25 }

		
		pmIfCurrentRxBroadcast OBJECT-TYPE
			SYNTAX Counter64
			MAX-ACCESS read-only
			STATUS current
			DESCRIPTION
				"PM_IFCURRENT_RXBROADCAST"
			::= { pmIfCurrentEntry 26 }

		
		pmIfCurrentDurPrdOperState OBJECT-TYPE
			SYNTAX INTEGER
			MAX-ACCESS read-only
			STATUS current
			DESCRIPTION
				"PM_IFCURRENT_DURPRDOPERSTATE"
			::= { pmIfCurrentEntry 27 }

		
		pmIfCurrentEndPrdOperState OBJECT-TYPE
			SYNTAX INTEGER
			MAX-ACCESS read-only
			STATUS current
			DESCRIPTION
				"PM_IFCURRENT_ENDPRDOPERSTATE"
			::= { pmIfCurrentEntry 28 }

		
		pmIfCurrentDurPrdAdminState OBJECT-TYPE
			SYNTAX INTEGER
			MAX-ACCESS read-only
			STATUS current
			DESCRIPTION
				"PM_IFCURRENT_DURPRDADMINSTATE"
			::= { pmIfCurrentEntry 29 }

		
		pmIfCurrentEndPrdAdminState OBJECT-TYPE
			SYNTAX INTEGER
			MAX-ACCESS read-only
			STATUS current
			DESCRIPTION
				"PM_IFCURRENT_ENDPRDADMINSTATE"
			::= { pmIfCurrentEntry 30 }

		
		pmIfCurrentOversize OBJECT-TYPE
			SYNTAX Counter64
			MAX-ACCESS read-only
			STATUS current
			DESCRIPTION
				"PM_IFCURRENT_OVERSIZE"
			::= { pmIfCurrentEntry 31 }


		pmIfUnTimedTable OBJECT-TYPE
			SYNTAX SEQUENCE OF PmIfUnTimedEntry
			MAX-ACCESS not-accessible
			STATUS current
			DESCRIPTION
				"Description."
			::= { pmIfPeriod 7 }

		
		pmIfUnTimedEntry OBJECT-TYPE
			SYNTAX PmIfUnTimedEntry
			MAX-ACCESS not-accessible
			STATUS current
			DESCRIPTION
				"Description."
			INDEX { pmIfUnTimedIfUnit }
			::= { pmIfUnTimedTable 1 }

		
		PmIfUnTimedEntry ::=
			SEQUENCE { 
				pmIfUnTimedIfUnit
					INTEGER,
				pmIfUnTimedStartTime
					Unsigned32,
				pmIfUnTimedEndTime
					Unsigned32,					
				pmIfUnTimedBinFlag
					INTEGER,
				pmIfUnTimedTx5mPps
					Counter64,
				pmIfUnTimedTx5mBps
					Counter64,
				pmIfUnTimedRx5mPps
					Counter64,
				pmIfUnTimedRx5mBps
					Counter64,
				pmIfUnTimedTxBytes
					Counter64,
				pmIfUnTimedRxBytes
					Counter64,
				pmIfUnTimedJunbo
					Counter64,
				pmIfUnTimedFcsErrs
					Counter64,
				pmIfUnTimedCollisions
					Counter64,
				pmIfUnTimedDropEvts
					Counter64,
				pmIfUnTimedUndersize
					Counter64,
				pmIfUnTimedFragments
					Counter64,
				pmIfUnTimedTxPkts
					Counter64,
				pmIfUnTimedTxPause
					Counter64,
				pmIfUnTimedTxUnicast
					Counter64,
				pmIfUnTimedTxMulticast
					Counter64,
				pmIfUnTimedTxBroadcast
					Counter64,
				pmIfUnTimedRxPkts
					Counter64,
				pmIfUnTimedRxPause
					Counter64,
				pmIfUnTimedRxUnicast
					Counter64,
				pmIfUnTimedRxMulticast
					Counter64,
				pmIfUnTimedRxBroadcast
					Counter64,
				pmIfUnTimedDurPrdOperState
					INTEGER,
				pmIfUnTimedEndPrdOperState
					INTEGER,
				pmIfUnTimedDurPrdAdminState
					INTEGER,
				pmIfUnTimedEndPrdAdminState
					INTEGER,
				pmIfUnTimedOversize
					Counter64
			 }

		pmIfUnTimedIfUnit OBJECT-TYPE
			SYNTAX INTEGER (1..2147483647)
			MAX-ACCESS read-only
			STATUS current
			DESCRIPTION
				"Description."
			::= { pmIfUnTimedEntry 1 }

		
		pmIfUnTimedStartTime OBJECT-TYPE
			SYNTAX Unsigned32
			MAX-ACCESS read-only
			STATUS current
			DESCRIPTION
				"PM_IFUNTIMED_STARTTIME"
			::= { pmIfUnTimedEntry 2 }


		pmIfUnTimedEndTime OBJECT-TYPE
			SYNTAX Unsigned32
			MAX-ACCESS read-only
			STATUS current
			DESCRIPTION
				"PM_IFUNTIMED_ENDTIME"
			::= { pmIfUnTimedEntry 3 }

		
		pmIfUnTimedBinFlag OBJECT-TYPE
			SYNTAX INTEGER
				{
				invalid(0),
				valid(1),
				partial(2)
				}
			MAX-ACCESS read-only
			STATUS current
			DESCRIPTION
				"PM_IFUNTIMED_BINFLAG"
			::= { pmIfUnTimedEntry 4 }

		
		pmIfUnTimedTx5mPps OBJECT-TYPE
			SYNTAX Counter64
			MAX-ACCESS read-only
			STATUS current
			DESCRIPTION
				"PM_IFUNTIMED_TX5MINPPS"
			::= { pmIfUnTimedEntry 5 }

		
		pmIfUnTimedTx5mBps OBJECT-TYPE
			SYNTAX Counter64
			MAX-ACCESS read-only
			STATUS current
			DESCRIPTION
				"PM_IFUNTIMED_TX5MINBPS"
			::= { pmIfUnTimedEntry 6 }

		
		pmIfUnTimedRx5mPps OBJECT-TYPE
			SYNTAX Counter64
			MAX-ACCESS read-only
			STATUS current
			DESCRIPTION
				"PM_IFUNTIMED_RX5MINPPS"
			::= { pmIfUnTimedEntry 7 }

		
		pmIfUnTimedRx5mBps OBJECT-TYPE
			SYNTAX Counter64
			MAX-ACCESS read-only
			STATUS current
			DESCRIPTION
				"PM_IFUNTIMED_RX5MINBPS"
			::= { pmIfUnTimedEntry 8 }

		
		pmIfUnTimedTxBytes OBJECT-TYPE
			SYNTAX Counter64
			MAX-ACCESS read-only
			STATUS current
			DESCRIPTION
				"PM_IFUNTIMED_TXBYTES"
			::= { pmIfUnTimedEntry 9 }

		
		pmIfUnTimedRxBytes OBJECT-TYPE
			SYNTAX Counter64
			MAX-ACCESS read-only
			STATUS current
			DESCRIPTION
				"PM_IFUNTIMED_RXBYTES"
			::= { pmIfUnTimedEntry 10 }

		
		pmIfUnTimedJunbo OBJECT-TYPE
			SYNTAX Counter64
			MAX-ACCESS read-only
			STATUS current
			DESCRIPTION
				"PM_IFUNTIMED_JUNBO"
			::= { pmIfUnTimedEntry 11 }

		
		pmIfUnTimedFcsErrs OBJECT-TYPE
			SYNTAX Counter64
			MAX-ACCESS read-only
			STATUS current
			DESCRIPTION
				"PM_IFUNTIMED_FCSERRS"
			::= { pmIfUnTimedEntry 12 }

		
		pmIfUnTimedCollisions OBJECT-TYPE
			SYNTAX Counter64
			MAX-ACCESS read-only
			STATUS current
			DESCRIPTION
				"PM_IFUNTIMED_COLLISIONS"
			::= { pmIfUnTimedEntry 13 }

		
		pmIfUnTimedDropEvts OBJECT-TYPE
			SYNTAX Counter64
			MAX-ACCESS read-only
			STATUS current
			DESCRIPTION
				"PM_IFUNTIMED_DROPEVTS"
			::= { pmIfUnTimedEntry 14 }

		
		pmIfUnTimedUndersize OBJECT-TYPE
			SYNTAX Counter64
			MAX-ACCESS read-only
			STATUS current
			DESCRIPTION
				"PM_IFUNTIMED_UNDERSIZE"
			::= { pmIfUnTimedEntry 15 }

		
		pmIfUnTimedFragments OBJECT-TYPE
			SYNTAX Counter64
			MAX-ACCESS read-only
			STATUS current
			DESCRIPTION
				"PM_IFUNTIMED_FRAGMENTS"
			::= { pmIfUnTimedEntry 16 }

		
		pmIfUnTimedTxPkts OBJECT-TYPE
			SYNTAX Counter64
			MAX-ACCESS read-only
			STATUS current
			DESCRIPTION
				"PM_IFUNTIMED_TXPKTS"
			::= { pmIfUnTimedEntry 17 }

		
		pmIfUnTimedTxPause OBJECT-TYPE
			SYNTAX Counter64
			MAX-ACCESS read-only
			STATUS current
			DESCRIPTION
				"PM_IFUNTIMED_TXPAUSE"
			::= { pmIfUnTimedEntry 18 }

		
		pmIfUnTimedTxUnicast OBJECT-TYPE
			SYNTAX Counter64
			MAX-ACCESS read-only
			STATUS current
			DESCRIPTION
				"PM_IFUNTIMED_TXUNICAST"
			::= { pmIfUnTimedEntry 19 }

		
		pmIfUnTimedTxMulticast OBJECT-TYPE
			SYNTAX Counter64
			MAX-ACCESS read-only
			STATUS current
			DESCRIPTION
				"PM_IFUNTIMED_TXMULTICAST"
			::= { pmIfUnTimedEntry 20 }

		
		pmIfUnTimedTxBroadcast OBJECT-TYPE
			SYNTAX Counter64
			MAX-ACCESS read-only
			STATUS current
			DESCRIPTION
				"PM_IFUNTIMED_TXBROADCAST"
			::= { pmIfUnTimedEntry 21 }

		
		pmIfUnTimedRxPkts OBJECT-TYPE
			SYNTAX Counter64
			MAX-ACCESS read-only
			STATUS current
			DESCRIPTION
				"PM_IFUNTIMED_RXPKTS"
			::= { pmIfUnTimedEntry 22 }

		
		pmIfUnTimedRxPause OBJECT-TYPE
			SYNTAX Counter64
			MAX-ACCESS read-only
			STATUS current
			DESCRIPTION
				"PM_IFUNTIMED_RXPAUSE"
			::= { pmIfUnTimedEntry 23 }

		
		pmIfUnTimedRxUnicast OBJECT-TYPE
			SYNTAX Counter64
			MAX-ACCESS read-only
			STATUS current
			DESCRIPTION
				"PM_IFUNTIMED_RXUNICAST"
			::= { pmIfUnTimedEntry 24 }

		
		pmIfUnTimedRxMulticast OBJECT-TYPE
			SYNTAX Counter64
			MAX-ACCESS read-only
			STATUS current
			DESCRIPTION
				"PM_IFUNTIMED_RXMULTICAST"
			::= { pmIfUnTimedEntry 25 }

		
		pmIfUnTimedRxBroadcast OBJECT-TYPE
			SYNTAX Counter64
			MAX-ACCESS read-only
			STATUS current
			DESCRIPTION
				"PM_IFUNTIMED_RXBROADCAST"
			::= { pmIfUnTimedEntry 26 }

		
		pmIfUnTimedDurPrdOperState OBJECT-TYPE
			SYNTAX INTEGER
			MAX-ACCESS read-only
			STATUS current
			DESCRIPTION
				"PM_IFUNTIMED_DURPRDOPERSTATE"
			::= { pmIfUnTimedEntry 27 }

		
		pmIfUnTimedEndPrdOperState OBJECT-TYPE
			SYNTAX INTEGER
			MAX-ACCESS read-only
			STATUS current
			DESCRIPTION
				"PM_IFUNTIMED_ENDPRDOPERSTATE"
			::= { pmIfUnTimedEntry 28 }

		
		pmIfUnTimedDurPrdAdminState OBJECT-TYPE
			SYNTAX INTEGER
			MAX-ACCESS read-only
			STATUS current
			DESCRIPTION
				"PM_IFUNTIMED_DURPRDADMINSTATE"
			::= { pmIfUnTimedEntry 29 }

		
		pmIfUnTimedEndPrdAdminState OBJECT-TYPE
			SYNTAX INTEGER
			MAX-ACCESS read-only
			STATUS current
			DESCRIPTION
				"PM_IFUNTIMED_ENDPRDADMINSTATE"
			::= { pmIfUnTimedEntry 30 }

		
		pmIfUnTimedOversize OBJECT-TYPE
			SYNTAX Counter64
			MAX-ACCESS read-only
			STATUS current
			DESCRIPTION
				"PM_IFUNTIMED_OVERSIZE"
			::= { pmIfUnTimedEntry 31 }

		                                      
		pmEServicePeriod OBJECT IDENTIFIER ::= { pm 2 }

		
		pmEServiceStatusTable OBJECT-TYPE
			SYNTAX SEQUENCE OF PmEServiceStatusEntry
			MAX-ACCESS not-accessible
			STATUS current
			DESCRIPTION
				"Description."
			::= { pmEServicePeriod 1 }

		
		pmEServiceStatusEntry OBJECT-TYPE
			SYNTAX PmEServiceStatusEntry
			MAX-ACCESS not-accessible
			STATUS current
			DESCRIPTION
				"Description."
			INDEX { pmEServiceMepId, pmEServiceMegIndex }
			::= { pmEServiceStatusTable 1 }

		
		PmEServiceStatusEntry ::=
			SEQUENCE { 
				pmEServiceMepId
					INTEGER,
				pmEServiceMegIndex
					INTEGER,
				pmEServiceStatusEntryStatus
					INTEGER,
				pmEServiceStatus
					INTEGER,
				pmEServiceRmepStat
					INTEGER
			 }

		pmEServiceMepId OBJECT-TYPE
			SYNTAX INTEGER (1..8191)
			MAX-ACCESS read-only
			STATUS current
			DESCRIPTION
				"Description."
			::= { pmEServiceStatusEntry 1 }

		
		pmEServiceMegIndex OBJECT-TYPE
			SYNTAX INTEGER (1..2147483647)
			MAX-ACCESS read-only
			STATUS current
			DESCRIPTION
				"Description."
			::= { pmEServiceStatusEntry 2 }

		
		pmEServiceStatusEntryStatus OBJECT-TYPE
			SYNTAX INTEGER
				{
				valid(1),
				createRequest(2),
				underCreation(3),
				invalid(4)
				}
			MAX-ACCESS read-write
			STATUS current
			DESCRIPTION
				"Description."
			::= { pmEServiceStatusEntry 3 }

		
		pmEServiceStatus OBJECT-TYPE
			SYNTAX INTEGER
				{
				disable(0),
				enable(1)
				}
			MAX-ACCESS read-write
			STATUS current
			DESCRIPTION
				"Description."
			::= { pmEServiceStatusEntry 4 }

		
		pmEServiceRmepStat OBJECT-TYPE
			SYNTAX INTEGER
			MAX-ACCESS read-only
			STATUS current
			DESCRIPTION
				"PM_SLA_RMEPSTAT"
			::= { pmEServiceStatusEntry 5 }

		
		pmEService1mStatTable OBJECT-TYPE
			SYNTAX SEQUENCE OF PmEService1mStatEntry
			MAX-ACCESS not-accessible
			STATUS current
			DESCRIPTION
				"Description."
			::= { pmEServicePeriod 2 }

		
		pmEService1mStatEntry OBJECT-TYPE
			SYNTAX PmEService1mStatEntry
			MAX-ACCESS not-accessible
			STATUS current
			DESCRIPTION
				"Description."
			INDEX { pmEService1mStatMepId, pmEService1mStatMegIndex, pmEService1mStatRmepId, pmEService1mStatTimeStamp }
			::= { pmEService1mStatTable 1 }

		
		PmEService1mStatEntry ::=
			SEQUENCE { 
				pmEService1mStatMepId
					INTEGER,
				pmEService1mStatMegIndex
					INTEGER,
				pmEService1mStatRmepId
					INTEGER,
				pmEService1mStatTimeStamp
					Unsigned32,
				pmEService1mStatBinFlag
					INTEGER,
				pmEService1mStatUasCounter
					Counter64,
				pmEService1mStatPasCounter
					Counter64,
				pmEService1mStatTotalTransBytes
					Counter64,
				pmEService1mStatTxRatePps
					Counter64,
				pmEService1mStatTxRateBps
					Counter64,
				pmEService1mStatTxUtilization
					Counter64,
				pmEService1mStatRxRatePps
					Counter64,
				pmEService1mStatRxRateBps
					Counter64,
				pmEService1mStatRxUtilization
					Counter64,
				pmEService1mStatRedBytes
					Counter64,
				pmEService1mStatGreenBytes
					Counter64,
				pmEService1mStatYellowBytes
					Counter64,
				pmEService1mStatTotalRecvPkts
					Counter64,
				pmEService1mStatTotalTransPkts
					Counter64,
				pmEService1mStatTotalRecvDropPkts
					Counter64,
				pmEService1mStatPerserAv
					Counter64,
				pmEService1mStatPerserUav
					Counter64,
				pmEService1mStatPerserPav
					Counter64,
				pmEService1mStatPerserEdgePairAv
					Counter64,
				pmEService1mStatPerserEdgePairUavr
					Counter64,
				pmEService1mStatPerserEdgePairUavl
					Counter64,
				pmEService1mStatDurPrdOperState
					INTEGER,
				pmEService1mStatEndPrdOperState
					INTEGER,
				pmEService1mStatDurPrdAdminState
					INTEGER,
				pmEService1mStatEndPrdAdminState
					INTEGER
			 }

		pmEService1mStatMepId OBJECT-TYPE
			SYNTAX INTEGER (1..8191)
			MAX-ACCESS read-only
			STATUS current
			DESCRIPTION
				"Description."
			::= { pmEService1mStatEntry 1 }

		
		pmEService1mStatMegIndex OBJECT-TYPE
			SYNTAX INTEGER (1..2147483647)
			MAX-ACCESS read-only
			STATUS current
			DESCRIPTION
				"Description."
			::= { pmEService1mStatEntry 2 }

		
		pmEService1mStatRmepId OBJECT-TYPE
			SYNTAX INTEGER (1..8191)
			MAX-ACCESS read-only
			STATUS current
			DESCRIPTION
				"Description."
			::= { pmEService1mStatEntry 3 }

		
		pmEService1mStatTimeStamp OBJECT-TYPE
			SYNTAX Unsigned32
			MAX-ACCESS read-only
			STATUS current
			DESCRIPTION
				"PM_ESERVICE24HOURSTAT_TIMESTAMP"
			::= { pmEService1mStatEntry 4 }

		
		pmEService1mStatBinFlag OBJECT-TYPE
			SYNTAX INTEGER
				{
				invalid(0),
				valid(1),
				partial(2)
				}
			MAX-ACCESS read-only
			STATUS current
			DESCRIPTION
				"PM_ESERVICE24HOURSTAT_BINFLAG"
			::= { pmEService1mStatEntry 5 }

		
		pmEService1mStatUasCounter OBJECT-TYPE
			SYNTAX Counter64
			MAX-ACCESS read-only
			STATUS current
			DESCRIPTION
				"PM_ESERVICE24HOURSTAT_UASCOUNTER"
			::= { pmEService1mStatEntry 6 }

		
		pmEService1mStatPasCounter OBJECT-TYPE
			SYNTAX Counter64
			MAX-ACCESS read-only
			STATUS current
			DESCRIPTION
				"PM_ESERVICE24HOURSTAT_PASCOUNTER"
			::= { pmEService1mStatEntry 7 }

		
		pmEService1mStatTotalTransBytes OBJECT-TYPE
			SYNTAX Counter64
			MAX-ACCESS read-only
			STATUS current
			DESCRIPTION
				"PM_ESERVICE24HOURSTAT_TOTALTRANSBYTES"
			::= { pmEService1mStatEntry 8 }

		
		pmEService1mStatTxRatePps OBJECT-TYPE
			SYNTAX Counter64
			MAX-ACCESS read-only
			STATUS current
			DESCRIPTION
				"PM_ESERVICE24HOURSTAT_TXRATEPPS"
			::= { pmEService1mStatEntry 9 }

		
		pmEService1mStatTxRateBps OBJECT-TYPE
			SYNTAX Counter64
			MAX-ACCESS read-only
			STATUS current
			DESCRIPTION
				"PM_ESERVICE24HOURSTAT_TXRATEBPS"
			::= { pmEService1mStatEntry 10 }

		
		pmEService1mStatTxUtilization OBJECT-TYPE
			SYNTAX Counter64
			MAX-ACCESS read-only
			STATUS current
			DESCRIPTION
				"PM_ESERVICE24HOURSTAT_TXUTILIZATION"
			::= { pmEService1mStatEntry 11 }

		
		pmEService1mStatRxRatePps OBJECT-TYPE
			SYNTAX Counter64
			MAX-ACCESS read-only
			STATUS current
			DESCRIPTION
				"PM_ESERVICE24HOURSTAT_RXRATEPPS"
			::= { pmEService1mStatEntry 12 }

		
		pmEService1mStatRxRateBps OBJECT-TYPE
			SYNTAX Counter64
			MAX-ACCESS read-only
			STATUS current
			DESCRIPTION
				"PM_ESERVICE24HOURSTAT_RXRATEBPS"
			::= { pmEService1mStatEntry 13 }

		
		pmEService1mStatRxUtilization OBJECT-TYPE
			SYNTAX Counter64
			MAX-ACCESS read-only
			STATUS current
			DESCRIPTION
				"PM_ESERVICE24HOURSTAT_RXUTILIZATION"
			::= { pmEService1mStatEntry 14 }

		
		pmEService1mStatRedBytes OBJECT-TYPE
			SYNTAX Counter64
			MAX-ACCESS read-only
			STATUS current
			DESCRIPTION
				"PM_ESERVICE24HOURSTAT_REDBYTES"
			::= { pmEService1mStatEntry 15 }

		
		pmEService1mStatGreenBytes OBJECT-TYPE
			SYNTAX Counter64
			MAX-ACCESS read-only
			STATUS current
			DESCRIPTION
				"PM_ESERVICE24HOURSTAT_GREENBYTES"
			::= { pmEService1mStatEntry 16 }

		
		pmEService1mStatYellowBytes OBJECT-TYPE
			SYNTAX Counter64
			MAX-ACCESS read-only
			STATUS current
			DESCRIPTION
				"PM_ESERVICE24HOURSTAT_YELLOWBYTES"
			::= { pmEService1mStatEntry 17 }

		
		pmEService1mStatTotalRecvPkts OBJECT-TYPE
			SYNTAX Counter64
			MAX-ACCESS read-only
			STATUS current
			DESCRIPTION
				"PM_ESERVICE24HOURSTAT_TOTALRECVPKTS"
			::= { pmEService1mStatEntry 18 }

		
		pmEService1mStatTotalTransPkts OBJECT-TYPE
			SYNTAX Counter64
			MAX-ACCESS read-only
			STATUS current
			DESCRIPTION
				"PM_ESERVICE24HOURSTAT_TOTALTRANSPKTS"
			::= { pmEService1mStatEntry 19 }

		
		pmEService1mStatTotalRecvDropPkts OBJECT-TYPE
			SYNTAX Counter64
			MAX-ACCESS read-only
			STATUS current
			DESCRIPTION
				"PM_ESERVICE24HOURSTAT_TOTALRECVDROPPKTS"
			::= { pmEService1mStatEntry 20 }

		
		pmEService1mStatPerserAv OBJECT-TYPE
			SYNTAX Counter64
			MAX-ACCESS read-only
			STATUS current
			DESCRIPTION
				"PM_ESERVICE24HOURSTAT_PERSERAV"
			::= { pmEService1mStatEntry 21 }

		
		pmEService1mStatPerserUav OBJECT-TYPE
			SYNTAX Counter64
			MAX-ACCESS read-only
			STATUS current
			DESCRIPTION
				"PM_ESERVICE24HOURSTAT_PERSERUAV"
			::= { pmEService1mStatEntry 22 }

		
		pmEService1mStatPerserPav OBJECT-TYPE
			SYNTAX Counter64
			MAX-ACCESS read-only
			STATUS current
			DESCRIPTION
				"PM_ESERVICE24HOURSTAT_PERSERPAV"
			::= { pmEService1mStatEntry 23 }

		
		pmEService1mStatPerserEdgePairAv OBJECT-TYPE
			SYNTAX Counter64
			MAX-ACCESS read-only
			STATUS current
			DESCRIPTION
				"PM_ESERVICE24HOURSTAT_PERSEREDGEPAIRAV"
			::= { pmEService1mStatEntry 24 }

		
		pmEService1mStatPerserEdgePairUavr OBJECT-TYPE
			SYNTAX Counter64
			MAX-ACCESS read-only
			STATUS current
			DESCRIPTION
				"PM_ESERVICE24HOURSTAT_PERSEREDGEPAIRUAVR"
			::= { pmEService1mStatEntry 25 }

		
		pmEService1mStatPerserEdgePairUavl OBJECT-TYPE
			SYNTAX Counter64
			MAX-ACCESS read-only
			STATUS current
			DESCRIPTION
				"PM_ESERVICE24HOURSTAT_PERSEREDGEPAIRUAVL"
			::= { pmEService1mStatEntry 26 }

		
		pmEService1mStatDurPrdOperState OBJECT-TYPE
			SYNTAX INTEGER
			MAX-ACCESS read-only
			STATUS current
			DESCRIPTION
				"PM_ESERVICE24HOURSTAT_DURPRDOPERSTATE"
			::= { pmEService1mStatEntry 27 }

		
		pmEService1mStatEndPrdOperState OBJECT-TYPE
			SYNTAX INTEGER
			MAX-ACCESS read-only
			STATUS current
			DESCRIPTION
				"PM_ESERVICE24HOURSTAT_ENDPRDOPERSTATE"
			::= { pmEService1mStatEntry 28 }

		
		pmEService1mStatDurPrdAdminState OBJECT-TYPE
			SYNTAX INTEGER
			MAX-ACCESS read-only
			STATUS current
			DESCRIPTION
				"PM_ESERVICE24HOURSTAT_DURPRDADMINSTATE"
			::= { pmEService1mStatEntry 29 }

		
		pmEService1mStatEndPrdAdminState OBJECT-TYPE
			SYNTAX INTEGER
			MAX-ACCESS read-only
			STATUS current
			DESCRIPTION
				"PM_ESERVICE24HOURSTAT_ENDPRDADMINSTATE"
			::= { pmEService1mStatEntry 30 }

		
		pmEService5mStatTable OBJECT-TYPE
			SYNTAX SEQUENCE OF PmEService5mStatEntry
			MAX-ACCESS not-accessible
			STATUS current
			DESCRIPTION
				"Description."
			::= { pmEServicePeriod 3 }

		
		pmEService5mStatEntry OBJECT-TYPE
			SYNTAX PmEService5mStatEntry
			MAX-ACCESS not-accessible
			STATUS current
			DESCRIPTION
				"Description."
			INDEX { pmEService5mStatMepId, pmEService5mStatMegIndex, pmEService5mStatRmepId, pmEService5mStatTimeStamp }
			::= { pmEService5mStatTable 1 }

		
		PmEService5mStatEntry ::=
			SEQUENCE { 
				pmEService5mStatMepId
					INTEGER,
				pmEService5mStatMegIndex
					INTEGER,
				pmEService5mStatRmepId
					INTEGER,
				pmEService5mStatTimeStamp
					Unsigned32,
				pmEService5mStatBinFlag
					INTEGER,
				pmEService5mStatUasCounter
					Counter64,
				pmEService5mStatPasCounter
					Counter64,
				pmEService5mStatTotalTransBytes
					Counter64,
				pmEService5mStatTxRatePps
					Counter64,
				pmEService5mStatTxRateBps
					Counter64,
				pmEService5mStatTxUtilization
					Counter64,
				pmEService5mStatRxRatePps
					Counter64,
				pmEService5mStatRxRateBps
					Counter64,
				pmEService5mStatRxUtilization
					Counter64,
				pmEService5mStatRedBytes
					Counter64,
				pmEService5mStatGreenBytes
					Counter64,
				pmEService5mStatYellowBytes
					Counter64,
				pmEService5mStatTotalRecvPkts
					Counter64,
				pmEService5mStatTotalTransPkts
					Counter64,
				pmEService5mStatTotalRecvDropPkts
					Counter64,
				pmEService5mStatPerserAv
					Counter64,
				pmEService5mStatPerserUav
					Counter64,
				pmEService5mStatPerserPav
					Counter64,
				pmEService5mStatPerserEdgePairAv
					Counter64,
				pmEService5mStatPerserEdgePairUavr
					Counter64,
				pmEService5mStatPerserEdgePairUavl
					Counter64,
				pmEService5mStatDurPrdOperState
					INTEGER,
				pmEService5mStatEndPrdOperState
					INTEGER,
				pmEService5mStatDurPrdAdminState
					INTEGER,
				pmEService5mStatEndPrdAdminState
					INTEGER
			 }

		pmEService5mStatMepId OBJECT-TYPE
			SYNTAX INTEGER (1..8191)
			MAX-ACCESS read-only
			STATUS current
			DESCRIPTION
				"Description."
			::= { pmEService5mStatEntry 1 }

		
		pmEService5mStatMegIndex OBJECT-TYPE
			SYNTAX INTEGER (1..2147483647)
			MAX-ACCESS read-only
			STATUS current
			DESCRIPTION
				"Description."
			::= { pmEService5mStatEntry 2 }

		
		pmEService5mStatRmepId OBJECT-TYPE
			SYNTAX INTEGER (1..8191)
			MAX-ACCESS read-only
			STATUS current
			DESCRIPTION
				"Description."
			::= { pmEService5mStatEntry 3 }

		
		pmEService5mStatTimeStamp OBJECT-TYPE
			SYNTAX Unsigned32
			MAX-ACCESS read-only
			STATUS current
			DESCRIPTION
				"PM_ESERVICE5MINSTAT_TIMESTAMP"
			::= { pmEService5mStatEntry 4 }

		
		pmEService5mStatBinFlag OBJECT-TYPE
			SYNTAX INTEGER
				{
				invalid(0),
				valid(1),
				partial(2)
				}
			MAX-ACCESS read-only
			STATUS current
			DESCRIPTION
				"PM_ESERVICE5MINSTAT_BINFLAG"
			::= { pmEService5mStatEntry 5 }

		
		pmEService5mStatUasCounter OBJECT-TYPE
			SYNTAX Counter64
			MAX-ACCESS read-only
			STATUS current
			DESCRIPTION
				"PM_ESERVICE5MINSTAT_UASCOUNTER"
			::= { pmEService5mStatEntry 6 }

		
		pmEService5mStatPasCounter OBJECT-TYPE
			SYNTAX Counter64
			MAX-ACCESS read-only
			STATUS current
			DESCRIPTION
				"PM_ESERVICE5MINSTAT_PASCOUNTER"
			::= { pmEService5mStatEntry 7 }

		
		pmEService5mStatTotalTransBytes OBJECT-TYPE
			SYNTAX Counter64
			MAX-ACCESS read-only
			STATUS current
			DESCRIPTION
				"PM_ESERVICE5MINSTAT_TOTALTRANSBYTES"
			::= { pmEService5mStatEntry 8 }

		
		pmEService5mStatTxRatePps OBJECT-TYPE
			SYNTAX Counter64
			MAX-ACCESS read-only
			STATUS current
			DESCRIPTION
				"PM_ESERVICE5MINSTAT_TXRATEPPS"
			::= { pmEService5mStatEntry 9 }

		
		pmEService5mStatTxRateBps OBJECT-TYPE
			SYNTAX Counter64
			MAX-ACCESS read-only
			STATUS current
			DESCRIPTION
				"PM_ESERVICE5MINSTAT_TXRATEBPS"
			::= { pmEService5mStatEntry 10 }

		
		pmEService5mStatTxUtilization OBJECT-TYPE
			SYNTAX Counter64
			MAX-ACCESS read-only
			STATUS current
			DESCRIPTION
				"PM_ESERVICE5MINSTAT_TXUTILIZATION"
			::= { pmEService5mStatEntry 11 }

		
		pmEService5mStatRxRatePps OBJECT-TYPE
			SYNTAX Counter64
			MAX-ACCESS read-only
			STATUS current
			DESCRIPTION
				"PM_ESERVICE5MINSTAT_RXRATEPPS"
			::= { pmEService5mStatEntry 12 }

		
		pmEService5mStatRxRateBps OBJECT-TYPE
			SYNTAX Counter64
			MAX-ACCESS read-only
			STATUS current
			DESCRIPTION
				"PM_ESERVICE5MINSTAT_RXRATEBPS"
			::= { pmEService5mStatEntry 13 }

		
		pmEService5mStatRxUtilization OBJECT-TYPE
			SYNTAX Counter64
			MAX-ACCESS read-only
			STATUS current
			DESCRIPTION
				"PM_ESERVICE5MINSTAT_RXUTILIZATION"
			::= { pmEService5mStatEntry 14 }

		
		pmEService5mStatRedBytes OBJECT-TYPE
			SYNTAX Counter64
			MAX-ACCESS read-only
			STATUS current
			DESCRIPTION
				"PM_ESERVICE5MINSTAT_REDBYTES"
			::= { pmEService5mStatEntry 15 }

		
		pmEService5mStatGreenBytes OBJECT-TYPE
			SYNTAX Counter64
			MAX-ACCESS read-only
			STATUS current
			DESCRIPTION
				"PM_ESERVICE5MINSTAT_GREENBYTES"
			::= { pmEService5mStatEntry 16 }

		
		pmEService5mStatYellowBytes OBJECT-TYPE
			SYNTAX Counter64
			MAX-ACCESS read-only
			STATUS current
			DESCRIPTION
				"PM_ESERVICE5MINSTAT_YELLOWBYTES"
			::= { pmEService5mStatEntry 17 }

		
		pmEService5mStatTotalRecvPkts OBJECT-TYPE
			SYNTAX Counter64
			MAX-ACCESS read-only
			STATUS current
			DESCRIPTION
				"PM_ESERVICE5MINSTAT_TOTALRECVPKTS"
			::= { pmEService5mStatEntry 18 }

		
		pmEService5mStatTotalTransPkts OBJECT-TYPE
			SYNTAX Counter64
			MAX-ACCESS read-only
			STATUS current
			DESCRIPTION
				"PM_ESERVICE5MINSTAT_TOTALTRANSPKTS"
			::= { pmEService5mStatEntry 19 }

		
		pmEService5mStatTotalRecvDropPkts OBJECT-TYPE
			SYNTAX Counter64
			MAX-ACCESS read-only
			STATUS current
			DESCRIPTION
				"PM_ESERVICE5MINSTAT_TOTALRECVDROPPKTS"
			::= { pmEService5mStatEntry 20 }

		
		pmEService5mStatPerserAv OBJECT-TYPE
			SYNTAX Counter64
			MAX-ACCESS read-only
			STATUS current
			DESCRIPTION
				"PM_ESERVICE5MINSTAT_PERSERAV"
			::= { pmEService5mStatEntry 21 }

		
		pmEService5mStatPerserUav OBJECT-TYPE
			SYNTAX Counter64
			MAX-ACCESS read-only
			STATUS current
			DESCRIPTION
				"PM_ESERVICE5MINSTAT_PERSERUAV"
			::= { pmEService5mStatEntry 22 }

		
		pmEService5mStatPerserPav OBJECT-TYPE
			SYNTAX Counter64
			MAX-ACCESS read-only
			STATUS current
			DESCRIPTION
				"PM_ESERVICE5MINSTAT_PERSERPAV"
			::= { pmEService5mStatEntry 23 }

		
		pmEService5mStatPerserEdgePairAv OBJECT-TYPE
			SYNTAX Counter64
			MAX-ACCESS read-only
			STATUS current
			DESCRIPTION
				"PM_ESERVICE5MINSTAT_PERSEREDGEPAIRAV"
			::= { pmEService5mStatEntry 24 }

		
		pmEService5mStatPerserEdgePairUavr OBJECT-TYPE
			SYNTAX Counter64
			MAX-ACCESS read-only
			STATUS current
			DESCRIPTION
				"PM_ESERVICE5MINSTAT_PERSEREDGEPAIRUAVR"
			::= { pmEService5mStatEntry 25 }

		
		pmEService5mStatPerserEdgePairUavl OBJECT-TYPE
			SYNTAX Counter64
			MAX-ACCESS read-only
			STATUS current
			DESCRIPTION
				"PM_ESERVICE5MINSTAT_PERSEREDGEPAIRUAVL"
			::= { pmEService5mStatEntry 26 }

		
		pmEService5mStatDurPrdOperState OBJECT-TYPE
			SYNTAX INTEGER
			MAX-ACCESS read-only
			STATUS current
			DESCRIPTION
				"PM_ESERVICE5MINSTAT_DURPRDOPERSTATE"
			::= { pmEService5mStatEntry 27 }

		
		pmEService5mStatEndPrdOperState OBJECT-TYPE
			SYNTAX INTEGER
			MAX-ACCESS read-only
			STATUS current
			DESCRIPTION
				"PM_ESERVICE5MINSTAT_ENDPRDOPERSTATE"
			::= { pmEService5mStatEntry 28 }

		
		pmEService5mStatDurPrdAdminState OBJECT-TYPE
			SYNTAX INTEGER
			MAX-ACCESS read-only
			STATUS current
			DESCRIPTION
				"PM_ESERVICE5MINSTAT_DURPRDADMINSTATE"
			::= { pmEService5mStatEntry 29 }

		
		pmEService5mStatEndPrdAdminState OBJECT-TYPE
			SYNTAX INTEGER
			MAX-ACCESS read-only
			STATUS current
			DESCRIPTION
				"PM_ESERVICE5MINSTAT_ENDPRDADMINSTATE"
			::= { pmEService5mStatEntry 30 }

		
		pmEService15mStatTable OBJECT-TYPE
			SYNTAX SEQUENCE OF PmEService15mStatEntry
			MAX-ACCESS not-accessible
			STATUS current
			DESCRIPTION
				"Description."
			::= { pmEServicePeriod 4 }

		
		pmEService15mStatEntry OBJECT-TYPE
			SYNTAX PmEService15mStatEntry
			MAX-ACCESS not-accessible
			STATUS current
			DESCRIPTION
				"Description."
			INDEX { pmEService15mStatMepId, pmEService15mStatMegIndex, pmEService15mStatRmepId, pmEService15mStatTimeStamp }
			::= { pmEService15mStatTable 1 }

		
		PmEService15mStatEntry ::=
			SEQUENCE { 
				pmEService15mStatMepId
					INTEGER,
				pmEService15mStatMegIndex
					INTEGER,
				pmEService15mStatRmepId
					INTEGER,
				pmEService15mStatTimeStamp
					Unsigned32,
				pmEService15mStatBinFlag
					INTEGER,
				pmEService15mStatUasCounter
					Counter64,
				pmEService15mStatPasCounter
					Counter64,
				pmEService15mStatTotalTransBytes
					Counter64,
				pmEService15mStatTxRatePps
					Counter64,
				pmEService15mStatTxRateBps
					Counter64,
				pmEService15mStatTxUtilization
					Counter64,
				pmEService15mStatRxRatePps
					Counter64,
				pmEService15mStatRxRateBps
					Counter64,
				pmEService15mStatRxUtilization
					Counter64,
				pmEService15mStatRedBytes
					Counter64,
				pmEService15mStatGreenBytes
					Counter64,
				pmEService15mStatYellowBytes
					Counter64,
				pmEService15mStatTotalRecvPkts
					Counter64,
				pmEService15mStatTotalTransPkts
					Counter64,
				pmEService15mStatTotalRecvDropPkts
					Counter64,
				pmEService15mStatPerserAv
					Counter64,
				pmEService15mStatPerserUav
					Counter64,
				pmEService15mStatPerserPav
					Counter64,
				pmEService15mStatPerserEdgePairAv
					Counter64,
				pmEService15mStatPerserEdgePairUavr
					Counter64,
				pmEService15mStatPerserEdgePairUavl
					Counter64,
				pmEService15mStatDurPrdOperState
					INTEGER,
				pmEService15mStatEndPrdOperState
					INTEGER,
				pmEService15mStatDurPrdAdminState
					INTEGER,
				pmEService15mStatEndPrdAdminState
					INTEGER
			 }

		pmEService15mStatMepId OBJECT-TYPE
			SYNTAX INTEGER (1..8191)
			MAX-ACCESS read-only
			STATUS current
			DESCRIPTION
				"Description."
			::= { pmEService15mStatEntry 1 }

		
		pmEService15mStatMegIndex OBJECT-TYPE
			SYNTAX INTEGER (1..2147483647)
			MAX-ACCESS read-only
			STATUS current
			DESCRIPTION
				"Description."
			::= { pmEService15mStatEntry 2 }

		
		pmEService15mStatRmepId OBJECT-TYPE
			SYNTAX INTEGER (1..8191)
			MAX-ACCESS read-only
			STATUS current
			DESCRIPTION
				"Description."
			::= { pmEService15mStatEntry 3 }

		
		pmEService15mStatTimeStamp OBJECT-TYPE
			SYNTAX Unsigned32
			MAX-ACCESS read-only
			STATUS current
			DESCRIPTION
				"PM_ESERVICE15MINSTAT_TIMESTAMP"
			::= { pmEService15mStatEntry 4 }

		
		pmEService15mStatBinFlag OBJECT-TYPE
			SYNTAX INTEGER
				{
				invalid(0),
				valid(1),
				partial(2)
				}
			MAX-ACCESS read-only
			STATUS current
			DESCRIPTION
				"PM_ESERVICE15MINSTAT_BINFLAG"
			::= { pmEService15mStatEntry 5 }

		
		pmEService15mStatUasCounter OBJECT-TYPE
			SYNTAX Counter64
			MAX-ACCESS read-only
			STATUS current
			DESCRIPTION
				"PM_ESERVICE15MINSTAT_UASCOUNTER"
			::= { pmEService15mStatEntry 6 }

		
		pmEService15mStatPasCounter OBJECT-TYPE
			SYNTAX Counter64
			MAX-ACCESS read-only
			STATUS current
			DESCRIPTION
				"PM_ESERVICE15MINSTAT_PASCOUNTER"
			::= { pmEService15mStatEntry 7 }

		
		pmEService15mStatTotalTransBytes OBJECT-TYPE
			SYNTAX Counter64
			MAX-ACCESS read-only
			STATUS current
			DESCRIPTION
				"PM_ESERVICE15MINSTAT_TOTALTRANSBYTES"
			::= { pmEService15mStatEntry 8 }

		
		pmEService15mStatTxRatePps OBJECT-TYPE
			SYNTAX Counter64
			MAX-ACCESS read-only
			STATUS current
			DESCRIPTION
				"PM_ESERVICE15MINSTAT_TXRATEPPS"
			::= { pmEService15mStatEntry 9 }

		
		pmEService15mStatTxRateBps OBJECT-TYPE
			SYNTAX Counter64
			MAX-ACCESS read-only
			STATUS current
			DESCRIPTION
				"PM_ESERVICE15MINSTAT_TXRATEBPS"
			::= { pmEService15mStatEntry 10 }

		
		pmEService15mStatTxUtilization OBJECT-TYPE
			SYNTAX Counter64
			MAX-ACCESS read-only
			STATUS current
			DESCRIPTION
				"PM_ESERVICE15MINSTAT_TXUTILIZATION"
			::= { pmEService15mStatEntry 11 }

		
		pmEService15mStatRxRatePps OBJECT-TYPE
			SYNTAX Counter64
			MAX-ACCESS read-only
			STATUS current
			DESCRIPTION
				"PM_ESERVICE15MINSTAT_RXRATEPPS"
			::= { pmEService15mStatEntry 12 }

		
		pmEService15mStatRxRateBps OBJECT-TYPE
			SYNTAX Counter64
			MAX-ACCESS read-only
			STATUS current
			DESCRIPTION
				"PM_ESERVICE15MINSTAT_RXRATEBPS"
			::= { pmEService15mStatEntry 13 }

		
		pmEService15mStatRxUtilization OBJECT-TYPE
			SYNTAX Counter64
			MAX-ACCESS read-only
			STATUS current
			DESCRIPTION
				"PM_ESERVICE15MINSTAT_RXUTILIZATION"
			::= { pmEService15mStatEntry 14 }

		
		pmEService15mStatRedBytes OBJECT-TYPE
			SYNTAX Counter64
			MAX-ACCESS read-only
			STATUS current
			DESCRIPTION
				"PM_ESERVICE15MINSTAT_REDBYTES"
			::= { pmEService15mStatEntry 15 }

		
		pmEService15mStatGreenBytes OBJECT-TYPE
			SYNTAX Counter64
			MAX-ACCESS read-only
			STATUS current
			DESCRIPTION
				"PM_ESERVICE15MINSTAT_GREENBYTES"
			::= { pmEService15mStatEntry 16 }

		
		pmEService15mStatYellowBytes OBJECT-TYPE
			SYNTAX Counter64
			MAX-ACCESS read-only
			STATUS current
			DESCRIPTION
				"PM_ESERVICE15MINSTAT_YELLOWBYTES"
			::= { pmEService15mStatEntry 17 }

		
		pmEService15mStatTotalRecvPkts OBJECT-TYPE
			SYNTAX Counter64
			MAX-ACCESS read-only
			STATUS current
			DESCRIPTION
				"PM_ESERVICE15MINSTAT_TOTALRECVPKTS"
			::= { pmEService15mStatEntry 18 }

		
		pmEService15mStatTotalTransPkts OBJECT-TYPE
			SYNTAX Counter64
			MAX-ACCESS read-only
			STATUS current
			DESCRIPTION
				"PM_ESERVICE15MINSTAT_TOTALTRANSPKTS"
			::= { pmEService15mStatEntry 19 }

		
		pmEService15mStatTotalRecvDropPkts OBJECT-TYPE
			SYNTAX Counter64
			MAX-ACCESS read-only
			STATUS current
			DESCRIPTION
				"PM_ESERVICE15MINSTAT_TOTALRECVDROPPKTS"
			::= { pmEService15mStatEntry 20 }

		
		pmEService15mStatPerserAv OBJECT-TYPE
			SYNTAX Counter64
			MAX-ACCESS read-only
			STATUS current
			DESCRIPTION
				"PM_ESERVICE15MINSTAT_PERSERAV"
			::= { pmEService15mStatEntry 21 }

		
		pmEService15mStatPerserUav OBJECT-TYPE
			SYNTAX Counter64
			MAX-ACCESS read-only
			STATUS current
			DESCRIPTION
				"PM_ESERVICE15MINSTAT_PERSERUAV"
			::= { pmEService15mStatEntry 22 }

		
		pmEService15mStatPerserPav OBJECT-TYPE
			SYNTAX Counter64
			MAX-ACCESS read-only
			STATUS current
			DESCRIPTION
				"PM_ESERVICE15MINSTAT_PERSERPAV"
			::= { pmEService15mStatEntry 23 }

		
		pmEService15mStatPerserEdgePairAv OBJECT-TYPE
			SYNTAX Counter64
			MAX-ACCESS read-only
			STATUS current
			DESCRIPTION
				"PM_ESERVICE15MINSTAT_PERSEREDGEPAIRAV"
			::= { pmEService15mStatEntry 24 }

		
		pmEService15mStatPerserEdgePairUavr OBJECT-TYPE
			SYNTAX Counter64
			MAX-ACCESS read-only
			STATUS current
			DESCRIPTION
				"PM_ESERVICE15MINSTAT_PERSEREDGEPAIRUAVR"
			::= { pmEService15mStatEntry 25 }

		
		pmEService15mStatPerserEdgePairUavl OBJECT-TYPE
			SYNTAX Counter64
			MAX-ACCESS read-only
			STATUS current
			DESCRIPTION
				"PM_ESERVICE15MINSTAT_PERSEREDGEPAIRUAVL"
			::= { pmEService15mStatEntry 26 }

		
		pmEService15mStatDurPrdOperState OBJECT-TYPE
			SYNTAX INTEGER
			MAX-ACCESS read-only
			STATUS current
			DESCRIPTION
				"PM_ESERVICE15MINSTAT_DURPRDOPERSTATE"
			::= { pmEService15mStatEntry 27 }

		
		pmEService15mStatEndPrdOperState OBJECT-TYPE
			SYNTAX INTEGER
			MAX-ACCESS read-only
			STATUS current
			DESCRIPTION
				"PM_ESERVICE15MINSTAT_ENDPRDOPERSTATE"
			::= { pmEService15mStatEntry 28 }

		
		pmEService15mStatDurPrdAdminState OBJECT-TYPE
			SYNTAX INTEGER
			MAX-ACCESS read-only
			STATUS current
			DESCRIPTION
				"PM_ESERVICE15MINSTAT_DURPRDADMINSTATE"
			::= { pmEService15mStatEntry 29 }

		
		pmEService15mStatEndPrdAdminState OBJECT-TYPE
			SYNTAX INTEGER
			MAX-ACCESS read-only
			STATUS current
			DESCRIPTION
				"PM_ESERVICE15MINSTAT_ENDPRDADMINSTATE"
			::= { pmEService15mStatEntry 30 }

		
		pmEService24hStatTable OBJECT-TYPE
			SYNTAX SEQUENCE OF PmEService24hStatEntry
			MAX-ACCESS not-accessible
			STATUS current
			DESCRIPTION
				"Description."
			::= { pmEServicePeriod 5 }

		
		pmEService24hStatEntry OBJECT-TYPE
			SYNTAX PmEService24hStatEntry
			MAX-ACCESS not-accessible
			STATUS current
			DESCRIPTION
				"Description."
			INDEX { pmEService24hStatMepId, pmEService24hStatMegIndex, pmEService24hStatRmepId, pmEService24hStatTimeStamp }
			::= { pmEService24hStatTable 1 }

		
		PmEService24hStatEntry ::=
			SEQUENCE { 
				pmEService24hStatMepId
					INTEGER,
				pmEService24hStatMegIndex
					INTEGER,
				pmEService24hStatRmepId
					INTEGER,
				pmEService24hStatTimeStamp
					Unsigned32,
				pmEService24hStatBinFlag
					INTEGER,
				pmEService24hStatUasCounter
					Counter64,
				pmEService24hStatPasCounter
					Counter64,
				pmEService24hStatTotalTransBytes
					Counter64,
				pmEService24hStatTxRatePps
					Counter64,
				pmEService24hStatTxRateBps
					Counter64,
				pmEService24hStatTxUtilization
					Counter64,
				pmEService24hStatRxRatePps
					Counter64,
				pmEService24hStatRxRateBps
					Counter64,
				pmEService24hStatRxUtilization
					Counter64,
				pmEService24hStatRedBytes
					Counter64,
				pmEService24hStatGreenBytes
					Counter64,
				pmEService24hStatYellowBytes
					Counter64,
				pmEService24hStatTotalRecvPkts
					Counter64,
				pmEService24hStatTotalTransPkts
					Counter64,
				pmEService24hStatTotalRecvDropPkts
					Counter64,
				pmEService24hStatPerserAv
					Counter64,
				pmEService24hStatPerserUav
					Counter64,
				pmEService24hStatPerserPav
					Counter64,
				pmEService24hStatPerserEdgePairAv
					Counter64,
				pmEService24hStatPerserEdgePairUavr
					Counter64,
				pmEService24hStatPerserEdgePairUavl
					Counter64,
				pmEService24hStatDurPrdOperState
					INTEGER,
				pmEService24hStatEndPrdOperState
					INTEGER,
				pmEService24hStatDurPrdAdminState
					INTEGER,
				pmEService24hStatEndPrdAdminState
					INTEGER
			 }

		pmEService24hStatMepId OBJECT-TYPE
			SYNTAX INTEGER (1..8191)
			MAX-ACCESS read-only
			STATUS current
			DESCRIPTION
				"Description."
			::= { pmEService24hStatEntry 1 }

		
		pmEService24hStatMegIndex OBJECT-TYPE
			SYNTAX INTEGER (1..2147483647)
			MAX-ACCESS read-only
			STATUS current
			DESCRIPTION
				"Description."
			::= { pmEService24hStatEntry 2 }

		
		pmEService24hStatRmepId OBJECT-TYPE
			SYNTAX INTEGER (1..8191)
			MAX-ACCESS read-only
			STATUS current
			DESCRIPTION
				"Description."
			::= { pmEService24hStatEntry 3 }

		
		pmEService24hStatTimeStamp OBJECT-TYPE
			SYNTAX Unsigned32
			MAX-ACCESS read-only
			STATUS current
			DESCRIPTION
				"PM_ESERVICE24HOURSTAT_TIMESTAMP"
			::= { pmEService24hStatEntry 4 }

		
		pmEService24hStatBinFlag OBJECT-TYPE
			SYNTAX INTEGER
				{
				invalid(0),
				valid(1),
				partial(2)
				}
			MAX-ACCESS read-only
			STATUS current
			DESCRIPTION
				"PM_ESERVICE24HOURSTAT_BINFLAG"
			::= { pmEService24hStatEntry 5 }

		
		pmEService24hStatUasCounter OBJECT-TYPE
			SYNTAX Counter64
			MAX-ACCESS read-only
			STATUS current
			DESCRIPTION
				"PM_ESERVICE24HOURSTAT_UASCOUNTER"
			::= { pmEService24hStatEntry 6 }

		
		pmEService24hStatPasCounter OBJECT-TYPE
			SYNTAX Counter64
			MAX-ACCESS read-only
			STATUS current
			DESCRIPTION
				"PM_ESERVICE24HOURSTAT_PASCOUNTER"
			::= { pmEService24hStatEntry 7 }

		
		pmEService24hStatTotalTransBytes OBJECT-TYPE
			SYNTAX Counter64
			MAX-ACCESS read-only
			STATUS current
			DESCRIPTION
				"PM_ESERVICE24HOURSTAT_TOTALTRANSBYTES"
			::= { pmEService24hStatEntry 8 }

		
		pmEService24hStatTxRatePps OBJECT-TYPE
			SYNTAX Counter64
			MAX-ACCESS read-only
			STATUS current
			DESCRIPTION
				"PM_ESERVICE24HOURSTAT_TXRATEPPS"
			::= { pmEService24hStatEntry 9 }

		
		pmEService24hStatTxRateBps OBJECT-TYPE
			SYNTAX Counter64
			MAX-ACCESS read-only
			STATUS current
			DESCRIPTION
				"PM_ESERVICE24HOURSTAT_TXRATEBPS"
			::= { pmEService24hStatEntry 10 }

		
		pmEService24hStatTxUtilization OBJECT-TYPE
			SYNTAX Counter64
			MAX-ACCESS read-only
			STATUS current
			DESCRIPTION
				"PM_ESERVICE24HOURSTAT_TXUTILIZATION"
			::= { pmEService24hStatEntry 11 }

		
		pmEService24hStatRxRatePps OBJECT-TYPE
			SYNTAX Counter64
			MAX-ACCESS read-only
			STATUS current
			DESCRIPTION
				"PM_ESERVICE24HOURSTAT_RXRATEPPS"
			::= { pmEService24hStatEntry 12 }

		
		pmEService24hStatRxRateBps OBJECT-TYPE
			SYNTAX Counter64
			MAX-ACCESS read-only
			STATUS current
			DESCRIPTION
				"PM_ESERVICE24HOURSTAT_RXRATEBPS"
			::= { pmEService24hStatEntry 13 }

		
		pmEService24hStatRxUtilization OBJECT-TYPE
			SYNTAX Counter64
			MAX-ACCESS read-only
			STATUS current
			DESCRIPTION
				"PM_ESERVICE24HOURSTAT_RXUTILIZATION"
			::= { pmEService24hStatEntry 14 }

		
		pmEService24hStatRedBytes OBJECT-TYPE
			SYNTAX Counter64
			MAX-ACCESS read-only
			STATUS current
			DESCRIPTION
				"PM_ESERVICE24HOURSTAT_REDBYTES"
			::= { pmEService24hStatEntry 15 }

		
		pmEService24hStatGreenBytes OBJECT-TYPE
			SYNTAX Counter64
			MAX-ACCESS read-only
			STATUS current
			DESCRIPTION
				"PM_ESERVICE24HOURSTAT_GREENBYTES"
			::= { pmEService24hStatEntry 16 }

		
		pmEService24hStatYellowBytes OBJECT-TYPE
			SYNTAX Counter64
			MAX-ACCESS read-only
			STATUS current
			DESCRIPTION
				"PM_ESERVICE24HOURSTAT_YELLOWBYTES"
			::= { pmEService24hStatEntry 17 }

		
		pmEService24hStatTotalRecvPkts OBJECT-TYPE
			SYNTAX Counter64
			MAX-ACCESS read-only
			STATUS current
			DESCRIPTION
				"PM_ESERVICE24HOURSTAT_TOTALRECVPKTS"
			::= { pmEService24hStatEntry 18 }

		
		pmEService24hStatTotalTransPkts OBJECT-TYPE
			SYNTAX Counter64
			MAX-ACCESS read-only
			STATUS current
			DESCRIPTION
				"PM_ESERVICE24HOURSTAT_TOTALTRANSPKTS"
			::= { pmEService24hStatEntry 19 }

		
		pmEService24hStatTotalRecvDropPkts OBJECT-TYPE
			SYNTAX Counter64
			MAX-ACCESS read-only
			STATUS current
			DESCRIPTION
				"PM_ESERVICE24HOURSTAT_TOTALRECVDROPPKTS"
			::= { pmEService24hStatEntry 20 }

		
		pmEService24hStatPerserAv OBJECT-TYPE
			SYNTAX Counter64
			MAX-ACCESS read-only
			STATUS current
			DESCRIPTION
				"PM_ESERVICE24HOURSTAT_PERSERAV"
			::= { pmEService24hStatEntry 21 }

		
		pmEService24hStatPerserUav OBJECT-TYPE
			SYNTAX Counter64
			MAX-ACCESS read-only
			STATUS current
			DESCRIPTION
				"PM_ESERVICE24HOURSTAT_PERSERUAV"
			::= { pmEService24hStatEntry 22 }

		
		pmEService24hStatPerserPav OBJECT-TYPE
			SYNTAX Counter64
			MAX-ACCESS read-only
			STATUS current
			DESCRIPTION
				"PM_ESERVICE24HOURSTAT_PERSERPAV"
			::= { pmEService24hStatEntry 23 }

		
		pmEService24hStatPerserEdgePairAv OBJECT-TYPE
			SYNTAX Counter64
			MAX-ACCESS read-only
			STATUS current
			DESCRIPTION
				"PM_ESERVICE24HOURSTAT_PERSEREDGEPAIRAV"
			::= { pmEService24hStatEntry 24 }

		
		pmEService24hStatPerserEdgePairUavr OBJECT-TYPE
			SYNTAX Counter64
			MAX-ACCESS read-only
			STATUS current
			DESCRIPTION
				"PM_ESERVICE24HOURSTAT_PERSEREDGEPAIRUAVR"
			::= { pmEService24hStatEntry 25 }

		
		pmEService24hStatPerserEdgePairUavl OBJECT-TYPE
			SYNTAX Counter64
			MAX-ACCESS read-only
			STATUS current
			DESCRIPTION
				"PM_ESERVICE24HOURSTAT_PERSEREDGEPAIRUAVL"
			::= { pmEService24hStatEntry 26 }

		
		pmEService24hStatDurPrdOperState OBJECT-TYPE
			SYNTAX INTEGER
			MAX-ACCESS read-only
			STATUS current
			DESCRIPTION
				"PM_ESERVICE24HOURSTAT_DURPRDOPERSTATE"
			::= { pmEService24hStatEntry 27 }

		
		pmEService24hStatEndPrdOperState OBJECT-TYPE
			SYNTAX INTEGER
			MAX-ACCESS read-only
			STATUS current
			DESCRIPTION
				"PM_ESERVICE24HOURSTAT_ENDPRDOPERSTATE"
			::= { pmEService24hStatEntry 28 }

		
		pmEService24hStatDurPrdAdminState OBJECT-TYPE
			SYNTAX INTEGER
			MAX-ACCESS read-only
			STATUS current
			DESCRIPTION
				"PM_ESERVICE24HOURSTAT_DURPRDADMINSTATE"
			::= { pmEService24hStatEntry 29 }

		
		pmEService24hStatEndPrdAdminState OBJECT-TYPE
			SYNTAX INTEGER
			MAX-ACCESS read-only
			STATUS current
			DESCRIPTION
				"PM_ESERVICE24HOURSTAT_ENDPRDADMINSTATE"
			::= { pmEService24hStatEntry 30 }

		
		pmSlaPeriod OBJECT IDENTIFIER ::= { pm 3 }

		
		pmSlaStatusTable OBJECT-TYPE
			SYNTAX SEQUENCE OF PmSlaStatusEntry
			MAX-ACCESS not-accessible
			STATUS current
			DESCRIPTION
				"Description."
			::= { pmSlaPeriod 1 }

		
		pmSlaStatusEntry OBJECT-TYPE
			SYNTAX PmSlaStatusEntry
			MAX-ACCESS not-accessible
			STATUS current
			DESCRIPTION
				"Description."
			INDEX { pmSlaMepId, pmSlaMegIndex }
			::= { pmSlaStatusTable 1 }

		
		PmSlaStatusEntry ::=
			SEQUENCE { 
				pmSlaMepId
					INTEGER,
				pmSlaMegIndex
					INTEGER,
				pmSlaStatusEntryStatus
					INTEGER,
				pmSlaThresholdDelayAvg
					Unsigned32,
				pmSlaThresholdDelayMax
					Unsigned32,
				pmSlaThresholdDelayVarAvg
					Unsigned32,
				pmSlaThresholdDelayVarMax
					Unsigned32,
				pmSlaThresholdLossRatioFar
					Unsigned32,
				pmSlaThresholdLossRatioNear
					Unsigned32,
				pmSlaRmepStat
					INTEGER, 
				pmSlaLevel
					Unsigned32,					
				pmSlaVlan
					Unsigned32				
			 }

		pmSlaMepId OBJECT-TYPE
			SYNTAX INTEGER (1..8191)
			MAX-ACCESS read-only
			STATUS current
			DESCRIPTION
				"Description."
			::= { pmSlaStatusEntry 1 }

		
		pmSlaMegIndex OBJECT-TYPE
			SYNTAX INTEGER (1..2147483647)
			MAX-ACCESS read-only
			STATUS current
			DESCRIPTION
				"Description."
			::= { pmSlaStatusEntry 2 }

		
		pmSlaStatusEntryStatus OBJECT-TYPE
			SYNTAX INTEGER
				{
				valid(1),
				createRequest(2),
				underCreation(3),
				invalid(4)
				}
			MAX-ACCESS read-write
			STATUS current
			DESCRIPTION
				"Description."
			::= { pmSlaStatusEntry 3 }

		
		pmSlaThresholdDelayAvg OBJECT-TYPE
			SYNTAX Unsigned32
			MAX-ACCESS read-write
			STATUS current
			DESCRIPTION
				"PM_SLA_THRESHOLDDELAYAVG"
			::= { pmSlaStatusEntry 4 }

		
		pmSlaThresholdDelayMax OBJECT-TYPE
			SYNTAX Unsigned32
			MAX-ACCESS read-write
			STATUS current
			DESCRIPTION
				"PM_SLA_THRESHOLDDELAYMAX"
			::= { pmSlaStatusEntry 5 }

		
		pmSlaThresholdDelayVarAvg OBJECT-TYPE
			SYNTAX Unsigned32
			MAX-ACCESS read-write
			STATUS current
			DESCRIPTION
				"PM_SLA_THRESHOLDDELAYVARAVG"
			::= { pmSlaStatusEntry 6 }

		
		pmSlaThresholdDelayVarMax OBJECT-TYPE
			SYNTAX Unsigned32
			MAX-ACCESS read-write
			STATUS current
			DESCRIPTION
				"PM_SLA_THRESHOLDDELAYVARMAX"
			::= { pmSlaStatusEntry 7 }

		
		pmSlaThresholdLossRatioFar OBJECT-TYPE
			SYNTAX Unsigned32
			MAX-ACCESS read-write
			STATUS current
			DESCRIPTION
				"PM_SLA_THRESHOLDLOSSRATIOFAR"
			::= { pmSlaStatusEntry 8 }

		
		pmSlaThresholdLossRatioNear OBJECT-TYPE
			SYNTAX Unsigned32
			MAX-ACCESS read-write
			STATUS current
			DESCRIPTION
				"PM_SLA_THRESHOLDLOSSRATIONEAR"
			::= { pmSlaStatusEntry 9 }

		
		pmSlaRmepStat OBJECT-TYPE
			SYNTAX INTEGER
			MAX-ACCESS read-only
			STATUS current
			DESCRIPTION
				"PM_SLA_RMEPSTAT"
			::= { pmSlaStatusEntry 10 }


		pmSlaLevel OBJECT-TYPE
			SYNTAX Unsigned32
			MAX-ACCESS read-only
			STATUS current
			DESCRIPTION
				"PM_SLA_LEVEL"
			::= { pmSlaStatusEntry 11 }


		pmSlaVlan OBJECT-TYPE
			SYNTAX Unsigned32
			MAX-ACCESS read-only
			STATUS current
			DESCRIPTION
				"PM_SLA_VLAN"
			::= { pmSlaStatusEntry 12 }

		
		pmSla1mStatTable OBJECT-TYPE
			SYNTAX SEQUENCE OF PmSla1mStatEntry
			MAX-ACCESS not-accessible
			STATUS current
			DESCRIPTION
				"Description."
			::= { pmSlaPeriod 2 }

		
		pmSla1mStatEntry OBJECT-TYPE
			SYNTAX PmSla1mStatEntry
			MAX-ACCESS not-accessible
			STATUS current
			DESCRIPTION
				"Description."
			INDEX { pmSla1mStatMepId, pmSla1mStatMegIndex, pmSla1mStatRmepId, pmSla1mStatTimeStamp }
			::= { pmSla1mStatTable 1 }

		
		PmSla1mStatEntry ::=
			SEQUENCE { 
				pmSla1mStatMepId
					INTEGER,
				pmSla1mStatMegIndex
					INTEGER,
				pmSla1mStatRmepId
					INTEGER,
				pmSla1mStatTimeStamp
					Unsigned32,
				pmSla1mStatBinFlag
					INTEGER,
				pmSla1mStatFarMin
					Unsigned32,
				pmSla1mStatFarMax
					Unsigned32,
				pmSla1mStatFarCur
					Unsigned32,
				pmSla1mStatFarAvg
					Unsigned32,
				pmSla1mStatFarSum
					Unsigned32,
				pmSla1mStatNearMin
					Unsigned32,
				pmSla1mStatNearMax
					Unsigned32,
				pmSla1mStatNearCur
					Unsigned32,
				pmSla1mStatNearAvg
					Unsigned32,
				pmSla1mStatNearSum
					Unsigned32,
				pmSla1mStatLmrRecv
					Counter64,
				pmSla1mStatLmmSend
					Counter64,
				pmSla1mStatDmrRecv
					Counter64,
				pmSla1mStatDmmSend
					Counter64,
				pmSla1mStatDmResultMin
					Counter64,
				pmSla1mStatDmResultMax
					Counter64,
				pmSla1mStatDvmResultMin
					Counter64,
				pmSla1mStatDvmResultMax
					Counter64,
				pmSla1mStatDvmResultCur
					Counter64,
				pmSla1mStatDmResultCur
					Counter64,
				pmSla1mStatDmResultAvg
					Counter64,
				pmSla1mStatDvmResultAvg
					Counter64,
				pmSla1mStatFarTxSum
					Unsigned32,
				pmSla1mStatFarLossSum
					Unsigned32,
				pmSla1mStatNearTxSum
					Unsigned32,
				pmSla1mStatNearLossSum
					Unsigned32,
				pmSla1mStatDelayTxTotal
					Unsigned32,
				pmSla1mStatDmResultSum
					Counter64,
				pmSla1mStatDvmResultSum
					Counter64
			 }

		pmSla1mStatMepId OBJECT-TYPE
			SYNTAX INTEGER (1..8191)
			MAX-ACCESS read-only
			STATUS current
			DESCRIPTION
				"Description."
			::= { pmSla1mStatEntry 1 }

		
		pmSla1mStatMegIndex OBJECT-TYPE
			SYNTAX INTEGER (1..2147483647)
			MAX-ACCESS read-only
			STATUS current
			DESCRIPTION
				"Description."
			::= { pmSla1mStatEntry 2 }

		
		pmSla1mStatRmepId OBJECT-TYPE
			SYNTAX INTEGER (1..8191)
			MAX-ACCESS read-only
			STATUS current
			DESCRIPTION
				"Description."
			::= { pmSla1mStatEntry 3 }

		
		pmSla1mStatTimeStamp OBJECT-TYPE
			SYNTAX Unsigned32
			MAX-ACCESS read-only
			STATUS current
			DESCRIPTION
				"PM_SLA1MINSTAT_TIMESTAMP"
			::= { pmSla1mStatEntry 4 }

		
		pmSla1mStatBinFlag OBJECT-TYPE
			SYNTAX INTEGER
				{
				invalid(0),
				valid(1),
				partial(2)
				}
			MAX-ACCESS read-only
			STATUS current
			DESCRIPTION
				"PM_SLA1MINSTAT_BINFLAG"
			::= { pmSla1mStatEntry 5 }

		
		pmSla1mStatFarMin OBJECT-TYPE
			SYNTAX Unsigned32
			MAX-ACCESS read-only
			STATUS current
			DESCRIPTION
				"PM_SLA1MINSTAT_FARMIN"
			::= { pmSla1mStatEntry 6 }

		
		pmSla1mStatFarMax OBJECT-TYPE
			SYNTAX Unsigned32
			MAX-ACCESS read-only
			STATUS current
			DESCRIPTION
				"PM_SLA1MINSTAT_FARMAX"
			::= { pmSla1mStatEntry 7 }

		
		pmSla1mStatFarCur OBJECT-TYPE
			SYNTAX Unsigned32
			MAX-ACCESS read-only
			STATUS current
			DESCRIPTION
				"PM_SLA1MINSTAT_FARCUR"
			::= { pmSla1mStatEntry 8 }

		
		pmSla1mStatFarAvg OBJECT-TYPE
			SYNTAX Unsigned32
			MAX-ACCESS read-only
			STATUS current
			DESCRIPTION
				"PM_SLA1MINSTAT_FARAVG"
			::= { pmSla1mStatEntry 9 }

		
		pmSla1mStatFarSum OBJECT-TYPE
			SYNTAX Unsigned32
			MAX-ACCESS read-only
			STATUS current
			DESCRIPTION
				"PM_SLA1MINSTAT_FARSUM"
			::= { pmSla1mStatEntry 10 }

		
		pmSla1mStatNearMin OBJECT-TYPE
			SYNTAX Unsigned32
			MAX-ACCESS read-only
			STATUS current
			DESCRIPTION
				"PM_SLA1MINSTAT_NEARMIN"
			::= { pmSla1mStatEntry 11 }

		
		pmSla1mStatNearMax OBJECT-TYPE
			SYNTAX Unsigned32
			MAX-ACCESS read-only
			STATUS current
			DESCRIPTION
				"PM_SLA1MINSTAT_NEARMAX"
			::= { pmSla1mStatEntry 12 }

		
		pmSla1mStatNearCur OBJECT-TYPE
			SYNTAX Unsigned32
			MAX-ACCESS read-only
			STATUS current
			DESCRIPTION
				"PM_SLA1MINSTAT_NEARCUR"
			::= { pmSla1mStatEntry 13 }

		
		pmSla1mStatNearAvg OBJECT-TYPE
			SYNTAX Unsigned32
			MAX-ACCESS read-only
			STATUS current
			DESCRIPTION
				"PM_SLA1MINSTAT_NEARAVG"
			::= { pmSla1mStatEntry 14 }

		
		pmSla1mStatNearSum OBJECT-TYPE
			SYNTAX Unsigned32
			MAX-ACCESS read-only
			STATUS current
			DESCRIPTION
				"PM_SLA1MINSTAT_NEARSUM"
			::= { pmSla1mStatEntry 15 }

		
		pmSla1mStatLmrRecv OBJECT-TYPE
			SYNTAX Counter64
			MAX-ACCESS read-only
			STATUS current
			DESCRIPTION
				"PM_SLA1MINSTAT_LMRRECV"
			::= { pmSla1mStatEntry 16 }

		
		pmSla1mStatLmmSend OBJECT-TYPE
			SYNTAX Counter64
			MAX-ACCESS read-only
			STATUS current
			DESCRIPTION
				"PM_SLA1MINSTAT_LMMSEND"
			::= { pmSla1mStatEntry 17 }

		
		pmSla1mStatDmrRecv OBJECT-TYPE
			SYNTAX Counter64
			MAX-ACCESS read-only
			STATUS current
			DESCRIPTION
				"PM_SLA1MINSTAT_DMRRECV"
			::= { pmSla1mStatEntry 18 }

		
		pmSla1mStatDmmSend OBJECT-TYPE
			SYNTAX Counter64
			MAX-ACCESS read-only
			STATUS current
			DESCRIPTION
				"PM_SLA1MINSTAT_DMMSEND"
			::= { pmSla1mStatEntry 19 }

		
		pmSla1mStatDmResultMin OBJECT-TYPE
			SYNTAX Counter64
			MAX-ACCESS read-only
			STATUS current
			DESCRIPTION
				"PM_SLA1MINSTAT_DMRESULTMIN"
			::= { pmSla1mStatEntry 20 }

		
		pmSla1mStatDmResultMax OBJECT-TYPE
			SYNTAX Counter64
			MAX-ACCESS read-only
			STATUS current
			DESCRIPTION
				"PM_SLA1MINSTAT_DMRESULTMAX"
			::= { pmSla1mStatEntry 21 }

		
		pmSla1mStatDvmResultMin OBJECT-TYPE
			SYNTAX Counter64
			MAX-ACCESS read-only
			STATUS current
			DESCRIPTION
				"PM_SLA1MINSTAT_DVMRESULTMIN"
			::= { pmSla1mStatEntry 22 }

		
		pmSla1mStatDvmResultMax OBJECT-TYPE
			SYNTAX Counter64
			MAX-ACCESS read-only
			STATUS current
			DESCRIPTION
				"PM_SLA1MINSTAT_DVMRESULTMAX"
			::= { pmSla1mStatEntry 23 }

		
		pmSla1mStatDvmResultCur OBJECT-TYPE
			SYNTAX Counter64
			MAX-ACCESS read-only
			STATUS current
			DESCRIPTION
				"PM_SLA1MINSTAT_DVMRESULTCUR"
			::= { pmSla1mStatEntry 24 }

		
		pmSla1mStatDmResultCur OBJECT-TYPE
			SYNTAX Counter64
			MAX-ACCESS read-only
			STATUS current
			DESCRIPTION
				"PM_SLA1MINSTAT_DMRESULTCUR"
			::= { pmSla1mStatEntry 25 }

		
		pmSla1mStatDmResultAvg OBJECT-TYPE
			SYNTAX Counter64
			MAX-ACCESS read-only
			STATUS current
			DESCRIPTION
				"PM_SLA1MINSTAT_DMRESULTAVG"
			::= { pmSla1mStatEntry 26 }

		
		pmSla1mStatDvmResultAvg OBJECT-TYPE
			SYNTAX Counter64
			MAX-ACCESS read-only
			STATUS current
			DESCRIPTION
				"PM_SLA1MINSTAT_DVMRESULTAVG"
			::= { pmSla1mStatEntry 27 }

		
		pmSla1mStatFarTxSum OBJECT-TYPE
			SYNTAX Unsigned32
			MAX-ACCESS read-only
			STATUS current
			DESCRIPTION
				"PM_SLA1MINSTAT_FARTXSUM"
			::= { pmSla1mStatEntry 28 }

		
		pmSla1mStatFarLossSum OBJECT-TYPE
			SYNTAX Unsigned32
			MAX-ACCESS read-only
			STATUS current
			DESCRIPTION
				"PM_SLA1MINSTAT_FARLOSSSUM"
			::= { pmSla1mStatEntry 29 }

		
		pmSla1mStatNearTxSum OBJECT-TYPE
			SYNTAX Unsigned32
			MAX-ACCESS read-only
			STATUS current
			DESCRIPTION
				"PM_SLA1MINSTAT_NEARTXSUM"
			::= { pmSla1mStatEntry 30 }

		
		pmSla1mStatNearLossSum OBJECT-TYPE
			SYNTAX Unsigned32
			MAX-ACCESS read-only
			STATUS current
			DESCRIPTION
				"PM_SLA1MINSTAT_NEARLOSSSUM"
			::= { pmSla1mStatEntry 31 }

		
		pmSla1mStatDelayTxTotal OBJECT-TYPE
			SYNTAX Unsigned32
			MAX-ACCESS read-only
			STATUS current
			DESCRIPTION
				"PM_SLA1MINSTAT_DELAYTXTOTAL"
			::= { pmSla1mStatEntry 32 }

		
		pmSla1mStatDmResultSum OBJECT-TYPE
			SYNTAX Counter64
			MAX-ACCESS read-only
			STATUS current
			DESCRIPTION
				"PM_SLA1MINSTAT_DMRESULTSUM"
			::= { pmSla1mStatEntry 33 }

		
		pmSla1mStatDvmResultSum OBJECT-TYPE
			SYNTAX Counter64
			MAX-ACCESS read-only
			STATUS current
			DESCRIPTION
				"PM_SLA1MINSTAT_DVMRESULTSUM"
			::= { pmSla1mStatEntry 34 }

		
		pmSla5mStatTable OBJECT-TYPE
			SYNTAX SEQUENCE OF PmSla5mStatEntry
			MAX-ACCESS not-accessible
			STATUS current
			DESCRIPTION
				"Description."
			::= { pmSlaPeriod 3 }

		
		pmSla5mStatEntry OBJECT-TYPE
			SYNTAX PmSla5mStatEntry
			MAX-ACCESS not-accessible
			STATUS current
			DESCRIPTION
				"Description."
			INDEX { pmSla5mStatMepId, pmSla5mStatMegIndex, pmSla5mStatRmepId, pmSla5mStatTimeStamp }
			::= { pmSla5mStatTable 1 }

		
		PmSla5mStatEntry ::=
			SEQUENCE { 
				pmSla5mStatMepId
					INTEGER,
				pmSla5mStatMegIndex
					INTEGER,
				pmSla5mStatRmepId
					INTEGER,
				pmSla5mStatTimeStamp
					Unsigned32,
				pmSla5mStatBinFlag
					INTEGER,
				pmSla5mStatFarMin
					Unsigned32,
				pmSla5mStatFarMax
					Unsigned32,
				pmSla5mStatFarCur
					Unsigned32,
				pmSla5mStatFarAvg
					Unsigned32,
				pmSla5mStatFarSum
					Unsigned32,
				pmSla5mStatNearMin
					Unsigned32,
				pmSla5mStatNearMax
					Unsigned32,
				pmSla5mStatNearCur
					Unsigned32,
				pmSla5mStatNearAvg
					Unsigned32,
				pmSla5mStatNearSum
					Unsigned32,
				pmSla5mStatLmrRecv
					Counter64,
				pmSla5mStatLmmSend
					Counter64,
				pmSla5mStatDmrRecv
					Counter64,
				pmSla5mStatDmmSend
					Counter64,
				pmSla5mStatDmResultMin
					Counter64,
				pmSla5mStatDmResultMax
					Counter64,
				pmSla5mStatDvmResultMin
					Counter64,
				pmSla5mStatDvmResultMax
					Counter64,
				pmSla5mStatDvmResultCur
					Counter64,
				pmSla5mStatDmResultCur
					Counter64,
				pmSla5mStatDmResultAvg
					Counter64,
				pmSla5mStatDvmResultAvg
					Counter64,
				pmSla5mStatFarTxSum
					Unsigned32,
				pmSla5mStatFarLossSum
					Unsigned32,
				pmSla5mStatNearTxSum
					Unsigned32,
				pmSla5mStatNearLossSum
					Unsigned32,
				pmSla5mStatDelayTxTotal
					Unsigned32,
				pmSla5mStatDmResultSum
					Counter64,
				pmSla5mStatDvmResultSum
					Counter64
			 }

		pmSla5mStatMepId OBJECT-TYPE
			SYNTAX INTEGER (1..8191)
			MAX-ACCESS read-only
			STATUS current
			DESCRIPTION
				"Description."
			::= { pmSla5mStatEntry 1 }

		
		pmSla5mStatMegIndex OBJECT-TYPE
			SYNTAX INTEGER (1..2147483647)
			MAX-ACCESS read-only
			STATUS current
			DESCRIPTION
				"Description."
			::= { pmSla5mStatEntry 2 }

		
		pmSla5mStatRmepId OBJECT-TYPE
			SYNTAX INTEGER (1..8191)
			MAX-ACCESS read-only
			STATUS current
			DESCRIPTION
				"Description."
			::= { pmSla5mStatEntry 3 }

		
		pmSla5mStatTimeStamp OBJECT-TYPE
			SYNTAX Unsigned32
			MAX-ACCESS read-only
			STATUS current
			DESCRIPTION
				"PM_SLA1MINSTAT_TIMESTAMP"
			::= { pmSla5mStatEntry 4 }

		
		pmSla5mStatBinFlag OBJECT-TYPE
			SYNTAX INTEGER
				{
				invalid(0),
				valid(1),
				partial(2)
				}
			MAX-ACCESS read-only
			STATUS current
			DESCRIPTION
				"PM_SLA1MINSTAT_BINFLAG"
			::= { pmSla5mStatEntry 5 }

		
		pmSla5mStatFarMin OBJECT-TYPE
			SYNTAX Unsigned32
			MAX-ACCESS read-only
			STATUS current
			DESCRIPTION
				"PM_SLA1MINSTAT_FARMIN"
			::= { pmSla5mStatEntry 6 }

		
		pmSla5mStatFarMax OBJECT-TYPE
			SYNTAX Unsigned32
			MAX-ACCESS read-only
			STATUS current
			DESCRIPTION
				"PM_SLA1MINSTAT_FARMAX"
			::= { pmSla5mStatEntry 7 }

		
		pmSla5mStatFarCur OBJECT-TYPE
			SYNTAX Unsigned32
			MAX-ACCESS read-only
			STATUS current
			DESCRIPTION
				"PM_SLA1MINSTAT_FARCUR"
			::= { pmSla5mStatEntry 8 }

		
		pmSla5mStatFarAvg OBJECT-TYPE
			SYNTAX Unsigned32
			MAX-ACCESS read-only
			STATUS current
			DESCRIPTION
				"PM_SLA1MINSTAT_FARAVG"
			::= { pmSla5mStatEntry 9 }

		
		pmSla5mStatFarSum OBJECT-TYPE
			SYNTAX Unsigned32
			MAX-ACCESS read-only
			STATUS current
			DESCRIPTION
				"PM_SLA1MINSTAT_FARSUM"
			::= { pmSla5mStatEntry 10 }

		
		pmSla5mStatNearMin OBJECT-TYPE
			SYNTAX Unsigned32
			MAX-ACCESS read-only
			STATUS current
			DESCRIPTION
				"PM_SLA1MINSTAT_NEARMIN"
			::= { pmSla5mStatEntry 11 }

		
		pmSla5mStatNearMax OBJECT-TYPE
			SYNTAX Unsigned32
			MAX-ACCESS read-only
			STATUS current
			DESCRIPTION
				"PM_SLA1MINSTAT_NEARMAX"
			::= { pmSla5mStatEntry 12 }

		
		pmSla5mStatNearCur OBJECT-TYPE
			SYNTAX Unsigned32
			MAX-ACCESS read-only
			STATUS current
			DESCRIPTION
				"PM_SLA1MINSTAT_NEARCUR"
			::= { pmSla5mStatEntry 13 }

		
		pmSla5mStatNearAvg OBJECT-TYPE
			SYNTAX Unsigned32
			MAX-ACCESS read-only
			STATUS current
			DESCRIPTION
				"PM_SLA1MINSTAT_NEARAVG"
			::= { pmSla5mStatEntry 14 }

		
		pmSla5mStatNearSum OBJECT-TYPE
			SYNTAX Unsigned32
			MAX-ACCESS read-only
			STATUS current
			DESCRIPTION
				"PM_SLA1MINSTAT_NEARSUM"
			::= { pmSla5mStatEntry 15 }

		
		pmSla5mStatLmrRecv OBJECT-TYPE
			SYNTAX Counter64
			MAX-ACCESS read-only
			STATUS current
			DESCRIPTION
				"PM_SLA1MINSTAT_LMRRECV"
			::= { pmSla5mStatEntry 16 }

		
		pmSla5mStatLmmSend OBJECT-TYPE
			SYNTAX Counter64
			MAX-ACCESS read-only
			STATUS current
			DESCRIPTION
				"PM_SLA1MINSTAT_LMMSEND"
			::= { pmSla5mStatEntry 17 }

		
		pmSla5mStatDmrRecv OBJECT-TYPE
			SYNTAX Counter64
			MAX-ACCESS read-only
			STATUS current
			DESCRIPTION
				"PM_SLA1MINSTAT_DMRRECV"
			::= { pmSla5mStatEntry 18 }

		
		pmSla5mStatDmmSend OBJECT-TYPE
			SYNTAX Counter64
			MAX-ACCESS read-only
			STATUS current
			DESCRIPTION
				"PM_SLA1MINSTAT_DMMSEND"
			::= { pmSla5mStatEntry 19 }

		
		pmSla5mStatDmResultMin OBJECT-TYPE
			SYNTAX Counter64
			MAX-ACCESS read-only
			STATUS current
			DESCRIPTION
				"PM_SLA1MINSTAT_DMRESULTMIN"
			::= { pmSla5mStatEntry 20 }

		
		pmSla5mStatDmResultMax OBJECT-TYPE
			SYNTAX Counter64
			MAX-ACCESS read-only
			STATUS current
			DESCRIPTION
				"PM_SLA1MINSTAT_DMRESULTMAX"
			::= { pmSla5mStatEntry 21 }

		
		pmSla5mStatDvmResultMin OBJECT-TYPE
			SYNTAX Counter64
			MAX-ACCESS read-only
			STATUS current
			DESCRIPTION
				"PM_SLA1MINSTAT_DVMRESULTMIN"
			::= { pmSla5mStatEntry 22 }

		
		pmSla5mStatDvmResultMax OBJECT-TYPE
			SYNTAX Counter64
			MAX-ACCESS read-only
			STATUS current
			DESCRIPTION
				"PM_SLA1MINSTAT_DVMRESULTMAX"
			::= { pmSla5mStatEntry 23 }

		
		pmSla5mStatDvmResultCur OBJECT-TYPE
			SYNTAX Counter64
			MAX-ACCESS read-only
			STATUS current
			DESCRIPTION
				"PM_SLA1MINSTAT_DVMRESULTCUR"
			::= { pmSla5mStatEntry 24 }

		
		pmSla5mStatDmResultCur OBJECT-TYPE
			SYNTAX Counter64
			MAX-ACCESS read-only
			STATUS current
			DESCRIPTION
				"PM_SLA1MINSTAT_DMRESULTCUR"
			::= { pmSla5mStatEntry 25 }

		
		pmSla5mStatDmResultAvg OBJECT-TYPE
			SYNTAX Counter64
			MAX-ACCESS read-only
			STATUS current
			DESCRIPTION
				"PM_SLA1MINSTAT_DMRESULTAVG"
			::= { pmSla5mStatEntry 26 }

		
		pmSla5mStatDvmResultAvg OBJECT-TYPE
			SYNTAX Counter64
			MAX-ACCESS read-only
			STATUS current
			DESCRIPTION
				"PM_SLA1MINSTAT_DVMRESULTAVG"
			::= { pmSla5mStatEntry 27 }

		
		pmSla5mStatFarTxSum OBJECT-TYPE
			SYNTAX Unsigned32
			MAX-ACCESS read-only
			STATUS current
			DESCRIPTION
				"PM_SLA1MINSTAT_FARTXSUM"
			::= { pmSla5mStatEntry 28 }

		
		pmSla5mStatFarLossSum OBJECT-TYPE
			SYNTAX Unsigned32
			MAX-ACCESS read-only
			STATUS current
			DESCRIPTION
				"PM_SLA1MINSTAT_FARLOSSSUM"
			::= { pmSla5mStatEntry 29 }

		
		pmSla5mStatNearTxSum OBJECT-TYPE
			SYNTAX Unsigned32
			MAX-ACCESS read-only
			STATUS current
			DESCRIPTION
				"PM_SLA1MINSTAT_NEARTXSUM"
			::= { pmSla5mStatEntry 30 }

		
		pmSla5mStatNearLossSum OBJECT-TYPE
			SYNTAX Unsigned32
			MAX-ACCESS read-only
			STATUS current
			DESCRIPTION
				"PM_SLA1MINSTAT_NEARLOSSSUM"
			::= { pmSla5mStatEntry 31 }

		
		pmSla5mStatDelayTxTotal OBJECT-TYPE
			SYNTAX Unsigned32
			MAX-ACCESS read-only
			STATUS current
			DESCRIPTION
				"PM_SLA1MINSTAT_DELAYTXTOTAL"
			::= { pmSla5mStatEntry 32 }

		
		pmSla5mStatDmResultSum OBJECT-TYPE
			SYNTAX Counter64
			MAX-ACCESS read-only
			STATUS current
			DESCRIPTION
				"PM_SLA1MINSTAT_DMRESULTSUM"
			::= { pmSla5mStatEntry 33 }

		
		pmSla5mStatDvmResultSum OBJECT-TYPE
			SYNTAX Counter64
			MAX-ACCESS read-only
			STATUS current
			DESCRIPTION
				"PM_SLA1MINSTAT_DVMRESULTSUM"
			::= { pmSla5mStatEntry 34 }

		
		pmSla15mStatTable OBJECT-TYPE
			SYNTAX SEQUENCE OF PmSla15mStatEntry
			MAX-ACCESS not-accessible
			STATUS current
			DESCRIPTION
				"Description."
			::= { pmSlaPeriod 4 }

		
		pmSla15mStatEntry OBJECT-TYPE
			SYNTAX PmSla15mStatEntry
			MAX-ACCESS not-accessible
			STATUS current
			DESCRIPTION
				"Description."
			INDEX { pmSla15mStatMepId, pmSla15mStatMegIndex, pmSla15mStatRmepId, pmSla15mStatTimeStamp }
			::= { pmSla15mStatTable 1 }

		
		PmSla15mStatEntry ::=
			SEQUENCE { 
				pmSla15mStatMepId
					INTEGER,
				pmSla15mStatMegIndex
					INTEGER,
				pmSla15mStatRmepId
					INTEGER,
				pmSla15mStatTimeStamp
					Unsigned32,
				pmSla15mStatBinFlag
					INTEGER,
				pmSla15mStatFarMin
					Unsigned32,
				pmSla15mStatFarMax
					Unsigned32,
				pmSla15mStatFarCur
					Unsigned32,
				pmSla15mStatFarAvg
					Unsigned32,
				pmSla15mStatFarSum
					Unsigned32,
				pmSla15mStatNearMin
					Unsigned32,
				pmSla15mStatNearMax
					Unsigned32,
				pmSla15mStatNearCur
					Unsigned32,
				pmSla15mStatNearAvg
					Unsigned32,
				pmSla15mStatNearSum
					Unsigned32,
				pmSla15mStatLmrRecv
					Counter64,
				pmSla15mStatLmmSend
					Counter64,
				pmSla15mStatDmrRecv
					Counter64,
				pmSla15mStatDmmSend
					Counter64,
				pmSla15mStatDmResultMin
					Counter64,
				pmSla15mStatDmResultMax
					Counter64,
				pmSla15mStatDvmResultMin
					Counter64,
				pmSla15mStatDvmResultMax
					Counter64,
				pmSla15mStatDvmResultCur
					Counter64,
				pmSla15mStatDmResultCur
					Counter64,
				pmSla15mStatDmResultAvg
					Counter64,
				pmSla15mStatDvmResultAvg
					Counter64,
				pmSla15mStatFarTxSum
					Unsigned32,
				pmSla15mStatFarLossSum
					Unsigned32,
				pmSla15mStatNearTxSum
					Unsigned32,
				pmSla15mStatNearLossSum
					Unsigned32,
				pmSla15mStatDelayTxTotal
					Unsigned32,
				pmSla15mStatDmResultSum
					Counter64,
				pmSla15mStatDvmResultSum
					Counter64
			 }

		pmSla15mStatMepId OBJECT-TYPE
			SYNTAX INTEGER (1..8191)
			MAX-ACCESS read-only
			STATUS current
			DESCRIPTION
				"Description."
			::= { pmSla15mStatEntry 1 }

		
		pmSla15mStatMegIndex OBJECT-TYPE
			SYNTAX INTEGER (1..2147483647)
			MAX-ACCESS read-only
			STATUS current
			DESCRIPTION
				"Description."
			::= { pmSla15mStatEntry 2 }

		
		pmSla15mStatRmepId OBJECT-TYPE
			SYNTAX INTEGER (1..8191)
			MAX-ACCESS read-only
			STATUS current
			DESCRIPTION
				"Description."
			::= { pmSla15mStatEntry 3 }

		
		pmSla15mStatTimeStamp OBJECT-TYPE
			SYNTAX Unsigned32
			MAX-ACCESS read-only
			STATUS current
			DESCRIPTION
				"PM_SLA15MINSTAT_TIMESTAMP"
			::= { pmSla15mStatEntry 4 }

		
		pmSla15mStatBinFlag OBJECT-TYPE
			SYNTAX INTEGER
				{
				invalid(0),
				valid(1),
				partial(2)
				}
			MAX-ACCESS read-only
			STATUS current
			DESCRIPTION
				"PM_SLA15MINSTAT_BINFLAG"
			::= { pmSla15mStatEntry 5 }

		
		pmSla15mStatFarMin OBJECT-TYPE
			SYNTAX Unsigned32
			MAX-ACCESS read-only
			STATUS current
			DESCRIPTION
				"PM_SLA15MINSTAT_FARMIN"
			::= { pmSla15mStatEntry 6 }

		
		pmSla15mStatFarMax OBJECT-TYPE
			SYNTAX Unsigned32
			MAX-ACCESS read-only
			STATUS current
			DESCRIPTION
				"PM_SLA15MINSTAT_FARMAX"
			::= { pmSla15mStatEntry 7 }

		
		pmSla15mStatFarCur OBJECT-TYPE
			SYNTAX Unsigned32
			MAX-ACCESS read-only
			STATUS current
			DESCRIPTION
				"PM_SLA15MINSTAT_FARCUR"
			::= { pmSla15mStatEntry 8 }

		
		pmSla15mStatFarAvg OBJECT-TYPE
			SYNTAX Unsigned32
			MAX-ACCESS read-only
			STATUS current
			DESCRIPTION
				"PM_SLA15MINSTAT_FARAVG"
			::= { pmSla15mStatEntry 9 }

		
		pmSla15mStatFarSum OBJECT-TYPE
			SYNTAX Unsigned32
			MAX-ACCESS read-only
			STATUS current
			DESCRIPTION
				"PM_SLA15MINSTAT_FARSUM"
			::= { pmSla15mStatEntry 10 }

		
		pmSla15mStatNearMin OBJECT-TYPE
			SYNTAX Unsigned32
			MAX-ACCESS read-only
			STATUS current
			DESCRIPTION
				"PM_SLA15MINSTAT_NEARMIN"
			::= { pmSla15mStatEntry 11 }

		
		pmSla15mStatNearMax OBJECT-TYPE
			SYNTAX Unsigned32
			MAX-ACCESS read-only
			STATUS current
			DESCRIPTION
				"PM_SLA15MINSTAT_NEARMAX"
			::= { pmSla15mStatEntry 12 }

		
		pmSla15mStatNearCur OBJECT-TYPE
			SYNTAX Unsigned32
			MAX-ACCESS read-only
			STATUS current
			DESCRIPTION
				"PM_SLA15MINSTAT_NEARCUR"
			::= { pmSla15mStatEntry 13 }

		
		pmSla15mStatNearAvg OBJECT-TYPE
			SYNTAX Unsigned32
			MAX-ACCESS read-only
			STATUS current
			DESCRIPTION
				"PM_SLA15MINSTAT_NEARAVG"
			::= { pmSla15mStatEntry 14 }

		
		pmSla15mStatNearSum OBJECT-TYPE
			SYNTAX Unsigned32
			MAX-ACCESS read-only
			STATUS current
			DESCRIPTION
				"PM_SLA15MINSTAT_NEARSUM"
			::= { pmSla15mStatEntry 15 }

		
		pmSla15mStatLmrRecv OBJECT-TYPE
			SYNTAX Counter64
			MAX-ACCESS read-only
			STATUS current
			DESCRIPTION
				"PM_SLA15MINSTAT_LMRRECV"
			::= { pmSla15mStatEntry 16 }

		
		pmSla15mStatLmmSend OBJECT-TYPE
			SYNTAX Counter64
			MAX-ACCESS read-only
			STATUS current
			DESCRIPTION
				"PM_SLA15MINSTAT_LMMSEND"
			::= { pmSla15mStatEntry 17 }

		
		pmSla15mStatDmrRecv OBJECT-TYPE
			SYNTAX Counter64
			MAX-ACCESS read-only
			STATUS current
			DESCRIPTION
				"PM_SLA15MINSTAT_DMRRECV"
			::= { pmSla15mStatEntry 18 }

		
		pmSla15mStatDmmSend OBJECT-TYPE
			SYNTAX Counter64
			MAX-ACCESS read-only
			STATUS current
			DESCRIPTION
				"PM_SLA15MINSTAT_DMMSEND"
			::= { pmSla15mStatEntry 19 }

		
		pmSla15mStatDmResultMin OBJECT-TYPE
			SYNTAX Counter64
			MAX-ACCESS read-only
			STATUS current
			DESCRIPTION
				"PM_SLA15MINSTAT_DMRESULTMIN"
			::= { pmSla15mStatEntry 20 }

		
		pmSla15mStatDmResultMax OBJECT-TYPE
			SYNTAX Counter64
			MAX-ACCESS read-only
			STATUS current
			DESCRIPTION
				"PM_SLA15MINSTAT_DMRESULTMAX"
			::= { pmSla15mStatEntry 21 }

		
		pmSla15mStatDvmResultMin OBJECT-TYPE
			SYNTAX Counter64
			MAX-ACCESS read-only
			STATUS current
			DESCRIPTION
				"PM_SLA15MINSTAT_DVMRESULTMIN"
			::= { pmSla15mStatEntry 22 }

		
		pmSla15mStatDvmResultMax OBJECT-TYPE
			SYNTAX Counter64
			MAX-ACCESS read-only
			STATUS current
			DESCRIPTION
				"PM_SLA15MINSTAT_DVMRESULTMAX"
			::= { pmSla15mStatEntry 23 }

		
		pmSla15mStatDvmResultCur OBJECT-TYPE
			SYNTAX Counter64
			MAX-ACCESS read-only
			STATUS current
			DESCRIPTION
				"PM_SLA15MINSTAT_DVMRESULTCUR"
			::= { pmSla15mStatEntry 24 }

		
		pmSla15mStatDmResultCur OBJECT-TYPE
			SYNTAX Counter64
			MAX-ACCESS read-only
			STATUS current
			DESCRIPTION
				"PM_SLA15MINSTAT_DMRESULTCUR"
			::= { pmSla15mStatEntry 25 }

		
		pmSla15mStatDmResultAvg OBJECT-TYPE
			SYNTAX Counter64
			MAX-ACCESS read-only
			STATUS current
			DESCRIPTION
				"PM_SLA15MINSTAT_DMRESULTAVG"
			::= { pmSla15mStatEntry 26 }

		
		pmSla15mStatDvmResultAvg OBJECT-TYPE
			SYNTAX Counter64
			MAX-ACCESS read-only
			STATUS current
			DESCRIPTION
				"PM_SLA15MINSTAT_DVMRESULTAVG"
			::= { pmSla15mStatEntry 27 }

		
		pmSla15mStatFarTxSum OBJECT-TYPE
			SYNTAX Unsigned32
			MAX-ACCESS read-only
			STATUS current
			DESCRIPTION
				"PM_SLA1MINSTAT_FARTXSUM"
			::= { pmSla15mStatEntry 28 }

		
		pmSla15mStatFarLossSum OBJECT-TYPE
			SYNTAX Unsigned32
			MAX-ACCESS read-only
			STATUS current
			DESCRIPTION
				"PM_SLA1MINSTAT_FARLOSSSUM"
			::= { pmSla15mStatEntry 29 }

		
		pmSla15mStatNearTxSum OBJECT-TYPE
			SYNTAX Unsigned32
			MAX-ACCESS read-only
			STATUS current
			DESCRIPTION
				"PM_SLA1MINSTAT_NEARTXSUM"
			::= { pmSla15mStatEntry 30 }

		
		pmSla15mStatNearLossSum OBJECT-TYPE
			SYNTAX Unsigned32
			MAX-ACCESS read-only
			STATUS current
			DESCRIPTION
				"PM_SLA1MINSTAT_NEARLOSSSUM"
			::= { pmSla15mStatEntry 31 }

		
		pmSla15mStatDelayTxTotal OBJECT-TYPE
			SYNTAX Unsigned32
			MAX-ACCESS read-only
			STATUS current
			DESCRIPTION
				"PM_SLA1MINSTAT_DELAYTXTOTAL"
			::= { pmSla15mStatEntry 32 }

		
		pmSla15mStatDmResultSum OBJECT-TYPE
			SYNTAX Counter64
			MAX-ACCESS read-only
			STATUS current
			DESCRIPTION
				"PM_SLA1MINSTAT_DMRESULTSUM"
			::= { pmSla15mStatEntry 33 }

		
		pmSla15mStatDvmResultSum OBJECT-TYPE
			SYNTAX Counter64
			MAX-ACCESS read-only
			STATUS current
			DESCRIPTION
				"PM_SLA1MINSTAT_DVMRESULTSUM"
			::= { pmSla15mStatEntry 34 }

		
		pmSla24hStatTable OBJECT-TYPE
			SYNTAX SEQUENCE OF PmSla24hStatEntry
			MAX-ACCESS not-accessible
			STATUS current
			DESCRIPTION
				"Description."
			::= { pmSlaPeriod 5 }

		
		pmSla24hStatEntry OBJECT-TYPE
			SYNTAX PmSla24hStatEntry
			MAX-ACCESS not-accessible
			STATUS current
			DESCRIPTION
				"Description."
			INDEX { pmSla24hStatMepId, pmSla24hStatMegIndex, pmSla24hStatRmepId, pmSla24hStatTimeStamp }
			::= { pmSla24hStatTable 1 }

		
		PmSla24hStatEntry ::=
			SEQUENCE { 
				pmSla24hStatMepId
					INTEGER,
				pmSla24hStatMegIndex
					INTEGER,
				pmSla24hStatRmepId
					INTEGER,
				pmSla24hStatTimeStamp
					Unsigned32,
				pmSla24hStatBinFlag
					INTEGER,
				pmSla24hStatFarMin
					Unsigned32,
				pmSla24hStatFarMax
					Unsigned32,
				pmSla24hStatFarCur
					Unsigned32,
				pmSla24hStatFarAvg
					Unsigned32,
				pmSla24hStatFarSum
					Unsigned32,
				pmSla24hStatNearMin
					Unsigned32,
				pmSla24hStatNearMax
					Unsigned32,
				pmSla24hStatNearCur
					Unsigned32,
				pmSla24hStatNearAvg
					Unsigned32,
				pmSla24hStatNearSum
					Unsigned32,
				pmSla24hStatLmrRecv
					Counter64,
				pmSla24hStatLmmSend
					Counter64,
				pmSla24hStatDmrRecv
					Counter64,
				pmSla24hStatDmmSend
					Counter64,
				pmSla24hStatDmResultMin
					Counter64,
				pmSla24hStatDmResultMax
					Counter64,
				pmSla24hStatDvmResultMin
					Counter64,
				pmSla24hStatDvmResultMax
					Counter64,
				pmSla24hStatDvmResultCur
					Counter64,
				pmSla24hStatDmResultCur
					Counter64,
				pmSla24hStatDmResultAvg
					Counter64,
				pmSla24hStatDvmResultAvg
					Counter64,
				pmSla24hStatFarTxSum
					Unsigned32,
				pmSla24hStatFarLossSum
					Unsigned32,
				pmSla24hStatNearTxSum
					Unsigned32,
				pmSla24hStatNearLossSum
					Unsigned32,
				pmSla24hStatDelayTxTotal
					Unsigned32,
				pmSla24hStatDmResultSum
					Counter64,
				pmSla24hStatDvmResultSum
					Counter64
			 }

		pmSla24hStatMepId OBJECT-TYPE
			SYNTAX INTEGER (1..8191)
			MAX-ACCESS read-only
			STATUS current
			DESCRIPTION
				"Description."
			::= { pmSla24hStatEntry 1 }

		
		pmSla24hStatMegIndex OBJECT-TYPE
			SYNTAX INTEGER (1..2147483647)
			MAX-ACCESS read-only
			STATUS current
			DESCRIPTION
				"Description."
			::= { pmSla24hStatEntry 2 }

		
		pmSla24hStatRmepId OBJECT-TYPE
			SYNTAX INTEGER (1..8191)
			MAX-ACCESS read-only
			STATUS current
			DESCRIPTION
				"Description."
			::= { pmSla24hStatEntry 3 }

		
		pmSla24hStatTimeStamp OBJECT-TYPE
			SYNTAX Unsigned32
			MAX-ACCESS read-only
			STATUS current
			DESCRIPTION
				"PM_SLA24HOURSTAT_TIMESTAMP"
			::= { pmSla24hStatEntry 4 }

		
		pmSla24hStatBinFlag OBJECT-TYPE
			SYNTAX INTEGER
				{
				invalid(0),
				valid(1),
				partial(2)
				}
			MAX-ACCESS read-only
			STATUS current
			DESCRIPTION
				"PM_SLA24HOURSTAT_BINFLAG"
			::= { pmSla24hStatEntry 5 }

		
		pmSla24hStatFarMin OBJECT-TYPE
			SYNTAX Unsigned32
			MAX-ACCESS read-only
			STATUS current
			DESCRIPTION
				"PM_SLA24HOURSTAT_FARMIN"
			::= { pmSla24hStatEntry 6 }

		
		pmSla24hStatFarMax OBJECT-TYPE
			SYNTAX Unsigned32
			MAX-ACCESS read-only
			STATUS current
			DESCRIPTION
				"PM_SLA24HOURSTAT_FARMAX"
			::= { pmSla24hStatEntry 7 }

		
		pmSla24hStatFarCur OBJECT-TYPE
			SYNTAX Unsigned32
			MAX-ACCESS read-only
			STATUS current
			DESCRIPTION
				"PM_SLA24HOURSTAT_FARCUR"
			::= { pmSla24hStatEntry 8 }

		
		pmSla24hStatFarAvg OBJECT-TYPE
			SYNTAX Unsigned32
			MAX-ACCESS read-only
			STATUS current
			DESCRIPTION
				"PM_SLA24HOURSTAT_FARAVG"
			::= { pmSla24hStatEntry 9 }

		
		pmSla24hStatFarSum OBJECT-TYPE
			SYNTAX Unsigned32
			MAX-ACCESS read-only
			STATUS current
			DESCRIPTION
				"PM_SLA24HOURSTAT_FARSUM"
			::= { pmSla24hStatEntry 10 }

		
		pmSla24hStatNearMin OBJECT-TYPE
			SYNTAX Unsigned32
			MAX-ACCESS read-only
			STATUS current
			DESCRIPTION
				"PM_SLA24HOURSTAT_NEARMIN"
			::= { pmSla24hStatEntry 11 }

		
		pmSla24hStatNearMax OBJECT-TYPE
			SYNTAX Unsigned32
			MAX-ACCESS read-only
			STATUS current
			DESCRIPTION
				"PM_SLA24HOURSTAT_NEARMAX"
			::= { pmSla24hStatEntry 12 }

		
		pmSla24hStatNearCur OBJECT-TYPE
			SYNTAX Unsigned32
			MAX-ACCESS read-only
			STATUS current
			DESCRIPTION
				"PM_SLA24HOURSTAT_NEARCUR"
			::= { pmSla24hStatEntry 13 }

		
		pmSla24hStatNearAvg OBJECT-TYPE
			SYNTAX Unsigned32
			MAX-ACCESS read-only
			STATUS current
			DESCRIPTION
				"PM_SLA24HOURSTAT_NEARAVG"
			::= { pmSla24hStatEntry 14 }

		
		pmSla24hStatNearSum OBJECT-TYPE
			SYNTAX Unsigned32
			MAX-ACCESS read-only
			STATUS current
			DESCRIPTION
				"PM_SLA24HOURSTAT_NEARSUM"
			::= { pmSla24hStatEntry 15 }

		
		pmSla24hStatLmrRecv OBJECT-TYPE
			SYNTAX Counter64
			MAX-ACCESS read-only
			STATUS current
			DESCRIPTION
				"PM_SLA24HOURSTAT_LMRRECV"
			::= { pmSla24hStatEntry 16 }

		
		pmSla24hStatLmmSend OBJECT-TYPE
			SYNTAX Counter64
			MAX-ACCESS read-only
			STATUS current
			DESCRIPTION
				"PM_SLA24HOURSTAT_LMMSEND"
			::= { pmSla24hStatEntry 17 }

		
		pmSla24hStatDmrRecv OBJECT-TYPE
			SYNTAX Counter64
			MAX-ACCESS read-only
			STATUS current
			DESCRIPTION
				"PM_SLA24HOURSTAT_DMRRECV"
			::= { pmSla24hStatEntry 18 }

		
		pmSla24hStatDmmSend OBJECT-TYPE
			SYNTAX Counter64
			MAX-ACCESS read-only
			STATUS current
			DESCRIPTION
				"PM_SLA24HOURSTAT_DMMSEND"
			::= { pmSla24hStatEntry 19 }

		
		pmSla24hStatDmResultMin OBJECT-TYPE
			SYNTAX Counter64
			MAX-ACCESS read-only
			STATUS current
			DESCRIPTION
				"PM_SLA24HOURSTAT_DMRESULTMIN"
			::= { pmSla24hStatEntry 20 }

		
		pmSla24hStatDmResultMax OBJECT-TYPE
			SYNTAX Counter64
			MAX-ACCESS read-only
			STATUS current
			DESCRIPTION
				"PM_SLA24HOURSTAT_DMRESULTMAX"
			::= { pmSla24hStatEntry 21 }

		
		pmSla24hStatDvmResultMin OBJECT-TYPE
			SYNTAX Counter64
			MAX-ACCESS read-only
			STATUS current
			DESCRIPTION
				"PM_SLA24HOURSTAT_DVMRESULTMIN"
			::= { pmSla24hStatEntry 22 }

		
		pmSla24hStatDvmResultMax OBJECT-TYPE
			SYNTAX Counter64
			MAX-ACCESS read-only
			STATUS current
			DESCRIPTION
				"PM_SLA24HOURSTAT_DVMRESULTMAX"
			::= { pmSla24hStatEntry 23 }

		
		pmSla24hStatDvmResultCur OBJECT-TYPE
			SYNTAX Counter64
			MAX-ACCESS read-only
			STATUS current
			DESCRIPTION
				"PM_SLA24HOURSTAT_DVMRESULTCUR"
			::= { pmSla24hStatEntry 24 }

		
		pmSla24hStatDmResultCur OBJECT-TYPE
			SYNTAX Counter64
			MAX-ACCESS read-only
			STATUS current
			DESCRIPTION
				"PM_SLA24HOURSTAT_DMRESULTCUR"
			::= { pmSla24hStatEntry 25 }

		
		pmSla24hStatDmResultAvg OBJECT-TYPE
			SYNTAX Counter64
			MAX-ACCESS read-only
			STATUS current
			DESCRIPTION
				"PM_SLA24HOURSTAT_DMRESULTAVG"
			::= { pmSla24hStatEntry 26 }

		
		pmSla24hStatDvmResultAvg OBJECT-TYPE
			SYNTAX Counter64
			MAX-ACCESS read-only
			STATUS current
			DESCRIPTION
				"PM_SLA24HOURSTAT_DVMRESULTAVG"
			::= { pmSla24hStatEntry 27 }

		
		pmSla24hStatFarTxSum OBJECT-TYPE
			SYNTAX Unsigned32
			MAX-ACCESS read-only
			STATUS current
			DESCRIPTION
				"PM_SLA1MINSTAT_FARTXSUM"
			::= { pmSla24hStatEntry 28 }

		
		pmSla24hStatFarLossSum OBJECT-TYPE
			SYNTAX Unsigned32
			MAX-ACCESS read-only
			STATUS current
			DESCRIPTION
				"PM_SLA1MINSTAT_FARLOSSSUM"
			::= { pmSla24hStatEntry 29 }

		
		pmSla24hStatNearTxSum OBJECT-TYPE
			SYNTAX Unsigned32
			MAX-ACCESS read-only
			STATUS current
			DESCRIPTION
				"PM_SLA1MINSTAT_NEARTXSUM"
			::= { pmSla24hStatEntry 30 }

		
		pmSla24hStatNearLossSum OBJECT-TYPE
			SYNTAX Unsigned32
			MAX-ACCESS read-only
			STATUS current
			DESCRIPTION
				"PM_SLA1MINSTAT_NEARLOSSSUM"
			::= { pmSla24hStatEntry 31 }

		
		pmSla24hStatDelayTxTotal OBJECT-TYPE
			SYNTAX Unsigned32
			MAX-ACCESS read-only
			STATUS current
			DESCRIPTION
				"PM_SLA1MINSTAT_DELAYTXTOTAL"
			::= { pmSla24hStatEntry 32 }

		
		pmSla24hStatDmResultSum OBJECT-TYPE
			SYNTAX Counter64
			MAX-ACCESS read-only
			STATUS current
			DESCRIPTION
				"PM_SLA1MINSTAT_DMRESULTSUM"
			::= { pmSla24hStatEntry 33 }

		
		pmSla24hStatDvmResultSum OBJECT-TYPE
			SYNTAX Counter64
			MAX-ACCESS read-only
			STATUS current
			DESCRIPTION
				"PM_SLA1MINSTAT_DVMRESULTSUM"
			::= { pmSla24hStatEntry 34 }


		pmSlaCurrentTable OBJECT-TYPE
			SYNTAX SEQUENCE OF PmSlaCurrentEntry
			MAX-ACCESS not-accessible
			STATUS current
			DESCRIPTION
				"Description."
			::= { pmSlaPeriod 6 }

		
		pmSlaCurrentEntry OBJECT-TYPE
			SYNTAX PmSlaCurrentEntry
			MAX-ACCESS not-accessible
			STATUS current
			DESCRIPTION
				"Description."
			INDEX { pmSlaCurrentMegIndex, pmSlaCurrentMepId, pmSlaCurrentRmepId }
			::= { pmSlaCurrentTable 1 }

		
		PmSlaCurrentEntry ::=
			SEQUENCE { 
				pmSlaCurrentMegIndex
					INTEGER,			
				pmSlaCurrentMepId
					INTEGER,
				pmSlaCurrentRmepId
					INTEGER,
				pmSlaCurrentStartTime
					Unsigned32,
				pmSlaCurrentEndTime
					Unsigned32,					
				pmSlaCurrentBinFlag
					INTEGER,
				pmSlaCurrentFarMin
					Unsigned32,
				pmSlaCurrentFarMax
					Unsigned32,
				pmSlaCurrentFarCur
					Unsigned32,
				pmSlaCurrentFarAvg
					Unsigned32,
				pmSlaCurrentFarSum
					Unsigned32,
				pmSlaCurrentNearMin
					Unsigned32,
				pmSlaCurrentNearMax
					Unsigned32,
				pmSlaCurrentNearCur
					Unsigned32,
				pmSlaCurrentNearAvg
					Unsigned32,
				pmSlaCurrentNearSum
					Unsigned32,
				pmSlaCurrentDmResultMin
					Counter64,
				pmSlaCurrentDmResultMax
					Counter64,
				pmSlaCurrentDvmResultMin
					Counter64,
				pmSlaCurrentDvmResultMax
					Counter64,
				pmSlaCurrentDvmResultCur
					Counter64,
				pmSlaCurrentDmResultCur
					Counter64,
				pmSlaCurrentDmResultAvg
					Counter64,
				pmSlaCurrentDvmResultAvg
					Counter64,
				pmSlaCurrentFarTxSum
					Unsigned32,
				pmSlaCurrentFarLossSum
					Unsigned32,
				pmSlaCurrentNearTxSum
					Unsigned32,
				pmSlaCurrentNearLossSum
					Unsigned32,
				pmSlaCurrentDelayTxTotal
					Unsigned32,
				pmSlaCurrentDmResultSum
					Counter64,
				pmSlaCurrentDvmResultSum
					Counter64
			 }

		pmSlaCurrentMegIndex OBJECT-TYPE
			SYNTAX INTEGER (1..2147483647)
			MAX-ACCESS read-only
			STATUS current
			DESCRIPTION
				"Description."
			::= { pmSlaCurrentEntry 1 }

		
		pmSlaCurrentMepId OBJECT-TYPE
			SYNTAX INTEGER (1..8191)
			MAX-ACCESS read-only
			STATUS current
			DESCRIPTION
				"Description."
			::= { pmSlaCurrentEntry 2 }

		
		pmSlaCurrentRmepId OBJECT-TYPE
			SYNTAX INTEGER (1..8191)
			MAX-ACCESS read-only
			STATUS current
			DESCRIPTION
				"Description."
			::= { pmSlaCurrentEntry 3 }

		
		pmSlaCurrentStartTime OBJECT-TYPE
			SYNTAX Unsigned32
			MAX-ACCESS read-only
			STATUS current
			DESCRIPTION
				"PM_SLACURRENT_STARTTIME"
			::= { pmSlaCurrentEntry 4 }


		pmSlaCurrentEndTime OBJECT-TYPE
			SYNTAX Unsigned32
			MAX-ACCESS read-only
			STATUS current
			DESCRIPTION
				"PM_SLACURRENT_ENDTIME"
			::= { pmSlaCurrentEntry 5 }

		
		pmSlaCurrentBinFlag OBJECT-TYPE
			SYNTAX INTEGER
				{
				invalid(0),
				valid(1),
				partial(2)
				}
			MAX-ACCESS read-only
			STATUS current
			DESCRIPTION
				"PM_SLACURRENT_BINFLAG"
			::= { pmSlaCurrentEntry 6 }

		
		pmSlaCurrentFarMin OBJECT-TYPE
			SYNTAX Unsigned32
			MAX-ACCESS read-only
			STATUS current
			DESCRIPTION
				"PM_SLACURRENT_FARMIN"
			::= { pmSlaCurrentEntry 7 }

		
		pmSlaCurrentFarMax OBJECT-TYPE
			SYNTAX Unsigned32
			MAX-ACCESS read-only
			STATUS current
			DESCRIPTION
				"PM_SLACURRENT_FARMAX"
			::= { pmSlaCurrentEntry 8 }

		
		pmSlaCurrentFarCur OBJECT-TYPE
			SYNTAX Unsigned32
			MAX-ACCESS read-only
			STATUS current
			DESCRIPTION
				"PM_SLACURRENT_FARCUR"
			::= { pmSlaCurrentEntry 9 }

		
		pmSlaCurrentFarAvg OBJECT-TYPE
			SYNTAX Unsigned32
			MAX-ACCESS read-only
			STATUS current
			DESCRIPTION
				"PM_SLACURRENT_FARAVG"
			::= { pmSlaCurrentEntry 10 }

		
		pmSlaCurrentFarSum OBJECT-TYPE
			SYNTAX Unsigned32
			MAX-ACCESS read-only
			STATUS current
			DESCRIPTION
				"PM_SLACURRENT_FARSUM"
			::= { pmSlaCurrentEntry 11 }

		
		pmSlaCurrentNearMin OBJECT-TYPE
			SYNTAX Unsigned32
			MAX-ACCESS read-only
			STATUS current
			DESCRIPTION
				"PM_SLACURRENT_NEARMIN"
			::= { pmSlaCurrentEntry 12 }

		
		pmSlaCurrentNearMax OBJECT-TYPE
			SYNTAX Unsigned32
			MAX-ACCESS read-only
			STATUS current
			DESCRIPTION
				"PM_SLACURRENT_NEARMAX"
			::= { pmSlaCurrentEntry 13 }

		
		pmSlaCurrentNearCur OBJECT-TYPE
			SYNTAX Unsigned32
			MAX-ACCESS read-only
			STATUS current
			DESCRIPTION
				"PM_SLACURRENT_NEARCUR"
			::= { pmSlaCurrentEntry 14 }

		
		pmSlaCurrentNearAvg OBJECT-TYPE
			SYNTAX Unsigned32
			MAX-ACCESS read-only
			STATUS current
			DESCRIPTION
				"PM_SLACURRENT_NEARAVG"
			::= { pmSlaCurrentEntry 15 }

		
		pmSlaCurrentNearSum OBJECT-TYPE
			SYNTAX Unsigned32
			MAX-ACCESS read-only
			STATUS current
			DESCRIPTION
				"PM_SLACURRENT_NEARSUM"
			::= { pmSlaCurrentEntry 16 }

		
		pmSlaCurrentDmResultMin OBJECT-TYPE
			SYNTAX Counter64
			MAX-ACCESS read-only
			STATUS current
			DESCRIPTION
				"PM_SLACURRENT_DMRESULTMIN"
			::= { pmSlaCurrentEntry 17 }

		
		pmSlaCurrentDmResultMax OBJECT-TYPE
			SYNTAX Counter64
			MAX-ACCESS read-only
			STATUS current
			DESCRIPTION
				"PM_SLACURRENT_DMRESULTMAX"
			::= { pmSlaCurrentEntry 18 }

		
		pmSlaCurrentDvmResultMin OBJECT-TYPE
			SYNTAX Counter64
			MAX-ACCESS read-only
			STATUS current
			DESCRIPTION
				"PM_SLACURRENT_DVMRESULTMIN"
			::= { pmSlaCurrentEntry 19 }

		
		pmSlaCurrentDvmResultMax OBJECT-TYPE
			SYNTAX Counter64
			MAX-ACCESS read-only
			STATUS current
			DESCRIPTION
				"PM_SLACURRENT_DVMRESULTMAX"
			::= { pmSlaCurrentEntry 20 }

		
		pmSlaCurrentDvmResultCur OBJECT-TYPE
			SYNTAX Counter64
			MAX-ACCESS read-only
			STATUS current
			DESCRIPTION
				"PM_SLACURRENT_DVMRESULTCUR"
			::= { pmSlaCurrentEntry 21 }

		
		pmSlaCurrentDmResultCur OBJECT-TYPE
			SYNTAX Counter64
			MAX-ACCESS read-only
			STATUS current
			DESCRIPTION
				"PM_SLACURRENT_DMRESULTCUR"
			::= { pmSlaCurrentEntry 22 }

		
		pmSlaCurrentDmResultAvg OBJECT-TYPE
			SYNTAX Counter64
			MAX-ACCESS read-only
			STATUS current
			DESCRIPTION
				"PM_SLACURRENT_DMRESULTAVG"
			::= { pmSlaCurrentEntry 23 }

		
		pmSlaCurrentDvmResultAvg OBJECT-TYPE
			SYNTAX Counter64
			MAX-ACCESS read-only
			STATUS current
			DESCRIPTION
				"PM_SLACURRENT_DVMRESULTAVG"
			::= { pmSlaCurrentEntry 24 }

		
		pmSlaCurrentFarTxSum OBJECT-TYPE
			SYNTAX Unsigned32
			MAX-ACCESS read-only
			STATUS current
			DESCRIPTION
				"PM_SLACURRENT_FARTXSUM"
			::= { pmSlaCurrentEntry 25 }

		
		pmSlaCurrentFarLossSum OBJECT-TYPE
			SYNTAX Unsigned32
			MAX-ACCESS read-only
			STATUS current
			DESCRIPTION
				"PM_SLACURRENT_FARLOSSSUM"
			::= { pmSlaCurrentEntry 26 }

		
		pmSlaCurrentNearTxSum OBJECT-TYPE
			SYNTAX Unsigned32
			MAX-ACCESS read-only
			STATUS current
			DESCRIPTION
				"PM_SLACURRENT_NEARTXSUM"
			::= { pmSlaCurrentEntry 27 }

		
		pmSlaCurrentNearLossSum OBJECT-TYPE
			SYNTAX Unsigned32
			MAX-ACCESS read-only
			STATUS current
			DESCRIPTION
				"PM_SLACURRENT_NEARLOSSSUM"
			::= { pmSlaCurrentEntry 28 }

		
		pmSlaCurrentDelayTxTotal OBJECT-TYPE
			SYNTAX Unsigned32
			MAX-ACCESS read-only
			STATUS current
			DESCRIPTION
				"PM_SLACURRENT_DELAYTXTOTAL"
			::= { pmSlaCurrentEntry 29 }

		
		pmSlaCurrentDmResultSum OBJECT-TYPE
			SYNTAX Counter64
			MAX-ACCESS read-only
			STATUS current
			DESCRIPTION
				"PM_SLACURRENT_DMRESULTSUM"
			::= { pmSlaCurrentEntry 30 }

		
		pmSlaCurrentDvmResultSum OBJECT-TYPE
			SYNTAX Counter64
			MAX-ACCESS read-only
			STATUS current
			DESCRIPTION
				"PM_SLACURRENT_DVMRESULTSUM"
			::= { pmSlaCurrentEntry 31 }


		pmSlaUnTimedTable OBJECT-TYPE
			SYNTAX SEQUENCE OF PmSlaUnTimedEntry
			MAX-ACCESS not-accessible
			STATUS current
			DESCRIPTION
				"Description."
			::= { pmSlaPeriod 7 }

		
		pmSlaUnTimedEntry OBJECT-TYPE
			SYNTAX PmSlaUnTimedEntry
			MAX-ACCESS not-accessible
			STATUS current
			DESCRIPTION
				"Description."
			INDEX { pmSlaUnTimedMegIndex, pmSlaUnTimedMepId, pmSlaUnTimedRmepId }
			::= { pmSlaUnTimedTable 1 }

		
		PmSlaUnTimedEntry ::=
			SEQUENCE { 
				pmSlaUnTimedMegIndex
					INTEGER,			
				pmSlaUnTimedMepId
					INTEGER,
				pmSlaUnTimedRmepId
					INTEGER,
				pmSlaUnTimedStartTime
					Unsigned32,
				pmSlaUnTimedEndTime
					Unsigned32,					
				pmSlaUnTimedBinFlag
					INTEGER,
				pmSlaUnTimedFarMin
					Unsigned32,
				pmSlaUnTimedFarMax
					Unsigned32,
				pmSlaUnTimedFarCur
					Unsigned32,
				pmSlaUnTimedFarAvg
					Unsigned32,
				pmSlaUnTimedFarSum
					Unsigned32,
				pmSlaUnTimedNearMin
					Unsigned32,
				pmSlaUnTimedNearMax
					Unsigned32,
				pmSlaUnTimedNearCur
					Unsigned32,
				pmSlaUnTimedNearAvg
					Unsigned32,
				pmSlaUnTimedNearSum
					Unsigned32,
				pmSlaUnTimedDmResultMin
					Counter64,
				pmSlaUnTimedDmResultMax
					Counter64,
				pmSlaUnTimedDvmResultMin
					Counter64,
				pmSlaUnTimedDvmResultMax
					Counter64,
				pmSlaUnTimedDvmResultCur
					Counter64,
				pmSlaUnTimedDmResultCur
					Counter64,
				pmSlaUnTimedDmResultAvg
					Counter64,
				pmSlaUnTimedDvmResultAvg
					Counter64,
				pmSlaUnTimedFarTxSum
					Unsigned32,
				pmSlaUnTimedFarLossSum
					Unsigned32,
				pmSlaUnTimedNearTxSum
					Unsigned32,
				pmSlaUnTimedNearLossSum
					Unsigned32,
				pmSlaUnTimedDelayTxTotal
					Unsigned32,
				pmSlaUnTimedDmResultSum
					Counter64,
				pmSlaUnTimedDvmResultSum
					Counter64
			 }

		pmSlaUnTimedMegIndex OBJECT-TYPE
			SYNTAX INTEGER (1..2147483647)
			MAX-ACCESS read-only
			STATUS current
			DESCRIPTION
				"Description."
			::= { pmSlaUnTimedEntry 1 }

		
		pmSlaUnTimedMepId OBJECT-TYPE
			SYNTAX INTEGER (1..8191)
			MAX-ACCESS read-only
			STATUS current
			DESCRIPTION
				"Description."
			::= { pmSlaUnTimedEntry 2 }

		
		pmSlaUnTimedRmepId OBJECT-TYPE
			SYNTAX INTEGER (1..8191)
			MAX-ACCESS read-only
			STATUS current
			DESCRIPTION
				"Description."
			::= { pmSlaUnTimedEntry 3 }

		
		pmSlaUnTimedStartTime OBJECT-TYPE
			SYNTAX Unsigned32
			MAX-ACCESS read-only
			STATUS current
			DESCRIPTION
				"PM_SLAUNTIMED_STARTTIME"
			::= { pmSlaUnTimedEntry 4 }


		pmSlaUnTimedEndTime OBJECT-TYPE
			SYNTAX Unsigned32
			MAX-ACCESS read-only
			STATUS current
			DESCRIPTION
				"PM_SLAUNTIMED_ENDTIME"
			::= { pmSlaUnTimedEntry 5 }

		
		pmSlaUnTimedBinFlag OBJECT-TYPE
			SYNTAX INTEGER
				{
				invalid(0),
				valid(1),
				partial(2)
				}
			MAX-ACCESS read-only
			STATUS current
			DESCRIPTION
				"PM_SLAUNTIMED_BINFLAG"
			::= { pmSlaUnTimedEntry 6 }

		
		pmSlaUnTimedFarMin OBJECT-TYPE
			SYNTAX Unsigned32
			MAX-ACCESS read-only
			STATUS current
			DESCRIPTION
				"PM_SLAUNTIMED_FARMIN"
			::= { pmSlaUnTimedEntry 7 }

		
		pmSlaUnTimedFarMax OBJECT-TYPE
			SYNTAX Unsigned32
			MAX-ACCESS read-only
			STATUS current
			DESCRIPTION
				"PM_SLAUNTIMED_FARMAX"
			::= { pmSlaUnTimedEntry 8 }

		
		pmSlaUnTimedFarCur OBJECT-TYPE
			SYNTAX Unsigned32
			MAX-ACCESS read-only
			STATUS current
			DESCRIPTION
				"PM_SLAUNTIMED_FARCUR"
			::= { pmSlaUnTimedEntry 9 }

		
		pmSlaUnTimedFarAvg OBJECT-TYPE
			SYNTAX Unsigned32
			MAX-ACCESS read-only
			STATUS current
			DESCRIPTION
				"PM_SLAUNTIMED_FARAVG"
			::= { pmSlaUnTimedEntry 10 }

		
		pmSlaUnTimedFarSum OBJECT-TYPE
			SYNTAX Unsigned32
			MAX-ACCESS read-only
			STATUS current
			DESCRIPTION
				"PM_SLAUNTIMED_FARSUM"
			::= { pmSlaUnTimedEntry 11 }

		
		pmSlaUnTimedNearMin OBJECT-TYPE
			SYNTAX Unsigned32
			MAX-ACCESS read-only
			STATUS current
			DESCRIPTION
				"PM_SLAUNTIMED_NEARMIN"
			::= { pmSlaUnTimedEntry 12 }

		
		pmSlaUnTimedNearMax OBJECT-TYPE
			SYNTAX Unsigned32
			MAX-ACCESS read-only
			STATUS current
			DESCRIPTION
				"PM_SLAUNTIMED_NEARMAX"
			::= { pmSlaUnTimedEntry 13 }

		
		pmSlaUnTimedNearCur OBJECT-TYPE
			SYNTAX Unsigned32
			MAX-ACCESS read-only
			STATUS current
			DESCRIPTION
				"PM_SLAUNTIMED_NEARCUR"
			::= { pmSlaUnTimedEntry 14 }

		
		pmSlaUnTimedNearAvg OBJECT-TYPE
			SYNTAX Unsigned32
			MAX-ACCESS read-only
			STATUS current
			DESCRIPTION
				"PM_SLAUNTIMED_NEARAVG"
			::= { pmSlaUnTimedEntry 15 }

		
		pmSlaUnTimedNearSum OBJECT-TYPE
			SYNTAX Unsigned32
			MAX-ACCESS read-only
			STATUS current
			DESCRIPTION
				"PM_SLAUNTIMED_NEARSUM"
			::= { pmSlaUnTimedEntry 16 }

		
		pmSlaUnTimedDmResultMin OBJECT-TYPE
			SYNTAX Counter64
			MAX-ACCESS read-only
			STATUS current
			DESCRIPTION
				"PM_SLAUNTIMED_DMRESULTMIN"
			::= { pmSlaUnTimedEntry 17 }

		
		pmSlaUnTimedDmResultMax OBJECT-TYPE
			SYNTAX Counter64
			MAX-ACCESS read-only
			STATUS current
			DESCRIPTION
				"PM_SLAUNTIMED_DMRESULTMAX"
			::= { pmSlaUnTimedEntry 18 }

		
		pmSlaUnTimedDvmResultMin OBJECT-TYPE
			SYNTAX Counter64
			MAX-ACCESS read-only
			STATUS current
			DESCRIPTION
				"PM_SLAUNTIMED_DVMRESULTMIN"
			::= { pmSlaUnTimedEntry 19 }

		
		pmSlaUnTimedDvmResultMax OBJECT-TYPE
			SYNTAX Counter64
			MAX-ACCESS read-only
			STATUS current
			DESCRIPTION
				"PM_SLAUNTIMED_DVMRESULTMAX"
			::= { pmSlaUnTimedEntry 20 }

		
		pmSlaUnTimedDvmResultCur OBJECT-TYPE
			SYNTAX Counter64
			MAX-ACCESS read-only
			STATUS current
			DESCRIPTION
				"PM_SLAUNTIMED_DVMRESULTCUR"
			::= { pmSlaUnTimedEntry 21 }

		
		pmSlaUnTimedDmResultCur OBJECT-TYPE
			SYNTAX Counter64
			MAX-ACCESS read-only
			STATUS current
			DESCRIPTION
				"PM_SLAUNTIMED_DMRESULTCUR"
			::= { pmSlaUnTimedEntry 22 }

		
		pmSlaUnTimedDmResultAvg OBJECT-TYPE
			SYNTAX Counter64
			MAX-ACCESS read-only
			STATUS current
			DESCRIPTION
				"PM_SLAUNTIMED_DMRESULTAVG"
			::= { pmSlaUnTimedEntry 23 }

		
		pmSlaUnTimedDvmResultAvg OBJECT-TYPE
			SYNTAX Counter64
			MAX-ACCESS read-only
			STATUS current
			DESCRIPTION
				"PM_SLAUNTIMED_DVMRESULTAVG"
			::= { pmSlaUnTimedEntry 24 }

		
		pmSlaUnTimedFarTxSum OBJECT-TYPE
			SYNTAX Unsigned32
			MAX-ACCESS read-only
			STATUS current
			DESCRIPTION
				"PM_SLAUNTIMED_FARTXSUM"
			::= { pmSlaUnTimedEntry 25 }

		
		pmSlaUnTimedFarLossSum OBJECT-TYPE
			SYNTAX Unsigned32
			MAX-ACCESS read-only
			STATUS current
			DESCRIPTION
				"PM_SLAUNTIMED_FARLOSSSUM"
			::= { pmSlaUnTimedEntry 26 }

		
		pmSlaUnTimedNearTxSum OBJECT-TYPE
			SYNTAX Unsigned32
			MAX-ACCESS read-only
			STATUS current
			DESCRIPTION
				"PM_SLAUNTIMED_NEARTXSUM"
			::= { pmSlaUnTimedEntry 27 }

		
		pmSlaUnTimedNearLossSum OBJECT-TYPE
			SYNTAX Unsigned32
			MAX-ACCESS read-only
			STATUS current
			DESCRIPTION
				"PM_SLAUNTIMED_NEARLOSSSUM"
			::= { pmSlaUnTimedEntry 28 }

		
		pmSlaUnTimedDelayTxTotal OBJECT-TYPE
			SYNTAX Unsigned32
			MAX-ACCESS read-only
			STATUS current
			DESCRIPTION
				"PM_SLAUNTIMED_DELAYTXTOTAL"
			::= { pmSlaUnTimedEntry 29 }

		
		pmSlaUnTimedDmResultSum OBJECT-TYPE
			SYNTAX Counter64
			MAX-ACCESS read-only
			STATUS current
			DESCRIPTION
				"PM_SLAUNTIMED_DMRESULTSUM"
			::= { pmSlaUnTimedEntry 30 }

		
		pmSlaUnTimedDvmResultSum OBJECT-TYPE
			SYNTAX Counter64
			MAX-ACCESS read-only
			STATUS current
			DESCRIPTION
				"PM_SLAUNTIMED_DVMRESULTSUM"
			::= { pmSlaUnTimedEntry 31 }

		
		pmRmep OBJECT IDENTIFIER ::= { pm 4 }

		
		pmRmepTable OBJECT-TYPE
			SYNTAX SEQUENCE OF PmRmepEntry
			MAX-ACCESS not-accessible
			STATUS current
			DESCRIPTION
				"Description."
			::= { pmRmep 1 }

		
		pmRmepEntry OBJECT-TYPE
			SYNTAX PmRmepEntry
			MAX-ACCESS not-accessible
			STATUS current
			DESCRIPTION
				"Description."
			INDEX { pmMepId, pmRmepId, pmMegIndex }
			::= { pmRmepTable 1 }

		
		PmRmepEntry ::=
			SEQUENCE { 
				pmMepId
					INTEGER,
				pmRmepId
					INTEGER,
				pmMegIndex
					INTEGER,
				pmRmepEntryStatus
					INTEGER,
				pmRmepType
					INTEGER,
				pmRmepCcStatus
					INTEGER,
				pmRmepSlaStatus
					INTEGER,
				pmRmepStartTime
					Unsigned32,
				pmRmepPriority
					INTEGER,
				pmRmepLmFrequency
					INTEGER,
				pmRmepDmFrequency
					INTEGER,
				pmRmepDstMac
					OCTET STRING,
				pmRmepStatClear
					INTEGER
			 }

		pmMepId OBJECT-TYPE
			SYNTAX INTEGER (1..8191)
			MAX-ACCESS read-only
			STATUS current
			DESCRIPTION
				"Description."
			::= { pmRmepEntry 1 }

		
		pmRmepId OBJECT-TYPE
			SYNTAX INTEGER (1..8191)
			MAX-ACCESS read-only
			STATUS current
			DESCRIPTION
				"PM_RMEP_ID"
			::= { pmRmepEntry 2 }

		
		pmMegIndex OBJECT-TYPE
			SYNTAX INTEGER (1..2147483647)
			MAX-ACCESS read-write
			STATUS current
			DESCRIPTION
				"Description."
			::= { pmRmepEntry 3 }

		
		pmRmepEntryStatus OBJECT-TYPE
			SYNTAX INTEGER
				{
				valid(1),
				createRequest(2),
				underCreation(3),
				invalid(4)
				}
			MAX-ACCESS read-write
			STATUS current
			DESCRIPTION
				"Description."
			::= { pmRmepEntry 4 }

		
		pmRmepType OBJECT-TYPE
			SYNTAX INTEGER
				{
				norole(0),
				initiator(1),
				responder(2)
				}
			MAX-ACCESS read-write
			STATUS current
			DESCRIPTION
				"PM_RMEP_TYPE"
			::= { pmRmepEntry 5 }

		
		pmRmepCcStatus OBJECT-TYPE
			SYNTAX INTEGER
			MAX-ACCESS read-only
			STATUS current
			DESCRIPTION
				"Description."
			::= { pmRmepEntry 6 }

		
		pmRmepSlaStatus OBJECT-TYPE
			SYNTAX INTEGER
				{
				enable(1),
				disable(2)
				}
			MAX-ACCESS read-write
			STATUS current
			DESCRIPTION
				"PM_RMEP_STATUS"
			::= { pmRmepEntry 7 }

		
		pmRmepStartTime OBJECT-TYPE
			SYNTAX Unsigned32
			MAX-ACCESS read-only
			STATUS current
			DESCRIPTION
				"Description."
			::= { pmRmepEntry 8 }

		
		pmRmepPriority OBJECT-TYPE
			SYNTAX INTEGER (0..7)
			MAX-ACCESS read-write
			STATUS current
			DESCRIPTION
				"PM_RMEP_PRIORITY"
			::= { pmRmepEntry 9 }

		
		pmRmepLmFrequency OBJECT-TYPE
			SYNTAX INTEGER
			MAX-ACCESS read-write
			STATUS current
			DESCRIPTION
				"PM_RMEP_LMFREQUENCY"
			::= { pmRmepEntry 10 }

		
		pmRmepDmFrequency OBJECT-TYPE
			SYNTAX INTEGER
			MAX-ACCESS read-write
			STATUS current
			DESCRIPTION
				"PM_RMEP_DMFREQUENCY"
			::= { pmRmepEntry 11 }

		
		pmRmepDstMac OBJECT-TYPE
			SYNTAX OCTET STRING
			MAX-ACCESS read-write
			STATUS current
			DESCRIPTION
				"PM_RMEP_DSTMAC"
			::= { pmRmepEntry 12 }

		
		pmRmepStatClear OBJECT-TYPE
			SYNTAX INTEGER
				{
				clearall(0),
				clear1m(1),
				clear5m(2),
				clear15m(3),
				clear24h(4),
				clearUnTimed(5)
				}
			MAX-ACCESS read-write
			STATUS current
			DESCRIPTION
				"PM_RMEP_STATUS"
			::= { pmRmepEntry 13 }

		
		pmGlobals OBJECT IDENTIFIER ::= { pm 6 }

		
		pmStatus OBJECT-TYPE
			SYNTAX INTEGER
				{
				start(1),
				stop(2)				
				}
			MAX-ACCESS read-write
			STATUS current
			DESCRIPTION
				"Description."
			::= { pmGlobals 1 }

		
		pmIfMax OBJECT-TYPE
			SYNTAX INTEGER
			MAX-ACCESS read-only
			STATUS current
			DESCRIPTION
				"PM_GLOBAL_IFMAX"
			::= { pmGlobals 2 }

		
		pmIfUsed OBJECT-TYPE
			SYNTAX INTEGER
			MAX-ACCESS read-only
			STATUS current
			DESCRIPTION
				"PM_GLOBAL_IFUSED"
			::= { pmGlobals 3 }

		
		pmSlaMax OBJECT-TYPE
			SYNTAX INTEGER
			MAX-ACCESS read-only
			STATUS current
			DESCRIPTION
				"PM_GLOBAL_SLAMAX"
			::= { pmGlobals 4 }

		
		pmSlaUsed OBJECT-TYPE
			SYNTAX INTEGER
			MAX-ACCESS read-only
			STATUS current
			DESCRIPTION
				"PM_GLOBAL_SLAUSED"
			::= { pmGlobals 5 }

		
		pmRmepMax OBJECT-TYPE
			SYNTAX INTEGER
			MAX-ACCESS read-only
			STATUS current
			DESCRIPTION
				"PM_GLOBAL_RMEPMAX"
			::= { pmGlobals 6 }

		
		pmRmepUsed OBJECT-TYPE
			SYNTAX INTEGER
			MAX-ACCESS read-only
			STATUS current
			DESCRIPTION
				"PM_GLOBAL_RMEPUSED"
			::= { pmGlobals 7 }

		
		pmEServiceMax OBJECT-TYPE
			SYNTAX INTEGER
			MAX-ACCESS read-only
			STATUS current
			DESCRIPTION
				"PM_GLOBAL_ESERVICEMAX"
			::= { pmGlobals 8 }

		
		pmEServiceUsed OBJECT-TYPE
			SYNTAX INTEGER
			MAX-ACCESS read-only
			STATUS current
			DESCRIPTION
				"PM_GLOBAL_ESERVICEUSED"
			::= { pmGlobals 9 }

		
		pmIfStatMax OBJECT-TYPE
			SYNTAX INTEGER
			MAX-ACCESS read-only
			STATUS current
			DESCRIPTION
				"PM_GLOBAL_IFSTATMAX"
			::= { pmGlobals 10 }

		
		pmIfStatUsed OBJECT-TYPE
			SYNTAX INTEGER
			MAX-ACCESS read-only
			STATUS current
			DESCRIPTION
				"PM_GLOBAL_IFSTATUSED"
			::= { pmGlobals 11 }

		
		pmEServiceStatMax OBJECT-TYPE
			SYNTAX INTEGER
			MAX-ACCESS read-only
			STATUS current
			DESCRIPTION
				"PM_GLOBAL_ESERVICESTATMAX"
			::= { pmGlobals 12 }

		
		pmEServiceStatUsed OBJECT-TYPE
			SYNTAX INTEGER
			MAX-ACCESS read-only
			STATUS current
			DESCRIPTION
				"PM_GLOBAL_ESERVICESTATUSED"
			::= { pmGlobals 13 }

		
		pmSlaStatMax OBJECT-TYPE
			SYNTAX INTEGER
			MAX-ACCESS read-only
			STATUS current
			DESCRIPTION
				"PM_GLOBAL_SLASTATMAX"
			::= { pmGlobals 14 }

		
		pmSlaStatUsed OBJECT-TYPE
			SYNTAX INTEGER
			MAX-ACCESS read-only
			STATUS current
			DESCRIPTION
				"PM_GLOBAL_SLASTATUSED"
			::= { pmGlobals 15 }

		
		pmSyncIf OBJECT-TYPE
			SYNTAX INTEGER
			MAX-ACCESS read-only
			STATUS current
			DESCRIPTION
				"PM_GLOBAL_SYNCIF"
			::= { pmGlobals 16 }

		
		pmSyncSla OBJECT-TYPE
			SYNTAX INTEGER
			MAX-ACCESS read-only
			STATUS current
			DESCRIPTION
				"PM_GLOBAL_SYNCSLA"
			::= { pmGlobals 17 }

		
		pmSyncEService OBJECT-TYPE
			SYNTAX INTEGER
			MAX-ACCESS read-only
			STATUS current
			DESCRIPTION
				"PM_GLOBAL_SYNCESERVICE"
			::= { pmGlobals 18 }

		
		pmSyncRecvPkts OBJECT-TYPE
			SYNTAX INTEGER
			MAX-ACCESS read-only
			STATUS current
			DESCRIPTION
				"PM_GLOBAL_SYNCRECVPKTS"
			::= { pmGlobals 19 }

		
	
	END

--
-- WRI-PM-MIB.mib
--
