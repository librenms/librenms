-- These MIBs were created on 1/7/2003
-- This module defines enterprise MIBs for NS OSPF
-- 
-- Copyright (c) 1999-2004, Juniper Networks, Inc.
-- All rights reserved.


NETSCREEN-OSPF-MIB DEFINITIONS ::= BEGIN

    IMPORTS
            MODULE-IDENTITY, OBJECT-TYPE, Counter32, Gauge32,
            Integer32, IpAddress
                FROM SNMPv2-SMI
            TEXTUAL-CONVENTION, TruthValue, RowStatus
                FROM SNMPv2-TC
            MODULE-COMPLIANCE, OBJECT-GROUP          FROM SNMPv2-CONF
            mib-2                                    FROM RFC1213-MIB
			netscreenVR								 FROM NETSCREEN-SMI;

--  This MIB module uses the extended OBJECT-TYPE macro as
--  defined in [9].

nsOspf MODULE-IDENTITY
    LAST-UPDATED  "200506032022Z" -- June 20, 2005
    ORGANIZATION
        "Juniper Networks, Inc."
    CONTACT-INFO
        "Customer Support

         1194 North Mathilda Avenue 
         Sunnyvale, California 94089-1206
         USA

         Tel: 1-800-638-8296
         E-mail: customerservice@juniper.net
         HTTP://www.juniper.net"
    DESCRIPTION
       "The MIB module to describe the NS-OSPF Version 2
       Protocol"
    ::= { netscreenVR 2 }

--  The Area ID, in OSPF, has the same format as an IP Address,
--  but has the function of defining a summarization point for
--  Link State Advertisements

AreaID ::= TEXTUAL-CONVENTION
    STATUS      deprecated
    DESCRIPTION
       "An OSPF Area Identifier."
    SYNTAX      IpAddress

--  The Router ID, in OSPF, has the same format as an IP Address,

--  but identifies the router independent of its IP Address.

RouterID ::= TEXTUAL-CONVENTION
    STATUS      deprecated
    DESCRIPTION
       "A OSPF Router Identifier."
    SYNTAX      IpAddress

--  The OSPF Metric is defined as an unsigned value in the range

Metric ::= TEXTUAL-CONVENTION
    STATUS      deprecated
    DESCRIPTION
       "The OSPF Internal Metric."
    SYNTAX      Integer32 (0..'FFFF'H)

BigMetric ::= TEXTUAL-CONVENTION
    STATUS      deprecated
    DESCRIPTION
       "The OSPF External Metric."
    SYNTAX      Integer32 (0..'FFFFFF'H)

--  Status Values

Status ::= TEXTUAL-CONVENTION
    STATUS      deprecated
    DESCRIPTION
       "The status of an interface: 'enabled' indicates that
       it is willing to communicate with other OSPF Routers,
       while 'disabled' indicates that it is not."
    SYNTAX      INTEGER { enabled (1), disabled (2) }

--  Time Durations measured in seconds

PositiveInteger ::= TEXTUAL-CONVENTION
    STATUS      deprecated
    DESCRIPTION
       "A positive integer. Values in excess are precluded as
       unnecessary and prone to interoperability issues."
    SYNTAX      Integer32 (0..'7FFFFFFF'H)

HelloRange ::= TEXTUAL-CONVENTION
    STATUS      deprecated
    DESCRIPTION
       "The range of intervals on which hello messages are
       exchanged."
    SYNTAX      Integer32 (1..'FFFF'H)

UpToMaxAge ::= TEXTUAL-CONVENTION
    STATUS      deprecated
    DESCRIPTION
       "The values that one might find or configure for
       variables bounded by the maximum age of an LSA."
    SYNTAX      Integer32 (0..3600)

--  The range of ifIndex

InterfaceIndex ::= TEXTUAL-CONVENTION
    STATUS      deprecated
    DESCRIPTION
       "The range of ifIndex."
    SYNTAX      Integer32

--  Potential Priorities for the Designated Router Election

DesignatedRouterPriority ::= TEXTUAL-CONVENTION
    STATUS      deprecated
    DESCRIPTION
       "The values defined for the priority of a system for
       becoming the designated router."
    SYNTAX      Integer32 (0..'FF'H)

TOSType ::= TEXTUAL-CONVENTION
    STATUS      deprecated
    DESCRIPTION
       "Type of Service is defined as a mapping to the IP Type of
       Service Flags as defined in the IP Forwarding Table MIB

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy

           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22

           1 1 0 0  ==>  24      1 1 0 1  ==>  26
           1 1 1 0  ==>  28      1 1 1 1  ==>  30

       The remaining values are left for future definition."
    SYNTAX      Integer32 (0..30)

--  OSPF General Variables

--      These parameters apply globally to the Router's
--      OSPF Process.

    nsOspfGeneralTable OBJECT-TYPE
        SYNTAX   SEQUENCE OF  NsOspfGeneralEntry
        MAX-ACCESS   not-accessible
        STATUS   deprecated
        DESCRIPTION
           "Ospf general information table per VR"
      ::= { nsOspf 1 }

    nsOspfGeneralEntry OBJECT-TYPE
        SYNTAX    NsOspfGeneralEntry
        MAX-ACCESS   not-accessible
        STATUS   deprecated
        DESCRIPTION
           "Ospf general information table per VR"
       INDEX { nsOspfGeneralVRID }
       ::= { nsOspfGeneralTable 1 }

 NsOspfGeneralEntry ::=
    SEQUENCE {
        nsOspfRouterId
            RouterID,
        nsOspfAdminStat
            Status,
        nsOspfVersionNumber
            INTEGER,
        nsOspfAreaBdrRtrStatus
            TruthValue,
        nsOspfASBdrRtrStatus
            TruthValue,
        nsOspfExternLsaCount
            Gauge32,
        nsOspfAreaLsaCount
            Gauge32,
        nsOspfExternLsaCksumSum
            Integer32,
        nsOspfTOSSupport
            TruthValue,
        nsOspfOriginateNewLsas
            Counter32,
        nsOspfRxNewLsas
            Counter32,
        nsOspfExtLsdbLimit
            Integer32,
        nsOspfMulticastExtensions
            Integer32,
        nsOspfExitOverflowInterval
            PositiveInteger,
        nsOspfDemandExtensions
            TruthValue,
        nsOspfGeneralVRID
            INTEGER
              }

    nsOspfRouterId OBJECT-TYPE
        SYNTAX   RouterID
        MAX-ACCESS   read-only
        STATUS   deprecated
        DESCRIPTION
           "A  32-bit  integer  uniquely  identifying  the
           router in the Autonomous System.

           By  convention,  to  ensure  uniqueness,   this
           should  default  to  the  value  of  one of the
           router's IP interface addresses."
       REFERENCE
          "OSPF Version 2, C.1 Global parameters"
      ::= { nsOspfGeneralEntry 1 }

    nsOspfAdminStat OBJECT-TYPE
        SYNTAX   Status
        MAX-ACCESS   read-only
        STATUS   deprecated
        DESCRIPTION
           "The  administrative  status  of  OSPF  in  the
           router.   The  value 'enabled' denotes that the
           OSPF Process is active on at least  one  inter-
           face;  'disabled'  disables  it  on  all inter-
           faces."
       ::= { nsOspfGeneralEntry 2 }

    nsOspfVersionNumber OBJECT-TYPE
        SYNTAX   INTEGER    { version2 (2) }
        MAX-ACCESS   read-only
        STATUS   deprecated
        DESCRIPTION

           "The deprecated version number of the OSPF  proto-
           col is 2."
       REFERENCE
          "OSPF Version 2, Title"
      ::= { nsOspfGeneralEntry 3 }

    nsOspfAreaBdrRtrStatus OBJECT-TYPE
        SYNTAX   TruthValue
        MAX-ACCESS   read-only
        STATUS   deprecated
        DESCRIPTION
           "A flag to note whether this router is an  area
           border router."
       REFERENCE
          "OSPF Version 2, Section 3 Splitting the AS into
          Areas"
      ::= { nsOspfGeneralEntry 4 }

    nsOspfASBdrRtrStatus OBJECT-TYPE
        SYNTAX   TruthValue
        MAX-ACCESS   read-only
        STATUS   deprecated
        DESCRIPTION
           "A flag to note whether this router is  config-
           ured as an Autonomous System border router."
       REFERENCE
          "OSPF Version 2, Section 3.3  Classification  of
          routers"
      ::= { nsOspfGeneralEntry 5 }

    nsOspfExternLsaCount OBJECT-TYPE
        SYNTAX   Gauge32
        MAX-ACCESS   read-only
        STATUS   deprecated
        DESCRIPTION
           "The number of external (LS type 5)  link-state
           advertisements in the link-state database."
       REFERENCE
          "OSPF Version 2, Appendix A.4.5 AS external link
          advertisements"
      ::= { nsOspfGeneralEntry 6 }

    nsOspfExternLsaCksumSum OBJECT-TYPE
        SYNTAX   Integer32
        MAX-ACCESS   read-only

        STATUS   deprecated
        DESCRIPTION
           "The 32-bit unsigned sum of the LS checksums of
           the  external  link-state  advertisements  con-
           tained in the link-state  database.   This  sum
           can  be  used  to determine if there has been a
           change in a router's link state  database,  and
           to  compare  the  link-state  database  of  two
           routers."
       ::= { nsOspfGeneralEntry 7 }

    nsOspfTOSSupport OBJECT-TYPE
        SYNTAX   TruthValue
        MAX-ACCESS   read-only
        STATUS   deprecated
        DESCRIPTION
           "The router's support for type-of-service rout-
           ing."
       REFERENCE
          "OSPF Version 2,  Appendix  F.1.2  Optional  TOS
          support"
      ::= { nsOspfGeneralEntry 8 }

    nsOspfOriginateNewLsas OBJECT-TYPE
        SYNTAX   Counter32
        MAX-ACCESS   read-only
        STATUS   deprecated
        DESCRIPTION
           "The number of  new  link-state  advertisements
           that  have been originated.  This number is in-
           cremented each time the router originates a new
           LSA."
       ::= { nsOspfGeneralEntry 9 }

    nsOspfRxNewLsas OBJECT-TYPE
        SYNTAX   Counter32
        MAX-ACCESS   read-only
        STATUS   deprecated
        DESCRIPTION
           "The number of  link-state  advertisements  re-
           ceived  determined  to  be  new instantiations.
           This number does not include  newer  instantia-
           tions  of self-originated link-state advertise-
           ments."
       ::= { nsOspfGeneralEntry 10 }

    nsOspfExtLsdbLimit OBJECT-TYPE
        SYNTAX   Integer32 (-1..'7FFFFFFF'H)
        MAX-ACCESS   read-only
        STATUS   deprecated
        DESCRIPTION
           "The  maximum   number   of   non-default   AS-
           external-LSAs entries that can be stored in the
           link-state database.  If the value is -1,  then
           there is no limit.

           When the number of non-default AS-external-LSAs
           in   a  router's  link-state  database  reaches
           nsOspfExtLsdbLimit, the router  enters  Overflow-
           State.   The   router  never  holds  more  than
           nsOspfExtLsdbLimit  non-default  AS-external-LSAs
           in  its  database.  OspfExtLsdbLimit MUST be set
           identically in all routers attached to the OSPF
           backbone  and/or  any regular OSPF area. (i.e.,
           OSPF stub areas and NSSAs are excluded)."
       DEFVAL { -1 }
       ::= { nsOspfGeneralEntry 11 }

    nsOspfMulticastExtensions OBJECT-TYPE
        SYNTAX   Integer32
        MAX-ACCESS   read-only
        STATUS   deprecated
        DESCRIPTION
           "A Bit Mask indicating whether  the  router  is
           forwarding  IP  multicast  (Class  D) datagrams
           based on the algorithms defined in  the  Multi-
           cast Extensions to OSPF.

           Bit 0, if set, indicates that  the  router  can
           forward  IP multicast datagrams in the router's
           directly attached areas (called intra-area mul-
           ticast routing).

           Bit 1, if set, indicates that  the  router  can
           forward  IP  multicast  datagrams  between OSPF
           areas (called inter-area multicast routing).

           Bit 2, if set, indicates that  the  router  can
           forward  IP  multicast  datagrams between Auto-
           nomous Systems (called inter-AS multicast rout-
           ing).

           Only certain combinations of bit  settings  are
           allowed,  namely: 0 (no multicast forwarding is

           enabled), 1 (intra-area multicasting  only),  3
           (intra-area  and  inter-area  multicasting),  5
           (intra-area and inter-AS  multicasting)  and  7
           (multicasting  everywhere). By default, no mul-
           ticast forwarding is enabled."
       DEFVAL { 0 }
       ::= { nsOspfGeneralEntry 12 }

    nsOspfExitOverflowInterval OBJECT-TYPE
        SYNTAX   PositiveInteger
        MAX-ACCESS   read-only
        STATUS   deprecated
        DESCRIPTION
           "The number of  seconds  that,  after  entering
           OverflowState,  a  router will attempt to leave
           OverflowState. This allows the router to  again
           originate  non-default  AS-external-LSAs.  When
           set to 0, the router will not  leave  Overflow-
           State until restarted."
       DEFVAL { 0 }
       ::= { nsOspfGeneralEntry 13 }

    nsOspfDemandExtensions OBJECT-TYPE
        SYNTAX   TruthValue
        MAX-ACCESS   read-only
        STATUS   deprecated
        DESCRIPTION
           "The router's support for demand routing."
       REFERENCE
          "OSPF Version 2, Appendix on Demand Routing"
      ::= { nsOspfGeneralEntry 14 }

    nsOspfGeneralVRID OBJECT-TYPE
        SYNTAX   INTEGER (0..65535)
        MAX-ACCESS   read-only
        STATUS   deprecated
        DESCRIPTION
           "Virtual Router ID"
       ::= { nsOspfGeneralEntry 15 }

--      The OSPF Area Data Structure contains information
--      regarding the various areas. The interfaces and
--      virtual links are configured as part of these areas.
--      Area 0.0.0.0, by definition, is the Backbone Area

    nsOspfAreaTable OBJECT-TYPE
        SYNTAX   SEQUENCE OF  NsOspfAreaEntry
        MAX-ACCESS   not-accessible
        STATUS   deprecated
        DESCRIPTION
           "Information describing the configured  parame-
           ters  and cumulative statistics of the router's
           attached areas."

       REFERENCE
          "OSPF Version 2, Section 6  The Area Data Struc-
          ture"
      ::= { nsOspf 2 }

    nsOspfAreaEntry OBJECT-TYPE
        SYNTAX    NsOspfAreaEntry
        MAX-ACCESS   not-accessible
        STATUS   deprecated
        DESCRIPTION
           "Information describing the configured  parame-
           ters  and  cumulative  statistics of one of the
           router's attached areas."
       INDEX { nsOspfAreaId, nsOspfAreaVRID }
       ::= { nsOspfAreaTable 1 }

 NsOspfAreaEntry ::=
    SEQUENCE {
        nsOspfAreaId
            AreaID,
        nsOspfImportAsExtern
            INTEGER,
        nsOspfSpfRuns
            Counter32,
        nsOspfAreaBdrRtrCount
            Gauge32,
        nsOspfAsBdrRtrCount
            Gauge32,
        nsOspfAreaLsaCount
            Gauge32,
        nsOspfAreaLsaCksumSum
            Integer32,
        nsOspfAreaSummary
            INTEGER,
        nsOspfAreaStatus
            RowStatus,
        nsOspfAreaVRID
            INTEGER
              }

    nsOspfAreaId OBJECT-TYPE
        SYNTAX   AreaID
        MAX-ACCESS   read-only
        STATUS   deprecated
        DESCRIPTION
           "A 32-bit integer uniquely identifying an area.
           Area ID 0.0.0.0 is used for the OSPF backbone."

       REFERENCE
          "OSPF Version 2, Appendix C.2 Area parameters"
      ::= { nsOspfAreaEntry 1 }

    nsOspfImportAsExtern OBJECT-TYPE
        SYNTAX   INTEGER    {
                    importExternal (1),
                    importNoExternal (2),
                    importNssa (3)
                  }
        MAX-ACCESS   read-create
        STATUS   deprecated
        DESCRIPTION
           "The area's support for importing  AS  external
           link- state advertisements."
       REFERENCE
          "OSPF Version 2, Appendix C.2 Area parameters"
      DEFVAL { importExternal }
      ::= { nsOspfAreaEntry 3 }

    nsOspfSpfRuns OBJECT-TYPE
        SYNTAX   Counter32
        MAX-ACCESS   read-only
        STATUS   deprecated
        DESCRIPTION
           "The number of times that the intra-area  route
           table  has  been  calculated  using this area's
           link-state database.  This  is  typically  done
           using Dijkstra's algorithm."

       ::= { nsOspfAreaEntry 4 }

    nsOspfAreaBdrRtrCount OBJECT-TYPE
        SYNTAX   Gauge32
        MAX-ACCESS   read-only
        STATUS   deprecated
        DESCRIPTION
           "The total number of area border routers reach-
           able within this area.  This is initially zero,
           and is calculated in each SPF Pass."
       ::= { nsOspfAreaEntry 5 }

    nsOspfAsBdrRtrCount OBJECT-TYPE
        SYNTAX   Gauge32
        MAX-ACCESS   read-only
        STATUS   deprecated
        DESCRIPTION
           "The total number of Autonomous  System  border
           routers  reachable  within  this area.  This is
           initially zero, and is calculated in  each  SPF
           Pass."
       ::= { nsOspfAreaEntry 6 }

    nsOspfAreaLsaCount OBJECT-TYPE
        SYNTAX   Gauge32
        MAX-ACCESS   read-only
        STATUS   deprecated
        DESCRIPTION
           "The total number of link-state  advertisements
           in  this  area's link-state database, excluding
           AS External LSA's."
       ::= { nsOspfAreaEntry 7 }

    nsOspfAreaLsaCksumSum OBJECT-TYPE
        SYNTAX   Integer32
        MAX-ACCESS   read-only
        STATUS   deprecated
        DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of

           two routers."
       DEFVAL   { 0 }
       ::= { nsOspfAreaEntry 8 }

    nsOspfAreaSummary OBJECT-TYPE
        SYNTAX   INTEGER    {
                    noAreaSummary (1),
                    sendAreaSummary (2)
                  }
        MAX-ACCESS   read-create
        STATUS   deprecated
        DESCRIPTION
           "The variable nsOspfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { noAreaSummary }
       ::= { nsOspfAreaEntry 9 }

    nsOspfAreaStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfAreaEntry 10 }

    nsOspfAreaVRID OBJECT-TYPE
        SYNTAX   INTEGER (0..65535)
        MAX-ACCESS   read-only
        STATUS   deprecated
        DESCRIPTION
           "Virtual Router ID"
       ::= { nsOspfAreaEntry 11 }

--  OSPF Area Default Metric Table

--      The OSPF Area Default Metric Table describes the metrics
--      that a default Area Border Router will advertise into a
--      Stub area.

    nsOspfStubAreaTable OBJECT-TYPE
        SYNTAX   SEQUENCE OF  NsOspfStubAreaEntry

        MAX-ACCESS   not-accessible
        STATUS   deprecated
        DESCRIPTION
           "The set of metrics that will be advertised  by
           a default Area Border Router into a stub area."
       REFERENCE
          "OSPF Version 2, Appendix C.2, Area Parameters"
      ::= { nsOspf 3 }

    nsOspfStubAreaEntry OBJECT-TYPE
        SYNTAX    NsOspfStubAreaEntry
        MAX-ACCESS   not-accessible
        STATUS   deprecated
        DESCRIPTION
           "The metric for a given Type  of  Service  that
           will  be  advertised  by  a default Area Border
           Router into a stub area."
       REFERENCE
          "OSPF Version 2, Appendix C.2, Area Parameters"
      INDEX { nsOspfStubAreaId, nsOspfStubTOS, nsOspfStubVRID }
      ::= { nsOspfStubAreaTable 1 }

 NsOspfStubAreaEntry ::=
    SEQUENCE {
        nsOspfStubAreaId
            AreaID,
        nsOspfStubTOS
            TOSType,
        nsOspfStubMetric
            BigMetric,
        nsOspfStubStatus
            RowStatus,
        nsOspfStubMetricType
            INTEGER,
        nsOspfStubVRID
            INTEGER
              }

    nsOspfStubAreaId OBJECT-TYPE
        SYNTAX   AreaID
        MAX-ACCESS   read-only
        STATUS   deprecated
        DESCRIPTION
           "The 32 bit identifier for the Stub  Area.   On
           creation,  this  can  be  derived  from the in-
           stance."
       ::= { nsOspfStubAreaEntry 1 }

    nsOspfStubTOS OBJECT-TYPE
        SYNTAX   TOSType
        MAX-ACCESS   read-only
        STATUS   deprecated
        DESCRIPTION
           "The  Type  of  Service  associated  with   the
           metric.   On creation, this can be derived from
           the instance."
       ::= { nsOspfStubAreaEntry 2 }

    nsOspfStubMetric OBJECT-TYPE
        SYNTAX   BigMetric
        MAX-ACCESS   read-create
        STATUS   deprecated
        DESCRIPTION
           "The metric value applied at the indicated type
           of  service.  By default, this equals the least
           metric at the type of service among the  inter-
           faces to other areas."
       ::= { nsOspfStubAreaEntry 3 }

    nsOspfStubStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfStubAreaEntry 4 }

    nsOspfStubMetricType OBJECT-TYPE
        SYNTAX   INTEGER    {
                    nsOspfMetric (1),                -- OSPF Metric
                    comparableCost (2),        -- external type 1
                    nonComparable  (3)        -- external type 2
                  }
        MAX-ACCESS   read-create
        STATUS   deprecated
        DESCRIPTION
           "This variable displays the type of metric  ad-
           vertised as a default route."
       DEFVAL   { nsOspfMetric }
       ::= { nsOspfStubAreaEntry 5 }

    nsOspfStubVRID OBJECT-TYPE
        SYNTAX   INTEGER (0..65535)
        MAX-ACCESS   read-only
        STATUS   deprecated
        DESCRIPTION
           "Virtual Router ID"
       ::= { nsOspfStubAreaEntry 6 }

--  OSPF Link State Database

--      The Link State Database contains the Link State
--      Advertisements from throughout the areas that the
--      device is attached to.

    nsOspfLsdbTable OBJECT-TYPE
        SYNTAX   SEQUENCE OF  NsOspfLsdbEntry
        MAX-ACCESS   not-accessible
        STATUS   deprecated
        DESCRIPTION
           "The OSPF Process's Link State Database."
       REFERENCE
          "OSPF Version 2, Section 12  Link  State  Adver-
          tisements"
      ::= { nsOspf 4 }

    nsOspfLsdbEntry OBJECT-TYPE
        SYNTAX    NsOspfLsdbEntry
        MAX-ACCESS   not-accessible
        STATUS   deprecated
        DESCRIPTION
           "A single Link State Advertisement."
       INDEX { nsOspfLsdbAreaId, nsOspfLsdbType,
               nsOspfLsdbLsid, nsOspfLsdbRouterId, nsOspfLsdbVRID }
       ::= { nsOspfLsdbTable 1 }

 NsOspfLsdbEntry ::=
    SEQUENCE {
        nsOspfLsdbAreaId
            AreaID,
        nsOspfLsdbType
            INTEGER,
        nsOspfLsdbLsid
            IpAddress,
        nsOspfLsdbRouterId
            RouterID,
        nsOspfLsdbSequence
            Integer32,
        nsOspfLsdbAge
            Integer32,
        nsOspfLsdbChecksum
            Integer32,
        nsOspfLsdbAdvertisement
            OCTET STRING,
        nsOspfLsdbVRID
            INTEGER
              }

    nsOspfLsdbAreaId OBJECT-TYPE
        SYNTAX   AreaID
        MAX-ACCESS   read-only
        STATUS   deprecated
        DESCRIPTION
           "The 32 bit identifier of the Area  from  which
           the LSA was received."
       REFERENCE
          "OSPF Version 2, Appendix C.2 Area parameters"
      ::= { nsOspfLsdbEntry 1 }

-- External Link State Advertisements are permitted
-- for backward compatibility, but should be displayed in
-- the nsOspfExtLsdbTable rather than here.

    nsOspfLsdbType OBJECT-TYPE
        SYNTAX   INTEGER    {
                    routerLink (1),
                    networkLink (2),
                    summaryLink (3),
                    asSummaryLink (4),
                    asExternalLink (5), -- but see nsOspfExtLsdbTable
                    multicastLink (6),
                    nssaExternalLink (7)
                  }
        MAX-ACCESS   read-only
        STATUS   deprecated
        DESCRIPTION
           "The type  of  the  link  state  advertisement.
           Each  link state type has a separate advertise-
           ment format."
       REFERENCE
          "OSPF Version 2, Appendix A.4.1 The  Link  State
          Advertisement header"
      ::= { nsOspfLsdbEntry 2 }

    nsOspfLsdbLsid OBJECT-TYPE
        SYNTAX   IpAddress
        MAX-ACCESS   read-only
        STATUS   deprecated
        DESCRIPTION
           "The Link State ID is an LS Type Specific field
           containing either a Router ID or an IP Address;
           it identifies the piece of the  routing  domain
           that is being described by the advertisement."
       REFERENCE
          "OSPF Version 2, Section 12.1.4 Link State ID"
      ::= { nsOspfLsdbEntry 3 }

    nsOspfLsdbRouterId OBJECT-TYPE
        SYNTAX   RouterID
        MAX-ACCESS   read-only
        STATUS   deprecated
        DESCRIPTION
           "The 32 bit number that uniquely identifies the
           originating router in the Autonomous System."
       REFERENCE
          "OSPF Version 2, Appendix C.1 Global parameters"
      ::= { nsOspfLsdbEntry 4 }

--  Note that the OSPF Sequence Number is a 32 bit signed
--  integer.  It starts with the value '80000001'h,
--  or -'7FFFFFFF'h, and increments until '7FFFFFFF'h
--  Thus, a typical sequence number will be very negative.

    nsOspfLsdbSequence OBJECT-TYPE
        SYNTAX   Integer32
        MAX-ACCESS   read-only
        STATUS   deprecated
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { nsOspfLsdbEntry 5 }

    nsOspfLsdbAge OBJECT-TYPE
        SYNTAX   Integer32    -- Should be 0..MaxAge
        MAX-ACCESS   read-only
        STATUS   deprecated
        DESCRIPTION
           "This field is the age of the link state adver-
           tisement in seconds."
       REFERENCE
          "OSPF Version 2, Section 12.1.1 LS age"
      ::= { nsOspfLsdbEntry 6 }

    nsOspfLsdbChecksum OBJECT-TYPE
        SYNTAX   Integer32
        MAX-ACCESS   read-only
        STATUS   deprecated

        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { nsOspfLsdbEntry 7 }

    nsOspfLsdbAdvertisement OBJECT-TYPE
        SYNTAX   OCTET STRING (SIZE (1..65535))
        MAX-ACCESS   read-only
        STATUS   deprecated
        DESCRIPTION
           "The entire Link State Advertisement, including
           its header."
       REFERENCE
          "OSPF Version 2, Section 12  Link  State  Adver-
          tisements"
      ::= { nsOspfLsdbEntry 8 }

    nsOspfLsdbVRID OBJECT-TYPE
        SYNTAX   INTEGER (0..65535)
        MAX-ACCESS   read-only
        STATUS   deprecated
        DESCRIPTION
           "Virtual Router ID"
       ::= { nsOspfLsdbEntry 9 }

--  OSPF Host Table

--      The Host/Metric Table indicates what hosts are directly

--      attached to the Router, and what metrics and types of
--      service should be advertised for them.

    nsOspfHostTable OBJECT-TYPE
        SYNTAX   SEQUENCE OF  NsOspfHostEntry
        MAX-ACCESS   not-accessible
        STATUS   deprecated
        DESCRIPTION
           "The list of Hosts, and their metrics, that the
           router will advertise as host routes."
       REFERENCE
          "OSPF Version 2, Appendix C.6  Host route param-
          eters"
      ::= { nsOspf 6 }

    nsOspfHostEntry OBJECT-TYPE
        SYNTAX    NsOspfHostEntry
        MAX-ACCESS   not-accessible
        STATUS   deprecated
        DESCRIPTION
           "A metric to be advertised, for a given type of
           service, when a given host is reachable."
       INDEX { nsOspfHostIpAddress, nsOspfHostTOS, nsOspfHostVRID }
       ::= { nsOspfHostTable 1 }

 NsOspfHostEntry ::=
    SEQUENCE {
        nsOspfHostIpAddress
            IpAddress,
        nsOspfHostTOS
            TOSType,
        nsOspfHostMetric
            Metric,
        nsOspfHostStatus
            RowStatus,
        nsOspfHostAreaID
            AreaID,
        nsOspfHostVRID
            INTEGER
              }

    nsOspfHostIpAddress OBJECT-TYPE
        SYNTAX   IpAddress
        MAX-ACCESS   read-only
        STATUS   deprecated
        DESCRIPTION
           "The IP Address of the Host."
       REFERENCE
          "OSPF Version 2, Appendix C.6 Host route parame-

          ters"
      ::= { nsOspfHostEntry 1 }

    nsOspfHostTOS OBJECT-TYPE
        SYNTAX   TOSType
        MAX-ACCESS   read-only
        STATUS   deprecated
        DESCRIPTION
           "The Type of Service of the route being config-
           ured."
       REFERENCE
          "OSPF Version 2, Appendix C.6 Host route parame-
          ters"
      ::= { nsOspfHostEntry 2 }

    nsOspfHostMetric OBJECT-TYPE
        SYNTAX   Metric
        MAX-ACCESS   read-create
        STATUS   deprecated
        DESCRIPTION
           "The Metric to be advertised."
       REFERENCE
          "OSPF Version 2, Appendix C.6 Host route parame-
          ters"
      ::= { nsOspfHostEntry 3 }

    nsOspfHostStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfHostEntry 4 }

    nsOspfHostAreaID OBJECT-TYPE
        SYNTAX   AreaID
        MAX-ACCESS   read-only
        STATUS   deprecated
        DESCRIPTION
           "The Area the Host Entry is to be found within.
           By  default, the area that a subsuming OSPF in-
           terface is in, or 0.0.0.0"

       REFERENCE
          "OSPF Version 2, Appendix C.2 Area parameters"
      ::= { nsOspfHostEntry 5 }

    nsOspfHostVRID OBJECT-TYPE
        SYNTAX   INTEGER (0..65535)
        MAX-ACCESS   read-only
        STATUS   deprecated
        DESCRIPTION
           "Virtual Router ID"
       ::= { nsOspfHostEntry 6 }

--  OSPF Interface Table

--      The OSPF Interface Table augments the ipAddrTable
--             with OSPF specific information.

    nsOspfIfTable OBJECT-TYPE
        SYNTAX   SEQUENCE OF  NsOspfIfEntry
        MAX-ACCESS   not-accessible
        STATUS   deprecated
        DESCRIPTION
           "The OSPF Interface Table describes the  inter-
           faces from the viewpoint of OSPF."
       REFERENCE
          "OSPF Version 2, Appendix C.3  Router  interface
          parameters"
      ::= { nsOspf 7 }

    nsOspfIfEntry OBJECT-TYPE
        SYNTAX    NsOspfIfEntry
        MAX-ACCESS   not-accessible
        STATUS   deprecated
        DESCRIPTION
           "The OSPF Interface Entry describes one  inter-
           face from the viewpoint of OSPF."
       INDEX { nsOspfIfIpAddress, nsOspfAddressLessIf, nsOspfIfVRID }
       ::= { nsOspfIfTable 1 }

 NsOspfIfEntry ::=
    SEQUENCE {
        nsOspfIfIpAddress
            IpAddress,
        nsOspfAddressLessIf
            Integer32,
        nsOspfIfAreaId
            AreaID,
        nsOspfIfType
            INTEGER,
        nsOspfIfAdminStat
            Status,
        nsOspfIfRtrPriority
            DesignatedRouterPriority,
        nsOspfIfTransitDelay

            UpToMaxAge,
        nsOspfIfRetransInterval
            UpToMaxAge,
        nsOspfIfHelloInterval
            HelloRange,
        nsOspfIfRtrDeadInterval
            PositiveInteger,
        nsOspfIfPollInterval
            PositiveInteger,
        nsOspfIfState
            INTEGER,
        nsOspfIfDesignatedRouter
            IpAddress,
        nsOspfIfBackupDesignatedRouter
            IpAddress,
        nsOspfIfEvents
            Counter32,
        nsOspfIfAuthType
            INTEGER,
        nsOspfIfAuthKey
            OCTET STRING,
        nsOspfIfStatus
            RowStatus,
        nsOspfIfMulticastForwarding
            INTEGER,
        nsOspfIfDemand
            TruthValue,
        nsOspfIfVRID
            INTEGER
              }

    nsOspfIfIpAddress OBJECT-TYPE
        SYNTAX   IpAddress
        MAX-ACCESS   read-only
        STATUS   deprecated
        DESCRIPTION
           "The IP address of this OSPF interface."
       ::= { nsOspfIfEntry 1 }

    nsOspfAddressLessIf OBJECT-TYPE
        SYNTAX   Integer32
        MAX-ACCESS   read-only
        STATUS   deprecated
        DESCRIPTION
           "For the purpose of easing  the  instancing  of
           addressed   and  addressless  interfaces;  This
           variable takes the value 0 on  interfaces  with
           IP  Addresses,  and  the corresponding value of
           ifIndex for interfaces having no IP Address."
       ::= { nsOspfIfEntry 2 }

    nsOspfIfAreaId OBJECT-TYPE
        SYNTAX   AreaID
        MAX-ACCESS   read-create
        STATUS   deprecated
        DESCRIPTION
           "A 32-bit integer uniquely identifying the area
           to  which  the  interface  connects.   Area  ID
           0.0.0.0 is used for the OSPF backbone."
       DEFVAL   { '00000000'H }    -- 0.0.0.0
       ::= { nsOspfIfEntry 3 }

    nsOspfIfType OBJECT-TYPE
        SYNTAX   INTEGER    {
                    broadcast (1),
                    nbma (2),
                    pointToPoint (3),
                    pointToMultipoint (5)
                  }
        MAX-ACCESS   read-create
        STATUS   deprecated
        DESCRIPTION
           "The OSPF interface type.

           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
       ::= { nsOspfIfEntry 4 }

    nsOspfIfAdminStat OBJECT-TYPE
        SYNTAX   Status
        MAX-ACCESS   read-create
        STATUS   deprecated
        DESCRIPTION
           "The OSPF  interface's  administrative  status.
           The  value formed on the interface, and the in-
           terface will be advertised as an internal route
           to  some  area.   The  value 'disabled' denotes
           that the interface is external to OSPF."
       DEFVAL { enabled }
       ::= { nsOspfIfEntry 5 }

    nsOspfIfRtrPriority OBJECT-TYPE
        SYNTAX   DesignatedRouterPriority

        MAX-ACCESS   read-create
        STATUS   deprecated
        DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
       DEFVAL { 1 }
       ::= { nsOspfIfEntry 6 }

    nsOspfIfTransitDelay OBJECT-TYPE
        SYNTAX   UpToMaxAge
        MAX-ACCESS   read-create
        STATUS   deprecated
        DESCRIPTION
           "The estimated number of seconds  it  takes  to
           transmit  a  link state update packet over this
           interface."
       DEFVAL { 1 }
       ::= { nsOspfIfEntry 7 }

    nsOspfIfRetransInterval OBJECT-TYPE
        SYNTAX   UpToMaxAge
        MAX-ACCESS   read-create
        STATUS   deprecated
        DESCRIPTION
           "The number of seconds between  link-state  ad-
           vertisement  retransmissions,  for  adjacencies
           belonging to this  interface.   This  value  is
           also used when retransmitting database descrip-
           tion and link-state request packets."
       DEFVAL { 5 }
       ::= { nsOspfIfEntry 8 }

    nsOspfIfHelloInterval OBJECT-TYPE
        SYNTAX   HelloRange
        MAX-ACCESS   read-create
        STATUS   deprecated
        DESCRIPTION
           "The length of time, in  seconds,  between  the
           Hello  packets that the router sends on the in-

           terface.  This value must be the same  for  all
           routers attached to a common network."
       DEFVAL { 10 }
       ::= { nsOspfIfEntry 9 }

    nsOspfIfRtrDeadInterval OBJECT-TYPE
        SYNTAX   PositiveInteger
        MAX-ACCESS   read-create
        STATUS   deprecated
        DESCRIPTION
           "The number of seconds that  a  router's  Hello
           packets  have  not been seen before it's neigh-
           bors declare the router down.  This  should  be
           some  multiple  of  the  Hello  interval.  This
           value must be the same for all routers attached
           to a common network."
       DEFVAL { 40 }
       ::= { nsOspfIfEntry 10 }

    nsOspfIfPollInterval OBJECT-TYPE
        SYNTAX   PositiveInteger
        MAX-ACCESS   read-create
        STATUS   deprecated
        DESCRIPTION
           "The larger time interval, in seconds,  between
           the  Hello  packets  sent  to  an inactive non-
           broadcast multi- access neighbor."
       DEFVAL { 120 }
       ::= { nsOspfIfEntry 11 }

    nsOspfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   deprecated
        DESCRIPTION
           "The OSPF Interface State."
       DEFVAL { down }

       ::= { nsOspfIfEntry 12 }

    nsOspfIfDesignatedRouter OBJECT-TYPE
        SYNTAX   IpAddress
        MAX-ACCESS   read-only
        STATUS   deprecated
        DESCRIPTION
           "The IP Address of the Designated Router."
       DEFVAL   { '00000000'H }    -- 0.0.0.0
       ::= { nsOspfIfEntry 13 }

    nsOspfIfBackupDesignatedRouter OBJECT-TYPE
        SYNTAX   IpAddress
        MAX-ACCESS   read-only
        STATUS   deprecated
        DESCRIPTION
           "The  IP  Address  of  the  Backup   Designated
           Router."
       DEFVAL   { '00000000'H }    -- 0.0.0.0
       ::= { nsOspfIfEntry 14 }

    nsOspfIfEvents OBJECT-TYPE
        SYNTAX   Counter32
        MAX-ACCESS   read-only
        STATUS   deprecated
        DESCRIPTION
           "The number of times this  OSPF  interface  has
           changed its state, or an error has occurred."
       ::= { nsOspfIfEntry 15 }

    nsOspfIfAuthKey OBJECT-TYPE
        SYNTAX   OCTET STRING (SIZE (0..256))
        MAX-ACCESS   read-create
        STATUS   deprecated
        DESCRIPTION
           "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-

           ment.

           When read, nsOspfIfAuthKey always returns an  Oc-
           tet String of length zero."
       REFERENCE
          "OSPF Version 2, Section 9  The  Interface  Data
          Structure"
      DEFVAL   { '0000000000000000'H }    -- 0.0.0.0.0.0.0.0
      ::= { nsOspfIfEntry 16 }

    nsOspfIfStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfIfEntry 17 }

    nsOspfIfMulticastForwarding OBJECT-TYPE
        SYNTAX   INTEGER    {
                            blocked (1),        -- no multicast forwarding
                            multicast (2),        -- using multicast address
                            unicast (3)        -- to each OSPF neighbor
                  }
        MAX-ACCESS   read-create
        STATUS   deprecated
        DESCRIPTION
           "The way multicasts should  forwarded  on  this
           interface;  not  forwarded,  forwarded  as data
           link multicasts, or forwarded as data link uni-
           casts.   Data link multicasting is not meaning-
           ful on point to point and NBMA interfaces,  and
           setting nsOspfMulticastForwarding to 0 effective-
           ly disables all multicast forwarding."
       DEFVAL { blocked }
       ::= { nsOspfIfEntry 18 }

    nsOspfIfDemand OBJECT-TYPE
        SYNTAX   TruthValue
        MAX-ACCESS   read-create
        STATUS   deprecated
        DESCRIPTION
           "Indicates whether Demand OSPF procedures (hel-

           lo supression to FULL neighbors and setting the
           DoNotAge flag on proogated LSAs) should be per-
           formed on this interface."
       DEFVAL { false }
       ::= { nsOspfIfEntry 19 }

    nsOspfIfAuthType OBJECT-TYPE
        SYNTAX   INTEGER (0..255)
                    -- none (0),
                    -- simplePassword (1)
                    -- md5 (2)
                    -- reserved for specification by IANA (> 2)
        MAX-ACCESS   read-create
        STATUS   deprecated
        DESCRIPTION
           "The authentication type specified for  an  in-
           terface.   Additional  authentication types may
           be assigned locally."
       REFERENCE
          "OSPF Version 2, Appendix E Authentication"
      DEFVAL { 0 }        -- no authentication, by default
      ::= { nsOspfIfEntry 20 }

    nsOspfIfVRID OBJECT-TYPE
        SYNTAX   INTEGER (0..65535)
        MAX-ACCESS   read-only
        STATUS   deprecated
        DESCRIPTION
           "Virtual Router ID"
       ::= { nsOspfIfEntry 21 }

--  OSPF Interface Metric Table

--      The Metric Table describes the metrics to be advertised
--      for a specified interface at the various types of service.
--      As such, this table is an adjunct of the OSPF Interface
--      Table.

-- Types of service, as defined by RFC 791, have the ability
-- to request low delay, high bandwidth, or reliable linkage.

-- For the purposes of this specification, the measure of
-- bandwidth

--      Metric = 10^8 / ifSpeed

-- is the default value.  For multiple link interfaces, note
-- that ifSpeed is the sum of the individual link speeds.
-- This yields a number having the following typical values:

--      Network Type/bit rate   Metric

--      >= 100 MBPS                 1
--      Ethernet/802.3             10

--      E1                         48
--      T1 (ESF)                   65
--       64 KBPS                 1562
--       56 KBPS                 1785
--       19.2 KBPS               5208
--        9.6 KBPS              10416

-- Routes that are not specified use the default (TOS 0) metric

    nsOspfIfMetricTable OBJECT-TYPE
        SYNTAX   SEQUENCE OF  NsOspfIfMetricEntry
        MAX-ACCESS   not-accessible
        STATUS   deprecated
        DESCRIPTION
           "The TOS metrics for  a  non-virtual  interface
           identified by the interface index."
       REFERENCE
          "OSPF Version 2, Appendix C.3  Router  interface
          parameters"
      ::= { nsOspf 8 }

    nsOspfIfMetricEntry OBJECT-TYPE
        SYNTAX    NsOspfIfMetricEntry
        MAX-ACCESS   not-accessible
        STATUS   deprecated
        DESCRIPTION
           "A particular TOS metric for a non-virtual  in-
           terface identified by the interface index."
       REFERENCE
          "OSPF Version 2, Appendix C.3  Router  interface
          parameters"
      INDEX { nsOspfIfMetricIpAddress,
  nsOspfIfMetricAddressLessIf,
  nsOspfIfMetricTOS,
  nsOspfIfMetricVRID }
      ::= { nsOspfIfMetricTable 1 }

 NsOspfIfMetricEntry ::=
    SEQUENCE {
        nsOspfIfMetricIpAddress
            IpAddress,
        nsOspfIfMetricAddressLessIf
            Integer32,
        nsOspfIfMetricTOS
            TOSType,
        nsOspfIfMetricValue
            Metric,
        nsOspfIfMetricStatus
            RowStatus,
        nsOspfIfMetricVRID
            INTEGER

              }

    nsOspfIfMetricIpAddress OBJECT-TYPE
        SYNTAX   IpAddress
        MAX-ACCESS   read-only
        STATUS   deprecated
        DESCRIPTION
           "The IP address of this OSPF interface.  On row
           creation,  this  can  be  derived  from the in-
           stance."
       ::= { nsOspfIfMetricEntry 1 }

    nsOspfIfMetricAddressLessIf OBJECT-TYPE
        SYNTAX   Integer32
        MAX-ACCESS   read-only
        STATUS   deprecated
        DESCRIPTION
           "For the purpose of easing  the  instancing  of
           addressed   and  addressless  interfaces;  This
           variable takes the value 0 on  interfaces  with
           IP  Addresses, and the value of ifIndex for in-
           terfaces having no IP Address.   On  row  crea-
           tion, this can be derived from the instance."
       ::= { nsOspfIfMetricEntry 2 }

    nsOspfIfMetricTOS OBJECT-TYPE
        SYNTAX   TOSType
        MAX-ACCESS   read-only
        STATUS   deprecated
        DESCRIPTION
           "The type of service metric  being  referenced.
           On  row  creation, this can be derived from the
           instance."
       ::= { nsOspfIfMetricEntry 3 }

    nsOspfIfMetricValue OBJECT-TYPE
        SYNTAX   Metric
        MAX-ACCESS   read-create
        STATUS   deprecated
        DESCRIPTION
           "The metric of using this type  of  service  on
           this interface.  The default value of the TOS 0
           Metric is 10^8 / ifSpeed."
       ::= { nsOspfIfMetricEntry 4 }

    nsOspfIfMetricStatus OBJECT-TYPE

        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfIfMetricEntry 5 }

    nsOspfIfMetricVRID OBJECT-TYPE
        SYNTAX   INTEGER (0..65535)
        MAX-ACCESS   read-only
        STATUS   deprecated
        DESCRIPTION
           "Virtual Router ID"
       ::= { nsOspfIfMetricEntry 6 }

--  OSPF Virtual Interface Table

--      The Virtual Interface Table describes the virtual
--      links that the OSPF Process is configured to
--      carry on.

    nsOspfVirtIfTable OBJECT-TYPE
        SYNTAX   SEQUENCE OF  NsOspfVirtIfEntry
        MAX-ACCESS   not-accessible
        STATUS   deprecated
        DESCRIPTION
           "Information about this router's virtual inter-
           faces."
       REFERENCE
          "OSPF Version  2,  Appendix  C.4   Virtual  link
          parameters"
      ::= { nsOspf 9 }

    nsOspfVirtIfEntry OBJECT-TYPE
        SYNTAX    NsOspfVirtIfEntry
        MAX-ACCESS   not-accessible
        STATUS   deprecated
        DESCRIPTION
           "Information about a single Virtual Interface."
       INDEX { nsOspfVirtIfAreaId, nsOspfVirtIfNeighbor, nsOspfVirtIfVRID }
       ::= { nsOspfVirtIfTable 1 }

 NsOspfVirtIfEntry ::=
    SEQUENCE {
        nsOspfVirtIfAreaId
            AreaID,
        nsOspfVirtIfNeighbor
            RouterID,
        nsOspfVirtIfTransitDelay
            UpToMaxAge,
        nsOspfVirtIfRetransInterval

            UpToMaxAge,
        nsOspfVirtIfHelloInterval
            HelloRange,
        nsOspfVirtIfRtrDeadInterval
            PositiveInteger,
        nsOspfVirtIfState
            INTEGER,
        nsOspfVirtIfEvents
            Counter32,
        nsOspfVirtIfAuthType
            INTEGER,
        nsOspfVirtIfAuthKey
            OCTET STRING,
        nsOspfVirtIfStatus
            RowStatus,
        nsOspfVirtIfVRID
            INTEGER
              }

    nsOspfVirtIfAreaId OBJECT-TYPE
        SYNTAX   AreaID
        MAX-ACCESS   read-only
        STATUS   deprecated
        DESCRIPTION
           "The  Transit  Area  that  the   Virtual   Link
           traverses.  By definition, this is not 0.0.0.0"
       ::= { nsOspfVirtIfEntry 1 }

    nsOspfVirtIfNeighbor OBJECT-TYPE
        SYNTAX   RouterID
        MAX-ACCESS   read-only
        STATUS   deprecated
        DESCRIPTION
           "The Router ID of the Virtual Neighbor."
       ::= { nsOspfVirtIfEntry 2 }

    nsOspfVirtIfTransitDelay OBJECT-TYPE
        SYNTAX   UpToMaxAge
        MAX-ACCESS   read-create
        STATUS   deprecated
        DESCRIPTION
           "The estimated number of seconds  it  takes  to
           transmit  a link- state update packet over this
           interface."
       DEFVAL { 1 }
       ::= { nsOspfVirtIfEntry 3 }

    nsOspfVirtIfRetransInterval OBJECT-TYPE
        SYNTAX   UpToMaxAge
        MAX-ACCESS   read-create
        STATUS   deprecated
        DESCRIPTION
           "The number of seconds between  link-state  ad-
           vertisement  retransmissions,  for  adjacencies
           belonging to this  interface.   This  value  is
           also used when retransmitting database descrip-
           tion  and  link-state  request  packets.   This
           value  should  be well over the expected round-
           trip time."
       DEFVAL { 5 }
       ::= { nsOspfVirtIfEntry 4 }

    nsOspfVirtIfHelloInterval OBJECT-TYPE
        SYNTAX   HelloRange
        MAX-ACCESS   read-create
        STATUS   deprecated
        DESCRIPTION
           "The length of time, in  seconds,  between  the
           Hello  packets that the router sends on the in-
           terface.  This value must be the same  for  the
           virtual neighbor."
       DEFVAL { 10 }
       ::= { nsOspfVirtIfEntry 5 }

    nsOspfVirtIfRtrDeadInterval OBJECT-TYPE
        SYNTAX   PositiveInteger
        MAX-ACCESS   read-create
        STATUS   deprecated
        DESCRIPTION
           "The number of seconds that  a  router's  Hello
           packets  have  not been seen before it's neigh-
           bors declare the router down.  This  should  be
           some  multiple  of  the  Hello  interval.  This
           value must be the same for the  virtual  neigh-
           bor."
       DEFVAL { 60 }
       ::= { nsOspfVirtIfEntry 6 }

    nsOspfVirtIfState OBJECT-TYPE
        SYNTAX   INTEGER    {
                    down (1),            -- these use the same encoding
                    pointToPoint (4)     -- as the nsOspfIfTable

                  }
        MAX-ACCESS   read-only
        STATUS   deprecated
        DESCRIPTION
           "OSPF virtual interface states."
       DEFVAL   { down }
       ::= { nsOspfVirtIfEntry 7 }

    nsOspfVirtIfEvents OBJECT-TYPE
        SYNTAX   Counter32
        MAX-ACCESS   read-only
        STATUS   deprecated
        DESCRIPTION
           "The number of state changes or error events on
           this Virtual Link"
       ::= { nsOspfVirtIfEntry 8 }

    nsOspfVirtIfAuthKey OBJECT-TYPE
        SYNTAX   OCTET STRING (SIZE(0..256))
        MAX-ACCESS   read-create
        STATUS   deprecated
        DESCRIPTION
           "If Authentication Type is simplePassword,  the
           device  will left adjust and zero fill to 8 oc-
           tets.

           Note that unauthenticated  interfaces  need  no
           authentication key, and simple password authen-
           tication cannot use a key of more  than  8  oc-
           tets.  Larger keys are useful only with authen-
           tication mechanisms not specified in this docu-
           ment.

           When  read,  nsOspfVifAuthKey  always  returns  a
           string of length zero."
       REFERENCE
          "OSPF Version 2, Section 9  The  Interface  Data
          Structure"
      DEFVAL   { '0000000000000000'H }    -- 0.0.0.0.0.0.0.0
      ::= { nsOspfVirtIfEntry 9 }

    nsOspfVirtIfStatus OBJECT-TYPE
        SYNTAX   RowStatus
        MAX-ACCESS   read-create
        STATUS   deprecated

        DESCRIPTION
           "This variable displays the status of  the  en-
           try.  Setting it to 'invalid' has the effect of
           rendering it inoperative.  The internal  effect
           (row removal) is implementation dependent."
       ::= { nsOspfVirtIfEntry 10 }

    nsOspfVirtIfAuthType OBJECT-TYPE
        SYNTAX   INTEGER (0..255)
                    -- none (0),
                    -- simplePassword (1)
                    -- md5 (2)
                    -- reserved for specification by IANA (> 2)
        MAX-ACCESS   read-create
        STATUS   deprecated
        DESCRIPTION
           "The authentication type specified for a virtu-
           al  interface.  Additional authentication types
           may be assigned locally."
       REFERENCE
          "OSPF Version 2, Appendix E Authentication"
      DEFVAL { 0 }        -- no authentication, by default
      ::= { nsOspfVirtIfEntry 11 }

    nsOspfVirtIfVRID OBJECT-TYPE
        SYNTAX   INTEGER (0..65535)
        MAX-ACCESS   read-only
        STATUS   deprecated
        DESCRIPTION
           "Virtual Router ID"
       ::= { nsOspfVirtIfEntry 12 }

--  OSPF Neighbor Table

--      The OSPF Neighbor Table describes all neighbors in
--      the locality of the subject router.

    nsOspfNbrTable OBJECT-TYPE
        SYNTAX   SEQUENCE OF  NsOspfNbrEntry
        MAX-ACCESS   not-accessible
        STATUS   deprecated
        DESCRIPTION
           "A table of non-virtual neighbor information."
       REFERENCE
          "OSPF Version 2, Section 10  The  Neighbor  Data
          Structure"
      ::= { nsOspf 10 }

    nsOspfNbrEntry OBJECT-TYPE
        SYNTAX    NsOspfNbrEntry
        MAX-ACCESS   not-accessible
        STATUS   deprecated
        DESCRIPTION

           "The information regarding a single neighbor."
       REFERENCE
          "OSPF Version 2, Section 10  The  Neighbor  Data
          Structure"
      INDEX { nsOspfNbrIpAddr, nsOspfNbrAddressLessIndex, nsOspfNbrVRID }
      ::= { nsOspfNbrTable 1 }

 NsOspfNbrEntry ::=
    SEQUENCE {
        nsOspfNbrIpAddr
            IpAddress,
        nsOspfNbrAddressLessIndex
            InterfaceIndex,
        nsOspfNbrRtrId
            RouterID,
        nsOspfNbrOptions
            Integer32,
        nsOspfNbrPriority
            DesignatedRouterPriority,
        nsOspfNbrState
            INTEGER,
        nsOspfNbrEvents
            Counter32,
        nsOspfNbrLsRetransQLen
            Gauge32,
        nsOspfNbmaNbrStatus
            RowStatus,
        nsOspfNbmaNbrPermanence
            INTEGER,
        nsOspfNbrHelloSuppressed
            TruthValue,
        nsOspfNbrVRID
            INTEGER
              }

    nsOspfNbrIpAddr OBJECT-TYPE
        SYNTAX   IpAddress
        MAX-ACCESS   read-only
        STATUS   deprecated
        DESCRIPTION
           "The IP address this neighbor is using  in  its
           IP  Source  Address.  Note that, on addressless
           links, this will not be 0.0.0.0,  but  the  ad-
           dress of another of the neighbor's interfaces."
       ::= { nsOspfNbrEntry 1 }

    nsOspfNbrAddressLessIndex OBJECT-TYPE
        SYNTAX   InterfaceIndex
        MAX-ACCESS   read-only

        STATUS   deprecated
        DESCRIPTION
           "On an interface having an  IP  Address,  zero.
           On  addressless  interfaces,  the corresponding
           value of ifIndex in the Internet Standard  MIB.
           On  row  creation, this can be derived from the
           instance."
       ::= { nsOspfNbrEntry 2 }

    nsOspfNbrRtrId OBJECT-TYPE
        SYNTAX   RouterID
        MAX-ACCESS   read-only
        STATUS   deprecated
        DESCRIPTION
           "A 32-bit integer (represented as a type  IpAd-
           dress)  uniquely  identifying  the  neighboring
           router in the Autonomous System."
       DEFVAL   { '00000000'H }    -- 0.0.0.0
       ::= { nsOspfNbrEntry 3 }

    nsOspfNbrOptions OBJECT-TYPE
        SYNTAX   Integer32
        MAX-ACCESS   read-only
        STATUS   deprecated
        DESCRIPTION
           "A Bit Mask corresponding to the neighbor's op-
           tions field.

           Bit 0, if set, indicates that the  system  will
           operate  on  Type of Service metrics other than
           TOS 0.  If zero, the neighbor will  ignore  all
           metrics except the TOS 0 metric.

           Bit 1, if set, indicates  that  the  associated
           area  accepts and operates on external informa-
           tion; if zero, it is a stub area.

           Bit 2, if set, indicates that the system is ca-
           pable  of routing IP Multicast datagrams; i.e.,
           that it implements the Multicast Extensions  to
           OSPF.

           Bit 3, if set, indicates  that  the  associated
           area  is  an  NSSA.  These areas are capable of
           carrying type 7 external advertisements,  which
           are  translated into type 5 external advertise-

           ments at NSSA borders."
       REFERENCE
          "OSPF Version 2, Section 12.1.2 Options"
      DEFVAL { 0 }
      ::= { nsOspfNbrEntry 4 }

    nsOspfNbrPriority OBJECT-TYPE
        SYNTAX   DesignatedRouterPriority
        MAX-ACCESS   read-create
        STATUS   deprecated
        DESCRIPTION
           "The priority of this neighbor in the designat-
           ed router election algorithm.  The value 0 sig-
           nifies that the neighbor is not eligible to be-
           come  the  designated router on this particular
           network."
       DEFVAL { 1 }
       ::= { nsOspfNbrEntry 5 }

    nsOspfNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   deprecated
        DESCRIPTION
           "The State of the relationship with this Neigh-
           bor."
       REFERENCE
          "OSPF Version 2, Section 10.1 Neighbor States"
      DEFVAL   { down }
      ::= { nsOspfNbrEntry 6 }

    nsOspfNbrEvents OBJECT-TYPE
        SYNTAX   Counter32
        MAX-ACCESS   read-only
        STATUS   deprecated
        DESCRIPTION

           "The number of times this neighbor relationship
           has changed state, or an error has occurred."
       ::= { nsOspfNbrEntry 7 }

    nsOspfNbrLsRetransQLen OBJECT-TYPE
        SYNTAX   Gauge32
        MAX-ACCESS   read-only
        STATUS   deprecated
        DESCRIPTION
           "The  deprecated  length  of  the   retransmission
           queue."
       ::= { nsOspfNbrEntry 8 }

    nsOspfNbmaNbrStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfNbrEntry 9 }

    nsOspfNbmaNbrPermanence OBJECT-TYPE
        SYNTAX   INTEGER    {
                    dynamic (1),        -- learned through protocol
                    permanent (2)       -- configured address
                  }
        MAX-ACCESS   read-only
        STATUS   deprecated
        DESCRIPTION
           "This variable displays the status of  the  en-
           try.   'dynamic'  and  'permanent' refer to how
           the neighbor became known."
       DEFVAL { permanent }
       ::= { nsOspfNbrEntry 10 }

    nsOspfNbrHelloSuppressed OBJECT-TYPE
        SYNTAX   TruthValue
        MAX-ACCESS   read-only
        STATUS   deprecated
        DESCRIPTION
           "Indicates whether Hellos are being  suppressed

           to the neighbor"
       ::= { nsOspfNbrEntry 11 }

    nsOspfNbrVRID OBJECT-TYPE
        SYNTAX   INTEGER (0..65535)
        MAX-ACCESS   read-only
        STATUS   deprecated
        DESCRIPTION
           "Virtual Router ID"
       ::= { nsOspfNbrEntry 12 }

--  OSPF Virtual Neighbor Table

--      This table describes all virtual neighbors.
--      Since Virtual Links are configured in the
--      virtual interface table, this table is read-only.

    nsOspfVirtNbrTable OBJECT-TYPE
        SYNTAX   SEQUENCE OF  NsOspfVirtNbrEntry
        MAX-ACCESS   not-accessible
        STATUS   deprecated
        DESCRIPTION
           "A table of virtual neighbor information."
       REFERENCE
          "OSPF Version 2, Section 15  Virtual Links"
      ::= { nsOspf 11 }

    nsOspfVirtNbrEntry OBJECT-TYPE
        SYNTAX    NsOspfVirtNbrEntry
        MAX-ACCESS   not-accessible
        STATUS   deprecated
        DESCRIPTION
           "Virtual neighbor information."
       INDEX { nsOspfVirtNbrArea, nsOspfVirtNbrRtrId, nsOspfVirtNbrVRID }
       ::= { nsOspfVirtNbrTable 1 }

 NsOspfVirtNbrEntry ::=
    SEQUENCE {
        nsOspfVirtNbrArea
            AreaID,
        nsOspfVirtNbrRtrId
            RouterID,
        nsOspfVirtNbrIpAddr
            IpAddress,
        nsOspfVirtNbrOptions
            Integer32,
        nsOspfVirtNbrState
            INTEGER,
        nsOspfVirtNbrEvents
            Counter32,
        nsOspfVirtNbrLsRetransQLen
            Gauge32,
        nsOspfVirtNbrHelloSuppressed
                TruthValue,
        nsOspfVirtNbrVRID
            INTEGER

              }

    nsOspfVirtNbrArea OBJECT-TYPE
        SYNTAX   AreaID
        MAX-ACCESS   read-only
        STATUS   deprecated
        DESCRIPTION
           "The Transit Area Identifier."
       ::= { nsOspfVirtNbrEntry 1 }

    nsOspfVirtNbrRtrId OBJECT-TYPE
        SYNTAX   RouterID
        MAX-ACCESS   read-only
        STATUS   deprecated
        DESCRIPTION
           "A  32-bit  integer  uniquely  identifying  the
           neighboring router in the Autonomous System."
       ::= { nsOspfVirtNbrEntry 2 }

    nsOspfVirtNbrIpAddr OBJECT-TYPE
        SYNTAX   IpAddress
        MAX-ACCESS   read-only
        STATUS   deprecated
        DESCRIPTION
           "The IP address this Virtual  Neighbor  is  us-
           ing."
       ::= { nsOspfVirtNbrEntry 3 }

    nsOspfVirtNbrOptions OBJECT-TYPE
        SYNTAX   Integer32
        MAX-ACCESS   read-only
        STATUS   deprecated
        DESCRIPTION
           "A Bit Mask corresponding to the neighbor's op-
           tions field.

           Bit 1, if set, indicates that the  system  will
           operate  on  Type of Service metrics other than
           TOS 0.  If zero, the neighbor will  ignore  all
           metrics except the TOS 0 metric.

           Bit 2, if set, indicates  that  the  system  is
           Network  Multicast  capable; ie, that it imple-
           ments OSPF Multicast Routing."
       ::= { nsOspfVirtNbrEntry 4 }

    nsOspfVirtNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   deprecated
        DESCRIPTION
           "The state of the  Virtual  Neighbor  Relation-
           ship."
       ::= { nsOspfVirtNbrEntry 5 }

    nsOspfVirtNbrEvents OBJECT-TYPE
        SYNTAX   Counter32
        MAX-ACCESS   read-only
        STATUS   deprecated
        DESCRIPTION
           "The number of  times  this  virtual  link  has
           changed its state, or an error has occurred."
       ::= { nsOspfVirtNbrEntry 6 }

    nsOspfVirtNbrLsRetransQLen OBJECT-TYPE
        SYNTAX   Gauge32
        MAX-ACCESS   read-only
        STATUS   deprecated
        DESCRIPTION
           "The  deprecated  length  of  the   retransmission
           queue."
       ::= { nsOspfVirtNbrEntry 7 }

    nsOspfVirtNbrHelloSuppressed OBJECT-TYPE
        SYNTAX   TruthValue
        MAX-ACCESS   read-only
        STATUS   deprecated
        DESCRIPTION
           "Indicates whether Hellos are being  suppressed
           to the neighbor"
       ::= { nsOspfVirtNbrEntry 8 }

    nsOspfVirtNbrVRID OBJECT-TYPE
        SYNTAX   INTEGER (0..65535)
        MAX-ACCESS   read-only
        STATUS   deprecated
        DESCRIPTION
           "Virtual Router ID"
       ::= { nsOspfVirtNbrEntry 9 }

--  OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

    nsOspfExtLsdbTable OBJECT-TYPE
        SYNTAX   SEQUENCE OF  NsOspfExtLsdbEntry
        MAX-ACCESS   not-accessible
        STATUS   deprecated
        DESCRIPTION
           "The OSPF Process's Links State Database."
       REFERENCE
          "OSPF Version 2, Section 12  Link  State  Adver-
          tisements"
      ::= { nsOspf 12 }

    nsOspfExtLsdbEntry OBJECT-TYPE
        SYNTAX    NsOspfExtLsdbEntry
        MAX-ACCESS   not-accessible
        STATUS   deprecated
        DESCRIPTION
           "A single Link State Advertisement."
       INDEX { nsOspfExtLsdbType, nsOspfExtLsdbLsid, nsOspfExtLsdbRouterId, nsOspfExtLsdbVRID }
       ::= { nsOspfExtLsdbTable 1 }

 NsOspfExtLsdbEntry ::=
    SEQUENCE {
        nsOspfExtLsdbType
            INTEGER,
        nsOspfExtLsdbLsid
            IpAddress,
        nsOspfExtLsdbRouterId
            RouterID,
        nsOspfExtLsdbSequence
            Integer32,
        nsOspfExtLsdbAge
            Integer32,
        nsOspfExtLsdbChecksum
            Integer32,
        nsOspfExtLsdbAdvertisement
            OCTET STRING,
        nsOspfExtLsdbVRID
            INTEGER
              }

    nsOspfExtLsdbType OBJECT-TYPE
        SYNTAX   INTEGER    {
                    asExternalLink (5)
                  }
        MAX-ACCESS   read-only
        STATUS   deprecated
        DESCRIPTION
           "The type  of  the  link  state  advertisement.
           Each  link state type has a separate advertise-
           ment format."
       REFERENCE
          "OSPF Version 2, Appendix A.4.1 The  Link  State
          Advertisement header"
      ::= { nsOspfExtLsdbEntry 1 }

    nsOspfExtLsdbLsid OBJECT-TYPE
        SYNTAX   IpAddress
        MAX-ACCESS   read-only
        STATUS   deprecated
        DESCRIPTION
           "The Link State ID is an LS Type Specific field
           containing either a Router ID or an IP Address;
           it identifies the piece of the  routing  domain
           that is being described by the advertisement."
       REFERENCE
          "OSPF Version 2, Section 12.1.4 Link State ID"
      ::= { nsOspfExtLsdbEntry 2 }

    nsOspfExtLsdbRouterId OBJECT-TYPE
        SYNTAX   RouterID
        MAX-ACCESS   read-only
        STATUS   deprecated
        DESCRIPTION
           "The 32 bit number that uniquely identifies the
           originating router in the Autonomous System."
       REFERENCE
          "OSPF Version 2, Appendix C.1 Global parameters"
      ::= { nsOspfExtLsdbEntry 3 }

--  Note that the OSPF Sequence Number is a 32 bit signed
--  integer.  It starts with the value '80000001'h,
--  or -'7FFFFFFF'h, and increments until '7FFFFFFF'h
--  Thus, a typical sequence number will be very negative.

    nsOspfExtLsdbSequence OBJECT-TYPE
        SYNTAX   Integer32
        MAX-ACCESS   read-only
        STATUS   deprecated
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { nsOspfExtLsdbEntry 4 }

    nsOspfExtLsdbAge OBJECT-TYPE
        SYNTAX   Integer32    -- Should be 0..MaxAge
        MAX-ACCESS   read-only
        STATUS   deprecated
        DESCRIPTION
           "This field is the age of the link state adver-
           tisement in seconds."
       REFERENCE
          "OSPF Version 2, Section 12.1.1 LS age"
      ::= { nsOspfExtLsdbEntry 5 }

    nsOspfExtLsdbChecksum OBJECT-TYPE
        SYNTAX   Integer32
        MAX-ACCESS   read-only
        STATUS   deprecated
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { nsOspfExtLsdbEntry 6 }

    nsOspfExtLsdbAdvertisement OBJECT-TYPE

        SYNTAX   OCTET STRING (SIZE(36))
        MAX-ACCESS   read-only
        STATUS   deprecated
        DESCRIPTION
           "The entire Link State Advertisement, including
           its header."
       REFERENCE
          "OSPF Version 2, Section 12  Link  State  Adver-
          tisements"
      ::= { nsOspfExtLsdbEntry 7 }

    nsOspfExtLsdbVRID OBJECT-TYPE
        SYNTAX   INTEGER (0..65535)
        MAX-ACCESS   read-only
        STATUS   deprecated
        DESCRIPTION
           "Virtual Router ID"
       ::= { nsOspfExtLsdbEntry 8 }


--
--      The OSPF Area Aggregate Table
--
--      This table replaces the OSPF Area Summary Table, being an
--      extension of that for CIDR routers.

    nsOspfAreaAggregateTable OBJECT-TYPE
        SYNTAX   SEQUENCE OF  NsOspfAreaAggregateEntry
        MAX-ACCESS   not-accessible
        STATUS   deprecated
        DESCRIPTION
           "A range of IP addresses  specified  by  an  IP
           address/IP  network  mask  pair.   For example,
           class B address range of X.X.X.X with a network
           mask  of  255.255.0.0 includes all IP addresses
           from X.X.0.0  to  X.X.255.255.   Note  that  if
           ranges  are configured such that one range sub-
           sumes  another  range  (e.g.,   10.0.0.0   mask
           255.0.0.0  and  10.1.0.0 mask 255.255.0.0), the
           most specific match is the preferred one."
       REFERENCE
          "OSPF Version 2, Appendix C.2  Area parameters"
      ::= { nsOspf 14 }

    nsOspfAreaAggregateEntry OBJECT-TYPE
        SYNTAX    NsOspfAreaAggregateEntry
        MAX-ACCESS   not-accessible
        STATUS   deprecated
        DESCRIPTION
           "A range of IP addresses  specified  by  an  IP
           address/IP  network  mask  pair.   For example,
           class B address range of X.X.X.X with a network
           mask  of  255.255.0.0 includes all IP addresses
           from X.X.0.0  to  X.X.255.255.   Note  that  if
           ranges are range configured such that one range
           subsumes another  range  (e.g.,  10.0.0.0  mask
           255.0.0.0  and  10.1.0.0 mask 255.255.0.0), the

           most specific match is the preferred one."
       REFERENCE
          "OSPF Version 2, Appendix C.2  Area parameters"
      INDEX { nsOspfAreaAggregateAreaID, nsOspfAreaAggregateLsdbType,
              nsOspfAreaAggregateNet, nsOspfAreaAggregateMask, nsOspfAreaAggregateVRID }
      ::= { nsOspfAreaAggregateTable 1 }

 NsOspfAreaAggregateEntry ::=
    SEQUENCE {
        nsOspfAreaAggregateAreaID
            AreaID,
        nsOspfAreaAggregateLsdbType
            INTEGER,
        nsOspfAreaAggregateNet
            IpAddress,
        nsOspfAreaAggregateMask
            IpAddress,
        nsOspfAreaAggregateStatus
            RowStatus,
        nsOspfAreaAggregateEffect
            INTEGER,
        nsOspfAreaAggregateVRID
            INTEGER
              }

    nsOspfAreaAggregateAreaID OBJECT-TYPE
        SYNTAX   AreaID
        MAX-ACCESS   read-only
        STATUS   deprecated
        DESCRIPTION
           "The Area the Address Aggregate is to be  found
           within."
       REFERENCE
          "OSPF Version 2, Appendix C.2 Area parameters"
      ::= { nsOspfAreaAggregateEntry 1 }

    nsOspfAreaAggregateLsdbType OBJECT-TYPE
        SYNTAX   INTEGER    {
                    summaryLink (3),
                    nssaExternalLink (7)
                  }
        MAX-ACCESS   read-only
        STATUS   deprecated
        DESCRIPTION
           "The type of the Address Aggregate.  This field
           specifies  the  Lsdb type that this Address Ag-
           gregate applies to."
       REFERENCE

          "OSPF Version 2, Appendix A.4.1 The  Link  State
          Advertisement header"
      ::= { nsOspfAreaAggregateEntry 2 }

    nsOspfAreaAggregateNet OBJECT-TYPE
        SYNTAX   IpAddress
        MAX-ACCESS   read-only
        STATUS   deprecated
        DESCRIPTION
           "The IP Address of the Net or Subnet  indicated
           by the range."
       REFERENCE
          "OSPF Version 2, Appendix C.2 Area parameters"
      ::= { nsOspfAreaAggregateEntry 3 }

    nsOspfAreaAggregateMask OBJECT-TYPE
        SYNTAX   IpAddress
        MAX-ACCESS   read-only
        STATUS   deprecated
        DESCRIPTION
           "The Subnet Mask that pertains to  the  Net  or
           Subnet."
       REFERENCE
          "OSPF Version 2, Appendix C.2 Area parameters"
      ::= { nsOspfAreaAggregateEntry 4 }

    nsOspfAreaAggregateStatus OBJECT-TYPE
        SYNTAX   RowStatus
        MAX-ACCESS   read-create
        STATUS   deprecated
        DESCRIPTION
           "This variable displays the status of  the  en-
           try.  Setting it to 'invalid' has the effect of
           rendering it inoperative.  The internal  effect
           (row removal) is implementation dependent."
       ::= { nsOspfAreaAggregateEntry 5 }

    nsOspfAreaAggregateEffect OBJECT-TYPE
        SYNTAX   INTEGER    {
                    advertiseMatching (1),
                    doNotAdvertiseMatching (2)
                  }
        MAX-ACCESS   read-create
        STATUS   deprecated

        DESCRIPTION
           "Subnets subsumed by ranges either trigger  the
           advertisement  of  the indicated aggregate (ad-
           vertiseMatching), or result in the subnet's not
           being advertised at all outside the area."
       DEFVAL   { advertiseMatching }
       ::= { nsOspfAreaAggregateEntry 6 }

    nsOspfAreaAggregateVRID OBJECT-TYPE
        SYNTAX   INTEGER (0..65535)
        MAX-ACCESS   read-only
        STATUS   deprecated
        DESCRIPTION
           "Virtual Router ID"
       ::= { nsOspfAreaAggregateEntry 7 }

END
