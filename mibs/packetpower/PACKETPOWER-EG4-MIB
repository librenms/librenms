-- File Name   : PACKETPOWER-EG4-MIB
-- Date        : Mon, 05 Dec 2022 17:38:30 GMT
-- emxChannels : 1.9.6
-- Author      : Packet Power LLC



PACKETPOWER-EG4-MIB     DEFINITIONS ::= BEGIN
    IMPORTS
        DateAndTime, DisplayString
            FROM SNMPv2-TC
        MODULE-IDENTITY, OBJECT-TYPE, enterprises, Integer32, mib-2
            FROM SNMPv2-SMI
        OBJECT-GROUP
            FROM SNMPv2-CONF;

    packetPowerNodeMIB    MODULE-IDENTITY
        LAST-UPDATED "202212051700Z"
        ORGANIZATION "www.packetpower.com"
        CONTACT-INFO "email: support@packetpower.com"
        DESCRIPTION "Packet Power Node MIB"
        REVISION    "202212051700Z"
        DESCRIPTION "Update to channel list version 1.9.6"
        REVISION    "201706301440Z"
        DESCRIPTION "Update to channel list version 1.7.0"
        REVISION    "201706010914Z"
        DESCRIPTION "Update to channel list version 1.5.0"
        REVISION    "201703060845Z"
        DESCRIPTION "Fix channelId enumeration"
        REVISION    "201611281340Z"
        DESCRIPTION "Correct range for 16-bit GUID elements"
        REVISION    "201611161700Z"
        DESCRIPTION "Fixed validation errors in the MIB"

        ::= { mib-2 78 }

    packetPowerMIBConformance   OBJECT IDENTIFIER
        ::= { packetPowerNodeMIB 3 }

    packetPower     OBJECT IDENTIFIER
        ::=  {  enterprises  33688  }

    eg4     OBJECT IDENTIFIER
        ::=  {  packetPower  4  }

    readingsTable   OBJECT-TYPE
        SYNTAX      SEQUENCE  OF  ReadingsEntry
        MAX-ACCESS      not-accessible
        STATUS      current
        DESCRIPTION     "Table of most recent, time-stamped readings on all channels monitored by each node."
        ::=  { eg4  1 }

    readingsEntry   OBJECT-TYPE
        SYNTAX      ReadingsEntry
        MAX-ACCESS      not-accessible
        STATUS      current
        DESCRIPTION     "Time-stamped reading corresponding to a physical value most recently reported on a given measurement channel."
        INDEX       {  reNodeId1, reNodeId2, reNodeId3, reNodeId4, channelId  }
        ::=  { readingsTable 1 }

    ReadingsEntry  ::=  SEQUENCE {
        reNodeId1  Integer32,
        reNodeId2  Integer32,
        reNodeId3  Integer32,
        reNodeId4  Integer32,
        channelId  INTEGER,
        reNodeIdHex  DisplayString,
        reNodeIdString  DisplayString,
        reChannelName  DisplayString,
        reTime  DateAndTime,
        reUnixTime  Integer32,
        reIso8601Time  DisplayString,
        reValue  Integer32,
        reUnits  DisplayString
        }

    readingsGroup OBJECT-GROUP
        OBJECTS {
            reNodeIdHex,
            reNodeIdString,
            reChannelName,
            reTime,
            reUnixTime,
            reIso8601Time,
            reValue,
            reUnits
            }
        STATUS  current
        DESCRIPTION "Time-stamped reading group"
        ::= { packetPowerMIBConformance 1 }

    reNodeId1       OBJECT-TYPE
        SYNTAX          Integer32  ( 0 .. 65535  )
        MAX-ACCESS          not-accessible
        STATUS          current
        DESCRIPTION         "Node identifier, part 1 of 4 (16 bits, bits 63-48 of the id - part AAAA of AAAA-BBBB-CCCC-DDDD)."
        ::=  {  readingsEntry  1  }


    reNodeId2       OBJECT-TYPE
        SYNTAX          Integer32  ( 0 .. 65535  )
        MAX-ACCESS          not-accessible
        STATUS          current
        DESCRIPTION         "Node identifier, part 2 of 4 (16 bits, bits 47-32 of the id - part BBBB of AAAA-BBBB-CCCC-DDDD)."
        ::=  {  readingsEntry  2  }


    reNodeId3       OBJECT-TYPE
        SYNTAX          Integer32  ( 0 .. 65535  )
        MAX-ACCESS          not-accessible
        STATUS          current
        DESCRIPTION         "Node identifier, part 3 of 4 (16 bits, bits 31-16 of the id - part CCCC of AAAA-BBBB-CCCC-DDDD)."
        ::=  {  readingsEntry  3  }


    reNodeId4       OBJECT-TYPE
        SYNTAX          Integer32  ( 0 .. 65535  )
        MAX-ACCESS          not-accessible
        STATUS          current
        DESCRIPTION         "Node identifier, part 4 of 4 (16 bits, bits 15-0 of the id - part DDDD of AAAA-BBBB-CCCC-DDDD)."
        ::=  {  readingsEntry  4  }


    channelId       OBJECT-TYPE
        SYNTAX          INTEGER  { energy ( 1 ) ,
            energya ( 2 ) ,
            energyb ( 3 ) ,
            energyc ( 4 ) ,
            energyexporta ( 5 ) ,
            energyexportb ( 6 ) ,
            energyexportc ( 7 ) ,
            power ( 10 ) ,
            powera ( 11 ) ,
            powerb ( 12 ) ,
            powerc ( 13 ) ,
            current ( 20 ) ,
            currenta ( 21 ) ,
            currentb ( 22 ) ,
            currentc ( 23 ) ,
            voltage ( 30 ) ,
            voltagea ( 31 ) ,
            voltageb ( 32 ) ,
            voltagec ( 33 ) ,
            frequency ( 50 ) ,
            phaseanglea ( 51 ) ,
            phaseangleb ( 52 ) ,
            phaseanglec ( 53 ) ,
            powerfactora ( 54 ) ,
            powerfactorb ( 55 ) ,
            powerfactorc ( 56 ) ,
            temperature ( 60 ) ,
            var ( 70 ) ,
            vara ( 71 ) ,
            varb ( 72 ) ,
            varc ( 73 ) ,
            host ( 92 ) ,
            uptime ( 93 ) ,
            mostrecentreport ( 95 ) ,
            powersource ( 96 ) ,
            circuittype ( 97 ) ,
            temperature0 ( 100 ) ,
            temperature1 ( 101 ) ,
            temperature2 ( 102 ) ,
            temperature3 ( 103 ) ,
            temperature4 ( 104 ) ,
            temperature5 ( 105 ) ,
            temperature6 ( 106 ) ,
            temperature7 ( 107 ) ,
            temperature8 ( 108 ) ,
            temperature9 ( 109 ) ,
            temperature10 ( 110 ) ,
            temperature11 ( 111 ) ,
            temperature12 ( 112 ) ,
            vah ( 120 ) ,
            vaha ( 121 ) ,
            vahb ( 122 ) ,
            vahc ( 123 ) ,
            vahd ( 124 ) ,
            vahe ( 125 ) ,
            vahf ( 126 ) ,
            powerd ( 127 ) ,
            powere ( 128 ) ,
            powerf ( 129 ) ,
            powerfactord ( 130 ) ,
            powerfactore ( 131 ) ,
            powerfactorf ( 132 ) ,
            vard ( 133 ) ,
            vare ( 134 ) ,
            varf ( 135 ) ,
            vdd ( 190 ) ,
            humidity ( 191 ) ,
            battery ( 192 ) ,
            dewpoint ( 193 ) ,
            pressure ( 201 ) ,
            contact1 ( 211 ) ,
            contact2 ( 212 ) ,
            contact3 ( 213 ) ,
            contact4 ( 214 ) ,
            contact5 ( 215 ) ,
            contact6 ( 216 ) ,
            contact7 ( 217 ) ,
            contact8 ( 218 ) ,
            contact9 ( 219 ) ,
            contact10 ( 220 ) ,
            contactcount1 ( 221 ) ,
            contactcount2 ( 222 ) ,
            contactcount3 ( 223 ) ,
            contactcount4 ( 224 ) ,
            contactcount5 ( 225 ) ,
            contactcount6 ( 226 ) ,
            contactcount7 ( 227 ) ,
            contactcount8 ( 228 ) ,
            contactcount9 ( 229 ) ,
            contactcount10 ( 230 ) ,
            contactcount11 ( 231 ) ,
            contactcount12 ( 232 ) ,
            contact11 ( 233 ) ,
            contact12 ( 234 ) ,
            voltaged ( 235 ) ,
            voltagee ( 236 ) ,
            voltagef ( 237 ) ,
            currentd ( 238 ) ,
            currente ( 239 ) ,
            currentf ( 240 ) ,
            currentn ( 248 ) ,
            ah ( 250 ) ,
            aha ( 251 ) ,
            ahb ( 252 ) ,
            ahc ( 253 ) ,
            ahd ( 254 ) ,
            ahe ( 255 ) ,
            ahf ( 256 ) ,
            voltageab ( 260 ) ,
            voltageca ( 261 ) ,
            voltagebc ( 262 ) ,
            phaseid ( 269 ) ,
            phaseida ( 270 ) ,
            phaseidb ( 271 ) ,
            phaseidc ( 272 ) ,
            phaseidd ( 273 ) ,
            phaseide ( 274 ) ,
            phaseidf ( 275 ) ,
            probestatus1 ( 300 ) ,
            probestatus2 ( 301 ) ,
            probestatus3 ( 302 ) ,
            probestatus4 ( 303 ) ,
            probestatus5 ( 304 ) ,
            probestatus6 ( 305 ) ,
            probestatus7 ( 306 ) ,
            probestatus8 ( 307 ) ,
            probestatus9 ( 308 ) ,
            probestatus10 ( 309 ) ,
            probestatus11 ( 310 ) ,
            probestatus12 ( 311 ) ,
            humidity1 ( 320 ) ,
            humidity2 ( 321 ) ,
            humidity3 ( 322 ) ,
            humidity4 ( 323 ) ,
            humidity5 ( 324 ) ,
            humidity6 ( 325 ) ,
            humidity7 ( 326 ) ,
            humidity8 ( 327 ) ,
            humidity9 ( 328 ) ,
            humidity10 ( 329 ) ,
            humidity11 ( 330 ) ,
            humidity12 ( 331 ) ,
            vmax ( 402 ) ,
            imax ( 403 ) ,
            firmwareversion ( 404 ) ,
            firmwareimage ( 405 ) ,
            reportsperminute ( 411 ) ,
            phaselabel ( 412 ) ,
            pue ( 420 ) ,
            j6channelcount ( 430 ) ,
            j6phaselabel ( 431 ) ,
            j6rangea ( 432 ) ,
            j6rangev ( 433 ) ,
            meshtime ( 440 ) ,
            uniquereportrate ( 441 ) ,
            allreportrate ( 442 ) ,
            reportrateest ( 443 ) ,
            coveragerateest ( 444 ) ,
            gatewaynodecount ( 445 ) ,
            gatewaynominalmeshreportinterval ( 446 ) ,
            nodeage ( 447 ) ,
            resetid ( 450 ) ,
            resetcount ( 451 ) ,
            failureflags ( 452 ) ,
            meshleavecount ( 453 ) ,
            meshjoincount ( 454 ) ,
            meshjointime ( 455 ) ,
            boottime ( 456 ) ,
            status ( 457 ) ,
            currentfundamental1a ( 500 ) ,
            currentfundamental1b ( 501 ) ,
            currentfundamental1c ( 502 ) ,
            currentfundamental3a ( 503 ) ,
            currentfundamental3b ( 504 ) ,
            currentfundamental3c ( 505 ) ,
            currentfundamental5a ( 506 ) ,
            currentfundamental5b ( 507 ) ,
            currentfundamental5c ( 508 ) ,
            currentfundamental7a ( 509 ) ,
            currentfundamental7b ( 510 ) ,
            currentfundamental7c ( 511 ) ,
            currentfundamental9a ( 512 ) ,
            currentfundamental9b ( 513 ) ,
            currentfundamental9c ( 514 ) ,
            currentfundamental11a ( 515 ) ,
            currentfundamental11b ( 516 ) ,
            currentfundamental11c ( 517 ) ,
            currentfundamental13a ( 518 ) ,
            currentfundamental13b ( 519 ) ,
            currentfundamental13c ( 520 ) ,
            currentfundamental15a ( 521 ) ,
            currentfundamental15b ( 522 ) ,
            currentfundamental15c ( 523 ) ,
            currentharmonic1a ( 524 ) ,
            currentharmonic1b ( 525 ) ,
            currentharmonic1c ( 526 ) ,
            currentharmonic3a ( 527 ) ,
            currentharmonic3b ( 528 ) ,
            currentharmonic3c ( 529 ) ,
            currentharmonic5a ( 530 ) ,
            currentharmonic5b ( 531 ) ,
            currentharmonic5c ( 532 ) ,
            currentharmonic7a ( 533 ) ,
            currentharmonic7b ( 534 ) ,
            currentharmonic7c ( 535 ) ,
            currentharmonic9a ( 536 ) ,
            currentharmonic9b ( 537 ) ,
            currentharmonic9c ( 538 ) ,
            currentharmonic11a ( 539 ) ,
            currentharmonic11b ( 540 ) ,
            currentharmonic11c ( 541 ) ,
            currentharmonic13a ( 542 ) ,
            currentharmonic13b ( 543 ) ,
            currentharmonic13c ( 544 ) ,
            currentharmonic15a ( 545 ) ,
            currentharmonic15b ( 546 ) ,
            currentharmonic15c ( 547 ) ,
            voltagefundamental1a ( 548 ) ,
            voltagefundamental1b ( 549 ) ,
            voltagefundamental1c ( 550 ) ,
            voltagefundamental3a ( 551 ) ,
            voltagefundamental3b ( 552 ) ,
            voltagefundamental3c ( 553 ) ,
            voltagefundamental5a ( 554 ) ,
            voltagefundamental5b ( 555 ) ,
            voltagefundamental5c ( 556 ) ,
            voltagefundamental7a ( 557 ) ,
            voltagefundamental7b ( 558 ) ,
            voltagefundamental7c ( 559 ) ,
            voltagefundamental9a ( 560 ) ,
            voltagefundamental9b ( 561 ) ,
            voltagefundamental9c ( 562 ) ,
            voltagefundamental11a ( 563 ) ,
            voltagefundamental11b ( 564 ) ,
            voltagefundamental11c ( 565 ) ,
            voltagefundamental13a ( 566 ) ,
            voltagefundamental13b ( 567 ) ,
            voltagefundamental13c ( 568 ) ,
            voltagefundamental15a ( 569 ) ,
            voltagefundamental15b ( 570 ) ,
            voltagefundamental15c ( 571 ) ,
            voltageharmonic1a ( 572 ) ,
            voltageharmonic1b ( 573 ) ,
            voltageharmonic1c ( 574 ) ,
            voltageharmonic3a ( 575 ) ,
            voltageharmonic3b ( 576 ) ,
            voltageharmonic3c ( 577 ) ,
            voltageharmonic5a ( 578 ) ,
            voltageharmonic5b ( 579 ) ,
            voltageharmonic5c ( 580 ) ,
            voltageharmonic7a ( 581 ) ,
            voltageharmonic7b ( 582 ) ,
            voltageharmonic7c ( 583 ) ,
            voltageharmonic9a ( 584 ) ,
            voltageharmonic9b ( 585 ) ,
            voltageharmonic9c ( 586 ) ,
            voltageharmonic11a ( 587 ) ,
            voltageharmonic11b ( 588 ) ,
            voltageharmonic11c ( 589 ) ,
            voltageharmonic13a ( 590 ) ,
            voltageharmonic13b ( 591 ) ,
            voltageharmonic13c ( 592 ) ,
            voltageharmonic15a ( 593 ) ,
            voltageharmonic15b ( 594 ) ,
            voltageharmonic15c ( 595 ) ,
            thdia ( 600 ) ,
            thdib ( 601 ) ,
            thdic ( 602 ) ,
            thdva ( 603 ) ,
            thdvb ( 604 ) ,
            thdvc ( 605 ) ,
            icbreceived ( 610 ) ,
            icbexpected ( 611 ) ,
            icbimage ( 612 ) ,
            icbversion ( 613 ) ,
            batterychargeremaining ( 614 ) ,
            batterycharging ( 615 ) ,
            batterycurrent ( 616 ) ,
            batterydischarging ( 617 ) ,
            batterytimeremaining ( 618 ) ,
            batteryvoltage ( 619 ) ,
            codetected ( 620 ) ,
            gasflow ( 621 ) ,
            metermode ( 622 ) ,
            occupancy ( 623 ) ,
            onbattery ( 624 ) ,
            pulse ( 625 ) ,
            smokedetected ( 626 ) ,
            voltageanglel1l2 ( 627 ) ,
            voltageanglel1l3 ( 628 ) ,
            volume ( 629 ) ,
            voltageanglel2l3 ( 630 ) ,
            current1 ( 32768 ) ,
            current2 ( 32769 ) ,
            current3 ( 32770 ) ,
            current4 ( 32771 ) ,
            current5 ( 32772 ) ,
            current6 ( 32773 ) ,
            current7 ( 32774 ) ,
            current8 ( 32775 ) ,
            current9 ( 32776 ) ,
            current10 ( 32777 ) ,
            current11 ( 32778 ) ,
            current12 ( 32779 ) ,
            current13 ( 32780 ) ,
            current14 ( 32781 ) ,
            current15 ( 32782 ) ,
            current16 ( 32783 ) ,
            current17 ( 32784 ) ,
            current18 ( 32785 ) ,
            current19 ( 32786 ) ,
            current20 ( 32787 ) ,
            current21 ( 32788 ) ,
            current22 ( 32789 ) ,
            current23 ( 32790 ) ,
            current24 ( 32791 ) ,
            current25 ( 32792 ) ,
            current26 ( 32793 ) ,
            current27 ( 32794 ) ,
            current28 ( 32795 ) ,
            current29 ( 32796 ) ,
            current30 ( 32797 ) ,
            current31 ( 32798 ) ,
            current32 ( 32799 ) ,
            current33 ( 32800 ) ,
            current34 ( 32801 ) ,
            current35 ( 32802 ) ,
            current36 ( 32803 ) ,
            current37 ( 32804 ) ,
            current38 ( 32805 ) ,
            current39 ( 32806 ) ,
            current40 ( 32807 ) ,
            current41 ( 32808 ) ,
            current42 ( 32809 ) ,
            current43 ( 32810 ) ,
            current44 ( 32811 ) ,
            current45 ( 32812 ) ,
            current46 ( 32813 ) ,
            current47 ( 32814 ) ,
            current48 ( 32815 ) ,
            current49 ( 32816 ) ,
            current50 ( 32817 ) ,
            current51 ( 32818 ) ,
            current52 ( 32819 ) ,
            current53 ( 32820 ) ,
            current54 ( 32821 ) ,
            current55 ( 32822 ) ,
            current56 ( 32823 ) ,
            current57 ( 32824 ) ,
            current58 ( 32825 ) ,
            current59 ( 32826 ) ,
            current60 ( 32827 ) ,
            current61 ( 32828 ) ,
            current62 ( 32829 ) ,
            current63 ( 32830 ) ,
            current64 ( 32831 ) ,
            current65 ( 32832 ) ,
            current66 ( 32833 ) ,
            current67 ( 32834 ) ,
            current68 ( 32835 ) ,
            current69 ( 32836 ) ,
            current70 ( 32837 ) ,
            current71 ( 32838 ) ,
            current72 ( 32839 ) ,
            current73 ( 32840 ) ,
            current74 ( 32841 ) ,
            current75 ( 32842 ) ,
            current76 ( 32843 ) ,
            current77 ( 32844 ) ,
            current78 ( 32845 ) ,
            current79 ( 32846 ) ,
            current80 ( 32847 ) ,
            current81 ( 32848 ) ,
            current82 ( 32849 ) ,
            current83 ( 32850 ) ,
            current84 ( 32851 ) ,
            current85 ( 32852 ) ,
            current86 ( 32853 ) ,
            current87 ( 32854 ) ,
            current88 ( 32855 ) ,
            current89 ( 32856 ) ,
            current90 ( 32857 ) ,
            current91 ( 32858 ) ,
            current92 ( 32859 ) ,
            current93 ( 32860 ) ,
            current94 ( 32861 ) ,
            current95 ( 32862 ) ,
            current96 ( 32863 ) ,
            current97 ( 32864 ) ,
            current98 ( 32865 ) ,
            current99 ( 32866 ) ,
            current100 ( 32867 ) ,
            current101 ( 32868 ) ,
            current102 ( 32869 ) ,
            current103 ( 32870 ) ,
            current104 ( 32871 ) ,
            current105 ( 32872 ) ,
            current106 ( 32873 ) ,
            current107 ( 32874 ) ,
            current108 ( 32875 ) ,
            current109 ( 32876 ) ,
            current110 ( 32877 ) ,
            current111 ( 32878 ) ,
            current112 ( 32879 ) ,
            current113 ( 32880 ) ,
            current114 ( 32881 ) ,
            current115 ( 32882 ) ,
            current116 ( 32883 ) ,
            current117 ( 32884 ) ,
            current118 ( 32885 ) ,
            current119 ( 32886 ) ,
            current120 ( 32887 ) ,
            current121 ( 32888 ) ,
            current122 ( 32889 ) ,
            current123 ( 32890 ) ,
            current124 ( 32891 ) ,
            current125 ( 32892 ) ,
            current126 ( 32893 ) ,
            current127 ( 32894 ) ,
            current128 ( 32895 ) ,
            ah1 ( 32896 ) ,
            ah2 ( 32897 ) ,
            ah3 ( 32898 ) ,
            ah4 ( 32899 ) ,
            ah5 ( 32900 ) ,
            ah6 ( 32901 ) ,
            ah7 ( 32902 ) ,
            ah8 ( 32903 ) ,
            ah9 ( 32904 ) ,
            ah10 ( 32905 ) ,
            ah11 ( 32906 ) ,
            ah12 ( 32907 ) ,
            ah13 ( 32908 ) ,
            ah14 ( 32909 ) ,
            ah15 ( 32910 ) ,
            ah16 ( 32911 ) ,
            ah17 ( 32912 ) ,
            ah18 ( 32913 ) ,
            ah19 ( 32914 ) ,
            ah20 ( 32915 ) ,
            ah21 ( 32916 ) ,
            ah22 ( 32917 ) ,
            ah23 ( 32918 ) ,
            ah24 ( 32919 ) ,
            ah25 ( 32920 ) ,
            ah26 ( 32921 ) ,
            ah27 ( 32922 ) ,
            ah28 ( 32923 ) ,
            ah29 ( 32924 ) ,
            ah30 ( 32925 ) ,
            ah31 ( 32926 ) ,
            ah32 ( 32927 ) ,
            ah33 ( 32928 ) ,
            ah34 ( 32929 ) ,
            ah35 ( 32930 ) ,
            ah36 ( 32931 ) ,
            ah37 ( 32932 ) ,
            ah38 ( 32933 ) ,
            ah39 ( 32934 ) ,
            ah40 ( 32935 ) ,
            ah41 ( 32936 ) ,
            ah42 ( 32937 ) ,
            ah43 ( 32938 ) ,
            ah44 ( 32939 ) ,
            ah45 ( 32940 ) ,
            ah46 ( 32941 ) ,
            ah47 ( 32942 ) ,
            ah48 ( 32943 ) ,
            ah49 ( 32944 ) ,
            ah50 ( 32945 ) ,
            ah51 ( 32946 ) ,
            ah52 ( 32947 ) ,
            ah53 ( 32948 ) ,
            ah54 ( 32949 ) ,
            ah55 ( 32950 ) ,
            ah56 ( 32951 ) ,
            ah57 ( 32952 ) ,
            ah58 ( 32953 ) ,
            ah59 ( 32954 ) ,
            ah60 ( 32955 ) ,
            ah61 ( 32956 ) ,
            ah62 ( 32957 ) ,
            ah63 ( 32958 ) ,
            ah64 ( 32959 ) ,
            ah65 ( 32960 ) ,
            ah66 ( 32961 ) ,
            ah67 ( 32962 ) ,
            ah68 ( 32963 ) ,
            ah69 ( 32964 ) ,
            ah70 ( 32965 ) ,
            ah71 ( 32966 ) ,
            ah72 ( 32967 ) ,
            ah73 ( 32968 ) ,
            ah74 ( 32969 ) ,
            ah75 ( 32970 ) ,
            ah76 ( 32971 ) ,
            ah77 ( 32972 ) ,
            ah78 ( 32973 ) ,
            ah79 ( 32974 ) ,
            ah80 ( 32975 ) ,
            ah81 ( 32976 ) ,
            ah82 ( 32977 ) ,
            ah83 ( 32978 ) ,
            ah84 ( 32979 ) ,
            ah85 ( 32980 ) ,
            ah86 ( 32981 ) ,
            ah87 ( 32982 ) ,
            ah88 ( 32983 ) ,
            ah89 ( 32984 ) ,
            ah90 ( 32985 ) ,
            ah91 ( 32986 ) ,
            ah92 ( 32987 ) ,
            ah93 ( 32988 ) ,
            ah94 ( 32989 ) ,
            ah95 ( 32990 ) ,
            ah96 ( 32991 ) ,
            ah97 ( 32992 ) ,
            ah98 ( 32993 ) ,
            ah99 ( 32994 ) ,
            ah100 ( 32995 ) ,
            ah101 ( 32996 ) ,
            ah102 ( 32997 ) ,
            ah103 ( 32998 ) ,
            ah104 ( 32999 ) ,
            ah105 ( 33000 ) ,
            ah106 ( 33001 ) ,
            ah107 ( 33002 ) ,
            ah108 ( 33003 ) ,
            ah109 ( 33004 ) ,
            ah110 ( 33005 ) ,
            ah111 ( 33006 ) ,
            ah112 ( 33007 ) ,
            ah113 ( 33008 ) ,
            ah114 ( 33009 ) ,
            ah115 ( 33010 ) ,
            ah116 ( 33011 ) ,
            ah117 ( 33012 ) ,
            ah118 ( 33013 ) ,
            ah119 ( 33014 ) ,
            ah120 ( 33015 ) ,
            ah121 ( 33016 ) ,
            ah122 ( 33017 ) ,
            ah123 ( 33018 ) ,
            ah124 ( 33019 ) ,
            ah125 ( 33020 ) ,
            ah126 ( 33021 ) ,
            ah127 ( 33022 ) ,
            ah128 ( 33023 ) ,
            energy1 ( 33024 ) ,
            energy2 ( 33025 ) ,
            energy3 ( 33026 ) ,
            energy4 ( 33027 ) ,
            energy5 ( 33028 ) ,
            energy6 ( 33029 ) ,
            energy7 ( 33030 ) ,
            energy8 ( 33031 ) ,
            energy9 ( 33032 ) ,
            energy10 ( 33033 ) ,
            energy11 ( 33034 ) ,
            energy12 ( 33035 ) ,
            energy13 ( 33036 ) ,
            energy14 ( 33037 ) ,
            energy15 ( 33038 ) ,
            energy16 ( 33039 ) ,
            energy17 ( 33040 ) ,
            energy18 ( 33041 ) ,
            energy19 ( 33042 ) ,
            energy20 ( 33043 ) ,
            energy21 ( 33044 ) ,
            energy22 ( 33045 ) ,
            energy23 ( 33046 ) ,
            energy24 ( 33047 ) ,
            energy25 ( 33048 ) ,
            energy26 ( 33049 ) ,
            energy27 ( 33050 ) ,
            energy28 ( 33051 ) ,
            energy29 ( 33052 ) ,
            energy30 ( 33053 ) ,
            energy31 ( 33054 ) ,
            energy32 ( 33055 ) ,
            energy33 ( 33056 ) ,
            energy34 ( 33057 ) ,
            energy35 ( 33058 ) ,
            energy36 ( 33059 ) ,
            energy37 ( 33060 ) ,
            energy38 ( 33061 ) ,
            energy39 ( 33062 ) ,
            energy40 ( 33063 ) ,
            energy41 ( 33064 ) ,
            energy42 ( 33065 ) ,
            energy43 ( 33066 ) ,
            energy44 ( 33067 ) ,
            energy45 ( 33068 ) ,
            energy46 ( 33069 ) ,
            energy47 ( 33070 ) ,
            energy48 ( 33071 ) ,
            energy49 ( 33072 ) ,
            energy50 ( 33073 ) ,
            energy51 ( 33074 ) ,
            energy52 ( 33075 ) ,
            energy53 ( 33076 ) ,
            energy54 ( 33077 ) ,
            energy55 ( 33078 ) ,
            energy56 ( 33079 ) ,
            energy57 ( 33080 ) ,
            energy58 ( 33081 ) ,
            energy59 ( 33082 ) ,
            energy60 ( 33083 ) ,
            energy61 ( 33084 ) ,
            energy62 ( 33085 ) ,
            energy63 ( 33086 ) ,
            energy64 ( 33087 ) ,
            energy65 ( 33088 ) ,
            energy66 ( 33089 ) ,
            energy67 ( 33090 ) ,
            energy68 ( 33091 ) ,
            energy69 ( 33092 ) ,
            energy70 ( 33093 ) ,
            energy71 ( 33094 ) ,
            energy72 ( 33095 ) ,
            energy73 ( 33096 ) ,
            energy74 ( 33097 ) ,
            energy75 ( 33098 ) ,
            energy76 ( 33099 ) ,
            energy77 ( 33100 ) ,
            energy78 ( 33101 ) ,
            energy79 ( 33102 ) ,
            energy80 ( 33103 ) ,
            energy81 ( 33104 ) ,
            energy82 ( 33105 ) ,
            energy83 ( 33106 ) ,
            energy84 ( 33107 ) ,
            energy85 ( 33108 ) ,
            energy86 ( 33109 ) ,
            energy87 ( 33110 ) ,
            energy88 ( 33111 ) ,
            energy89 ( 33112 ) ,
            energy90 ( 33113 ) ,
            energy91 ( 33114 ) ,
            energy92 ( 33115 ) ,
            energy93 ( 33116 ) ,
            energy94 ( 33117 ) ,
            energy95 ( 33118 ) ,
            energy96 ( 33119 ) ,
            energy97 ( 33120 ) ,
            energy98 ( 33121 ) ,
            energy99 ( 33122 ) ,
            energy100 ( 33123 ) ,
            energy101 ( 33124 ) ,
            energy102 ( 33125 ) ,
            energy103 ( 33126 ) ,
            energy104 ( 33127 ) ,
            energy105 ( 33128 ) ,
            energy106 ( 33129 ) ,
            energy107 ( 33130 ) ,
            energy108 ( 33131 ) ,
            energy109 ( 33132 ) ,
            energy110 ( 33133 ) ,
            energy111 ( 33134 ) ,
            energy112 ( 33135 ) ,
            energy113 ( 33136 ) ,
            energy114 ( 33137 ) ,
            energy115 ( 33138 ) ,
            energy116 ( 33139 ) ,
            energy117 ( 33140 ) ,
            energy118 ( 33141 ) ,
            energy119 ( 33142 ) ,
            energy120 ( 33143 ) ,
            energy121 ( 33144 ) ,
            energy122 ( 33145 ) ,
            energy123 ( 33146 ) ,
            energy124 ( 33147 ) ,
            energy125 ( 33148 ) ,
            energy126 ( 33149 ) ,
            energy127 ( 33150 ) ,
            energy128 ( 33151 ) ,
            power1 ( 33152 ) ,
            power2 ( 33153 ) ,
            power3 ( 33154 ) ,
            power4 ( 33155 ) ,
            power5 ( 33156 ) ,
            power6 ( 33157 ) ,
            power7 ( 33158 ) ,
            power8 ( 33159 ) ,
            power9 ( 33160 ) ,
            power10 ( 33161 ) ,
            power11 ( 33162 ) ,
            power12 ( 33163 ) ,
            power13 ( 33164 ) ,
            power14 ( 33165 ) ,
            power15 ( 33166 ) ,
            power16 ( 33167 ) ,
            power17 ( 33168 ) ,
            power18 ( 33169 ) ,
            power19 ( 33170 ) ,
            power20 ( 33171 ) ,
            power21 ( 33172 ) ,
            power22 ( 33173 ) ,
            power23 ( 33174 ) ,
            power24 ( 33175 ) ,
            power25 ( 33176 ) ,
            power26 ( 33177 ) ,
            power27 ( 33178 ) ,
            power28 ( 33179 ) ,
            power29 ( 33180 ) ,
            power30 ( 33181 ) ,
            power31 ( 33182 ) ,
            power32 ( 33183 ) ,
            power33 ( 33184 ) ,
            power34 ( 33185 ) ,
            power35 ( 33186 ) ,
            power36 ( 33187 ) ,
            power37 ( 33188 ) ,
            power38 ( 33189 ) ,
            power39 ( 33190 ) ,
            power40 ( 33191 ) ,
            power41 ( 33192 ) ,
            power42 ( 33193 ) ,
            power43 ( 33194 ) ,
            power44 ( 33195 ) ,
            power45 ( 33196 ) ,
            power46 ( 33197 ) ,
            power47 ( 33198 ) ,
            power48 ( 33199 ) ,
            power49 ( 33200 ) ,
            power50 ( 33201 ) ,
            power51 ( 33202 ) ,
            power52 ( 33203 ) ,
            power53 ( 33204 ) ,
            power54 ( 33205 ) ,
            power55 ( 33206 ) ,
            power56 ( 33207 ) ,
            power57 ( 33208 ) ,
            power58 ( 33209 ) ,
            power59 ( 33210 ) ,
            power60 ( 33211 ) ,
            power61 ( 33212 ) ,
            power62 ( 33213 ) ,
            power63 ( 33214 ) ,
            power64 ( 33215 ) ,
            power65 ( 33216 ) ,
            power66 ( 33217 ) ,
            power67 ( 33218 ) ,
            power68 ( 33219 ) ,
            power69 ( 33220 ) ,
            power70 ( 33221 ) ,
            power71 ( 33222 ) ,
            power72 ( 33223 ) ,
            power73 ( 33224 ) ,
            power74 ( 33225 ) ,
            power75 ( 33226 ) ,
            power76 ( 33227 ) ,
            power77 ( 33228 ) ,
            power78 ( 33229 ) ,
            power79 ( 33230 ) ,
            power80 ( 33231 ) ,
            power81 ( 33232 ) ,
            power82 ( 33233 ) ,
            power83 ( 33234 ) ,
            power84 ( 33235 ) ,
            power85 ( 33236 ) ,
            power86 ( 33237 ) ,
            power87 ( 33238 ) ,
            power88 ( 33239 ) ,
            power89 ( 33240 ) ,
            power90 ( 33241 ) ,
            power91 ( 33242 ) ,
            power92 ( 33243 ) ,
            power93 ( 33244 ) ,
            power94 ( 33245 ) ,
            power95 ( 33246 ) ,
            power96 ( 33247 ) ,
            power97 ( 33248 ) ,
            power98 ( 33249 ) ,
            power99 ( 33250 ) ,
            power100 ( 33251 ) ,
            power101 ( 33252 ) ,
            power102 ( 33253 ) ,
            power103 ( 33254 ) ,
            power104 ( 33255 ) ,
            power105 ( 33256 ) ,
            power106 ( 33257 ) ,
            power107 ( 33258 ) ,
            power108 ( 33259 ) ,
            power109 ( 33260 ) ,
            power110 ( 33261 ) ,
            power111 ( 33262 ) ,
            power112 ( 33263 ) ,
            power113 ( 33264 ) ,
            power114 ( 33265 ) ,
            power115 ( 33266 ) ,
            power116 ( 33267 ) ,
            power117 ( 33268 ) ,
            power118 ( 33269 ) ,
            power119 ( 33270 ) ,
            power120 ( 33271 ) ,
            power121 ( 33272 ) ,
            power122 ( 33273 ) ,
            power123 ( 33274 ) ,
            power124 ( 33275 ) ,
            power125 ( 33276 ) ,
            power126 ( 33277 ) ,
            power127 ( 33278 ) ,
            power128 ( 33279 ) ,
            var1 ( 33280 ) ,
            var2 ( 33281 ) ,
            var3 ( 33282 ) ,
            var4 ( 33283 ) ,
            var5 ( 33284 ) ,
            var6 ( 33285 ) ,
            var7 ( 33286 ) ,
            var8 ( 33287 ) ,
            var9 ( 33288 ) ,
            var10 ( 33289 ) ,
            var11 ( 33290 ) ,
            var12 ( 33291 ) ,
            var13 ( 33292 ) ,
            var14 ( 33293 ) ,
            var15 ( 33294 ) ,
            var16 ( 33295 ) ,
            var17 ( 33296 ) ,
            var18 ( 33297 ) ,
            var19 ( 33298 ) ,
            var20 ( 33299 ) ,
            var21 ( 33300 ) ,
            var22 ( 33301 ) ,
            var23 ( 33302 ) ,
            var24 ( 33303 ) ,
            var25 ( 33304 ) ,
            var26 ( 33305 ) ,
            var27 ( 33306 ) ,
            var28 ( 33307 ) ,
            var29 ( 33308 ) ,
            var30 ( 33309 ) ,
            var31 ( 33310 ) ,
            var32 ( 33311 ) ,
            var33 ( 33312 ) ,
            var34 ( 33313 ) ,
            var35 ( 33314 ) ,
            var36 ( 33315 ) ,
            var37 ( 33316 ) ,
            var38 ( 33317 ) ,
            var39 ( 33318 ) ,
            var40 ( 33319 ) ,
            var41 ( 33320 ) ,
            var42 ( 33321 ) ,
            var43 ( 33322 ) ,
            var44 ( 33323 ) ,
            var45 ( 33324 ) ,
            var46 ( 33325 ) ,
            var47 ( 33326 ) ,
            var48 ( 33327 ) ,
            var49 ( 33328 ) ,
            var50 ( 33329 ) ,
            var51 ( 33330 ) ,
            var52 ( 33331 ) ,
            var53 ( 33332 ) ,
            var54 ( 33333 ) ,
            var55 ( 33334 ) ,
            var56 ( 33335 ) ,
            var57 ( 33336 ) ,
            var58 ( 33337 ) ,
            var59 ( 33338 ) ,
            var60 ( 33339 ) ,
            var61 ( 33340 ) ,
            var62 ( 33341 ) ,
            var63 ( 33342 ) ,
            var64 ( 33343 ) ,
            var65 ( 33344 ) ,
            var66 ( 33345 ) ,
            var67 ( 33346 ) ,
            var68 ( 33347 ) ,
            var69 ( 33348 ) ,
            var70 ( 33349 ) ,
            var71 ( 33350 ) ,
            var72 ( 33351 ) ,
            var73 ( 33352 ) ,
            var74 ( 33353 ) ,
            var75 ( 33354 ) ,
            var76 ( 33355 ) ,
            var77 ( 33356 ) ,
            var78 ( 33357 ) ,
            var79 ( 33358 ) ,
            var80 ( 33359 ) ,
            var81 ( 33360 ) ,
            var82 ( 33361 ) ,
            var83 ( 33362 ) ,
            var84 ( 33363 ) ,
            var85 ( 33364 ) ,
            var86 ( 33365 ) ,
            var87 ( 33366 ) ,
            var88 ( 33367 ) ,
            var89 ( 33368 ) ,
            var90 ( 33369 ) ,
            var91 ( 33370 ) ,
            var92 ( 33371 ) ,
            var93 ( 33372 ) ,
            var94 ( 33373 ) ,
            var95 ( 33374 ) ,
            var96 ( 33375 ) ,
            var97 ( 33376 ) ,
            var98 ( 33377 ) ,
            var99 ( 33378 ) ,
            var100 ( 33379 ) ,
            var101 ( 33380 ) ,
            var102 ( 33381 ) ,
            var103 ( 33382 ) ,
            var104 ( 33383 ) ,
            var105 ( 33384 ) ,
            var106 ( 33385 ) ,
            var107 ( 33386 ) ,
            var108 ( 33387 ) ,
            var109 ( 33388 ) ,
            var110 ( 33389 ) ,
            var111 ( 33390 ) ,
            var112 ( 33391 ) ,
            var113 ( 33392 ) ,
            var114 ( 33393 ) ,
            var115 ( 33394 ) ,
            var116 ( 33395 ) ,
            var117 ( 33396 ) ,
            var118 ( 33397 ) ,
            var119 ( 33398 ) ,
            var120 ( 33399 ) ,
            var121 ( 33400 ) ,
            var122 ( 33401 ) ,
            var123 ( 33402 ) ,
            var124 ( 33403 ) ,
            var125 ( 33404 ) ,
            var126 ( 33405 ) ,
            var127 ( 33406 ) ,
            var128 ( 33407 ) ,
            voltage1 ( 33408 ) ,
            voltage2 ( 33409 ) ,
            voltage3 ( 33410 ) ,
            voltage4 ( 33411 ) ,
            voltage5 ( 33412 ) ,
            voltage6 ( 33413 ) ,
            voltage7 ( 33414 ) ,
            voltage8 ( 33415 ) ,
            voltage9 ( 33416 ) ,
            voltage10 ( 33417 ) ,
            voltage11 ( 33418 ) ,
            voltage12 ( 33419 ) ,
            voltage13 ( 33420 ) ,
            voltage14 ( 33421 ) ,
            voltage15 ( 33422 ) ,
            voltage16 ( 33423 ) ,
            voltage17 ( 33424 ) ,
            voltage18 ( 33425 ) ,
            voltage19 ( 33426 ) ,
            voltage20 ( 33427 ) ,
            voltage21 ( 33428 ) ,
            voltage22 ( 33429 ) ,
            voltage23 ( 33430 ) ,
            voltage24 ( 33431 ) ,
            voltage25 ( 33432 ) ,
            voltage26 ( 33433 ) ,
            voltage27 ( 33434 ) ,
            voltage28 ( 33435 ) ,
            voltage29 ( 33436 ) ,
            voltage30 ( 33437 ) ,
            voltage31 ( 33438 ) ,
            voltage32 ( 33439 ) ,
            voltage33 ( 33440 ) ,
            voltage34 ( 33441 ) ,
            voltage35 ( 33442 ) ,
            voltage36 ( 33443 ) ,
            voltage37 ( 33444 ) ,
            voltage38 ( 33445 ) ,
            voltage39 ( 33446 ) ,
            voltage40 ( 33447 ) ,
            voltage41 ( 33448 ) ,
            voltage42 ( 33449 ) ,
            voltage43 ( 33450 ) ,
            voltage44 ( 33451 ) ,
            voltage45 ( 33452 ) ,
            voltage46 ( 33453 ) ,
            voltage47 ( 33454 ) ,
            voltage48 ( 33455 ) ,
            voltage49 ( 33456 ) ,
            voltage50 ( 33457 ) ,
            voltage51 ( 33458 ) ,
            voltage52 ( 33459 ) ,
            voltage53 ( 33460 ) ,
            voltage54 ( 33461 ) ,
            voltage55 ( 33462 ) ,
            voltage56 ( 33463 ) ,
            voltage57 ( 33464 ) ,
            voltage58 ( 33465 ) ,
            voltage59 ( 33466 ) ,
            voltage60 ( 33467 ) ,
            voltage61 ( 33468 ) ,
            voltage62 ( 33469 ) ,
            voltage63 ( 33470 ) ,
            voltage64 ( 33471 ) ,
            voltage65 ( 33472 ) ,
            voltage66 ( 33473 ) ,
            voltage67 ( 33474 ) ,
            voltage68 ( 33475 ) ,
            voltage69 ( 33476 ) ,
            voltage70 ( 33477 ) ,
            voltage71 ( 33478 ) ,
            voltage72 ( 33479 ) ,
            voltage73 ( 33480 ) ,
            voltage74 ( 33481 ) ,
            voltage75 ( 33482 ) ,
            voltage76 ( 33483 ) ,
            voltage77 ( 33484 ) ,
            voltage78 ( 33485 ) ,
            voltage79 ( 33486 ) ,
            voltage80 ( 33487 ) ,
            voltage81 ( 33488 ) ,
            voltage82 ( 33489 ) ,
            voltage83 ( 33490 ) ,
            voltage84 ( 33491 ) ,
            voltage85 ( 33492 ) ,
            voltage86 ( 33493 ) ,
            voltage87 ( 33494 ) ,
            voltage88 ( 33495 ) ,
            voltage89 ( 33496 ) ,
            voltage90 ( 33497 ) ,
            voltage91 ( 33498 ) ,
            voltage92 ( 33499 ) ,
            voltage93 ( 33500 ) ,
            voltage94 ( 33501 ) ,
            voltage95 ( 33502 ) ,
            voltage96 ( 33503 ) ,
            voltage97 ( 33504 ) ,
            voltage98 ( 33505 ) ,
            voltage99 ( 33506 ) ,
            voltage100 ( 33507 ) ,
            voltage101 ( 33508 ) ,
            voltage102 ( 33509 ) ,
            voltage103 ( 33510 ) ,
            voltage104 ( 33511 ) ,
            voltage105 ( 33512 ) ,
            voltage106 ( 33513 ) ,
            voltage107 ( 33514 ) ,
            voltage108 ( 33515 ) ,
            voltage109 ( 33516 ) ,
            voltage110 ( 33517 ) ,
            voltage111 ( 33518 ) ,
            voltage112 ( 33519 ) ,
            voltage113 ( 33520 ) ,
            voltage114 ( 33521 ) ,
            voltage115 ( 33522 ) ,
            voltage116 ( 33523 ) ,
            voltage117 ( 33524 ) ,
            voltage118 ( 33525 ) ,
            voltage119 ( 33526 ) ,
            voltage120 ( 33527 ) ,
            voltage121 ( 33528 ) ,
            voltage122 ( 33529 ) ,
            voltage123 ( 33530 ) ,
            voltage124 ( 33531 ) ,
            voltage125 ( 33532 ) ,
            voltage126 ( 33533 ) ,
            voltage127 ( 33534 ) ,
            voltage128 ( 33535 ) ,
            powerfactor1 ( 33536 ) ,
            powerfactor2 ( 33537 ) ,
            powerfactor3 ( 33538 ) ,
            powerfactor4 ( 33539 ) ,
            powerfactor5 ( 33540 ) ,
            powerfactor6 ( 33541 ) ,
            powerfactor7 ( 33542 ) ,
            powerfactor8 ( 33543 ) ,
            powerfactor9 ( 33544 ) ,
            powerfactor10 ( 33545 ) ,
            powerfactor11 ( 33546 ) ,
            powerfactor12 ( 33547 ) ,
            powerfactor13 ( 33548 ) ,
            powerfactor14 ( 33549 ) ,
            powerfactor15 ( 33550 ) ,
            powerfactor16 ( 33551 ) ,
            powerfactor17 ( 33552 ) ,
            powerfactor18 ( 33553 ) ,
            powerfactor19 ( 33554 ) ,
            powerfactor20 ( 33555 ) ,
            powerfactor21 ( 33556 ) ,
            powerfactor22 ( 33557 ) ,
            powerfactor23 ( 33558 ) ,
            powerfactor24 ( 33559 ) ,
            powerfactor25 ( 33560 ) ,
            powerfactor26 ( 33561 ) ,
            powerfactor27 ( 33562 ) ,
            powerfactor28 ( 33563 ) ,
            powerfactor29 ( 33564 ) ,
            powerfactor30 ( 33565 ) ,
            powerfactor31 ( 33566 ) ,
            powerfactor32 ( 33567 ) ,
            powerfactor33 ( 33568 ) ,
            powerfactor34 ( 33569 ) ,
            powerfactor35 ( 33570 ) ,
            powerfactor36 ( 33571 ) ,
            powerfactor37 ( 33572 ) ,
            powerfactor38 ( 33573 ) ,
            powerfactor39 ( 33574 ) ,
            powerfactor40 ( 33575 ) ,
            powerfactor41 ( 33576 ) ,
            powerfactor42 ( 33577 ) ,
            powerfactor43 ( 33578 ) ,
            powerfactor44 ( 33579 ) ,
            powerfactor45 ( 33580 ) ,
            powerfactor46 ( 33581 ) ,
            powerfactor47 ( 33582 ) ,
            powerfactor48 ( 33583 ) ,
            powerfactor49 ( 33584 ) ,
            powerfactor50 ( 33585 ) ,
            powerfactor51 ( 33586 ) ,
            powerfactor52 ( 33587 ) ,
            powerfactor53 ( 33588 ) ,
            powerfactor54 ( 33589 ) ,
            powerfactor55 ( 33590 ) ,
            powerfactor56 ( 33591 ) ,
            powerfactor57 ( 33592 ) ,
            powerfactor58 ( 33593 ) ,
            powerfactor59 ( 33594 ) ,
            powerfactor60 ( 33595 ) ,
            powerfactor61 ( 33596 ) ,
            powerfactor62 ( 33597 ) ,
            powerfactor63 ( 33598 ) ,
            powerfactor64 ( 33599 ) ,
            powerfactor65 ( 33600 ) ,
            powerfactor66 ( 33601 ) ,
            powerfactor67 ( 33602 ) ,
            powerfactor68 ( 33603 ) ,
            powerfactor69 ( 33604 ) ,
            powerfactor70 ( 33605 ) ,
            powerfactor71 ( 33606 ) ,
            powerfactor72 ( 33607 ) ,
            powerfactor73 ( 33608 ) ,
            powerfactor74 ( 33609 ) ,
            powerfactor75 ( 33610 ) ,
            powerfactor76 ( 33611 ) ,
            powerfactor77 ( 33612 ) ,
            powerfactor78 ( 33613 ) ,
            powerfactor79 ( 33614 ) ,
            powerfactor80 ( 33615 ) ,
            powerfactor81 ( 33616 ) ,
            powerfactor82 ( 33617 ) ,
            powerfactor83 ( 33618 ) ,
            powerfactor84 ( 33619 ) ,
            powerfactor85 ( 33620 ) ,
            powerfactor86 ( 33621 ) ,
            powerfactor87 ( 33622 ) ,
            powerfactor88 ( 33623 ) ,
            powerfactor89 ( 33624 ) ,
            powerfactor90 ( 33625 ) ,
            powerfactor91 ( 33626 ) ,
            powerfactor92 ( 33627 ) ,
            powerfactor93 ( 33628 ) ,
            powerfactor94 ( 33629 ) ,
            powerfactor95 ( 33630 ) ,
            powerfactor96 ( 33631 ) ,
            powerfactor97 ( 33632 ) ,
            powerfactor98 ( 33633 ) ,
            powerfactor99 ( 33634 ) ,
            powerfactor100 ( 33635 ) ,
            powerfactor101 ( 33636 ) ,
            powerfactor102 ( 33637 ) ,
            powerfactor103 ( 33638 ) ,
            powerfactor104 ( 33639 ) ,
            powerfactor105 ( 33640 ) ,
            powerfactor106 ( 33641 ) ,
            powerfactor107 ( 33642 ) ,
            powerfactor108 ( 33643 ) ,
            powerfactor109 ( 33644 ) ,
            powerfactor110 ( 33645 ) ,
            powerfactor111 ( 33646 ) ,
            powerfactor112 ( 33647 ) ,
            powerfactor113 ( 33648 ) ,
            powerfactor114 ( 33649 ) ,
            powerfactor115 ( 33650 ) ,
            powerfactor116 ( 33651 ) ,
            powerfactor117 ( 33652 ) ,
            powerfactor118 ( 33653 ) ,
            powerfactor119 ( 33654 ) ,
            powerfactor120 ( 33655 ) ,
            powerfactor121 ( 33656 ) ,
            powerfactor122 ( 33657 ) ,
            powerfactor123 ( 33658 ) ,
            powerfactor124 ( 33659 ) ,
            powerfactor125 ( 33660 ) ,
            powerfactor126 ( 33661 ) ,
            powerfactor127 ( 33662 ) ,
            powerfactor128 ( 33663 ) ,
            circuittype1 ( 33664 ) ,
            circuittype2 ( 33665 ) ,
            circuittype3 ( 33666 ) ,
            circuittype4 ( 33667 ) ,
            circuittype5 ( 33668 ) ,
            circuittype6 ( 33669 ) ,
            circuittype7 ( 33670 ) ,
            circuittype8 ( 33671 ) ,
            circuittype9 ( 33672 ) ,
            circuittype10 ( 33673 ) ,
            circuittype11 ( 33674 ) ,
            circuittype12 ( 33675 ) ,
            circuittype13 ( 33676 ) ,
            circuittype14 ( 33677 ) ,
            circuittype15 ( 33678 ) ,
            circuittype16 ( 33679 ) ,
            circuittype17 ( 33680 ) ,
            circuittype18 ( 33681 ) ,
            circuittype19 ( 33682 ) ,
            circuittype20 ( 33683 ) ,
            circuittype21 ( 33684 ) ,
            circuittype22 ( 33685 ) ,
            circuittype23 ( 33686 ) ,
            circuittype24 ( 33687 ) ,
            circuittype25 ( 33688 ) ,
            circuittype26 ( 33689 ) ,
            circuittype27 ( 33690 ) ,
            circuittype28 ( 33691 ) ,
            circuittype29 ( 33692 ) ,
            circuittype30 ( 33693 ) ,
            circuittype31 ( 33694 ) ,
            circuittype32 ( 33695 ) ,
            circuittype33 ( 33696 ) ,
            circuittype34 ( 33697 ) ,
            circuittype35 ( 33698 ) ,
            circuittype36 ( 33699 ) ,
            circuittype37 ( 33700 ) ,
            circuittype38 ( 33701 ) ,
            circuittype39 ( 33702 ) ,
            circuittype40 ( 33703 ) ,
            circuittype41 ( 33704 ) ,
            circuittype42 ( 33705 ) ,
            circuittype43 ( 33706 ) ,
            circuittype44 ( 33707 ) ,
            circuittype45 ( 33708 ) ,
            circuittype46 ( 33709 ) ,
            circuittype47 ( 33710 ) ,
            circuittype48 ( 33711 ) ,
            circuittype49 ( 33712 ) ,
            circuittype50 ( 33713 ) ,
            circuittype51 ( 33714 ) ,
            circuittype52 ( 33715 ) ,
            circuittype53 ( 33716 ) ,
            circuittype54 ( 33717 ) ,
            circuittype55 ( 33718 ) ,
            circuittype56 ( 33719 ) ,
            circuittype57 ( 33720 ) ,
            circuittype58 ( 33721 ) ,
            circuittype59 ( 33722 ) ,
            circuittype60 ( 33723 ) ,
            circuittype61 ( 33724 ) ,
            circuittype62 ( 33725 ) ,
            circuittype63 ( 33726 ) ,
            circuittype64 ( 33727 ) ,
            circuittype65 ( 33728 ) ,
            circuittype66 ( 33729 ) ,
            circuittype67 ( 33730 ) ,
            circuittype68 ( 33731 ) ,
            circuittype69 ( 33732 ) ,
            circuittype70 ( 33733 ) ,
            circuittype71 ( 33734 ) ,
            circuittype72 ( 33735 ) ,
            circuittype73 ( 33736 ) ,
            circuittype74 ( 33737 ) ,
            circuittype75 ( 33738 ) ,
            circuittype76 ( 33739 ) ,
            circuittype77 ( 33740 ) ,
            circuittype78 ( 33741 ) ,
            circuittype79 ( 33742 ) ,
            circuittype80 ( 33743 ) ,
            circuittype81 ( 33744 ) ,
            circuittype82 ( 33745 ) ,
            circuittype83 ( 33746 ) ,
            circuittype84 ( 33747 ) ,
            circuittype85 ( 33748 ) ,
            circuittype86 ( 33749 ) ,
            circuittype87 ( 33750 ) ,
            circuittype88 ( 33751 ) ,
            circuittype89 ( 33752 ) ,
            circuittype90 ( 33753 ) ,
            circuittype91 ( 33754 ) ,
            circuittype92 ( 33755 ) ,
            circuittype93 ( 33756 ) ,
            circuittype94 ( 33757 ) ,
            circuittype95 ( 33758 ) ,
            circuittype96 ( 33759 ) ,
            circuittype97 ( 33760 ) ,
            circuittype98 ( 33761 ) ,
            circuittype99 ( 33762 ) ,
            circuittype100 ( 33763 ) ,
            circuittype101 ( 33764 ) ,
            circuittype102 ( 33765 ) ,
            circuittype103 ( 33766 ) ,
            circuittype104 ( 33767 ) ,
            circuittype105 ( 33768 ) ,
            circuittype106 ( 33769 ) ,
            circuittype107 ( 33770 ) ,
            circuittype108 ( 33771 ) ,
            circuittype109 ( 33772 ) ,
            circuittype110 ( 33773 ) ,
            circuittype111 ( 33774 ) ,
            circuittype112 ( 33775 ) ,
            circuittype113 ( 33776 ) ,
            circuittype114 ( 33777 ) ,
            circuittype115 ( 33778 ) ,
            circuittype116 ( 33779 ) ,
            circuittype117 ( 33780 ) ,
            circuittype118 ( 33781 ) ,
            circuittype119 ( 33782 ) ,
            circuittype120 ( 33783 ) ,
            circuittype121 ( 33784 ) ,
            circuittype122 ( 33785 ) ,
            circuittype123 ( 33786 ) ,
            circuittype124 ( 33787 ) ,
            circuittype125 ( 33788 ) ,
            circuittype126 ( 33789 ) ,
            circuittype127 ( 33790 ) ,
            circuittype128 ( 33791 ) ,
            phaseid1 ( 33792 ) ,
            phaseid2 ( 33793 ) ,
            phaseid3 ( 33794 ) ,
            phaseid4 ( 33795 ) ,
            phaseid5 ( 33796 ) ,
            phaseid6 ( 33797 ) ,
            phaseid7 ( 33798 ) ,
            phaseid8 ( 33799 ) ,
            phaseid9 ( 33800 ) ,
            phaseid10 ( 33801 ) ,
            phaseid11 ( 33802 ) ,
            phaseid12 ( 33803 ) ,
            phaseid13 ( 33804 ) ,
            phaseid14 ( 33805 ) ,
            phaseid15 ( 33806 ) ,
            phaseid16 ( 33807 ) ,
            phaseid17 ( 33808 ) ,
            phaseid18 ( 33809 ) ,
            phaseid19 ( 33810 ) ,
            phaseid20 ( 33811 ) ,
            phaseid21 ( 33812 ) ,
            phaseid22 ( 33813 ) ,
            phaseid23 ( 33814 ) ,
            phaseid24 ( 33815 ) ,
            phaseid25 ( 33816 ) ,
            phaseid26 ( 33817 ) ,
            phaseid27 ( 33818 ) ,
            phaseid28 ( 33819 ) ,
            phaseid29 ( 33820 ) ,
            phaseid30 ( 33821 ) ,
            phaseid31 ( 33822 ) ,
            phaseid32 ( 33823 ) ,
            phaseid33 ( 33824 ) ,
            phaseid34 ( 33825 ) ,
            phaseid35 ( 33826 ) ,
            phaseid36 ( 33827 ) ,
            phaseid37 ( 33828 ) ,
            phaseid38 ( 33829 ) ,
            phaseid39 ( 33830 ) ,
            phaseid40 ( 33831 ) ,
            phaseid41 ( 33832 ) ,
            phaseid42 ( 33833 ) ,
            phaseid43 ( 33834 ) ,
            phaseid44 ( 33835 ) ,
            phaseid45 ( 33836 ) ,
            phaseid46 ( 33837 ) ,
            phaseid47 ( 33838 ) ,
            phaseid48 ( 33839 ) ,
            phaseid49 ( 33840 ) ,
            phaseid50 ( 33841 ) ,
            phaseid51 ( 33842 ) ,
            phaseid52 ( 33843 ) ,
            phaseid53 ( 33844 ) ,
            phaseid54 ( 33845 ) ,
            phaseid55 ( 33846 ) ,
            phaseid56 ( 33847 ) ,
            phaseid57 ( 33848 ) ,
            phaseid58 ( 33849 ) ,
            phaseid59 ( 33850 ) ,
            phaseid60 ( 33851 ) ,
            phaseid61 ( 33852 ) ,
            phaseid62 ( 33853 ) ,
            phaseid63 ( 33854 ) ,
            phaseid64 ( 33855 ) ,
            phaseid65 ( 33856 ) ,
            phaseid66 ( 33857 ) ,
            phaseid67 ( 33858 ) ,
            phaseid68 ( 33859 ) ,
            phaseid69 ( 33860 ) ,
            phaseid70 ( 33861 ) ,
            phaseid71 ( 33862 ) ,
            phaseid72 ( 33863 ) ,
            phaseid73 ( 33864 ) ,
            phaseid74 ( 33865 ) ,
            phaseid75 ( 33866 ) ,
            phaseid76 ( 33867 ) ,
            phaseid77 ( 33868 ) ,
            phaseid78 ( 33869 ) ,
            phaseid79 ( 33870 ) ,
            phaseid80 ( 33871 ) ,
            phaseid81 ( 33872 ) ,
            phaseid82 ( 33873 ) ,
            phaseid83 ( 33874 ) ,
            phaseid84 ( 33875 ) ,
            phaseid85 ( 33876 ) ,
            phaseid86 ( 33877 ) ,
            phaseid87 ( 33878 ) ,
            phaseid88 ( 33879 ) ,
            phaseid89 ( 33880 ) ,
            phaseid90 ( 33881 ) ,
            phaseid91 ( 33882 ) ,
            phaseid92 ( 33883 ) ,
            phaseid93 ( 33884 ) ,
            phaseid94 ( 33885 ) ,
            phaseid95 ( 33886 ) ,
            phaseid96 ( 33887 ) ,
            phaseid97 ( 33888 ) ,
            phaseid98 ( 33889 ) ,
            phaseid99 ( 33890 ) ,
            phaseid100 ( 33891 ) ,
            phaseid101 ( 33892 ) ,
            phaseid102 ( 33893 ) ,
            phaseid103 ( 33894 ) ,
            phaseid104 ( 33895 ) ,
            phaseid105 ( 33896 ) ,
            phaseid106 ( 33897 ) ,
            phaseid107 ( 33898 ) ,
            phaseid108 ( 33899 ) ,
            phaseid109 ( 33900 ) ,
            phaseid110 ( 33901 ) ,
            phaseid111 ( 33902 ) ,
            phaseid112 ( 33903 ) ,
            phaseid113 ( 33904 ) ,
            phaseid114 ( 33905 ) ,
            phaseid115 ( 33906 ) ,
            phaseid116 ( 33907 ) ,
            phaseid117 ( 33908 ) ,
            phaseid118 ( 33909 ) ,
            phaseid119 ( 33910 ) ,
            phaseid120 ( 33911 ) ,
            phaseid121 ( 33912 ) ,
            phaseid122 ( 33913 ) ,
            phaseid123 ( 33914 ) ,
            phaseid124 ( 33915 ) ,
            phaseid125 ( 33916 ) ,
            phaseid126 ( 33917 ) ,
            phaseid127 ( 33918 ) ,
            phaseid128 ( 33919 ) ,
            phaseangle1 ( 33920 ) ,
            phaseangle2 ( 33921 ) ,
            phaseangle3 ( 33922 ) ,
            phaseangle4 ( 33923 ) ,
            phaseangle5 ( 33924 ) ,
            phaseangle6 ( 33925 ) ,
            phaseangle7 ( 33926 ) ,
            phaseangle8 ( 33927 ) ,
            phaseangle9 ( 33928 ) ,
            phaseangle10 ( 33929 ) ,
            phaseangle11 ( 33930 ) ,
            phaseangle12 ( 33931 ) ,
            phaseangle13 ( 33932 ) ,
            phaseangle14 ( 33933 ) ,
            phaseangle15 ( 33934 ) ,
            phaseangle16 ( 33935 ) ,
            phaseangle17 ( 33936 ) ,
            phaseangle18 ( 33937 ) ,
            phaseangle19 ( 33938 ) ,
            phaseangle20 ( 33939 ) ,
            phaseangle21 ( 33940 ) ,
            phaseangle22 ( 33941 ) ,
            phaseangle23 ( 33942 ) ,
            phaseangle24 ( 33943 ) ,
            phaseangle25 ( 33944 ) ,
            phaseangle26 ( 33945 ) ,
            phaseangle27 ( 33946 ) ,
            phaseangle28 ( 33947 ) ,
            phaseangle29 ( 33948 ) ,
            phaseangle30 ( 33949 ) ,
            phaseangle31 ( 33950 ) ,
            phaseangle32 ( 33951 ) ,
            phaseangle33 ( 33952 ) ,
            phaseangle34 ( 33953 ) ,
            phaseangle35 ( 33954 ) ,
            phaseangle36 ( 33955 ) ,
            phaseangle37 ( 33956 ) ,
            phaseangle38 ( 33957 ) ,
            phaseangle39 ( 33958 ) ,
            phaseangle40 ( 33959 ) ,
            phaseangle41 ( 33960 ) ,
            phaseangle42 ( 33961 ) ,
            phaseangle43 ( 33962 ) ,
            phaseangle44 ( 33963 ) ,
            phaseangle45 ( 33964 ) ,
            phaseangle46 ( 33965 ) ,
            phaseangle47 ( 33966 ) ,
            phaseangle48 ( 33967 ) ,
            phaseangle49 ( 33968 ) ,
            phaseangle50 ( 33969 ) ,
            phaseangle51 ( 33970 ) ,
            phaseangle52 ( 33971 ) ,
            phaseangle53 ( 33972 ) ,
            phaseangle54 ( 33973 ) ,
            phaseangle55 ( 33974 ) ,
            phaseangle56 ( 33975 ) ,
            phaseangle57 ( 33976 ) ,
            phaseangle58 ( 33977 ) ,
            phaseangle59 ( 33978 ) ,
            phaseangle60 ( 33979 ) ,
            phaseangle61 ( 33980 ) ,
            phaseangle62 ( 33981 ) ,
            phaseangle63 ( 33982 ) ,
            phaseangle64 ( 33983 ) ,
            phaseangle65 ( 33984 ) ,
            phaseangle66 ( 33985 ) ,
            phaseangle67 ( 33986 ) ,
            phaseangle68 ( 33987 ) ,
            phaseangle69 ( 33988 ) ,
            phaseangle70 ( 33989 ) ,
            phaseangle71 ( 33990 ) ,
            phaseangle72 ( 33991 ) ,
            phaseangle73 ( 33992 ) ,
            phaseangle74 ( 33993 ) ,
            phaseangle75 ( 33994 ) ,
            phaseangle76 ( 33995 ) ,
            phaseangle77 ( 33996 ) ,
            phaseangle78 ( 33997 ) ,
            phaseangle79 ( 33998 ) ,
            phaseangle80 ( 33999 ) ,
            phaseangle81 ( 34000 ) ,
            phaseangle82 ( 34001 ) ,
            phaseangle83 ( 34002 ) ,
            phaseangle84 ( 34003 ) ,
            phaseangle85 ( 34004 ) ,
            phaseangle86 ( 34005 ) ,
            phaseangle87 ( 34006 ) ,
            phaseangle88 ( 34007 ) ,
            phaseangle89 ( 34008 ) ,
            phaseangle90 ( 34009 ) ,
            phaseangle91 ( 34010 ) ,
            phaseangle92 ( 34011 ) ,
            phaseangle93 ( 34012 ) ,
            phaseangle94 ( 34013 ) ,
            phaseangle95 ( 34014 ) ,
            phaseangle96 ( 34015 ) ,
            phaseangle97 ( 34016 ) ,
            phaseangle98 ( 34017 ) ,
            phaseangle99 ( 34018 ) ,
            phaseangle100 ( 34019 ) ,
            phaseangle101 ( 34020 ) ,
            phaseangle102 ( 34021 ) ,
            phaseangle103 ( 34022 ) ,
            phaseangle104 ( 34023 ) ,
            phaseangle105 ( 34024 ) ,
            phaseangle106 ( 34025 ) ,
            phaseangle107 ( 34026 ) ,
            phaseangle108 ( 34027 ) ,
            phaseangle109 ( 34028 ) ,
            phaseangle110 ( 34029 ) ,
            phaseangle111 ( 34030 ) ,
            phaseangle112 ( 34031 ) ,
            phaseangle113 ( 34032 ) ,
            phaseangle114 ( 34033 ) ,
            phaseangle115 ( 34034 ) ,
            phaseangle116 ( 34035 ) ,
            phaseangle117 ( 34036 ) ,
            phaseangle118 ( 34037 ) ,
            phaseangle119 ( 34038 ) ,
            phaseangle120 ( 34039 ) ,
            phaseangle121 ( 34040 ) ,
            phaseangle122 ( 34041 ) ,
            phaseangle123 ( 34042 ) ,
            phaseangle124 ( 34043 ) ,
            phaseangle125 ( 34044 ) ,
            phaseangle126 ( 34045 ) ,
            phaseangle127 ( 34046 ) ,
            phaseangle128 ( 34047 ) ,
            alarm1 ( 34048 ) ,
            alarm2 ( 34049 ) ,
            alarm3 ( 34050 ) ,
            alarm4 ( 34051 ) ,
            alarm5 ( 34052 ) ,
            alarm6 ( 34053 ) ,
            alarm7 ( 34054 ) ,
            alarm8 ( 34055 ) ,
            alarm9 ( 34056 ) ,
            alarm10 ( 34057 ) ,
            alarm11 ( 34058 ) ,
            alarm12 ( 34059 ) ,
            alarm13 ( 34060 ) ,
            alarm14 ( 34061 ) ,
            alarm15 ( 34062 ) ,
            alarm16 ( 34063 ) ,
            alarm17 ( 34064 ) ,
            alarm18 ( 34065 ) ,
            alarm19 ( 34066 ) ,
            alarm20 ( 34067 ) ,
            alarm21 ( 34068 ) ,
            alarm22 ( 34069 ) ,
            alarm23 ( 34070 ) ,
            alarm24 ( 34071 ) ,
            alarm25 ( 34072 ) ,
            alarm26 ( 34073 ) ,
            alarm27 ( 34074 ) ,
            alarm28 ( 34075 ) ,
            alarm29 ( 34076 ) ,
            alarm30 ( 34077 ) ,
            alarm31 ( 34078 ) ,
            alarm32 ( 34079 ) ,
            alarm33 ( 34080 ) ,
            alarm34 ( 34081 ) ,
            alarm35 ( 34082 ) ,
            alarm36 ( 34083 ) ,
            alarm37 ( 34084 ) ,
            alarm38 ( 34085 ) ,
            alarm39 ( 34086 ) ,
            alarm40 ( 34087 ) ,
            alarm41 ( 34088 ) ,
            alarm42 ( 34089 ) ,
            alarm43 ( 34090 ) ,
            alarm44 ( 34091 ) ,
            alarm45 ( 34092 ) ,
            alarm46 ( 34093 ) ,
            alarm47 ( 34094 ) ,
            alarm48 ( 34095 ) ,
            alarm49 ( 34096 ) ,
            alarm50 ( 34097 ) ,
            alarm51 ( 34098 ) ,
            alarm52 ( 34099 ) ,
            alarm53 ( 34100 ) ,
            alarm54 ( 34101 ) ,
            alarm55 ( 34102 ) ,
            alarm56 ( 34103 ) ,
            alarm57 ( 34104 ) ,
            alarm58 ( 34105 ) ,
            alarm59 ( 34106 ) ,
            alarm60 ( 34107 ) ,
            alarm61 ( 34108 ) ,
            alarm62 ( 34109 ) ,
            alarm63 ( 34110 ) ,
            alarm64 ( 34111 ) ,
            alarm65 ( 34112 ) ,
            alarm66 ( 34113 ) ,
            alarm67 ( 34114 ) ,
            alarm68 ( 34115 ) ,
            alarm69 ( 34116 ) ,
            alarm70 ( 34117 ) ,
            alarm71 ( 34118 ) ,
            alarm72 ( 34119 ) ,
            alarm73 ( 34120 ) ,
            alarm74 ( 34121 ) ,
            alarm75 ( 34122 ) ,
            alarm76 ( 34123 ) ,
            alarm77 ( 34124 ) ,
            alarm78 ( 34125 ) ,
            alarm79 ( 34126 ) ,
            alarm80 ( 34127 ) ,
            alarm81 ( 34128 ) ,
            alarm82 ( 34129 ) ,
            alarm83 ( 34130 ) ,
            alarm84 ( 34131 ) ,
            alarm85 ( 34132 ) ,
            alarm86 ( 34133 ) ,
            alarm87 ( 34134 ) ,
            alarm88 ( 34135 ) ,
            alarm89 ( 34136 ) ,
            alarm90 ( 34137 ) ,
            alarm91 ( 34138 ) ,
            alarm92 ( 34139 ) ,
            alarm93 ( 34140 ) ,
            alarm94 ( 34141 ) ,
            alarm95 ( 34142 ) ,
            alarm96 ( 34143 ) ,
            alarm97 ( 34144 ) ,
            alarm98 ( 34145 ) ,
            alarm99 ( 34146 ) ,
            alarm100 ( 34147 ) ,
            alarm101 ( 34148 ) ,
            alarm102 ( 34149 ) ,
            alarm103 ( 34150 ) ,
            alarm104 ( 34151 ) ,
            alarm105 ( 34152 ) ,
            alarm106 ( 34153 ) ,
            alarm107 ( 34154 ) ,
            alarm108 ( 34155 ) ,
            alarm109 ( 34156 ) ,
            alarm110 ( 34157 ) ,
            alarm111 ( 34158 ) ,
            alarm112 ( 34159 ) ,
            alarm113 ( 34160 ) ,
            alarm114 ( 34161 ) ,
            alarm115 ( 34162 ) ,
            alarm116 ( 34163 ) ,
            alarm117 ( 34164 ) ,
            alarm118 ( 34165 ) ,
            alarm119 ( 34166 ) ,
            alarm120 ( 34167 ) ,
            alarm121 ( 34168 ) ,
            alarm122 ( 34169 ) ,
            alarm123 ( 34170 ) ,
            alarm124 ( 34171 ) ,
            alarm125 ( 34172 ) ,
            alarm126 ( 34173 ) ,
            alarm127 ( 34174 ) ,
            alarm128 ( 34175 ) ,
            alarmcount1 ( 34176 ) ,
            alarmcount2 ( 34177 ) ,
            alarmcount3 ( 34178 ) ,
            alarmcount4 ( 34179 ) ,
            alarmcount5 ( 34180 ) ,
            alarmcount6 ( 34181 ) ,
            alarmcount7 ( 34182 ) ,
            alarmcount8 ( 34183 ) ,
            alarmcount9 ( 34184 ) ,
            alarmcount10 ( 34185 ) ,
            alarmcount11 ( 34186 ) ,
            alarmcount12 ( 34187 ) ,
            alarmcount13 ( 34188 ) ,
            alarmcount14 ( 34189 ) ,
            alarmcount15 ( 34190 ) ,
            alarmcount16 ( 34191 ) ,
            alarmcount17 ( 34192 ) ,
            alarmcount18 ( 34193 ) ,
            alarmcount19 ( 34194 ) ,
            alarmcount20 ( 34195 ) ,
            alarmcount21 ( 34196 ) ,
            alarmcount22 ( 34197 ) ,
            alarmcount23 ( 34198 ) ,
            alarmcount24 ( 34199 ) ,
            alarmcount25 ( 34200 ) ,
            alarmcount26 ( 34201 ) ,
            alarmcount27 ( 34202 ) ,
            alarmcount28 ( 34203 ) ,
            alarmcount29 ( 34204 ) ,
            alarmcount30 ( 34205 ) ,
            alarmcount31 ( 34206 ) ,
            alarmcount32 ( 34207 ) ,
            alarmcount33 ( 34208 ) ,
            alarmcount34 ( 34209 ) ,
            alarmcount35 ( 34210 ) ,
            alarmcount36 ( 34211 ) ,
            alarmcount37 ( 34212 ) ,
            alarmcount38 ( 34213 ) ,
            alarmcount39 ( 34214 ) ,
            alarmcount40 ( 34215 ) ,
            alarmcount41 ( 34216 ) ,
            alarmcount42 ( 34217 ) ,
            alarmcount43 ( 34218 ) ,
            alarmcount44 ( 34219 ) ,
            alarmcount45 ( 34220 ) ,
            alarmcount46 ( 34221 ) ,
            alarmcount47 ( 34222 ) ,
            alarmcount48 ( 34223 ) ,
            alarmcount49 ( 34224 ) ,
            alarmcount50 ( 34225 ) ,
            alarmcount51 ( 34226 ) ,
            alarmcount52 ( 34227 ) ,
            alarmcount53 ( 34228 ) ,
            alarmcount54 ( 34229 ) ,
            alarmcount55 ( 34230 ) ,
            alarmcount56 ( 34231 ) ,
            alarmcount57 ( 34232 ) ,
            alarmcount58 ( 34233 ) ,
            alarmcount59 ( 34234 ) ,
            alarmcount60 ( 34235 ) ,
            alarmcount61 ( 34236 ) ,
            alarmcount62 ( 34237 ) ,
            alarmcount63 ( 34238 ) ,
            alarmcount64 ( 34239 ) ,
            alarmcount65 ( 34240 ) ,
            alarmcount66 ( 34241 ) ,
            alarmcount67 ( 34242 ) ,
            alarmcount68 ( 34243 ) ,
            alarmcount69 ( 34244 ) ,
            alarmcount70 ( 34245 ) ,
            alarmcount71 ( 34246 ) ,
            alarmcount72 ( 34247 ) ,
            alarmcount73 ( 34248 ) ,
            alarmcount74 ( 34249 ) ,
            alarmcount75 ( 34250 ) ,
            alarmcount76 ( 34251 ) ,
            alarmcount77 ( 34252 ) ,
            alarmcount78 ( 34253 ) ,
            alarmcount79 ( 34254 ) ,
            alarmcount80 ( 34255 ) ,
            alarmcount81 ( 34256 ) ,
            alarmcount82 ( 34257 ) ,
            alarmcount83 ( 34258 ) ,
            alarmcount84 ( 34259 ) ,
            alarmcount85 ( 34260 ) ,
            alarmcount86 ( 34261 ) ,
            alarmcount87 ( 34262 ) ,
            alarmcount88 ( 34263 ) ,
            alarmcount89 ( 34264 ) ,
            alarmcount90 ( 34265 ) ,
            alarmcount91 ( 34266 ) ,
            alarmcount92 ( 34267 ) ,
            alarmcount93 ( 34268 ) ,
            alarmcount94 ( 34269 ) ,
            alarmcount95 ( 34270 ) ,
            alarmcount96 ( 34271 ) ,
            alarmcount97 ( 34272 ) ,
            alarmcount98 ( 34273 ) ,
            alarmcount99 ( 34274 ) ,
            alarmcount100 ( 34275 ) ,
            alarmcount101 ( 34276 ) ,
            alarmcount102 ( 34277 ) ,
            alarmcount103 ( 34278 ) ,
            alarmcount104 ( 34279 ) ,
            alarmcount105 ( 34280 ) ,
            alarmcount106 ( 34281 ) ,
            alarmcount107 ( 34282 ) ,
            alarmcount108 ( 34283 ) ,
            alarmcount109 ( 34284 ) ,
            alarmcount110 ( 34285 ) ,
            alarmcount111 ( 34286 ) ,
            alarmcount112 ( 34287 ) ,
            alarmcount113 ( 34288 ) ,
            alarmcount114 ( 34289 ) ,
            alarmcount115 ( 34290 ) ,
            alarmcount116 ( 34291 ) ,
            alarmcount117 ( 34292 ) ,
            alarmcount118 ( 34293 ) ,
            alarmcount119 ( 34294 ) ,
            alarmcount120 ( 34295 ) ,
            alarmcount121 ( 34296 ) ,
            alarmcount122 ( 34297 ) ,
            alarmcount123 ( 34298 ) ,
            alarmcount124 ( 34299 ) ,
            alarmcount125 ( 34300 ) ,
            alarmcount126 ( 34301 ) ,
            alarmcount127 ( 34302 ) ,
            alarmcount128 ( 34303 ) ,
            failure1 ( 34304 ) ,
            failure2 ( 34305 ) ,
            failure3 ( 34306 ) ,
            failure4 ( 34307 ) ,
            failure5 ( 34308 ) ,
            failure6 ( 34309 ) ,
            failure7 ( 34310 ) ,
            failure8 ( 34311 ) ,
            failure9 ( 34312 ) ,
            failure10 ( 34313 ) ,
            failure11 ( 34314 ) ,
            failure12 ( 34315 ) ,
            failure13 ( 34316 ) ,
            failure14 ( 34317 ) ,
            failure15 ( 34318 ) ,
            failure16 ( 34319 ) ,
            failure17 ( 34320 ) ,
            failure18 ( 34321 ) ,
            failure19 ( 34322 ) ,
            failure20 ( 34323 ) ,
            failure21 ( 34324 ) ,
            failure22 ( 34325 ) ,
            failure23 ( 34326 ) ,
            failure24 ( 34327 ) ,
            failure25 ( 34328 ) ,
            failure26 ( 34329 ) ,
            failure27 ( 34330 ) ,
            failure28 ( 34331 ) ,
            failure29 ( 34332 ) ,
            failure30 ( 34333 ) ,
            failure31 ( 34334 ) ,
            failure32 ( 34335 ) ,
            failure33 ( 34336 ) ,
            failure34 ( 34337 ) ,
            failure35 ( 34338 ) ,
            failure36 ( 34339 ) ,
            failure37 ( 34340 ) ,
            failure38 ( 34341 ) ,
            failure39 ( 34342 ) ,
            failure40 ( 34343 ) ,
            failure41 ( 34344 ) ,
            failure42 ( 34345 ) ,
            failure43 ( 34346 ) ,
            failure44 ( 34347 ) ,
            failure45 ( 34348 ) ,
            failure46 ( 34349 ) ,
            failure47 ( 34350 ) ,
            failure48 ( 34351 ) ,
            failure49 ( 34352 ) ,
            failure50 ( 34353 ) ,
            failure51 ( 34354 ) ,
            failure52 ( 34355 ) ,
            failure53 ( 34356 ) ,
            failure54 ( 34357 ) ,
            failure55 ( 34358 ) ,
            failure56 ( 34359 ) ,
            failure57 ( 34360 ) ,
            failure58 ( 34361 ) ,
            failure59 ( 34362 ) ,
            failure60 ( 34363 ) ,
            failure61 ( 34364 ) ,
            failure62 ( 34365 ) ,
            failure63 ( 34366 ) ,
            failure64 ( 34367 ) ,
            failure65 ( 34368 ) ,
            failure66 ( 34369 ) ,
            failure67 ( 34370 ) ,
            failure68 ( 34371 ) ,
            failure69 ( 34372 ) ,
            failure70 ( 34373 ) ,
            failure71 ( 34374 ) ,
            failure72 ( 34375 ) ,
            failure73 ( 34376 ) ,
            failure74 ( 34377 ) ,
            failure75 ( 34378 ) ,
            failure76 ( 34379 ) ,
            failure77 ( 34380 ) ,
            failure78 ( 34381 ) ,
            failure79 ( 34382 ) ,
            failure80 ( 34383 ) ,
            failure81 ( 34384 ) ,
            failure82 ( 34385 ) ,
            failure83 ( 34386 ) ,
            failure84 ( 34387 ) ,
            failure85 ( 34388 ) ,
            failure86 ( 34389 ) ,
            failure87 ( 34390 ) ,
            failure88 ( 34391 ) ,
            failure89 ( 34392 ) ,
            failure90 ( 34393 ) ,
            failure91 ( 34394 ) ,
            failure92 ( 34395 ) ,
            failure93 ( 34396 ) ,
            failure94 ( 34397 ) ,
            failure95 ( 34398 ) ,
            failure96 ( 34399 ) ,
            failure97 ( 34400 ) ,
            failure98 ( 34401 ) ,
            failure99 ( 34402 ) ,
            failure100 ( 34403 ) ,
            failure101 ( 34404 ) ,
            failure102 ( 34405 ) ,
            failure103 ( 34406 ) ,
            failure104 ( 34407 ) ,
            failure105 ( 34408 ) ,
            failure106 ( 34409 ) ,
            failure107 ( 34410 ) ,
            failure108 ( 34411 ) ,
            failure109 ( 34412 ) ,
            failure110 ( 34413 ) ,
            failure111 ( 34414 ) ,
            failure112 ( 34415 ) ,
            failure113 ( 34416 ) ,
            failure114 ( 34417 ) ,
            failure115 ( 34418 ) ,
            failure116 ( 34419 ) ,
            failure117 ( 34420 ) ,
            failure118 ( 34421 ) ,
            failure119 ( 34422 ) ,
            failure120 ( 34423 ) ,
            failure121 ( 34424 ) ,
            failure122 ( 34425 ) ,
            failure123 ( 34426 ) ,
            failure124 ( 34427 ) ,
            failure125 ( 34428 ) ,
            failure126 ( 34429 ) ,
            failure127 ( 34430 ) ,
            failure128 ( 34431 ) ,
            humidity13 ( 34432 ) ,
            humidity14 ( 34433 ) ,
            humidity15 ( 34434 ) ,
            humidity16 ( 34435 ) ,
            humidity17 ( 34436 ) ,
            humidity18 ( 34437 ) ,
            humidity19 ( 34438 ) ,
            humidity20 ( 34439 ) ,
            humidity21 ( 34440 ) ,
            humidity22 ( 34441 ) ,
            humidity23 ( 34442 ) ,
            humidity24 ( 34443 ) ,
            humidity25 ( 34444 ) ,
            humidity26 ( 34445 ) ,
            humidity27 ( 34446 ) ,
            humidity28 ( 34447 ) ,
            humidity29 ( 34448 ) ,
            humidity30 ( 34449 ) ,
            humidity31 ( 34450 ) ,
            humidity32 ( 34451 ) ,
            humidity33 ( 34452 ) ,
            humidity34 ( 34453 ) ,
            humidity35 ( 34454 ) ,
            humidity36 ( 34455 ) ,
            humidity37 ( 34456 ) ,
            humidity38 ( 34457 ) ,
            humidity39 ( 34458 ) ,
            humidity40 ( 34459 ) ,
            humidity41 ( 34460 ) ,
            humidity42 ( 34461 ) ,
            humidity43 ( 34462 ) ,
            humidity44 ( 34463 ) ,
            humidity45 ( 34464 ) ,
            humidity46 ( 34465 ) ,
            humidity47 ( 34466 ) ,
            humidity48 ( 34467 ) ,
            humidity49 ( 34468 ) ,
            humidity50 ( 34469 ) ,
            humidity51 ( 34470 ) ,
            humidity52 ( 34471 ) ,
            humidity53 ( 34472 ) ,
            humidity54 ( 34473 ) ,
            humidity55 ( 34474 ) ,
            humidity56 ( 34475 ) ,
            humidity57 ( 34476 ) ,
            humidity58 ( 34477 ) ,
            humidity59 ( 34478 ) ,
            humidity60 ( 34479 ) ,
            humidity61 ( 34480 ) ,
            humidity62 ( 34481 ) ,
            humidity63 ( 34482 ) ,
            humidity64 ( 34483 ) ,
            humidity65 ( 34484 ) ,
            humidity66 ( 34485 ) ,
            humidity67 ( 34486 ) ,
            humidity68 ( 34487 ) ,
            humidity69 ( 34488 ) ,
            humidity70 ( 34489 ) ,
            humidity71 ( 34490 ) ,
            humidity72 ( 34491 ) ,
            humidity73 ( 34492 ) ,
            humidity74 ( 34493 ) ,
            humidity75 ( 34494 ) ,
            humidity76 ( 34495 ) ,
            humidity77 ( 34496 ) ,
            humidity78 ( 34497 ) ,
            humidity79 ( 34498 ) ,
            humidity80 ( 34499 ) ,
            humidity81 ( 34500 ) ,
            humidity82 ( 34501 ) ,
            humidity83 ( 34502 ) ,
            humidity84 ( 34503 ) ,
            humidity85 ( 34504 ) ,
            humidity86 ( 34505 ) ,
            humidity87 ( 34506 ) ,
            humidity88 ( 34507 ) ,
            humidity89 ( 34508 ) ,
            humidity90 ( 34509 ) ,
            humidity91 ( 34510 ) ,
            humidity92 ( 34511 ) ,
            humidity93 ( 34512 ) ,
            humidity94 ( 34513 ) ,
            humidity95 ( 34514 ) ,
            humidity96 ( 34515 ) ,
            humidity97 ( 34516 ) ,
            humidity98 ( 34517 ) ,
            humidity99 ( 34518 ) ,
            humidity100 ( 34519 ) ,
            humidity101 ( 34520 ) ,
            humidity102 ( 34521 ) ,
            humidity103 ( 34522 ) ,
            humidity104 ( 34523 ) ,
            humidity105 ( 34524 ) ,
            humidity106 ( 34525 ) ,
            humidity107 ( 34526 ) ,
            humidity108 ( 34527 ) ,
            humidity109 ( 34528 ) ,
            humidity110 ( 34529 ) ,
            humidity111 ( 34530 ) ,
            humidity112 ( 34531 ) ,
            humidity113 ( 34532 ) ,
            humidity114 ( 34533 ) ,
            humidity115 ( 34534 ) ,
            humidity116 ( 34535 ) ,
            humidity117 ( 34536 ) ,
            humidity118 ( 34537 ) ,
            humidity119 ( 34538 ) ,
            humidity120 ( 34539 ) ,
            humidity121 ( 34540 ) ,
            humidity122 ( 34541 ) ,
            humidity123 ( 34542 ) ,
            humidity124 ( 34543 ) ,
            humidity125 ( 34544 ) ,
            humidity126 ( 34545 ) ,
            humidity127 ( 34546 ) ,
            humidity128 ( 34547 ) ,
            imax1 ( 34548 ) ,
            imax2 ( 34549 ) ,
            imax3 ( 34550 ) ,
            imax4 ( 34551 ) ,
            imax5 ( 34552 ) ,
            imax6 ( 34553 ) ,
            imax7 ( 34554 ) ,
            imax8 ( 34555 ) ,
            imax9 ( 34556 ) ,
            imax10 ( 34557 ) ,
            imax11 ( 34558 ) ,
            imax12 ( 34559 ) ,
            imax13 ( 34560 ) ,
            imax14 ( 34561 ) ,
            imax15 ( 34562 ) ,
            imax16 ( 34563 ) ,
            imax17 ( 34564 ) ,
            imax18 ( 34565 ) ,
            imax19 ( 34566 ) ,
            imax20 ( 34567 ) ,
            imax21 ( 34568 ) ,
            imax22 ( 34569 ) ,
            imax23 ( 34570 ) ,
            imax24 ( 34571 ) ,
            imax25 ( 34572 ) ,
            imax26 ( 34573 ) ,
            imax27 ( 34574 ) ,
            imax28 ( 34575 ) ,
            imax29 ( 34576 ) ,
            imax30 ( 34577 ) ,
            imax31 ( 34578 ) ,
            imax32 ( 34579 ) ,
            imax33 ( 34580 ) ,
            imax34 ( 34581 ) ,
            imax35 ( 34582 ) ,
            imax36 ( 34583 ) ,
            imax37 ( 34584 ) ,
            imax38 ( 34585 ) ,
            imax39 ( 34586 ) ,
            imax40 ( 34587 ) ,
            imax41 ( 34588 ) ,
            imax42 ( 34589 ) ,
            imax43 ( 34590 ) ,
            imax44 ( 34591 ) ,
            imax45 ( 34592 ) ,
            imax46 ( 34593 ) ,
            imax47 ( 34594 ) ,
            imax48 ( 34595 ) ,
            imax49 ( 34596 ) ,
            imax50 ( 34597 ) ,
            imax51 ( 34598 ) ,
            imax52 ( 34599 ) ,
            imax53 ( 34600 ) ,
            imax54 ( 34601 ) ,
            imax55 ( 34602 ) ,
            imax56 ( 34603 ) ,
            imax57 ( 34604 ) ,
            imax58 ( 34605 ) ,
            imax59 ( 34606 ) ,
            imax60 ( 34607 ) ,
            imax61 ( 34608 ) ,
            imax62 ( 34609 ) ,
            imax63 ( 34610 ) ,
            imax64 ( 34611 ) ,
            imax65 ( 34612 ) ,
            imax66 ( 34613 ) ,
            imax67 ( 34614 ) ,
            imax68 ( 34615 ) ,
            imax69 ( 34616 ) ,
            imax70 ( 34617 ) ,
            imax71 ( 34618 ) ,
            imax72 ( 34619 ) ,
            imax73 ( 34620 ) ,
            imax74 ( 34621 ) ,
            imax75 ( 34622 ) ,
            imax76 ( 34623 ) ,
            imax77 ( 34624 ) ,
            imax78 ( 34625 ) ,
            imax79 ( 34626 ) ,
            imax80 ( 34627 ) ,
            imax81 ( 34628 ) ,
            imax82 ( 34629 ) ,
            imax83 ( 34630 ) ,
            imax84 ( 34631 ) ,
            imax85 ( 34632 ) ,
            imax86 ( 34633 ) ,
            imax87 ( 34634 ) ,
            imax88 ( 34635 ) ,
            imax89 ( 34636 ) ,
            imax90 ( 34637 ) ,
            imax91 ( 34638 ) ,
            imax92 ( 34639 ) ,
            imax93 ( 34640 ) ,
            imax94 ( 34641 ) ,
            imax95 ( 34642 ) ,
            imax96 ( 34643 ) ,
            imax97 ( 34644 ) ,
            imax98 ( 34645 ) ,
            imax99 ( 34646 ) ,
            imax100 ( 34647 ) ,
            imax101 ( 34648 ) ,
            imax102 ( 34649 ) ,
            imax103 ( 34650 ) ,
            imax104 ( 34651 ) ,
            imax105 ( 34652 ) ,
            imax106 ( 34653 ) ,
            imax107 ( 34654 ) ,
            imax108 ( 34655 ) ,
            imax109 ( 34656 ) ,
            imax110 ( 34657 ) ,
            imax111 ( 34658 ) ,
            imax112 ( 34659 ) ,
            imax113 ( 34660 ) ,
            imax114 ( 34661 ) ,
            imax115 ( 34662 ) ,
            imax116 ( 34663 ) ,
            imax117 ( 34664 ) ,
            imax118 ( 34665 ) ,
            imax119 ( 34666 ) ,
            imax120 ( 34667 ) ,
            imax121 ( 34668 ) ,
            imax122 ( 34669 ) ,
            imax123 ( 34670 ) ,
            imax124 ( 34671 ) ,
            imax125 ( 34672 ) ,
            imax126 ( 34673 ) ,
            imax127 ( 34674 ) ,
            imax128 ( 34675 ) ,
            genericreading1 ( 34804 ) ,
            genericreading2 ( 34805 ) ,
            genericreading3 ( 34806 ) ,
            genericreading4 ( 34807 ) ,
            genericreading5 ( 34808 ) ,
            genericreading6 ( 34809 ) ,
            genericreading7 ( 34810 ) ,
            genericreading8 ( 34811 ) ,
            genericreading9 ( 34812 ) ,
            genericreading10 ( 34813 ) ,
            genericreading11 ( 34814 ) ,
            genericreading12 ( 34815 ) ,
            genericreading13 ( 34816 ) ,
            genericreading14 ( 34817 ) ,
            genericreading15 ( 34818 ) ,
            genericreading16 ( 34819 ) ,
            genericreading17 ( 34820 ) ,
            genericreading18 ( 34821 ) ,
            genericreading19 ( 34822 ) ,
            genericreading20 ( 34823 ) ,
            genericreading21 ( 34824 ) ,
            genericreading22 ( 34825 ) ,
            genericreading23 ( 34826 ) ,
            genericreading24 ( 34827 ) ,
            genericreading25 ( 34828 ) ,
            genericreading26 ( 34829 ) ,
            genericreading27 ( 34830 ) ,
            genericreading28 ( 34831 ) ,
            genericreading29 ( 34832 ) ,
            genericreading30 ( 34833 ) ,
            genericreading31 ( 34834 ) ,
            genericreading32 ( 34835 ) ,
            genericreading33 ( 34836 ) ,
            genericreading34 ( 34837 ) ,
            genericreading35 ( 34838 ) ,
            genericreading36 ( 34839 ) ,
            genericreading37 ( 34840 ) ,
            genericreading38 ( 34841 ) ,
            genericreading39 ( 34842 ) ,
            genericreading40 ( 34843 ) ,
            genericreading41 ( 34844 ) ,
            genericreading42 ( 34845 ) ,
            genericreading43 ( 34846 ) ,
            genericreading44 ( 34847 ) ,
            genericreading45 ( 34848 ) ,
            genericreading46 ( 34849 ) ,
            genericreading47 ( 34850 ) ,
            genericreading48 ( 34851 ) ,
            genericreading49 ( 34852 ) ,
            genericreading50 ( 34853 ) ,
            genericreading51 ( 34854 ) ,
            genericreading52 ( 34855 ) ,
            genericreading53 ( 34856 ) ,
            genericreading54 ( 34857 ) ,
            genericreading55 ( 34858 ) ,
            genericreading56 ( 34859 ) ,
            genericreading57 ( 34860 ) ,
            genericreading58 ( 34861 ) ,
            genericreading59 ( 34862 ) ,
            genericreading60 ( 34863 ) ,
            genericreading61 ( 34864 ) ,
            genericreading62 ( 34865 ) ,
            genericreading63 ( 34866 ) ,
            genericreading64 ( 34867 ) ,
            genericreading65 ( 34868 ) ,
            genericreading66 ( 34869 ) ,
            genericreading67 ( 34870 ) ,
            genericreading68 ( 34871 ) ,
            genericreading69 ( 34872 ) ,
            genericreading70 ( 34873 ) ,
            genericreading71 ( 34874 ) ,
            genericreading72 ( 34875 ) ,
            genericreading73 ( 34876 ) ,
            genericreading74 ( 34877 ) ,
            genericreading75 ( 34878 ) ,
            genericreading76 ( 34879 ) ,
            genericreading77 ( 34880 ) ,
            genericreading78 ( 34881 ) ,
            genericreading79 ( 34882 ) ,
            genericreading80 ( 34883 ) ,
            genericreading81 ( 34884 ) ,
            genericreading82 ( 34885 ) ,
            genericreading83 ( 34886 ) ,
            genericreading84 ( 34887 ) ,
            genericreading85 ( 34888 ) ,
            genericreading86 ( 34889 ) ,
            genericreading87 ( 34890 ) ,
            genericreading88 ( 34891 ) ,
            genericreading89 ( 34892 ) ,
            genericreading90 ( 34893 ) ,
            genericreading91 ( 34894 ) ,
            genericreading92 ( 34895 ) ,
            genericreading93 ( 34896 ) ,
            genericreading94 ( 34897 ) ,
            genericreading95 ( 34898 ) ,
            genericreading96 ( 34899 ) ,
            genericreading97 ( 34900 ) ,
            genericreading98 ( 34901 ) ,
            genericreading99 ( 34902 ) ,
            genericreading100 ( 34903 ) ,
            genericreading101 ( 34904 ) ,
            genericreading102 ( 34905 ) ,
            genericreading103 ( 34906 ) ,
            genericreading104 ( 34907 ) ,
            genericreading105 ( 34908 ) ,
            genericreading106 ( 34909 ) ,
            genericreading107 ( 34910 ) ,
            genericreading108 ( 34911 ) ,
            genericreading109 ( 34912 ) ,
            genericreading110 ( 34913 ) ,
            genericreading111 ( 34914 ) ,
            genericreading112 ( 34915 ) ,
            genericreading113 ( 34916 ) ,
            genericreading114 ( 34917 ) ,
            genericreading115 ( 34918 ) ,
            genericreading116 ( 34919 ) ,
            genericreading117 ( 34920 ) ,
            genericreading118 ( 34921 ) ,
            genericreading119 ( 34922 ) ,
            genericreading120 ( 34923 ) ,
            genericreading121 ( 34924 ) ,
            genericreading122 ( 34925 ) ,
            genericreading123 ( 34926 ) ,
            genericreading124 ( 34927 ) ,
            genericreading125 ( 34928 ) ,
            genericreading126 ( 34929 ) ,
            genericreading127 ( 34930 ) ,
            genericreading128 ( 34931 ) ,
            genericstatus1 ( 34932 ) ,
            genericstatus2 ( 34933 ) ,
            genericstatus3 ( 34934 ) ,
            genericstatus4 ( 34935 ) ,
            genericstatus5 ( 34936 ) ,
            genericstatus6 ( 34937 ) ,
            genericstatus7 ( 34938 ) ,
            genericstatus8 ( 34939 ) ,
            genericstatus9 ( 34940 ) ,
            genericstatus10 ( 34941 ) ,
            genericstatus11 ( 34942 ) ,
            genericstatus12 ( 34943 ) ,
            genericstatus13 ( 34944 ) ,
            genericstatus14 ( 34945 ) ,
            genericstatus15 ( 34946 ) ,
            genericstatus16 ( 34947 ) ,
            genericstatus17 ( 34948 ) ,
            genericstatus18 ( 34949 ) ,
            genericstatus19 ( 34950 ) ,
            genericstatus20 ( 34951 ) ,
            genericstatus21 ( 34952 ) ,
            genericstatus22 ( 34953 ) ,
            genericstatus23 ( 34954 ) ,
            genericstatus24 ( 34955 ) ,
            genericstatus25 ( 34956 ) ,
            genericstatus26 ( 34957 ) ,
            genericstatus27 ( 34958 ) ,
            genericstatus28 ( 34959 ) ,
            genericstatus29 ( 34960 ) ,
            genericstatus30 ( 34961 ) ,
            genericstatus31 ( 34962 ) ,
            genericstatus32 ( 34963 ) ,
            genericstatus33 ( 34964 ) ,
            genericstatus34 ( 34965 ) ,
            genericstatus35 ( 34966 ) ,
            genericstatus36 ( 34967 ) ,
            genericstatus37 ( 34968 ) ,
            genericstatus38 ( 34969 ) ,
            genericstatus39 ( 34970 ) ,
            genericstatus40 ( 34971 ) ,
            genericstatus41 ( 34972 ) ,
            genericstatus42 ( 34973 ) ,
            genericstatus43 ( 34974 ) ,
            genericstatus44 ( 34975 ) ,
            genericstatus45 ( 34976 ) ,
            genericstatus46 ( 34977 ) ,
            genericstatus47 ( 34978 ) ,
            genericstatus48 ( 34979 ) ,
            genericstatus49 ( 34980 ) ,
            genericstatus50 ( 34981 ) ,
            genericstatus51 ( 34982 ) ,
            genericstatus52 ( 34983 ) ,
            genericstatus53 ( 34984 ) ,
            genericstatus54 ( 34985 ) ,
            genericstatus55 ( 34986 ) ,
            genericstatus56 ( 34987 ) ,
            genericstatus57 ( 34988 ) ,
            genericstatus58 ( 34989 ) ,
            genericstatus59 ( 34990 ) ,
            genericstatus60 ( 34991 ) ,
            genericstatus61 ( 34992 ) ,
            genericstatus62 ( 34993 ) ,
            genericstatus63 ( 34994 ) ,
            genericstatus64 ( 34995 ) ,
            genericstatus65 ( 34996 ) ,
            genericstatus66 ( 34997 ) ,
            genericstatus67 ( 34998 ) ,
            genericstatus68 ( 34999 ) ,
            genericstatus69 ( 35000 ) ,
            genericstatus70 ( 35001 ) ,
            genericstatus71 ( 35002 ) ,
            genericstatus72 ( 35003 ) ,
            genericstatus73 ( 35004 ) ,
            genericstatus74 ( 35005 ) ,
            genericstatus75 ( 35006 ) ,
            genericstatus76 ( 35007 ) ,
            genericstatus77 ( 35008 ) ,
            genericstatus78 ( 35009 ) ,
            genericstatus79 ( 35010 ) ,
            genericstatus80 ( 35011 ) ,
            genericstatus81 ( 35012 ) ,
            genericstatus82 ( 35013 ) ,
            genericstatus83 ( 35014 ) ,
            genericstatus84 ( 35015 ) ,
            genericstatus85 ( 35016 ) ,
            genericstatus86 ( 35017 ) ,
            genericstatus87 ( 35018 ) ,
            genericstatus88 ( 35019 ) ,
            genericstatus89 ( 35020 ) ,
            genericstatus90 ( 35021 ) ,
            genericstatus91 ( 35022 ) ,
            genericstatus92 ( 35023 ) ,
            genericstatus93 ( 35024 ) ,
            genericstatus94 ( 35025 ) ,
            genericstatus95 ( 35026 ) ,
            genericstatus96 ( 35027 ) ,
            genericstatus97 ( 35028 ) ,
            genericstatus98 ( 35029 ) ,
            genericstatus99 ( 35030 ) ,
            genericstatus100 ( 35031 ) ,
            genericstatus101 ( 35032 ) ,
            genericstatus102 ( 35033 ) ,
            genericstatus103 ( 35034 ) ,
            genericstatus104 ( 35035 ) ,
            genericstatus105 ( 35036 ) ,
            genericstatus106 ( 35037 ) ,
            genericstatus107 ( 35038 ) ,
            genericstatus108 ( 35039 ) ,
            genericstatus109 ( 35040 ) ,
            genericstatus110 ( 35041 ) ,
            genericstatus111 ( 35042 ) ,
            genericstatus112 ( 35043 ) ,
            genericstatus113 ( 35044 ) ,
            genericstatus114 ( 35045 ) ,
            genericstatus115 ( 35046 ) ,
            genericstatus116 ( 35047 ) ,
            genericstatus117 ( 35048 ) ,
            genericstatus118 ( 35049 ) ,
            genericstatus119 ( 35050 ) ,
            genericstatus120 ( 35051 ) ,
            genericstatus121 ( 35052 ) ,
            genericstatus122 ( 35053 ) ,
            genericstatus123 ( 35054 ) ,
            genericstatus124 ( 35055 ) ,
            genericstatus125 ( 35056 ) ,
            genericstatus126 ( 35057 ) ,
            genericstatus127 ( 35058 ) ,
            genericstatus128 ( 35059 ) ,
            temperature13 ( 35060 ) ,
            temperature14 ( 35061 ) ,
            temperature15 ( 35062 ) ,
            temperature16 ( 35063 ) ,
            temperature17 ( 35064 ) ,
            temperature18 ( 35065 ) ,
            temperature19 ( 35066 ) ,
            temperature20 ( 35067 ) ,
            temperature21 ( 35068 ) ,
            temperature22 ( 35069 ) ,
            temperature23 ( 35070 ) ,
            temperature24 ( 35071 ) ,
            temperature25 ( 35072 ) ,
            temperature26 ( 35073 ) ,
            temperature27 ( 35074 ) ,
            temperature28 ( 35075 ) ,
            temperature29 ( 35076 ) ,
            temperature30 ( 35077 ) ,
            temperature31 ( 35078 ) ,
            temperature32 ( 35079 ) ,
            temperature33 ( 35080 ) ,
            temperature34 ( 35081 ) ,
            temperature35 ( 35082 ) ,
            temperature36 ( 35083 ) ,
            temperature37 ( 35084 ) ,
            temperature38 ( 35085 ) ,
            temperature39 ( 35086 ) ,
            temperature40 ( 35087 ) ,
            temperature41 ( 35088 ) ,
            temperature42 ( 35089 ) ,
            temperature43 ( 35090 ) ,
            temperature44 ( 35091 ) ,
            temperature45 ( 35092 ) ,
            temperature46 ( 35093 ) ,
            temperature47 ( 35094 ) ,
            temperature48 ( 35095 ) ,
            temperature49 ( 35096 ) ,
            temperature50 ( 35097 ) ,
            temperature51 ( 35098 ) ,
            temperature52 ( 35099 ) ,
            temperature53 ( 35100 ) ,
            temperature54 ( 35101 ) ,
            temperature55 ( 35102 ) ,
            temperature56 ( 35103 ) ,
            temperature57 ( 35104 ) ,
            temperature58 ( 35105 ) ,
            temperature59 ( 35106 ) ,
            temperature60 ( 35107 ) ,
            temperature61 ( 35108 ) ,
            temperature62 ( 35109 ) ,
            temperature63 ( 35110 ) ,
            temperature64 ( 35111 ) ,
            temperature65 ( 35112 ) ,
            temperature66 ( 35113 ) ,
            temperature67 ( 35114 ) ,
            temperature68 ( 35115 ) ,
            temperature69 ( 35116 ) ,
            temperature70 ( 35117 ) ,
            temperature71 ( 35118 ) ,
            temperature72 ( 35119 ) ,
            temperature73 ( 35120 ) ,
            temperature74 ( 35121 ) ,
            temperature75 ( 35122 ) ,
            temperature76 ( 35123 ) ,
            temperature77 ( 35124 ) ,
            temperature78 ( 35125 ) ,
            temperature79 ( 35126 ) ,
            temperature80 ( 35127 ) ,
            temperature81 ( 35128 ) ,
            temperature82 ( 35129 ) ,
            temperature83 ( 35130 ) ,
            temperature84 ( 35131 ) ,
            temperature85 ( 35132 ) ,
            temperature86 ( 35133 ) ,
            temperature87 ( 35134 ) ,
            temperature88 ( 35135 ) ,
            temperature89 ( 35136 ) ,
            temperature90 ( 35137 ) ,
            temperature91 ( 35138 ) ,
            temperature92 ( 35139 ) ,
            temperature93 ( 35140 ) ,
            temperature94 ( 35141 ) ,
            temperature95 ( 35142 ) ,
            temperature96 ( 35143 ) ,
            temperature97 ( 35144 ) ,
            temperature98 ( 35145 ) ,
            temperature99 ( 35146 ) ,
            temperature100 ( 35147 ) ,
            temperature101 ( 35148 ) ,
            temperature102 ( 35149 ) ,
            temperature103 ( 35150 ) ,
            temperature104 ( 35151 ) ,
            temperature105 ( 35152 ) ,
            temperature106 ( 35153 ) ,
            temperature107 ( 35154 ) ,
            temperature108 ( 35155 ) ,
            temperature109 ( 35156 ) ,
            temperature110 ( 35157 ) ,
            temperature111 ( 35158 ) ,
            temperature112 ( 35159 ) ,
            temperature113 ( 35160 ) ,
            temperature114 ( 35161 ) ,
            temperature115 ( 35162 ) ,
            temperature116 ( 35163 ) ,
            temperature117 ( 35164 ) ,
            temperature118 ( 35165 ) ,
            temperature119 ( 35166 ) ,
            temperature120 ( 35167 ) ,
            temperature121 ( 35168 ) ,
            temperature122 ( 35169 ) ,
            temperature123 ( 35170 ) ,
            temperature124 ( 35171 ) ,
            temperature125 ( 35172 ) ,
            temperature126 ( 35173 ) ,
            temperature127 ( 35174 ) ,
            temperature128 ( 35175 ) ,
            contact13 ( 35176 ) ,
            contact14 ( 35177 ) ,
            contact15 ( 35178 ) ,
            contact16 ( 35179 ) ,
            contact17 ( 35180 ) ,
            contact18 ( 35181 ) ,
            contact19 ( 35182 ) ,
            contact20 ( 35183 ) ,
            contact21 ( 35184 ) ,
            contact22 ( 35185 ) ,
            contact23 ( 35186 ) ,
            contact24 ( 35187 ) ,
            contact25 ( 35188 ) ,
            contact26 ( 35189 ) ,
            contact27 ( 35190 ) ,
            contact28 ( 35191 ) ,
            contact29 ( 35192 ) ,
            contact30 ( 35193 ) ,
            contact31 ( 35194 ) ,
            contact32 ( 35195 ) ,
            contact33 ( 35196 ) ,
            contact34 ( 35197 ) ,
            contact35 ( 35198 ) ,
            contact36 ( 35199 ) ,
            contact37 ( 35200 ) ,
            contact38 ( 35201 ) ,
            contact39 ( 35202 ) ,
            contact40 ( 35203 ) ,
            contact41 ( 35204 ) ,
            contact42 ( 35205 ) ,
            contact43 ( 35206 ) ,
            contact44 ( 35207 ) ,
            contact45 ( 35208 ) ,
            contact46 ( 35209 ) ,
            contact47 ( 35210 ) ,
            contact48 ( 35211 ) ,
            contact49 ( 35212 ) ,
            contact50 ( 35213 ) ,
            contact51 ( 35214 ) ,
            contact52 ( 35215 ) ,
            contact53 ( 35216 ) ,
            contact54 ( 35217 ) ,
            contact55 ( 35218 ) ,
            contact56 ( 35219 ) ,
            contact57 ( 35220 ) ,
            contact58 ( 35221 ) ,
            contact59 ( 35222 ) ,
            contact60 ( 35223 ) ,
            contact61 ( 35224 ) ,
            contact62 ( 35225 ) ,
            contact63 ( 35226 ) ,
            contact64 ( 35227 ) ,
            contact65 ( 35228 ) ,
            contact66 ( 35229 ) ,
            contact67 ( 35230 ) ,
            contact68 ( 35231 ) ,
            contact69 ( 35232 ) ,
            contact70 ( 35233 ) ,
            contact71 ( 35234 ) ,
            contact72 ( 35235 ) ,
            contact73 ( 35236 ) ,
            contact74 ( 35237 ) ,
            contact75 ( 35238 ) ,
            contact76 ( 35239 ) ,
            contact77 ( 35240 ) ,
            contact78 ( 35241 ) ,
            contact79 ( 35242 ) ,
            contact80 ( 35243 ) ,
            contact81 ( 35244 ) ,
            contact82 ( 35245 ) ,
            contact83 ( 35246 ) ,
            contact84 ( 35247 ) ,
            contact85 ( 35248 ) ,
            contact86 ( 35249 ) ,
            contact87 ( 35250 ) ,
            contact88 ( 35251 ) ,
            contact89 ( 35252 ) ,
            contact90 ( 35253 ) ,
            contact91 ( 35254 ) ,
            contact92 ( 35255 ) ,
            contact93 ( 35256 ) ,
            contact94 ( 35257 ) ,
            contact95 ( 35258 ) ,
            contact96 ( 35259 ) ,
            contact97 ( 35260 ) ,
            contact98 ( 35261 ) ,
            contact99 ( 35262 ) ,
            contact100 ( 35263 ) ,
            contact101 ( 35264 ) ,
            contact102 ( 35265 ) ,
            contact103 ( 35266 ) ,
            contact104 ( 35267 ) ,
            contact105 ( 35268 ) ,
            contact106 ( 35269 ) ,
            contact107 ( 35270 ) ,
            contact108 ( 35271 ) ,
            contact109 ( 35272 ) ,
            contact110 ( 35273 ) ,
            contact111 ( 35274 ) ,
            contact112 ( 35275 ) ,
            contact113 ( 35276 ) ,
            contact114 ( 35277 ) ,
            contact115 ( 35278 ) ,
            contact116 ( 35279 ) ,
            contact117 ( 35280 ) ,
            contact118 ( 35281 ) ,
            contact119 ( 35282 ) ,
            contact120 ( 35283 ) ,
            contact121 ( 35284 ) ,
            contact122 ( 35285 ) ,
            contact123 ( 35286 ) ,
            contact124 ( 35287 ) ,
            contact125 ( 35288 ) ,
            contact126 ( 35289 ) ,
            contact127 ( 35290 ) ,
            contact128 ( 35291 ) ,
            contactcount13 ( 35292 ) ,
            contactcount14 ( 35293 ) ,
            contactcount15 ( 35294 ) ,
            contactcount16 ( 35295 ) ,
            contactcount17 ( 35296 ) ,
            contactcount18 ( 35297 ) ,
            contactcount19 ( 35298 ) ,
            contactcount20 ( 35299 ) ,
            contactcount21 ( 35300 ) ,
            contactcount22 ( 35301 ) ,
            contactcount23 ( 35302 ) ,
            contactcount24 ( 35303 ) ,
            contactcount25 ( 35304 ) ,
            contactcount26 ( 35305 ) ,
            contactcount27 ( 35306 ) ,
            contactcount28 ( 35307 ) ,
            contactcount29 ( 35308 ) ,
            contactcount30 ( 35309 ) ,
            contactcount31 ( 35310 ) ,
            contactcount32 ( 35311 ) ,
            contactcount33 ( 35312 ) ,
            contactcount34 ( 35313 ) ,
            contactcount35 ( 35314 ) ,
            contactcount36 ( 35315 ) ,
            contactcount37 ( 35316 ) ,
            contactcount38 ( 35317 ) ,
            contactcount39 ( 35318 ) ,
            contactcount40 ( 35319 ) ,
            contactcount41 ( 35320 ) ,
            contactcount42 ( 35321 ) ,
            contactcount43 ( 35322 ) ,
            contactcount44 ( 35323 ) ,
            contactcount45 ( 35324 ) ,
            contactcount46 ( 35325 ) ,
            contactcount47 ( 35326 ) ,
            contactcount48 ( 35327 ) ,
            contactcount49 ( 35328 ) ,
            contactcount50 ( 35329 ) ,
            contactcount51 ( 35330 ) ,
            contactcount52 ( 35331 ) ,
            contactcount53 ( 35332 ) ,
            contactcount54 ( 35333 ) ,
            contactcount55 ( 35334 ) ,
            contactcount56 ( 35335 ) ,
            contactcount57 ( 35336 ) ,
            contactcount58 ( 35337 ) ,
            contactcount59 ( 35338 ) ,
            contactcount60 ( 35339 ) ,
            contactcount61 ( 35340 ) ,
            contactcount62 ( 35341 ) ,
            contactcount63 ( 35342 ) ,
            contactcount64 ( 35343 ) ,
            contactcount65 ( 35344 ) ,
            contactcount66 ( 35345 ) ,
            contactcount67 ( 35346 ) ,
            contactcount68 ( 35347 ) ,
            contactcount69 ( 35348 ) ,
            contactcount70 ( 35349 ) ,
            contactcount71 ( 35350 ) ,
            contactcount72 ( 35351 ) ,
            contactcount73 ( 35352 ) ,
            contactcount74 ( 35353 ) ,
            contactcount75 ( 35354 ) ,
            contactcount76 ( 35355 ) ,
            contactcount77 ( 35356 ) ,
            contactcount78 ( 35357 ) ,
            contactcount79 ( 35358 ) ,
            contactcount80 ( 35359 ) ,
            contactcount81 ( 35360 ) ,
            contactcount82 ( 35361 ) ,
            contactcount83 ( 35362 ) ,
            contactcount84 ( 35363 ) ,
            contactcount85 ( 35364 ) ,
            contactcount86 ( 35365 ) ,
            contactcount87 ( 35366 ) ,
            contactcount88 ( 35367 ) ,
            contactcount89 ( 35368 ) ,
            contactcount90 ( 35369 ) ,
            contactcount91 ( 35370 ) ,
            contactcount92 ( 35371 ) ,
            contactcount93 ( 35372 ) ,
            contactcount94 ( 35373 ) ,
            contactcount95 ( 35374 ) ,
            contactcount96 ( 35375 ) ,
            contactcount97 ( 35376 ) ,
            contactcount98 ( 35377 ) ,
            contactcount99 ( 35378 ) ,
            contactcount100 ( 35379 ) ,
            contactcount101 ( 35380 ) ,
            contactcount102 ( 35381 ) ,
            contactcount103 ( 35382 ) ,
            contactcount104 ( 35383 ) ,
            contactcount105 ( 35384 ) ,
            contactcount106 ( 35385 ) ,
            contactcount107 ( 35386 ) ,
            contactcount108 ( 35387 ) ,
            contactcount109 ( 35388 ) ,
            contactcount110 ( 35389 ) ,
            contactcount111 ( 35390 ) ,
            contactcount112 ( 35391 ) ,
            contactcount113 ( 35392 ) ,
            contactcount114 ( 35393 ) ,
            contactcount115 ( 35394 ) ,
            contactcount116 ( 35395 ) ,
            contactcount117 ( 35396 ) ,
            contactcount118 ( 35397 ) ,
            contactcount119 ( 35398 ) ,
            contactcount120 ( 35399 ) ,
            contactcount121 ( 35400 ) ,
            contactcount122 ( 35401 ) ,
            contactcount123 ( 35402 ) ,
            contactcount124 ( 35403 ) ,
            contactcount125 ( 35404 ) ,
            contactcount126 ( 35405 ) ,
            contactcount127 ( 35406 ) ,
            contactcount128 ( 35407 ) ,
            probestatus13 ( 35408 ) ,
            probestatus14 ( 35409 ) ,
            probestatus15 ( 35410 ) ,
            probestatus16 ( 35411 ) ,
            probestatus17 ( 35412 ) ,
            probestatus18 ( 35413 ) ,
            probestatus19 ( 35414 ) ,
            probestatus20 ( 35415 ) ,
            probestatus21 ( 35416 ) ,
            probestatus22 ( 35417 ) ,
            probestatus23 ( 35418 ) ,
            probestatus24 ( 35419 ) ,
            probestatus25 ( 35420 ) ,
            probestatus26 ( 35421 ) ,
            probestatus27 ( 35422 ) ,
            probestatus28 ( 35423 ) ,
            probestatus29 ( 35424 ) ,
            probestatus30 ( 35425 ) ,
            probestatus31 ( 35426 ) ,
            probestatus32 ( 35427 ) ,
            probestatus33 ( 35428 ) ,
            probestatus34 ( 35429 ) ,
            probestatus35 ( 35430 ) ,
            probestatus36 ( 35431 ) ,
            probestatus37 ( 35432 ) ,
            probestatus38 ( 35433 ) ,
            probestatus39 ( 35434 ) ,
            probestatus40 ( 35435 ) ,
            probestatus41 ( 35436 ) ,
            probestatus42 ( 35437 ) ,
            probestatus43 ( 35438 ) ,
            probestatus44 ( 35439 ) ,
            probestatus45 ( 35440 ) ,
            probestatus46 ( 35441 ) ,
            probestatus47 ( 35442 ) ,
            probestatus48 ( 35443 ) ,
            probestatus49 ( 35444 ) ,
            probestatus50 ( 35445 ) ,
            probestatus51 ( 35446 ) ,
            probestatus52 ( 35447 ) ,
            probestatus53 ( 35448 ) ,
            probestatus54 ( 35449 ) ,
            probestatus55 ( 35450 ) ,
            probestatus56 ( 35451 ) ,
            probestatus57 ( 35452 ) ,
            probestatus58 ( 35453 ) ,
            probestatus59 ( 35454 ) ,
            probestatus60 ( 35455 ) ,
            probestatus61 ( 35456 ) ,
            probestatus62 ( 35457 ) ,
            probestatus63 ( 35458 ) ,
            probestatus64 ( 35459 ) ,
            probestatus65 ( 35460 ) ,
            probestatus66 ( 35461 ) ,
            probestatus67 ( 35462 ) ,
            probestatus68 ( 35463 ) ,
            probestatus69 ( 35464 ) ,
            probestatus70 ( 35465 ) ,
            probestatus71 ( 35466 ) ,
            probestatus72 ( 35467 ) ,
            probestatus73 ( 35468 ) ,
            probestatus74 ( 35469 ) ,
            probestatus75 ( 35470 ) ,
            probestatus76 ( 35471 ) ,
            probestatus77 ( 35472 ) ,
            probestatus78 ( 35473 ) ,
            probestatus79 ( 35474 ) ,
            probestatus80 ( 35475 ) ,
            probestatus81 ( 35476 ) ,
            probestatus82 ( 35477 ) ,
            probestatus83 ( 35478 ) ,
            probestatus84 ( 35479 ) ,
            probestatus85 ( 35480 ) ,
            probestatus86 ( 35481 ) ,
            probestatus87 ( 35482 ) ,
            probestatus88 ( 35483 ) ,
            probestatus89 ( 35484 ) ,
            probestatus90 ( 35485 ) ,
            probestatus91 ( 35486 ) ,
            probestatus92 ( 35487 ) ,
            probestatus93 ( 35488 ) ,
            probestatus94 ( 35489 ) ,
            probestatus95 ( 35490 ) ,
            probestatus96 ( 35491 ) ,
            probestatus97 ( 35492 ) ,
            probestatus98 ( 35493 ) ,
            probestatus99 ( 35494 ) ,
            probestatus100 ( 35495 ) ,
            probestatus101 ( 35496 ) ,
            probestatus102 ( 35497 ) ,
            probestatus103 ( 35498 ) ,
            probestatus104 ( 35499 ) ,
            probestatus105 ( 35500 ) ,
            probestatus106 ( 35501 ) ,
            probestatus107 ( 35502 ) ,
            probestatus108 ( 35503 ) ,
            probestatus109 ( 35504 ) ,
            probestatus110 ( 35505 ) ,
            probestatus111 ( 35506 ) ,
            probestatus112 ( 35507 ) ,
            probestatus113 ( 35508 ) ,
            probestatus114 ( 35509 ) ,
            probestatus115 ( 35510 ) ,
            probestatus116 ( 35511 ) ,
            probestatus117 ( 35512 ) ,
            probestatus118 ( 35513 ) ,
            probestatus119 ( 35514 ) ,
            probestatus120 ( 35515 ) ,
            probestatus121 ( 35516 ) ,
            probestatus122 ( 35517 ) ,
            probestatus123 ( 35518 ) ,
            probestatus124 ( 35519 ) ,
            probestatus125 ( 35520 ) ,
            probestatus126 ( 35521 ) ,
            probestatus127 ( 35522 ) ,
            probestatus128 ( 35523 ) ,
            sr1 ( 35524 ) ,
            sr2 ( 35525 ) ,
            sr3 ( 35526 ) ,
            sr4 ( 35527 ) ,
            sr5 ( 35528 ) ,
            sr6 ( 35529 ) ,
            sr7 ( 35530 ) ,
            sr8 ( 35531 ) ,
            sr9 ( 35532 ) ,
            sr10 ( 35533 ) ,
            sr11 ( 35534 ) ,
            sr12 ( 35535 ) ,
            sr13 ( 35536 ) ,
            sr14 ( 35537 ) ,
            sr15 ( 35538 ) ,
            sr16 ( 35539 ) ,
            sr17 ( 35540 ) ,
            sr18 ( 35541 ) ,
            sr19 ( 35542 ) ,
            sr20 ( 35543 ) ,
            sr21 ( 35544 ) ,
            sr22 ( 35545 ) ,
            sr23 ( 35546 ) ,
            sr24 ( 35547 ) ,
            sr25 ( 35548 ) ,
            sr26 ( 35549 ) ,
            sr27 ( 35550 ) ,
            sr28 ( 35551 ) ,
            sr29 ( 35552 ) ,
            sr30 ( 35553 ) ,
            sr31 ( 35554 ) ,
            sr32 ( 35555 ) ,
            sr33 ( 35556 ) ,
            sr34 ( 35557 ) ,
            sr35 ( 35558 ) ,
            sr36 ( 35559 ) ,
            sr37 ( 35560 ) ,
            sr38 ( 35561 ) ,
            sr39 ( 35562 ) ,
            sr40 ( 35563 ) ,
            sr41 ( 35564 ) ,
            sr42 ( 35565 ) ,
            sr43 ( 35566 ) ,
            sr44 ( 35567 ) ,
            sr45 ( 35568 ) ,
            sr46 ( 35569 ) ,
            sr47 ( 35570 ) ,
            sr48 ( 35571 ) ,
            sr49 ( 35572 ) ,
            sr50 ( 35573 ) ,
            sr51 ( 35574 ) ,
            sr52 ( 35575 ) ,
            sr53 ( 35576 ) ,
            sr54 ( 35577 ) ,
            sr55 ( 35578 ) ,
            sr56 ( 35579 ) ,
            sr57 ( 35580 ) ,
            sr58 ( 35581 ) ,
            sr59 ( 35582 ) ,
            sr60 ( 35583 ) ,
            sr61 ( 35584 ) ,
            sr62 ( 35585 ) ,
            sr63 ( 35586 ) ,
            sr64 ( 35587 ) }
        MAX-ACCESS          not-accessible
        STATUS          current
        DESCRIPTION         "Channel ID, indicating the type of measurement reported."
        ::=  {  readingsEntry  5  }


    reNodeIdHex     OBJECT-TYPE
        SYNTAX          DisplayString  ( SIZE ( 0 .. 16  ) )
        MAX-ACCESS          read-only
        STATUS          current
        DESCRIPTION         "Node ID number as as 16-character uppercase hexadecimal string."
        ::=  {  readingsEntry  6  }


    reNodeIdString  OBJECT-TYPE
        SYNTAX          DisplayString  ( SIZE ( 0 .. 19  ) )
        MAX-ACCESS          read-only
        STATUS          current
        DESCRIPTION         "Node identifier (hex), formatted XXXX-XXXX-XXXX-XXXX (matches all Packet Power product labels)."
        ::=  {  readingsEntry  7  }


    reChannelName   OBJECT-TYPE
        SYNTAX          DisplayString  ( SIZE ( 0 .. 255  ) )
        MAX-ACCESS          read-only
        STATUS          current
        DESCRIPTION         "Channel name, indicating channel type and instance (e.g.VoltageA)."
        ::=  {  readingsEntry  8  }


    reTime  OBJECT-TYPE
        SYNTAX          DateAndTime
        MAX-ACCESS          read-only
        STATUS          current
        DESCRIPTION         "Timestamp of the reading."
        ::=  {  readingsEntry  9  }


    reUnixTime      OBJECT-TYPE
        SYNTAX          Integer32  ( -2147483648 .. 2147483647  )
        MAX-ACCESS          read-only
        STATUS          current
        DESCRIPTION         "Reading timestamp, UNIX epoch format."
        ::=  {  readingsEntry  10  }


    reIso8601Time   OBJECT-TYPE
        SYNTAX          DisplayString  ( SIZE ( 0 .. 255  ) )
        MAX-ACCESS          read-only
        STATUS          current
        DESCRIPTION         "Reading timestamp, ISO8601 format."
        ::=  {  readingsEntry  11  }


    reValue OBJECT-TYPE
        SYNTAX          Integer32  ( -2147483648 .. 2147483647  )
        MAX-ACCESS          read-only
        STATUS          current
        DESCRIPTION         "Reading value at timestamp."
        ::=  {  readingsEntry  12  }


    reUnits OBJECT-TYPE
        SYNTAX          DisplayString  ( SIZE ( 0 .. 255  ) )
        MAX-ACCESS          read-only
        STATUS          current
        DESCRIPTION         "Units of measure."
        ::=  {  readingsEntry  13  }

    nodesTable      OBJECT-TYPE
        SYNTAX      SEQUENCE  OF  NodesEntry
        MAX-ACCESS      not-accessible
        STATUS      current
        DESCRIPTION     "Table of all active nodes."
        ::=  { eg4  2 }

    nodesEntry      OBJECT-TYPE
        SYNTAX      NodesEntry
        MAX-ACCESS      not-accessible
        STATUS      current
        DESCRIPTION     "Node status, including most recent activity time and radio link quality."
        INDEX       {  ntNodeId1, ntNodeId2, ntNodeId3, ntNodeId4  }
        ::=  { nodesTable 1 }

    NodesEntry  ::=  SEQUENCE {
        ntNodeId1  Integer32,
        ntNodeId2  Integer32,
        ntNodeId3  Integer32,
        ntNodeId4  Integer32,
        ntNodeIdHex  DisplayString,
        ntNodeIdString  DisplayString,
        ntTime  DateAndTime,
        ntUnixTime  Integer32,
        ntIso8601Time  DisplayString,
        ntLinkQuality  Integer32
        }

    nodesGroup OBJECT-GROUP
        OBJECTS {
            ntNodeIdHex,
            ntNodeIdString,
            ntTime,
            ntUnixTime,
            ntIso8601Time,
            ntLinkQuality
            }
        STATUS  current
        DESCRIPTION "Node status group"
        ::= { packetPowerMIBConformance 2 }


    ntNodeId1       OBJECT-TYPE
        SYNTAX          Integer32  ( 0 .. 65535  )
        MAX-ACCESS          not-accessible
        STATUS          current
        DESCRIPTION         "Node identifier, part 1 of 4 (16 bits, bits 63-48 of the id - part AAAA of AAAA-BBBB-CCCC-DDDD)."
        ::=  {  nodesEntry  1  }


    ntNodeId2       OBJECT-TYPE
        SYNTAX          Integer32  ( 0 .. 65535  )
        MAX-ACCESS          not-accessible
        STATUS          current
        DESCRIPTION         "Node identifier, part 2 of 4 (16 bits, bits 47-32 of the id - part BBBB of AAAA-BBBB-CCCC-DDDD)."
        ::=  {  nodesEntry  2  }


    ntNodeId3       OBJECT-TYPE
        SYNTAX          Integer32  ( 0 .. 65535  )
        MAX-ACCESS          not-accessible
        STATUS          current
        DESCRIPTION         "Node identifier, part 3 of 4 (16 bits, bits 31-16 of the id - part CCCC of AAAA-BBBB-CCCC-DDDD)."
        ::=  {  nodesEntry  3  }


    ntNodeId4       OBJECT-TYPE
        SYNTAX          Integer32  ( 0 .. 65535  )
        MAX-ACCESS          not-accessible
        STATUS          current
        DESCRIPTION         "Node identifier, part 4 of 4 (16 bits, bits 15-0 of the id - part DDDD of AAAA-BBBB-CCCC-DDDD)."
        ::=  {  nodesEntry  4  }


    ntNodeIdHex     OBJECT-TYPE
        SYNTAX          DisplayString  ( SIZE ( 0 .. 16  ) )
        MAX-ACCESS          read-only
        STATUS          current
        DESCRIPTION         "Node ID number as as 16-character uppercase hexadecimal string."
        ::=  {  nodesEntry  5  }


    ntNodeIdString  OBJECT-TYPE
        SYNTAX          DisplayString  ( SIZE ( 0 .. 19  ) )
        MAX-ACCESS          read-only
        STATUS          current
        DESCRIPTION         "Node identifier (hex), formatted XXXX-XXXX-XXXX-XXXX (matches all Packet Power product labels)."
        ::=  {  nodesEntry  6  }


    ntTime  OBJECT-TYPE
        SYNTAX          DateAndTime
        MAX-ACCESS          read-only
        STATUS          current
        DESCRIPTION         "Timestamp of the most recent reading from the node."
        ::=  {  nodesEntry  7  }


    ntUnixTime      OBJECT-TYPE
        SYNTAX          Integer32  ( -2147483648 .. 2147483647  )
        MAX-ACCESS          read-only
        STATUS          current
        DESCRIPTION         "Timestamp of the most recent reading from the node, UNIX epoch format."
        ::=  {  nodesEntry  8  }


    ntIso8601Time   OBJECT-TYPE
        SYNTAX          DisplayString  ( SIZE ( 0 .. 255  ) )
        MAX-ACCESS          read-only
        STATUS          current
        DESCRIPTION         "Timestamp of the most recent reading from the node, ISO8601 format."
        ::=  {  nodesEntry  9  }


    ntLinkQuality   OBJECT-TYPE
        SYNTAX          Integer32  ( 0 .. 100  )
        MAX-ACCESS          read-only
        STATUS          current
        DESCRIPTION         "Radio link quality 0..100"
        ::=  {  nodesEntry  10  }

END
