GSW-2008MS-MIB DEFINITIONS ::= BEGIN 
  
    IMPORTS
        enterprises,
        NOTIFICATION-TYPE,
        MODULE-IDENTITY,
        OBJECT-TYPE,
        Counter32,
        Integer32,
        Unsigned32,
        Gauge32,
        Counter64,
        IpAddress
            FROM SNMPv2-SMI
        MODULE-COMPLIANCE,
        OBJECT-GROUP,
        NOTIFICATION-GROUP
            FROM SNMPv2-CONF
        DisplayString,
        DateAndTime,
        MacAddress,
        TruthValue
            FROM SNMPv2-TC
        Float32TC
            FROM FLOAT-TC-MIB
    ; 

    -- 1.3.6.1.4.1.4756
    ctc MODULE-IDENTITY
        LAST-UPDATED "201604110000Z"        -- Apr 11, 2016 at
        ORGANIZATION
            " CTC Union Technologies Co., Ltd. "
        CONTACT-INFO
            " Postal: 8F, No.60, ZhouZi Street, Nei-Hu, Taipei 114, Taiwan
              Tel: +886-2-2659-1021
              Fax: +886-2-2672-5211
              Web: http://www.ctcu.com
              Email: support@ctcu.com " 
        DESCRIPTION
            " GSW-2008MS MIB File "
        
        REVISION "201604110000Z"        -- Apr 11, 2016 at        
        DESCRIPTION
            " V1.05  - Fixed offset of timezone Yangon (Rangoon)."
             
        REVISION "201508120000Z"        -- Aug 12, 2015 at    
        DESCRIPTION
            " V1.04  - Added Ingress Port Shaper."
                
        REVISION "201405290000Z"        -- May 29, 2014 at
        DESCRIPTION
            " V1.03  - Added ALS and SFP table."
        
        REVISION "201312020000Z"        -- Dec 02, 2013 at
        DESCRIPTION
            " V1.02  - Removed some nodes that are unsupported."
        
        REVISION "201311050000Z"        -- Nov 05, 2013 at
        DESCRIPTION
            " V1.01  - Added 'Ingress Port Policer FC'."
        
        REVISION "201309100000Z"        -- Sep 10, 2013 at
        DESCRIPTION
            " V1.00  - Initial Document."
        ::= { enterprises 4756 }



--
-- Node definitions 
--
     
    -- 1.3.6.1.4.1.4756.104
    gsw2008ms OBJECT IDENTIFIER ::= { ctc 104 }
    
-- System
    -- 1.3.6.1.4.1.4756.104.10
    ctcSystem OBJECT IDENTIFIER ::= { gsw2008ms 10 }

    -- 1.3.6.1.4.1.4756.104.10.1
    ctcSystemInformation OBJECT IDENTIFIER ::= { ctcSystem 1 }
            
    -- 1.3.6.1.4.1.4756.104.10.1.1
    ctcChipRevision OBJECT-TYPE
        SYNTAX      DisplayString
        MAX-ACCESS  read-only
        STATUS      current
        DESCRIPTION
            "The chip revision of this switch."
        ::= { ctcSystemInformation 1 }
             
    -- 1.3.6.1.4.1.4756.104.10.1.2
    ctcBaseMacAddress OBJECT-TYPE
        SYNTAX      MacAddress
        MAX-ACCESS  read-only
        STATUS      current
        DESCRIPTION
            "The MAC Address of this switch."
        ::= { ctcSystemInformation 2 }
             
    -- 1.3.6.1.4.1.4756.104.10.1.3
    ctcSoftWareVersion OBJECT-TYPE
        SYNTAX      DisplayString
        MAX-ACCESS  read-only
        STATUS      current
        DESCRIPTION
            "The software version of this switch."
        ::= { ctcSystemInformation 3 }
            
    -- 1.3.6.1.4.1.4756.104.10.1.4
    ctcSoftWareDate OBJECT-TYPE
        SYNTAX      DisplayString
        MAX-ACCESS  read-only
        STATUS      current
        DESCRIPTION
            "The date when the switch software was produced."
        ::= { ctcSystemInformation 4 }
            
    -- 1.3.6.1.4.1.4756.104.10.1.5
    ctcConfigurationFile OBJECT-TYPE
        SYNTAX      DisplayString
        MAX-ACCESS  read-only
        STATUS      current
        DESCRIPTION
            "The filename when the switch configuration was produced."
        ::= { ctcSystemInformation 5 }

    -- 1.3.6.1.4.1.4756.104.10.1.7
    ctcDhcpOption60 OBJECT-TYPE
        SYNTAX      DisplayString
        MAX-ACCESS  read-write
        STATUS      current
        DESCRIPTION
            "Configure the DHCP option 60 vendor class ID.
             The allowed string length is 0 to 60."
        ::= { ctcSystemInformation 7 }
              
    -- 1.3.6.1.4.1.4756.104.10.1.8
    ctcDnsServer OBJECT-TYPE
        SYNTAX      IpAddress
        MAX-ACCESS  read-write
        STATUS      current
        DESCRIPTION
            "Provide the IP address of the DNS Server in dotted decimal notation."
        ::= { ctcSystemInformation 8 }
            
    -- 1.3.6.1.4.1.4756.104.10.1.9
    ctcSystemTime OBJECT-TYPE
        SYNTAX      DisplayString
        MAX-ACCESS  read-write
        STATUS      current
        DESCRIPTION
            "The current (GMT) system time and date."
        ::= { ctcSystemInformation 9 }
            
    -- 1.3.6.1.4.1.4756.104.10.2
    ctcNTP OBJECT IDENTIFIER ::= { ctcSystem 2 }

    -- 1.3.6.1.4.1.4756.104.10.2.1
    ctcNtpMode OBJECT-TYPE
        SYNTAX      INTEGER {
                        enabled(1),
                        disabled(2)
                    }
        MAX-ACCESS  read-write
        STATUS      current
        DESCRIPTION
            "Indicates the NTP mode operation. Possible modes are:
             Enabled: Enable NTP mode operation. When NTP mode operation is enabled,
                      the agent forwards NTP messages between the clients and the server
                      when they are not on the same subnet domain.
             Disabled: Disable NTP mode operation. "
        ::= { ctcNTP 1 }

    -- 1.3.6.1.4.1.4756.104.10.2.2
    ctcNtpServerTable OBJECT-TYPE
        SYNTAX      SEQUENCE OF CtcNtpServerEntry
        MAX-ACCESS  not-accessible
        STATUS      current
        DESCRIPTION
            "The switch system log information."
        ::= { ctcNTP 2 }

    -- 1.3.6.1.4.1.4756.104.10.2.2.1
    ctcNtpServerEntry OBJECT-TYPE
        SYNTAX      CtcNtpServerEntry
        MAX-ACCESS  not-accessible
        STATUS      current
        DESCRIPTION
            "The system log entry."
        INDEX { ctcNtpServerIndex }
        ::= { ctcNtpServerTable 1 }

    CtcNtpServerEntry ::=
        SEQUENCE {
            ctcNtpServerIndex        Integer32,
            ctcNtpServerAddress      DisplayString
        }

        -- 1.3.6.1.4.1.4756.104.10.2.2.1.1
        ctcNtpServerIndex OBJECT-TYPE
            SYNTAX      Integer32 (1..5)
            MAX-ACCESS  read-only
            STATUS      current
            DESCRIPTION
                "The Index of the NTP server."
            ::= { ctcNtpServerEntry 1 }

        -- 1.3.6.1.4.1.4756.104.10.2.2.1.2
        ctcNtpServerAddress OBJECT-TYPE
            SYNTAX      DisplayString
            MAX-ACCESS  read-write
            STATUS      current
            DESCRIPTION
                "It must either be a valid IP address or a valid hostname.
                 A valid hostname is a string drawn from the alphabet(A-Za-z), digits(0-9), dot(.), dash(-).
                 Spaces are not allowed, the first character must be an alpha character,
                 and the first and last characters must not be a dot or a dash.
                 IPv4 address is in dotted decimal notation ('x.y.z.w').
                 IPv6 address is in 128-bit records represented as eight fields of up to
                 four hexadecimal digits with a colon separating each field (:)."
            ::= { ctcNtpServerEntry 2 }
 


    -- 1.3.6.1.4.1.4756.104.10.3
    ctcTime OBJECT IDENTIFIER ::= { ctcSystem 3 }
    
    -- 1.3.6.1.4.1.4756.104.10.3.1
    ctcTimezone OBJECT-TYPE
        SYNTAX      Integer32 (-7200..7800)
        MAX-ACCESS  read-write
        STATUS      current
        DESCRIPTION
            "Lists various Time Zones world wide below.
             -7200: '(GMT-12:00) International Date Line West',
             -6600: '(GMT-11:00) Midway Island, Samoa',
             -6000: '(GMT-10:00) Hawaii',
             -5400: '(GMT-09:00) Alaska',
             -4800: '(GMT-08:00) Pacific Time (US and Canada)',
             -4801: '(GMT-08:00) Tijuana, Baja California',
             -4200: '(GMT-07:00) Arizona',
             -4201: '(GMT-07:00) Chihuahua, La Paz, Mazatlan - New',
             -4202: '(GMT-07:00) Chihuahua, La Paz, Mazatlan - Old',
             -4203: '(GMT-07:00) Mountain Time (US and Canada)',
             -3600: '(GMT-06:00) Central America',
             -3601: '(GMT-06:00) Central Time (US and Canada)',
             -3602: '(GMT-06:00) Guadalajara, Mexico City, Monterrey - New',
             -3603: '(GMT-06:00) Guadalajara, Mexico City, Monterrey - Old',
             -3604: '(GMT-06:00) Saskatchewan',
             -3000: '(GMT-05:00) Bogota, Lima, Quito, Rio Branco',
             -3001: '(GMT-05:00) Eastern Time (US and Canada)',
             -3002: '(GMT-05:00) Indiana (East)',
             -2700: '(GMT-04:30) Caracas',
             -2400: '(GMT-04:00) Atlantic Time (Canada)',
             -2401: '(GMT-04:00) La Paz','(GMT-04:00) Manaus',
             -2402: '(GMT-04:00) Santiago','(GMT-03:30) Newfoundland',
             -1800: '(GMT-03:00) Brasilia','(GMT-03:00) Buenos Aires',
             -1801: '(GMT-03:00) Georgetown','(GMT-03:00) Greenland',
             -1802: '(GMT-03:00) Montevideo','(GMT-02:00) Mid-Atlantic',
              -600: '(GMT-01:00) Azores',
              -601: '(GMT-01:00) Cape Verde Is.',
                 0: 'None',
                 1: '(GMT) Casablanca',
                 2: '(GMT) Greenwich Mean Time : Dublin, Edinburgh, Lisbon, London',
                 3: '(GMT) Monrovia, Reykjavik',
               600: '(GMT+01:00) Amsterdam, Berlin, Bern, Rome, Stockholm, Vienna',
               601: '(GMT+01:00) Belgrade, Bratislava, Budapest, Ljubljana, Prague',
               602: '(GMT+01:00) Brussels, Copenhagen, Madrid, Paris',
               603: '(GMT+01:00) Sarajevo, Skopje, Warsaw, Zagreb',
               604: '(GMT+01:00) West Central Africa',
              1200: '(GMT+02:00) Amman',
              1201: '(GMT+02:00) Athens, Bucharest, Istanbul',
              1202: '(GMT+02:00) Beirut',
              1203: '(GMT+02:00) Cairo',
              1204: '(GMT+02:00) Harare, Pretoria',
              1205: '(GMT+02:00) Helsinki, Kyiv, Riga, Sofia, Tallinn, Vilnius',
              1206: '(GMT+02:00) Jerusalem',
              1207: '(GMT+02:00) Minsk',
              1208: '(GMT+02:00) Windhoek',
              1800: '(GMT+03:00) Baghdad',
              1801: '(GMT+03:00) Kuwait, Riyadh',
              1802: '(GMT+03:00) Moscow, St. Petersburg, Volgograd',
              1803: '(GMT+03:00) Nairobi',
              1804: '(GMT+03:00) Tbilisi',
              2100: '(GMT+03:30) Tehran',
              2400: '(GMT+04:00) Abu Dhabi, Muscat',
              2401: '(GMT+04:00) Baku',
              2402: '(GMT+04:00) Caucasus Standard Time',
              2403: '(GMT+04:00) Port Louis',
              2404: '(GMT+04:00) Yerevan',
              2700: '(GMT+04:30) Kabul',
              3000: '(GMT+05:00) Ekaterinburg',
              3001: '(GMT+05:00) Islamabad, Karachi',
              3002: '(GMT+05:00) Tashkent',
              3300: '(GMT+05:30) Chennai, Kolkata, Mumbai, New Delhi',
              3301: '(GMT+05:30) Sri Jayawardenepura',
              3455: '(GMT+05:45) Kathmandu',
              3600: '(GMT+06:00) Almaty, Novosibirsk',
              3601: '(GMT+06:00) Astana, Dhaka',
              3900: '(GMT+06:30) Yangon (Rangoon)',
              4200: '(GMT+07:00) Bangkok, Hanoi, Jakarta',
              4201: '(GMT+07:00) Krasnoyarsk',
              4800: '(GMT+08:00) Beijing, Chongqing, Hong Kong, Urumqi',
              4801: '(GMT+08:00) Irkutsk, Ulaan Bataar',
              4802: '(GMT+08:00) Kuala Lumpur, Singapore',
              4803: '(GMT+08:00) Perth',
              4804: '(GMT+08:00) Taipei',
              5400: '(GMT+09:00) Osaka, Sapporo, Tokyo',
              5401: '(GMT+09:00) Seoul',
              5402: '(GMT+09:00) Yakutsk',
              5700: '(GMT+09:30) Adelaide',
              5701: '(GMT+09:30) Darwin',
              6000: '(GMT+10:00) Brisbane',
              6001: '(GMT+10:00) Canberra, Melbourne, Sydney',
              6002: '(GMT+10:00) Guam, Port Moresby',
              6003: '(GMT+10:00) Hobart',
              6004: '(GMT+10:00) Vladivostok',
              6600: '(GMT+11:00) Magadan, Solomon Is., New Caledonia',
              7200: '(GMT+12:00) Auckland, Wellington',
              7201: '(GMT+12:00) Fiji, Kamchatka, Marshall Is.',
              7800: '(GMT+13:00) Nuku'alofa'"
        ::= { ctcTime 1 }

    -- 1.3.6.1.4.1.4756.104.10.3.2
    ctcTimezoneAcronym OBJECT-TYPE
        SYNTAX      DisplayString
        MAX-ACCESS  read-write
        STATUS      current
        DESCRIPTION
            "User can set the acronym of the time zone.
             This is a User configurable acronym to identify the time zone.
             ( Range : Up to 16 alpha-numeric characters and can contain '-', '_' or '.')"
        ::= { ctcTime 2 }

    -- 1.3.6.1.4.1.4756.104.10.3.3 
    ctcDaylightSavingTimeMode OBJECT-TYPE
        SYNTAX      INTEGER {
                        disabled(1),
                        recurring(2),
                        nonRecurring(3)
                    }
        MAX-ACCESS  read-write
        STATUS      current
        DESCRIPTION
            "This is used to set the clock forward or backward according to the Daylight Saving Time duration.
             Select 'Disable' to disable the Daylight Saving Time configuration.
             Select 'Recurring' and configure the Daylight Saving Time duration to repeat the configuration every year.
             Select 'Non-Recurring' and configure the Daylight Saving Time duration for single time configuration.
             ( Default : Disabled )"
        DEFVAL      { 1 }
        ::= { ctcTime 3 }
             
    -- 1.3.6.1.4.1.4756.104.10.3.4
    ctcDaylightSavingStartingWeek OBJECT-TYPE
        SYNTAX      Integer32 (1..5)
        MAX-ACCESS  read-write
        STATUS      current
        DESCRIPTION
            "Select the starting week number if Daylight Saving Time Mode is 'recurring'."
    ::= { ctcTime 4 }
             
    -- 1.3.6.1.4.1.4756.104.10.3.5
    ctcDaylightSavingStartingDay OBJECT-TYPE
        SYNTAX      INTEGER {
                        mon(1),
                        tue(2),
                        wed(3),
                        thu(4),
                        fri(5),
                        sat(6),
                        sun(7)
                    }
        MAX-ACCESS  read-write
        STATUS      current
        DESCRIPTION
            "Select the starting day if Daylight Saving Time Mode is 'recurring'."
        ::= { ctcTime 5 }
             
    -- 1.3.6.1.4.1.4756.104.10.3.6
    ctcDaylightSavingStartingMonth OBJECT-TYPE
        SYNTAX      INTEGER {
                        jan(1),
                        feb(2),
                        mar(3),
                        apr(4),
                        may(5),
                        jun(6),
                        jul(7),
                        aug(8),
                        sep(9),
                        oct(10),
                        nov(11),
                        dec(12)
                    }
        MAX-ACCESS  read-write
        STATUS      current
        DESCRIPTION
            "Select the starting month if Daylight Saving Time Mode is 'recurring' or 'nonRecurring'."
        ::= { ctcTime 6 }
             
    -- 1.3.6.1.4.1.4756.104.10.3.7
    ctcDaylightSavingStartingDate OBJECT-TYPE
        SYNTAX      Integer32 (1..31)
        MAX-ACCESS  read-write
        STATUS      current
        DESCRIPTION
            "Select the starting date if Daylight Saving Time Mode is 'nonRecurring'."
        ::= { ctcTime 7 }
             
    -- 1.3.6.1.4.1.4756.104.10.3.8
    ctcDaylightSavingStartingYear OBJECT-TYPE
        SYNTAX      Integer32 (2000..2097)
        MAX-ACCESS  read-write
        STATUS      current
        DESCRIPTION
            "Select the starting year if Daylight Saving Time Mode is 'nonRecurring'."
        ::= { ctcTime 8 }
            
    -- 1.3.6.1.4.1.4756.104.10.3.9
    ctcDaylightSavingStartingHour OBJECT-TYPE
        SYNTAX      Integer32 (0..23)
        MAX-ACCESS  read-write
        STATUS      current
        DESCRIPTION
            "Select the starting Hour if Daylight Saving Time Mode is 'recurring' or 'nonRecurring'."
        ::= { ctcTime 9 }
            
    -- 1.3.6.1.4.1.4756.104.10.3.10
    ctcDaylightSavingStartingMinute OBJECT-TYPE
        SYNTAX      Integer32 (0..59)
        MAX-ACCESS  read-write
        STATUS      current
        DESCRIPTION
            "Select the starting Minute if Daylight Saving Time Mode is 'recurring' or 'nonRecurring'."
        ::= { ctcTime 10 }
             
    -- 1.3.6.1.4.1.4756.104.10.3.11
    ctcDaylightSavingEndingWeek OBJECT-TYPE
        SYNTAX      Integer32 (1..5)
        MAX-ACCESS  read-write
        STATUS      current
        DESCRIPTION
            "Select the ending week number if Daylight Saving Time Mode is 'recurring'."
        ::= { ctcTime 11 }
             
    -- 1.3.6.1.4.1.4756.104.10.3.12
    ctcDaylightSavingEndingDay OBJECT-TYPE
        SYNTAX      INTEGER {
                        mon(1),
                        tue(2),
                        wed(3),
                        thu(4),
                        fri(5),
                        sat(6),
                        sun(7)
                    }
        MAX-ACCESS  read-write
        STATUS      current
        DESCRIPTION
            "Select the ending day if Daylight Saving Time Mode is 'recurring'."
        ::= { ctcTime 12 }
             
    -- 1.3.6.1.4.1.4756.104.10.3.13
    ctcDaylightSavingEndingMonth OBJECT-TYPE
        SYNTAX      INTEGER {
                        jan(1),
                        feb(2),
                        mar(3),
                        apr(4),
                        may(5),
                        jun(6),
                        jul(7),
                        aug(8),
                        sep(9),
                        oct(10),
                        nov(11),
                        dec(12)
                    }
        MAX-ACCESS  read-write
        STATUS      current
        DESCRIPTION
            "Select the ending month if Daylight Saving Time Mode is 'recurring' or 'nonRecurring'."
        ::= { ctcTime 13 }
             
    -- 1.3.6.1.4.1.4756.104.10.3.14
    ctcDaylightSavingEndingDate OBJECT-TYPE
        SYNTAX      Integer32 (1..31)
        MAX-ACCESS  read-write
        STATUS      current
        DESCRIPTION
            "Select the ending date if Daylight Saving Time Mode is 'nonRecurring'."
        ::= { ctcTime 14 }
             
    -- 1.3.6.1.4.1.4756.104.10.3.15
    ctcDaylightSavingEndingYear OBJECT-TYPE
        SYNTAX      Integer32 (2000..2097)
        MAX-ACCESS  read-write
        STATUS      current
        DESCRIPTION
            "Select the ending year if Daylight Saving Time Mode is 'nonRecurring'."
        ::= { ctcTime 15 }
            
    -- 1.3.6.1.4.1.4756.104.10.3.16
    ctcDaylightSavingEndingHour OBJECT-TYPE
        SYNTAX      Integer32 (0..23)
        MAX-ACCESS  read-write
        STATUS      current
        DESCRIPTION
            "Select the ending Hour if Daylight Saving Time Mode is 'recurring' or 'nonRecurring'."
        ::= { ctcTime 16 }
            
    -- 1.3.6.1.4.1.4756.104.10.3.17
    ctcDaylightSavingEndingMinute OBJECT-TYPE
        SYNTAX      Integer32 (0..59)
        MAX-ACCESS  read-write
        STATUS      current
        DESCRIPTION
            "Select the ending Minute if Daylight Saving Time Mode is 'recurring' or 'nonRecurring'."
        ::= { ctcTime 17 }
            
    -- 1.3.6.1.4.1.4756.104.10.3.18
    ctcDaylightSavingTimeOffset OBJECT-TYPE
        SYNTAX      Integer32 (0..1440)
        MAX-ACCESS  read-write
        STATUS      current
        DESCRIPTION
            "Set the number of minutes to add during Daylight Saving Time. ( Range: 1 to 1440 )"
        ::= { ctcTime 18 }

  
    -- 1.3.6.1.4.1.4756.104.10.4
    ctcSystemLog OBJECT IDENTIFIER ::= { ctcSystem 4 }

    -- 1.3.6.1.4.1.4756.104.10.4.1
    ctcSystemLogServerMode OBJECT-TYPE
        SYNTAX      INTEGER {
                        enabled(1),
                        disabled(2)
                    }
        MAX-ACCESS  read-write
        STATUS      current
        DESCRIPTION
            "Indicates the server mode operation.
             Enabled: Enable server mode operation.
             Disabled: Disable server mode operation."
        ::= { ctcSystemLog 1 }
           
    -- 1.3.6.1.4.1.4756.104.10.4.2
    ctcSystemLogServerAddress OBJECT-TYPE
        SYNTAX      DisplayString
        MAX-ACCESS  read-write
        STATUS      current
        DESCRIPTION
            "Indicates the IPv4 host address of syslog server.
             If the switch provide DNS feature, it also can be a Host Name."
        ::= { ctcSystemLog 2 }

    -- 1.3.6.1.4.1.4756.104.10.4.3
    ctcSystemLogLevel OBJECT-TYPE
        SYNTAX      INTEGER {
                        info(1),
                        warning(2),
                        error(3)
                    }
        MAX-ACCESS  read-write
        STATUS      current
        DESCRIPTION
            "Indicates what kind of message will send to syslog server. Possible modes are:
             Info: Send informations, warnings and errors.
             Warning: Send warnings and errors.
             Error: Send errors."
        ::= { ctcSystemLog 3 }

    -- 1.3.6.1.4.1.4756.104.10.4.4
    ctcSystemLogClear OBJECT-TYPE
        SYNTAX      INTEGER {
                        trigger(1),
                        normal(2)
                    }
        MAX-ACCESS  read-write
        STATUS      current
        DESCRIPTION
            "Flushes all system log entries."
        ::= { ctcSystemLog 4 }

    -- 1.3.6.1.4.1.4756.104.10.4.5
    ctcSystemLogTable OBJECT-TYPE
        SYNTAX      SEQUENCE OF CtcSystemLogEntry
        MAX-ACCESS  not-accessible
        STATUS      current
        DESCRIPTION
            "The switch system log information."
        ::= { ctcSystemLog 5 }

    -- 1.3.6.1.4.1.4756.104.10.4.5.1
    ctcSystemLogEntry OBJECT-TYPE
        SYNTAX      CtcSystemLogEntry
        MAX-ACCESS  not-accessible
        STATUS      current
        DESCRIPTION
            "The system log entry."
        INDEX { ctcSystemLogMessageID }
        ::= { ctcSystemLogTable 1 }

    CtcSystemLogEntry ::=
        SEQUENCE {
            ctcSystemLogMessageID        Integer32,
            ctcSystemLogMessageLevel     INTEGER,
            ctcSystemLogMessageTime      DisplayString,
            ctcSystemLogMessage          DisplayString
        }

        -- 1.3.6.1.4.1.4756.104.10.4.5.1.1
        ctcSystemLogMessageID OBJECT-TYPE
            SYNTAX      Integer32 (1..999)
            MAX-ACCESS  not-accessible
            STATUS      current
            DESCRIPTION
                "The Index of the system log entry."
            ::= { ctcSystemLogEntry 1 }

        -- 1.3.6.1.4.1.4756.104.10.4.5.1.2
        ctcSystemLogMessageLevel OBJECT-TYPE
            SYNTAX      INTEGER {
                            info(1),
                            warning(2),
                            error(3)
                        }
            MAX-ACCESS  read-only
            STATUS      current
            DESCRIPTION
                "Indicates what kind of message."
            ::= { ctcSystemLogEntry 2 }

        -- 1.3.6.1.4.1.4756.104.10.4.5.1.3
        ctcSystemLogMessageTime OBJECT-TYPE
            SYNTAX      DisplayString
            MAX-ACCESS  read-only
            STATUS      current
            DESCRIPTION
                "The time of the system log entry."
            ::= { ctcSystemLogEntry 3 }
                            
        -- 1.3.6.1.4.1.4756.104.10.4.5.1.4
        ctcSystemLogMessage OBJECT-TYPE
            SYNTAX      DisplayString
            MAX-ACCESS  read-only
            STATUS      current
            DESCRIPTION
                "The message of the system log entry."
            ::= { ctcSystemLogEntry 4 }
            
  
    -- 1.3.6.1.4.1.4756.104.10.5
    ctcMaintenance OBJECT IDENTIFIER ::= { ctcSystem 5 }

    -- 1.3.6.1.4.1.4756.104.10.5.1
    ctcRestartDevice OBJECT-TYPE
        SYNTAX      INTEGER {
                        trigger(1),
                        normal(2)
                    }
        MAX-ACCESS  read-write
        STATUS      current
        DESCRIPTION
            "You can restart the device on this node."
        ::= { ctcMaintenance 1 }

    -- 1.3.6.1.4.1.4756.104.10.6
    ctcAutoProvision OBJECT IDENTIFIER ::= { ctcSystem 6 }
                
    -- 1.3.6.1.4.1.4756.104.10.6.1
    ctcAutoProvisionMode OBJECT-TYPE
        SYNTAX      INTEGER {
                        enabled(1),
                        disabled(2)
                    }
        MAX-ACCESS  read-write
        STATUS      current
        DESCRIPTION
            "Enable or disable the Auto-Provisioning.
             This feature automatic downloading of new software and configurations using DHCP and TFTP/HTTP/FTP."
        ::= { ctcAutoProvision 1 }
                
    -- 1.3.6.1.4.1.4756.104.10.6.2
    ctcAutoProvisionHttpFtpLoginMode OBJECT-TYPE
        SYNTAX      INTEGER {
                        enabled(1),
                        disabled(2)
                    }
        MAX-ACCESS  read-write
        STATUS      current
        DESCRIPTION
            "Indicates the HTTP/FTP downloading mode operation. Possible modes are:
             Enabled: When HTTP/FTP Login is enabled, the device downloads software and
                      configuration with username and password if given.
             Disabled: Downloads software and configuration without username and password."
        ::= { ctcAutoProvision 2 }

    -- 1.3.6.1.4.1.4756.104.60.1.3.1.2
    ctcAutoProvisionHttpFtpUserName OBJECT-TYPE
        SYNTAX      OCTET STRING (SIZE (0..20))
        MAX-ACCESS  read-write
        STATUS      current
        DESCRIPTION
            "The name identifying the HTTP/FTP Login user. The allowed string length is 0 to 20.
             the valid charactores are '0'~'9', 'a'~'z', 'A'~'Z' and '_'."
        ::= { ctcAutoProvision 3 }
    -- 1.3.6.1.4.1.4756.104.60.1.3.1.3
    
    ctcAutoProvisionHttpFtpPassword OBJECT-TYPE
        SYNTAX      OCTET STRING (SIZE (0..20))
        MAX-ACCESS  read-write
        STATUS      current
        DESCRIPTION
            "The password of the user. The allowed string length is 0 to 20."
        ::= { ctcAutoProvision 4 }


-- Power Reduction           
    -- 1.3.6.1.4.1.4756.104.30
    ctcPowerReduction OBJECT IDENTIFIER ::= { gsw2008ms 30 }

    -- 1.3.6.1.4.1.4756.104.30.1
    ctcLedPower OBJECT IDENTIFIER ::= { ctcPowerReduction 1 }

    -- 1.3.6.1.4.1.4756.104.30.1.1
    ctcCreateLedTimer OBJECT-TYPE
        SYNTAX      Integer32 (0..23)
        MAX-ACCESS  read-write
        STATUS      current
        DESCRIPTION                                  
            "Add a new timer and the hour can be configured as needed."
        ::= { ctcLedPower 1 }

    -- 1.3.6.1.4.1.4756.104.30.1.2
    ctcDeleteLedTimer OBJECT-TYPE
        SYNTAX      Integer32 (0..23)
        MAX-ACCESS  read-write
        STATUS      current
        DESCRIPTION
            "Delete a timer from indicated hour."
        ::= { ctcLedPower 2 }

    -- 1.3.6.1.4.1.4756.104.30.1.3
    ctcLedPowerTable OBJECT-TYPE
        SYNTAX      SEQUENCE OF CtcLedPowerEntry
        MAX-ACCESS  not-accessible
        STATUS      current
        DESCRIPTION
            "The LEDs power consumption can be reduced by lowering the LEDs intensity.
             LEDs intensity could for example be lowered during night time,
             or they could be turn completely off."
        ::= { ctcLedPower 3 }

    -- 1.3.6.1.4.1.4756.104.30.1.3.1
    ctcLedPowerEntry OBJECT-TYPE
        SYNTAX      CtcLedPowerEntry
        MAX-ACCESS  not-accessible
        STATUS      current
        DESCRIPTION
            "It is possible to configure 24 different hours of the day,
             at where the LEDs intensity should be set."
        INDEX { ctcLedTimerIndex }
        ::= { ctcLedPowerTable 1 }

    CtcLedPowerEntry ::=
        SEQUENCE {
            ctcLedTimerIndex    Integer32,
            ctcLedPowerTime     Integer32,
            ctcLedIntensity	    INTEGER
        }

        -- 1.3.6.1.4.1.4756.104.30.1.3.1.1
        ctcLedTimerIndex OBJECT-TYPE
            SYNTAX      Integer32 (1..24)
            MAX-ACCESS  read-only
            STATUS      current
            DESCRIPTION
                "The LEDs intensity timers index."
            ::= { ctcLedPowerEntry 1 }

        -- 1.3.6.1.4.1.4756.104.30.1.3.1.2
        ctcLedPowerTime OBJECT-TYPE
            SYNTAX      Integer32 (0..23)
            UNITS       "O'clock"
            MAX-ACCESS  read-write
            STATUS      current
            DESCRIPTION
                "The time at which the LEDs intensity shall be set."
            ::= { ctcLedPowerEntry 2 }
        
        -- 1.3.6.1.4.1.4756.104.30.1.3.1.3
        ctcLedIntensity OBJECT-TYPE
            SYNTAX      INTEGER {
                            intensity100(1),
                            intensity90(2),
                            intensity80(3),
                            intensity70(4),
                            intensity60(5),
                            intensity50(6),
                            intensity40(7),
                            intensity30(8),
                            intensity20(9),
                            intensity10(10),
                            intensity0(11)
                        }
            MAX-ACCESS  read-write
            STATUS  current
            DESCRIPTION
                "The LEDs intensity (100% = Full power, 0% = LED off)."
            ::= { ctcLedPowerEntry 3 }
                        
    -- 1.3.6.1.4.1.4756.104.30.1.4
    ctcLedOnTime OBJECT-TYPE
        SYNTAX      Integer32 (10..9999)
        UNITS       "Second"
        MAX-ACCESS  read-write
        STATUS      current
        DESCRIPTION
            "The number of seconds that the LEDs will have full intensity."
        ::= { ctcLedPower 4 }
                       
    -- 1.3.6.1.4.1.4756.104.30.1.5
    ctcLedOnAtError OBJECT-TYPE
        SYNTAX      INTEGER {
                        enabled(1),
                        disabled(2)
                    }
        MAX-ACCESS  read-write
        STATUS  current
        DESCRIPTION
            "Controls whether the LEDs will have full intensity at errors are occured."
        ::= { ctcLedPower 5 }
                       
    -- 1.3.6.1.4.1.4756.104.30.2
    ctcEEE OBJECT IDENTIFIER ::= { ctcPowerReduction 2 }

    -- 1.3.6.1.4.1.4756.104.30.2.1
    ctcEeePortTable OBJECT-TYPE
        SYNTAX      SEQUENCE OF CtcEEEPortEntry
        MAX-ACCESS  not-accessible
        STATUS      current
        DESCRIPTION
            "This table allows the user to inspect and configure the current EEE port settings."
        ::= { ctcEEE 1 }

    -- 1.3.6.1.4.1.4756.104.30.2.1.1
    ctcEeePortEntry OBJECT-TYPE
        SYNTAX      CtcEEEPortEntry
        MAX-ACCESS  not-accessible
        STATUS      current
        DESCRIPTION
            "The entry of EEE ports."
        INDEX { ctcPortIndex }
        ::= { ctcEeePortTable 1 }

    CtcEEEPortEntry ::=
        SEQUENCE {
            ctcPortIndex         Integer32,
            ctcEeePortEnabled    TruthValue,
            ctcEeeUrgentQueues   DisplayString
        }
                
        -- 1.3.6.1.4.1.4756.104.30.2.2.1.1
        ctcPortIndex OBJECT-TYPE
            SYNTAX      Integer32 (1..10)
            MAX-ACCESS  read-only
            STATUS      current
            DESCRIPTION
                "This is the logical port number for this and below rows."
            ::= { ctcEeePortEntry 1 }

        -- 1.3.6.1.4.1.4756.104.30.2.2.1.2
        ctcEeePortEnabled OBJECT-TYPE
            SYNTAX      TruthValue
            MAX-ACCESS  read-write
            STATUS      current
            DESCRIPTION
                "Controls whether EEE is enabled for this switch port."
            ::= { ctcEeePortEntry 2 }                

        -- 1.3.6.1.4.1.4756.104.30.2.2.1.3
        ctcEeeUrgentQueues OBJECT-TYPE
            SYNTAX      DisplayString (SIZE (0..128))
            MAX-ACCESS  read-write
            STATUS      current
            DESCRIPTION
                "Queues set will activate transmition of frames as soon as any data is available."
            ::= { ctcEeePortEntry 3 }                

           
-- Thermal Protection
    -- 1.3.6.1.4.1.4756.104.40
    ctcThermalProtection OBJECT IDENTIFIER ::= { gsw2008ms 40 }

    -- 1.3.6.1.4.1.4756.104.40.1
    ctcThermalPriorityGroupsTable OBJECT-TYPE
        SYNTAX      SEQUENCE OF CtcThermalPriorityGroupsEntry
        MAX-ACCESS  not-accessible
        STATUS      current
        DESCRIPTION
            "This table allows the user to configure the Temperature of priorities."
        ::= { ctcThermalProtection 1 }

    -- 1.3.6.1.4.1.4756.104.40.1.1
    ctcThermalPriorityGroupsEntry OBJECT-TYPE
        SYNTAX      CtcThermalPriorityGroupsEntry
        MAX-ACCESS  not-accessible
        STATUS      current
        DESCRIPTION
            "The entry of priorities."
        INDEX { ctcThermalPriorityIndex }
        ::= { ctcThermalPriorityGroupsTable 1 }

    CtcThermalPriorityGroupsEntry ::=
        SEQUENCE {
            ctcThermalPriorityIndex  Integer32,
            ctcThermalTemperature    Integer32
        }
                
        -- 1.3.6.1.4.1.4756.104.40.1.1.1
        ctcThermalPriorityIndex OBJECT-TYPE
            SYNTAX      Integer32 (0..3)
            MAX-ACCESS  read-only
            STATUS      current
            DESCRIPTION
                "Temperature settings for priority groups."
            ::= { ctcThermalPriorityGroupsEntry 1 }
       
        -- 1.3.6.1.4.1.4756.104.40.1.1.2
        ctcThermalTemperature OBJECT-TYPE
            SYNTAX      Integer32 (0..255)
            UNITS       "Degrees Celcius"
            MAX-ACCESS  read-write
            STATUS      current
            DESCRIPTION
                "The temperature at which the ports with the corresponding priority will be turned off."
            ::= { ctcThermalPriorityGroupsEntry 2 }                

    -- 1.3.6.1.4.1.4756.104.40.2
    ctcThermaProtectionPortsTable OBJECT-TYPE
        SYNTAX      SEQUENCE OF CtcThermaProtectionPortsEntry
        MAX-ACCESS  not-accessible
        STATUS      current
        DESCRIPTION
            "This table allows the user to configure the priority of ports."
        ::= { ctcThermalProtection 2 }

    -- 1.3.6.1.4.1.4756.104.40.2.1
    ctcThermaProtectionPortsEntry OBJECT-TYPE
        SYNTAX      CtcThermaProtectionPortsEntry
        MAX-ACCESS  not-accessible
        STATUS      current
        DESCRIPTION
            "The entry of ports."
        INDEX { ctcPortIndex }
        ::= { ctcThermaProtectionPortsTable 1 }

    CtcThermaProtectionPortsEntry ::=
        SEQUENCE {
            ctcThermalPortPriorityConfig     Integer32,
            ctcThermalPortTemperature        Integer32,
            ctcThermalPortStatus             INTEGER
        }

        -- 1.3.6.1.4.1.4756.104.40.2.1.1
        ctcThermalPortPriorityConfig OBJECT-TYPE
            SYNTAX      Integer32 (0..3)
            MAX-ACCESS  read-write
            STATUS      current
            DESCRIPTION
                "The priority the port belongs to. There are 4 priorities are supported."
            ::= { ctcThermaProtectionPortsEntry 1 }                
        
        -- 1.3.6.1.4.1.4756.104.40.2.1.2
        ctcThermalPortTemperature OBJECT-TYPE
            SYNTAX      Integer32 (0..255)
            UNITS       "Degrees Celcius"
            MAX-ACCESS  read-only
            STATUS      current
            DESCRIPTION
                "The current chip temperature in degrees Celcius."
            ::= { ctcThermaProtectionPortsEntry 2 }                

        -- 1.3.6.1.4.1.4756.104.40.2.1.3
        ctcThermalPortStatus OBJECT-TYPE
            SYNTAX      INTEGER {
                        thermalProtected(1),
                        operatingNormally(2)
                    }
            MAX-ACCESS  read-only
            STATUS      current
            DESCRIPTION
                "The port status, Port link operating normally or thermal protected(Link is down)."
            ::= { ctcThermaProtectionPortsEntry 3 }                

           
-- Ports
    -- 1.3.6.1.4.1.4756.104.50
    ctcPorts OBJECT IDENTIFIER ::= { gsw2008ms 50 }

    -- 1.3.6.1.4.1.4756.104.50.1
    ctcPortsConfigTable OBJECT-TYPE
        SYNTAX      SEQUENCE OF CtcPortsConfigEntry
        MAX-ACCESS  not-accessible
        STATUS      current
        DESCRIPTION
            "This table shows current port configurations. Ports can also be configured here."
        ::= { ctcPorts 1 }

    -- 1.3.6.1.4.1.4756.104.50.1.1
    ctcPortsConfigEntry OBJECT-TYPE
        SYNTAX      CtcPortsConfigEntry
        MAX-ACCESS  not-accessible
        STATUS      current
        DESCRIPTION
            "The entry of ports."
        INDEX { ctcPortIndex }
        ::= { ctcPortsConfigTable 1 }

    CtcPortsConfigEntry ::=
        SEQUENCE {
            ctcPortLink              INTEGER,
            ctcPortSpeedCurrent      INTEGER,
            ctcPortSpeedMode         INTEGER,
            ctcPortFlowCtrlCurrentRx TruthValue,
            ctcPortFlowCtrlCurrentTx TruthValue,
            ctcPortFlowCtrlEnabled   TruthValue,
            ctcPortMaxFrameSize      Integer32,
            ctcPortExcCollMode       INTEGER,
            ctcPortPowerControl      INTEGER
        }
                         
        -- 1.3.6.1.4.1.4756.104.50.1.1.1
        ctcPortLink OBJECT-TYPE
            SYNTAX      INTEGER {
                            linkUp(1),
                            linkDown(2),
                            linkDownByACL(3),
                            linkDownByThermalProtect(4),
                            linkDownByLoopProtect(5)
                        }
            MAX-ACCESS  read-only
            STATUS      current
            DESCRIPTION
                "The current link state."
            ::= { ctcPortsConfigEntry 1 }
                  
        -- 1.3.6.1.4.1.4756.104.50.1.1.2
        ctcPortSpeedCurrent OBJECT-TYPE
            SYNTAX      INTEGER {
                            linkDown(1),
                            link10Mhdx(2),
                            link10Mfdx(3),
                            link100Mhdx(4),
                            link100Mfdx(5),
                            link1Gfdx(6)
                        }
            MAX-ACCESS  read-only
            STATUS      current
            DESCRIPTION
                "Provides the current link speed of the port."
            ::= { ctcPortsConfigEntry 2 }
                  
        -- 1.3.6.1.4.1.4756.104.50.1.1.3
        ctcPortSpeedMode OBJECT-TYPE
            SYNTAX      INTEGER {
                            disabled(1),
                            auto(2),
                            speed10Mhdx(3),
                            speed10Mfdx(4),
                            speed100Mhdx(5),
                            speed100Mfdx(6),
                            speed1Gfdx(7),
                            detection(8)
                        }
            MAX-ACCESS  read-write
            STATUS      current
            DESCRIPTION
                "Select link speed for the switch port."
            ::= { ctcPortsConfigEntry 3 }
                   
        -- 1.3.6.1.4.1.4756.104.50.1.1.4
        ctcPortFlowCtrlCurrentRx OBJECT-TYPE
            SYNTAX      TruthValue
            MAX-ACCESS  read-only
            STATUS      current
            DESCRIPTION
                "Indicates whether pause frames on the port are obeyed."
            ::= { ctcPortsConfigEntry 4 }
                  
        -- 1.3.6.1.4.1.4756.104.50.1.1.5
        ctcPortFlowCtrlCurrentTx OBJECT-TYPE
            SYNTAX      TruthValue
            MAX-ACCESS  read-only
            STATUS      current
            DESCRIPTION
                "Indicates whether pause frames on the port are transmitted."
            ::= { ctcPortsConfigEntry 5 }
                  
        -- 1.3.6.1.4.1.4756.104.50.1.1.6
        ctcPortFlowCtrlEnabled OBJECT-TYPE
            SYNTAX      TruthValue
            MAX-ACCESS  read-write
            STATUS      current
            DESCRIPTION
                "When Auto Speed is selected on a port,
                 this section indicates the flow control capability that is advertised to the link partner."
            ::= { ctcPortsConfigEntry 6 }
                  
        -- 1.3.6.1.4.1.4756.104.50.1.1.7
        ctcPortMaxFrameSize OBJECT-TYPE
            SYNTAX      Integer32 (1518..9600)
            UNITS       "Octet"
            MAX-ACCESS  read-write
            STATUS      current
            DESCRIPTION
                "The maximum frame size allowed for the switch port, including FCS."
            ::= { ctcPortsConfigEntry 7 }
                  
        -- 1.3.6.1.4.1.4756.104.50.1.1.8
        ctcPortExcCollMode OBJECT-TYPE
            SYNTAX      INTEGER {
                            discard(1),
                            restart(2)
                        }
            MAX-ACCESS  read-write
            STATUS      current
            DESCRIPTION
                "Configure port transmit collision behavior.
                 Discard: Discard frame after 16 collisions (default).
                 Restart: Restart backoff algorithm after 16 collisions."
            DEFVAL      { 1 }
            ::= { ctcPortsConfigEntry 8 }
                  
        -- 1.3.6.1.4.1.4756.104.50.1.1.9
        ctcPortPowerControl OBJECT-TYPE
            SYNTAX      INTEGER {
                            disabled(1),
                            actiPHY(2),
                            perfectReach(3),
                            enabled(4)
                        }
            MAX-ACCESS  read-write
            STATUS      current
            DESCRIPTION
                "The Configured allows for changing the power savings mode parameters per port.
                 Disabled: All power savings mechanisms disabled.
                 ActiPHY: Link down power savings enabled.
                 PerfectReach: Link up power savings enabled.
                 Enabled: Both link up and link down power savings enabled."
            ::= { ctcPortsConfigEntry 9 }

    -- 1.3.6.1.4.1.4756.104.50.2
    ctcAutoLaserShutdownTable OBJECT-TYPE
        SYNTAX      SEQUENCE OF CtcAutoLaserShutdownEntry
        MAX-ACCESS  not-accessible
        STATUS      current
        DESCRIPTION
            "This table allows the user to inspect and configure the current setting for transceiver module Tx power."
        ::= { ctcPorts 2 }

    -- 1.3.6.1.4.1.4756.104.50.2.1
    ctcAutoLaserShutdownEntry OBJECT-TYPE
        SYNTAX      CtcAutoLaserShutdownEntry
        MAX-ACCESS  not-accessible
        STATUS      current
        DESCRIPTION
            "The entry of fibre ports."
        INDEX { ctcFiberPortIndex }
        ::= { ctcAutoLaserShutdownTable 1 }

    CtcAutoLaserShutdownEntry ::=
        SEQUENCE {
            ctcFiberPortIndex       Integer32,
            ctcAlsEnabled           TruthValue,
            ctcAlsLaserOnPeriod     Integer32,
            ctcAlsLaserOffPeriod    Integer32
        }

        -- 1.3.6.1.4.1.4756.104.50.2.1.1
        ctcFiberPortIndex OBJECT-TYPE
            SYNTAX      Integer32 (9..10)
            MAX-ACCESS  read-only
            STATUS      current
            DESCRIPTION
                "This is the logical port number for this and below rows."
            ::= { ctcAutoLaserShutdownEntry 1 }

        -- 1.3.6.1.4.1.4756.104.50.2.1.2
        ctcAlsEnabled OBJECT-TYPE
            SYNTAX      TruthValue
            MAX-ACCESS  read-write
            STATUS      current
            DESCRIPTION
                "Enable/Disable the laser power of transceiver module shutdown automatically."
            ::= { ctcAutoLaserShutdownEntry 2 }

        -- 1.3.6.1.4.1.4756.104.50.2.1.3
        ctcAlsLaserOnPeriod OBJECT-TYPE
            SYNTAX      Integer32 (2..30)
            UNITS       "100ms"
            MAX-ACCESS  read-write
            STATUS      current
            DESCRIPTION
                "The period is Tx laser power turn ON.
                 The allowed range is 2 to 30 in tenths of seconds,
                 default period is 10 in tenths of seconds (1 second)."
            DEFVAL      { 10 }
            ::= { ctcAutoLaserShutdownEntry 3 }

        -- 1.3.6.1.4.1.4756.104.50.2.1.4
        ctcAlsLaserOffPeriod OBJECT-TYPE
            SYNTAX      Integer32 (10..50)
            UNITS       "100ms"
            MAX-ACCESS  read-write
            STATUS      current
            DESCRIPTION
                "The period is Tx laser power turn OFF.
                 The allowed range is 10 to 50 in tenths of seconds,
                 default period is 30 in tenths of seconds (3 second)."
            DEFVAL      { 30 }
            ::= { ctcAutoLaserShutdownEntry 4 }

    -- 1.3.6.1.4.1.4756.104.50.3
    ctcSfpStatusTable OBJECT-TYPE
        SYNTAX      SEQUENCE OF CtcSfpStatusEntry
        MAX-ACCESS  not-accessible
        STATUS      current
        DESCRIPTION
            "This table provides status of SFPs."
        ::= { ctcPorts 3 }

    -- 1.3.6.1.4.1.4756.104.50.3.1
    ctcSfpStatusEntry OBJECT-TYPE
        SYNTAX      CtcSfpStatusEntry
        MAX-ACCESS  not-accessible
        STATUS      current
        DESCRIPTION
            "The entry of fiber ports."
        INDEX { ctcFiberPortIndex }
        ::= { ctcSfpStatusTable 1 }

    CtcSfpStatusEntry ::=
        SEQUENCE {
            ctcSfpModule                INTEGER,
            ctcSfpVendorName            DisplayString,
            ctcSfpVendorPartNumber      DisplayString,
            ctcSfpVendorSerialNumber    DisplayString,
            ctcSfpType                  INTEGER,
            ctcSfpWaveLength1           Integer32,
            ctcSfpWaveLength2           Integer32,
            ctcSfpLinkLength            Integer32,
            ctcSfpSupportedDDM          INTEGER,
            ctcSfpTxPower               Float32TC,
            ctcSfpRxPower               Float32TC,
            ctcSfpRxSensitivity         Float32TC,
            ctcSfpTxBias                INTEGER,
            ctcSfpSupplyVoltage         Float32TC,
            ctcSfpTemperature           Float32TC
        }
        
        -- 1.3.6.1.4.1.4756.104.50.3.1.1
        ctcSfpModule  OBJECT-TYPE
            SYNTAX      INTEGER {
                            inserted(1),
                            removed(2)
                        }
            MAX-ACCESS  read-only
            STATUS      current
            DESCRIPTION
                "Indicate the SFP module is existent or not."
            ::= { ctcSfpStatusEntry 1 }

        -- 1.3.6.1.4.1.4756.104.50.3.1.2
        ctcSfpVendorName  OBJECT-TYPE
            SYNTAX      DisplayString
            MAX-ACCESS  read-only
            STATUS      current
            DESCRIPTION
                "The name of SFP vendor."
            ::= { ctcSfpStatusEntry 2 }

        -- 1.3.6.1.4.1.4756.104.50.3.1.3
        ctcSfpVendorPartNumber  OBJECT-TYPE
            SYNTAX      DisplayString
            MAX-ACCESS  read-only
            STATUS      current
            DESCRIPTION
                "The part number provided by SFP vendor."
            ::= { ctcSfpStatusEntry 3 }

        -- 1.3.6.1.4.1.4756.104.50.3.1.4
        ctcSfpVendorSerialNumber  OBJECT-TYPE
            SYNTAX      DisplayString
            MAX-ACCESS  read-only
            STATUS      current
            DESCRIPTION
                "The serial number provided by SFP vendor."
            ::= { ctcSfpStatusEntry 4 }

        -- 1.3.6.1.4.1.4756.104.50.3.1.5
        ctcSfpType  OBJECT-TYPE
            SYNTAX      INTEGER {
                            none(0),
                            singleMode(1),
                            multiMode(2)
                        }
            MAX-ACCESS  read-only
            STATUS      current
            DESCRIPTION
                "The type of fibre channel transmission media."
            ::= { ctcSfpStatusEntry 5 }

        -- 1.3.6.1.4.1.4756.104.50.3.1.6
        ctcSfpWaveLength1  OBJECT-TYPE
            SYNTAX      Integer32
            UNITS		"nm"
            MAX-ACCESS  read-only
            STATUS      current
            DESCRIPTION
                "The wave length in nm."
            ::= { ctcSfpStatusEntry 6 }

        -- 1.3.6.1.4.1.4756.104.50.3.1.7
        ctcSfpWaveLength2  OBJECT-TYPE
            SYNTAX      Integer32
            UNITS		"nm"
            MAX-ACCESS  read-only
            STATUS      current
            DESCRIPTION
                "The wave length in nm."
            ::= { ctcSfpStatusEntry 7 }

        -- 1.3.6.1.4.1.4756.104.50.3.1.8
        ctcSfpLinkLength  OBJECT-TYPE
            SYNTAX      Integer32
            UNITS		"m"
            MAX-ACCESS  read-only
            STATUS      current
            DESCRIPTION
                "The link length in meter."
            ::= { ctcSfpStatusEntry 8 }

        -- 1.3.6.1.4.1.4756.104.50.3.1.9
        ctcSfpSupportedDDM  OBJECT-TYPE
            SYNTAX      INTEGER {
                            yes(1),
                            no(2)
                        }
            MAX-ACCESS  read-only
            STATUS      current
            DESCRIPTION
                "Indicate the SFP module supported Digital Diagnostics Monitoring(DDM) or not."
            ::= { ctcSfpStatusEntry 9 }

        -- 1.3.6.1.4.1.4756.104.50.3.1.10
        ctcSfpTxPower  OBJECT-TYPE
            SYNTAX      Float32TC
            UNITS		"dBm"
            MAX-ACCESS  read-only
            STATUS      current
            DESCRIPTION
                "The TX output power in dBm."
            ::= { ctcSfpStatusEntry 10 }

        -- 1.3.6.1.4.1.4756.104.50.3.1.11
        ctcSfpRxPower  OBJECT-TYPE
            SYNTAX      Float32TC
            UNITS		"dBm"
            MAX-ACCESS  read-only
            STATUS      current
            DESCRIPTION
                "The RX input power in dBm."
            ::= { ctcSfpStatusEntry 11}

        -- 1.3.6.1.4.1.4756.104.50.3.1.12
        ctcSfpRxSensitivity  OBJECT-TYPE
            SYNTAX      Float32TC
            UNITS		"dBm"
            MAX-ACCESS  read-only
            STATUS      current
            DESCRIPTION
                "The RX sensitivity in dBm."
            ::= { ctcSfpStatusEntry 12}

        -- 1.3.6.1.4.1.4756.104.50.3.1.13
        ctcSfpTxBias  OBJECT-TYPE
            SYNTAX      INTEGER
            UNITS		"mA"
            MAX-ACCESS  read-only
            STATUS      current
            DESCRIPTION
                "The TX bias current in mA."
            ::= { ctcSfpStatusEntry 13 }

        -- 1.3.6.1.4.1.4756.104.50.3.1.14
        ctcSfpSupplyVoltage  OBJECT-TYPE
            SYNTAX      Float32TC
            UNITS		"V"
            MAX-ACCESS  read-only
            STATUS      current
            DESCRIPTION
                "The transceiver supply voltage in V."
            ::= { ctcSfpStatusEntry 14 }

        -- 1.3.6.1.4.1.4756.104.50.3.1.15
        ctcSfpTemperature  OBJECT-TYPE
            SYNTAX      Float32TC
            UNITS		"degree C"
            MAX-ACCESS  read-only
            STATUS      current
            DESCRIPTION
                "The transceiver temperature in degree C."
            ::= { ctcSfpStatusEntry 15 }

    -- 1.3.6.1.4.1.4756.104.50.5
    ctcPortsTrafficClear OBJECT-TYPE
        SYNTAX      INTEGER {
                        trigger(1),
                        normal(2)
                    }
        MAX-ACCESS  read-write
        STATUS      current
        DESCRIPTION
            "Clears the counters for all ports."
        ::= { ctcPorts 5 }

    -- 1.3.6.1.4.1.4756.104.50.6
    ctcPortsTrafficOverviewTable OBJECT-TYPE
        SYNTAX      SEQUENCE OF CtcPortsTrafficOverviewEntry
        MAX-ACCESS  not-accessible
        STATUS      current
        DESCRIPTION
            "This table provides an overview of general traffic statistics for all switch ports."
        ::= { ctcPorts 6 }

    -- 1.3.6.1.4.1.4756.104.50.6.1
    ctcPortsTrafficOverviewEntry OBJECT-TYPE
        SYNTAX      CtcPortsTrafficOverviewEntry
        MAX-ACCESS  not-accessible
        STATUS      current
        DESCRIPTION
            "The entry of ports."
        INDEX { ctcPortIndex }
        ::= { ctcPortsTrafficOverviewTable 1 }

    CtcPortsTrafficOverviewEntry ::=
        SEQUENCE {
            ctcReceivedPackets       Counter64,
            ctcTransmittedPackets    Counter64,
            ctcReceivedBytes         Counter64,
            ctcTransmittedBytes      Counter64,
            ctcReceivedErrors        Counter64,
            ctcTransmittedErrors     Counter64,
            ctcReceivedDrops         Counter64,
            ctcTransmittedDrops      Counter64,
            ctcReceivedFiltered      Counter64
        }
                  
        -- 1.3.6.1.4.1.4756.104.50.6.1.1    
        ctcReceivedPackets OBJECT-TYPE
            SYNTAX      Counter64
            UNITS       "Packets"
            MAX-ACCESS  read-only
            STATUS      current
            DESCRIPTION
                "The number of received packets per port."
            ::= { ctcPortsTrafficOverviewEntry 1 }

        -- 1.3.6.1.4.1.4756.104.50.6.1.2    
        ctcTransmittedPackets OBJECT-TYPE
            SYNTAX      Counter64
            UNITS       "Packets"
            MAX-ACCESS  read-only
            STATUS      current
            DESCRIPTION
                "The number of transmitted packets per port."
            ::= { ctcPortsTrafficOverviewEntry 2 }
                  
        -- 1.3.6.1.4.1.4756.104.50.6.1.3    
        ctcReceivedBytes OBJECT-TYPE
            SYNTAX      Counter64
            UNITS       "Bytes"
            MAX-ACCESS  read-only
            STATUS      current
            DESCRIPTION
                "The number of received bytes per port."
            ::= { ctcPortsTrafficOverviewEntry 3 }
                  
        -- 1.3.6.1.4.1.4756.104.50.6.1.4    
        ctcTransmittedBytes OBJECT-TYPE
            SYNTAX      Counter64
            UNITS       "Bytes"
            MAX-ACCESS  read-only
            STATUS      current
            DESCRIPTION
                "The number of transmitted bytes per port."
            ::= { ctcPortsTrafficOverviewEntry 4 }
                  
        -- 1.3.6.1.4.1.4756.104.50.6.1.5    
        ctcReceivedErrors OBJECT-TYPE
            SYNTAX      Counter64
            UNITS       "Packets"
            MAX-ACCESS  read-only
            STATUS      current
            DESCRIPTION
                "The number of frames received in error."
            ::= { ctcPortsTrafficOverviewEntry 5 }
                  
        -- 1.3.6.1.4.1.4756.104.50.6.1.6    
        ctcTransmittedErrors OBJECT-TYPE
            SYNTAX      Counter64
            UNITS       "Packets"
            MAX-ACCESS  read-only
            STATUS      current
            DESCRIPTION
                "The number of incomplete transmissions per port."
            ::= { ctcPortsTrafficOverviewEntry 6 }
                  
        -- 1.3.6.1.4.1.4756.104.50.6.1.7    
        ctcReceivedDrops OBJECT-TYPE
            SYNTAX      Counter64
            UNITS       "Packets"
            MAX-ACCESS  read-only
            STATUS      current
            DESCRIPTION
                "The number of frames discarded due to ingress congestion."
            ::= { ctcPortsTrafficOverviewEntry 7 }
                  
        -- 1.3.6.1.4.1.4756.104.50.6.1.8    
        ctcTransmittedDrops OBJECT-TYPE
            SYNTAX      Counter64
            UNITS       "Packets"
            MAX-ACCESS  read-only
            STATUS      current
            DESCRIPTION
                "The number of frames discarded due to egress congestion."
            ::= { ctcPortsTrafficOverviewEntry 8 }
                  
        -- 1.3.6.1.4.1.4756.104.50.6.1.9    
        ctcReceivedFiltered OBJECT-TYPE
            SYNTAX      Counter64
            UNITS       "Packets"
            MAX-ACCESS  read-only
            STATUS      current
            DESCRIPTION
                "The number of received frames filtered by the forwarding process."
            ::= { ctcPortsTrafficOverviewEntry 9 }

    -- 1.3.6.1.4.1.4756.104.50.7
    ctcPortsQosStatisticsClear OBJECT-TYPE
        SYNTAX      INTEGER {
                        trigger(1),
                        normal(2)
                    }
        MAX-ACCESS  read-write
        STATUS      current
        DESCRIPTION
            "Clears the counters for all ports."
        ::= { ctcPorts 7 }

    -- 1.3.6.1.4.1.4756.104.50.8
    ctcPortsQosStatisticsTable OBJECT-TYPE
        SYNTAX      SEQUENCE OF CtcPortsQosStatisticsEntry
        MAX-ACCESS  not-accessible
        STATUS      current
        DESCRIPTION
            "This table provides statistics for the different queues for all switch ports."
        ::= { ctcPorts 8 }

    -- 1.3.6.1.4.1.4756.104.50.8.1
    ctcPortsQosStatisticsEntry OBJECT-TYPE
        SYNTAX      CtcPortsQosStatisticsEntry
        MAX-ACCESS  not-accessible
        STATUS      current
        DESCRIPTION
            "Each entry contains 8 QoS queues per port."
        INDEX { ctcPortIndex, ctcQueueIndex }
        ::= { ctcPortsQosStatisticsTable 1 }

    CtcPortsQosStatisticsEntry ::=
        SEQUENCE {
            ctcQueueIndex            Integer32,
            ctcQueueRxPackets        Counter64,
            ctcQueueTxPackets        Counter64
        }

        -- 1.3.6.1.4.1.4756.104.50.8.1.1
        ctcQueueIndex OBJECT-TYPE
            SYNTAX      Integer32 (0..7)
            MAX-ACCESS  read-only
            STATUS      current
            DESCRIPTION
                "There are 8 QoS queues per port. Q0 is the lowest priority queue."
            ::= { ctcPortsQosStatisticsEntry 1 }
                  
        -- 1.3.6.1.4.1.4756.104.50.8.1.2    
        ctcQueueRxPackets OBJECT-TYPE
            SYNTAX      Counter64
            MAX-ACCESS  read-only
            STATUS      current
            DESCRIPTION
                "The number of received packets per queue."
            ::= { ctcPortsQosStatisticsEntry 2 }
                  
        -- 1.3.6.1.4.1.4756.104.50.8.1.3    
        ctcQueueTxPackets OBJECT-TYPE
            SYNTAX      Counter64
            MAX-ACCESS  read-only
            STATUS      current
            DESCRIPTION
                "The number of transmitted  packets per queue."
            ::= { ctcPortsQosStatisticsEntry 3 }

    -- 1.3.6.1.4.1.4756.104.50.9
    ctcPortsQclResolveConflict  OBJECT-TYPE
        SYNTAX      INTEGER {
                        trigger(1),
                        normal(2)
                    }
        MAX-ACCESS  read-write
        STATUS      current
        DESCRIPTION
            "Resolves conflict by releaseing the resource required by the QCE."
        ::= { ctcPorts 9 }

    -- 1.3.6.1.4.1.4756.104.50.10
    ctcPortsQclStatusTable OBJECT-TYPE
        SYNTAX      SEQUENCE OF CtcPortsQclStatusEntry
        MAX-ACCESS  not-accessible
        STATUS      current
        DESCRIPTION
            "This table shows the QCL status by different QCL users."
        ::= { ctcPorts 10 }

    -- 1.3.6.1.4.1.4756.104.50.10.1
    ctcPortsQclStatusEntry OBJECT-TYPE
        SYNTAX      CtcPortsQclStatusEntry
        MAX-ACCESS  not-accessible
        STATUS      current
        DESCRIPTION
            "Each entry describes the QCE that is defined."
        INDEX { ctcQclStatusIndex }
        ::= { ctcPortsQclStatusTable 1 }

    CtcPortsQclStatusEntry ::=
        SEQUENCE {
            ctcQclStatusIndex    Integer32,
            ctcQclUser           INTEGER,
            ctcQCEntryNumber     Integer32,
            ctcQclFrameType      INTEGER,
            ctcQclPort           DisplayString,
            ctcQclActionClass    Integer32,
            ctcQclActionDPL      Integer32,
            ctcQclActionDSCP     Integer32,
            ctcQclConflict       TruthValue
        }

        -- 1.3.6.1.4.1.4756.104.50.10.1.1
        ctcQclStatusIndex OBJECT-TYPE
            SYNTAX      Integer32 (1..240)
            MAX-ACCESS  read-only
            STATUS      current
            DESCRIPTION
                "The index of QoS Control List Status."
            ::= { ctcPortsQclStatusEntry 1 }
                  
        -- 1.3.6.1.4.1.4756.104.50.10.1.2    
        ctcQclUser OBJECT-TYPE
            SYNTAX      INTEGER {
                            static(1),
                            voiceVLAN(2)
                        }
            MAX-ACCESS  read-only
            STATUS      current
            DESCRIPTION
                "Indicates the QCL user."
            ::= { ctcPortsQclStatusEntry 2 }
                  
        -- 1.3.6.1.4.1.4756.104.50.10.1.3    
        ctcQCEntryNumber OBJECT-TYPE
            SYNTAX      Integer32
            MAX-ACCESS  read-only
            STATUS      current
            DESCRIPTION
                "Indicates the index of QCE."
            ::= { ctcPortsQclStatusEntry 3 }
                  
        -- 1.3.6.1.4.1.4756.104.50.10.1.4    
        ctcQclFrameType OBJECT-TYPE
            SYNTAX      INTEGER {
                            any(1),
                            ethernet(2),
                            llc(3),
                            snap(4),
                            ipv4(5),
                            ipv6(6)
                        }
            MAX-ACCESS  read-only
            STATUS      current
            DESCRIPTION
                "Indicates the type of frame to look for incomming frames. Possible frame types are:
                 Any: The QCE will match all frame type.
                 Ethernet: Only Ethernet frames (with Ether Type 0x600-0xFFFF) are allowed.
                 LLC: Only (LLC) frames are allowed.
                 LLC: Only (SNAP) frames are allowed.
                 IPv4: The QCE will match only IPV4 frames.
                 IPv6: The QCE will match only IPV6 frames."
            ::= { ctcPortsQclStatusEntry 4 }
                  
        -- 1.3.6.1.4.1.4756.104.50.10.1.5    
        ctcQclPort OBJECT-TYPE
            SYNTAX      DisplayString (SIZE (1..128))
            MAX-ACCESS  read-only
            STATUS      current
            DESCRIPTION
                "Indicates the list of ports configured with the QCE."
            ::= { ctcPortsQclStatusEntry 5 }     
                  
        -- 1.3.6.1.4.1.4756.104.50.10.1.6    
        ctcQclActionClass OBJECT-TYPE
            SYNTAX      Integer32  (-1 | 0..7)
            MAX-ACCESS  read-only
            STATUS      current
            DESCRIPTION
                "Classified QoS Class, if a frame matches the QCE it will be put in the queue.
                 -1: default
                 0 to 7: class0 to class7"
            DEFVAL      { -1 }
            ::= { ctcPortsQclStatusEntry 6 }
                  
        -- 1.3.6.1.4.1.4756.104.50.10.1.7    
        ctcQclActionDPL OBJECT-TYPE
            SYNTAX      Integer32 (-1 | 0..1)
            MAX-ACCESS  read-only
            STATUS      current
            DESCRIPTION
                "Drop Precedence Level,
                 if a frame matches the QCE then DP level will set to value displayed under DPL column.
                 -1: default
                 0, 1: DPL0 and DPL1"
            DEFVAL      { -1 }
            ::= { ctcPortsQclStatusEntry 7 }
                  
        -- 1.3.6.1.4.1.4756.104.50.10.1.8    
        ctcQclActionDSCP OBJECT-TYPE
            SYNTAX      Integer32 (-1 | 0..63)
            MAX-ACCESS  read-only
            STATUS      current
            DESCRIPTION
                "If a frame matches the QCE then DSCP will be classified with the value displayed under DSCP column.
                 -1: default
                 0 to 63: DSCP0 to DSCP63"
            DEFVAL      { -1 }
            ::= { ctcPortsQclStatusEntry 8 }
                  
        -- 1.3.6.1.4.1.4756.104.50.10.1.9    
        ctcQclConflict OBJECT-TYPE
            SYNTAX      TruthValue
            MAX-ACCESS  read-only
            STATUS      current
            DESCRIPTION
                "Displays QCE status. It may happen that resources required to add a QCE may not available."
            ::= { ctcPortsQclStatusEntry 9 }


-- Security
    -- 1.3.6.1.4.1.4756.104.60
    ctcSecurity OBJECT IDENTIFIER ::= { gsw2008ms 60 }

    -- 1.3.6.1.4.1.4756.104.60.1
    ctcSecuritySwitch OBJECT IDENTIFIER ::= { ctcSecurity 1 }

    -- 1.3.6.1.4.1.4756.104.60.1.1    
    ctcAddUser OBJECT-TYPE
        SYNTAX      OCTET STRING (SIZE (1..32))
        MAX-ACCESS  read-write
        STATUS      current
        DESCRIPTION
            "A string identifying the user name that this entry should belong to.
             The allowed string length is 1 to 32.
             The valid user name is a combination of letters, numbers and underscores."
        ::= { ctcSecuritySwitch 1 }

    -- 1.3.6.1.4.1.4756.104.60.1.2    
    ctcDeleteUser OBJECT-TYPE
        SYNTAX      OCTET STRING (SIZE (1..32))
        MAX-ACCESS  read-write
        STATUS      current
        DESCRIPTION
            "Delete the user by name."
        ::= { ctcSecuritySwitch 2 }

    -- 1.3.6.1.4.1.4756.104.60.1.3
    ctcUserConfigTable OBJECT-TYPE
        SYNTAX      SEQUENCE OF CtcUserConfigEntry
        MAX-ACCESS  not-accessible
        STATUS      current
        DESCRIPTION
            "This table provides User Configurations."
        ::= { ctcSecuritySwitch 3 }

    -- 1.3.6.1.4.1.4756.104.60.1.3.1
    ctcUserConfigEntry OBJECT-TYPE
        SYNTAX      CtcUserConfigEntry
        MAX-ACCESS  not-accessible
        STATUS      current
        DESCRIPTION
            "The Entry of User Configurations."
        INDEX { ctcUserIndex }
        ::= { ctcUserConfigTable 1 }

    CtcUserConfigEntry ::=
        SEQUENCE {
            ctcUserIndex             Integer32,
            ctcUserName              OCTET STRING,
            ctcUserPassword          OCTET STRING,
            ctcUserPrivilegeLevel    Integer32
        }

        -- 1.3.6.1.4.1.4756.104.60.1.3.1.1
        ctcUserIndex OBJECT-TYPE
            SYNTAX      Integer32 (1..20)
            MAX-ACCESS  read-only
            STATUS      current
            DESCRIPTION
                "The index of user entries."
            ::= { ctcUserConfigEntry 1 }

        -- 1.3.6.1.4.1.4756.104.60.1.3.1.2
        ctcUserName OBJECT-TYPE
            SYNTAX      OCTET STRING (SIZE (1..32))
            MAX-ACCESS  read-only
            STATUS      current
            DESCRIPTION
                "The name identifying the user."
            ::= { ctcUserConfigEntry 2 }

        -- 1.3.6.1.4.1.4756.104.60.1.3.1.3
        ctcUserPassword OBJECT-TYPE
            SYNTAX      OCTET STRING (SIZE (0..32))
            MAX-ACCESS  read-write
            STATUS      current
            DESCRIPTION
                "The password of the user. The allowed string length is 0 to 32."
            ::= { ctcUserConfigEntry 3 }

        -- 1.3.6.1.4.1.4756.104.60.1.3.1.4
        ctcUserPrivilegeLevel OBJECT-TYPE
            SYNTAX      Integer32 (1..15)
            MAX-ACCESS  read-write
            STATUS      current
            DESCRIPTION
                "The privilege level of the user. The allowed range is 1 to 15.
                 If the privilege level value is 15, it can access all groups,
                 i.e. that is granted the fully control of the device.
                 But others value need to refer to each group privilege level.
                 User's privilege should be same or greater than the group privilege level to have the access of that group.
                 By default setting, most groups privilege level 5 has the read-only access
                 and privilege level 10 has the read-write access. And the system maintenance
                 (software upload, factory defaults and etc.) need user privilege level 15.
                 Generally, the privilege level 15 can be used for an administrator account,
                 privilege level 10 for a standard user account and privilege level 5 for a guest account."
            ::= { ctcUserConfigEntry 4 }

    -- 1.3.6.1.4.1.4756.104.60.1.4
    ctcPrivilegeLevelTable OBJECT-TYPE
        SYNTAX      SEQUENCE OF CtcPrivilegeLevelEntry
        MAX-ACCESS  not-accessible
        STATUS      current
        DESCRIPTION
            "This table provides privilege levels configurations."
        ::= { ctcSecuritySwitch 4 }

    -- 1.3.6.1.4.1.4756.104.60.1.4.1
    ctcPrivilegeLevelEntry OBJECT-TYPE
        SYNTAX      CtcPrivilegeLevelEntry
        MAX-ACCESS  not-accessible
        STATUS      current
        DESCRIPTION
            "The entry of privilege groups."
        INDEX { ctcPrivilegeGroupID }
        ::= { ctcPrivilegeLevelTable 1 }

    CtcPrivilegeLevelEntry ::=
        SEQUENCE {
            ctcPrivilegeGroupID                  Integer32,
            ctcPrivilegeGroupName                DisplayString,
            ctcPrivilegeConfigReadOnlyLevel      Integer32,
            ctcPrivilegeConfigReadWriteLevel     Integer32,
            ctcPrivilegeStatusReadOnlyLevel      Integer32,
            ctcPrivilegeStatusReadWriteLevel     Integer32
        }

        -- 1.3.6.1.4.1.4756.104.60.1.4.1.1
        ctcPrivilegeGroupID OBJECT-TYPE
            SYNTAX      Integer32 (1..26)
            MAX-ACCESS  read-only
            STATUS      current
            DESCRIPTION
                "The ID of privilege groups."
            ::= { ctcPrivilegeLevelEntry 1 }

        -- 1.3.6.1.4.1.4756.104.60.1.4.1.2
        ctcPrivilegeGroupName OBJECT-TYPE
            SYNTAX      DisplayString
            MAX-ACCESS  read-only
            STATUS      current
            DESCRIPTION
                "The name identifying the privilege group. In most cases,
                 a privilege level group consists of a single module (e.g. Ports, VLANs or QoS),
                 but a few of them contains more than one."
            ::= { ctcPrivilegeLevelEntry 2 }

        -- 1.3.6.1.4.1.4756.104.60.1.4.1.3
        ctcPrivilegeConfigReadOnlyLevel OBJECT-TYPE
            SYNTAX      Integer32 (1..15)
            MAX-ACCESS  read-write
            STATUS      current
            DESCRIPTION
                "The authorization privilege level for configuration read-only of the group.
                 The privilege level of 'Read-only' should be less or equal 'Read/write'."
            ::= { ctcPrivilegeLevelEntry 3 }

        -- 1.3.6.1.4.1.4756.104.60.1.4.1.4
        ctcPrivilegeConfigReadWriteLevel OBJECT-TYPE
            SYNTAX      Integer32 (1..15)
            MAX-ACCESS  read-write
            STATUS      current
            DESCRIPTION
                "The authorization privilege level for configuration/execute read-write of the group.
                 The privilege level of 'Configuration/Execute Read/write'
                 should be great or equal 'Status/Statistics Read-only'"
            ::= { ctcPrivilegeLevelEntry 4 }

        -- 1.3.6.1.4.1.4756.104.60.1.4.1.5
        ctcPrivilegeStatusReadOnlyLevel OBJECT-TYPE
            SYNTAX      Integer32 (1..15)
            MAX-ACCESS  read-write
            STATUS      current
            DESCRIPTION
                "The authorization privilege level for status/statistics read-only of the group.
                 The privilege level of 'Read-only' should be less or equal 'Read/write'."
            ::= { ctcPrivilegeLevelEntry 5 }

        -- 1.3.6.1.4.1.4756.104.60.1.4.1.6
        ctcPrivilegeStatusReadWriteLevel OBJECT-TYPE
            SYNTAX      Integer32 (1..15)
            MAX-ACCESS  read-write
            STATUS      current
            DESCRIPTION
                "The authorization privilege level for status/statistics read-write
                 (e.g. for clearing of statistics) of the group."
            ::= { ctcPrivilegeLevelEntry 6 }

    -- 1.3.6.1.4.1.4756.104.60.1.5
    ctcAuthenticationMethodTable OBJECT-TYPE
        SYNTAX      SEQUENCE OF CtcAuthenticationMethodEntry
        MAX-ACCESS  not-accessible
        STATUS      current
        DESCRIPTION
            "This table allows you to configure how a user is authenticated when
             he logs into the switch via one of the management client interfaces."
        ::= { ctcSecuritySwitch 5 }

    -- 1.3.6.1.4.1.4756.104.60.1.5.1
    ctcAuthenticationMethodEntry OBJECT-TYPE
        SYNTAX      CtcAuthenticationMethodEntry
        MAX-ACCESS  not-accessible
        STATUS      current
        DESCRIPTION
            "The entry of the management client interfaces."
        INDEX { ctcAuthenticationClientIndex }
        ::= { ctcAuthenticationMethodTable 1 }

    CtcAuthenticationMethodEntry ::=
        SEQUENCE {
            ctcAuthenticationClientIndex         Integer32,
            ctcAuthenticationClientInterface     DisplayString,
            ctcAuthenticationMethod              INTEGER,
            ctcAuthenticationFallbackEnable      TruthValue
        }

        -- 1.3.6.1.4.1.4756.104.60.1.5.1.1
        ctcAuthenticationClientIndex OBJECT-TYPE
            SYNTAX      Integer32 (1..4)
            MAX-ACCESS  read-only
            STATUS      current
            DESCRIPTION
                "The index of the management client interfaces."
            ::= { ctcAuthenticationMethodEntry 1 }

        -- 1.3.6.1.4.1.4756.104.60.1.5.1.2
        ctcAuthenticationClientInterface OBJECT-TYPE
            SYNTAX      DisplayString
            MAX-ACCESS  read-only
            STATUS      current
            DESCRIPTION
                "The management client interface."
            ::= { ctcAuthenticationMethodEntry 2 }

        -- 1.3.6.1.4.1.4756.104.60.1.5.1.3
        ctcAuthenticationMethod OBJECT-TYPE
            SYNTAX      INTEGER {
                            none(1),
                            local(2),
                            radius(3),
                            tacacsPlus(4)
                        }
            MAX-ACCESS  read-write
            STATUS      current
            DESCRIPTION
                "Authentication Method can be set to one of the following values:
                 none : authentication is disabled and login is not possible.
                 local : use the local user database on the switch for authentication.
                 radius : use a remote RADIUS server for authentication.
                 tacacs+ : use a remote TACACS+ server for authentication."
            ::= { ctcAuthenticationMethodEntry 3 }

        -- 1.3.6.1.4.1.4756.104.60.1.5.1.4
        ctcAuthenticationFallbackEnable OBJECT-TYPE
            SYNTAX      TruthValue
            MAX-ACCESS  read-write
            STATUS      current
            DESCRIPTION
                "Enable fallback to local authentication.
                 If none of the configured authentication servers are alive,
                 the local user database is used for authentication.
                 This is only possible if the Authentication Method is set to a value other than 'none' or 'local'."
            ::= { ctcAuthenticationMethodEntry 4 }

    -- 1.3.6.1.4.1.4756.104.60.1.6    
    ctcSshMode OBJECT-TYPE
        SYNTAX      INTEGER {
                        enabled(1),
                        disabled(2)
                    }
        MAX-ACCESS  read-write
        STATUS      current
        DESCRIPTION
            "Indicates the SSH mode operation. Possible modes are: 
             Enabled: Enable SSH mode operation. 
             Disabled: Disable SSH mode operation."
        ::= { ctcSecuritySwitch 6 }

    -- 1.3.6.1.4.1.4756.104.60.1.7    
    ctcHttpsMode OBJECT-TYPE
        SYNTAX      INTEGER {
                        enabled(1),
                        disabled(2)
                    }
        MAX-ACCESS  read-write
        STATUS      current
        DESCRIPTION
            "Indicates the HTTPS mode operation. Possible modes are: 
             Enabled: Enable HTTPS mode operation. 
             Disabled: Disable HTTPS mode operation."
        ::= { ctcSecuritySwitch 7 }

    -- 1.3.6.1.4.1.4756.104.60.1.8    
    ctcHttpsAutomaticRedirect OBJECT-TYPE
        SYNTAX      INTEGER {
                        enabled(1),
                        disabled(2)
                    }
        MAX-ACCESS  read-write
        STATUS      current
        DESCRIPTION
            "Indicates the HTTPS redirect mode operation.
             Automatically redirect web browser to HTTPS when HTTPS mode is enabled. Possible modes are: 
             Enabled: Enable HTTPS redirect mode operation. 
             Disabled: Disable HTTPS redirect mode operation."
        ::= { ctcSecuritySwitch 8 }

    -- 1.3.6.1.4.1.4756.104.60.1.9
    ctcAccessManagement OBJECT IDENTIFIER ::= { ctcSecuritySwitch 9 }

    -- 1.3.6.1.4.1.4756.104.60.1.9.1    
    ctcAccessMgmtProtocolMode OBJECT-TYPE
        SYNTAX      INTEGER {
                        enabled(1),
                        disabled(2)
                    }
        MAX-ACCESS  read-write
        STATUS      current
        DESCRIPTION
            "Indicates the access management protocol mode operation. Possible modes are: 
             Enabled: Enable access management protocol mode operation,
                      and there must at least one entry provide SNMP service. 
             Disabled: Disable access management protocol mode operation."
        ::= { ctcAccessManagement 1 }

    -- 1.3.6.1.4.1.4756.104.60.1.9.2    
    ctcAddAccessMgmtProtocol OBJECT-TYPE
        SYNTAX      Integer32 (0 | 1..16)
        MAX-ACCESS  read-write
        STATUS      current
        DESCRIPTION
            "Add a new access management entry: 
             Value 0: Add entry by the first valid ID of list. 
             Value 1~16: Insert new entry by this ID."
        ::= { ctcAccessManagement 2 }

    -- 1.3.6.1.4.1.4756.104.60.1.9.3    
    ctcDeleteAccessMgmtProtocol OBJECT-TYPE
        SYNTAX      Integer32 (1..16)
        MAX-ACCESS  read-write
        STATUS      current
        DESCRIPTION
            "Delete entry by given ID."
        ::= { ctcAccessManagement 3 }

    -- 1.3.6.1.4.1.4756.104.60.1.9.4
    ctcAccessMgmtProtocolTable OBJECT-TYPE
        SYNTAX      SEQUENCE OF CtcAccessMgmtProtocolEntry
        MAX-ACCESS  not-accessible
        STATUS      current
        DESCRIPTION
            "Configure access management protocol on this table."
        ::= { ctcAccessManagement 4 }

    -- 1.3.6.1.4.1.4756.104.60.1.9.4.1
    ctcAccessMgmtProtocolEntry OBJECT-TYPE
        SYNTAX      CtcAccessMgmtProtocolEntry
        MAX-ACCESS  not-accessible
        STATUS      current
        DESCRIPTION
            "The entry of the access management protocol table."
        INDEX { ctcAccessMgmtID }
        ::= { ctcAccessMgmtProtocolTable 1 }

    CtcAccessMgmtProtocolEntry ::=
        SEQUENCE {
            ctcAccessMgmtID                  Integer32,
            ctcAccessMgmtProtocolStartIP     DisplayString,
            ctcAccessMgmtProtocolEndIP       DisplayString,
            ctcAccessMgmtHttpHttpsEnable     TruthValue,
            ctcAccessMgmtSnmpEnable          TruthValue,
            ctcAccessMgmtTelnetSshEnable     TruthValue
        }

        -- 1.3.6.1.4.1.4756.104.60.1.9.4.1.1
        ctcAccessMgmtID OBJECT-TYPE
            SYNTAX      Integer32 (1..16)
            MAX-ACCESS  read-only
            STATUS      current
            DESCRIPTION
                "The Id of the access management entry."
            ::= { ctcAccessMgmtProtocolEntry 1 }

        -- 1.3.6.1.4.1.4756.104.60.1.9.4.1.2
        ctcAccessMgmtProtocolStartIP OBJECT-TYPE
            SYNTAX      DisplayString
            MAX-ACCESS  read-write
            STATUS      current
            DESCRIPTION
                "Indicates the start IP address for the access management entry.
                 It must either be a valid IPv4 or IPv6 address.
                 IPv4 address is in dotted decimal notation ('x.y.z.w').
                 IPv6 address is in 128-bit records represented as eight fields of up to
                 four hexadecimal digits with a colon separating each field (:)."
            ::= { ctcAccessMgmtProtocolEntry 2 }

        -- 1.3.6.1.4.1.4756.104.60.1.9.4.1.3
        ctcAccessMgmtProtocolEndIP OBJECT-TYPE
            SYNTAX      DisplayString
            MAX-ACCESS  read-write
            STATUS      current
            DESCRIPTION
                "Indicates the end IP address for the access management entry..
                 It must either be a valid IPv4 or IPv6 address.
                 IPv4 address is in dotted decimal notation ('x.y.z.w').
                 IPv6 address is in 128-bit records represented as eight fields of up to
                 four hexadecimal digits with a colon separating each field (:)."
            ::= { ctcAccessMgmtProtocolEntry 3 }

        -- 1.3.6.1.4.1.4756.104.60.1.9.4.1.4
        ctcAccessMgmtHttpHttpsEnable OBJECT-TYPE
            SYNTAX      TruthValue
            MAX-ACCESS  read-write
            STATUS      current
            DESCRIPTION
                "Indicates that the host can access the switch from HTTP/HTTPS interface if
                 the host IP address matches the IP address range provided in the entry."
            ::= { ctcAccessMgmtProtocolEntry 4 }

        -- 1.3.6.1.4.1.4756.104.60.1.9.4.1.5
        ctcAccessMgmtSnmpEnable OBJECT-TYPE
            SYNTAX      TruthValue
            MAX-ACCESS  read-write
            STATUS      current
            DESCRIPTION
                "Indicates that the host can access the switch from SNMP interface if
                 the host IP address matches the IP address range provided in the entry."
            ::= { ctcAccessMgmtProtocolEntry 5 }

        -- 1.3.6.1.4.1.4756.104.60.1.9.4.1.6
        ctcAccessMgmtTelnetSshEnable OBJECT-TYPE
            SYNTAX      TruthValue
            MAX-ACCESS  read-write
            STATUS      current
            DESCRIPTION
                "Indicates that the host can access the switch from TELNET/SSH interface if
                 the host IP address matches the IP address range provided in the entry."
            ::= { ctcAccessMgmtProtocolEntry 6 }

    -- 1.3.6.1.4.1.4756.104.60.1.9.5    
    ctcAccessMgmtPortsMode OBJECT-TYPE
        SYNTAX      INTEGER {
                        enabled(1),
                        disabled(2)
                    }
        MAX-ACCESS  read-write
        STATUS      current
        DESCRIPTION
            "Indicates the access management ports mode operation. Possible modes are: 
             Enabled: Enable access management ports mode operation,
                      and there must at least one port was allowed port. 
             Disabled: Disable access management ports mode operation."
        ::= { ctcAccessManagement 5 }

    -- 1.3.6.1.4.1.4756.104.60.1.9.6
    ctcAccessMgmtPortsTable OBJECT-TYPE
        SYNTAX      SEQUENCE OF CtcAccessMgmtPortsEntry
        MAX-ACCESS  not-accessible
        STATUS      current
        DESCRIPTION
            "Configure access management protocol on this table."
        ::= { ctcAccessManagement 6 }

    -- 1.3.6.1.4.1.4756.104.60.1.9.6.1
    ctcAccessMgmtPortsEntry OBJECT-TYPE
        SYNTAX      CtcAccessMgmtPortsEntry
        MAX-ACCESS  not-accessible
        STATUS      current
        DESCRIPTION
            "The entry of the access management protocol table."
        INDEX { ctcPortIndex }
        ::= { ctcAccessMgmtPortsTable 1 }

    CtcAccessMgmtPortsEntry ::=
        SEQUENCE {
            ctcAccessMgmtPortAllowed   TruthValue
        }

        -- 1.3.6.1.4.1.4756.104.60.1.9.6.1.1
        ctcAccessMgmtPortAllowed OBJECT-TYPE
            SYNTAX      TruthValue
            MAX-ACCESS  read-write
            STATUS      current
            DESCRIPTION
                "Indicates that the host can access the switch from this port."
            ::= { ctcAccessMgmtPortsEntry 1 }

    -- 1.3.6.1.4.1.4756.104.60.1.9.7
    ctcAccessMgmtStatisticsClear OBJECT-TYPE
        SYNTAX      INTEGER {
                        trigger(1),
                        normal(2)
                    }
        MAX-ACCESS  read-write
        STATUS      current
        DESCRIPTION
            "Clear all Access Management statistics"
        ::= { ctcAccessManagement 7 }

    -- 1.3.6.1.4.1.4756.104.60.1.9.8
    ctcAccessMgmtStatisticsTable OBJECT-TYPE
        SYNTAX      SEQUENCE OF CtcAccessMgmtStatisticsEntry
        MAX-ACCESS  not-accessible
        STATUS      current
        DESCRIPTION
            "Configure access management protocol on this table."
        ::= { ctcAccessManagement 8 }

    -- 1.3.6.1.4.1.4756.104.60.1.9.8.1
    ctcAccessMgmtStatisticsEntry OBJECT-TYPE
        SYNTAX      CtcAccessMgmtStatisticsEntry
        MAX-ACCESS  not-accessible
        STATUS      current
        DESCRIPTION
            "The entry of the access management protocol table."
        INDEX { ctcAccessMgmtInterfaceIndex }
        ::= { ctcAccessMgmtStatisticsTable 1 }

    CtcAccessMgmtStatisticsEntry ::=
        SEQUENCE {
            ctcAccessMgmtInterfaceIndex      Integer32,
            ctcAccessMgmtInterface           DisplayString,
            ctcAccessMgmtReceivedPackets     Counter32,
            ctcAccessMgmtAllowedPackets      Counter32,
            ctcAccessMgmtDiscardedPackets    Counter32
        }

        -- 1.3.6.1.4.1.4756.104.60.1.9.8.1.1
        ctcAccessMgmtInterfaceIndex OBJECT-TYPE
            SYNTAX      Integer32 (1..5)
            MAX-ACCESS  read-only
            STATUS      current
            DESCRIPTION
                "The Id of the access management entry."
            ::= { ctcAccessMgmtStatisticsEntry 1 }

        -- 1.3.6.1.4.1.4756.104.60.1.9.8.1.2
        ctcAccessMgmtInterface OBJECT-TYPE
            SYNTAX      DisplayString
            MAX-ACCESS  read-only
            STATUS      current
            DESCRIPTION
                "The Id of the access management entry."
            ::= { ctcAccessMgmtStatisticsEntry 2 }

        -- 1.3.6.1.4.1.4756.104.60.1.9.8.1.3
        ctcAccessMgmtReceivedPackets OBJECT-TYPE
            SYNTAX      Counter32
            MAX-ACCESS  read-only
            STATUS      current
            DESCRIPTION
                "The Id of the access management entry."
            ::= { ctcAccessMgmtStatisticsEntry 3 }

        -- 1.3.6.1.4.1.4756.104.60.1.9.8.1.4
        ctcAccessMgmtAllowedPackets OBJECT-TYPE
            SYNTAX      Counter32
            MAX-ACCESS  read-only
            STATUS      current
            DESCRIPTION
                "The Id of the access management entry."
            ::= { ctcAccessMgmtStatisticsEntry 4 }

        -- 1.3.6.1.4.1.4756.104.60.1.9.8.1.5
        ctcAccessMgmtDiscardedPackets OBJECT-TYPE
            SYNTAX      Counter32
            MAX-ACCESS  read-only
            STATUS      current
            DESCRIPTION
                "The Id of the access management entry."
            ::= { ctcAccessMgmtStatisticsEntry 5 }

    
    -- 1.3.6.1.4.1.4756.104.60.2
    ctcSecurityNetwork OBJECT IDENTIFIER ::= { ctcSecurity 2 }
    
    -- 1.3.6.1.4.1.4756.104.60.2.1
    ctcPortSecurity OBJECT IDENTIFIER ::= { ctcSecurityNetwork 1 }

    -- 1.3.6.1.4.1.4756.104.60.2.1.1    
    ctcPsecLimitControlMode OBJECT-TYPE
        SYNTAX      INTEGER {
                        enabled(1),
                        disabled(2)
                    }
        MAX-ACCESS  read-write
        STATUS      current
        DESCRIPTION
            "Indicates if Limit Control is globally enabled or disabled on the switch."
        ::= { ctcPortSecurity 1 }

    -- 1.3.6.1.4.1.4756.104.60.2.1.2    
    ctcPsecLimitControlAgingEnabled OBJECT-TYPE
        SYNTAX      TruthValue
        MAX-ACCESS  read-write
        STATUS      current
        DESCRIPTION
            "If enabled, secured MAC addresses are subject to aging as discussed under Aging Period."
        ::= { ctcPortSecurity 2 }

    -- 1.3.6.1.4.1.4756.104.60.2.1.3    
    ctcPsecLimitControlAgingPeriod OBJECT-TYPE
        SYNTAX      Integer32 (10..10000000)
        UNITS       "Seconds"
        MAX-ACCESS  read-write
        STATUS      current
        DESCRIPTION
            "If 'Aging' is Enabled, then the aging period is controlled with this value."
        ::= { ctcPortSecurity 3 }

    -- 1.3.6.1.4.1.4756.104.60.2.1.4
    ctcPsecLimitControlPortConfigTable OBJECT-TYPE
        SYNTAX      SEQUENCE OF CtcPsecLimitControlPortConfigEntry
        MAX-ACCESS  not-accessible
        STATUS      current
        DESCRIPTION
            "This table provides Port Security Limit Control Configurations."
        ::= { ctcPortSecurity 4 }

    -- 1.3.6.1.4.1.4756.104.60.2.1.4.1
    ctcPsecLimitControlPortConfigEntry OBJECT-TYPE
        SYNTAX      CtcPsecLimitControlPortConfigEntry
        MAX-ACCESS  not-accessible
        STATUS      current
        DESCRIPTION
            "The Entry of Port Security Limit Control Configurations."
        INDEX { ctcPortIndex }
        ::= { ctcPsecLimitControlPortConfigTable 1 }

    CtcPsecLimitControlPortConfigEntry ::=
        SEQUENCE {
            ctcPsecLimitControlPortMode      INTEGER,
            ctcPsecLimitControlMacLimit      Integer32,
            ctcPsecLimitControlAction        INTEGER,
            ctcPsecLimitControlPortReopen    INTEGER
        }

        -- 1.3.6.1.4.1.4756.104.60.2.1.4.1.1
        ctcPsecLimitControlPortMode OBJECT-TYPE
            SYNTAX      INTEGER {
                            enable(1),
                            disable(2)
                        }
            MAX-ACCESS  read-write
            STATUS      current
            DESCRIPTION
                "Controls whether Limit Control is enabled on this port.
                 Both this and the Global Mode must be set to Enabled for Limit Control to be in effect.
                 Notice that other modules may still use the underlying port security features
                 without enabling Limit Control on a given port."
            ::= { ctcPsecLimitControlPortConfigEntry 1 }

        -- 1.3.6.1.4.1.4756.104.60.2.1.4.1.2
        ctcPsecLimitControlMacLimit OBJECT-TYPE
            SYNTAX      Integer32 (1..1024)
            MAX-ACCESS  read-write
            STATUS      current
            DESCRIPTION
                "The maximum number of MAC addresses that can be secured on this port.
                 This number cannot exceed 1024.
                 If the limit is exceeded, the corresponding action is taken.
                 The switch is 'born' with a total number of MAC addresses from which all ports draw
                 whenever a new MAC address is seen on a Port Security-enabled port.
                 Since all ports draw from the same pool,
                 it may happen that a configured maximum cannot be granted,
                 if the remaining ports have already used all available MAC addresses."
            ::= { ctcPsecLimitControlPortConfigEntry 2 }

        -- 1.3.6.1.4.1.4756.104.60.2.1.4.1.3
        ctcPsecLimitControlAction OBJECT-TYPE
            SYNTAX      INTEGER {
                            none(1),
                            trap(2),
                            shutdown(3),
                            trapAndShutdown(4)
                        }
            MAX-ACCESS  read-write
            STATUS      current
            DESCRIPTION
                "If Limit is reached, the switch can take one of the following actions:
                 None: Do not allow more than Limit MAC addresses on the port,
                       but take no further action.
                 Trap: If Limit + 1 MAC addresses is seen on the port,
                       send an SNMP trap. If Aging is disabled,
                       only one SNMP trap will be sent, but with Aging enabled,
                       new SNMP traps will be sent everytime the limit gets exceeded.
                 Shutdown: If Limit + 1 MAC addresses is seen on the port, shut down the port.
                           This implies that all secured MAC addresses will be removed from the port,
                           and no new address will be learned.
                           Even if the link is physically disconnected and reconnected on the port
                           (by disconnecting the cable), the port will remain shut down.
                           There are three ways to re-open the port:
                           1) Boot the switch,
                           2) Disable and re-enable Limit Control on the port or the switch,
                           3) Trigger Reopen node.
                 Trap & Shutdown: If Limit + 1 MAC addresses is seen on the port, both the 'Trap' and
                                  the 'Shutdown' actions described above will be taken."
            ::= { ctcPsecLimitControlPortConfigEntry 3 }

        -- 1.3.6.1.4.1.4756.104.60.2.1.4.1.4
        ctcPsecLimitControlPortReopen OBJECT-TYPE
            SYNTAX      INTEGER {
                            trigger(1),
                            normal(2)
                        }
            MAX-ACCESS  read-write
            STATUS      current
            DESCRIPTION
                "If a port is shutdown by this module, you may reopen it by triggering this node."
            ::= { ctcPsecLimitControlPortConfigEntry 4 }

    -- 1.3.6.1.4.1.4756.104.60.2.1.5
    ctcPsecSwitchStatusTable OBJECT-TYPE
        SYNTAX      SEQUENCE OF CtcPsecSwitchStatusEntry
        MAX-ACCESS  not-accessible
        STATUS      current
        DESCRIPTION
            "This table provides Port Security Limit Control Switch Status."
        ::= { ctcPortSecurity 5 }

    -- 1.3.6.1.4.1.4756.104.60.2.1.5.1
    ctcPsecSwitchStatusEntry OBJECT-TYPE
        SYNTAX      CtcPsecSwitchStatusEntry
        MAX-ACCESS  not-accessible
        STATUS      current
        DESCRIPTION
            "The Entry of Port Security Limit Control Switch Status."
        INDEX { ctcPortIndex }
        ::= { ctcPsecSwitchStatusTable 1 }

    CtcPsecSwitchStatusEntry ::=
        SEQUENCE {
            ctcPsecSwitchStatusPortUsers     DisplayString,
            ctcPsecSwitchStatusPortState     INTEGER,
            ctcPsecSwitchStatusMacCount      Integer32
        }

        -- 1.3.6.1.4.1.4756.104.60.2.1.5.1.1
        ctcPsecSwitchStatusPortUsers OBJECT-TYPE
            SYNTAX      DisplayString
            MAX-ACCESS  read-only
            STATUS      current
            DESCRIPTION
                "Each of the user modules has a column that shows whether that module has enabled
                 Port Security or not. A '-' means that the corresponding user module is not enabled,
                 whereas a letter indicates that the user module abbreviated by that letter (see below)
                 has enabled port security.
                 Limit Control: L
                 802.1X       : 8
                 DHCP Snooping: D
                 Voice VLAN   : V "
            ::= { ctcPsecSwitchStatusEntry 1 }

        -- 1.3.6.1.4.1.4756.104.60.2.1.5.1.2
        ctcPsecSwitchStatusPortState OBJECT-TYPE
            SYNTAX      INTEGER {
                            disabled(1),
                            ready(2),
                            limitReached(3),
                            shutdown(4)
                        }
            MAX-ACCESS  read-only
            STATUS      current
            DESCRIPTION
                "This node shows the current state of the port.
                 The state takes one of four values:
                 Disabled: Limit Control is either globally disabled or disabled on the port.
                 Ready: The limit is not yet reached. This can be shown for all actions.
                 Limit Reached: Indicates that the limit is reached on this port.
                                This state can only be shown if Action is set to None or Trap.
                 Shutdown: Indicates that the port is shut down by the Limit Control module.
                           This state can only be shown if Action is set to Shutdown or Trap & Shutdown."
            ::= { ctcPsecSwitchStatusEntry 2 }

        -- 1.3.6.1.4.1.4756.104.60.2.1.5.1.3
        ctcPsecSwitchStatusMacCount OBJECT-TYPE
            SYNTAX      Integer32 (-1 | 0..1024) 
            MAX-ACCESS  read-only
            STATUS      current
            DESCRIPTION
                "This indicate the number of currently learned MAC addresses(forwarding as well as blocked)
                 If no user modules are enabled on the port, the Current Count will show a value(-1)."
            ::= { ctcPsecSwitchStatusEntry 3 }

    -- 1.3.6.1.4.1.4756.104.60.2.1.6
    ctcPsecPortStatusTable OBJECT-TYPE
        SYNTAX      SEQUENCE OF CtcPsecPortStatusEntry
        MAX-ACCESS  not-accessible
        STATUS      current
        DESCRIPTION
            "This table provides Port Security Port Status."
        ::= { ctcPortSecurity 6 }

    -- 1.3.6.1.4.1.4756.104.60.2.1.6.1
    ctcPsecPortStatusEntry OBJECT-TYPE
        SYNTAX      CtcPsecPortStatusEntry
        MAX-ACCESS  not-accessible
        STATUS      current
        DESCRIPTION
            "The Entry of Port Security Port Status."
        INDEX { ctcPortIndex, ctcPsecMacIndex }
        ::= { ctcPsecPortStatusTable 1 }

    CtcPsecPortStatusEntry ::=
        SEQUENCE {
            ctcPsecMacIndex          Integer32,
            ctcPsecMacAddress        MacAddress,
            ctcPsecMacVlanID         Integer32,
            ctcPsecMacState          INTEGER,
            ctcPsecMacAdditionTime   DisplayString,
            ctcPsecMacAge            Integer32
        }

        -- 1.3.6.1.4.1.4756.104.60.2.1.6.1.1
        ctcPsecMacIndex OBJECT-TYPE
            SYNTAX      Integer32 (1..1024) 
            MAX-ACCESS  read-only
            STATUS      current
            DESCRIPTION
                "The mac address index of the port."
            ::= { ctcPsecPortStatusEntry 1 }

        -- 1.3.6.1.4.1.4756.104.60.2.1.6.1.2
        ctcPsecMacAddress OBJECT-TYPE
            SYNTAX      MacAddress 
            MAX-ACCESS  read-only
            STATUS      current
            DESCRIPTION
                "The MAC address that is seen on this port."
            ::= { ctcPsecPortStatusEntry 2 }

        -- 1.3.6.1.4.1.4756.104.60.2.1.6.1.3
        ctcPsecMacVlanID OBJECT-TYPE
            SYNTAX      Integer32 (1..4095) 
            MAX-ACCESS  read-only
            STATUS      current
            DESCRIPTION
                "The VLAN ID that is seen on this port."
            ::= { ctcPsecPortStatusEntry 3 }

        -- 1.3.6.1.4.1.4756.104.60.2.1.6.1.4
        ctcPsecMacState OBJECT-TYPE
            SYNTAX      INTEGER {
                            blocked(1),
                            forwarding(2)
                        }     
            MAX-ACCESS  read-only
            STATUS      current
            DESCRIPTION
                "Indicates whether the corresponding MAC address is blocked or forwarding.
                 In the blocked state, it will not be allowed to transmit or receive traffic."
            ::= { ctcPsecPortStatusEntry 4 }

        -- 1.3.6.1.4.1.4756.104.60.2.1.6.1.5
        ctcPsecMacAdditionTime OBJECT-TYPE
            SYNTAX      DisplayString     
            MAX-ACCESS  read-only
            STATUS      current
            DESCRIPTION
                "Shows the date and time when this MAC address was first seen on the port."
            ::= { ctcPsecPortStatusEntry 5 }

        -- 1.3.6.1.4.1.4756.104.60.2.1.6.1.6
        ctcPsecMacAge OBJECT-TYPE
            SYNTAX      Integer32 (-1 | 0..1000000)     
            MAX-ACCESS  read-only
            STATUS      current
            DESCRIPTION
                "If at least one user module has decided to block this MAC address,
                 it will stay in the blocked state until the hold time(measured in seconds) expires.
                 If all user modules have decided to allow this MAC address to forward, and aging is enabled,
                 the Port Security module will periodically check that this MAC address still forwards traffic.
                 If the age period (measured in seconds) expires and no frames have been seen,
                 the MAC address will be removed from the MAC table. Otherwise a new age period will begin.
                 If aging is disabled or a user module has decided to hold the MAC address indefinitely,
                 a value (-1) will be shown."
            ::= { ctcPsecPortStatusEntry 6 }
        
                
    -- 1.3.6.1.4.1.4756.104.60.2.2
    ctcNAS OBJECT IDENTIFIER ::= { ctcSecurityNetwork 2 }

    -- 1.3.6.1.4.1.4756.104.60.2.2.1    
    ctcNasMode OBJECT-TYPE
        SYNTAX      INTEGER {
                        enabled(1),
                        disabled(2)
                    }
        MAX-ACCESS  read-write
        STATUS      current
        DESCRIPTION
            "Indicates if NAS is globally enabled or disabled on the switch.
             If globally disabled, all ports are allowed forwarding of frames."
        ::= { ctcNAS 1 }

    -- 1.3.6.1.4.1.4756.104.60.2.2.2    
    ctcNasReauthenticationEnabled OBJECT-TYPE
        SYNTAX      TruthValue
        MAX-ACCESS  read-write
        STATUS      current
        DESCRIPTION
            "If enabled, successfully authenticated supplicants/clients are reauthenticated
             after the interval specified by the Reauthentication Period.
             Reauthentication for 802.1X-enabled ports can be used to detect if a new device
             is plugged into a switch port or if a supplicant is no longer attached. 
             For MAC-based ports, reauthentication is only useful if the RADIUS server configuration has changed.
             It does not involve communication between the switch and the client,
             and therefore doesn't imply that a client is still present on a port."
        ::= { ctcNAS 2 }

    -- 1.3.6.1.4.1.4756.104.60.2.2.3    
    ctcNasReauthenticationPeriod OBJECT-TYPE
        SYNTAX      Integer32 (1..3600)
        UNITS       "Seconds"
        MAX-ACCESS  read-write
        STATUS      current
        DESCRIPTION
            "Determines the period, in seconds,
             after which a connected client must be reauthenticated.
             This is only active if the Reauthentication is Enabled.
             Valid values are in the range 1 to 3600 seconds."
        ::= { ctcNAS 3 }

    -- 1.3.6.1.4.1.4756.104.60.2.2.4    
    ctcNasEapolTimeout OBJECT-TYPE
        SYNTAX      Integer32 (1..65535)
        UNITS       "Seconds"
        MAX-ACCESS  read-write
        STATUS      current
        DESCRIPTION
            "Determines the time for retransmission of Request Identity EAPOL frames.
             Valid values are in the range 1 to 65535 seconds.
             This has no effect for MAC-based ports."
        ::= { ctcNAS 4 }

    -- 1.3.6.1.4.1.4756.104.60.2.2.5    
    ctcNasAgingPeriod OBJECT-TYPE
        SYNTAX      Integer32 (10..1000000)
        UNITS       "Seconds"
        MAX-ACCESS  read-write
        STATUS      current
        DESCRIPTION
            "This setting applies to the following modes,
             i.e. modes using the Port Security functionality to secure MAC addresses:
             Single 802.1X, Multi 802.1X or MAC-Based Auth.
             When the NAS module uses the Port Security module to secure MAC addresses,
             the Port Security module needs to check for activity on the MAC address in question at
             regular intervals and free resources if no activity is seen within a given period of time.
             This parameter controls exactly this period and can be set to a number between 10 and 1000000 seconds.
             If reauthentication is enabled and the port is in an 802.1X-based mode,
             this is not so critical, since supplicants that are no longer attached to
             the port will get removed upon the next reauthentication, which will fail.
             But if reauthentication is not enabled, the only way to free resources is by aging the entries.
             For ports in MAC-based Auth. mode, reauthentication doesn't cause direct communication between
             the switch and the client, so this will not detect whether the client is still attached or not,
             and the only way to free any resources is to age the entry."
        ::= { ctcNAS 5 }

    -- 1.3.6.1.4.1.4756.104.60.2.2.6    
    ctcNasHoldTime OBJECT-TYPE
        SYNTAX      Integer32 (10..1000000)
        UNITS       "Seconds"
        MAX-ACCESS  read-write
        STATUS      current
        DESCRIPTION
            "This setting applies to the following modes,
             i.e. modes using the Port Security functionality to secure MAC addresses:
             Single 802.1X, Multi 802.1X or MAC-Based Auth.
             If a client is denied access - either because the RADIUS server denies the client access or
             because the RADIUS server request times out, the client is put on hold in the Unauthorized state.
             The hold timer does not count during an on-going authentication.
             In MAC-based Auth. mode, the switch will ignore new frames coming from the client during the hold time.
             The Hold Time can be set to a number between 10 and 1000000 seconds."
        ::= { ctcNAS 6 }

    -- 1.3.6.1.4.1.4756.104.60.2.2.7    
    ctcNasRadiusAssignedQosEnabled OBJECT-TYPE
        SYNTAX      TruthValue
        MAX-ACCESS  read-write
        STATUS      current
        DESCRIPTION
            "RADIUS-assigned QoS provides a means to centrally control the traffic class to which traffic
             coming from a successfully authenticated supplicant is assigned on the switch.
             The RADIUS server must be configured to transmit special RADIUS attributes to
             take advantage of this feature."
        ::= { ctcNAS 7 }

    -- 1.3.6.1.4.1.4756.104.60.2.2.8    
    ctcNasRadiusAssignedVlanEnabled OBJECT-TYPE
        SYNTAX      TruthValue
        MAX-ACCESS  read-write
        STATUS      current
        DESCRIPTION
            "RADIUS-assigned VLAN provides a means to centrally control the VLAN on which a
             successfully authenticated supplicant is placed on the switch.
             Incoming traffic will be classified to and switched on the RADIUS-assigned VLAN.
             The RADIUS server must be configured to transmit special RADIUS attributes to
             take advantage of this feature."
        ::= { ctcNAS 8 }

    -- 1.3.6.1.4.1.4756.104.60.2.2.9    
    ctcNasGuestVlanEnabled OBJECT-TYPE
        SYNTAX      TruthValue
        MAX-ACCESS  read-write
        STATUS      current
        DESCRIPTION
            "A Guest VLAN is a special VLAN - typically with limited network access - on which
             802.1X-unaware clients are placed after a network administrator-defined timeout.
             The switch follows a set of rules for entering and leaving the Guest VLAN."
        ::= { ctcNAS 9 }

    -- 1.3.6.1.4.1.4756.104.60.2.2.10    
    ctcNasGuestVlanID OBJECT-TYPE
        SYNTAX      Integer32 (1..4095)
        MAX-ACCESS  read-write
        STATUS      current
        DESCRIPTION
            "This is the value that a port's Port VLAN ID is set to if a port is moved into the Guest VLAN.
             It is only changeable if the Guest VLAN option is globally enabled.
             Valid values are in the range 1 to 4095."
        ::= { ctcNAS 10 }

    -- 1.3.6.1.4.1.4756.104.60.2.2.11    
    ctcNasMaxReauthenticationCount OBJECT-TYPE
        SYNTAX      Integer32 (1..255)
        MAX-ACCESS  read-write
        STATUS      current
        DESCRIPTION
            "The number of times the switch transmits an EAPOL Request Identity frame without response
             before considering entering the Guest VLAN is adjusted with this setting.
             The value can only be changed if the Guest VLAN option is globally enabled.
             Valid values are in the range 1 to 255."
        ::= { ctcNAS 11 }

    -- 1.3.6.1.4.1.4756.104.60.2.2.12    
    ctcNasAllowGuestVlanIfEapolSeen OBJECT-TYPE
        SYNTAX      TruthValue
        MAX-ACCESS  read-write
        STATUS      current
        DESCRIPTION
            "The switch remembers if an EAPOL frame has been received on the port for the life-time
             of the port. Once the switch considers whether to enter the Guest VLAN,
             it will first check if this option is enabled or disabled.
             If disabled, the switch will only enter the Guest VLAN if an EAPOL frame has not been
             received on the port for the life-time of the port.
             If enabled, the switch will consider entering the Guest VLAN even if an EAPOL frame has
             been received on the port for the life-time of the port."
        ::= { ctcNAS 12 }

    -- 1.3.6.1.4.1.4756.104.60.2.2.13
    ctcNasPortConfigTable OBJECT-TYPE
        SYNTAX      SEQUENCE OF CtcNasPortConfigEntry
        MAX-ACCESS  not-accessible
        STATUS      current
        DESCRIPTION
            "This table provides Network Access Server Port Configurations."
        ::= { ctcNAS 13 }

    -- 1.3.6.1.4.1.4756.104.60.2.2.13.1
    ctcNasPortConfigEntry OBJECT-TYPE
        SYNTAX      CtcNasPortConfigEntry
        MAX-ACCESS  not-accessible
        STATUS      current
        DESCRIPTION
            "The Entry of Network Access Server Port Configurations."
        INDEX { ctcPortIndex }
        ::= { ctcNasPortConfigTable 1 }

    CtcNasPortConfigEntry ::=
        SEQUENCE {
            ctcNasPortAdminState                 INTEGER,
            ctcNasPortRadiusAssignedQosEnabled   TruthValue,
            ctcNasPortRadiusAssignedVlanEnabled  TruthValue,
            ctcNasPortGuestVlanEnabled           TruthValue,
            ctcNasPortReauthenticateRestart      INTEGER,
            ctcNasPortReinitializeRestart        INTEGER
        }

        -- 1.3.6.1.4.1.4756.104.60.2.2.13.1.1
        ctcNasPortAdminState OBJECT-TYPE
            SYNTAX      INTEGER {
                            forceAuthorized(1),
                            forceUnauthorized(2),
                            portBased802dot1X(3),
                            single802dot1X(4),
                            multi802dot1X(5),
                            macBasedAuthentication(6)
                        }
            MAX-ACCESS  read-write
            STATUS      current
            DESCRIPTION
                "If NAS is globally enabled, this node controls the port's authentication mode."
            ::= { ctcNasPortConfigEntry 1 }

        -- 1.3.6.1.4.1.4756.104.60.2.2.13.1.2
        ctcNasPortRadiusAssignedQosEnabled OBJECT-TYPE
            SYNTAX      TruthValue
            MAX-ACCESS  read-write
            STATUS      current
            DESCRIPTION
                "When RADIUS-Assigned QoS is both globally enabled and enabled on a given port,
                 the switch reacts to QoS Class information carried in the RADIUS Access-Accept
                 packet transmitted by the RADIUS server when a supplicant is successfully authenticated.
                 If present and valid, traffic received on the supplicant's port will be classified to
                 the given QoS Class. If (re-)authentication fails or the RADIUS Access-Accept packet
                 no longer carries a QoS Class or it's invalid, or the supplicant is otherwise no longer
                 present on the port, the port's QoS Class is immediately reverted to the original QoS Class
                 (which may be changed by the administrator in the meanwhile without affecting the RADIUS-assigned).
                 This option is only available for single-client modes, i.e. Port-based 802.1X or Single 802.1X."
            ::= { ctcNasPortConfigEntry 2 }

        -- 1.3.6.1.4.1.4756.104.60.2.2.13.1.3
        ctcNasPortRadiusAssignedVlanEnabled OBJECT-TYPE
            SYNTAX      TruthValue
            MAX-ACCESS  read-write
            STATUS      current
            DESCRIPTION
                "When RADIUS-Assigned VLAN is both globally enabled and enabled for a given port,
                 the switch reacts to VLAN ID information carried in the RADIUS Access-Accept
                 packet transmitted by the RADIUS server when a supplicant is successfully authenticated.
                 If present and valid, the port's Port VLAN ID will be changed to this VLAN ID,
                 the port will be set to be a member of that VLAN ID, and the port will be forced into
                 VLAN unaware mode. Once assigned, all traffic arriving on the port will be classified and
                 switched on the RADIUS-assigned VLAN ID. If (re-)authentication fails or the RADIUS Access-Accept
                 packet no longer carries a VLAN ID or it's invalid, or the supplicant is otherwise no longer
                 present on the port, the port's VLAN ID is immediately reverted to the original VLAN ID
                 (which may be changed by the administrator in the meanwhile without affecting the RADIUS-assigned).
                 This option is only available for single-client modes, i.e. Port-based 802.1X or Single 802.1X."
            ::= { ctcNasPortConfigEntry 3 }

        -- 1.3.6.1.4.1.4756.104.60.2.2.13.1.4
        ctcNasPortGuestVlanEnabled OBJECT-TYPE
            SYNTAX      TruthValue
            MAX-ACCESS  read-write
            STATUS      current
            DESCRIPTION
                "When Guest VLAN is both globally enabled and enabled for a given port,
                 the switch considers moving the port into the Guest VLAN according to the rules outlined below.
                 This option is only available for EAPOL-based modes, i.e.:
                 Port-based 802.1X, Single 802.1X or Multi 802.1X."
            ::= { ctcNasPortConfigEntry 4 }

        -- 1.3.6.1.4.1.4756.104.60.2.2.13.1.5
        ctcNasPortReauthenticateRestart OBJECT-TYPE
            SYNTAX      INTEGER {
                            trigger(1),
                            normal(2)
                        }
            MAX-ACCESS  read-write
            STATUS      current
            DESCRIPTION
                "Schedules a reauthentication whenever the quiet-period of the port runs out
                 (EAPOL-based authentication). For MAC-based authentication,
                 reauthentication will be attempted immediately.
                 The node is only has effect when authentication is globally enabled and
                 the port's Admin State is in an EAPOL-based or MAC-based mode."
            ::= { ctcNasPortConfigEntry 5 }

        -- 1.3.6.1.4.1.4756.104.60.2.2.13.1.6
        ctcNasPortReinitializeRestart OBJECT-TYPE
            SYNTAX      INTEGER {
                            trigger(1),
                            normal(2)
                        }
            MAX-ACCESS  read-write
            STATUS      current
            DESCRIPTION
                "Forces a reinitialization of the clients on the port and thereby a reauthentication immediately.
                 The clients will transfer to the unauthorized state while the reauthentication is in progress.
                 The node is only has effect when authentication is globally enabled and
                 the port's Admin State is in an EAPOL-based or MAC-based mode."
            ::= { ctcNasPortConfigEntry 6 }

    -- 1.3.6.1.4.1.4756.104.60.2.2.14
    ctcNasSwitchStatusTable OBJECT-TYPE
        SYNTAX      SEQUENCE OF CtcNasSwitchStatusEntry
        MAX-ACCESS  not-accessible
        STATUS      current
        DESCRIPTION
            "This page provides an overview of the current NAS port states."
        ::= { ctcNAS 14 }

    -- 1.3.6.1.4.1.4756.104.60.2.2.14.1
    ctcNasSwitchStatusEntry OBJECT-TYPE
        SYNTAX      CtcNasSwitchStatusEntry
        MAX-ACCESS  not-accessible
        STATUS      current
        DESCRIPTION
            "The Entry of Network Access Server Switch Status."
        INDEX { ctcPortIndex }
        ::= { ctcNasSwitchStatusTable 1 }

    CtcNasSwitchStatusEntry ::=
        SEQUENCE {
            ctcNasSwitchPortAdminState   INTEGER,
            ctcNasSwitchPortState        DisplayString,
            ctcNasSwitchPortLastSource   DisplayString,
            ctcNasSwitchPortLastID       DisplayString,
            ctcNasSwitchPortQosClass     DisplayString,
            ctcNasSwitchPortVlanID       DisplayString
        }

        -- 1.3.6.1.4.1.4756.104.60.2.2.14.1.1
        ctcNasSwitchPortAdminState OBJECT-TYPE
            SYNTAX      INTEGER {
                            forceAuthorized(1),
                            forceUnauthorized(2),
                            portBased802dot1X(3),
                            single802dot1X(4),
                            multi802dot1X(5),
                            macBasedAuthentication(6)
                        }
            MAX-ACCESS  read-only
            STATUS      current
            DESCRIPTION
                "The port's current administrative state."
            ::= { ctcNasSwitchStatusEntry 1 }

        -- 1.3.6.1.4.1.4756.104.60.2.2.14.1.2
        ctcNasSwitchPortState OBJECT-TYPE
            SYNTAX      DisplayString
            MAX-ACCESS  read-only
            STATUS      current
            DESCRIPTION
                "The current state of the port. It can undertake one of the following values:
                 Globally Disabled: NAS is globally disabled.
                 Link Down: NAS is globally enabled, but there is no link on the port.
                 Authorized: The port is in Force Authorized or a single-supplicant mode and
                             the supplicant is authorized.
                 Unauthorized: The port is in Force Unauthorized or a single-supplicant mode and
                               the supplicant is not successfully authorized by the RADIUS server.
                 X Auth/Y Unauth: The port is in a multi-supplicant mode.
                                  Currently X clients are authorized and Y are unauthorized."
            ::= { ctcNasSwitchStatusEntry 2 }

        -- 1.3.6.1.4.1.4756.104.60.2.2.14.1.3
        ctcNasSwitchPortLastSource OBJECT-TYPE
            SYNTAX      DisplayString
            MAX-ACCESS  read-only
            STATUS      current
            DESCRIPTION
                "The source MAC address carried in the most recently received EAPOL frame for
                 EAPOL-based authentication, and the most recently received frame from a
                 new client for MAC-based authentication."
            ::= { ctcNasSwitchStatusEntry 3 }

        -- 1.3.6.1.4.1.4756.104.60.2.2.14.1.4
        ctcNasSwitchPortLastID OBJECT-TYPE
            SYNTAX      DisplayString
            MAX-ACCESS  read-only
            STATUS      current
            DESCRIPTION
                "The user name (supplicant identity) carried in the most recently received
                 Response Identity EAPOL frame for EAPOL-based authentication,
                 and the source MAC address from the most recently received frame from a
                 new client for MAC-based authentication."
            ::= { ctcNasSwitchStatusEntry 4 }

        -- 1.3.6.1.4.1.4756.104.60.2.2.14.1.5
        ctcNasSwitchPortQosClass OBJECT-TYPE
            SYNTAX      DisplayString
            MAX-ACCESS  read-only
            STATUS      current
            DESCRIPTION
                "QoS Class assigned to the port by the RADIUS server if enabled."
            ::= { ctcNasSwitchStatusEntry 5 }

        -- 1.3.6.1.4.1.4756.104.60.2.2.14.1.6
        ctcNasSwitchPortVlanID OBJECT-TYPE
            SYNTAX      DisplayString
            MAX-ACCESS  read-only
            STATUS      current
            DESCRIPTION
                "The VLAN ID that NAS has put the port in.
                 The return string is blank, if the Port VLAN ID is not overridden by NAS."
            ::= { ctcNasSwitchStatusEntry 6 }

    -- 1.3.6.1.4.1.4756.104.60.2.2.15
    ctcNasPortStatisticsTable OBJECT-TYPE
        SYNTAX      SEQUENCE OF CtcNasPortStatisticsEntry
        MAX-ACCESS  not-accessible
        STATUS      current
        DESCRIPTION
            "This page provides an overview of the current NAS port states."
        ::= { ctcNAS 15 }

    -- 1.3.6.1.4.1.4756.104.60.2.2.15.1
    ctcNasPortStatisticsEntry OBJECT-TYPE
        SYNTAX      CtcNasPortStatisticsEntry
        MAX-ACCESS  not-accessible
        STATUS      current
        DESCRIPTION
            "The Entry of Network Access Server Switch Status."
        INDEX { ctcPortIndex }
        ::= { ctcNasPortStatisticsTable 1 }

    CtcNasPortStatisticsEntry ::=
        SEQUENCE {
            ctcNasPortStatisticsClearAll     INTEGER,
            ctcNasRxEapolTotal               Counter32,
            ctcNasRxEapolResponseID          Counter32,
            ctcNasRxEapolResponses           Counter32,
            ctcNasRxEapolStart               Counter32,
            ctcNasRxEapolLogoff              Counter32,
            ctcNasRxEapolInvalidType         Counter32,
            ctcNasRxEapolInvalidLength       Counter32,
            ctcNasTxEapolTotal               Counter32,
            ctcNasTxEapolRequestID           Counter32,
            ctcNasTxEapolRequests            Counter32,
            ctcNasRxBackendAccessChallenges  Counter32,
            ctcNasRxBackendOtherRequests     Counter32,
            ctcNasRxBackendAuthSuccesses     Counter32,
            ctcNasRxBackendAuthFailures      Counter32,
            ctcNasTxBackendResponeses        Counter32
        }

        -- 1.3.6.1.4.1.4756.104.60.2.2.15.1.1
        ctcNasPortStatisticsClearAll OBJECT-TYPE
            SYNTAX      INTEGER {
                            trigger(1),
                            normal(2)
                        }
            MAX-ACCESS  read-write
            STATUS      current
            DESCRIPTION
                "Triggers to clear both the port counters and all of the attached client's counters."
            ::= { ctcNasPortStatisticsEntry 1 }

        -- 1.3.6.1.4.1.4756.104.60.2.2.15.1.2
        ctcNasRxEapolTotal OBJECT-TYPE
            SYNTAX      Counter32
            MAX-ACCESS  read-only
            STATUS      current
            DESCRIPTION
                "The number of valid EAPOL frames of any type that have been received by the switch."
            ::= { ctcNasPortStatisticsEntry 2 }

        -- 1.3.6.1.4.1.4756.104.60.2.2.15.1.3
        ctcNasRxEapolResponseID OBJECT-TYPE
            SYNTAX      Counter32
            MAX-ACCESS  read-only
            STATUS      current
            DESCRIPTION
                "The number of valid EAPOL Response Identity frames that have been received by the switch."
            ::= { ctcNasPortStatisticsEntry 3 }

        -- 1.3.6.1.4.1.4756.104.60.2.2.15.1.4
        ctcNasRxEapolResponses OBJECT-TYPE
            SYNTAX      Counter32
            MAX-ACCESS  read-only
            STATUS      current
            DESCRIPTION
                "The number of valid EAPOL response frames (other than Response Identity frames)
                 that have been received by the switch."
            ::= { ctcNasPortStatisticsEntry 4 }

        -- 1.3.6.1.4.1.4756.104.60.2.2.15.1.5
        ctcNasRxEapolStart OBJECT-TYPE
            SYNTAX      Counter32
            MAX-ACCESS  read-only
            STATUS      current
            DESCRIPTION
                "The number of EAPOL Start frames that have been received by the switch."
            ::= { ctcNasPortStatisticsEntry 5 }

        -- 1.3.6.1.4.1.4756.104.60.2.2.15.1.6
        ctcNasRxEapolLogoff OBJECT-TYPE
            SYNTAX      Counter32
            MAX-ACCESS  read-only
            STATUS      current
            DESCRIPTION
                "The number of valid EAPOL Logoff frames that have been received by the switch."
            ::= { ctcNasPortStatisticsEntry 6 }

        -- 1.3.6.1.4.1.4756.104.60.2.2.15.1.7
        ctcNasRxEapolInvalidType OBJECT-TYPE
            SYNTAX      Counter32
            MAX-ACCESS  read-only
            STATUS      current
            DESCRIPTION
                "The number of EAPOL frames that have been received by the switch in which
                 the frame type is not recognized."
            ::= { ctcNasPortStatisticsEntry 7 }

        -- 1.3.6.1.4.1.4756.104.60.2.2.15.1.8
        ctcNasRxEapolInvalidLength OBJECT-TYPE
            SYNTAX      Counter32
            MAX-ACCESS  read-only
            STATUS      current
            DESCRIPTION
                "The number of EAPOL frames that have been received by the switch in which
                 the Packet Body Length field is invalid."
            ::= { ctcNasPortStatisticsEntry 8 }

        -- 1.3.6.1.4.1.4756.104.60.2.2.15.1.9
        ctcNasTxEapolTotal OBJECT-TYPE
            SYNTAX      Counter32
            MAX-ACCESS  read-only
            STATUS      current
            DESCRIPTION
                "The number of EAPOL frames of any type that have been transmitted by the switch."
            ::= { ctcNasPortStatisticsEntry 9 }

        -- 1.3.6.1.4.1.4756.104.60.2.2.15.1.10
        ctcNasTxEapolRequestID OBJECT-TYPE
            SYNTAX      Counter32
            MAX-ACCESS  read-only
            STATUS      current
            DESCRIPTION
                "The number of EAPOL Request Identity frames that have been transmitted by the switch."
            ::= { ctcNasPortStatisticsEntry 10 }

        -- 1.3.6.1.4.1.4756.104.60.2.2.15.1.11
        ctcNasTxEapolRequests OBJECT-TYPE
            SYNTAX      Counter32
            MAX-ACCESS  read-only
            STATUS      current
            DESCRIPTION
                "The number of valid EAPOL Request frames (other than Request Identity frames)
                 that have been transmitted by the switch."
            ::= { ctcNasPortStatisticsEntry 11 }

        -- 1.3.6.1.4.1.4756.104.60.2.2.15.1.12
        ctcNasRxBackendAccessChallenges OBJECT-TYPE
            SYNTAX      Counter32
            MAX-ACCESS  read-only
            STATUS      current
            DESCRIPTION
                "802.1X-based: Counts the number of times that the switch receives the first request from
                               the backend server following the first response from the supplicant.
                               Indicates that the backend server has communication with the switch.
                 MAC-based: Counts all Access Challenges received from the backend server for this port
                           (left-most table) or client (right-most table)."
            ::= { ctcNasPortStatisticsEntry 12 }

        -- 1.3.6.1.4.1.4756.104.60.2.2.15.1.13
        ctcNasRxBackendOtherRequests OBJECT-TYPE
            SYNTAX      Counter32
            MAX-ACCESS  read-only
            STATUS      current
            DESCRIPTION
                "802.1X-based: Counts the number of times that the switch sends an EAP Request packet
                               following the first to the supplicant.
                               Indicates that the backend server chose an EAP-method.
                 MAC-based: Not applicable."
            ::= { ctcNasPortStatisticsEntry 13 }

        -- 1.3.6.1.4.1.4756.104.60.2.2.15.1.14
        ctcNasRxBackendAuthSuccesses OBJECT-TYPE
            SYNTAX      Counter32
            MAX-ACCESS  read-only
            STATUS      current
            DESCRIPTION
                "802.1X- and MAC-based: Counts the number of times that the switch receives a
                                        success indication. Indicates that the supplicant/client
                                        has successfully authenticated to the backend server."
            ::= { ctcNasPortStatisticsEntry 14 }

        -- 1.3.6.1.4.1.4756.104.60.2.2.15.1.15
        ctcNasRxBackendAuthFailures OBJECT-TYPE
            SYNTAX      Counter32
            MAX-ACCESS  read-only
            STATUS      current
            DESCRIPTION
                "802.1X- and MAC-based: Counts the number of times that the switch receives a
                                        failure message. This indicates that the supplicant/client
                                        has not authenticated to the backend server."
            ::= { ctcNasPortStatisticsEntry 15 }

        -- 1.3.6.1.4.1.4756.104.60.2.2.15.1.16
        ctcNasTxBackendResponeses OBJECT-TYPE
            SYNTAX      Counter32
            MAX-ACCESS  read-only
            STATUS      current
            DESCRIPTION
                "802.1X-based: Counts the number of times that the switch attempts to send a
                               supplicant's first response packet to the backend server.
                               Indicates the switch attempted communication with the backend server.
                               Possible retransmissions are not counted.
                 MAC-based: Counts all the backend server packets sent from the switch towards
                            the backend server for a given port (left-most table) or client (right-most table).
                            Possible retransmissions are not counted."
            ::= { ctcNasPortStatisticsEntry 16 }

    
    -- 1.3.6.1.4.1.4756.104.60.2.3
    ctcACL OBJECT IDENTIFIER ::= { ctcSecurityNetwork 3 }

    -- 1.3.6.1.4.1.4756.104.60.2.3.1
    ctcAclPortCounterClear OBJECT-TYPE
        SYNTAX      INTEGER {
                        trigger(1),
                        normal(2)
                    }
        MAX-ACCESS  read-write
        STATUS      current
        DESCRIPTION
            "Clear the counters."
        ::= { ctcACL 1 }

    -- 1.3.6.1.4.1.4756.104.60.2.3.2
    ctcAclPortConfigTable OBJECT-TYPE
        SYNTAX      SEQUENCE OF CtcAclPortConfigEntry
        MAX-ACCESS  not-accessible
        STATUS      current
        DESCRIPTION
            "This table configure the ACL parameters (ACE) of each switch port.
             These parameters will affect frames received on a port unless the frame matches a specific ACE."
        ::= { ctcACL 2 }

    -- 1.3.6.1.4.1.4756.104.60.2.3.2.1
    ctcAclPortConfigEntry OBJECT-TYPE
        SYNTAX      CtcAclPortConfigEntry
        MAX-ACCESS  not-accessible
        STATUS      current
        DESCRIPTION
            "The Entry of ACL ports configuration."
        INDEX { ctcPortIndex }
        ::= { ctcAclPortConfigTable 1 }

    CtcAclPortConfigEntry ::=
        SEQUENCE {
            ctcAclPortPollcyID           Integer32,
            ctcAclPortAction             INTEGER,
            ctcAclPortRateLimiterID      Integer32,
            ctcAclPortRedirectPorts      DisplayString,
            ctcAclPortMirror             INTEGER,
            ctcAclPortLogging            INTEGER,
            ctcAclPortShutdown           INTEGER,
            ctcAclPortState              INTEGER,
            ctcAclPortCounter            Counter32
        }

        -- 1.3.6.1.4.1.4756.104.60.2.3.2.1.1
        ctcAclPortPollcyID OBJECT-TYPE
            SYNTAX      Integer32 (0..255)
            MAX-ACCESS  read-write
            STATUS      current
            DESCRIPTION
                "Select the policy to apply to this port. The allowed values are 0 through 255.
                 The default value is 0."
            DEFVAL      { 1 }
            ::= { ctcAclPortConfigEntry 1 }

        -- 1.3.6.1.4.1.4756.104.60.2.3.2.1.2
        ctcAclPortAction OBJECT-TYPE
            SYNTAX      INTEGER {
                            deny(1),
                            permit(2)
                        }
            MAX-ACCESS  read-write
            STATUS      current
            DESCRIPTION
                "Select whether forwarding is permitted (permit) or denied (deny).
                 The default value is permit."
            ::= { ctcAclPortConfigEntry 2 }

        -- 1.3.6.1.4.1.4756.104.60.2.3.2.1.3
        ctcAclPortRateLimiterID OBJECT-TYPE
            SYNTAX      Integer32 (0 | 1..16)
            MAX-ACCESS  read-write
            STATUS      current
            DESCRIPTION
                "Select which rate limiter to apply on this port.
                 The allowed values are 0(Disabled) or the values 1 through 16.
                 The default value is 0(Disabled)."
            ::= { ctcAclPortConfigEntry 3 }

        -- 1.3.6.1.4.1.4756.104.60.2.3.2.1.4
        ctcAclPortRedirectPorts OBJECT-TYPE
            SYNTAX      DisplayString
            MAX-ACCESS  read-write
            STATUS      current
            DESCRIPTION
                "Select which port frames are redirected on.
                 The allowed values are Disabled or a specific port number and
                 it can't be set when action is permitted. The default value is 'Disabled'."
            ::= { ctcAclPortConfigEntry 4 }

        -- 1.3.6.1.4.1.4756.104.60.2.3.2.1.5
        ctcAclPortMirror OBJECT-TYPE
            SYNTAX      INTEGER {
                            enable(1),
                            disable(2)
                        }
            MAX-ACCESS  read-write
            STATUS      current
            DESCRIPTION
                "Specify the mirror operation of this port. The allowed values are:
                 Enabled: Frames received on the port are mirrored.
                 Disabled: Frames received on the port are not mirrored.
                 The default value is Disabled."
            ::= { ctcAclPortConfigEntry 5 }

        -- 1.3.6.1.4.1.4756.104.60.2.3.2.1.6
        ctcAclPortLogging OBJECT-TYPE
            SYNTAX      INTEGER {
                            enable(1),
                            disable(2)
                        }
            MAX-ACCESS  read-write
            STATUS      current
            DESCRIPTION
                "Specify the logging operation of this port. The allowed values are:
                 Enabled: Frames received on the port are stored in the System Log.
                 Disabled: Frames received on the port are not logged.
                 The default value is Disabled.
                 Please note that the System Log memory size and logging rate is limited."
            ::= { ctcAclPortConfigEntry 6 }

        -- 1.3.6.1.4.1.4756.104.60.2.3.2.1.7
        ctcAclPortShutdown OBJECT-TYPE
            SYNTAX      INTEGER {
                            enable(1),
                            disable(2)
                        }
            MAX-ACCESS  read-write
            STATUS      current
            DESCRIPTION
                "Specify the port shut down operation of this port. The allowed values are:
                 Enabled: If a frame is received on the port, the port will be disabled.
                 Disabled: Port shut down is disabled.
                 The default value is Disabled."
            ::= { ctcAclPortConfigEntry 7 }

        -- 1.3.6.1.4.1.4756.104.60.2.3.2.1.8
        ctcAclPortState OBJECT-TYPE
            SYNTAX      INTEGER {
                            enable(1),
                            disable(2)
                        }
            MAX-ACCESS  read-write
            STATUS      current            
            DESCRIPTION
                "Specify the port state of this port. The allowed values are:
                 Enabled: To reopen ports by changing the volatile port configuration of the ACL user module.
                 Disabled: To close ports by changing the volatile port configuration of the ACL user module.
                 The default value is Enabled."
            DEFVAL      { 1 }     
            ::= { ctcAclPortConfigEntry 8 }

        -- 1.3.6.1.4.1.4756.104.60.2.3.2.1.9
        ctcAclPortCounter OBJECT-TYPE
            SYNTAX      Counter32
            UNITS       "Frames"
            MAX-ACCESS  read-only
            STATUS      current
            DESCRIPTION
                "Counts the number of frames that match this ACE."
            ::= { ctcAclPortConfigEntry 9 }

    -- 1.3.6.1.4.1.4756.104.60.2.3.3
    ctcAclRateLimiterConfigTable OBJECT-TYPE
        SYNTAX      SEQUENCE OF CtcAclRateLimiterConfigEntry
        MAX-ACCESS  not-accessible
        STATUS      current
        DESCRIPTION
            "This table configure the rate limiter for the ACL of the switch."
        ::= { ctcACL 3 }

    -- 1.3.6.1.4.1.4756.104.60.2.3.3.1
    ctcAclRateLimiterConfigEntry OBJECT-TYPE
        SYNTAX      CtcAclRateLimiterConfigEntry
        MAX-ACCESS  not-accessible
        STATUS      current
        DESCRIPTION
            "The Entry of ACL Rate Limiter Configuration."
        INDEX { ctcAclRateLimiterID }
        ::= { ctcAclRateLimiterConfigTable 1 }

    CtcAclRateLimiterConfigEntry ::=
        SEQUENCE {
            ctcAclRateLimiterID          Integer32,
            ctcAclLimitedRate            Integer32,
            ctcAclLimitedUnit            INTEGER
        }

        -- 1.3.6.1.4.1.4756.104.60.2.3.3.1.1
        ctcAclRateLimiterID OBJECT-TYPE
            SYNTAX      Integer32 (1..16)
            MAX-ACCESS  read-only
            STATUS      current
            DESCRIPTION
                "The ID of rate limiter entry."
            ::= { ctcAclRateLimiterConfigEntry 1 }

        -- 1.3.6.1.4.1.4756.104.60.2.3.3.1.2
        ctcAclLimitedRate OBJECT-TYPE
            SYNTAX      Integer32 (0..3276700)
            MAX-ACCESS  read-write
            STATUS      current
            DESCRIPTION
                "The allowed values are: 0-3276700 in pps 
                 or 0, 100, 200, 300, ..., 1000000 in kbps."
            ::= { ctcAclRateLimiterConfigEntry 2 }

        -- 1.3.6.1.4.1.4756.104.60.2.3.3.1.3
        ctcAclLimitedUnit OBJECT-TYPE
            SYNTAX      INTEGER {
                            pps(1),
                            kbps(2)
                        }
            MAX-ACCESS  read-write
            STATUS      current
            DESCRIPTION
                "Specify the rate unit. The allowed values are:
                 pps: packets per second.
                 kbps: Kbits per second."
            ::= { ctcAclRateLimiterConfigEntry 3 }

    -- 1.3.6.1.4.1.4756.104.60.2.3.4
    ctcAddACE OBJECT-TYPE
        SYNTAX      Integer32 (0 | 1..256)
        MAX-ACCESS  read-write
        STATUS      current
        DESCRIPTION                                  
            "Inserts a new ACE to list.
             Value 0: Add ACE to end of list.
             Value 1 ~ 256: Insert new ACE before this ACE index."
        ::= { ctcACL 4 }

    -- 1.3.6.1.4.1.4756.104.60.2.3.5
    ctcDeleteACE OBJECT-TYPE
        SYNTAX      Integer32 (1..256)
        MAX-ACCESS  read-write
        STATUS      current
        DESCRIPTION
            "Deletes the ACE by Index."
        ::= { ctcACL 5 }

    -- 1.3.6.1.4.1.4756.104.60.2.3.6
    ctcRemoveAllACE OBJECT-TYPE
        SYNTAX      INTEGER {
                        trigger(1),
                        normal(2)
                    }
        MAX-ACCESS  read-write
        STATUS      current
        DESCRIPTION
            "Remove all ACEs."
        ::= { ctcACL 6 }

    -- 1.3.6.1.4.1.4756.104.60.2.3.7
    ctcMoveAceDown OBJECT-TYPE
        SYNTAX      Integer32 (1..256)
        MAX-ACCESS  read-write
        STATUS      current
        DESCRIPTION
            "Moves the ACE down the list."
        ::= { ctcACL 7 }

    -- 1.3.6.1.4.1.4756.104.60.2.3.8
    ctcAceCounterClear OBJECT-TYPE
        SYNTAX      INTEGER {
                        trigger(1),
                        normal(2)
                    }
        MAX-ACCESS  read-write
        STATUS      current
        DESCRIPTION
            "Clear the counters."
        ::= { ctcACL 8 }

    -- 1.3.6.1.4.1.4756.104.60.2.3.9
    ctcAceConfigTable OBJECT-TYPE
        SYNTAX      SEQUENCE OF CtcAceConfigEntry
        MAX-ACCESS  not-accessible
        STATUS      current
        DESCRIPTION
            "Configure an ACE (Access Control Entry) on this table.
             An ACE consists of several parameters.
             These parameters vary according to the frame type that you select."
        ::= { ctcACL 9 }

    -- 1.3.6.1.4.1.4756.104.60.2.3.9.1
    ctcAceConfigEntry OBJECT-TYPE
        SYNTAX      CtcAceConfigEntry
        MAX-ACCESS  not-accessible
        STATUS      current
        DESCRIPTION
            "The entry of ACE List."
        INDEX { ctcAceIndex }
        ::= { ctcAceConfigTable 1 }

    CtcAceConfigEntry ::=
        SEQUENCE {
            ctcAceIndex                         Integer32,
            ctcAceIngressPort                   DisplayString,
            ctcAcePolicyFilter                  INTEGER,
            ctcAcePolicyValue                   Integer32,
            ctcAcePolicyBitmask                 DisplayString,
            ctcAceFrameType                     INTEGER,
            ctcAceSMacFilter                    INTEGER,
            ctcAceSMacValue                     MacAddress,
            ctcAceDMacFilter                    INTEGER,
            ctcAceDMacValue                     MacAddress,      -- 10      
            ctcAce802dot1qTagged                INTEGER,
            ctcAceVlanIdFilter                  INTEGER,
            ctcAceVlanID                        Integer32,       
            ctcAceTagPriority                   Integer32,
            ctcAceEtherTypeFilter               INTEGER,
            ctcAceEtherTypeValue                DisplayString,
            ctcAceArpFlagArpRarp                INTEGER,
            ctcAceArpFlagRequestRelay           INTEGER,
            ctcAceArpSenderIpFilter             INTEGER,
            ctcAceArpSenderIpAddress            IpAddress,       -- 20
            ctcAceArpSenderIpMask               IpAddress,
            ctcAceArpTargetIpFilter             INTEGER,
            ctcAceArpTargetIpAddress            IpAddress,       
            ctcAceArpTargetIpMask               IpAddress,
            ctcAceArpSMacMatch                  INTEGER,
            ctcAceRarpDMacMatch                 INTEGER,
            ctcAceArpIpEthernetLength           INTEGER,
            ctcAceArpIp                         INTEGER,
            ctcAceArpEthernet                   INTEGER,
            ctcAceIpProtocolFilter              INTEGER,         -- 30
            ctcAceIpProtocolValue               Integer32,
            ctcAceIpTTL                         INTEGER,
            ctcAceIpFragment                    INTEGER,         
            ctcAceIpOption                      INTEGER,
            ctcAceSIpFilter                     INTEGER,
            ctcAceSIpAddress                    IpAddress,
            ctcAceSIpMask                       IpAddress,
            ctcAceDIpFilter                     INTEGER,
            ctcAceDIpAddress                    IpAddress,
            ctcAceDIpMask                       IpAddress,       -- 40
            ctcAceIcmpTypeFilter                INTEGER,
            ctcAceIcmpTypeValue                 Integer32,
            ctcAceIcmpCodeFilter                INTEGER,         
            ctcAceIcmpCodeValue                 Integer32,
            ctcAceUdpSPortFilter                INTEGER,
            ctcAceUdpSPortNumberSpecific        Integer32,
            ctcAceUdpSPortNumberStart           Integer32,
            ctcAceUdpSPortNumberLast            Integer32,
            ctcAceUdpDPortFilter                INTEGER,
            ctcAceUdpDPortNumberSpecific        Integer32,       -- 50
            ctcAceUdpDPortNumberStart           Integer32,
            ctcAceUdpDPortNumberLast            Integer32,
            ctcAceTcpSPortFilter                INTEGER,         
            ctcAceTcpSPortNumberSpecific        Integer32,
            ctcAceTcpSPortNumberStart           Integer32,
            ctcAceTcpSPortNumberLast            Integer32,
            ctcAceTcpDPortFilter                INTEGER,
            ctcAceTcpDPortNumberSpecific        Integer32,
            ctcAceTcpDPortNumberStart           Integer32,
            ctcAceTcpDPortNumberLast            Integer32,       -- 60
            ctcAceTcpFIN                        INTEGER,
            ctcAceTcpSYN                        INTEGER,
            ctcAceTcpRST                        INTEGER,         
            ctcAceTcpPSH                        INTEGER,
            ctcAceTcpACK                        INTEGER,
            ctcAceTcpURG                        INTEGER,
            ctcAceAction                        INTEGER,
            ctcAceRateLimiterID                 Integer32,
            ctcAcePortRedirect                  DisplayString,
            ctcAceMirror                        INTEGER,         -- 70
            ctcAceLogging                       INTEGER,
            ctcAceShutdown                      INTEGER
        }

        -- 1.3.6.1.4.1.4756.104.60.2.3.9.1.1    
        ctcAceIndex OBJECT-TYPE
            SYNTAX      Integer32 (1..256)
            MAX-ACCESS  read-only
            STATUS      current
            DESCRIPTION
                "Indicates the Index of ACE entries."
            ::= { ctcAceConfigEntry 1 }

        -- 1.3.6.1.4.1.4756.104.60.2.3.9.1.2    
        ctcAceIngressPort OBJECT-TYPE
            SYNTAX      DisplayString    
            MAX-ACCESS  read-write
            STATUS      current
            DESCRIPTION
                "Select the ingress port for which this ACE applies. 
                 All: The ACE applies to all port. 
                 Port n/list: The ACE applies to this port(s) number, where n is the number of the switch port.
                 The default value is 'All'.
                 Syntex: [all | (port <port_list>)]"
            ::= { ctcAceConfigEntry 2 }

        -- 1.3.6.1.4.1.4756.104.60.2.3.9.1.4    
        ctcAcePolicyFilter OBJECT-TYPE
            SYNTAX      INTEGER {
                            any(1),
                            specific(2)
                        }    
            MAX-ACCESS  read-write
            STATUS      current
            DESCRIPTION
                "Specify the policy number filter for this ACE. 
                 Any: No policy filter is specified. (policy filter status is 'don't-care'.) 
                 Specific: If you want to filter a specific policy with this ACE, choose this value."
            ::= { ctcAceConfigEntry 3 }

        -- 1.3.6.1.4.1.4756.104.60.2.3.9.1.5    
        ctcAcePolicyValue OBJECT-TYPE
            SYNTAX      Integer32 (0..255)    
            MAX-ACCESS  read-write
            STATUS      current
            DESCRIPTION
                "When 'Specific' is selected for the policy filter, you can enter a specific policy value.
                 The allowed range is 0 to 255."
            ::= { ctcAceConfigEntry 4 }

        -- 1.3.6.1.4.1.4756.104.60.2.3.9.1.6   
        ctcAcePolicyBitmask OBJECT-TYPE
            SYNTAX      DisplayString    
            MAX-ACCESS  read-write
            STATUS      current
            DESCRIPTION
                "When 'Specific' is selected for the policy filter, you can enter a specific policy bitmask.
                 The allowed range is 0x0 to 0xff."
            ::= { ctcAceConfigEntry 5 }

        -- 1.3.6.1.4.1.4756.104.60.2.3.9.1.3    
        ctcAceFrameType OBJECT-TYPE
            SYNTAX      INTEGER {
                            any(1),
                            ethernetType(2),
                            arp(3),
                            ipv4(4)
                        }    
            MAX-ACCESS  read-write
            STATUS      current
            DESCRIPTION
                "Select the ingress port for which this ACE applies.
                 Any: The ACE applies to any port.
                 Port n: The ACE applies to this port number, where n is the number of the switch port.
                 Policy n: The ACE applies to this policy number, where n can range from 1 through 8.
                 The default value is 'Any'."
            ::= { ctcAceConfigEntry 6 }

        -- 1.3.6.1.4.1.4756.104.60.2.3.9.1.7    
        ctcAceSMacFilter OBJECT-TYPE
            SYNTAX      INTEGER {
                            any(1),
                            specific(2)
                        }    
            MAX-ACCESS  read-write
            STATUS      current
            DESCRIPTION
                "(Only effected when the frame type is Ethernet Type or ARP.)
                 Specify the source MAC filter for this ACE.
                 Any: No SMAC filter is specified. (SMAC filter status is don't-care.)
                 Specific: Filter a specific source MAC address with this ACE.
                 The default value is 'Any'."
            ::= { ctcAceConfigEntry 7 }

        -- 1.3.6.1.4.1.4756.104.60.2.3.9.1.8    
        ctcAceSMacValue OBJECT-TYPE
            SYNTAX      MacAddress    
            MAX-ACCESS  read-write
            STATUS      current
            DESCRIPTION
                "When 'Specific' is selected for the SMAC filter,
                 you can enter a specific source MAC address.
                 The legal format is 'xx-xx-xx-xx-xx-xx'.
                 A frame that hits this ACE matches this SMAC value."
            ::= { ctcAceConfigEntry 8 }

        -- 1.3.6.1.4.1.4756.104.60.2.3.9.1.9    
        ctcAceDMacFilter OBJECT-TYPE
            SYNTAX      INTEGER {
                            any(1),
                            multicast(2),
                            broadcast(3),
                            unicast(4),
                            specific(5)
                        }    
            MAX-ACCESS  read-write
            STATUS      current
            DESCRIPTION
                "Specify the destination MAC filter for this ACE.
                 Any: No DMAC filter is specified. (DMAC filter status is don't-care.)
                 Multicast: Frame must be multicast.
                 Broadcast: Frame must be broadcast.
                 Unicast: Frame must be unicast.
                 Specific: If you want to filter a specific destination MAC address with this ACE.
                 The default value is 'Any'."
            ::= { ctcAceConfigEntry 9 }

        -- 1.3.6.1.4.1.4756.104.60.2.3.9.1.10    
        ctcAceDMacValue OBJECT-TYPE
            SYNTAX      MacAddress    
            MAX-ACCESS  read-write
            STATUS      current
            DESCRIPTION
                "When 'Specific' is selected for the DMAC filter,
                 you can enter a specific destination MAC address.
                 The legal format is 'xx-xx-xx-xx-xx-xx'.
                 A frame that hits this ACE matches this DMAC value."
            ::= { ctcAceConfigEntry 10 }

        -- 1.3.6.1.4.1.4756.104.60.2.3.9.1.11    
        ctcAce802dot1qTagged OBJECT-TYPE
            SYNTAX      INTEGER {
                            any(1),
                            disabled(2),
                            enabled(3)
                        }    
            MAX-ACCESS  read-write
            STATUS      current
            DESCRIPTION
                "Specify whether frames can hit the action according to the 802.1Q tagged.
                 The allowed values are:
                 Any: Any value is allowed ('don't-care').
                 Enabled: Tagged frame only.
                 Disabled: Untagged frame only.
                 The default value is 'Any'."
            ::= { ctcAceConfigEntry 11 }

        -- 1.3.6.1.4.1.4756.104.60.2.3.9.1.12    
        ctcAceVlanIdFilter OBJECT-TYPE
            SYNTAX      INTEGER {
                            any(1),
                            specific(2)
                        }    
            MAX-ACCESS  read-write
            STATUS      current
            DESCRIPTION
                "Specify the VLAN ID filter for this ACE.
                 Any: No VLAN ID filter is specified. (VLAN ID filter status is don't-care.)
                 Specific: Filter a specific VLAN ID with this ACE.
                 The default value is 'Any'."
            ::= { ctcAceConfigEntry 12 }

        -- 1.3.6.1.4.1.4756.104.60.2.3.9.1.13    
        ctcAceVlanID OBJECT-TYPE
            SYNTAX      Integer32 (1..4095)    
            MAX-ACCESS  read-write
            STATUS      current
            DESCRIPTION
                "When Specific is selected for the VLAN ID filter, you can enter a specific VLAN ID number.
                 The allowed range is 1 to 4095. A frame that hits this ACE matches this VLAN ID value."
            ::= { ctcAceConfigEntry 13 }

        -- 1.3.6.1.4.1.4756.104.60.2.3.9.1.14    
        ctcAceTagPriority OBJECT-TYPE
            SYNTAX      Integer32 (-1..7)    
            MAX-ACCESS  read-write
            STATUS      current
            DESCRIPTION
                "Specify the tag priority for this ACE.
                 A frame that hits this ACE matches this tag priority.
                 The allowed number range is -1 to 7.
                 The value -1(Any) means that no tag priority is specified (tag priority is don't-care.)
                 The default value is -1(Any)."
            ::= { ctcAceConfigEntry 14 }

        -- 1.3.6.1.4.1.4756.104.60.2.3.9.1.15    
        ctcAceEtherTypeFilter OBJECT-TYPE
            SYNTAX      INTEGER {
                            any(1),
                            specific(2)
                        }    
            MAX-ACCESS  read-write
            STATUS      current
            DESCRIPTION
                "Specify the Ethernet type filter for this ACE.
                 Any: No EtherType filter is specified (EtherType filter status is don't-care).
                 Specific: Filter a specific EtherType filter with this ACE.
                 The default value is 'Any'."
            ::= { ctcAceConfigEntry 15 }

        -- 1.3.6.1.4.1.4756.104.60.2.3.9.1.16    
        ctcAceEtherTypeValue OBJECT-TYPE
            SYNTAX      DisplayString    
            MAX-ACCESS  read-write
            STATUS      current
            DESCRIPTION
                "When 'Specific' is selected for the EtherType filter,
                 you can enter a specific EtherType value.
                 The allowed range is 0x600 to 0xFFFF but excluding 0x800(IPv4), 0x806(ARP) and 0x86DD(IPv6).
                 A frame that hits this ACE matches this EtherType value."
            ::= { ctcAceConfigEntry 16 }

        -- 1.3.6.1.4.1.4756.104.60.2.3.9.1.17    
        ctcAceArpFlagArpRarp OBJECT-TYPE
            SYNTAX      INTEGER {
                            any(1),
                            arp(2),
                            rarp(3),
                            other(4)
                        }    
            MAX-ACCESS  read-write
            STATUS      current
            DESCRIPTION
                "Specify the available ARP/RARP opcode (OP) flag for this ACE.
                 Any: No ARP/RARP OP flag is specified. (OP is don't-care.)
                 ARP: Frame must have ARP/RARP opcode set to ARP.
                 RARP: Frame must have ARP/RARP opcode set to RARP.
                 Other: Frame has unknown ARP/RARP Opcode flag. 
                 The default value is 'Any'."
            ::= { ctcAceConfigEntry 17 }

        -- 1.3.6.1.4.1.4756.104.60.2.3.9.1.18    
        ctcAceArpFlagRequestRelay OBJECT-TYPE
            SYNTAX      INTEGER {
                            any(1),
                            request(2),
                            reply(3)
                        }    
            MAX-ACCESS  read-write
            STATUS      current
            DESCRIPTION
                "Specify the available ARP/RARP opcode (OP) flag for this ACE.
                 Any: No ARP/RARP OP flag is specified. (OP is 'don't-care'.)
                 Request: Frame must have ARP Request or RARP Request OP flag set.
                 Reply: Frame must have ARP Reply or RARP Reply OP flag.  
                 The default value is 'Any'."
            ::= { ctcAceConfigEntry 18 }

        -- 1.3.6.1.4.1.4756.104.60.2.3.9.1.19    
        ctcAceArpSenderIpFilter OBJECT-TYPE
            SYNTAX      INTEGER {
                            any(1),
                            host(2),
                            network(3)
                        }    
            MAX-ACCESS  read-write
            STATUS      current
            DESCRIPTION
                "Specify the sender IP filter for this ACE.
                 Any: No sender IP filter is specified. (Sender IP filter is don't-care.)
                 Host: Sender IP filter is set to Host.
                       Specify the sender IP address in the SIP Address field that appears.
                 Network: Sender IP filter is set to Network.
                          Specify the sender IP address and sender IP mask in the SIP Address
                          and SIP Mask fields that appear.  
                 The default value is 'Any'."
            ::= { ctcAceConfigEntry 19 }

        -- 1.3.6.1.4.1.4756.104.60.2.3.9.1.20    
        ctcAceArpSenderIpAddress OBJECT-TYPE
            SYNTAX      IpAddress    
            MAX-ACCESS  read-write
            STATUS      current
            DESCRIPTION
                "When 'Host' or 'Network' is selected for the sender IP filter,
                 you can enter a specific sender IP address in dotted decimal notation."
            ::= { ctcAceConfigEntry 20 }

        -- 1.3.6.1.4.1.4756.104.60.2.3.9.1.21    
        ctcAceArpSenderIpMask OBJECT-TYPE
            SYNTAX      IpAddress    
            MAX-ACCESS  read-write
            STATUS      current
            DESCRIPTION
                "When 'Network' is selected for the sender IP filter,
                 you can enter a specific sender IP mask in dotted decimal notation."
            ::= { ctcAceConfigEntry 21 }

        -- 1.3.6.1.4.1.4756.104.60.2.3.9.1.22    
        ctcAceArpTargetIpFilter OBJECT-TYPE
            SYNTAX      INTEGER {
                            any(1),
                            host(2),
                            network(3)
                        }    
            MAX-ACCESS  read-write
            STATUS      current
            DESCRIPTION
                "Specify the target IP filter for this specific ACE.
                 Any: No target IP filter is specified. (Target IP filter is don't-care.)
                 Host: Target IP filter is set to Host.
                       Specify the target IP address in the Target IP Address field that appears.
                 Network: Target IP filter is set to Network.
                          Specify the target IP address and target IP mask in the Target IP Address
                          and Target IP Mask fields that appear.  
                 The default value is 'Any'."
            ::= { ctcAceConfigEntry 22 }

        -- 1.3.6.1.4.1.4756.104.60.2.3.9.1.23    
        ctcAceArpTargetIpAddress OBJECT-TYPE
            SYNTAX      IpAddress    
            MAX-ACCESS  read-write
            STATUS      current
            DESCRIPTION
                "When 'Host' or 'Network' is selected for the target IP filter,
                 you can enter a specific target IP address in dotted decimal notation."
            ::= { ctcAceConfigEntry 23 }

        -- 1.3.6.1.4.1.4756.104.60.2.3.9.1.24    
        ctcAceArpTargetIpMask OBJECT-TYPE
            SYNTAX      IpAddress    
            MAX-ACCESS  read-write
            STATUS      current
            DESCRIPTION
                "When 'Network' is selected for the target IP filter,
                 you can enter a specific target IP mask in dotted decimal notation."
            ::= { ctcAceConfigEntry 24 }

        -- 1.3.6.1.4.1.4756.104.60.2.3.9.1.25    
        ctcAceArpSMacMatch OBJECT-TYPE
            SYNTAX      INTEGER {
                            any(1),
                            unequal(2),
                            equal(3)
                        }    
            MAX-ACCESS  read-write
            STATUS      current
            DESCRIPTION
                "Specify whether frames can hit the action according to
                 their sender hardware address field (SHA) settings.
                 Unequal: ARP frames where SHA is not equal to the SMAC address.
                 Equal: ARP frames where SHA is equal to the SMAC address.
                 Any: Any value is allowed (don't-care).   
                 The default value is 'Any'."
            ::= { ctcAceConfigEntry 25 }

        -- 1.3.6.1.4.1.4756.104.60.2.3.9.1.26    
        ctcAceRarpDMacMatch OBJECT-TYPE
            SYNTAX      INTEGER {
                            any(1),
                            unequal(2),
                            equal(3)
                        }    
            MAX-ACCESS  read-write
            STATUS      current
            DESCRIPTION
                "Specify whether frames can hit the action according to
                 their target hardware address field (THA) settings.
                 Unequal: RARP frames where THA is not equal to the DMAC address.
                 Equal: RARP frames where THA is equal to the DMAC address.
                 Any: Any value is allowed (don't-care).    
                 The default value is 'Any'."
            ::= { ctcAceConfigEntry 26 }

        -- 1.3.6.1.4.1.4756.104.60.2.3.9.1.27    
        ctcAceArpIpEthernetLength OBJECT-TYPE
            SYNTAX      INTEGER {
                            any(1),
                            unequal(2),
                            equal(3)
                        }    
            MAX-ACCESS  read-write
            STATUS      current
            DESCRIPTION
                "Specify whether frames can hit the action according to their
                 ARP/RARP hardware address length (HLN) and protocol address length (PLN) settings.
                 Unequal: ARP/RARP frames where the HLN is not equal to Ethernet (0x06) or
                          the (PLN) is not equal to IPv4 (0x04).
                 Equal: ARP/RARP frames where the HLN is equal to Ethernet (0x06) and
                        the (PLN) is equal to IPv4 (0x04).
                 Any: Any value is allowed (don't-care).     
                 The default value is 'Any'."
            ::= { ctcAceConfigEntry 27 }

        -- 1.3.6.1.4.1.4756.104.60.2.3.9.1.28    
        ctcAceArpIp OBJECT-TYPE
            SYNTAX      INTEGER {
                            any(1),
                            unequal(2),
                            equal(3)
                        }    
            MAX-ACCESS  read-write
            STATUS      current
            DESCRIPTION
                "Specify whether frames can hit the action according to
                 their ARP/RARP hardware address space (HRD) settings.
                 Unequal: ARP/RARP frames where the HLD is not equal to Ethernet (1).
                 Equal: ARP/RARP frames where the HLD is equal to Ethernet (1).
                 Any: Any value is allowed (don't-care).      
                 The default value is 'Any'."
            ::= { ctcAceConfigEntry 28 }

        -- 1.3.6.1.4.1.4756.104.60.2.3.9.1.29    
        ctcAceArpEthernet OBJECT-TYPE
            SYNTAX      INTEGER {
                            any(1),
                            unequal(2),
                            equal(3)
                        }    
            MAX-ACCESS  read-write
            STATUS      current
            DESCRIPTION
                "Specify whether frames can hit the action according to
                 their ARP/RARP protocol address space (PRO) settings.
                 Unequal: ARP/RARP frames where the PRO is not equal to IP (0x800).
                 Equal: ARP/RARP frames where the PRO is equal to IP (0x800).
                 Any: Any value is allowed (don't-care).       
                 The default value is 'Any'."
            ::= { ctcAceConfigEntry 29 }

        -- 1.3.6.1.4.1.4756.104.60.2.3.9.1.30    
        ctcAceIpProtocolFilter OBJECT-TYPE
            SYNTAX      INTEGER {
                            any(1),
                            icmp(2),
                            udp(3),
                            tcp(4),
                            other(5)
                        }    
            MAX-ACCESS  read-write
            STATUS      current
            DESCRIPTION
                "Specify the IP protocol filter for this ACE.
                 Any: No IP protocol filter is specified (don't-care).
                 
                 ICMP: Select ICMP to filter IPv4 ICMP protocol frames.
                       Extra fields for defining ICMP parameters will appear.
                       These fields are explained later in this help file.
                 UDP: Select UDP to filter IPv4 UDP protocol frames.
                      Extra fields for defining UDP parameters will appear.
                      These fields are explained later in this help file.
                 TCP: Select TCP to filter IPv4 TCP protocol frames.
                      Extra fields for defining TCP parameters will appear.
                      These fields are explained later in this help file.
                 Specific: Filter a specific IP protocol filter with this ACE.             
                 The default value is 'Any'."
            ::= { ctcAceConfigEntry 30 }

        -- 1.3.6.1.4.1.4756.104.60.2.3.9.1.31    
        ctcAceIpProtocolValue OBJECT-TYPE
            SYNTAX      Integer32 (0..255)   
            MAX-ACCESS  read-write
            STATUS      current
            DESCRIPTION
                "When 'Specific' is selected for the IP protocol value,
                 you can enter a specific value. The allowed range is 0 to 255.
                 A frame that hits this ACE matches this IP protocol value."
            ::= { ctcAceConfigEntry 31 }

        -- 1.3.6.1.4.1.4756.104.60.2.3.9.1.32   
        ctcAceIpTTL OBJECT-TYPE
            SYNTAX      INTEGER {
                            any(1),
                            nonZero(2),
                            zero(3)
                        }    
            MAX-ACCESS  read-write
            STATUS      current
            DESCRIPTION
                "Specify the Time-to-Live settings for this ACE.
                 Zero: IPv4 frames with a Time-to-Live field greater than zero must not be able to match this entry.
                 Non-zero: IPv4 frames with a Time-to-Live field greater than zero must be able to match this entry.
                 Any: Any value is allowed (don't-care).        
                 The default value is 'Any'."
            ::= { ctcAceConfigEntry 32 }

        -- 1.3.6.1.4.1.4756.104.60.2.3.9.1.33   
        ctcAceIpFragment OBJECT-TYPE
            SYNTAX      INTEGER {
                            any(1),
                            yes(2),
                            no(3)
                        }    
            MAX-ACCESS  read-write
            STATUS      current
            DESCRIPTION
                "Specify the fragment offset settings for this ACE.
                 This involves the settings for the More Fragments (MF) bit
                 and the Fragment Offset (FRAG OFFSET) field for an IPv4 frame.
                 No: IPv4 frames where the MF bit is set or the FRAG OFFSET field is greater than
                     zero must not be able to match this entry.
                 Yes: IPv4 frames where the MF bit is set or the FRAG OFFSET field is greater than
                      zero must be able to match this entry.
                 Any: Any value is allowed (don't-care).      
                 The default value is 'Any'."
            ::= { ctcAceConfigEntry 33 }

        -- 1.3.6.1.4.1.4756.104.60.2.3.9.1.34   
        ctcAceIpOption OBJECT-TYPE
            SYNTAX      INTEGER {
                            any(1),
                            yes(2),
                            no(3)
                        }    
            MAX-ACCESS  read-write
            STATUS      current
            DESCRIPTION
                "Specify the options flag setting for this ACE.
                 No: IPv4 frames where the options flag is set must not be able to match this entry.
                 Yes: IPv4 frames where the options flag is set must be able to match this entry.
                 Any: Any value is allowed (don't-care).       
                 The default value is 'Any'."
            ::= { ctcAceConfigEntry 34 }

        -- 1.3.6.1.4.1.4756.104.60.2.3.9.1.35    
        ctcAceSIpFilter OBJECT-TYPE
            SYNTAX      INTEGER {
                            any(1),
                            host(2),
                            network(3)
                        }    
            MAX-ACCESS  read-write
            STATUS      current
            DESCRIPTION
                "Specify the source IP filter for this ACE.
                 Any: No source IP filter is specified. (Source IP filter is don't-care.)
                 Host: Source IP filter is set to Host.
                       Specify the source IP address in the SIP Address field that appears.
                 Network: Source IP filter is set to Network.
                          Specify the source IP address and source IP mask in the SIP Address
                          and SIP Mask fields that appear.   
                 The default value is 'Any'."
            ::= { ctcAceConfigEntry 35 }

        -- 1.3.6.1.4.1.4756.104.60.2.3.9.1.36    
        ctcAceSIpAddress OBJECT-TYPE
            SYNTAX      IpAddress    
            MAX-ACCESS  read-write
            STATUS      current
            DESCRIPTION
                "When 'Host' or 'Network' is selected for the source IP filter,
                 you can enter a specific SIP address in dotted decimal notation."
            ::= { ctcAceConfigEntry 36 }

        -- 1.3.6.1.4.1.4756.104.60.2.3.9.1.37    
        ctcAceSIpMask OBJECT-TYPE
            SYNTAX      IpAddress    
            MAX-ACCESS  read-write
            STATUS      current
            DESCRIPTION
                "When 'Network' is selected for the source IP filter,
                 you can enter a specific SIP mask in dotted decimal notation."
            ::= { ctcAceConfigEntry 37 }

        -- 1.3.6.1.4.1.4756.104.60.2.3.9.1.38    
        ctcAceDIpFilter OBJECT-TYPE
            SYNTAX      INTEGER {
                            any(1),
                            host(2),
                            network(3)
                        }    
            MAX-ACCESS  read-write
            STATUS      current
            DESCRIPTION
                "Specify the destination IP filter for this ACE.
                 Any: No destination IP filter is specified. (Destination IP filter is don't-care.)
                 Host: Destination IP filter is set to Host.
                       Specify the destination IP address in the DIP Address field that appears.
                 Network: Destination IP filter is set to Network.
                          Specify the destination IP address and destination IP mask in the DIP Address
                          and DIP Mask fields that appear.   
                 The default value is 'Any'."
            ::= { ctcAceConfigEntry 38 }

        -- 1.3.6.1.4.1.4756.104.60.2.3.9.1.39    
        ctcAceDIpAddress OBJECT-TYPE
            SYNTAX      IpAddress    
            MAX-ACCESS  read-write
            STATUS      current
            DESCRIPTION
                "When 'Host' or 'Network' is selected for the destination IP filter,
                 you can enter a specific DIP address in dotted decimal notation."
            ::= { ctcAceConfigEntry 39 }

        -- 1.3.6.1.4.1.4756.104.60.2.3.9.1.40    
        ctcAceDIpMask OBJECT-TYPE
            SYNTAX      IpAddress    
            MAX-ACCESS  read-write
            STATUS      current
            DESCRIPTION
                "When 'Network' is selected for the destination IP filter,
                 you can enter a specific DIP mask in dotted decimal notation. "
            ::= { ctcAceConfigEntry 40 }

        -- 1.3.6.1.4.1.4756.104.60.2.3.9.1.41    
        ctcAceIcmpTypeFilter OBJECT-TYPE
            SYNTAX      INTEGER {
                            any(1),
                            specific(2)
                        }    
            MAX-ACCESS  read-write
            STATUS      current
            DESCRIPTION
                "Specify the ICMP filter for this ACE.
                 Any: No ICMP filter is specified (ICMP filter status is don't-care).
                 Specific: If you want to filter a specific ICMP filter with this ACE,
                           you can enter a specific ICMP value.
                           A field for entering an ICMP value appears.    
                 The default value is 'Any'."
            ::= { ctcAceConfigEntry 41 }

        -- 1.3.6.1.4.1.4756.104.60.2.3.9.1.42    
        ctcAceIcmpTypeValue OBJECT-TYPE
            SYNTAX      Integer32 (0..255)   
            MAX-ACCESS  read-write
            STATUS      current
            DESCRIPTION
                "When 'Specific' is selected for the ICMP filter,
                 you can enter a specific ICMP value. The allowed range is 0 to 255.
                 A frame that hits this ACE matches this ICMP value."
            ::= { ctcAceConfigEntry 42 }

        -- 1.3.6.1.4.1.4756.104.60.2.3.9.1.43    
        ctcAceIcmpCodeFilter OBJECT-TYPE
            SYNTAX      INTEGER {
                            any(1),
                            specific(2)
                        }    
            MAX-ACCESS  read-write
            STATUS      current
            DESCRIPTION
                "Specify the ICMP code filter for this ACE.
                 Any: No ICMP code filter is specified (ICMP code filter status is don't-care).
                 Specific: If you want to filter a specific ICMP code filter with this ACE,
                           you can enter a specific ICMP code value.
                           A field for entering an ICMP code value appears.     
                 The default value is 'Any'."
            ::= { ctcAceConfigEntry 43 }

        -- 1.3.6.1.4.1.4756.104.60.2.3.9.1.44    
        ctcAceIcmpCodeValue OBJECT-TYPE
            SYNTAX      Integer32 (0..255)   
            MAX-ACCESS  read-write
            STATUS      current
            DESCRIPTION
                "When 'Specific' is selected for the ICMP code filter,
                 you can enter a specific ICMP code value. The allowed range is 0 to 255.
                 A frame that hits this ACE matches this ICMP code value."
            ::= { ctcAceConfigEntry 44 }

        -- 1.3.6.1.4.1.4756.104.60.2.3.9.1.45    
        ctcAceUdpSPortFilter OBJECT-TYPE
            SYNTAX      INTEGER {
                            any(1),
                            specific(2),
                            range(3)
                        }    
            MAX-ACCESS  read-write
            STATUS      current
            DESCRIPTION
                "Specify the UDP source filter for this ACE.
                 Any: No UDP source filter is specified (UDP source filter status is don't-care).
                 Specific: Filter a specific UDP source filter with this ACE.
                 Range: Filter a specific UDP source range filter with this ACE.    
                 The default value is 'Any'."
            ::= { ctcAceConfigEntry 45 }

        -- 1.3.6.1.4.1.4756.104.60.2.3.9.1.46    
        ctcAceUdpSPortNumberSpecific OBJECT-TYPE
            SYNTAX      Integer32 (0..65535)   
            MAX-ACCESS  read-write
            STATUS      current
            DESCRIPTION
                "When 'Specific' is selected for the UDP source filter,
                 you can enter a specific UDP source value. The allowed range is 0 to 65535.
                 A frame that hits this ACE matches this UDP source value."
            ::= { ctcAceConfigEntry 46 }

        -- 1.3.6.1.4.1.4756.104.60.2.3.9.1.47    
        ctcAceUdpSPortNumberStart OBJECT-TYPE
            SYNTAX      Integer32 (0..65534)   
            MAX-ACCESS  read-write
            STATUS      current
            DESCRIPTION
                "When 'Range' is selected for the UDP source filter,
                 the starting Source UDP port number of range can be configured here.
                 The allowed range is 0 to 65534."
            ::= { ctcAceConfigEntry 47 }

        -- 1.3.6.1.4.1.4756.104.60.2.3.9.1.48    
        ctcAceUdpSPortNumberLast OBJECT-TYPE
            SYNTAX      Integer32 (1..65535)   
            MAX-ACCESS  read-write
            STATUS      current
            DESCRIPTION
                "When 'Range' is selected for the UDP source filter,
                 the last Source UDP port number of range can be configured here.
                 The allowed range is 1 to 65535."
            ::= { ctcAceConfigEntry 48 }

        -- 1.3.6.1.4.1.4756.104.60.2.3.9.1.49    
        ctcAceUdpDPortFilter OBJECT-TYPE
            SYNTAX      INTEGER {
                            any(1),
                            specific(2),
                            range(3)
                        }    
            MAX-ACCESS  read-write
            STATUS      current
            DESCRIPTION
                "Specify the UDP destination filter for this ACE.
                 Any: No UDP destination filter is specified (UDP destination filter status is don't-care).
                 Specific: Filter a specific UDP destination filter with this ACE.
                 Range: Filter a specific range UDP destination filter with this ACE.
                 The default value is 'Any'."
            ::= { ctcAceConfigEntry 49 }

        -- 1.3.6.1.4.1.4756.104.60.2.3.9.1.50    
        ctcAceUdpDPortNumberSpecific OBJECT-TYPE
            SYNTAX      Integer32 (0..65535)   
            MAX-ACCESS  read-write
            STATUS      current
            DESCRIPTION
                "When 'Specific' is selected for the UDP destination filter,
                 you can enter a specific UDP destination value. The allowed range is 0 to 65535.
                 A frame that hits this ACE matches this UDP destination value."
            ::= { ctcAceConfigEntry 50 }

        -- 1.3.6.1.4.1.4756.104.60.2.3.9.1.51    
        ctcAceUdpDPortNumberStart OBJECT-TYPE
            SYNTAX      Integer32 (0..65534)   
            MAX-ACCESS  read-write
            STATUS      current
            DESCRIPTION
                "When 'Range' is selected for the UDP destination filter,
                 the starting Destination UDP port number of range can be configured here.
                 The allowed range is 0 to 65534."
            ::= { ctcAceConfigEntry 51 }

        -- 1.3.6.1.4.1.4756.104.60.2.3.9.1.52    
        ctcAceUdpDPortNumberLast OBJECT-TYPE
            SYNTAX      Integer32 (1..65535)   
            MAX-ACCESS  read-write
            STATUS      current
            DESCRIPTION
                "When 'Range' is selected for the UDP destination filter,
                 the last Destination UDP port number of range can be configured here.
                 The allowed range is 1 to 65535."
            ::= { ctcAceConfigEntry 52 }

        -- 1.3.6.1.4.1.4756.104.60.2.3.9.1.53    
        ctcAceTcpSPortFilter OBJECT-TYPE
            SYNTAX      INTEGER {
                            any(1),
                            specific(2),
                            range(3)
                        }    
            MAX-ACCESS  read-write
            STATUS      current
            DESCRIPTION
                "Specify the TCP source filter for this ACE.
                 Any: No TCP source filter is specified (TCP source filter status is don't-care).
                 Specific: Filter a specific TCP source filter with this ACE.
                 Range: Filter a specific TCP source range filter with this ACE.    
                 The default value is 'Any'."
            ::= { ctcAceConfigEntry 53 }

        -- 1.3.6.1.4.1.4756.104.60.2.3.9.1.54    
        ctcAceTcpSPortNumberSpecific OBJECT-TYPE
            SYNTAX      Integer32 (0..65535)   
            MAX-ACCESS  read-write
            STATUS      current
            DESCRIPTION
                "When 'Specific' is selected for the TCP source filter,
                 you can enter a specific TCP source value. The allowed range is 0 to 65535.
                 A frame that hits this ACE matches this TCP source value."
            ::= { ctcAceConfigEntry 54 }

        -- 1.3.6.1.4.1.4756.104.60.2.3.9.1.55    
        ctcAceTcpSPortNumberStart OBJECT-TYPE
            SYNTAX      Integer32 (0..65534)   
            MAX-ACCESS  read-write
            STATUS      current
            DESCRIPTION
                "When 'Range' is selected for the TCP source filter,
                 the starting Source TCP port number of range can be configured here.
                 The allowed range is 0 to 65534."
            ::= { ctcAceConfigEntry 55 }

        -- 1.3.6.1.4.1.4756.104.60.2.3.9.1.56    
        ctcAceTcpSPortNumberLast OBJECT-TYPE
            SYNTAX      Integer32 (1..65535)   
            MAX-ACCESS  read-write
            STATUS      current
            DESCRIPTION
                "When 'Range' is selected for the TCP source filter,
                 the last Source TCP port number of range can be configured here.
                 The allowed range is 1 to 65535."
            ::= { ctcAceConfigEntry 56 }

        -- 1.3.6.1.4.1.4756.104.60.2.3.9.1.57    
        ctcAceTcpDPortFilter OBJECT-TYPE
            SYNTAX      INTEGER {
                            any(1),
                            specific(2),
                            range(3)
                        }    
            MAX-ACCESS  read-write
            STATUS      current
            DESCRIPTION
                "Specify the TCP destination filter for this ACE.
                 Any: No TCP destination filter is specified (TCP destination filter status is don't-care).
                 Specific: Filter a specific TCP destination filter with this ACE.
                 Range: Filter a specific range TCP destination filter with this ACE.
                 The default value is 'Any'."
            ::= { ctcAceConfigEntry 57 }

        -- 1.3.6.1.4.1.4756.104.60.2.3.9.1.58    
        ctcAceTcpDPortNumberSpecific OBJECT-TYPE
            SYNTAX      Integer32 (0..65535)   
            MAX-ACCESS  read-write
            STATUS      current
            DESCRIPTION
                "When 'Specific' is selected for the TCP destination filter,
                 you can enter a specific TCP destination value. The allowed range is 0 to 65535.
                 A frame that hits this ACE matches this TCP destination value."
            ::= { ctcAceConfigEntry 58 }

        -- 1.3.6.1.4.1.4756.104.60.2.3.9.1.59    
        ctcAceTcpDPortNumberStart OBJECT-TYPE
            SYNTAX      Integer32 (0..65534)   
            MAX-ACCESS  read-write
            STATUS      current
            DESCRIPTION
                "When 'Range' is selected for the TCP destination filter,
                 the starting Destination TCP port number of range can be configured here.
                 The allowed range is 0 to 65534."
            ::= { ctcAceConfigEntry 59 }

        -- 1.3.6.1.4.1.4756.104.60.2.3.9.1.60    
        ctcAceTcpDPortNumberLast OBJECT-TYPE
            SYNTAX      Integer32 (1..65535)   
            MAX-ACCESS  read-write
            STATUS      current
            DESCRIPTION
                "When 'Range' is selected for the TCP destination filter,
                 the last Destination TCP port number of range can be configured here.
                 The allowed range is 1 to 65535."
            ::= { ctcAceConfigEntry 60 }

        -- 1.3.6.1.4.1.4756.104.60.2.3.9.1.61    
        ctcAceTcpFIN OBJECT-TYPE
            SYNTAX      INTEGER {
                            any(1),
                            unable(2),
                            able(3)
                        }    
            MAX-ACCESS  read-write
            STATUS      current
            DESCRIPTION
                "Specify the TCP 'No more data from sender' (FIN) value for this ACE.
                 Unable: TCP frames where the FIN field is set must not be able to match this entry.
                 Able: TCP frames where the FIN field is set must be able to match this entry.
                 Any: Any value is allowed (don't-care).
                 The default value is 'Any'"
            ::= { ctcAceConfigEntry 61 }

        -- 1.3.6.1.4.1.4756.104.60.2.3.9.1.62    
        ctcAceTcpSYN OBJECT-TYPE
            SYNTAX      INTEGER {
                            any(1),
                            unable(2),
                            able(3)
                        }    
            MAX-ACCESS  read-write
            STATUS      current
            DESCRIPTION
                "Specify the TCP 'Synchronize sequence numbers' (SYN) value for this ACE.
                 Unable: TCP frames where the SYN field is set must not be able to match this entry.
                 Able: TCP frames where the SYN field is set must be able to match this entry.
                 Any: Any value is allowed (don't-care). 
                 The default value is 'Any'"
            ::= { ctcAceConfigEntry 62 }

        -- 1.3.6.1.4.1.4756.104.60.2.3.9.1.63    
        ctcAceTcpRST OBJECT-TYPE
            SYNTAX      INTEGER {
                            any(1),
                            unable(2),
                            able(3)
                        }    
            MAX-ACCESS  read-write
            STATUS      current
            DESCRIPTION
                "Specify the TCP 'Reset the connection' (RST) value for this ACE.
                 Unable: TCP frames where the RST field is set must not be able to match this entry.
                 Able: TCP frames where the RST field is set must be able to match this entry.
                 Any: Any value is allowed (don't-care).  
                 The default value is 'Any'"
            ::= { ctcAceConfigEntry 63 }

        -- 1.3.6.1.4.1.4756.104.60.2.3.9.1.64    
        ctcAceTcpPSH OBJECT-TYPE
            SYNTAX      INTEGER {
                            any(1),
                            unable(2),
                            able(3)
                        }    
            MAX-ACCESS  read-write
            STATUS      current
            DESCRIPTION
                "Specify the TCP 'Push Function' (PSH) value for this ACE.
                 Unable: TCP frames where the PSH field is set must not be able to match this entry.
                 Able: TCP frames where the PSH field is set must be able to match this entry.
                 Any: Any value is allowed (don't-care).   
                 The default value is 'Any'"
            ::= { ctcAceConfigEntry 64 }

        -- 1.3.6.1.4.1.4756.104.60.2.3.9.1.65    
        ctcAceTcpACK OBJECT-TYPE
            SYNTAX      INTEGER {
                            any(1),
                            unable(2),
                            able(3)
                        }    
            MAX-ACCESS  read-write
            STATUS      current
            DESCRIPTION
                "Specify the TCP 'Acknowledgment field significant' (ACK) value for this ACE.
                 Unable: TCP frames where the ACK field is set must not be able to match this entry.
                 Able: TCP frames where the ACK field is set must be able to match this entry.
                 Any: Any value is allowed (don't-care).    
                 The default value is 'Any'"
            ::= { ctcAceConfigEntry 65 }

        -- 1.3.6.1.4.1.4756.104.60.2.3.9.1.66    
        ctcAceTcpURG OBJECT-TYPE
            SYNTAX      INTEGER {
                            any(1),
                            unable(2),
                            able(3)
                        }    
            MAX-ACCESS  read-write
            STATUS      current
            DESCRIPTION
                "Specify the TCP 'Urgent Pointer field significant' (URG) value for this ACE.
                 Unable: TCP frames where the URG field is set must not be able to match this entry.
                 Able: TCP frames where the URG field is set must be able to match this entry.
                 Any: Any value is allowed (don't-care).     
                 The default value is 'Any'"
            ::= { ctcAceConfigEntry 66 }

        -- 1.3.6.1.4.1.4756.104.60.2.3.9.1.67
        ctcAceAction OBJECT-TYPE
            SYNTAX      INTEGER {
                            deny(1),
                            permit(2)
                        }
            MAX-ACCESS  read-write
            STATUS      current
            DESCRIPTION
                "Specify the action to take with a frame that hits this ACE.
                 Permit: The frame that hits this ACE is granted permission for the ACE operation.
                 Deny: The frame that hits this ACE is dropped.
                 The default value is 'Permit'."
            ::= { ctcAceConfigEntry 67 }

        -- 1.3.6.1.4.1.4756.104.60.2.3.9.1.68
        ctcAceRateLimiterID OBJECT-TYPE
            SYNTAX      Integer32 (0 | 1..16)
            MAX-ACCESS  read-write
            STATUS      current
            DESCRIPTION
                "Specify the rate limiter in number of base units.
                 The allowed range is 0{Disabled) to 16.
                 The value 0(Disabled) indicates that the rate limiter operation is disabled.
                 The default value is 0(Disabled)."
            ::= { ctcAceConfigEntry 68 }

        -- 1.3.6.1.4.1.4756.104.60.2.3.9.1.69
        ctcAcePortRedirect OBJECT-TYPE
            SYNTAX      DisplayString
            MAX-ACCESS  read-write
            STATUS      current
            DESCRIPTION
                "Frames that hit the ACE are redirected to the port number specified here.
                 The allowed range is the same as the switch port number range.
                 Disabled indicates that the port redirect operation is disabled and
                 the specific port number of 'Port Redirect' can't be set when action is permitted."
            ::= { ctcAceConfigEntry 69 }

        -- 1.3.6.1.4.1.4756.104.60.2.3.9.1.70
        ctcAceMirror OBJECT-TYPE
            SYNTAX      INTEGER {
                            enable(1),
                            disable(2)
                        }
            MAX-ACCESS  read-write
            STATUS      current
            DESCRIPTION
                "Specify the mirror operation of this port.
                 Frames matching the ACE are mirrored to the destination mirror port.
                 The allowed values are:
                 Enabled: Frames received on the port are mirrored.
                 Disabled: Frames received on the port are not mirrored.
                 The default value is Disabled."
            ::= { ctcAceConfigEntry 70 }

        -- 1.3.6.1.4.1.4756.104.60.2.3.9.1.71
        ctcAceLogging OBJECT-TYPE
            SYNTAX      INTEGER {
                            enable(1),
                            disable(2)
                        }
            MAX-ACCESS  read-write
            STATUS      current
            DESCRIPTION
                "Specify the logging operation of the ACE. The allowed values are:
                 Enabled: Frames matching the ACE are stored in the System Log.
                 Disabled: Frames matching the ACE are not logged. 
                 The default value is Disabled.
                 Please note that the System Log memory size and logging rate is limited."
            ::= { ctcAceConfigEntry 71 }

        -- 1.3.6.1.4.1.4756.104.60.2.3.9.1.72
        ctcAceShutdown OBJECT-TYPE
            SYNTAX      INTEGER {
                            enable(1),
                            disable(2)
                        }
            MAX-ACCESS  read-write
            STATUS      current
            DESCRIPTION
                "Specify the port shut down operation of the ACE. The allowed values are:
                 Enabled: If a frame matches the ACE, the ingress port will be disabled.
                 Disabled: Port shut down is disabled for the ACE. 
                 The default value is Disabled."
            ::= { ctcAceConfigEntry 72 }

    -- 1.3.6.1.4.1.4756.104.60.2.3.10
    ctcAclStatusTable OBJECT-TYPE
        SYNTAX      SEQUENCE OF CtcAclStatusEntry
        MAX-ACCESS  not-accessible
        STATUS      current
        DESCRIPTION
            "This table shows the ACL status."
        ::= { ctcACL 10 }

    -- 1.3.6.1.4.1.4756.104.60.2.3.10.1
    ctcAclStatusEntry OBJECT-TYPE
        SYNTAX      CtcAclStatusEntry
        MAX-ACCESS  not-accessible
        STATUS      current
        DESCRIPTION
            "The Entry of ACL status."
        INDEX { ctcAclStatusIndex }
        ::= { ctcAclStatusTable 1 }

    CtcAclStatusEntry ::=
        SEQUENCE {
            ctcAclStatusIndex        Integer32,
            ctcAclUser               INTEGER,
            ctcAclIngressPort        DisplayString,
            ctcAclFrameType          DisplayString,
            ctcAclAction             INTEGER,
            ctcAclRateLimiter        Integer32,
            ctcAclPortRedirect       DisplayString,
            ctcAclMirror             INTEGER,
            ctcAclToCPU              INTEGER,
            ctcAclToCpuOnce          INTEGER,
            ctcAclCounter            Counter32,
            ctcAclConflict           INTEGER
        }

        -- 1.3.6.1.4.1.4756.104.60.2.3.10.1.1    
        ctcAclStatusIndex OBJECT-TYPE
            SYNTAX      Integer32 (1..256)
            MAX-ACCESS  read-only
            STATUS      current
            DESCRIPTION
                "Indicates the Index of ACL Status entries."
            ::= { ctcAclStatusEntry 1 }

        -- 1.3.6.1.4.1.4756.104.60.2.3.10.1.2    
        ctcAclUser OBJECT-TYPE
            SYNTAX      INTEGER {
                            static(1),
                            ipManagement(2),
                            ipmc(3),
                            arpInspection(4),
                            upnp(5),
                            dhcp(6)
                        }    
            MAX-ACCESS  read-only
            STATUS      current
            DESCRIPTION
                "Indicates the ACL user."
            ::= { ctcAclStatusEntry 2 }

        -- 1.3.6.1.4.1.4756.104.60.2.3.10.1.3    
        ctcAclIngressPort OBJECT-TYPE
            SYNTAX      DisplayString  
            MAX-ACCESS  read-only
            STATUS      current
            DESCRIPTION
                "Indicates the ingress port of the ACE. Possible values are:
                 Any: The ACE will match any ingress port.
                 Policy: The ACE will match ingress ports with a specific policy.
                 Port: The ACE will match a specific ingress port."
            ::= { ctcAclStatusEntry 3 }

        -- 1.3.6.1.4.1.4756.104.60.2.3.10.1.4    
        ctcAclFrameType OBJECT-TYPE
            SYNTAX      DisplayString    
            MAX-ACCESS  read-only
            STATUS      current
            DESCRIPTION
                "Indicates the frame type of the ACE. Possible values are:
                 Any: The ACE will match any frame type.
                 EType: The ACE will match Ethernet Type frames.
                        Note that an Ethernet Type based ACE will not get matched by IP and ARP frames.
                 ARP: The ACE will match ARP/RARP frames.
                 IPv4: The ACE will match all IPv4 frames.
                 IPv4/ICMP: The ACE will match IPv4 frames with ICMP protocol.
                 IPv4/UDP: The ACE will match IPv4 frames with UDP protocol.
                 IPv4/TCP: The ACE will match IPv4 frames with TCP protocol.
                 IPv4/Other: The ACE will match IPv4 frames, which are not ICMP/UDP/TCP."
            ::= { ctcAclStatusEntry 4 }

        -- 1.3.6.1.4.1.4756.104.60.2.3.10.1.5
        ctcAclAction OBJECT-TYPE
            SYNTAX      INTEGER {
                            deny(1),
                            permit(2)
                        }
            MAX-ACCESS  read-only
            STATUS      current
            DESCRIPTION
                "Indicates the forwarding action of the ACE.
                 Permit: Frames matching the ACE may be forwarded and learned.
                 Deny: Frames matching the ACE are dropped."
            ::= { ctcAclStatusEntry 5 }

        -- 1.3.6.1.4.1.4756.104.60.2.3.10.1.6
        ctcAclRateLimiter OBJECT-TYPE
            SYNTAX      Integer32 (0..16)
            MAX-ACCESS  read-only
            STATUS      current
            DESCRIPTION
                "Indicates the rate limiter number of the ACE.
                 The allowed range is 0(Disable) to 16.
                 When 0(Disabled) is displayed, the rate limiter operation is disabled."
            ::= { ctcAclStatusEntry 6 }

        -- 1.3.6.1.4.1.4756.104.60.2.3.10.1.7
        ctcAclPortRedirect OBJECT-TYPE
            SYNTAX      DisplayString
            MAX-ACCESS  read-only
            STATUS      current
            DESCRIPTION
                "Indicates the port Redirect operation of the ACE.
                 Frames matching the ACE are Redirected to the port number.
                 The allowed values are 'Disabled' or a specific port number.
                 When 'Disabled' is displayed, the port copy operation is disabled."
            ::= { ctcAclStatusEntry 7 }

        -- 1.3.6.1.4.1.4756.104.60.2.3.10.1.8
        ctcAclMirror OBJECT-TYPE
            SYNTAX      INTEGER {
                            enable(1),
                            disable(2)
                        }
            MAX-ACCESS  read-only
            STATUS      current
            DESCRIPTION
                "Indicates the mirror operation of this port. The allowed values are:
                 Enabled: Frames received on the port are mirrored.
                 Disabled: Frames received on the port are not mirrored."
            ::= { ctcAclStatusEntry 8 }

        -- 1.3.6.1.4.1.4756.104.60.2.3.10.1.9
        ctcAclToCPU OBJECT-TYPE
            SYNTAX      INTEGER {
                            yes(1),
                            no(2)
                        }
            MAX-ACCESS  read-only
            STATUS      current
            DESCRIPTION
                "Forward packet that matched the specific ACE to CPU."
            ::= { ctcAclStatusEntry 9 }

        -- 1.3.6.1.4.1.4756.104.60.2.3.10.1.10
        ctcAclToCpuOnce OBJECT-TYPE
            SYNTAX      INTEGER {
                            yes(1),
                            no(2)
                        }
            MAX-ACCESS  read-only
            STATUS      current
            DESCRIPTION
                "Forward first packet that matched the specific ACE to CPU."
            ::= { ctcAclStatusEntry 10 }

        -- 1.3.6.1.4.1.4756.104.60.2.3.10.1.11
        ctcAclCounter OBJECT-TYPE
            SYNTAX      Counter32
            UNITS       "Frames"
            MAX-ACCESS  read-only
            STATUS      current
            DESCRIPTION
                "The counter indicates the number of times the ACE was hit by a frame."
            ::= { ctcAclStatusEntry 11 }

        -- 1.3.6.1.4.1.4756.104.60.2.3.10.1.12
        ctcAclConflict OBJECT-TYPE
            SYNTAX      INTEGER {
                            yes(1),
                            no(2)
                        }
            MAX-ACCESS  read-only
            STATUS      current
            DESCRIPTION
                "Indicates the hardware status of the specific ACE.
                 The specific ACE is not applied to the hardware due to hardware limitations."
            ::= { ctcAclStatusEntry 12 }


    -- 1.3.6.1.4.1.4756.104.60.2.4
    ctcDHCP OBJECT IDENTIFIER ::= { ctcSecurityNetwork 4 }

    -- 1.3.6.1.4.1.4756.104.60.2.4.1    
    ctcDhcpSnoopingMode OBJECT-TYPE
        SYNTAX      INTEGER {
                        enabled(1),
                        disabled(2)
                    }
        MAX-ACCESS  read-write
        STATUS      current
        DESCRIPTION
            "Indicates the DHCP snooping mode operation. Possible modes are:
             Enabled: Enable DHCP snooping mode operation.
                      When DHCP snooping mode operation is enabled,
                      the DHCP request messages will be forwarded to trusted ports
                      and only allow reply packets from trusted ports.
             Disabled: Disable DHCP snooping mode operation."
        ::= { ctcDHCP 1 }

    -- 1.3.6.1.4.1.4756.104.60.2.4.2
    ctcDhcpSnoopingPortConfigTable OBJECT-TYPE
        SYNTAX      SEQUENCE OF CtcDhcpSnoopingPortConfigEntry
        MAX-ACCESS  not-accessible
        STATUS      current
        DESCRIPTION
            "Configure DHCP Snooping on this table."
        ::= { ctcDHCP 2 }

    -- 1.3.6.1.4.1.4756.104.60.2.4.2.1
    ctcDhcpSnoopingPortConfigEntry OBJECT-TYPE
        SYNTAX      CtcDhcpSnoopingPortConfigEntry
        MAX-ACCESS  not-accessible
        STATUS      current
        DESCRIPTION
            "The Entry of DHCP Snooping ports."
        INDEX { ctcPortIndex }
        ::= { ctcDhcpSnoopingPortConfigTable 1 }

    CtcDhcpSnoopingPortConfigEntry ::=
        SEQUENCE {
            ctcDhcpSnoopingPortMode             INTEGER
        }

        -- 1.3.6.1.4.1.4756.104.60.2.4.2.1.1
        ctcDhcpSnoopingPortMode OBJECT-TYPE
            SYNTAX      INTEGER {
                            trusted(1),
                            untrusted(2)
                        }
            MAX-ACCESS  read-write
            STATUS      current
            DESCRIPTION
                "Indicates the DHCP snooping port mode. Possible port modes are:
                 Trusted: Configures the port as trusted source of the DHCP messages.
                 Untrusted: Configures the port as untrusted source of the DHCP messages."
            ::= { ctcDhcpSnoopingPortConfigEntry 1 }

    -- 1.3.6.1.4.1.4756.104.60.2.4.3
    ctcDhcpSnoopingPortStatisticsTable OBJECT-TYPE
        SYNTAX      SEQUENCE OF CtcDhcpSnoopingPortStatisticsEntry
        MAX-ACCESS  not-accessible
        STATUS      current
        DESCRIPTION
            "This table provides statistics for DHCP snooping."
        ::= { ctcDHCP 3 }

    -- 1.3.6.1.4.1.4756.104.60.2.4.3.1
    ctcDhcpSnoopingPortStatisticsEntry OBJECT-TYPE
        SYNTAX      CtcDhcpSnoopingPortStatisticsEntry
        MAX-ACCESS  not-accessible
        STATUS      current
        DESCRIPTION
            "The Entry of DHCP Snooping port statistics."
        INDEX { ctcPortIndex }
        ::= { ctcDhcpSnoopingPortStatisticsTable 1 }

    CtcDhcpSnoopingPortStatisticsEntry ::=
        SEQUENCE {
            ctcDhcpSnoopingPortStatisticsClear   INTEGER,
            ctcDhcpSnoopingRxDiscover            Counter32,
            ctcDhcpSnoopingRxOffer               Counter32,
            ctcDhcpSnoopingRxRequest             Counter32,
            ctcDhcpSnoopingRxDecline             Counter32,
            ctcDhcpSnoopingRxACK                 Counter32,
            ctcDhcpSnoopingRxNAK                 Counter32,
            ctcDhcpSnoopingRxRelease             Counter32,
            ctcDhcpSnoopingRxInform              Counter32,
            ctcDhcpSnoopingRxLeaseQuery          Counter32,
            ctcDhcpSnoopingRxLeaseUnassigned     Counter32,
            ctcDhcpSnoopingRxLeaseUnknown        Counter32,
            ctcDhcpSnoopingRxLeaseActive         Counter32,
            ctcDhcpSnoopingTxDiscover            Counter32,
            ctcDhcpSnoopingTxOffer               Counter32,
            ctcDhcpSnoopingTxRequest             Counter32,
            ctcDhcpSnoopingTxDecline             Counter32,
            ctcDhcpSnoopingTxACK                 Counter32,
            ctcDhcpSnoopingTxNAK                 Counter32,
            ctcDhcpSnoopingTxRelease             Counter32,
            ctcDhcpSnoopingTxInform              Counter32,
            ctcDhcpSnoopingTxLeaseQuery          Counter32,
            ctcDhcpSnoopingTxLeaseUnassigned     Counter32,
            ctcDhcpSnoopingTxLeaseUnknown        Counter32,
            ctcDhcpSnoopingTxLeaseActive         Counter32
        }

        -- 1.3.6.1.4.1.4756.104.60.2.4.3.1.1
        ctcDhcpSnoopingPortStatisticsClear OBJECT-TYPE
            SYNTAX      INTEGER {
                            trigger(1),
                            normal(2)
                        }
            MAX-ACCESS  read-write
            STATUS      current
            DESCRIPTION
                "Clears the counters for this port."
            ::= { ctcDhcpSnoopingPortStatisticsEntry 1 }

        -- 1.3.6.1.4.1.4756.104.60.2.4.3.1.2
        ctcDhcpSnoopingRxDiscover OBJECT-TYPE
            SYNTAX      Counter32
            UNITS       "Packets"
            MAX-ACCESS  read-only
            STATUS      current
            DESCRIPTION
                "The number of discover(option 53 with value 1) packets received."
            ::= { ctcDhcpSnoopingPortStatisticsEntry 2 }

        -- 1.3.6.1.4.1.4756.104.60.2.4.3.1.3
        ctcDhcpSnoopingRxOffer OBJECT-TYPE
            SYNTAX      Counter32
            UNITS       "Packets"
            MAX-ACCESS  read-only
            STATUS      current
            DESCRIPTION
                "The number of offer(option 53 with value 2) packets received."
            ::= { ctcDhcpSnoopingPortStatisticsEntry 3 }

        -- 1.3.6.1.4.1.4756.104.60.2.4.3.1.4
        ctcDhcpSnoopingRxRequest OBJECT-TYPE
            SYNTAX      Counter32
            UNITS       "Packets"
            MAX-ACCESS  read-only
            STATUS      current
            DESCRIPTION
                "The number of request(option 53 with value 3) packets received."
            ::= { ctcDhcpSnoopingPortStatisticsEntry 4 }

        -- 1.3.6.1.4.1.4756.104.60.2.4.3.1.5
        ctcDhcpSnoopingRxDecline OBJECT-TYPE
            SYNTAX      Counter32
            UNITS       "Packets"
            MAX-ACCESS  read-only
            STATUS      current
            DESCRIPTION
                "The number of decline(option 53 with value 4) packets received."
            ::= { ctcDhcpSnoopingPortStatisticsEntry 5 }

        -- 1.3.6.1.4.1.4756.104.60.2.4.3.1.6
        ctcDhcpSnoopingRxACK OBJECT-TYPE
            SYNTAX      Counter32
            UNITS       "Packets"
            MAX-ACCESS  read-only
            STATUS      current
            DESCRIPTION
                "The number of ACK(option 53 with value 5) packets received."
            ::= { ctcDhcpSnoopingPortStatisticsEntry 6 }

        -- 1.3.6.1.4.1.4756.104.60.2.4.3.1.7
        ctcDhcpSnoopingRxNAK OBJECT-TYPE
            SYNTAX      Counter32
            UNITS       "Packets"
            MAX-ACCESS  read-only
            STATUS      current
            DESCRIPTION
                "The number of NAK(option 53 with value 6) packets received."
            ::= { ctcDhcpSnoopingPortStatisticsEntry 7 }

        -- 1.3.6.1.4.1.4756.104.60.2.4.3.1.8
        ctcDhcpSnoopingRxRelease OBJECT-TYPE
            SYNTAX      Counter32
            UNITS       "Packets"
            MAX-ACCESS  read-only
            STATUS      current
            DESCRIPTION
                "The number of release(option 53 with value 7) packets received."
            ::= { ctcDhcpSnoopingPortStatisticsEntry 8 }

        -- 1.3.6.1.4.1.4756.104.60.2.4.3.1.9
        ctcDhcpSnoopingRxInform OBJECT-TYPE
            SYNTAX      Counter32
            UNITS       "Packets"
            MAX-ACCESS  read-only
            STATUS      current
            DESCRIPTION
                "The number of inform(option 53 with value 8) packets received."
            ::= { ctcDhcpSnoopingPortStatisticsEntry 9 }

        -- 1.3.6.1.4.1.4756.104.60.2.4.3.1.10
        ctcDhcpSnoopingRxLeaseQuery OBJECT-TYPE
            SYNTAX      Counter32
            UNITS       "Packets"
            MAX-ACCESS  read-only
            STATUS      current
            DESCRIPTION
                "The number of lease query(option 53 with value 9) packets received."
            ::= { ctcDhcpSnoopingPortStatisticsEntry 10 }

        -- 1.3.6.1.4.1.4756.104.60.2.4.3.1.11
        ctcDhcpSnoopingRxLeaseUnassigned OBJECT-TYPE
            SYNTAX      Counter32
            UNITS       "Packets"
            MAX-ACCESS  read-only
            STATUS      current
            DESCRIPTION
                "The number of lease unassigned(option 53 with value 10) packets received."
            ::= { ctcDhcpSnoopingPortStatisticsEntry 11 }

        -- 1.3.6.1.4.1.4756.104.60.2.4.3.1.12
        ctcDhcpSnoopingRxLeaseUnknown OBJECT-TYPE
            SYNTAX      Counter32
            UNITS       "Packets"
            MAX-ACCESS  read-only
            STATUS      current
            DESCRIPTION
                "The number of lease unknown(option 53 with value 11) packets received."
            ::= { ctcDhcpSnoopingPortStatisticsEntry 12 }

        -- 1.3.6.1.4.1.4756.104.60.2.4.3.1.13
        ctcDhcpSnoopingRxLeaseActive OBJECT-TYPE
            SYNTAX      Counter32
            UNITS       "Packets"
            MAX-ACCESS  read-only
            STATUS      current
            DESCRIPTION
                "The number of lease active(option 53 with value 12) packets received."
            ::= { ctcDhcpSnoopingPortStatisticsEntry 13 }

        -- 1.3.6.1.4.1.4756.104.60.2.4.3.1.14
        ctcDhcpSnoopingTxDiscover OBJECT-TYPE
            SYNTAX      Counter32
            UNITS       "Packets"
            MAX-ACCESS  read-only
            STATUS      current
            DESCRIPTION
                "The number of discover(option 53 with value 1) packets transmitted."
            ::= { ctcDhcpSnoopingPortStatisticsEntry 14 }

        -- 1.3.6.1.4.1.4756.104.60.2.4.3.1.15
        ctcDhcpSnoopingTxOffer OBJECT-TYPE
            SYNTAX      Counter32
            UNITS       "Packets"
            MAX-ACCESS  read-only
            STATUS      current
            DESCRIPTION
                "The number of offer(option 53 with value 2) packets transmitted."
            ::= { ctcDhcpSnoopingPortStatisticsEntry 15 }

        -- 1.3.6.1.4.1.4756.104.60.2.4.3.1.16
        ctcDhcpSnoopingTxRequest OBJECT-TYPE
            SYNTAX      Counter32
            UNITS       "Packets"
            MAX-ACCESS  read-only
            STATUS      current
            DESCRIPTION
                "The number of request(option 53 with value 3) packets transmitted."
            ::= { ctcDhcpSnoopingPortStatisticsEntry 16 }

        -- 1.3.6.1.4.1.4756.104.60.2.4.3.1.17
        ctcDhcpSnoopingTxDecline OBJECT-TYPE
            SYNTAX      Counter32
            UNITS       "Packets"
            MAX-ACCESS  read-only
            STATUS      current
            DESCRIPTION
                "The number of decline(option 53 with value 4) packets transmitted."
            ::= { ctcDhcpSnoopingPortStatisticsEntry 17 }

        -- 1.3.6.1.4.1.4756.104.60.2.4.3.1.18
        ctcDhcpSnoopingTxACK OBJECT-TYPE
            SYNTAX      Counter32
            UNITS       "Packets"
            MAX-ACCESS  read-only
            STATUS      current
            DESCRIPTION
                "The number of ACK(option 53 with value 5) packets transmitted."
            ::= { ctcDhcpSnoopingPortStatisticsEntry 18 }

        -- 1.3.6.1.4.1.4756.104.60.2.4.3.1.19
        ctcDhcpSnoopingTxNAK OBJECT-TYPE
            SYNTAX      Counter32
            UNITS       "Packets"
            MAX-ACCESS  read-only
            STATUS      current
            DESCRIPTION
                "The number of NAK(option 53 with value 6) packets transmitted."
            ::= { ctcDhcpSnoopingPortStatisticsEntry 19 }

        -- 1.3.6.1.4.1.4756.104.60.2.4.3.1.20
        ctcDhcpSnoopingTxRelease OBJECT-TYPE
            SYNTAX      Counter32
            UNITS       "Packets"
            MAX-ACCESS  read-only
            STATUS      current
            DESCRIPTION
                "The number of release(option 53 with value 7) packets transmitted."
            ::= { ctcDhcpSnoopingPortStatisticsEntry 20 }

        -- 1.3.6.1.4.1.4756.104.60.2.4.3.1.21
        ctcDhcpSnoopingTxInform OBJECT-TYPE
            SYNTAX      Counter32
            UNITS       "Packets"
            MAX-ACCESS  read-only
            STATUS      current
            DESCRIPTION
                "The number of inform(option 53 with value 8) packets transmitted."
            ::= { ctcDhcpSnoopingPortStatisticsEntry 21 }

        -- 1.3.6.1.4.1.4756.104.60.2.4.3.1.22
        ctcDhcpSnoopingTxLeaseQuery OBJECT-TYPE
            SYNTAX      Counter32
            UNITS       "Packets"
            MAX-ACCESS  read-only
            STATUS      current
            DESCRIPTION
                "The number of lease query(option 53 with value 9) packets transmitted."
            ::= { ctcDhcpSnoopingPortStatisticsEntry 22 }

        -- 1.3.6.1.4.1.4756.104.60.2.4.3.1.23
        ctcDhcpSnoopingTxLeaseUnassigned OBJECT-TYPE
            SYNTAX      Counter32
            UNITS       "Packets"
            MAX-ACCESS  read-only
            STATUS      current
            DESCRIPTION
                "The number of lease unassigned(option 53 with value 10) packets transmitted."
            ::= { ctcDhcpSnoopingPortStatisticsEntry 23 }

        -- 1.3.6.1.4.1.4756.104.60.2.4.3.1.24
        ctcDhcpSnoopingTxLeaseUnknown OBJECT-TYPE
            SYNTAX      Counter32
            UNITS       "Packets"
            MAX-ACCESS  read-only
            STATUS      current
            DESCRIPTION
                "The number of lease unknown(option 53 with value 11) packets transmitted."
            ::= { ctcDhcpSnoopingPortStatisticsEntry 24 }

        -- 1.3.6.1.4.1.4756.104.60.2.4.3.1.25
        ctcDhcpSnoopingTxLeaseActive OBJECT-TYPE
            SYNTAX      Counter32
            UNITS       "Packets"
            MAX-ACCESS  read-only
            STATUS      current
            DESCRIPTION
                "The number of lease active(option 53 with value 12) packets transmitted."
            ::= { ctcDhcpSnoopingPortStatisticsEntry 25 }

    -- 1.3.6.1.4.1.4756.104.60.2.4.4    
    ctcDhcpRelayMode OBJECT-TYPE
        SYNTAX      INTEGER {
                        enabled(1),
                        disabled(2)
                    }
        MAX-ACCESS  read-write
        STATUS      current
        DESCRIPTION
            "Indicates the DHCP relay mode operation. Possible modes are:
             Enabled:Enable DHCP relay mode operation.
                     When DHCP relay mode operation is enabled,
                     the agent forwards and transfers DHCP messages between the clients
                     and the server when they are not in the same subnet domain.
                     And the DHCP broadcast message won't be flooded for security considerations.
             Disabled: Disable DHCP relay mode operation.
             Relay mode doesn't allowed enabled when 'Relay Server' is '0.0.0.0'"
        ::= { ctcDHCP 4 }

    -- 1.3.6.1.4.1.4756.104.60.2.4.5    
    ctcDhcpRelayServerIP OBJECT-TYPE
        SYNTAX      IpAddress
        MAX-ACCESS  read-write
        STATUS      current
        DESCRIPTION
            "Indicates the DHCP relay server IP address.
             A DHCP relay agent is used to forward and to transfer DHCP messages between the clients
             and the server when they are not in the same subnet domain.
             'Relay Server' doesn't allowed '0.0.0.0' when relay mode is enabled."
        ::= { ctcDHCP 5 }

    -- 1.3.6.1.4.1.4756.104.60.2.4.6    
    ctcDhcpRelayInformationMode OBJECT-TYPE
        SYNTAX      INTEGER {
                        enabled(1),
                        disabled(2)
                    }
        MAX-ACCESS  read-write
        STATUS      current
        DESCRIPTION
            "Indicates the DHCP relay information mode option operation.
             The option 82 circuit ID format as '[vlan_id][module_id][port_no]'.
             The first four characters represent the VLAN ID,
             the fifth and sixth characters are the module ID,
             and the last two characters are the port number. Possible modes are:
             Enabled: Enable DHCP relay information mode operation.
                      When DHCP relay information mode operation is enabled,
                      the agent inserts specific information (option 82) into a DHCP message when forwarding
                      to DHCP server and removes it from a DHCP message when transferring to DHCP client.
                      It only works when DHCP relay operation mode is enabled.
             Disabled: Disable DHCP relay information mode operation."
        ::= { ctcDHCP 6 }

    -- 1.3.6.1.4.1.4756.104.60.2.4.7    
    ctcDhcpRelayInformationPolicy OBJECT-TYPE
        SYNTAX      INTEGER {
                        replace(1),
                        keep(2),
                        drop(3)
                    }
        MAX-ACCESS  read-write
        STATUS      current
        DESCRIPTION
            "Indicates the DHCP relay information option policy.
             When DHCP relay information mode operation is enabled,
             if agent receives a DHCP message that already contains
             relay agent information it will enforce the policy.
             And it only works under DHCP if relay information operation mode is enabled.
             Possible policies are:
             Replace:Replace the original relay information when a DHCP message that already contains it is received.
             Keep:Keep the original relay information when a DHCP message that already contains it is received.
             Drop:Drop the package when a DHCP message that already contains relay information is received."
        ::= { ctcDHCP 7 }

    -- 1.3.6.1.4.1.4756.104.60.2.4.9
    ctcDhcpRelayStatisticsClear OBJECT-TYPE
        SYNTAX      INTEGER {
                        trigger(1),
                        normal(2)
                    }
        MAX-ACCESS  read-write
        STATUS      current
        DESCRIPTION
            "Clear all statistics."
        ::= { ctcDHCP 9 }

    -- 1.3.6.1.4.1.4756.104.60.2.4.10
    ctcDhcpRelayServerStatistics OBJECT IDENTIFIER ::= { ctcDHCP 10 }

    -- 1.3.6.1.4.1.4756.104.60.2.4.10.1
    ctcDhcpRelayServerTxToServer OBJECT-TYPE
        SYNTAX      Counter32
        UNITS       "Packets"
        MAX-ACCESS  read-only
        STATUS      current
        DESCRIPTION
            "The number of packets that are relayed from client to server."
        ::= { ctcDhcpRelayServerStatistics 1 }

    -- 1.3.6.1.4.1.4756.104.60.2.4.10.2
    ctcDhcpRelayServerTxError OBJECT-TYPE
        SYNTAX      Counter32
        UNITS       "Packets"
        MAX-ACCESS  read-only
        STATUS      current
        DESCRIPTION
            "The number of packets that resulted in errors while being sent to clients."
        ::= { ctcDhcpRelayServerStatistics 2 }

    -- 1.3.6.1.4.1.4756.104.60.2.4.10.3
    ctcDhcpRelayServerRxFromServer OBJECT-TYPE
        SYNTAX      Counter32
        UNITS       "Packets"
        MAX-ACCESS  read-only
        STATUS      current
        DESCRIPTION
            "The number of packets received from server."
        ::= { ctcDhcpRelayServerStatistics 3 }

    -- 1.3.6.1.4.1.4756.104.60.2.4.10.4
    ctcDhcpRelayServerRxMissingAgentOption OBJECT-TYPE
        SYNTAX      Counter32
        UNITS       "Packets"
        MAX-ACCESS  read-only
        STATUS      current
        DESCRIPTION
            "The number of packets received without agent information options."
        ::= { ctcDhcpRelayServerStatistics 4 }

    -- 1.3.6.1.4.1.4756.104.60.2.4.10.5
    ctcDhcpRelayServerRxMissingCircuitID OBJECT-TYPE
        SYNTAX      Counter32
        UNITS       "Packets"
        MAX-ACCESS  read-only
        STATUS      current
        DESCRIPTION
            "The number of packets received with the Circuit ID option missing."
        ::= { ctcDhcpRelayServerStatistics 5 }

    -- 1.3.6.1.4.1.4756.104.60.2.4.10.6
    ctcDhcpRelayServerRxMissingRemoteID OBJECT-TYPE
        SYNTAX      Counter32
        UNITS       "Packets"
        MAX-ACCESS  read-only
        STATUS      current
        DESCRIPTION
            "The number of packets received with the Remote ID option missing."
        ::= { ctcDhcpRelayServerStatistics 6 }

    -- 1.3.6.1.4.1.4756.104.60.2.4.10.7
    ctcDhcpRelayServerRxBadCircuitID OBJECT-TYPE
        SYNTAX      Counter32
        UNITS       "Packets"
        MAX-ACCESS  read-only
        STATUS      current
        DESCRIPTION
            "The number of packets whose Circuit ID option did not match known circuit ID."
        ::= { ctcDhcpRelayServerStatistics 7 }

    -- 1.3.6.1.4.1.4756.104.60.2.4.10.8
    ctcDhcpRelayServerRxBadRemoteID OBJECT-TYPE
        SYNTAX      Counter32
        UNITS       "Packets"
        MAX-ACCESS  read-only
        STATUS      current
        DESCRIPTION
            "The number of packets whose Remote ID option did not match known Remote ID."
        ::= { ctcDhcpRelayServerStatistics 8 }

    -- 1.3.6.1.4.1.4756.104.60.2.4.11
    ctcDhcpRelayClientStatistics OBJECT IDENTIFIER ::= { ctcDHCP 11 }

    -- 1.3.6.1.4.1.4756.104.60.2.4.11.1
    ctcDhcpRelayClientTxToClient OBJECT-TYPE
        SYNTAX      Counter32
        UNITS       "Packets"
        MAX-ACCESS  read-only
        STATUS      current
        DESCRIPTION
            "The number of relayed packets from server to client."
        ::= { ctcDhcpRelayClientStatistics 1 }

    -- 1.3.6.1.4.1.4756.104.60.2.4.11.2
    ctcDhcpRelayClientTxError OBJECT-TYPE
        SYNTAX      Counter32
        UNITS       "Packets"
        MAX-ACCESS  read-only
        STATUS      current
        DESCRIPTION
            "The number of packets that resulted in error while being sent to servers."
        ::= { ctcDhcpRelayClientStatistics 2 }

    -- 1.3.6.1.4.1.4756.104.60.2.4.11.3
    ctcDhcpRelayClientRxFromClient OBJECT-TYPE
        SYNTAX      Counter32
        UNITS       "Packets"
        MAX-ACCESS  read-only
        STATUS      current
        DESCRIPTION
            "The number of received packets from server."
        ::= { ctcDhcpRelayClientStatistics 3 }

    -- 1.3.6.1.4.1.4756.104.60.2.4.11.4
     ctcDhcpRelayClientRxAgentOption OBJECT-TYPE
        SYNTAX      Counter32
        UNITS       "Packets"
        MAX-ACCESS  read-only
        STATUS      current
        DESCRIPTION
            "The number of received packets with relay agent information option."
        ::= { ctcDhcpRelayClientStatistics 4 }

    -- 1.3.6.1.4.1.4756.104.60.2.4.11.5
    ctcDhcpRelayClientReplaceAgentOption OBJECT-TYPE
        SYNTAX      Counter32
        UNITS       "Packets"
        MAX-ACCESS  read-only
        STATUS      current
        DESCRIPTION
            "The number of packets which were replaced with relay agent information option."
        ::= { ctcDhcpRelayClientStatistics 5 }

    -- 1.3.6.1.4.1.4756.104.60.2.4.11.6
    ctcDhcpRelayClientKeepAgentOption OBJECT-TYPE
        SYNTAX      Counter32
        UNITS       "Packets"
        MAX-ACCESS  read-only
        STATUS      current
        DESCRIPTION
            "The number of packets whose relay agent information was retained."
        ::= { ctcDhcpRelayClientStatistics 6 }

    -- 1.3.6.1.4.1.4756.104.60.2.4.11.7
    ctcDhcpRelayClientDropAgentOption OBJECT-TYPE
        SYNTAX      Counter32
        UNITS       "Packets"
        MAX-ACCESS  read-only
        STATUS      current
        DESCRIPTION
            "The number of packets that were dropped which were received with relay agent information."
        ::= { ctcDhcpRelayClientStatistics 7 }


    
    -- 1.3.6.1.4.1.4756.104.60.2.5
    ctcIpSourceGuard OBJECT IDENTIFIER ::= { ctcSecurityNetwork 5 }

    -- 1.3.6.1.4.1.4756.104.60.2.5.1    
    ctcIpSourceGuardMode OBJECT-TYPE
        SYNTAX      INTEGER {
                        enabled(1),
                        disabled(2)
                    }
        MAX-ACCESS  read-write
        STATUS      current
        DESCRIPTION
            "Enable the Global IP Source Guard or disable the Global IP Source Guard."
        ::= { ctcIpSourceGuard 1 }

    -- 1.3.6.1.4.1.4756.104.60.2.5.2    
    ctcIpTranslateDynamicToStatic OBJECT-TYPE
        SYNTAX      INTEGER {
                        trigger(1),
                        normal(2)
                    }
        MAX-ACCESS  read-write
        STATUS      current
        DESCRIPTION
            "To translate all dynamic IP Source Guard entries to static entries."
        ::= { ctcIpSourceGuard 2 }

    -- 1.3.6.1.4.1.4756.104.60.2.5.3
    ctcIpSourceGuardPortConfigTable OBJECT-TYPE
        SYNTAX      SEQUENCE OF CtcIpSourceGuardPortConfigEntry
        MAX-ACCESS  not-accessible
        STATUS      current
        DESCRIPTION
            "This table provides IP Source Guard port configuration."
        ::= { ctcIpSourceGuard 3 }

    -- 1.3.6.1.4.1.4756.104.60.2.5.3.1
    ctcIpSourceGuardPortConfigEntry OBJECT-TYPE
        SYNTAX      CtcIpSourceGuardPortConfigEntry
        MAX-ACCESS  not-accessible
        STATUS      current
        DESCRIPTION
            "The Entry of IP Source Guard ports."
        INDEX { ctcPortIndex }
        ::= { ctcIpSourceGuardPortConfigTable 1 }

    CtcIpSourceGuardPortConfigEntry ::=
        SEQUENCE {
            ctcIpSourceGuardPortMode             INTEGER,
            ctcIpSourceGuardMaxDynamicClients    INTEGER
        }

        -- 1.3.6.1.4.1.4756.104.60.2.5.3.1.1
        ctcIpSourceGuardPortMode OBJECT-TYPE
            SYNTAX      INTEGER {
                            enable(1),
                            disable(2)
                        }
            MAX-ACCESS  read-write
            STATUS      current
            DESCRIPTION
                "Specify IP Source Guard is enabled on which ports.
                 Only when both Global Mode and Port Mode on a given port are enabled,
                 IP Source Guard is enabled on this given port."
            ::= { ctcIpSourceGuardPortConfigEntry 1 }

        -- 1.3.6.1.4.1.4756.104.60.2.5.3.1.2
        ctcIpSourceGuardMaxDynamicClients OBJECT-TYPE
            SYNTAX      INTEGER {
                            unlimited(1),
                            limited0(2),
                            limited1(3),
                            limited2(4)
                        }
            MAX-ACCESS  read-write
            STATUS      current
            DESCRIPTION
                "Specify the maximum number of dynamic clients that can be learned on given port.
                 This value can be 0, 1, 2 or unlimited.
                 If the port mode is enabled and the value of max dynamic client is equal to 0,
                 it means only allow the IP packets forwarding that are matched in static entries
                 on the specific port."
            ::= { ctcIpSourceGuardPortConfigEntry 2 }

    -- 1.3.6.1.4.1.4756.104.60.2.5.4
    ctcAddStaticIpSourceGuard OBJECT-TYPE
        SYNTAX      DisplayString
        MAX-ACCESS  read-write
        STATUS      current
        DESCRIPTION                                  
            "Add a new entry to the Static IP Source Guard table.
             Specify the Port, VLAN ID, IP address, and MAC address for the new entry.
             Syntax: <port_no> <vid> <allowed_ip> <allowed_mac> 
             The Static ARP Inspection table can support maximum 64 entries per port."
        ::= { ctcIpSourceGuard 4 }

    -- 1.3.6.1.4.1.4756.104.60.2.5.5
    ctcDeleteStaticIpSourceGuard OBJECT-TYPE
        SYNTAX      DisplayString
        MAX-ACCESS  read-write
        STATUS      current
        DESCRIPTION
            "Delete a Static IP Source Guard from table.
             Syntax: <port_no> <vid> <allowed_ip> <allowed_mac>"
        ::= { ctcIpSourceGuard 5 }

    -- 1.3.6.1.4.1.4756.104.60.2.5.6
    ctcStaticIpSourceGuardTable OBJECT-TYPE
        SYNTAX      SEQUENCE OF CtcStaticIpSourceGuardEntry
        MAX-ACCESS  not-accessible
        STATUS      current
        DESCRIPTION
            "This table provides Static IP Source Guard status."
        ::= { ctcIpSourceGuard 6 }

    -- 1.3.6.1.4.1.4756.104.60.2.5.6.1
    ctcStaticIpSourceGuardEntry OBJECT-TYPE
        SYNTAX      CtcStaticIpSourceGuardEntry
        MAX-ACCESS  not-accessible
        STATUS      current
        DESCRIPTION
            "The Entry of Static IP Source Guard."
        INDEX { ctcStaticIpSourceGuardIndex }
        ::= { ctcStaticIpSourceGuardTable 1 }

    CtcStaticIpSourceGuardEntry ::=
        SEQUENCE {
            ctcStaticIpSourceGuardIndex      Integer32,
            ctcStaticIpSourceGuardPort       Integer32,
            ctcStaticIpSourceGuardVlanID     Integer32,
            ctcStaticIpSourceGuardIP         IpAddress,
            ctcStaticIpSourceGuardMAC        MacAddress                
        }

        -- 1.3.6.1.4.1.4756.104.60.2.5.6.1.1
        ctcStaticIpSourceGuardIndex OBJECT-TYPE
            SYNTAX      Integer32 (1..112)
            MAX-ACCESS  read-only
            STATUS      current
            DESCRIPTION
                "The index of Static IP Source Guard entries."
            ::= { ctcStaticIpSourceGuardEntry 1 }

        -- 1.3.6.1.4.1.4756.104.60.2.5.6.1.2
        ctcStaticIpSourceGuardPort OBJECT-TYPE
            SYNTAX      Integer32 (1..6)
            MAX-ACCESS  read-only
            STATUS      current
            DESCRIPTION
                "The logical port number of the entry."
            ::= { ctcStaticIpSourceGuardEntry 2 }

        -- 1.3.6.1.4.1.4756.104.60.2.5.6.1.3
        ctcStaticIpSourceGuardVlanID OBJECT-TYPE
            SYNTAX      Integer32 (1..4095)
            MAX-ACCESS  read-only
            STATUS      current
            DESCRIPTION
                "The VLAN ID of the entry."
            ::= { ctcStaticIpSourceGuardEntry 3 }

        -- 1.3.6.1.4.1.4756.104.60.2.5.6.1.4
        ctcStaticIpSourceGuardIP OBJECT-TYPE
            SYNTAX      IpAddress
            MAX-ACCESS  read-only
            STATUS      current
            DESCRIPTION
                "Allowed Source IP address."
            ::= { ctcStaticIpSourceGuardEntry 4 }

        -- 1.3.6.1.4.1.4756.104.60.2.5.6.1.5
        ctcStaticIpSourceGuardMAC OBJECT-TYPE
            SYNTAX      MacAddress
            MAX-ACCESS  read-only
            STATUS      current
            DESCRIPTION
                "Allowed Source MAC address."
            ::= { ctcStaticIpSourceGuardEntry 5 }

    -- 1.3.6.1.4.1.4756.104.60.2.5.6
    ctcDynamicIpSourceGuardTable OBJECT-TYPE
        SYNTAX      SEQUENCE OF CtcDynamicIpSourceGuardEntry
        MAX-ACCESS  not-accessible
        STATUS      current
        DESCRIPTION
            "This table provides Dynamic IP Source Guard status."
        ::= { ctcIpSourceGuard 7 }

    -- 1.3.6.1.4.1.4756.104.60.2.5.7.1
    ctcDynamicIpSourceGuardEntry OBJECT-TYPE
        SYNTAX      CtcDynamicIpSourceGuardEntry
        MAX-ACCESS  not-accessible
        STATUS      current
        DESCRIPTION
            "The Entry of Dynamic IP Source Guard."
        INDEX { ctcDynamicIpSourceGuardIndex }
        ::= { ctcDynamicIpSourceGuardTable 1 }

    CtcDynamicIpSourceGuardEntry ::=
        SEQUENCE {
            ctcDynamicIpSourceGuardIndex     Integer32,
            ctcDynamicIpSourceGuardPort      Integer32,
            ctcDynamicIpSourceGuardVlanID    Integer32,
            ctcDynamicIpSourceGuardIP        IpAddress,
            ctcDynamicIpSourceGuardMAC       MacAddress   
        }

        -- 1.3.6.1.4.1.4756.104.60.2.5.7.1.1
        ctcDynamicIpSourceGuardIndex OBJECT-TYPE
            SYNTAX      Integer32 (1..112)
            MAX-ACCESS  read-only
            STATUS      current
            DESCRIPTION
                "The index of Dynamic IP Source Guard entries."
            ::= { ctcDynamicIpSourceGuardEntry 1 }

        -- 1.3.6.1.4.1.4756.104.60.2.5.7.1.2
        ctcDynamicIpSourceGuardPort OBJECT-TYPE
            SYNTAX      Integer32 (1..6)
            MAX-ACCESS  read-only
            STATUS      current
            DESCRIPTION
                "The logical port number of the entry."
            ::= { ctcDynamicIpSourceGuardEntry 2 }

        -- 1.3.6.1.4.1.4756.104.60.2.5.7.1.3
        ctcDynamicIpSourceGuardVlanID OBJECT-TYPE
            SYNTAX      Integer32 (1..4095)
            MAX-ACCESS  read-only
            STATUS      current
            DESCRIPTION
                "The VLAN ID the IP traffic is permitted."
            ::= { ctcDynamicIpSourceGuardEntry 3 }

        -- 1.3.6.1.4.1.4756.104.60.2.5.7.1.4
        ctcDynamicIpSourceGuardIP OBJECT-TYPE
            SYNTAX      IpAddress
            MAX-ACCESS  read-only
            STATUS      current
            DESCRIPTION
                "User IP address of the entry."
            ::= { ctcDynamicIpSourceGuardEntry 4 }

        -- 1.3.6.1.4.1.4756.104.60.2.5.7.1.5
        ctcDynamicIpSourceGuardMAC OBJECT-TYPE
            SYNTAX      MacAddress
            MAX-ACCESS  read-only
            STATUS      current
            DESCRIPTION
                "User MAC address of the entry."
            ::= { ctcDynamicIpSourceGuardEntry 5 }

    
    -- 1.3.6.1.4.1.4756.104.60.2.6
    ctcArpInspection OBJECT IDENTIFIER ::= { ctcSecurityNetwork 6 }

    -- 1.3.6.1.4.1.4756.104.60.2.6.1    
    ctcArpInspectionMode OBJECT-TYPE
        SYNTAX      INTEGER {
                        enabled(1),
                        disabled(2)
                    }
        MAX-ACCESS  read-write
        STATUS      current
        DESCRIPTION
            "Enable the Global ARP Inspection or disable the Global ARP Inspection."
        ::= { ctcArpInspection 1 }

    -- 1.3.6.1.4.1.4756.104.60.2.6.2    
    ctcArpTranslateDynamicToStatic OBJECT-TYPE
        SYNTAX      INTEGER {
                        trigger(1),
                        normal(2)
                    }
        MAX-ACCESS  read-write
        STATUS      current
        DESCRIPTION
            "To translate all dynamic entries to static entries."
        ::= { ctcArpInspection 2 }

    -- 1.3.6.1.4.1.4756.104.60.2.6.3
    ctcArpInspectionPortConfigTable OBJECT-TYPE
        SYNTAX      SEQUENCE OF CtcArpInspectionPortConfigEntry
        MAX-ACCESS  not-accessible
        STATUS      current
        DESCRIPTION
            "This table provides ARP Inspection port configuration."
        ::= { ctcArpInspection 3 }

    -- 1.3.6.1.4.1.4756.104.60.2.6.3.1
    ctcArpInspectionPortConfigEntry OBJECT-TYPE
        SYNTAX      CtcArpInspectionPortConfigEntry
        MAX-ACCESS  not-accessible
        STATUS      current
        DESCRIPTION
            "The Entry of ARP Inspection ports."
        INDEX { ctcPortIndex }
        ::= { ctcArpInspectionPortConfigTable 1 }

    CtcArpInspectionPortConfigEntry ::=
        SEQUENCE {
            ctcArpInspectionPortMode         INTEGER    
        }

        -- 1.3.6.1.4.1.4756.104.60.2.6.3.1.1
        ctcArpInspectionPortMode OBJECT-TYPE
            SYNTAX      INTEGER {
                            enable(1),
                            disable(2)
                        }
            MAX-ACCESS  read-write
            STATUS      current
            DESCRIPTION
                "Specify ARP Inspection is enabled on this port.
                 Only when both Global Mode and Port Mode on a given port are enabled,
                 ARP Inspection is enabled on this given port."
            ::= { ctcArpInspectionPortConfigEntry 1 }

    -- 1.3.6.1.4.1.4756.104.60.2.6.4
    ctcAddStaticArpInspection OBJECT-TYPE
        SYNTAX      DisplayString
        MAX-ACCESS  read-write
        STATUS      current
        DESCRIPTION                                  
            "Add a new entry to the Static ARP Inspection table.
             Specify the Port, VLAN ID, MAC address, and IP address for the new entry.
             Syntax: <port_no> <vid> <allowed_mac> <allowed_ip> 
             The Static ARP Inspection table can support maximum 64 entries per port."
        ::= { ctcArpInspection 4 }

    -- 1.3.6.1.4.1.4756.104.60.2.6.5
    ctcDeleteStaticArpInspection OBJECT-TYPE
        SYNTAX      DisplayString
        MAX-ACCESS  read-write
        STATUS      current
        DESCRIPTION
            "Delete a Static ARP Inspection from table.
             Syntax: <port_no> <vid> <allowed_mac> <allowed_ip>"
        ::= { ctcArpInspection 5 }

    -- 1.3.6.1.4.1.4756.104.60.2.6.6
    ctcStaticArpInspectionTable OBJECT-TYPE
        SYNTAX      SEQUENCE OF CtcStaticArpInspectionEntry
        MAX-ACCESS  not-accessible
        STATUS      current
        DESCRIPTION
            "This table provides Static ARP Inspection status."
        ::= { ctcArpInspection 6 }

    -- 1.3.6.1.4.1.4756.104.60.2.6.6.1
    ctcStaticArpInspectionEntry OBJECT-TYPE
        SYNTAX      CtcStaticArpInspectionEntry
        MAX-ACCESS  not-accessible
        STATUS      current
        DESCRIPTION
            "The Entry of Static ARP Inspection."
        INDEX { ctcStaticArpInspectionIndex }
        ::= { ctcStaticArpInspectionTable 1 }

    CtcStaticArpInspectionEntry ::=
        SEQUENCE {
            ctcStaticArpInspectionIndex      Integer32,
            ctcStaticArpInspectionPort       Integer32,
            ctcStaticArpInspectionVlanID     Integer32,
            ctcStaticArpInspectionMAC        MacAddress,
            ctcStaticArpInspectionIP         IpAddress    
        }

        -- 1.3.6.1.4.1.4756.104.60.2.6.6.1.1
        ctcStaticArpInspectionIndex OBJECT-TYPE
            SYNTAX      Integer32 (1..256)
            MAX-ACCESS  read-only
            STATUS      current
            DESCRIPTION
                "The index of Static ARP Inspection entries."
            ::= { ctcStaticArpInspectionEntry 1 }

        -- 1.3.6.1.4.1.4756.104.60.2.6.6.1.2
        ctcStaticArpInspectionPort OBJECT-TYPE
            SYNTAX      Integer32 (1..6)
            MAX-ACCESS  read-only
            STATUS      current
            DESCRIPTION
                "The logical port number of the entry."
            ::= { ctcStaticArpInspectionEntry 2 }

        -- 1.3.6.1.4.1.4756.104.60.2.6.6.1.3
        ctcStaticArpInspectionVlanID OBJECT-TYPE
            SYNTAX      Integer32 (1..4095)
            MAX-ACCESS  read-only
            STATUS      current
            DESCRIPTION
                "The VLAN ID of the entry."
            ::= { ctcStaticArpInspectionEntry 3 }

        -- 1.3.6.1.4.1.4756.104.60.2.6.6.1.4
        ctcStaticArpInspectionMAC OBJECT-TYPE
            SYNTAX      MacAddress
            MAX-ACCESS  read-only
            STATUS      current
            DESCRIPTION
                "Allowed Source MAC address in ARP request packets."
            ::= { ctcStaticArpInspectionEntry 4 }

        -- 1.3.6.1.4.1.4756.104.60.2.6.6.1.5
        ctcStaticArpInspectionIP OBJECT-TYPE
            SYNTAX      IpAddress
            MAX-ACCESS  read-only
            STATUS      current
            DESCRIPTION
                "Allowed Source IP address in ARP request packets."
            ::= { ctcStaticArpInspectionEntry 5 }

    -- 1.3.6.1.4.1.4756.104.60.2.6.6
    ctcDynamicArpInspectionTable OBJECT-TYPE
        SYNTAX      SEQUENCE OF CtcDynamicArpInspectionEntry
        MAX-ACCESS  not-accessible
        STATUS      current
        DESCRIPTION
            "This table provides Dynamic ARP Inspection status."
        ::= { ctcArpInspection 7 }

    -- 1.3.6.1.4.1.4756.104.60.2.6.7.1
    ctcDynamicArpInspectionEntry OBJECT-TYPE
        SYNTAX      CtcDynamicArpInspectionEntry
        MAX-ACCESS  not-accessible
        STATUS      current
        DESCRIPTION
            "The Entry of Dynamic ARP Inspection."
        INDEX { ctcDynamicArpInspectionIndex }
        ::= { ctcDynamicArpInspectionTable 1 }

    CtcDynamicArpInspectionEntry ::=
        SEQUENCE {
            ctcDynamicArpInspectionIndex     Integer32,
            ctcDynamicArpInspectionPort      Integer32,
            ctcDynamicArpInspectionVlanID    Integer32,
            ctcDynamicArpInspectionMAC       MacAddress,
            ctcDynamicArpInspectionIP        IpAddress    
        }

        -- 1.3.6.1.4.1.4756.104.60.2.6.7.1.1
        ctcDynamicArpInspectionIndex OBJECT-TYPE
            SYNTAX      Integer32 (1..256)
            MAX-ACCESS  read-only
            STATUS      current
            DESCRIPTION
                "The index of Dynamic ARP Inspection entries."
            ::= { ctcDynamicArpInspectionEntry 1 }

        -- 1.3.6.1.4.1.4756.104.60.2.6.7.1.2
        ctcDynamicArpInspectionPort OBJECT-TYPE
            SYNTAX      Integer32 (1..6)
            MAX-ACCESS  read-only
            STATUS      current
            DESCRIPTION
                "The logical port number of the entry."
            ::= { ctcDynamicArpInspectionEntry 2 }

        -- 1.3.6.1.4.1.4756.104.60.2.6.7.1.3
        ctcDynamicArpInspectionVlanID OBJECT-TYPE
            SYNTAX      Integer32 (1..4095)
            MAX-ACCESS  read-only
            STATUS      current
            DESCRIPTION
                "The VLAN ID in which the ARP traffic is permitted."
            ::= { ctcDynamicArpInspectionEntry 3 }

        -- 1.3.6.1.4.1.4756.104.60.2.6.7.1.4
        ctcDynamicArpInspectionMAC OBJECT-TYPE
            SYNTAX      MacAddress
            MAX-ACCESS  read-only
            STATUS      current
            DESCRIPTION
                "User MAC address of the entry."
            ::= { ctcDynamicArpInspectionEntry 4 }

        -- 1.3.6.1.4.1.4756.104.60.2.6.7.1.5
        ctcDynamicArpInspectionIP OBJECT-TYPE
            SYNTAX      IpAddress
            MAX-ACCESS  read-only
            STATUS      current
            DESCRIPTION
                "User IP address of the entry."
            ::= { ctcDynamicArpInspectionEntry 5 }


    -- 1.3.6.1.4.1.4756.104.60.3
    ctcSecurityAAA OBJECT IDENTIFIER ::= { ctcSecurity 3 }

    -- 1.3.6.1.4.1.4756.104.60.3.1    
    ctcAaaServerTimeout OBJECT-TYPE
        SYNTAX      Integer32 (3..3600)
        UNITS       "Seconds"
        MAX-ACCESS  read-write
        STATUS      current
        DESCRIPTION
            "The Timeout, which can be set to a number between 3 and 3600 seconds,
             is the maximum time to wait for a reply from a server.
             If the server does not reply within this timeframe,
             we will consider it to be dead and continue with the next enabled server (if any).
             RADIUS servers are using the UDP protocol, which is unreliable by design.
             In order to cope with lost frames,
             the timeout interval is divided into 3 subintervals of equal length.
             If a reply is not received within the subinterval,
             the request is transmitted again.
             This algorithm causes the RADIUS server to be queried up to 3 times before
             it is considered to be dead."
        ::= { ctcSecurityAAA 1 }

    -- 1.3.6.1.4.1.4756.104.60.3.2    
    ctcAaaServerDeadTime OBJECT-TYPE
        SYNTAX      Integer32 (0..3600)
        UNITS       "Seconds"
        MAX-ACCESS  read-write
        STATUS      current
        DESCRIPTION
            "The Dead Time, which can be set to a number between 0 and 3600 seconds,
             is the period during which the switch will not send new requests to
             a server that has failed to respond to a previous request.
             This will stop the switch from continually trying to
             contact a server that it has already determined as dead.
             Setting the Dead Time to a value greater than 0(zero) will enable this feature,
             but only if more than one server has been configured."
        ::= { ctcSecurityAAA 2 }

    -- 1.3.6.1.4.1.4756.104.60.3.3
    ctcAuthServerConfigTable OBJECT-TYPE
        SYNTAX      SEQUENCE OF CtcAuthServerConfigEntry
        MAX-ACCESS  not-accessible
        STATUS      current
        DESCRIPTION
            "The table allows you to configure the Authentication Servers."
        ::= { ctcSecurityAAA 3 }

    -- 1.3.6.1.4.1.4756.104.60.3.3.1
    ctcAuthServerConfigEntry OBJECT-TYPE
        SYNTAX      CtcAuthServerConfigEntry
        MAX-ACCESS  not-accessible
        STATUS      current
        DESCRIPTION
            "The Entry of the Authentication Server configuration."
        INDEX { ctcAuthServerIndex }
        ::= { ctcAuthServerConfigTable 1 }

    CtcAuthServerConfigEntry ::=
        SEQUENCE {
            ctcAuthServerIndex               Integer32,
            ctcRadiusAuthEnabled             TruthValue,
            ctcRadiusAuthServerAddress       DisplayString,
            ctcRadiusAuthServerPort          Integer32,
            ctcRadiusAuthSecret              DisplayString,
            ctcRadiusAccountingEnabled       TruthValue,
            ctcRadiusAccountingServerAddress DisplayString,
            ctcRadiusAccountingServerPort    Integer32,
            ctcRadiusAccountingSecret        DisplayString,
            ctcTacacsPlusAuthEnabled         TruthValue,
            ctcTacacsPlusAuthServerAddress   DisplayString,
            ctcTacacsPlusAuthServerPort      Integer32,
            ctcTacacsPlusAuthSecret          DisplayString
        }

        -- 1.3.6.1.4.1.4756.104.60.3.3.1.1
        ctcAuthServerIndex OBJECT-TYPE
            SYNTAX      Integer32 (1..5)
            MAX-ACCESS  read-only
            STATUS      current
            DESCRIPTION
                "The Authentication Server number."
            ::= { ctcAuthServerConfigEntry 1 }

        -- 1.3.6.1.4.1.4756.104.60.3.3.1.2
        ctcRadiusAuthEnabled OBJECT-TYPE
            SYNTAX      TruthValue
            MAX-ACCESS  read-write
            STATUS      current
            DESCRIPTION
                "Enable the RADIUS Authentication Server."
            ::= { ctcAuthServerConfigEntry 2 }

        -- 1.3.6.1.4.1.4756.104.60.3.3.1.3
        ctcRadiusAuthServerAddress OBJECT-TYPE
            SYNTAX      DisplayString
            MAX-ACCESS  read-write
            STATUS      current
            DESCRIPTION
                "The IP address or hostname of the RADIUS Authentication Server.
                 IP address is expressed in dotted decimal notation."
            ::= { ctcAuthServerConfigEntry 3 }

        -- 1.3.6.1.4.1.4756.104.60.3.3.1.4
        ctcRadiusAuthServerPort OBJECT-TYPE
            SYNTAX      Integer32 (0..65535)
            MAX-ACCESS  read-write
            STATUS      current
            DESCRIPTION
                "The UDP port to use on the RADIUS Authentication Server.
                 If the port is set to 0(zero),
                 the default port(1812) is used on the RADIUS Authentication Server."
            ::= { ctcAuthServerConfigEntry 4 }

        -- 1.3.6.1.4.1.4756.104.60.3.3.1.5
        ctcRadiusAuthSecret OBJECT-TYPE
            SYNTAX      DisplayString
            MAX-ACCESS  read-write
            STATUS      current
            DESCRIPTION
                "The secret - up to 29 characters long,
                 shared between the RADIUS Authentication Server and the switch."
            ::= { ctcAuthServerConfigEntry 5 }

        -- 1.3.6.1.4.1.4756.104.60.3.3.1.6
        ctcRadiusAccountingEnabled OBJECT-TYPE
            SYNTAX      TruthValue
            MAX-ACCESS  read-write
            STATUS      current
            DESCRIPTION
                "Enable the RADIUS Accounting Server."
            ::= { ctcAuthServerConfigEntry 6 }

        -- 1.3.6.1.4.1.4756.104.60.3.3.1.7
        ctcRadiusAccountingServerAddress OBJECT-TYPE
            SYNTAX      DisplayString
            MAX-ACCESS  read-write
            STATUS      current
            DESCRIPTION
                "The IP address or hostname of the RADIUS Accounting Server.
                 IP address is expressed in dotted decimal notation."
            ::= { ctcAuthServerConfigEntry 7 }

        -- 1.3.6.1.4.1.4756.104.60.3.3.1.8
        ctcRadiusAccountingServerPort OBJECT-TYPE
            SYNTAX      Integer32 (0..65535)
            MAX-ACCESS  read-write
            STATUS      current
            DESCRIPTION
                "The UDP port to use on the RADIUS Accounting Server.
                 If the port is set to 0(zero),
                 the default port(1813) is used on the RADIUS Accounting Server."
            ::= { ctcAuthServerConfigEntry 8 }

        -- 1.3.6.1.4.1.4756.104.60.3.3.1.9
        ctcRadiusAccountingSecret OBJECT-TYPE
            SYNTAX      DisplayString
            MAX-ACCESS  read-write
            STATUS      current
            DESCRIPTION
                "The secret - up to 29 characters long,
                 shared between the RADIUS Accounting Server and the switch."
            ::= { ctcAuthServerConfigEntry 9 }

        -- 1.3.6.1.4.1.4756.104.60.3.3.1.10
        ctcTacacsPlusAuthEnabled OBJECT-TYPE
            SYNTAX      TruthValue
            MAX-ACCESS  read-write
            STATUS      current
            DESCRIPTION
                "Enable the TACACS+ Authentication Server."
            ::= { ctcAuthServerConfigEntry 10 }

        -- 1.3.6.1.4.1.4756.104.60.3.3.1.11
        ctcTacacsPlusAuthServerAddress OBJECT-TYPE
            SYNTAX      DisplayString
            MAX-ACCESS  read-write
            STATUS      current
            DESCRIPTION
                "The IP address or hostname of the TACACS+ Authentication Server.
                 IP address is expressed in dotted decimal notation."
            ::= { ctcAuthServerConfigEntry 11 }

        -- 1.3.6.1.4.1.4756.104.60.3.3.1.12
        ctcTacacsPlusAuthServerPort OBJECT-TYPE
            SYNTAX      Integer32 (0..65535)
            MAX-ACCESS  read-write
            STATUS      current
            DESCRIPTION
                "The TCP port to use on the TACACS+ Authentication Server.
                 If the port is set to 0(zero),
                 the default port(49) is used on the TACACS+ Authentication Server."
            ::= { ctcAuthServerConfigEntry 12 }

        -- 1.3.6.1.4.1.4756.104.60.3.3.1.13
        ctcTacacsPlusAuthSecret OBJECT-TYPE
            SYNTAX      DisplayString
            MAX-ACCESS  read-write
            STATUS      current
            DESCRIPTION
                "The secret - up to 29 characters long,
                 shared between the TACACS+ Authentication Server and the switch."
            ::= { ctcAuthServerConfigEntry 13 }

    -- 1.3.6.1.4.1.4756.104.60.3.4
    ctcRadiusServerStatusTable OBJECT-TYPE
        SYNTAX      SEQUENCE OF CtcRadiusServerStatusEntry
        MAX-ACCESS  not-accessible
        STATUS      current
        DESCRIPTION
            "This table provides the status of the RADIUS servers."
        ::= { ctcSecurityAAA 4 }

    -- 1.3.6.1.4.1.4756.104.60.3.4.1
    ctcRadiusServerStatusEntry OBJECT-TYPE
        SYNTAX      CtcRadiusServerStatusEntry
        MAX-ACCESS  not-accessible
        STATUS      current
        DESCRIPTION
            "The Entry of RADIUS Server status."
        INDEX { ctcAuthServerIndex }
        ::= { ctcRadiusServerStatusTable 1 }

    CtcRadiusServerStatusEntry ::=
        SEQUENCE {
            ctcRadiusAuthIpAddress           IpAddress,
            ctcRadiusAuthUdpPort             Integer32,
            ctcRadiusAuthState               INTEGER,
            ctcRadiusAuthRoundTripTime       Integer32,
            ctcRadiusAccountingIpAddress     IpAddress,
            ctcRadiusAccountingUdpPort       Integer32,
            ctcRadiusAccountingState         INTEGER,
            ctcRadiusAccountingRoundTripTime Integer32
        }

        -- 1.3.6.1.4.1.4756.104.60.3.4.1.1
        ctcRadiusAuthIpAddress OBJECT-TYPE
            SYNTAX      IpAddress
            MAX-ACCESS  read-only
            STATUS      current
            DESCRIPTION
                "The IP address of the RADIUS Authentication server."
            ::= { ctcRadiusServerStatusEntry 1 }

        -- 1.3.6.1.4.1.4756.104.60.3.4.1.2
        ctcRadiusAuthUdpPort OBJECT-TYPE
            SYNTAX      Integer32 (0..65535)
            MAX-ACCESS  read-only
            STATUS      current
            DESCRIPTION
                "The UDP port number of the RADIUS Authentication server."
            ::= { ctcRadiusServerStatusEntry 2 }

        -- 1.3.6.1.4.1.4756.104.60.3.4.1.3
        ctcRadiusAuthState OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { ctcRadiusServerStatusEntry 3 }

        -- 1.3.6.1.4.1.4756.104.60.3.4.1.4
        ctcRadiusAuthRoundTripTime OBJECT-TYPE
            SYNTAX      Integer32 (0..3600000)
            UNITS       "Millisecond"
            MAX-ACCESS  read-only
            STATUS      current
            DESCRIPTION
                "The time interval(measured in milliseconds) between
                 the most recent Access-Reply/Access-Challenge and the Access-Request
                 that matched it from the RADIUS authentication server.
                 The granularity of this measurement is 100 ms.
                 A value of 0 ms indicates that there hasn't been round-trip communication with the server yet."
            ::= { ctcRadiusServerStatusEntry 4 }

        -- 1.3.6.1.4.1.4756.104.60.3.4.1.5
        ctcRadiusAccountingIpAddress OBJECT-TYPE
            SYNTAX      IpAddress
            MAX-ACCESS  read-only
            STATUS      current
            DESCRIPTION
                "The IP address of the RADIUS Accounting server."
            ::= { ctcRadiusServerStatusEntry 5 }

        -- 1.3.6.1.4.1.4756.104.60.3.4.1.6
        ctcRadiusAccountingUdpPort OBJECT-TYPE
            SYNTAX      Integer32 (0..65535)
            MAX-ACCESS  read-only
            STATUS      current
            DESCRIPTION
                "The UDP port number of the RADIUS Accounting server."
            ::= { ctcRadiusServerStatusEntry 6 }

        -- 1.3.6.1.4.1.4756.104.60.3.4.1.7
        ctcRadiusAccountingState OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { ctcRadiusServerStatusEntry 7 }

        -- 1.3.6.1.4.1.4756.104.60.3.4.1.8
        ctcRadiusAccountingRoundTripTime OBJECT-TYPE
            SYNTAX      Integer32 (0..3600000)
            UNITS       "Millisecond"
            MAX-ACCESS  read-only
            STATUS      current
            DESCRIPTION
                "The time interval (measured in milliseconds) between the most recent Response and
                 the Request that matched it from the RADIUS accounting server.
                 The granularity of this measurement is 100 ms.
                 A value of 0 ms indicates that there hasn't been round-trip communication with the server yet."
            ::= { ctcRadiusServerStatusEntry 8 }

    -- 1.3.6.1.4.1.4756.104.60.3.5
    ctcRadiusAuthStatisticsTable OBJECT-TYPE
        SYNTAX      SEQUENCE OF CtcRadiusAuthStatisticsEntry
        MAX-ACCESS  not-accessible
        STATUS      current
        DESCRIPTION
            "This table provides the status of the RADIUS servers."
        ::= { ctcSecurityAAA 5 }

    -- 1.3.6.1.4.1.4756.104.60.3.5.1
    ctcRadiusAuthStatisticsEntry OBJECT-TYPE
        SYNTAX      CtcRadiusAuthStatisticsEntry
        MAX-ACCESS  not-accessible
        STATUS      current
        DESCRIPTION
            "The Entry of RADIUS Authentication Server status."
        INDEX { ctcAuthServerIndex }
        ::= { ctcRadiusAuthStatisticsTable 1 }

    CtcRadiusAuthStatisticsEntry ::=
        SEQUENCE {
            ctcRadiusStatisticsClear                 INTEGER,
            ctcRadiusAuthRxAccessAccepts             Counter32,
            ctcRadiusAuthRxAccessRejects             Counter32,
            ctcRadiusAuthRxAccessChallenges          Counter32,
            ctcRadiusAuthRxMalformedAccessRespones   Counter32,
            ctcRadiusAuthRxBadAuthentications        Counter32,
            ctcRadiusAuthRxUnknowTypes               Counter32,
            ctcRadiusAuthRxDroppeds                  Counter32,
            ctcRadiusAuthTxAccessRequests            Counter32,
            ctcRadiusAuthTxAccessRetransmissions     Counter32,
            ctcRadiusAuthTxPendingRequests           Counter32,
            ctcRadiusAuthTxTimeouts                  Counter32,
            ctcRadiusAccountingRxResponses           Counter32,
            ctcRadiusAccountingRxMalformedResponses  Counter32,
            ctcRadiusAccountingRxBadAuthentications  Counter32,
            ctcRadiusAccountingRxUnknowTypes         Counter32,
            ctcRadiusAccountingRxDroppeds            Counter32,
            ctcRadiusAccountingTxRequests            Counter32,
            ctcRadiusAccountingTxRetransmissions     Counter32,
            ctcRadiusAccountingTxPendingRequests     Counter32,
            ctcRadiusAccountingTxTimeouts            Counter32
        }

        -- 1.3.6.1.4.1.4756.104.60.3.5.1.1
        ctcRadiusStatisticsClear OBJECT-TYPE
            SYNTAX      INTEGER {
                            trigger(1),
                            normal(2)
                        }
            MAX-ACCESS  read-write
            STATUS      current
            DESCRIPTION
                "Clears the counters for all ports."
            ::= { ctcRadiusAuthStatisticsEntry 1 }

        -- 1.3.6.1.4.1.4756.104.60.3.5.1.2
        ctcRadiusAuthRxAccessAccepts OBJECT-TYPE
            SYNTAX      Counter32
            UNITS       "Packets"
            MAX-ACCESS  read-only
            STATUS      current
            DESCRIPTION
                "The number of RADIUS Access-Accept packets(valid or invalid) received from the server."
            ::= { ctcRadiusAuthStatisticsEntry 2 }

        -- 1.3.6.1.4.1.4756.104.60.3.5.1.3
        ctcRadiusAuthRxAccessRejects OBJECT-TYPE
            SYNTAX      Counter32
            UNITS       "Packets"
            MAX-ACCESS  read-only
            STATUS      current
            DESCRIPTION
                "The number of RADIUS Access-Reject packets(valid or invalid) received from the server."
            ::= { ctcRadiusAuthStatisticsEntry 3 }

        -- 1.3.6.1.4.1.4756.104.60.3.5.1.4
        ctcRadiusAuthRxAccessChallenges OBJECT-TYPE
            SYNTAX      Counter32
            UNITS       "Packets"
            MAX-ACCESS  read-only
            STATUS      current
            DESCRIPTION
                "The number of RADIUS Access-Challenge packets(valid or invalid) received from the server."
            ::= { ctcRadiusAuthStatisticsEntry 4 }

        -- 1.3.6.1.4.1.4756.104.60.3.5.1.5
        ctcRadiusAuthRxMalformedAccessRespones OBJECT-TYPE
            SYNTAX      Counter32
            UNITS       "Packets"
            MAX-ACCESS  read-only
            STATUS      current
            DESCRIPTION
                "The number of malformed RADIUS Access-Response packets received from the server.
                 Malformed packets include packets with an invalid length.
                 Bad authenticators or Message Authenticator attributes or
                 unknown types are not included as malformed access responses."
            ::= { ctcRadiusAuthStatisticsEntry 5 }

        -- 1.3.6.1.4.1.4756.104.60.3.5.1.6
        ctcRadiusAuthRxBadAuthentications OBJECT-TYPE
            SYNTAX      Counter32
            UNITS       "Packets"
            MAX-ACCESS  read-only
            STATUS      current
            DESCRIPTION
                "The number of RADIUS Access-Response packets containing invalid authenticators or
                 Message Authenticator attributes received from the server."
            ::= { ctcRadiusAuthStatisticsEntry 6 }

        -- 1.3.6.1.4.1.4756.104.60.3.5.1.7
        ctcRadiusAuthRxUnknowTypes OBJECT-TYPE
            SYNTAX      Counter32
            UNITS       "Packets"
            MAX-ACCESS  read-only
            STATUS      current
            DESCRIPTION
                "The number of RADIUS packets that were received with unknown types from
                 the server on the authentication port and dropped."
            ::= { ctcRadiusAuthStatisticsEntry 7 }

        -- 1.3.6.1.4.1.4756.104.60.3.5.1.8
        ctcRadiusAuthRxDroppeds OBJECT-TYPE
            SYNTAX      Counter32
            UNITS       "Packets"
            MAX-ACCESS  read-only
            STATUS      current
            DESCRIPTION
                "The number of RADIUS packets that were received from the server on
                 the authentication port and dropped for some other reason."
            ::= { ctcRadiusAuthStatisticsEntry 8 }

        -- 1.3.6.1.4.1.4756.104.60.3.5.1.9
        ctcRadiusAuthTxAccessRequests OBJECT-TYPE
            SYNTAX      Counter32
            UNITS       "Packets"
            MAX-ACCESS  read-only
            STATUS      current
            DESCRIPTION
                "The number of RADIUS Access-Request packets sent to the server.
                 This does not include retransmissions."
            ::= { ctcRadiusAuthStatisticsEntry 9 }

        -- 1.3.6.1.4.1.4756.104.60.3.5.1.10
        ctcRadiusAuthTxAccessRetransmissions OBJECT-TYPE
            SYNTAX      Counter32
            UNITS       "Packets"
            MAX-ACCESS  read-only
            STATUS      current
            DESCRIPTION
                "The number of RADIUS Access-Request packets retransmitted to
                 the RADIUS authentication server."
            ::= { ctcRadiusAuthStatisticsEntry 10 }

        -- 1.3.6.1.4.1.4756.104.60.3.5.1.11
        ctcRadiusAuthTxPendingRequests OBJECT-TYPE
            SYNTAX      Counter32
            UNITS       "Packets"
            MAX-ACCESS  read-only
            STATUS      current
            DESCRIPTION
                "The number of RADIUS Access-Request packets destined for the server
                 that have not yet timed out or received a response.
                 This variable is incremented when an Access-Request is sent and decremented due to
                 receipt of an Access-Accept, Access-Reject, Access-Challenge, timeout, or retransmission."
            ::= { ctcRadiusAuthStatisticsEntry 11 }

        -- 1.3.6.1.4.1.4756.104.60.3.5.1.12
        ctcRadiusAuthTxTimeouts OBJECT-TYPE
            SYNTAX      Counter32
            UNITS       "Packets"
            MAX-ACCESS  read-only
            STATUS      current
            DESCRIPTION
                "The number of authentication timeouts to the server. After a timeout,
                 the client may retry to the same server, send to a different server, or give up.
                 A retry to the same server is counted as a retransmit as well as a timeout.
                 A send to a different server is counted as a Request as well as a timeout."
            ::= { ctcRadiusAuthStatisticsEntry 12 }

        -- 1.3.6.1.4.1.4756.104.60.3.5.1.13
        ctcRadiusAccountingRxResponses OBJECT-TYPE
            SYNTAX      Counter32
            UNITS       "Packets"
            MAX-ACCESS  read-only
            STATUS      current
            DESCRIPTION
                "The number of RADIUS packets(valid or invalid) received from the server."
            ::= { ctcRadiusAuthStatisticsEntry 13 }

        -- 1.3.6.1.4.1.4756.104.60.3.5.1.14
        ctcRadiusAccountingRxMalformedResponses OBJECT-TYPE
            SYNTAX      Counter32
            UNITS       "Packets"
            MAX-ACCESS  read-only
            STATUS      current
            DESCRIPTION
                "The number of malformed RADIUS packets received from the server.
                 Malformed packets include packets with an invalid length.
                 Bad authenticators or unknown types are not included as malformed access responses."
            ::= { ctcRadiusAuthStatisticsEntry 14 }

        -- 1.3.6.1.4.1.4756.104.60.3.5.1.15
        ctcRadiusAccountingRxBadAuthentications OBJECT-TYPE
            SYNTAX      Counter32
            UNITS       "Packets"
            MAX-ACCESS  read-only
            STATUS      current
            DESCRIPTION
                "The number of RADIUS packets containing invalid authenticators received from the server."
            ::= { ctcRadiusAuthStatisticsEntry 15 }

        -- 1.3.6.1.4.1.4756.104.60.3.5.1.16
        ctcRadiusAccountingRxUnknowTypes OBJECT-TYPE
            SYNTAX      Counter32
            UNITS       "Packets"
            MAX-ACCESS  read-only
            STATUS      current
            DESCRIPTION
                "The number of RADIUS packets of unknown types that were received from
                 the server on the accounting port."
            ::= { ctcRadiusAuthStatisticsEntry 16 }

        -- 1.3.6.1.4.1.4756.104.60.3.5.1.17
        ctcRadiusAccountingRxDroppeds OBJECT-TYPE
            SYNTAX      Counter32
            UNITS       "Packets"
            MAX-ACCESS  read-only
            STATUS      current
            DESCRIPTION
                "The number of RADIUS packets that were received from the server on
                 the accounting port and dropped for some other reason."
            ::= { ctcRadiusAuthStatisticsEntry 17 }

        -- 1.3.6.1.4.1.4756.104.60.3.5.1.18
        ctcRadiusAccountingTxRequests OBJECT-TYPE
            SYNTAX      Counter32
            UNITS       "Packets"
            MAX-ACCESS  read-only
            STATUS      current
            DESCRIPTION
                "The number of RADIUS packets sent to the server.
                 This does not include retransmissions."
            ::= { ctcRadiusAuthStatisticsEntry 18 }

        -- 1.3.6.1.4.1.4756.104.60.3.5.1.19
        ctcRadiusAccountingTxRetransmissions OBJECT-TYPE
            SYNTAX      Counter32
            UNITS       "Packets"
            MAX-ACCESS  read-only
            STATUS      current
            DESCRIPTION
                "The number of RADIUS packets retransmitted to the RADIUS accounting server."
            ::= { ctcRadiusAuthStatisticsEntry 19 }

        -- 1.3.6.1.4.1.4756.104.60.3.5.1.20
        ctcRadiusAccountingTxPendingRequests OBJECT-TYPE
            SYNTAX      Counter32
            UNITS       "Packets"
            MAX-ACCESS  read-only
            STATUS      current
            DESCRIPTION
                "The number of RADIUS packets destined for the server
                 that have not yet timed out or received a response.
                 This variable is incremented when a Request is sent and decremented due to
                 receipt of a Response, timeout, or retransmission."
            ::= { ctcRadiusAuthStatisticsEntry 20 }

        -- 1.3.6.1.4.1.4756.104.60.3.5.1.21
        ctcRadiusAccountingTxTimeouts OBJECT-TYPE
            SYNTAX      Counter32
            UNITS       "Packets"
            MAX-ACCESS  read-only
            STATUS      current
            DESCRIPTION
                "The number of accounting timeouts to the server. After a timeout,
                 the client may retry to the same server, send to a different server, or give up.
                 A retry to the same server is counted as a retransmit as well as a timeout.
                 A send to a different server is counted as a Request as well as a timeout."
            ::= { ctcRadiusAuthStatisticsEntry 21 }
    
    
-- Aggregation
    ctcAggregation  OBJECT IDENTIFIER ::= { gsw2008ms 70 }

    -- 1.3.6.1.4.1.4756.104.70.10.10
    ctcStaticAggregation  OBJECT IDENTIFIER ::= { ctcAggregation 10 }

    -- 1.3.6.1.4.1.4756.104.70.10.1    
    ctcAggrHashSA OBJECT-TYPE
        SYNTAX      TruthValue
        MAX-ACCESS  read-write
        STATUS      current
        DESCRIPTION
            "The number of received packets per queue."
        ::= { ctcStaticAggregation 1 }
 
    -- 1.3.6.1.4.1.4756.104.70.10.2    
    ctcAggrHashDA OBJECT-TYPE
        SYNTAX      TruthValue
        MAX-ACCESS  read-write
        STATUS      current
        DESCRIPTION
            "The number of received packets per queue."
        ::= { ctcStaticAggregation 2 }
 
    -- 1.3.6.1.4.1.4756.104.70.10.3    
    ctcAggrHashIP OBJECT-TYPE
        SYNTAX      TruthValue
        MAX-ACCESS  read-write
        STATUS      current
        DESCRIPTION
            "The number of received packets per queue."
        ::= { ctcStaticAggregation 3 }

    -- 1.3.6.1.4.1.4756.104.70.10.4    
    ctcAggrHashPortNumber OBJECT-TYPE
        SYNTAX      TruthValue
        MAX-ACCESS  read-write
        STATUS      current
        DESCRIPTION
            "The TCP/UDP port number can be used to calculate the destination port for the frame."
        DEFVAL      { true }
        ::= { ctcStaticAggregation 4 }

    -- 1.3.6.1.4.1.4756.104.70.10.5
    ctcAggrGroupTable OBJECT-TYPE
        SYNTAX      SEQUENCE OF CtcAggrGroupEntry
        MAX-ACCESS  not-accessible
        STATUS      current
        DESCRIPTION
            "This table is used to configure the aggregation group."
        ::= { ctcStaticAggregation 5 }

    -- 1.3.6.1.4.1.4756.104.70.10.5.1
    ctcAggrGroupEntry OBJECT-TYPE
        SYNTAX      CtcAggrGroupEntry
        MAX-ACCESS  not-accessible
        STATUS      current
        DESCRIPTION
            "The Entry of aggregation group configuration."
        INDEX { ctcAggrGroupID }
        ::= { ctcAggrGroupTable 1 }

    CtcAggrGroupEntry ::=
        SEQUENCE {
            ctcAggrGroupID       Integer32,
            ctcAggrMemberPort    DisplayString
        }

        -- 1.3.6.1.4.1.4756.104.70.10.5.1.1
        ctcAggrGroupID OBJECT-TYPE
            SYNTAX      Integer32 (1..3)
            MAX-ACCESS  read-only
            STATUS      current
            DESCRIPTION
                "Indicates the group ID for the settings contained in the same row.
                 Only one group ID is valid per port."
            ::= { ctcAggrGroupEntry 1 }

        -- 1.3.6.1.4.1.4756.104.70.10.5.1.2    
        ctcAggrMemberPort OBJECT-TYPE
            SYNTAX      DisplayString
            MAX-ACCESS  read-write
            STATUS      current
            DESCRIPTION
                "Each switch port is listed for each group ID.
                 Only full duplex ports can join an aggregation and ports must be in the same speed in each group,
                 Static aggregation and LACP can not both be enabled on the same ports,
                 Static aggregation can not be enabed on ports whose 802.1X Admin State is not Authorized"
            ::= { ctcAggrGroupEntry 2 }

-- LACP
    -- 1.3.6.1.4.1.4756.104.70.20
    ctcLACP OBJECT IDENTIFIER ::= { ctcAggregation 20 }
    
    -- 1.3.6.1.4.1.4756.104.70.20.1
    ctcLacpPortConfigTable OBJECT-TYPE
        SYNTAX      SEQUENCE OF CtcLacpPortConfigEntry
        MAX-ACCESS  not-accessible
        STATUS      current
        DESCRIPTION
            "This table provides LACP configurations for all ports."
        ::= { ctcLACP 1 }

    -- 1.3.6.1.4.1.4756.104.70.20.1.1
    ctcLacpPortConfigEntry OBJECT-TYPE
        SYNTAX      CtcLacpPortConfigEntry
        MAX-ACCESS  not-accessible
        STATUS      current
        DESCRIPTION
            "The Entry of LACP port configurations."
        INDEX { ctcPortIndex }
        ::= { ctcLacpPortConfigTable 1 }

    CtcLacpPortConfigEntry ::=
        SEQUENCE {
            ctcLacpPortEnabled      TruthValue,          
            ctcLacpKey              Integer32,
            ctcLacpRole             INTEGER,
            ctcLacpTimeout          INTEGER,
            ctcLacpPriority         Integer32
        }

        -- 1.3.6.1.4.1.4756.104.70.20.1.1.1    
        ctcLacpPortEnabled OBJECT-TYPE
            SYNTAX      TruthValue
            MAX-ACCESS  read-write
            STATUS      current
            DESCRIPTION
                "Controls whether LACP is enabled on this switch port.
                 LACP will form an aggregation when 2 or more ports are connected to the same partner."
            ::= { ctcLacpPortConfigEntry 1 }

        -- 1.3.6.1.4.1.4756.104.70.20.1.1.2    
        ctcLacpKey OBJECT-TYPE
            SYNTAX      Integer32 (0..65535)
            MAX-ACCESS  read-write
            STATUS      current
            DESCRIPTION
                "The Key value incurred by the port, range 0-65535.
                 The 0(Zero) setting will set the key as appropriate by the physical link speed, 10Mb = 1, 100Mb = 2, 1Gb = 3.
                 Ports with the same Key value can participate in the same aggregation group,
                 while ports with different keys cannot."
            ::= { ctcLacpPortConfigEntry 2 }
            
        -- 1.3.6.1.4.1.4756.104.70.20.1.1.3    
        ctcLacpRole OBJECT-TYPE
            SYNTAX      INTEGER {
                            active(1),
                            passive(2)
                        }
            MAX-ACCESS  read-write
            STATUS      current
            DESCRIPTION
                "The Active will transmit LACP packets each second,
                 while Passive will wait for a LACP packet from a partner (speak if spoken to)."
            ::= { ctcLacpPortConfigEntry 3 }
            
        -- 1.3.6.1.4.1.4756.104.70.20.1.1.4   
        ctcLacpTimeout OBJECT-TYPE
            SYNTAX      INTEGER {
                            slow(1),
                            fast(2)
                        }
            MAX-ACCESS  read-write
            STATUS      current
            DESCRIPTION
                "The Timeout controls the period between BPDU transmissions.
                 Fast will transmit LACP packets each second,
                 while Slow will wait for 30 seconds before sending a LACP packet."
            ::= { ctcLacpPortConfigEntry 4 }

        -- 1.3.6.1.4.1.4756.104.70.20.1.1.5   
        ctcLacpPriority OBJECT-TYPE
            SYNTAX      Integer32 (1..65535)
            MAX-ACCESS  read-write
            STATUS      current
            DESCRIPTION
                "The Prio controls the priority of the port.
                 If the LACP partner wants to form a larger group than is supported by this device then
                 this parameter will control which ports will be active and which ports will be in a backup role.
                 Lower number means greater priority."
            ::= { ctcLacpPortConfigEntry 5 }
   
    -- 1.3.6.1.4.1.4756.104.70.20.2
    ctcLacpSystemStatusTable OBJECT-TYPE
        SYNTAX      SEQUENCE OF CtcLacpSystemStatusEntry
        MAX-ACCESS  not-accessible
        STATUS      current
        DESCRIPTION
            "This table provides a status overview for all LACP instances."
        ::= { ctcLACP 2 }

    -- 1.3.6.1.4.1.4756.104.70.20.2.1
    ctcLacpSystemStatusEntry OBJECT-TYPE
        SYNTAX      CtcLacpSystemStatusEntry
        MAX-ACCESS  not-accessible
        STATUS      current
        DESCRIPTION
            "The Entry of LACP System Status."
        INDEX { ctcLacpAggrID }
        ::= { ctcLacpSystemStatusTable 1 }

    CtcLacpSystemStatusEntry ::=
        SEQUENCE {
        	ctcLacpAggrID				Integer32,
            ctcLacpPartnerSystemID      DisplayString,          
            ctcLacpPartnerKey           Integer32,
            ctcLacpPartnerSystemPrio    Integer32,
            ctcLacpLastChangedTime      DisplayString,
            ctcLacpLocalPorts           DisplayString
        }

        -- 1.3.6.1.4.1.4756.104.70.20.2.1.1
        ctcLacpAggrID OBJECT-TYPE
            SYNTAX      Integer32 (1..5)
            MAX-ACCESS  read-only
            STATUS      current
            DESCRIPTION
                "The Aggregation ID associated with this aggregation instance."
            ::= { ctcLacpSystemStatusEntry 1 }

        -- 1.3.6.1.4.1.4756.104.70.20.2.1.2
        ctcLacpPartnerSystemID OBJECT-TYPE
            SYNTAX      DisplayString
            MAX-ACCESS  read-only
            STATUS      current
            DESCRIPTION
                "The system ID (MAC address) of the aggregation partner. "
            ::= { ctcLacpSystemStatusEntry 2 }

        -- 1.3.6.1.4.1.4756.104.70.20.2.1.3    
        ctcLacpPartnerKey OBJECT-TYPE
            SYNTAX      Integer32 (0..65535)
            MAX-ACCESS  read-only
            STATUS      current
            DESCRIPTION
                "The Key that the partner has assigned to this aggregation ID. "
            ::= { ctcLacpSystemStatusEntry 3 }

        -- 1.3.6.1.4.1.4756.104.70.20.2.1.4   
        ctcLacpPartnerSystemPrio OBJECT-TYPE
            SYNTAX      Integer32 (1..65535)
            MAX-ACCESS  read-only
            STATUS      current
            DESCRIPTION
                "The Priority that the partner has assigned to the system."
            ::= { ctcLacpSystemStatusEntry 4 }

        -- 1.3.6.1.4.1.4756.104.70.20.2.1.5
        ctcLacpLastChangedTime OBJECT-TYPE
            SYNTAX      DisplayString
            MAX-ACCESS  read-only
            STATUS      current
            DESCRIPTION
                "The time since this aggregation changed."
            ::= { ctcLacpSystemStatusEntry 5 }

        -- 1.3.6.1.4.1.4756.104.70.20.2.1.6
        ctcLacpLocalPorts OBJECT-TYPE
            SYNTAX      DisplayString
            MAX-ACCESS  read-only
            STATUS      current
            DESCRIPTION
                "The ports are a part of this aggregation for this switch."
            ::= { ctcLacpSystemStatusEntry 6 }
   
    -- 1.3.6.1.4.1.4756.104.70.20.3
    ctcLacpPortStatusTable OBJECT-TYPE
        SYNTAX      SEQUENCE OF CtcLacpPortStatusEntry
        MAX-ACCESS  not-accessible
        STATUS      current
        DESCRIPTION
            "This table provides a status overview for LACP status for all ports."
        ::= { ctcLACP 3 }

    -- 1.3.6.1.4.1.4756.104.70.20.3.1
    ctcLacpPortStatusEntry OBJECT-TYPE
        SYNTAX      CtcLacpPortStatusEntry
        MAX-ACCESS  not-accessible
        STATUS      current
        DESCRIPTION
            "The Entry of LACP status for all ports."
        INDEX { ctcPortIndex }
        ::= { ctcLacpPortStatusTable 1 }

    CtcLacpPortStatusEntry ::=
        SEQUENCE {
        	ctcLacpPortEnabledState		    INTEGER,
            ctcLacpPortKeyState             Integer32,          
            ctcLacpPortAggrID           	Integer32,
            ctcLacpPortPartnerSystemID      DisplayString,
            ctcLacpPortPartnerPort      	Integer32,
            ctcLacpPortPartnerPriority      Integer32
        }

        -- 1.3.6.1.4.1.4756.104.70.20.3.1.1    
        ctcLacpPortEnabledState OBJECT-TYPE
            SYNTAX      INTEGER {
                            no(1),
                            yes(2),
                            standby(3)
                        }
            MAX-ACCESS  read-only
            STATUS      current
            DESCRIPTION
                "'Yes' means that LACP is enabled and the port link is up.
                 'No' means that LACP is not enabled or that the port link is down.
                 'Standby' means that the port could not join the aggregation group but will join if other port leaves.
                  Meanwhile it's LACP status is disabled."
            ::= { ctcLacpPortStatusEntry 1 }

        -- 1.3.6.1.4.1.4756.104.70.20.3.1.2    
        ctcLacpPortKeyState OBJECT-TYPE
            SYNTAX      Integer32 (0..65535)
            MAX-ACCESS  read-only
            STATUS      current
            DESCRIPTION
                "The key assigned to this port. Only ports with the same key can aggregate together."
            ::= { ctcLacpPortStatusEntry 2 }

        -- 1.3.6.1.4.1.4756.104.70.20.3.1.3
        ctcLacpPortAggrID OBJECT-TYPE
            SYNTAX      Integer32 (1..3)
            MAX-ACCESS  read-only
            STATUS      current
            DESCRIPTION
                "The Aggregation ID assigned to this aggregation group."
            ::= { ctcLacpPortStatusEntry 3 }

        -- 1.3.6.1.4.1.4756.104.70.20.3.1.4
        ctcLacpPortPartnerSystemID OBJECT-TYPE
            SYNTAX      DisplayString
            MAX-ACCESS  read-only
            STATUS      current
            DESCRIPTION
                "The partner's System ID (MAC address)."
            ::= { ctcLacpPortStatusEntry 4 }

        -- 1.3.6.1.4.1.4756.104.70.20.3.1.5
        ctcLacpPortPartnerPort OBJECT-TYPE
            SYNTAX      Integer32 (1..6)
            MAX-ACCESS  read-only
            STATUS      current
            DESCRIPTION
                "The partner's port number connected to this port."
            ::= { ctcLacpPortStatusEntry 5 }

        -- 1.3.6.1.4.1.4756.104.70.20.3.1.6    
        ctcLacpPortPartnerPriority OBJECT-TYPE
            SYNTAX      Integer32 (1..65535)
            MAX-ACCESS  read-only
            STATUS      current
            DESCRIPTION
                "The partner's port priority."
            ::= { ctcLacpPortStatusEntry 6 }

    -- 1.3.6.1.4.1.4756.104.70.20.4
    ctcLacpPortStatisticsClear OBJECT-TYPE
        SYNTAX      INTEGER {
                        trigger(1),
                        normal(2)
                    }
        MAX-ACCESS  read-write
        STATUS      current
        DESCRIPTION
            "Clears the counters for all ports."
        ::= { ctcLACP 4 }
   
    -- 1.3.6.1.4.1.4756.104.70.20.5
    ctcLacpPortStatisticsTable OBJECT-TYPE
        SYNTAX      SEQUENCE OF CtcLacpPortStatisticsEntry
        MAX-ACCESS  not-accessible
        STATUS      current
        DESCRIPTION
            "This table provides an overview for LACP statistics for all ports."
        ::= { ctcLACP 5 }

    -- 1.3.6.1.4.1.4756.104.70.20.5.1
    ctcLacpPortStatisticsEntry OBJECT-TYPE
        SYNTAX      CtcLacpPortStatisticsEntry
        MAX-ACCESS  not-accessible
        STATUS      current
        DESCRIPTION
            "The Entry of LACP statistics for all ports."
        INDEX { ctcPortIndex }
        ::= { ctcLacpPortStatisticsTable 1 }

    CtcLacpPortStatisticsEntry ::=
        SEQUENCE {
        	ctcLacpPortReceived		    	Counter32,
            ctcLacpPortTransmitted          Counter32,          
            ctcLacpPortUnknownDiscarded     Counter32,
            ctcLacpPortIllegalDiscarded     Counter32
        }

        -- 1.3.6.1.4.1.4756.104.70.20.5.1.1   
        ctcLacpPortReceived OBJECT-TYPE
            SYNTAX      Counter32
            MAX-ACCESS  read-only
            STATUS      current
            DESCRIPTION
                "Shows how many LACP frames have been received at each port."
            ::= { ctcLacpPortStatisticsEntry 1 }

        -- 1.3.6.1.4.1.4756.104.70.20.3.1.2    
        ctcLacpPortTransmitted OBJECT-TYPE
            SYNTAX      Counter32
            MAX-ACCESS  read-only
            STATUS      current
            DESCRIPTION
                "Shows how many LACP frames have been sent from each port. "
            ::= { ctcLacpPortStatisticsEntry 2 }

        -- 1.3.6.1.4.1.4756.104.70.20.3.1.3    
        ctcLacpPortUnknownDiscarded OBJECT-TYPE
            SYNTAX      Counter32
            MAX-ACCESS  read-only
            STATUS      current
            DESCRIPTION
                "Shows how many unknown frames have been discarded at each port. "
            ::= { ctcLacpPortStatisticsEntry 3 }

        -- 1.3.6.1.4.1.4756.104.70.20.3.1.4    
        ctcLacpPortIllegalDiscarded OBJECT-TYPE
            SYNTAX      Counter32
            MAX-ACCESS  read-only
            STATUS      current
            DESCRIPTION
                "Shows how illegal LACP frames have been discarded at each port. "
            ::= { ctcLacpPortStatisticsEntry 4 }

                     
                     
-- Loop Protection
    -- 1.3.6.1.4.1.4756.104.75
    ctcLoopProtection  OBJECT IDENTIFIER ::= { gsw2008ms 75 }

    -- 1.3.6.1.4.1.4756.104.75.1
    ctcLoopProtectionEnable OBJECT-TYPE
        SYNTAX      TruthValue
        MAX-ACCESS  read-write
        STATUS      current
        DESCRIPTION
            "Controls whether loop protections is enabled (as a whole)."
        ::= { ctcLoopProtection 1 }

    -- 1.3.6.1.4.1.4756.104.75.2
    ctcLoopProtectionTxTime OBJECT-TYPE
        SYNTAX      Integer32 (1..10)
        UNITS       "Seconds"
        MAX-ACCESS  read-write
        STATUS      current
        DESCRIPTION
            "The interval between each loop protection PDU sent on each port.
             valid values are 1 to 10 seconds."
       ::= { ctcLoopProtection 2 }

    -- 1.3.6.1.4.1.4756.104.75.3
    ctcLoopProtectionShutdownTime OBJECT-TYPE
        SYNTAX      Integer32 (10..50)
        MAX-ACCESS  read-write
        STATUS      current
        DESCRIPTION
            "The period (in seconds) for which a port will be kept disabled in the event of
             a loop is detected (and the port action shuts down the port).
             Valid values are 0 to 604800 seconds (7 days).
             A value of zero will keep a port disabled (until next device restart)."
        ::= { ctcLoopProtection 3 }

    -- 1.3.6.1.4.1.4756.104.75.4
    ctcLoopProtectionPortConfigTable OBJECT-TYPE
        SYNTAX      SEQUENCE OF CtcLoopProtectionPortConfigEntry
        MAX-ACCESS  not-accessible
        STATUS      current
        DESCRIPTION
            "This table provides Loop Protection configurations for all ports."
        ::= { ctcLoopProtection 4 }

    -- 1.3.6.1.4.1.4756.104.75.4.1
    ctcLoopProtectionPortConfigEntry OBJECT-TYPE
        SYNTAX      CtcLoopProtectionPortConfigEntry
        MAX-ACCESS  not-accessible
        STATUS      current
        DESCRIPTION
            "The Entry of Loop Protection port configurations."
        INDEX { ctcPortIndex }
        ::= { ctcLoopProtectionPortConfigTable 1 }

    CtcLoopProtectionPortConfigEntry ::=
        SEQUENCE {
            ctcLoopProtectionPortEnabled     TruthValue,          
            ctcLoopProtectionPortAction      INTEGER,
            ctcLoopProtectionPortTxMode      INTEGER 
        }

        -- 1.3.6.1.4.1.4756.104.75.4.1.1    
        ctcLoopProtectionPortEnabled OBJECT-TYPE
            SYNTAX      TruthValue
            MAX-ACCESS  read-write
            STATUS      current
            DESCRIPTION
                "Controls whether loop protection is enabled on this switch port."
            ::= { ctcLoopProtectionPortConfigEntry 1 }

        -- 1.3.6.1.4.1.4756.104.75.4.1.2    
        ctcLoopProtectionPortAction OBJECT-TYPE
            SYNTAX      INTEGER {
                            shutdownPort(1),
                            shutdownPortAndLog(2),
                            logOnly(3)
                        }
            MAX-ACCESS  read-write
            STATUS      current
            DESCRIPTION
                "Configures the action performed when a loop is detected on a port.
                 Valid values are Shutdown Port, Shutdown Port and Log or Log Only."
            ::= { ctcLoopProtectionPortConfigEntry 2 }
            
        -- 1.3.6.1.4.1.4756.104.75.4.1.3    
        ctcLoopProtectionPortTxMode OBJECT-TYPE
            SYNTAX      INTEGER {
                            enabled(1),
                            disabled(2)
                        }
            MAX-ACCESS  read-write
            STATUS      current
            DESCRIPTION
                "Controls whether the port is actively generating loop protection PDU's,
                 or whether it is just passively looking for looped PDU's."
            ::= { ctcLoopProtectionPortConfigEntry 3 }

    -- 1.3.6.1.4.1.4756.104.75.5
    ctcLoopProtectionPortStatusTable OBJECT-TYPE
        SYNTAX      SEQUENCE OF CtcLoopProtectionPortStatusEntry
        MAX-ACCESS  not-accessible
        STATUS      current
        DESCRIPTION
            "This table provides Loop Protection status for all ports."
        ::= { ctcLoopProtection 5 }

    -- 1.3.6.1.4.1.4756.104.75.5.1
    ctcLoopProtectionPortStatusEntry OBJECT-TYPE
        SYNTAX      CtcLoopProtectionPortStatusEntry
        MAX-ACCESS  not-accessible
        STATUS      current
        DESCRIPTION
            "The Entry of Loop Protection port status."
        INDEX { ctcPortIndex }
        ::= { ctcLoopProtectionPortStatusTable 1 }

    CtcLoopProtectionPortStatusEntry ::=
        SEQUENCE {
            ctcLoopProtectionPortLoops     Integer32,          
            ctcLoopProtectionPortStatus    INTEGER,
            ctcLoopProtectionPortLoop      INTEGER,
            ctcLoopProtectionPortLastLoop  DisplayString
        }

        -- 1.3.6.1.4.1.4756.104.75.5.1.1    
        ctcLoopProtectionPortLoops OBJECT-TYPE
            SYNTAX      Integer32
            MAX-ACCESS  read-only
            STATUS      current
            DESCRIPTION
                "The number of loops detected on this port."
            ::= { ctcLoopProtectionPortStatusEntry 1 }

        -- 1.3.6.1.4.1.4756.104.75.5.1.2    
        ctcLoopProtectionPortStatus OBJECT-TYPE
            SYNTAX      INTEGER {
                            up(1),
                            down(2),
                            disabled(3)
                        }
            MAX-ACCESS  read-only
            STATUS      current
            DESCRIPTION
                "The current loop protection status of the port."
            ::= { ctcLoopProtectionPortStatusEntry 2 }
            
        -- 1.3.6.1.4.1.4756.104.75.5.1.3    
        ctcLoopProtectionPortLoop OBJECT-TYPE
            SYNTAX      INTEGER {
                            loop(1),
                            noLoop(2)
                        }
            MAX-ACCESS  read-only
            STATUS      current
            DESCRIPTION
                "Whether a loop is currently detected on the port."
            ::= { ctcLoopProtectionPortStatusEntry 3 }
            
        -- 1.3.6.1.4.1.4756.104.75.5.1.4    
        ctcLoopProtectionPortLastLoop OBJECT-TYPE
            SYNTAX      DisplayString
            MAX-ACCESS  read-only
            STATUS      current
            DESCRIPTION
                "The time of the last loop event detected."
            ::= { ctcLoopProtectionPortStatusEntry 4 }


-- Spanning Tree
    -- 1.3.6.1.4.1.4756.104.77
    ctcSpanningTree  OBJECT IDENTIFIER ::= { gsw2008ms 77 }

    -- 1.3.6.1.4.1.4756.104.77.1
    ctcBridgeSettings OBJECT IDENTIFIER ::= { ctcSpanningTree 1 }
    
    -- 1.3.6.1.4.1.4756.104.77.1.1
    ctcProtocolVersion OBJECT-TYPE
        SYNTAX      INTEGER {
	                    stp(1),
	                    rstp(2),
	                    mstp(3)
	                }
        MAX-ACCESS  read-write
        STATUS      current
        DESCRIPTION                                  
            "The MSTP / RSTP / STP protocol version setting."
        ::= { ctcBridgeSettings 1 }
        
    -- 1.3.6.1.4.1.4756.104.77.1.2
    ctcBridgePriority OBJECT-TYPE
        SYNTAX      INTEGER {
	                    priority0(1),
	                    priority4096(2),
	                    priority8192(3),
	                    priority12288(4),
	                    priority16384(5),
	                    priority20480(6),
	                    priority24576(7),
	                    priority28672(8),
	                    priority32768(9),
	                    priority36864(10),
	                    priority40960(11),
	                    priority45056(12),
	                    priority49152(13),
	                    priority53248(14),
	                    priority57344(15),
	                    priority61440(16)
	                }
        MAX-ACCESS  read-write
        STATUS      current
        DESCRIPTION                                  
            "Controls the bridge priority. Lower numeric values have better priority. 
             The bridge priority plus the MSTI instance number,
             concatenated with the 6-byte MAC address of the switch forms a Bridge Identifier. 
             For MSTP operation, this is the priority of the CIST.
             Otherwise, this is the priority of the STP/RSTP bridge."
        ::= { ctcBridgeSettings 2 }
        
    -- 1.3.6.1.4.1.4756.104.77.1.3
    ctcForwardDelay OBJECT-TYPE
        SYNTAX      Integer32 (4..30)
        UNITS       "Second"
        MAX-ACCESS  read-write
        STATUS      current
        DESCRIPTION                                  
            "The delay used by STP Bridges to transit Root and Designated Ports to Forwarding (used in STP compatible mode). 
             Valid values are in the range 4 to 30 seconds."
        ::= { ctcBridgeSettings 3 }
        
    -- 1.3.6.1.4.1.4756.104.77.1.4
    ctcMaxAge OBJECT-TYPE
        SYNTAX      Integer32 (6..40)
        UNITS       "Second"
        MAX-ACCESS  read-write
        STATUS      current
        DESCRIPTION                                  
            "The maximum age of the information transmitted by the Bridge when it is the Root Bridge. 
             Valid values are in the range 6 to 40 seconds, and MaxAge must be <= (FwdDelay-1)*2."
        ::= { ctcBridgeSettings 4 }
        
    -- 1.3.6.1.4.1.4756.104.77.1.5
    ctcMaximumHopCount OBJECT-TYPE
        SYNTAX      Integer32 (6..40)
        MAX-ACCESS  read-write
        STATUS      current
        DESCRIPTION                                  
            "This defines the initial value of remaining Hops for MSTI information generated at the boundary of an MSTI region. 
             It defines how many bridges a root bridge can distribute its BPDU information to.
             Valid values are in the range 6 to 40 hops."
        ::= { ctcBridgeSettings 5 }
        
    -- 1.3.6.1.4.1.4756.104.77.1.6
    ctcTransmitHoldCount OBJECT-TYPE
        SYNTAX      Integer32 (1..10)
        UNITS       "Frame"
        MAX-ACCESS  read-write
        STATUS      current
        DESCRIPTION                                  
            "The number of BPDU's a bridge port can send per second. When exceeded, transmission of the next BPDU will be delayed. 
             Valid values are in the range 1 to 10 BPDU's per second." 
        ::= { ctcBridgeSettings 6 }

    -- 1.3.6.1.4.1.4756.104.77.1.7
    ctcEdgePortBpduFiltering OBJECT-TYPE
        SYNTAX      TruthValue
        MAX-ACCESS  read-write
        STATUS      current
        DESCRIPTION                                  
            "Control whether a port explicitly configured as Edge will transmit and receive BPDUs."
        ::= { ctcBridgeSettings 7 }

    -- 1.3.6.1.4.1.4756.104.77.1.8
    ctcEdgePortBpduGuard OBJECT-TYPE
        SYNTAX      TruthValue
        MAX-ACCESS  read-write
        STATUS      current
        DESCRIPTION                                  
            "Control whether a port explicitly configured as Edge will disable itself upon reception of a BPDU.
             The port will enter the error-disabled state, and will be removed from the active topology."
        ::= { ctcBridgeSettings 8 }

    -- 1.3.6.1.4.1.4756.104.77.1.9
    ctcPortErrorRecoveryTimeout OBJECT-TYPE
        SYNTAX      Integer32 (0 | 30..86400)
        UNITS       "Second"
        MAX-ACCESS  read-write
        STATUS      current
        DESCRIPTION                                  
            "Control whether a port in the error-disabled state automatically will be enabled after a certain time. 
             If recovery is not enabled, ports have to be disabled and re-enabled for normal STP operation. 
             The condition is also cleared by a system reboot.
             The time to pass before a port in the error-disabled state can be enabled.
             Valid values are between 30 and 86400 seconds (24 hours) or 0 (disabled)."
        ::= { ctcBridgeSettings 9 }

    -- 1.3.6.1.4.1.4756.104.77.2
    ctcMstiMapping OBJECT IDENTIFIER ::= { ctcSpanningTree 2 }

    -- 1.3.6.1.4.1.4756.104.77.2.1
    ctcMstiConfigurationName OBJECT-TYPE
        SYNTAX      DisplayString (SIZE (0..32))
        MAX-ACCESS  read-write
        STATUS      current
        DESCRIPTION                                  
            "The name identifying the VLAN to MSTI mapping. 
             Bridges must share the name and revision (see below),
             as well as the VLAN-to-MSTI mapping configuration in order to share spanning trees for MSTI's (Intra-region). 
             The name is at most 32 characters."
        ::= { ctcMstiMapping 1 }

    -- 1.3.6.1.4.1.4756.104.77.2.2
    ctcMstiConfigurationRevision OBJECT-TYPE
        SYNTAX      Integer32 (0..65535)
        MAX-ACCESS  read-write
        STATUS      current
        DESCRIPTION                                  
            "The revision of the MSTI configuration named above. This must be an integer between 0 and 65535."
        ::= { ctcMstiMapping 2 }

    -- 1.3.6.1.4.1.4756.104.77.2.3
    ctcMstiMappingTable OBJECT-TYPE
        SYNTAX      SEQUENCE OF CtcMstiMappingEntry
        MAX-ACCESS  not-accessible
        STATUS      current
        DESCRIPTION
            "This table provides configurations of MSTI Mapping."
        ::= { ctcMstiMapping 3 }

    -- 1.3.6.1.4.1.4756.104.77.2.3.1
    ctcMstiMappingEntry OBJECT-TYPE
        SYNTAX      CtcMstiMappingEntry
        MAX-ACCESS  not-accessible
        STATUS      current
        DESCRIPTION
            "The Entry of MSTI configurations."
        INDEX { ctcMstiIndex }
        ::= { ctcMstiMappingTable 1 }

    CtcMstiMappingEntry ::=
        SEQUENCE {
            ctcMstiIndex        Integer32,
            ctcVlansMapped      DisplayString
        }
		
        -- 1.3.6.1.4.1.4756.104.77.2.3.1.1
        ctcMstiIndex OBJECT-TYPE
            SYNTAX      Integer32 (1..7)
            MAX-ACCESS  read-only
            STATUS      current
            DESCRIPTION
                "The bridge instance.
                 The CIST is not available for explicit mapping, as it will receive the VLANs not explicitly mapped."
            ::= { ctcMstiMappingEntry 1 }
            
        -- 1.3.6.1.4.1.4756.104.77.2.3.1.2
        ctcVlansMapped OBJECT-TYPE
            SYNTAX      DisplayString
            MAX-ACCESS  read-write
            STATUS      current
            DESCRIPTION
                "The list of VLANs mapped to the MSTI. 
                 The VLANs can be given as a single (xx, xx being between 1 and 4094) VLAN, or a range (xx-yy),
                 each of which must be separated with comma and/or space. 
                 A VLAN can only be mapped to one MSTI. 
                 An unused MSTI should just be left empty. (I.e. not having any VLANs mapped to it.)
                 Example: 2,5,20-40."
            ::= { ctcMstiMappingEntry 2 }    

    -- 1.3.6.1.4.1.4756.104.77.3
    ctcMstiPriority OBJECT IDENTIFIER ::= { ctcSpanningTree 3 }

    -- 1.3.6.1.4.1.4756.104.77.3.1
    ctcMstiPrioritiesTable OBJECT-TYPE
        SYNTAX      SEQUENCE OF CtcMstiPrioritiesEntry
        MAX-ACCESS  not-accessible
        STATUS      current
        DESCRIPTION
            "This table provides configurations for MSTI Priorities."
        ::= { ctcMstiPriority 1 }

    -- 1.3.6.1.4.1.4756.104.77.3.1.1
    ctcMstiPrioritiesEntry OBJECT-TYPE
        SYNTAX      CtcMstiPrioritiesEntry
        MAX-ACCESS  not-accessible
        STATUS      current
        DESCRIPTION
            "The Entry of MSTI Priorities configurations."
        INDEX { ctcStpInstanceIndex }
        ::= { ctcMstiPrioritiesTable 1 }

    CtcMstiPrioritiesEntry ::=
        SEQUENCE {
            ctcStpInstanceIndex     INTEGER,
            ctcMstiPriorities       INTEGER
        }

        -- 1.3.6.1.4.1.4756.104.77.3.1.1.1
        ctcStpInstanceIndex OBJECT-TYPE
            SYNTAX      INTEGER {
                            cist(0),
                            msti1(1),
                            msti2(2),
                            msti3(3),
                            msti4(4),
                            msti5(5),
                            msti6(6),
                            msti7(7)
                        }
            MAX-ACCESS  read-only
            STATUS      current
            DESCRIPTION
                "The index of MSTP instances."
            ::= { ctcMstiPrioritiesEntry 1 }
            
        -- 1.3.6.1.4.1.4756.104.77.2.1.1.2
        ctcMstiPriorities OBJECT-TYPE
            SYNTAX      INTEGER {
	                        priority0(1),
	                        priority4096(2),
	                        priority8192(3),
	                        priority12288(4),
	                        priority16384(5),
	                        priority20480(6),
	                        priority24576(7),
	                        priority28672(8),
	                        priority32768(9),
	                        priority36864(10),
	                        priority40960(11),
	                        priority45056(12),
	                        priority49152(13),
	                        priority53248(14),
	                        priority57344(15),
	                        priority61440(16)
	                    }
            MAX-ACCESS  read-write
            STATUS      current
            DESCRIPTION
                "Controls the bridge priority. Lower numeric values have better priority. 
                 The bridge priority plus the MSTI instance number,
                 concatenated with the 6-byte MAC address of the switch forms a Bridge Identifier."
            ::= { ctcMstiPrioritiesEntry 2 }

	-- 1.3.6.1.4.1.4756.104.77.4
    ctcCistPorts OBJECT IDENTIFIER ::= { ctcSpanningTree 4 }
	
    -- 1.3.6.1.4.1.4756.104.77.4.1
    ctcCistPortConfigTable OBJECT-TYPE
        SYNTAX      SEQUENCE OF CtcCistPortConfigEntry
        MAX-ACCESS  not-accessible
        STATUS      current
        DESCRIPTION
            "This table provides CIST configurations for all ports."
        ::= { ctcCistPorts 1 }

    -- 1.3.6.1.4.1.4756.104.77.4.1.1
    ctcCistPortConfigEntry OBJECT-TYPE
        SYNTAX      CtcCistPortConfigEntry
        MAX-ACCESS  not-accessible
        STATUS      current
        DESCRIPTION
            "The entry of CIST port Configuration."
        INDEX { ctcStpPortIndex }
        ::= { ctcCistPortConfigTable 1 }

    CtcCistPortConfigEntry ::=
        SEQUENCE {
            ctcStpPortIndex             INTEGER,
            ctcCistPortStpEnabled	    TruthValue,
            ctcCistPortPathCost	        Integer32,
            ctcCistPortPriority         INTEGER,
            ctcCistPortAdminEdge        INTEGER,
            ctcCistPortAutoEdge         TruthValue,
            ctcCistPortRestrictedRole   TruthValue,
            ctcCistPortRestrictedTCN    TruthValue,
            ctcCistPortBpduGuard        TruthValue,
            ctcCistPortPointToPoint     INTEGER
        }
        
        -- 1.3.6.1.4.1.4756.104.77.4.1.1.1
        ctcStpPortIndex OBJECT-TYPE
            SYNTAX      INTEGER {
                            aggregatedPort(0),
                            port1(1),
                            port2(2),
                            port3(3),
                            port4(4),
                            port5(5),
                            port6(6),
                            port7(7),
                            port8(8),
                            port9(9),
                            port10(10)
                        }
            MAX-ACCESS  read-only
            STATUS      current
            DESCRIPTION
                "Normal and aggregation ports Index"
            ::= { ctcCistPortConfigEntry 1 }
                  
        -- 1.3.6.1.4.1.4756.104.77.4.1.1.2
        ctcCistPortStpEnabled OBJECT-TYPE
            SYNTAX    	TruthValue
            MAX-ACCESS  read-write
            STATUS      current
            DESCRIPTION
                "Controls whether STP is enabled on this port."
            ::= { ctcCistPortConfigEntry 2 }
	
        -- 1.3.6.1.4.1.4756.104.77.4.1.1.3
        ctcCistPortPathCost OBJECT-TYPE
            SYNTAX      Integer32 (0..2000000000)
            MAX-ACCESS  read-write
            STATUS      current
            DESCRIPTION
                "Controls the path cost incurred by the port. 
                 The Auto setting(zero) will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0(auto) to 200000000."
            ::= { ctcCistPortConfigEntry 3 }
			
         -- 1.3.6.1.4.1.4756.104.77.4.1.1.4
         ctcCistPortPriority OBJECT-TYPE
            SYNTAX      INTEGER {
	                        priority0(1),
	                        priority16(2),
	                        priority32(3),
	                        priority48(4),
	                        priority64(5),
	                        priority80(6),
	                        priority96(7),
	                        priority112(8),
	                        priority128(9),
	                        priority144(10),
	                        priority160(11),
	                        priority176(12),
	                        priority192(13),
	                        priority208(14),
	                        priority224(15),
	                        priority240(16)
	                    }
            MAX-ACCESS  read-write
            STATUS      current
            DESCRIPTION
                "Controls the port priority.
                 This can be used to control priority of ports having identical port cost."
            ::= { ctcCistPortConfigEntry 4 }
	
        -- 1.3.6.1.4.1.4756.104.77.4.1.1.5
        ctcCistPortAdminEdge OBJECT-TYPE
            SYNTAX      INTEGER {
	                        nonEdge(1),
	                        edge(2)
	                    }
            MAX-ACCESS  read-write
            STATUS      current
            DESCRIPTION
                "Controls whether the operEdge flag(in 802.1w & 802.1t) should start as set or cleared.
                (The initial operEdge state when a port is initialized)."
            ::= { ctcCistPortConfigEntry 5 }
	
        -- 1.3.6.1.4.1.4756.104.77.4.1.1.6
        ctcCistPortAutoEdge OBJECT-TYPE
            SYNTAX    	TruthValue
            MAX-ACCESS  read-write
            STATUS      current
            DESCRIPTION
                "Controls whether the bridge should enable automatic edge detection on the bridge port.
                 This allows operEdge to be derived from whether BPDU's are received on the port or not."
            ::= { ctcCistPortConfigEntry 6 }
            
        -- 1.3.6.1.4.1.4756.104.77.4.1.1.7
        ctcCistPortRestrictedRole OBJECT-TYPE
            SYNTAX    	TruthValue
            MAX-ACCESS  read-write
            STATUS      current
            DESCRIPTION
                "If enabled, causes the port not to be selected as Root Port for the CIST or any MSTI, even if it has the best spanning tree priority vector. 
                 Such a port will be selected as an Alternate Port after the Root Port has been selected. 
                 If set, it can cause lack of spanning tree connectivity. 
                 It can be set by a network administrator to prevent bridges external to a core region of the network influence the spanning tree active topology,
                 possibly because those bridges are not under the full control of the administrator. 
                 This feature is also known as Root Guard." 
            ::= { ctcCistPortConfigEntry 7 }
            
        -- 1.3.6.1.4.1.4756.104.77.4.1.1.8
        ctcCistPortRestrictedTCN OBJECT-TYPE
            SYNTAX    	TruthValue
            MAX-ACCESS  read-write
            STATUS      current
            DESCRIPTION
                "If enabled, causes the port not to propagate received topology change notifications and topology changes to other ports. 
                 If set it can cause temporary loss of connectivity after changes in a spanning tree's active topology as
                 a result of persistently incorrect learned station location information. 
                 It is set by a network administrator to prevent bridges external to a core region of the network, causing address flushing in that region,
                 possibly because those bridges are not under the full control of the administrator or the physical link state of the attached LANs transits frequently." 
            ::= { ctcCistPortConfigEntry 8 }
            
        -- 1.3.6.1.4.1.4756.104.77.4.1.1.9
        ctcCistPortBpduGuard OBJECT-TYPE
            SYNTAX    	TruthValue
            MAX-ACCESS  read-write
            STATUS      current
            DESCRIPTION
                "If enabled, causes the port to disable itself upon receiving valid BPDU's. 
                 Contrary to the similar bridge setting, the port Edge status does not effect this setting. 
                 A port entering error-disabled state due to this setting is subject to the bridge Port Error Recovery setting as well." 
            ::= { ctcCistPortConfigEntry 9 }
	
        -- 1.3.6.1.4.1.4756.104.77.4.1.1.10
        ctcCistPortPointToPoint OBJECT-TYPE
            SYNTAX      INTEGER {
	                        forced-true(1),
	                        forced-false(2),
	                        auto(3)
	                    }
            MAX-ACCESS  read-write
            STATUS      current
            DESCRIPTION
                "Controls whether the port connects to a point-to-point LAN rather than to a shared medium. 
                 This can be automatically determined, or forced either true or false. 
                 Transition to the forwarding state is faster for point-to-point LANs than for shared media." 
            ::= { ctcCistPortConfigEntry 10 }
            

	-- 1.3.6.1.4.1.4756.104.77.5
    ctcMstiPorts OBJECT IDENTIFIER ::= { ctcSpanningTree 5 }
	
    -- 1.3.6.1.4.1.4756.104.77.5.1
    ctcMstiPortConfigTable OBJECT-TYPE
        SYNTAX      SEQUENCE OF CtcMstiPortConfigEntry
        MAX-ACCESS  not-accessible
        STATUS      current
        DESCRIPTION
            "This table provides MIST configurations for all ports."
        ::= { ctcMstiPorts 1 }

    -- 1.3.6.1.4.1.4756.104.77.5.1.1
    ctcMstiPortConfigEntry OBJECT-TYPE
        SYNTAX      CtcMstiPortConfigEntry
        MAX-ACCESS  not-accessible
        STATUS      current
        DESCRIPTION
            "The Entry of MIST Port Configurations."
        INDEX { ctcMstiIndex, ctcStpPortIndex }
        ::= { ctcMstiPortConfigTable 1 }

    CtcMstiPortConfigEntry ::=
        SEQUENCE {
            ctcMstiPortPathCost	        Integer32,
            ctcMstiPortPriority         INTEGER
        }
        	
        -- 1.3.6.1.4.1.4756.104.77.5.1.1.1
        ctcMstiPortPathCost OBJECT-TYPE
            SYNTAX      Integer32 (0..2000000000)
            MAX-ACCESS  read-write
            STATUS      current
            DESCRIPTION
                "Controls the path cost incurred by the port. 
                 The Auto setting(zero) will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0(auto) to 200000000."
            ::= { ctcMstiPortConfigEntry 1 }
			
         -- 1.3.6.1.4.1.4756.104.77.5.1.1.2
         ctcMstiPortPriority OBJECT-TYPE
            SYNTAX      INTEGER {
	                        priority0(1),
	                        priority16(2),
	                        priority32(3),
	                        priority48(4),
	                        priority64(5),
	                        priority80(6),
	                        priority96(7),
	                        priority112(8),
	                        priority128(9),
	                        priority144(10),
	                        priority160(11),
	                        priority176(12),
	                        priority192(13),
	                        priority208(14),
	                        priority224(15),
	                        priority240(16)
	                    }
            MAX-ACCESS  read-write
            STATUS      current
            DESCRIPTION
                "Controls the port priority.
                 This can be used to control priority of ports having identical port cost."
            ::= { ctcMstiPortConfigEntry 4 }

	-- 1.3.6.1.4.1.4756.104.77.6
    ctcBridgeStatus OBJECT IDENTIFIER ::= { ctcSpanningTree 6 }
    
    -- 1.3.6.1.4.1.4756.104.77.6.1
    ctcBridgeStatusTable OBJECT-TYPE
        SYNTAX      SEQUENCE OF CtcBridgeStatusEntry
        MAX-ACCESS  not-accessible
        STATUS      current
        DESCRIPTION
            "This table provides detailed information on STP bridge instances."
        ::= { ctcBridgeStatus 1 }

    -- 1.3.6.1.4.1.4756.104.77.6.1.1
    ctcBridgeStatusEntry OBJECT-TYPE
        SYNTAX      CtcBridgeStatusEntry
        MAX-ACCESS  not-accessible
        STATUS      current
        DESCRIPTION
            "The index of STP instances."
        INDEX { ctcStpInstanceIndex }
        ::= { ctcBridgeStatusTable 1 }

    CtcBridgeStatusEntry ::=
        SEQUENCE {
            ctcBridgeID                 DisplayString,
            ctcRootID                   DisplayString,
            ctcRootCost                 Integer32,
            ctcRootPort                 DisplayString,
            ctcRegionalRoot             DisplayString,
            ctcInternalRootCost         Integer32,
            ctcTopologyFlag             INTEGER,
            ctcTopologyChangeCount      Integer32,
            ctcTopologyChangeLast       DisplayString
        }
       
        -- 1.3.6.1.4.1.4756.104.77.6.1.1.1
        ctcBridgeID OBJECT-TYPE
            SYNTAX      DisplayString
            MAX-ACCESS  read-only
            STATUS      current
            DESCRIPTION
                "The Bridge ID of this Bridge instance."
            ::= { ctcBridgeStatusEntry 1 }
            
        -- 1.3.6.1.4.1.4756.104.77.6.1.1.2
        ctcRootID OBJECT-TYPE
            SYNTAX      DisplayString
            MAX-ACCESS  read-only
            STATUS      current
            DESCRIPTION
                "The Bridge ID of the currently elected root bridge."
            ::= { ctcBridgeStatusEntry 2 }
            
        -- 1.3.6.1.4.1.4756.104.77.6.1.1.3
        ctcRootCost OBJECT-TYPE
            SYNTAX      Integer32
            MAX-ACCESS  read-only
            STATUS      current
            DESCRIPTION
                "Root Path Cost. For the Root Bridge this is zero. 
                 For all other Bridges, it is the sum of the Port Path Costs on the least cost path to the Root Bridge."
            ::= { ctcBridgeStatusEntry 3 }
            
        -- 1.3.6.1.4.1.4756.104.77.6.1.1.4
        ctcRootPort OBJECT-TYPE
            SYNTAX      DisplayString
            MAX-ACCESS  read-only
            STATUS      current
            DESCRIPTION
                "The switch port currently assigned the root port role."
            ::= { ctcBridgeStatusEntry 4 }
            
        -- 1.3.6.1.4.1.4756.104.77.6.1.1.5
        ctcRegionalRoot OBJECT-TYPE
            SYNTAX      DisplayString
            MAX-ACCESS  read-only
            STATUS      current
            DESCRIPTION
                "The Bridge ID of the currently elected regional root bridge, inside the MSTP region of this bridge.
                 (For the CIST instance only)."
            ::= { ctcBridgeStatusEntry 5 }
            
        -- 1.3.6.1.4.1.4756.104.77.6.1.1.6
        ctcInternalRootCost OBJECT-TYPE
            SYNTAX      Integer32
            MAX-ACCESS  read-only
            STATUS      current
            DESCRIPTION
                "The Regional Root Path Cost. For the Regional Root Bridge this is zero. 
                 For all other CIST instances in the same MSTP region, 
                 it is the sum of the Internal Port Path Costs on the least cost path to the Internal Root Bridge.
                 (For the CIST instance only). "
            ::= { ctcBridgeStatusEntry 6 }
            
        -- 1.3.6.1.4.1.4756.104.77.6.1.1.7
        ctcTopologyFlag OBJECT-TYPE
            SYNTAX      INTEGER {
                            steady(1),
                            changing(2)
                        }
            MAX-ACCESS  read-only
            STATUS      current
            DESCRIPTION
                "The current state of the Topology Change Flag of this Bridge instance."
            ::= { ctcBridgeStatusEntry 7 }
            
       	-- 1.3.6.1.4.1.4756.104.77.6.1.1.8
        ctcTopologyChangeCount OBJECT-TYPE
            SYNTAX      Integer32
            MAX-ACCESS  read-only
            STATUS      current
            DESCRIPTION
                "The number of times where the topology change flag has been set (during a one-second interval)."
            ::= { ctcBridgeStatusEntry 8 }
        
        -- 1.3.6.1.4.1.4756.104.77.6.1.1.9
        ctcTopologyChangeLast OBJECT-TYPE
            SYNTAX      DisplayString
            MAX-ACCESS  read-only
            STATUS      current
            DESCRIPTION
                "The time passed since the Topology Flag was last set."
            ::= { ctcBridgeStatusEntry 9 }

    -- 1.3.6.1.4.1.4756.104.77.6.2
    ctcPortsAndAggrsStateTable OBJECT-TYPE
        SYNTAX      SEQUENCE OF CtcPortsAndAggrsStateEntry
        MAX-ACCESS  not-accessible
        STATUS      current
        DESCRIPTION
            "This table provides port state for all active ports associateds for all ports."
        ::= { ctcBridgeStatus 2 }

    -- 1.3.6.1.4.1.4756.104.77.6.2.1
    ctcPortsAndAggrsStateEntry OBJECT-TYPE
        SYNTAX      CtcPortsAndAggrsStateEntry
        MAX-ACCESS  not-accessible
        STATUS      current
        DESCRIPTION
            "The entry of ports."
        INDEX { ctcStpInstanceIndex, ctcPortsAndAggrsIndex }
        ::= { ctcPortsAndAggrsStateTable 1 }

    CtcPortsAndAggrsStateEntry ::=
        SEQUENCE {
            ctcPortsAndAggrsIndex   INTEGER,              
            ctcPortID               DisplayString,
			ctcPortRole             DisplayString,
            ctcPortState            DisplayString,
            ctcPortPathCost         DisplayString,
            ctcPortEdge             DisplayString,
            ctcPortPointToPoint     DisplayString,
            ctcPortUpTime           DisplayString
        }
        
        -- 1.3.6.1.4.1.4756.104.77.6.2.1.1
        ctcPortsAndAggrsIndex OBJECT-TYPE
            SYNTAX      INTEGER {
                            port1(1),
                            port2(2),
                            port3(3),
                            port4(4),
                            port5(5),
                            port6(6),
                            port7(7),
                            port8(8),
                            port9(9),
                            port10(10),
                            llag1(11),
                            llag2(12),
                            llag3(13),
                            llag4(14),
                            llag5(15)
                        }                            
            MAX-ACCESS  read-only
            STATUS      current
            DESCRIPTION
                "The switch port number of the logical STP port."
            ::= { ctcPortsAndAggrsStateEntry 1 }
        
        -- 1.3.6.1.4.1.4756.104.77.6.2.1.2
        ctcPortID OBJECT-TYPE
            SYNTAX      DisplayString
            MAX-ACCESS  read-only
            STATUS      current
            DESCRIPTION
                "The port id as used by the STP protocol.
                 This is the priority part and the logical port index of the bridge port."
            ::= { ctcPortsAndAggrsStateEntry 2 }
            
        -- 1.3.6.1.4.1.4756.104.77.6.2.1.3
        ctcPortRole OBJECT-TYPE
            SYNTAX      DisplayString
            MAX-ACCESS  read-only
            STATUS      current
            DESCRIPTION
                "The current STP port role.
                 The port role can be one of the following values: AlternatePort BackupPort RootPort DesignatedPort MasterPort."
            ::= { ctcPortsAndAggrsStateEntry 3 }
            
        -- 1.3.6.1.4.1.4756.104.77.6.2.1.4
        ctcPortState OBJECT-TYPE
            SYNTAX      DisplayString
            MAX-ACCESS  read-only
            STATUS      current
            DESCRIPTION
                "The current STP port state.
                 The port state can be one of the following values: Discarding Learning Forwarding."
            ::= { ctcPortsAndAggrsStateEntry 4 }
            
        -- 1.3.6.1.4.1.4756.104.77.6.2.1.5
        ctcPortPathCost OBJECT-TYPE
            SYNTAX      DisplayString
            MAX-ACCESS  read-only
            STATUS      current
            DESCRIPTION
                "The current STP port path cost.
                 This will either be a value computed from the Auto setting, or any explicitly configured value."
            ::= { ctcPortsAndAggrsStateEntry 5 }
            
        -- 1.3.6.1.4.1.4756.104.77.6.2.1.6
        ctcPortEdge OBJECT-TYPE
            SYNTAX      DisplayString
            MAX-ACCESS  read-only
            STATUS      current
            DESCRIPTION
                "The current STP port (operational) Edge Flag. An Edge Port is a switch port to which no Bridges are attached. 
                 The flag may be automatically computed or explicitly configured. 
                 Each Edge Port transits directly to the Forwarding Port State, since there is no possibility of it participating in a loop."
            ::= { ctcPortsAndAggrsStateEntry 6 }
            
        -- 1.3.6.1.4.1.4756.104.77.6.2.1.7
        ctcPortPointToPoint OBJECT-TYPE
            SYNTAX      DisplayString
            MAX-ACCESS  read-only
            STATUS      current
            DESCRIPTION
                "The current STP port point-to-point flag. A point-to-point port connects to a non-shared LAN media. 
                 The flag may be automatically computed or explicitly configured. 
                 The point-to-point properties of a port affect how fast it can transit to STP state." 
            ::= { ctcPortsAndAggrsStateEntry 7 }
            
        -- 1.3.6.1.4.1.4756.104.77.6.2.1.8
        ctcPortUpTime OBJECT-TYPE
            SYNTAX      DisplayString
            MAX-ACCESS  read-only
            STATUS      current
            DESCRIPTION
                "The time since the bridge port was last initialized."
            ::= { ctcPortsAndAggrsStateEntry 8 }

	-- 1.3.6.1.4.1.4756.104.77.7
    ctcStpPortStatus OBJECT IDENTIFIER ::= { ctcSpanningTree 7 }
            
    -- 1.3.6.1.4.1.4756.104.77.7.1
    ctcStpPortStatusTable OBJECT-TYPE
        SYNTAX      SEQUENCE OF CtcStpPortStatusEntry
        MAX-ACCESS  not-accessible
        STATUS      current
        DESCRIPTION
            "The table displays the STP CIST port status for physical ports of the switch."
        ::= { ctcStpPortStatus 1 }

    -- 1.3.6.1.4.1.4756.104.77.7.1.1
    ctcStpPortStatusEntry OBJECT-TYPE
        SYNTAX      CtcStpPortStatusEntry
        MAX-ACCESS  not-accessible
        STATUS      current
        DESCRIPTION
            "The entry of ports."
        INDEX { ctcPortsAndAggrsIndex }
        ::= { ctcStpPortStatusTable 1 }

    CtcStpPortStatusEntry ::=
        SEQUENCE {
            ctcPortCistRole         DisplayString,
            ctcPortCistState        DisplayString,
            ctcPortCistUptime       DisplayString
        }
        
        -- 1.3.6.1.4.1.4756.104.77.7.1.1.1
        ctcPortCistRole OBJECT-TYPE
            SYNTAX      DisplayString
            MAX-ACCESS  read-only
            STATUS      current
            DESCRIPTION
                "The current STP port role of the CIST port. 
                 The port role can be one of the following values: AlternatePort BackupPort RootPort DesignatedPort Disabled."
            ::= { ctcStpPortStatusEntry 1 }
            
        -- 1.3.6.1.4.1.4756.104.77.7.1.1.2
        ctcPortCistState OBJECT-TYPE
            SYNTAX      DisplayString
            MAX-ACCESS  read-only
            STATUS      current
            DESCRIPTION
                "The current STP port state of the CIST port.
                 The port state can be one of the following values: Discarding Learning Forwarding."
            ::= { ctcStpPortStatusEntry 2 }
            
        -- 1.3.6.1.4.1.4756.104.77.7.1.1.3
        ctcPortCistUptime OBJECT-TYPE
            SYNTAX      DisplayString
            MAX-ACCESS  read-only
            STATUS      current
            DESCRIPTION
                "The time since the bridge port was last initialized."
            ::= { ctcStpPortStatusEntry 3 }
    
	-- 1.3.6.1.4.1.4756.104.77.8
    ctcStpStatistics OBJECT IDENTIFIER ::= { ctcSpanningTree 8 }   
    
	-- 1.3.6.1.4.1.4756.104.77.8.1
    ctcStpStatisticsClear OBJECT-TYPE
      	SYNTAX      INTEGER {
                        trigger(1),
                        normal(2)
                    }
        MAX-ACCESS  read-write
        STATUS      current
        DESCRIPTION
            "Reset the counters"
        ::= { ctcStpStatistics 1 }
            
	-- 1.3.6.1.4.1.4756.104.77.8.2
    ctcStpStatisticsTable OBJECT-TYPE
        SYNTAX      SEQUENCE OF CtcStpStatisticsEntry
        MAX-ACCESS  not-accessible
        STATUS      current
        DESCRIPTION
            "The table displays the STP port statistics counters of bridge ports in the switch."
        ::= { ctcStpStatistics 2 }

    -- 1.3.6.1.4.1.4756.104.77.8.2.1
    ctcStpStatisticsEntry OBJECT-TYPE
        SYNTAX      CtcStpStatisticsEntry
        MAX-ACCESS  not-accessible
        STATUS      current
        DESCRIPTION
            "The entry of ports."
        INDEX { ctcPortsAndAggrsIndex }
        ::= { ctcStpStatisticsTable 1 }

    CtcStpStatisticsEntry ::=
        SEQUENCE {
            ctcTransmittedMSTP          Counter32,
            ctcTransmittedRSTP          Counter32,
            ctcTransmittedSTP           Counter32,
            ctcTransmittedTCN           Counter32,
            ctcReceivedMSTP             Counter32,
            ctcReceivedRSTP             Counter32,
            ctcReceivedSTP              Counter32,
            ctcReceivedTCN              Counter32,
            ctcDiscardedUnknown         Counter32,
            ctcDiscardedIllegal         Counter32
        }
        
        -- 1.3.6.1.4.1.4756.104.77.8.2.1.1    
        ctcTransmittedMSTP OBJECT-TYPE
            SYNTAX      Counter32
            MAX-ACCESS  read-only
            STATUS      current
            DESCRIPTION
                "The number of MSTP BPDU's transmitted on the port."
            ::= { ctcStpStatisticsEntry 1 }
            
        -- 1.3.6.1.4.1.4756.104.77.8.2.1.2    
        ctcTransmittedRSTP OBJECT-TYPE
            SYNTAX      Counter32
            MAX-ACCESS  read-only
            STATUS      current
            DESCRIPTION
                "The number of RSTP BPDU's transmitted on the port."
            ::= { ctcStpStatisticsEntry 2 }
            
        -- 1.3.6.1.4.1.4756.104.77.8.2.1.3
        ctcTransmittedSTP OBJECT-TYPE
            SYNTAX      Counter32
            MAX-ACCESS  read-only
            STATUS      current
            DESCRIPTION
                "The number of legacy STP Configuration BPDU's transmitted on the port."
            ::= { ctcStpStatisticsEntry 3 }
            
        -- 1.3.6.1.4.1.4756.104.77.8.2.1.4
        ctcTransmittedTCN OBJECT-TYPE
            SYNTAX      Counter32
            MAX-ACCESS  read-only
            STATUS      current
            DESCRIPTION
                "The number of (legacy) Topology Change Notification BPDU's transmitted on the port."
            ::= { ctcStpStatisticsEntry 4 }
            
        -- 1.3.6.1.4.1.4756.104.77.8.2.1.5    
        ctcReceivedMSTP OBJECT-TYPE
            SYNTAX      Counter32
            MAX-ACCESS  read-only
            STATUS      current
            DESCRIPTION
                "The number of MSTP BPDU's received on the port."
            ::= { ctcStpStatisticsEntry 5 }
            
        -- 1.3.6.1.4.1.4756.104.77.8.2.1.6
        ctcReceivedRSTP OBJECT-TYPE
            SYNTAX      Counter32
            MAX-ACCESS  read-only
            STATUS      current
            DESCRIPTION
                "The number of RSTP BPDU's received on the port."
            ::= { ctcStpStatisticsEntry 6 }
            
        -- 1.3.6.1.4.1.4756.104.77.8.2.1.7
        ctcReceivedSTP OBJECT-TYPE
            SYNTAX      Counter32
            MAX-ACCESS  read-only
            STATUS      current
            DESCRIPTION
                "The number of legacy STP Configuration BPDU's received on the port."
            ::= { ctcStpStatisticsEntry 7 }
            
        -- 1.3.6.1.4.1.4756.104.77.8.2.1.8
        ctcReceivedTCN OBJECT-TYPE
            SYNTAX      Counter32
            MAX-ACCESS  read-only
            STATUS      current
            DESCRIPTION
                "The number of (legacy) Topology Change Notification BPDU's received on the port."
            ::= { ctcStpStatisticsEntry 8 }
        
        -- 1.3.6.1.4.1.4756.104.77.8.2.1.9
        ctcDiscardedUnknown OBJECT-TYPE
            SYNTAX      Counter32
            MAX-ACCESS  read-only
            STATUS      current
            DESCRIPTION
                "The number of unknown Spanning Tree BPDU's received (and discarded) on the port."
            ::= { ctcStpStatisticsEntry 9 }
            
        -- 1.3.6.1.4.1.4756.104.77.8.2.1.10
        ctcDiscardedIllegal OBJECT-TYPE
            SYNTAX      Counter32
            MAX-ACCESS  read-only
            STATUS      current
            DESCRIPTION
                "The number of illegal Spanning Tree BPDU's received (and discarded) on the port."
            ::= { ctcStpStatisticsEntry 10 }            


-- MVR
    -- 1.3.6.1.4.1.4756.104.80
    ctcMVR  OBJECT IDENTIFIER ::= { gsw2008ms 80 }
                  
    -- 1.3.6.1.4.1.4756.104.80.1    
    ctcMvrMode OBJECT-TYPE
        SYNTAX      INTEGER {
                        enabled(1),
                        disabled(2)
                    }
        MAX-ACCESS  read-write
        STATUS      current
        DESCRIPTION
            "Enable/Disable the Global MVR.
             The Unregistered Flooding control depends on the current configuration in IGMP/MLD Snooping.
             It is suggested to enable Unregistered Flooding control when the MVR group table is full."
        ::= { ctcMVR 1 }

    -- 1.3.6.1.4.1.4756.104.80.2
    ctcAddMvrVlan OBJECT-TYPE
        SYNTAX      Integer32 (1..4095)
        MAX-ACCESS  read-write
        STATUS      current
        DESCRIPTION                                  
            "Add a new MVR VLAN.
             Retrieve number of MVR VLAN entries."
        ::= { ctcMVR 2 }

    -- 1.3.6.1.4.1.4756.104.80.3
    ctcDeleteMvrVlan OBJECT-TYPE
        SYNTAX      Integer32 (1..4095)
        MAX-ACCESS  read-write
        STATUS      current
        DESCRIPTION
            "Delete a MVR VLAN.
             Retrieve number of MVR VLAN entries."
        ::= { ctcMVR 3 }

    -- 1.3.6.1.4.1.4756.104.80.4
    ctcMvrVlanTable OBJECT-TYPE
        SYNTAX      SEQUENCE OF CtcMvrVlanEntry
        MAX-ACCESS  not-accessible
        STATUS      current
        DESCRIPTION
            "This table provides MVR VLAN related configurations."
        ::= { ctcMVR 4 }

    -- 1.3.6.1.4.1.4756.104.80.4.1
    ctcMvrVlanEntry OBJECT-TYPE
        SYNTAX      CtcMvrVlanEntry
        MAX-ACCESS  not-accessible
        STATUS      current
        DESCRIPTION
            "The entry of MVR VLAN related configurations."
        INDEX { ctcMvrVlanID }
        ::= { ctcMvrVlanTable 1 }

    CtcMvrVlanEntry ::=
        SEQUENCE {
            ctcMvrVlanID             Integer32,
            ctcMvrVlanName           OCTET STRING,          
            ctcMvrVlanMode           INTEGER,
            ctcMvrVlanTagging        INTEGER,
            ctcMvrVlanPriority       Integer32,
            ctcMvrVlanLLQI           Integer32,
            ctcAddMvrVlanChannel     DisplayString,
            ctcDeleteMvrVlanChannel  DisplayString
        }

        -- 1.3.6.1.4.1.4756.104.80.4.1.1    
        ctcMvrVlanID OBJECT-TYPE
            SYNTAX      Integer32 (1..4095)
            MAX-ACCESS  read-only
            STATUS      current
            DESCRIPTION
                "Specify the Multicast VLAN ID.
                 Be Caution: MVR source ports are not recommended to be overlapped with management VLAN ports."
            ::= { ctcMvrVlanEntry 1 }

        -- 1.3.6.1.4.1.4756.104.80.4.1.2
        ctcMvrVlanName OBJECT-TYPE
            SYNTAX      OCTET STRING (SIZE (0..32))
            MAX-ACCESS  read-write
            STATUS      current
            DESCRIPTION
                "MVR Name is an optional attribute to indicate the name of the specific MVR VLAN.
                 Maximum length of the MVR VLAN Name string is 32.
                 MVR VLAN Name can only contain alphabets or numbers.
                 When the optional MVR VLAN name is given, it should contain at least one alphabet.
                 MVR VLAN name can be edited for the existing MVR VLAN entries."
            ::= { ctcMvrVlanEntry 2 }

        -- 1.3.6.1.4.1.4756.104.80.4.1.3 
        ctcMvrVlanMode OBJECT-TYPE
            SYNTAX      INTEGER {
                            dynamic(1),
                            compatible(2)
                        }
            MAX-ACCESS  read-write
            STATUS      current
            DESCRIPTION
                "Specify the MVR mode of operation.
                 In Dynamic mode, MVR allows dynamic MVR membership reports on source ports.
                 In Compatible mode, MVR membership reports are forbidden on source ports.
                 The default is Dynamic mode."
            DEFVAL      { dynamic }
            ::= { ctcMvrVlanEntry 3 }

        -- 1.3.6.1.4.1.4756.104.80.4.1.4 
        ctcMvrVlanTagging OBJECT-TYPE
            SYNTAX      INTEGER {
                            tagged(1),
                            untagged(2)
                        }
            MAX-ACCESS  read-write
            STATUS      current
            DESCRIPTION
                "Specify whether the traversed IGMP/MLD control frames will be sent as Untagged or Tagged with MVR VID.
                 The default is Tagged."
            DEFVAL      { tagged }     
            ::= { ctcMvrVlanEntry 4 }

        -- 1.3.6.1.4.1.4756.104.80.4.1.5    
        ctcMvrVlanPriority OBJECT-TYPE
            SYNTAX      Integer32 (0..7)
            MAX-ACCESS  read-write
            STATUS      current
            DESCRIPTION
                "Specify how the traversed IGMP/MLD control frames will be sent in prioritized manner.
                 The default Priority is 0."
            DEFVAL      { 0 }     
            ::= { ctcMvrVlanEntry 5 }

        -- 1.3.6.1.4.1.4756.104.80.4.1.6    
        ctcMvrVlanLLQI OBJECT-TYPE
            SYNTAX      Integer32 (0..31744)
            UNITS       "100ms"
            MAX-ACCESS  read-write
            STATUS      current
            DESCRIPTION
                "Define the maximum time to wait for IGMP/MLD report memberships on a receiver port
                 before removing the port from multicast group membership.
                 The value is in units of tenths of a seconds. The range is from 0 to 31744.
                 The default LLQI is 5 tenths or one-half second."
            DEFVAL      { 5 }     
            ::= { ctcMvrVlanEntry 6 }

        -- 1.3.6.1.4.1.4756.104.80.4.1.7
        ctcAddMvrVlanChannel OBJECT-TYPE
            SYNTAX      DisplayString
            MAX-ACCESS  read-write
            STATUS      current
            DESCRIPTION
                "Add new Channel for the MVR VLAN. Specify the Address and configure the new entry.
                 Retrieve number of Channel of MVR VLAN entry.
                 Syntax: [channel] [channel_bound]
                 channel      : IPv4/IPv6 multicast group address.                                                                     
                 channel_bound: The boundary IPv4/IPv6 multicast group address for the channel."
            ::= { ctcMvrVlanEntry 7 }

        -- 1.3.6.1.4.1.4756.104.80.4.1.8
        ctcDeleteMvrVlanChannel OBJECT-TYPE
            SYNTAX      DisplayString
            MAX-ACCESS  read-write
            STATUS      current
            DESCRIPTION
                "Delete Channel for the MVR VLAN..
                 Retrieve number of Channel of MVR VLAN entry.
                 Syntax: [channel]
                 channel: IPv4/IPv6 multicast group address."
            ::= { ctcMvrVlanEntry 8 }

    -- 1.3.6.1.4.1.4756.104.80.10
    ctcMvrVlanPortTable OBJECT-TYPE
        SYNTAX      SEQUENCE OF CtcMvrVlanPortEntry
        MAX-ACCESS  not-accessible
        STATUS      current
        DESCRIPTION
            "This table is used for configuring an MVR port of the designated MVR VLAN as a role."
        ::= { ctcMVR 10 }

    -- 1.3.6.1.4.1.4756.104.80.10.1
    ctcMvrVlanPortEntry OBJECT-TYPE
        SYNTAX      CtcMvrVlanPortEntry
        MAX-ACCESS  not-accessible
        STATUS      current
        DESCRIPTION
            "The Entry of MVR VLAN ports."
        INDEX { ctcMvrVlanID, ctcPortIndex }
        ::= { ctcMvrVlanPortTable 1 }

    CtcMvrVlanPortEntry ::=
        SEQUENCE {
            ctcMvrVlanPortRole       INTEGER          
        }

        -- 1.3.6.1.4.1.4756.104.80.10.1.1    
        ctcMvrVlanPortRole OBJECT-TYPE
            SYNTAX      INTEGER {
                            inactive(1),
                            source(2),
                            receiver(3)
                        }
            MAX-ACCESS  read-write
            STATUS      current
            DESCRIPTION
                "Configure an MVR port of the designated MVR VLAN as one of the following roles.
                 Inactive: The designated port does not participate MVR operations.
                 Source: Configure uplink ports that receive and send multicast data as source ports.
                         Subscribers cannot be directly connected to source ports.
                 Receiver: Configure a port as a receiver port if it is a subscriber port and should only receive multicast data.
                           It does not receive data unless it becomes a member of the multicast group by issuing IGMP/MLD messages.                           
                 Be Caution: MVR source ports are not recommended to be overlapped with management VLAN ports.
                 The default Role is Inactive."
            DEFVAL      { inactive }     
            ::= { ctcMvrVlanPortEntry 1 }

    -- 1.3.6.1.4.1.4756.104.80.20
    ctcMvrVlanChannelTable OBJECT-TYPE
        SYNTAX      SEQUENCE OF CtcMvrVlanChannelEntry
        MAX-ACCESS  not-accessible
        STATUS      current
        DESCRIPTION
            "This table provides MVR channel settings for a specific MVR VLAN.
             There will be totally at maximum 256 group addresses for channel settings."
        ::= { ctcMVR 20 }

    -- 1.3.6.1.4.1.4756.104.80.20.1
    ctcMvrVlanChannelEntry OBJECT-TYPE
        SYNTAX      CtcMvrVlanChannelEntry
        MAX-ACCESS  not-accessible
        STATUS      current
        DESCRIPTION
            "The Entry of MVR channel table."
        INDEX { ctcMvrVlanID, ctcMvrVlanChannelIndex }
        ::= { ctcMvrVlanChannelTable 1 }

    CtcMvrVlanChannelEntry ::=
        SEQUENCE {
            ctcMvrVlanChannelIndex           Integer32,
            ctcMvrVlanChannelStartAddress    DisplayString,
            ctcMvrVlanChannelEndAddress      DisplayString,
            ctcMvrVlanChannelName            OCTET STRING          
        }

        -- 1.3.6.1.4.1.4756.104.80.20.1.1    
        ctcMvrVlanChannelIndex OBJECT-TYPE
            SYNTAX      Integer32 (0..16)
            MAX-ACCESS  read-only
            STATUS      current
            DESCRIPTION
                "Indicate the MVR VLAN channel index."   
            ::= { ctcMvrVlanChannelEntry 1 }

        -- 1.3.6.1.4.1.4756.104.80.20.1.2    
        ctcMvrVlanChannelStartAddress OBJECT-TYPE
            SYNTAX      DisplayString
            MAX-ACCESS  read-only
            STATUS      current
            DESCRIPTION
                "The starting IPv4/IPv6 Multicast Group Address that will be used as a streaming channel."   
            ::= { ctcMvrVlanChannelEntry 2 }

        -- 1.3.6.1.4.1.4756.104.80.20.1.3    
        ctcMvrVlanChannelEndAddress OBJECT-TYPE
            SYNTAX      DisplayString
            MAX-ACCESS  read-write
            STATUS      current
            DESCRIPTION
                "The ending IPv4/IPv6 Multicast Group Address that will be used as a streaming channel."   
            ::= { ctcMvrVlanChannelEntry 3 }

        -- 1.3.6.1.4.1.4756.104.80.20.1.4    
        ctcMvrVlanChannelName OBJECT-TYPE
            SYNTAX      OCTET STRING (SIZE (0..32))
            MAX-ACCESS  read-write
            STATUS      current
            DESCRIPTION
                "Indicate the name of the Channel of the specific Multicast VLAN.
                 Maximum length of the Channel Name string is 32.
                 Channel Name can only contain alphabets or numbers.
                 Channel name should contain at least one alphabet.
                 Channel name can be edited for the existing Channel entries."   
            ::= { ctcMvrVlanChannelEntry 4 }

    -- 1.3.6.1.4.1.4756.104.80.30
    ctcMvrPortImmediateLeaveTable OBJECT-TYPE
        SYNTAX      SEQUENCE OF CtcMvrPortImmediateLeaveEntry
        MAX-ACCESS  not-accessible
        STATUS      current
        DESCRIPTION
            "This table is used for configuring the switch MVR port."
        ::= { ctcMVR 30 }

    -- 1.3.6.1.4.1.4756.104.80.30.1
    ctcMvrPortImmediateLeaveEntry OBJECT-TYPE
        SYNTAX      CtcMvrPortImmediateLeaveEntry
        MAX-ACCESS  not-accessible
        STATUS      current
        DESCRIPTION
            "The Entry of MVR ports."
        INDEX { ctcPortIndex }
        ::= { ctcMvrPortImmediateLeaveTable 1 }

    CtcMvrPortImmediateLeaveEntry ::=
        SEQUENCE {
            ctcMvrPortImmediateLeave       INTEGER          
        }

        -- 1.3.6.1.4.1.4756.104.80.30.1.1    
        ctcMvrPortImmediateLeave OBJECT-TYPE
            SYNTAX      INTEGER {
                            enabled(1),
                            disabled(2)
                        }
            MAX-ACCESS  read-write
            STATUS      current
            DESCRIPTION
                "Enable/Disable the fast leave on the port."  
            ::= { ctcMvrPortImmediateLeaveEntry 1 }

    -- 1.3.6.1.4.1.4756.104.80.40
    ctcMvrStatisticsClear OBJECT-TYPE
        SYNTAX      INTEGER {
                        trigger(1),
                        normal(2)
                    }
        MAX-ACCESS  read-write
        STATUS      current
        DESCRIPTION
            "Clears all Statistics counters."
        ::= { ctcMVR 40 }

    -- 1.3.6.1.4.1.4756.104.80.41
    ctcMvrStatisticsTable OBJECT-TYPE
        SYNTAX      SEQUENCE OF CtcMvrStatisticsEntry
        MAX-ACCESS  not-accessible
        STATUS      current
        DESCRIPTION
            "This table provides MVR Statistics information."
        ::= { ctcMVR 41 }

    -- 1.3.6.1.4.1.4756.104.80.41.1
    ctcMvrStatisticsEntry OBJECT-TYPE
        SYNTAX      CtcMvrStatisticsEntry
        MAX-ACCESS  not-accessible
        STATUS      current
        DESCRIPTION
            "The Entry of MVR VLAN Statistics."
        INDEX { ctcMvrVlanID }
        ::= { ctcMvrStatisticsTable 1 }

    CtcMvrStatisticsEntry ::=
        SEQUENCE {
            ctcMvrIgmpQueriesRx      Counter32,
            ctcMvrIgmpQueriesTx      Counter32,
            ctcMvrIgmpV1JoinsRx      Counter32,
            ctcMvrIgmpV2JoinsRx      Counter32,
            ctcMvrIgmpV3JoinsRx      Counter32,
            ctcMvrIgmpV2LeavesRx     Counter32,
            ctcMvrMldQueriesRx       Counter32,
            ctcMvrMldQueriesTx       Counter32,
            ctcMvrMldV1ReportsRx     Counter32,
            ctcMvrMldV2ReportsRx     Counter32,
            ctcMvrMldV1DonesRx       Counter32
        }
                  
        -- 1.3.6.1.4.1.4756.104.80.41.1.1    
        ctcMvrIgmpQueriesRx OBJECT-TYPE
            SYNTAX      Counter32
            UNITS       "Packets"
            MAX-ACCESS  read-only
            STATUS      current
            DESCRIPTION
                "The number of Received Queries for IGMP."
            ::= { ctcMvrStatisticsEntry 1 }
                  
        -- 1.3.6.1.4.1.4756.104.80.41.1.2    
        ctcMvrIgmpQueriesTx OBJECT-TYPE
            SYNTAX      Counter32
            UNITS       "Packets"
            MAX-ACCESS  read-only
            STATUS      current
            DESCRIPTION
                "The number of Transmitted Queries for IGMP."
            ::= { ctcMvrStatisticsEntry 2 }
                  
        -- 1.3.6.1.4.1.4756.104.80.41.1.3    
        ctcMvrIgmpV1JoinsRx OBJECT-TYPE
            SYNTAX      Counter32
            UNITS       "Packets"
            MAX-ACCESS  read-only
            STATUS      current
            DESCRIPTION
                "The number of Received IGMPv1 Join's."
            ::= { ctcMvrStatisticsEntry 3 }
                  
        -- 1.3.6.1.4.1.4756.104.80.41.1.4    
        ctcMvrIgmpV2JoinsRx OBJECT-TYPE
            SYNTAX      Counter32
            UNITS       "Packets"
            MAX-ACCESS  read-only
            STATUS      current
            DESCRIPTION
                "The number of Received IGMPv2 Join's."
            ::= { ctcMvrStatisticsEntry 4 }
                  
        -- 1.3.6.1.4.1.4756.104.80.41.1.5    
        ctcMvrIgmpV3JoinsRx OBJECT-TYPE
            SYNTAX      Counter32
            UNITS       "Packets"
            MAX-ACCESS  read-only
            STATUS      current
            DESCRIPTION
                "The number of Received IGMPv3 Join's."
            ::= { ctcMvrStatisticsEntry 5 }
                  
        -- 1.3.6.1.4.1.4756.104.80.41.1.6    
        ctcMvrIgmpV2LeavesRx OBJECT-TYPE
            SYNTAX      Counter32
            UNITS       "Packets"
            MAX-ACCESS  read-only
            STATUS      current
            DESCRIPTION
                "The number of Received IGMPv2 Leave's."
            ::= { ctcMvrStatisticsEntry 6 }
                  
        -- 1.3.6.1.4.1.4756.104.80.41.1.7    
        ctcMvrMldQueriesRx OBJECT-TYPE
            SYNTAX      Counter32
            UNITS       "Packets"
            MAX-ACCESS  read-only
            STATUS      current
            DESCRIPTION
                "The number of Received Queries for MLD."
            ::= { ctcMvrStatisticsEntry 7 }
                  
        -- 1.3.6.1.4.1.4756.104.80.41.1.8    
        ctcMvrMldQueriesTx OBJECT-TYPE
            SYNTAX      Counter32
            UNITS       "Packets"
            MAX-ACCESS  read-only
            STATUS      current
            DESCRIPTION
                "The number of Transmitted Queries for MLD."
            ::= { ctcMvrStatisticsEntry 8 }
                  
        -- 1.3.6.1.4.1.4756.104.80.41.1.9    
        ctcMvrMldV1ReportsRx OBJECT-TYPE
            SYNTAX      Counter32
            UNITS       "Packets"
            MAX-ACCESS  read-only
            STATUS      current
            DESCRIPTION
                "The number of Received MLDv1 Report's."
            ::= { ctcMvrStatisticsEntry 9 }
                  
        -- 1.3.6.1.4.1.4756.104.80.41.1.10    
        ctcMvrMldV2ReportsRx OBJECT-TYPE
            SYNTAX      Counter32
            UNITS       "Packets"
            MAX-ACCESS  read-only
            STATUS      current
            DESCRIPTION
                "The number of Received MLDv2 Report's."
            ::= { ctcMvrStatisticsEntry 10 }
                  
        -- 1.3.6.1.4.1.4756.104.80.41.1.11    
        ctcMvrMldV1DonesRx OBJECT-TYPE
            SYNTAX      Counter32
            UNITS       "Packets"
            MAX-ACCESS  read-only
            STATUS      current
            DESCRIPTION
                "The number of Received MLDv1 Done's."
            ::= { ctcMvrStatisticsEntry 11 }

    -- 1.3.6.1.4.1.4756.104.80.50
    ctcMvrChannelsInformationTable OBJECT-TYPE
        SYNTAX      SEQUENCE OF CtcMvrChannelsInformationEntry
        MAX-ACCESS  not-accessible
        STATUS      current
        DESCRIPTION
            "The MVR Channels (Groups) Information Table."
        ::= { ctcMVR 50 }

    -- 1.3.6.1.4.1.4756.104.80.50.1
    ctcMvrChannelsInformationEntry OBJECT-TYPE
        SYNTAX      CtcMvrChannelsInformationEntry
        MAX-ACCESS  not-accessible
        STATUS      current
        DESCRIPTION
            "The Entry of MVR Channels (Groups) Information Table."
        INDEX { ctcMvrVlanID, ctcMvrChannelsIndex }
        ::= { ctcMvrChannelsInformationTable 1 }

    CtcMvrChannelsInformationEntry ::=
        SEQUENCE {
            ctcMvrChannelsIndex      Integer32, 
            ctcMvrChannelsGroup      DisplayString,
            ctcMvrGroupPortMembers   DisplayString
        }

        -- 1.3.6.1.4.1.4756.104.80.50.1.1    
        ctcMvrChannelsIndex OBJECT-TYPE
            SYNTAX      Integer32 (1..128)
            MAX-ACCESS  read-only
            STATUS      current
            DESCRIPTION
                "Indicate the MVR channel group index."   
            ::= { ctcMvrChannelsInformationEntry 1 }
        
        -- 1.3.6.1.4.1.4756.104.80.50.1.2    
        ctcMvrChannelsGroup OBJECT-TYPE
            SYNTAX      DisplayString
            MAX-ACCESS  read-only
            STATUS      current
            DESCRIPTION
                "Group address of the group."
            ::= { ctcMvrChannelsInformationEntry 2 }

        -- 1.3.6.1.4.1.4756.104.80.50.1.3    
        ctcMvrGroupPortMembers OBJECT-TYPE
            SYNTAX      DisplayString
            MAX-ACCESS  read-only
            STATUS      current
            DESCRIPTION
                "Ports under this group."
            ::= { ctcMvrChannelsInformationEntry 3 }

    -- 1.3.6.1.4.1.4756.104.80.60
    ctcMvrSfmInformationTable OBJECT-TYPE
        SYNTAX      SEQUENCE OF CtcMvrSfmInformationEntry
        MAX-ACCESS  not-accessible
        STATUS      current
        DESCRIPTION
            "The MVR SFM Information Table."
        ::= { ctcMVR 60 }

    -- 1.3.6.1.4.1.4756.104.80.60.1
    ctcMvrSfmInformationEntry OBJECT-TYPE
        SYNTAX      CtcMvrSfmInformationEntry
        MAX-ACCESS  not-accessible
        STATUS      current
        DESCRIPTION
            "The Entry of MVR SFM Information Table."
        INDEX { ctcMvrVlanID, ctcMvrSfmGroupIndex, ctcPortIndex }
        ::= { ctcMvrSfmInformationTable 1 }

    CtcMvrSfmInformationEntry ::=
        SEQUENCE {
            ctcMvrSfmGroupIndex      Integer32, 
            ctcMvrSfmGroupAddress    DisplayString,
            ctcMvrSfmMode            INTEGER,
            ctcMvrSfmSourceAddress   DisplayString,
            ctcMvrSfmType            INTEGER,
            ctcMvrSfmHardwareFilter  INTEGER   
        }

        -- 1.3.6.1.4.1.4756.104.80.60.1.1    
        ctcMvrSfmGroupIndex OBJECT-TYPE
            SYNTAX      Integer32 (1..128)
            MAX-ACCESS  read-only
            STATUS      current
            DESCRIPTION
                "Indicate the MVR SFM Information entry index."   
            ::= { ctcMvrSfmInformationEntry 1 }

        -- 1.3.6.1.4.1.4756.104.80.60.1.2    
        ctcMvrSfmGroupAddress OBJECT-TYPE
            SYNTAX      DisplayString
            MAX-ACCESS  read-only
            STATUS      current
            DESCRIPTION
                "Group address of the group."
            ::= { ctcMvrSfmInformationEntry 2 }

        -- 1.3.6.1.4.1.4756.104.80.60.1.3    
        ctcMvrSfmMode OBJECT-TYPE
            SYNTAX      INTEGER {
                            include(1),
                            exclude(2)
                        }
            MAX-ACCESS  read-only
            STATUS      current
            DESCRIPTION
                "Indicates the filtering mode maintained per (VLAN ID, port number, Group Address) basis.
                 It can be either Include or Exclude."   
            ::= { ctcMvrSfmInformationEntry 3 }

        -- 1.3.6.1.4.1.4756.104.80.60.1.4    
        ctcMvrSfmSourceAddress OBJECT-TYPE
            SYNTAX      DisplayString
            MAX-ACCESS  read-only
            STATUS      current
            DESCRIPTION
                "IP Address of the source. Currently,
                 system limits the total number of IP source addresses for filtering to be 128.
                 When there is no any source filtering address, the text 'None' is retrieved."
            ::= { ctcMvrSfmInformationEntry 4 }

        -- 1.3.6.1.4.1.4756.104.80.60.1.5    
        ctcMvrSfmType OBJECT-TYPE
            SYNTAX      INTEGER {
                            allow(1),
                            deny(2)
                        }
            MAX-ACCESS  read-only
            STATUS      current
            DESCRIPTION
                "ndicates the Type. It can be either Allow or Deny."   
            ::= { ctcMvrSfmInformationEntry 5 }

        -- 1.3.6.1.4.1.4756.104.80.60.1.6    
        ctcMvrSfmHardwareFilter OBJECT-TYPE
            SYNTAX      INTEGER {
                            yes(1),
                            no(2)
                        }
            MAX-ACCESS  read-only
            STATUS      current
            DESCRIPTION
                "Indicates whether data plane destined to the specific group address from
                 the source IPv4/IPv6 address could be handled by chip or not."   
            ::= { ctcMvrSfmInformationEntry 6 }

             
-- IPMC
    -- 1.3.6.1.4.1.4756.104.90
    ctcIPMC  OBJECT IDENTIFIER ::= { gsw2008ms 90 }

    -- 1.3.6.1.4.1.4756.104.90.1
    ctcIgmpSnooping  OBJECT IDENTIFIER ::= { ctcIPMC 1 }

    -- 1.3.6.1.4.1.4756.104.90.1.1
    ctcIgmpSnoopingEnabled OBJECT-TYPE
        SYNTAX      TruthValue
        MAX-ACCESS  read-write
        STATUS      current
        DESCRIPTION                                  
            "Enable the Global IGMP Snooping."
        ::= { ctcIgmpSnooping 1 }

    -- 1.3.6.1.4.1.4756.104.90.1.2
    ctcUnregisteredIpmcV4FloodingEnabled OBJECT-TYPE
        SYNTAX      TruthValue
        MAX-ACCESS  read-write
        STATUS      current
        DESCRIPTION                                  
            "Enable unregistered IPMC traffic flooding."
        ::= { ctcIgmpSnooping 2 }

    -- 1.3.6.1.4.1.4756.104.90.1.3
    ctcIgmpSsmRange OBJECT-TYPE
        SYNTAX      DisplayString
        MAX-ACCESS  read-write
        STATUS      current
        DESCRIPTION                                  
            "SSM (Source-Specific Multicast) Range allows the SSM-aware hosts and
             routers run the SSM service model for the groups in the address range.
             Syntax: (Range <mask_len>)"
        ::= { ctcIgmpSnooping 3 }

    -- 1.3.6.1.4.1.4756.104.90.1.4
    ctcIgmpLeaveProxyEnabled OBJECT-TYPE
        SYNTAX      TruthValue
        MAX-ACCESS  read-write
        STATUS      current
        DESCRIPTION                                  
            "Enable IGMP Leave Proxy.
             This feature can be used to avoid forwarding unnecessary leave messages to
             the router side."
        ::= { ctcIgmpSnooping 4 }

    -- 1.3.6.1.4.1.4756.104.90.1.5
    ctcIgmpProxyEnabled OBJECT-TYPE
        SYNTAX      TruthValue
        MAX-ACCESS  read-write
        STATUS      current
        DESCRIPTION                                  
            "Enable IGMP Proxy.
             This feature can be used to avoid forwarding unnecessary join and
             leave messages to the router side."
        ::= { ctcIgmpSnooping 5 }

    -- 1.3.6.1.4.1.4756.104.90.1.10
    ctcIgmpPortRelatedTable OBJECT-TYPE
        SYNTAX      SEQUENCE OF CtcIgmpPortRelatedEntry
        MAX-ACCESS  not-accessible
        STATUS      current
        DESCRIPTION
            "This table is used for configuring the Port Related."
        ::= { ctcIgmpSnooping 10 }

    -- 1.3.6.1.4.1.4756.104.90.1.10.1
    ctcIgmpPortRelatedEntry OBJECT-TYPE
        SYNTAX      CtcIgmpPortRelatedEntry
        MAX-ACCESS  not-accessible
        STATUS      current
        DESCRIPTION
            "The Entry of Port Related configurations."
        INDEX { ctcPortIndex }
        ::= { ctcIgmpPortRelatedTable 1 }

    CtcIgmpPortRelatedEntry ::=
        SEQUENCE {
            ctcIgmpRouterPortEnabled TruthValue,
            ctcIgmpRouterPortStatus  INTEGER,          
            ctcIgmpFastLeaveEnabled  TruthValue,
            ctcIgmpThrottling        Integer32
        }

        -- 1.3.6.1.4.1.4756.104.90.1.10.1.1    
        ctcIgmpRouterPortEnabled OBJECT-TYPE
            SYNTAX      TruthValue
            MAX-ACCESS  read-write
            STATUS      current
            DESCRIPTION
                "Specify which ports act as router ports.
                 A router port is a port on the Ethernet switch that
                 leads towards the Layer 3 multicast device or IGMP querier.
                 If an aggregation member port is selected as a router port,
                 the whole aggregation will act as a router port."
            ::= { ctcIgmpPortRelatedEntry 1 }

        -- 1.3.6.1.4.1.4756.104.90.1.10.1.2    
        ctcIgmpRouterPortStatus OBJECT-TYPE
            SYNTAX      INTEGER {
                            none(1),
                            static(2),
                            dynamic(3),
                            both(4)
                        }
            MAX-ACCESS  read-only
            STATUS      current
            DESCRIPTION
                "Shows IGMP router port mode."
            ::= { ctcIgmpPortRelatedEntry 2 }

        -- 1.3.6.1.4.1.4756.104.90.1.10.1.3    
        ctcIgmpFastLeaveEnabled OBJECT-TYPE
            SYNTAX      TruthValue
            MAX-ACCESS  read-write
            STATUS      current
            DESCRIPTION
                "Enable the fast leave on the port."
            ::= { ctcIgmpPortRelatedEntry 3 }

        -- 1.3.6.1.4.1.4756.104.90.1.10.1.4    
        ctcIgmpThrottling OBJECT-TYPE
            SYNTAX      Integer32 (0..10)
            MAX-ACCESS  read-write
            STATUS      current
            DESCRIPTION
                "Enable to limit the number of multicast groups to which a switch port can belong.
                 Set to zero for unlimited."
            ::= { ctcIgmpPortRelatedEntry 4 }

    -- 1.3.6.1.4.1.4756.104.90.1.20
    ctcAddIgmpVlan OBJECT-TYPE
        SYNTAX      Integer32 (1..4095)
        MAX-ACCESS  read-write
        STATUS      current
        DESCRIPTION                                  
            "Add a new entry to the IGMP VLAN table.
             Specify the VID and configure the new entry.
             The specific IGMP VLAN starts working after the corresponding static VLAN is also created."
        ::= { ctcIgmpSnooping 20 }

    -- 1.3.6.1.4.1.4756.104.90.1.21
    ctcDeleteIgmpVlan OBJECT-TYPE
        SYNTAX      Integer32 (1..4095)
        MAX-ACCESS  read-write
        STATUS      current
        DESCRIPTION
            "Delete an IGMP VLAN from table."
        ::= { ctcIgmpSnooping 21 }

    -- 1.3.6.1.4.1.4756.104.90.1.22
    ctcIgmpVlanConfigTable OBJECT-TYPE
        SYNTAX      SEQUENCE OF CtcIgmpVlanConfigEntry
        MAX-ACCESS  not-accessible
        STATUS      current
        DESCRIPTION
            "This table allows for configure IGMP snooping VLAN."
        ::= { ctcIgmpSnooping 22 }

    -- 1.3.6.1.4.1.4756.104.90.1.22.1
    ctcIgmpVlanConfigEntry OBJECT-TYPE
        SYNTAX      CtcIgmpVlanConfigEntry
        MAX-ACCESS  not-accessible
        STATUS      current
        DESCRIPTION
            "The Entry of IGMP snooping VLAN."
        INDEX { ctcIgmpVlanID }
        ::= { ctcIgmpVlanConfigTable 1 }

    CtcIgmpVlanConfigEntry ::=
        SEQUENCE {     
            ctcIgmpVlanID            Integer32,
            ctcIgmpPerVlanEnabled    TruthValue,
            ctcIgmpQuerierEnabled    TruthValue,
            ctcIgmpCompatibility     INTEGER,
            ctcIgmpRV                Integer32,
            ctcIgmpQI                Integer32,
            ctcIgmpQRI               Integer32,
            ctcIgmpLLQI              Integer32,
            ctcIgmpURI               Integer32           
        }

        -- 1.3.6.1.4.1.4756.104.90.1.22.1.1    
        ctcIgmpVlanID OBJECT-TYPE
            SYNTAX      Integer32 (1..4095)
            MAX-ACCESS  read-only
            STATUS      current
            DESCRIPTION
                "Indicates the ID of this particular IGMP snooping VLAN."
            ::= { ctcIgmpVlanConfigEntry 1 }

        -- 1.3.6.1.4.1.4756.104.90.1.22.1.2    
        ctcIgmpPerVlanEnabled OBJECT-TYPE
            SYNTAX      TruthValue
            MAX-ACCESS  read-write
            STATUS      current
            DESCRIPTION
                "Enable the per-VLAN IGMP Snooping. Only up to 64 VLANs can be selected."
            ::= { ctcIgmpVlanConfigEntry 2 }

        -- 1.3.6.1.4.1.4756.104.90.1.22.1.3    
        ctcIgmpQuerierEnabled OBJECT-TYPE
            SYNTAX      TruthValue
            MAX-ACCESS  read-write
            STATUS      current
            DESCRIPTION
                "Enable the IGMP Querier in the VLAN."
            ::= { ctcIgmpVlanConfigEntry 3 }

        -- 1.3.6.1.4.1.4756.104.90.1.22.1.4    
        ctcIgmpCompatibility OBJECT-TYPE
            SYNTAX      INTEGER {
                            forcedIgmpV1(1),
                            forcedIgmpV2(2),
                            forcedIgmpV3(3),
            	            igmpAuto(4)
            	        }
            MAX-ACCESS  read-write
            STATUS      current
            DESCRIPTION
                "Compatibility is maintained by hosts and routers taking appropriate actions depending on
                 the versions of IGMP operating on hosts and routers within a network.
                 The allowed selection is IGMP-Auto, Forced IGMPv1, Forced IGMPv2, Forced IGMPv3,
                 default compatibility value is IGMP-Auto."
            DEFVAL      { igmpAuto }
            ::= { ctcIgmpVlanConfigEntry 4 }

        -- 1.3.6.1.4.1.4756.104.90.1.22.1.5    
        ctcIgmpRV OBJECT-TYPE
            SYNTAX      Integer32 (1..255)
            MAX-ACCESS  read-write
            STATUS      current
            DESCRIPTION
                "Robustness Variable.
                 The Robustness Variable allows tuning for the expected packet loss on a network.
                 The allowed range is 1 to 255, default robustness variable value is 2,
                 Robustness Variable SHOULD NOT be one."
            DEFVAL     { 2 }
            ::= { ctcIgmpVlanConfigEntry 5 }

        -- 1.3.6.1.4.1.4756.104.90.1.22.1.6    
        ctcIgmpQI OBJECT-TYPE
            SYNTAX      Integer32 (1..255)
            UNITS       "Seconds"
            MAX-ACCESS  read-write
            STATUS      current
            DESCRIPTION
                "Query Interval.
                 The Query Interval is the interval between General Queries sent by the Querier.
                 The allowed range is 1 to 255 seconds, default query interval is 125 seconds.
                 Note: The number of seconds represented by QRI must be less than QI!"
            DEFVAL     { 125 }     
            ::= { ctcIgmpVlanConfigEntry 6 }

        -- 1.3.6.1.4.1.4756.104.90.1.22.1.7    
        ctcIgmpQRI OBJECT-TYPE
            SYNTAX      Integer32 (0..31744)
            UNITS       "100 millisecond"
            MAX-ACCESS  read-write
            STATUS      current
            DESCRIPTION
                "Query Response Interval.
                 The Max Response Time used to calculate the Max Resp Code inserted into the periodic General Queries.
                 The allowed range is 0 to 31744 in tenths of seconds,
                 default query response interval is 100 in tenths of seconds (10 seconds).
                 The number of seconds represented by QRI must be less than QI!"
            DEFVAL     { 100 }     
            ::= { ctcIgmpVlanConfigEntry 7 }

        -- 1.3.6.1.4.1.4756.104.90.1.22.1.8    
        ctcIgmpLLQI OBJECT-TYPE
            SYNTAX      Integer32 (0..31744)
            UNITS       "100 millisecond"
            MAX-ACCESS  read-write
            STATUS      current
            DESCRIPTION
                "Last Member Query Interval.
                 The Last Member Query Time is the time value represented by the Last Member Query Interval,
                 multiplied by the Last Member Query Count.
                 The allowed range is 0 to 31744 in tenths of seconds,
                 default last member query interval is 10 in tenths of seconds (1 second)."
            DEFVAL     { 10 }     
            ::= { ctcIgmpVlanConfigEntry 8 }

        -- 1.3.6.1.4.1.4756.104.90.1.22.1.9    
        ctcIgmpURI OBJECT-TYPE
            SYNTAX      Integer32 (0..31744)
            UNITS       "Seconds"
            MAX-ACCESS  read-write
            STATUS      current
            DESCRIPTION
                "Unsolicited Report Interval.
                 The Unsolicited Report Interval is the time between repetitions of
                 a host's initial report of membership in a group.
                 The allowed range is 0 to 31744 seconds,
                 default unsolicited report interval is 1 second."
            DEFVAL     { 1 }     
            ::= { ctcIgmpVlanConfigEntry 9 }

    -- 1.3.6.1.4.1.4756.104.90.1.30
    ctcAddIgmpPortFilteringGroup OBJECT-TYPE
        SYNTAX      DisplayString
        MAX-ACCESS  read-write
        STATUS      current
        DESCRIPTION                                  
            "Add a new entry to the Group Filtering table.
             Specify the Port, and Filtering Group of the new entry.
             Syntax: <port_no> <group_addr>
             The IGMP Snooping can support maximum 5 entries per port."
        ::= { ctcIgmpSnooping 30 }

    -- 1.3.6.1.4.1.4756.104.90.1.31
    ctcDeleteIgmpPortFilteringGroup OBJECT-TYPE
        SYNTAX      DisplayString
        MAX-ACCESS  read-write
        STATUS      current
        DESCRIPTION
            "Delete an IGMP Snooping Port Group Filtering from table.
             Syntax: <port_no> <group_addr>"
        ::= { ctcIgmpSnooping 31 }

    -- 1.3.6.1.4.1.4756.104.90.1.32
    ctcIgmpPortGroupFilteringTable OBJECT-TYPE
        SYNTAX      SEQUENCE OF CtcIgmpPortGroupFilteringEntry
        MAX-ACCESS  not-accessible
        STATUS      current
        DESCRIPTION
            "This table is used for configuring the port group filtering."
        ::= { ctcIgmpSnooping 32 }

    -- 1.3.6.1.4.1.4756.104.90.1.32.1
    ctcIgmpPortGroupFilteringEntry OBJECT-TYPE
        SYNTAX      CtcIgmpPortGroupFilteringEntry
        MAX-ACCESS  not-accessible
        STATUS      current
        DESCRIPTION
            "The Entry of port group filtering configurations."
        INDEX { ctcIgmpPortGroupFilteringIndex }
        ::= { ctcIgmpPortGroupFilteringTable 1 }

    CtcIgmpPortGroupFilteringEntry ::=
        SEQUENCE {
            ctcIgmpPortGroupFilteringIndex   Integer32,          
            ctcIgmpPortGroupFilteringPort    Integer32,
            ctcIgmpPortGroupFilteringGroups  IpAddress
        }

        -- 1.3.6.1.4.1.4756.104.90.1.32.1.1    
        ctcIgmpPortGroupFilteringIndex OBJECT-TYPE
            SYNTAX      Integer32 (1..50)
            MAX-ACCESS  read-only
            STATUS      current
            DESCRIPTION
                "The index of IGMP snooping port group filtering entry."
            ::= { ctcIgmpPortGroupFilteringEntry 1 }

        -- 1.3.6.1.4.1.4756.104.90.1.32.1.2    
        ctcIgmpPortGroupFilteringPort OBJECT-TYPE
            SYNTAX      Integer32 (1..6)
            MAX-ACCESS  read-only
            STATUS      current
            DESCRIPTION
                "The logical port for the settings."
            ::= { ctcIgmpPortGroupFilteringEntry 2 }

        -- 1.3.6.1.4.1.4756.104.90.1.32.1.3    
        ctcIgmpPortGroupFilteringGroups OBJECT-TYPE
            SYNTAX      IpAddress
            MAX-ACCESS  read-only
            STATUS      current
            DESCRIPTION
                "The IP Multicast Group that will be filtered."
            ::= { ctcIgmpPortGroupFilteringEntry 3 }

    -- 1.3.6.1.4.1.4756.104.90.1.40
    ctcIgmpSnoopingStatisticsClear OBJECT-TYPE
        SYNTAX      INTEGER {
                        trigger(1),
                        normal(2)
                    }
        MAX-ACCESS  read-write
        STATUS      current
        DESCRIPTION
            "Clears all Statistics counters."
        ::= { ctcIgmpSnooping 40 }

    -- 1.3.6.1.4.1.4756.104.90.1.41
    ctcIgmpSnoopingStatisticsTable OBJECT-TYPE
        SYNTAX      SEQUENCE OF CtcIgmpSnoopingStatisticsEntry
        MAX-ACCESS  not-accessible
        STATUS      current
        DESCRIPTION
            "This table provides IGMP Snooping status."
        ::= { ctcIgmpSnooping 41 }

    -- 1.3.6.1.4.1.4756.104.90.1.41.1
    ctcIgmpSnoopingStatisticsEntry OBJECT-TYPE
        SYNTAX      CtcIgmpSnoopingStatisticsEntry
        MAX-ACCESS  not-accessible
        STATUS      current
        DESCRIPTION
            "The Entry of VLAN ID."
        INDEX { ctcIgmpSnoopingVlanID }
        ::= { ctcIgmpSnoopingStatisticsTable 1 }

    CtcIgmpSnoopingStatisticsEntry ::=
        SEQUENCE {       
            ctcIgmpSnoopingVlanID        Integer32,
            ctcIgmpQuerierVersion        Integer32,
            ctcIgmpHostVersion           Integer32,
            ctcIgmpQuerierStatus         INTEGER,
            ctcIgmpQueriesTransmitted    Counter32,
            ctcIgmpQueriesReceived       Counter32,
            ctcIgmpV1ReportsReceived     Counter32,
            ctcIgmpV2ReportsReceived     Counter32,
            ctcIgmpV3ReportsReceived     Counter32,
            ctcIgmpV2LeavesReceived      Counter32
        }
        
        -- 1.3.6.1.4.1.4756.104.90.1.41.1.1    
        ctcIgmpSnoopingVlanID OBJECT-TYPE
            SYNTAX      Integer32 (1..4095)
            MAX-ACCESS  read-only
            STATUS      current
            DESCRIPTION
                 "The VLAN ID of the entry."
            ::= { ctcIgmpSnoopingStatisticsEntry 1 }

        -- 1.3.6.1.4.1.4756.104.90.1.41.1.2    
        ctcIgmpQuerierVersion OBJECT-TYPE
            SYNTAX      Integer32 (1..3)
            MAX-ACCESS  read-only
            STATUS      current
            DESCRIPTION
                "Working Querier Version currently."
            ::= { ctcIgmpSnoopingStatisticsEntry 2 }

        -- 1.3.6.1.4.1.4756.104.90.1.41.1.3    
        ctcIgmpHostVersion OBJECT-TYPE
            SYNTAX      Integer32 (1..3)
            MAX-ACCESS  read-only
            STATUS      current
            DESCRIPTION
                "Working Host Version currently."
            ::= { ctcIgmpSnoopingStatisticsEntry 3 }

        -- 1.3.6.1.4.1.4756.104.90.1.41.1.4    
        ctcIgmpQuerierStatus OBJECT-TYPE
            SYNTAX      INTEGER {
                            idle(1),
                            active(2),
                            disable(3)
                        }
            MAX-ACCESS  read-only
            STATUS      current
            DESCRIPTION
                "Shows the Querier status is ACTIVE or IDLE.
                 DISABLE denotes the specific interface is administratively disabled."
            ::= { ctcIgmpSnoopingStatisticsEntry 4 }

        -- 1.3.6.1.4.1.4756.104.90.1.41.1.5    
        ctcIgmpQueriesTransmitted OBJECT-TYPE
            SYNTAX      Counter32
            UNITS       "Packets"
            MAX-ACCESS  read-only
            STATUS      current
            DESCRIPTION
                "The number of Transmitted Queries."
            ::= { ctcIgmpSnoopingStatisticsEntry 5 }

        -- 1.3.6.1.4.1.4756.104.90.1.41.1.6    
        ctcIgmpQueriesReceived OBJECT-TYPE
            SYNTAX      Counter32
            UNITS       "Packets"
            MAX-ACCESS  read-only
            STATUS      current
            DESCRIPTION
                "The number of Received Queries."
            ::= { ctcIgmpSnoopingStatisticsEntry 6 }

        -- 1.3.6.1.4.1.4756.104.90.1.41.1.7    
        ctcIgmpV1ReportsReceived OBJECT-TYPE
            SYNTAX      Counter32
            UNITS       "Packets"
            MAX-ACCESS  read-only
            STATUS      current
            DESCRIPTION
                "The number of Received V1 Reports."
            ::= { ctcIgmpSnoopingStatisticsEntry 7 }

        -- 1.3.6.1.4.1.4756.104.90.1.41.1.8    
        ctcIgmpV2ReportsReceived OBJECT-TYPE
            SYNTAX      Counter32
            UNITS       "Packets"
            MAX-ACCESS  read-only
            STATUS      current
            DESCRIPTION
                "The number of Received V2 Reports."
            ::= { ctcIgmpSnoopingStatisticsEntry 8 }

        -- 1.3.6.1.4.1.4756.104.90.1.41.1.9    
        ctcIgmpV3ReportsReceived OBJECT-TYPE
            SYNTAX      Counter32
            UNITS       "Packets"
            MAX-ACCESS  read-only
            STATUS      current
            DESCRIPTION
                "The number of Received V3 Reports."
            ::= { ctcIgmpSnoopingStatisticsEntry 9 }

        -- 1.3.6.1.4.1.4756.104.90.1.41.1.10    
        ctcIgmpV2LeavesReceived OBJECT-TYPE
            SYNTAX      Counter32
            UNITS       "Packets"
            MAX-ACCESS  read-only
            STATUS      current
            DESCRIPTION
                "The number of Received V2 Leaves."
            ::= { ctcIgmpSnoopingStatisticsEntry 10 }

    -- 1.3.6.1.4.1.4756.104.90.1.50
    ctcIgmpGroupsInfoTable OBJECT-TYPE
        SYNTAX      SEQUENCE OF CtcIgmpGroupsInfoEntry
        MAX-ACCESS  not-accessible
        STATUS      current
        DESCRIPTION
            "This table shows IGMP snooping groups information."
        ::= { ctcIgmpSnooping 50 }

    -- 1.3.6.1.4.1.4756.104.90.1.50.1
    ctcIgmpGroupsInfoEntry OBJECT-TYPE
        SYNTAX      CtcIgmpGroupsInfoEntry
        MAX-ACCESS  not-accessible
        STATUS      current
        DESCRIPTION
            "The Entry of IGMP snooping groups information."
        INDEX { ctcIgmpGroupsInfoIndex }
        ::= { ctcIgmpGroupsInfoTable 1 }

    CtcIgmpGroupsInfoEntry ::=
        SEQUENCE {
            ctcIgmpGroupsInfoIndex    Integer32,
            ctcIgmpGroupsInfoVlanID   Integer32,          
            ctcIgmpGroupsInfo         IpAddress,
            ctcIgmpGroupsPortMembers  DisplayString
        }

        -- 1.3.6.1.4.1.4756.104.90.1.50.1.1    
        ctcIgmpGroupsInfoIndex OBJECT-TYPE
            SYNTAX      Integer32 (1..4095)
            MAX-ACCESS  read-only
            STATUS      current
            DESCRIPTION
                "Entries in the IGMP group table."
            ::= { ctcIgmpGroupsInfoEntry 1 }

        -- 1.3.6.1.4.1.4756.104.90.1.50.1.2    
        ctcIgmpGroupsInfoVlanID OBJECT-TYPE
            SYNTAX      Integer32 (1..4095)
            MAX-ACCESS  read-only
            STATUS      current
            DESCRIPTION
                "VLAN ID of the group."
            ::= { ctcIgmpGroupsInfoEntry 2 }

        -- 1.3.6.1.4.1.4756.104.90.1.50.1.3    
        ctcIgmpGroupsInfo OBJECT-TYPE
            SYNTAX      IpAddress
            MAX-ACCESS  read-only
            STATUS      current
            DESCRIPTION
                "Group address of the entry."
            ::= { ctcIgmpGroupsInfoEntry 3 }

        -- 1.3.6.1.4.1.4756.104.90.1.50.1.4    
        ctcIgmpGroupsPortMembers OBJECT-TYPE
            SYNTAX      DisplayString
            MAX-ACCESS  read-only
            STATUS      current
            DESCRIPTION
                "Ports under this group."
            ::= { ctcIgmpGroupsInfoEntry 4 }

    -- 1.3.6.1.4.1.4756.104.90.1.60
    ctcIgmpSfmInfoTable OBJECT-TYPE
        SYNTAX      SEQUENCE OF CtcIgmpSfmInfoEntry
        MAX-ACCESS  not-accessible
        STATUS      current
        DESCRIPTION
            "This table shows IGMP SSM(Source-Filtered Multicast) information.
             The IGMP SFM Information Table also contains the SSM(Source-Specific Multicast) information."
        ::= { ctcIgmpSnooping 60 }

    -- 1.3.6.1.4.1.4756.104.90.1.60.1
    ctcIgmpSfmInfoEntry OBJECT-TYPE
        SYNTAX      CtcIgmpSfmInfoEntry
        MAX-ACCESS  not-accessible
        STATUS      current
        DESCRIPTION
            "The Entry of IGMP SSM information."
        INDEX { ctcIgmpSfmInfoIndex }
        ::= { ctcIgmpSfmInfoTable 1 }

    CtcIgmpSfmInfoEntry ::=
        SEQUENCE {
            ctcIgmpSfmInfoIndex              Integer32,
            ctcIgmpSfmInfoVlanID             Integer32,
            ctcIgmpSfmInfoGroup              IpAddress,          
            ctcIgmpSfmPortNumber             Integer32,
            ctcIgmpSfmMode                   INTEGER,
            ctcIgmpSfmSourceAddress          IpAddress,
            ctcIgmpSfmType                   INTEGER,
            ctcIgmpSfmHardwareFilterSwitch   INTEGER
        }

        -- 1.3.6.1.4.1.4756.104.90.1.60.1.1    
        ctcIgmpSfmInfoIndex OBJECT-TYPE
            SYNTAX      Integer32 (1..4095)
            MAX-ACCESS  read-only
            STATUS      current
            DESCRIPTION
                "Entries in the IGMP SSM information table."
            ::= { ctcIgmpSfmInfoEntry 1 }

        -- 1.3.6.1.4.1.4756.104.90.1.60.1.2    
        ctcIgmpSfmInfoVlanID OBJECT-TYPE
            SYNTAX      Integer32 (1..4095)
            MAX-ACCESS  read-only
            STATUS      current
            DESCRIPTION
                "VLAN ID of the group."
            ::= { ctcIgmpSfmInfoEntry 2 }

        -- 1.3.6.1.4.1.4756.104.90.1.60.1.3    
        ctcIgmpSfmInfoGroup OBJECT-TYPE
            SYNTAX      IpAddress
            MAX-ACCESS  read-only
            STATUS      current
            DESCRIPTION
                "Group address of the entry."
            ::= { ctcIgmpSfmInfoEntry 3 }

        -- 1.3.6.1.4.1.4756.104.90.1.60.1.4    
        ctcIgmpSfmPortNumber OBJECT-TYPE
            SYNTAX      Integer32 (1..6)
            MAX-ACCESS  read-only
            STATUS      current
            DESCRIPTION
                "Switch port number."
            ::= { ctcIgmpSfmInfoEntry 4 }

        -- 1.3.6.1.4.1.4756.104.90.1.60.1.5    
        ctcIgmpSfmMode OBJECT-TYPE
            SYNTAX      INTEGER {
                            exclude(1),
                            include(2)
                        }
            MAX-ACCESS  read-only
            STATUS      current
            DESCRIPTION
                "Indicates the filtering mode maintained per (VLAN ID, port number, Group Address) basis.
                 It can be either Include or Exclude."
            ::= { ctcIgmpSfmInfoEntry 5 }

        -- 1.3.6.1.4.1.4756.104.90.1.60.1.6    
        ctcIgmpSfmSourceAddress OBJECT-TYPE
            SYNTAX      IpAddress
            MAX-ACCESS  read-only
            STATUS      current
            DESCRIPTION
                "IP Address of the source.
                 Currently, system limits the total number of IP source addresses for filtering to be 128."
            ::= { ctcIgmpSfmInfoEntry 6 }

        -- 1.3.6.1.4.1.4756.104.90.1.60.1.7    
        ctcIgmpSfmType OBJECT-TYPE
            SYNTAX      INTEGER {
                            deny(1),
                            allow(2)
                        }
            MAX-ACCESS  read-only
            STATUS      current
            DESCRIPTION
                "Indicates the Type. It can be either Allow or Deny."
            ::= { ctcIgmpSfmInfoEntry 7 }

        -- 1.3.6.1.4.1.4756.104.90.1.60.1.8    
        ctcIgmpSfmHardwareFilterSwitch OBJECT-TYPE
            SYNTAX      INTEGER {
                            no(1),
                            yes(2)
                        }
            MAX-ACCESS  read-only
            STATUS      current
            DESCRIPTION
                "Indicates whether data plane destined to the specific group address from
                 the source IPv4 address could be handled by chip or not."
            ::= { ctcIgmpSfmInfoEntry 8 }

--MLD Snooping
    -- 1.3.6.1.4.1.4756.104.90.2
    ctcMldSnooping  OBJECT IDENTIFIER ::= { ctcIPMC 2 }

    -- 1.3.6.1.4.1.4756.104.90.2.1
    ctcMldSnoopingEnabled OBJECT-TYPE
        SYNTAX      TruthValue
        MAX-ACCESS  read-write
        STATUS      current
        DESCRIPTION                                  
            "Enable the Global MLD Snooping."
        ::= { ctcMldSnooping 1 }

    -- 1.3.6.1.4.1.4756.104.90.2.2
    ctcUnregisteredIpmcV6FloodingEnabled OBJECT-TYPE
        SYNTAX      TruthValue
        MAX-ACCESS  read-write
        STATUS      current
        DESCRIPTION                                  
            "Enable unregistered IPMCv6 traffic flooding.
             Please note that disabling unregistered IPMCv6 traffic flooding
             may lead to failure of Neighbor Discovery."
        ::= { ctcMldSnooping 2 }

    -- 1.3.6.1.4.1.4756.104.90.2.3
    ctcMldSsmRange OBJECT-TYPE
        SYNTAX      DisplayString
        MAX-ACCESS  read-write
        STATUS      current
        DESCRIPTION                                  
            "SSM (Source-Specific Multicast) Range allows the SSM-aware hosts and
             routers run the SSM service model for the groups in the address range.
             Syntax: (Range <prefix>)"
        ::= { ctcMldSnooping 3 }

    -- 1.3.6.1.4.1.4756.104.90.2.4
    ctcMldLeaveProxyEnabled OBJECT-TYPE
        SYNTAX      TruthValue
        MAX-ACCESS  read-write
        STATUS      current
        DESCRIPTION                                  
            "Enable MLD Leave Proxy.
             This feature can be used to avoid forwarding unnecessary leave messages to
             the router side."
        ::= { ctcMldSnooping 4 }

    -- 1.3.6.1.4.1.4756.104.90.2.5
    ctcMldProxyEnabled OBJECT-TYPE
        SYNTAX      TruthValue
        MAX-ACCESS  read-write
        STATUS      current
        DESCRIPTION                                  
            "Enable MLD Proxy.
             This feature can be used to avoid forwarding unnecessary join and
             leave messages to the router side."
        ::= { ctcMldSnooping 5 }

    -- 1.3.6.1.4.1.4756.104.90.2.10
    ctcMldPortRelatedTable OBJECT-TYPE
        SYNTAX      SEQUENCE OF CtcMldPortRelatedEntry
        MAX-ACCESS  not-accessible
        STATUS      current
        DESCRIPTION
            "This table is used for configuring the Port Related."
        ::= { ctcMldSnooping 10 }

    -- 1.3.6.1.4.1.4756.104.90.2.10.1
    ctcMldPortRelatedEntry OBJECT-TYPE
        SYNTAX      CtcMldPortRelatedEntry
        MAX-ACCESS  not-accessible
        STATUS      current
        DESCRIPTION
            "The Entry of Port Related configurations."
        INDEX { ctcPortIndex }
        ::= { ctcMldPortRelatedTable 1 }

    CtcMldPortRelatedEntry ::=
        SEQUENCE {
            ctcMldRouterPortEnabled  TruthValue,
            ctcMldRouterPortStatus   INTEGER,          
            ctcMldFastLeaveEnabled   TruthValue,
            ctcMldThrottling         Integer32
        }

        -- 1.3.6.1.4.1.4756.104.90.2.10.1.1    
        ctcMldRouterPortEnabled OBJECT-TYPE
            SYNTAX      TruthValue
            MAX-ACCESS  read-write
            STATUS      current
            DESCRIPTION
                "Specify which ports act as router ports.
                 A router port is a port on the Ethernet switch that
                 leads towards the Layer 3 multicast device or MLD querier.
                 If an aggregation member port is selected as a router port,
                 the whole aggregation will act as a router port."
            ::= { ctcMldPortRelatedEntry 1 }

        -- 1.3.6.1.4.1.4756.104.90.2.10.1.2    
        ctcMldRouterPortStatus OBJECT-TYPE
            SYNTAX      INTEGER {
                            none(1),
                            static(2),
                            dynamic(3),
                            both(4)
                        }
            MAX-ACCESS  read-only
            STATUS      current
            DESCRIPTION
                "Shows MLD router port mode."
            ::= { ctcMldPortRelatedEntry 2 }

        -- 1.3.6.1.4.1.4756.104.90.2.10.1.3    
        ctcMldFastLeaveEnabled OBJECT-TYPE
            SYNTAX      TruthValue
            MAX-ACCESS  read-write
            STATUS      current
            DESCRIPTION
                "Enable the fast leave on the port."
            ::= { ctcMldPortRelatedEntry 3 }

        -- 1.3.6.1.4.1.4756.104.90.2.10.1.4    
        ctcMldThrottling OBJECT-TYPE
            SYNTAX      Integer32 (0..10)
            MAX-ACCESS  read-write
            STATUS      current
            DESCRIPTION
                "Enable to limit the number of multicast groups to which a switch port can belong.
                 Set to zero for unlimited."
            ::= { ctcMldPortRelatedEntry 4 }

    -- 1.3.6.1.4.1.4756.104.90.2.20
    ctcAddMldVlan OBJECT-TYPE
        SYNTAX      Integer32 (1..4095)
        MAX-ACCESS  read-write
        STATUS      current
        DESCRIPTION                                  
            "Add a new entry to the MLD VLAN table.
             Specify the VID and configure the new entry.
             The specific MLD VLAN starts working after the corresponding static VLAN is also created."
        ::= { ctcMldSnooping 20 }

    -- 1.3.6.1.4.1.4756.104.90.2.21
    ctcDeleteMldVlan OBJECT-TYPE
        SYNTAX      Integer32 (1..4095)
        MAX-ACCESS  read-write
        STATUS      current
        DESCRIPTION
            "Delete an MLD VLAN from table."
        ::= { ctcMldSnooping 21 }

    -- 1.3.6.1.4.1.4756.104.90.2.22
    ctcMldVlanConfigTable OBJECT-TYPE
        SYNTAX      SEQUENCE OF CtcMldVlanConfigEntry
        MAX-ACCESS  not-accessible
        STATUS      current
        DESCRIPTION
            "This table allows for configure MLD snooping VLAN."
        ::= { ctcMldSnooping 22 }

    -- 1.3.6.1.4.1.4756.104.90.2.22.1
    ctcMldVlanConfigEntry OBJECT-TYPE
        SYNTAX      CtcMldVlanConfigEntry
        MAX-ACCESS  not-accessible
        STATUS      current
        DESCRIPTION
            "The Entry of MLD snooping VLAN."
        INDEX { ctcMldVlanID }
        ::= { ctcMldVlanConfigTable 1 }

    CtcMldVlanConfigEntry ::=
        SEQUENCE {     
            ctcMldVlanID             Integer32,
            ctcMldPerVlanEnabled     TruthValue,
            ctcMldQuerierEnabled     TruthValue,
            ctcMldCompatibility      INTEGER,
            ctcMldRV                 Integer32,
            ctcMldQI                 Integer32,
            ctcMldQRI                Integer32,
            ctcMldLLQI               Integer32,
            ctcMldURI                Integer32           
        }

        -- 1.3.6.1.4.1.4756.104.90.2.22.1.1    
        ctcMldVlanID OBJECT-TYPE
            SYNTAX      Integer32 (1..4095)
            MAX-ACCESS  read-only
            STATUS      current
            DESCRIPTION
                "Indicates the ID of this particular MLD snooping VLAN."
            ::= { ctcMldVlanConfigEntry 1 }

        -- 1.3.6.1.4.1.4756.104.90.2.22.1.2    
        ctcMldPerVlanEnabled OBJECT-TYPE
            SYNTAX      TruthValue
            MAX-ACCESS  read-write
            STATUS      current
            DESCRIPTION
                "Enable the per-VLAN MLD Snooping. Only up to 64 VLANs can be selected."
            ::= { ctcMldVlanConfigEntry 2 }

        -- 1.3.6.1.4.1.4756.104.90.2.22.1.3    
        ctcMldQuerierEnabled OBJECT-TYPE
            SYNTAX      TruthValue
            MAX-ACCESS  read-write
            STATUS      current
            DESCRIPTION
                "Enable the MLD Querier in the VLAN."
            ::= { ctcMldVlanConfigEntry 3 }

        -- 1.3.6.1.4.1.4756.104.90.2.22.1.4    
        ctcMldCompatibility OBJECT-TYPE
            SYNTAX      INTEGER {
                            forcedMldV1(1),
                            forcedMldV2(2),
            	            mldAuto(3)
            	        }
            MAX-ACCESS  read-write
            STATUS      current
            DESCRIPTION
                "Compatibility is maintained by hosts and routers taking appropriate actions depending on
                 the versions of MLD operating on hosts and routers within a network.
                 The allowed selection is MLD-Auto, Forced MLDv1, Forced MLDv2,
                 default compatibility value is MLD-Auto."
            DEFVAL      { mldAuto }
            ::= { ctcMldVlanConfigEntry 4 }

        -- 1.3.6.1.4.1.4756.104.90.2.22.1.5    
        ctcMldRV OBJECT-TYPE
            SYNTAX      Integer32 (1..255)
            MAX-ACCESS  read-write
            STATUS      current
            DESCRIPTION
                "Robustness Variable.
                 The Robustness Variable allows tuning for the expected packet loss on a link.
                 The allowed range is 1 to 255, default robustness variable value is 2,
                 Robustness Variable SHOULD NOT be one."
            DEFVAL      { 2 }     
            ::= { ctcMldVlanConfigEntry 5 }

        -- 1.3.6.1.4.1.4756.104.90.2.22.1.6    
        ctcMldQI OBJECT-TYPE
            SYNTAX      Integer32 (1..255)
            UNITS       "Seconds"
            MAX-ACCESS  read-write
            STATUS      current
            DESCRIPTION
                "Query Interval.
                 The Query Interval is the interval between General Queries sent by the Querier.
                 The allowed range is 1 to 255 seconds, default query interval is 125 seconds.
                 Note: The number of seconds represented by QRI must be less than QI!"
            DEFVAL      { 125 }    
            ::= { ctcMldVlanConfigEntry 6 }

        -- 1.3.6.1.4.1.4756.104.90.2.22.1.7    
        ctcMldQRI OBJECT-TYPE
            SYNTAX      Integer32 (0..31744)
            UNITS       "100 millisecond"
            MAX-ACCESS  read-write
            STATUS      current
            DESCRIPTION
                "Query Response Interval.
                 The Max Response Time used to calculate the Max Resp Code inserted into the periodic General Queries.
                 The allowed range is 0 to 31744 in tenths of seconds,
                 default query response interval is 100 in tenths of seconds (10 seconds).
                 The number of seconds represented by QRI must be less than QI!"
            DEFVAL      { 100 }     
            ::= { ctcMldVlanConfigEntry 7 }

        -- 1.3.6.1.4.1.4756.104.90.2.22.1.8    
        ctcMldLLQI OBJECT-TYPE
            SYNTAX      Integer32 (0..31744)
            UNITS       "100 millisecond"
            MAX-ACCESS  read-write
            STATUS      current
            DESCRIPTION
                "Last Member Query Interval.
                 The Last Member Query Time is the time value represented by the Last Member Query Interval,
                 multiplied by the Last Member Query Count.
                 The allowed range is 0 to 31744 in tenths of seconds,
                 default last member query interval is 10 in tenths of seconds (1 second)."
            DEFVAL      { 10 }     
            ::= { ctcMldVlanConfigEntry 8 }

        -- 1.3.6.1.4.1.4756.104.90.2.22.1.9    
        ctcMldURI OBJECT-TYPE
            SYNTAX      Integer32 (0..31744)
            UNITS       "Seconds"
            MAX-ACCESS  read-write
            STATUS      current
            DESCRIPTION
                "Unsolicited Report Interval.
                 The Unsolicited Report Interval is the time between repetitions of
                 a host's initial report of membership in a group.
                 The allowed range is 0 to 31744 seconds,
                 default unsolicited report interval is 1 second."
            DEFVAL      { 1 }     
            ::= { ctcMldVlanConfigEntry 9 }

    -- 1.3.6.1.4.1.4756.104.90.1.30
    ctcAddMldPortFilteringGroup OBJECT-TYPE
        SYNTAX      DisplayString
        MAX-ACCESS  read-write
        STATUS      current
        DESCRIPTION                                  
            "Add a new entry to the Group Filtering table.
             Specify the Port, and Filtering Group of the new entry.
             Syntax: <port_no> <group_addr>
             The MLD Snooping can support maximum 5 entries per port."
        ::= { ctcMldSnooping 30 }

    -- 1.3.6.1.4.1.4756.104.90.1.31
    ctcDeleteMldPortFilteringGroup OBJECT-TYPE
        SYNTAX      DisplayString
        MAX-ACCESS  read-write
        STATUS      current
        DESCRIPTION
            "Delete an MLD Snooping Port Group Filtering from table.
             Syntax: <port_no> <group_addr>"
        ::= { ctcMldSnooping 31 }

    -- 1.3.6.1.4.1.4756.104.90.2.32
    ctcMldPortGroupFilteringTable OBJECT-TYPE
        SYNTAX      SEQUENCE OF CtcMldPortGroupFilteringEntry
        MAX-ACCESS  not-accessible
        STATUS      current
        DESCRIPTION
            "This table is used for configuring the port group filtering."
        ::= { ctcMldSnooping 32 }

    -- 1.3.6.1.4.1.4756.104.90.2.32.1
    ctcMldPortGroupFilteringEntry OBJECT-TYPE
        SYNTAX      CtcMldPortGroupFilteringEntry
        MAX-ACCESS  not-accessible
        STATUS      current
        DESCRIPTION
            "The Entry of port group filtering configurations."
        INDEX { ctcMldPortGroupFilteringIndex }
        ::= { ctcMldPortGroupFilteringTable 1 }

    CtcMldPortGroupFilteringEntry ::=
        SEQUENCE {
            ctcMldPortGroupFilteringIndex    Integer32,          
            ctcMldPortGroupFilteringPort     Integer32,
            ctcMldPortGroupFilteringGroups   DisplayString
        }

        -- 1.3.6.1.4.1.4756.104.90.2.32.1.1    
        ctcMldPortGroupFilteringIndex OBJECT-TYPE
            SYNTAX      Integer32 (1..50)
            MAX-ACCESS  read-only
            STATUS      current
            DESCRIPTION
                "The index of MLD snooping port group filtering entry."
            ::= { ctcMldPortGroupFilteringEntry 1 }

        -- 1.3.6.1.4.1.4756.104.90.2.32.1.2    
        ctcMldPortGroupFilteringPort OBJECT-TYPE
            SYNTAX      Integer32 (1..6)
            MAX-ACCESS  read-only
            STATUS      current
            DESCRIPTION
                "The logical port for the settings."
            ::= { ctcMldPortGroupFilteringEntry 2 }

        -- 1.3.6.1.4.1.4756.104.90.2.32.1.3    
        ctcMldPortGroupFilteringGroups OBJECT-TYPE
            SYNTAX      DisplayString
            MAX-ACCESS  read-only
            STATUS      current
            DESCRIPTION
                "The IPv6 Multicast Group that will be filtered."
            ::= { ctcMldPortGroupFilteringEntry 3 }

    -- 1.3.6.1.4.1.4756.104.90.2.40
    ctcMldSnoopingStatisticsClear OBJECT-TYPE
        SYNTAX      INTEGER {
                        trigger(1),
                        normal(2)
                    }
        MAX-ACCESS  read-write
        STATUS      current
        DESCRIPTION
            "Clears all Statistics counters."
        ::= { ctcMldSnooping 40 }

    -- 1.3.6.1.4.1.4756.104.90.2.41
    ctcMldSnoopingStatisticsTable OBJECT-TYPE
        SYNTAX      SEQUENCE OF CtcMldSnoopingStatisticsEntry
        MAX-ACCESS  not-accessible
        STATUS      current
        DESCRIPTION
            "This table provides MLD Snooping status."
        ::= { ctcMldSnooping 41 }

    -- 1.3.6.1.4.1.4756.104.90.2.41.1
    ctcMldSnoopingStatisticsEntry OBJECT-TYPE
        SYNTAX      CtcMldSnoopingStatisticsEntry
        MAX-ACCESS  not-accessible
        STATUS      current
        DESCRIPTION
            "The Entry of VLAN ID."
        INDEX { ctcMldSnoopingVlanID }
        ::= { ctcMldSnoopingStatisticsTable 1 }

    CtcMldSnoopingStatisticsEntry ::=
        SEQUENCE {       
            ctcMldSnoopingVlanID         Integer32,
            ctcMldQuerierVersion         Integer32,
            ctcMldHostVersion            Integer32,
            ctcMldQuerierStatus          INTEGER,
            ctcMldQueriesTransmitted     Counter32,
            ctcMldQueriesReceived        Counter32,
            ctcMldV1ReportsReceived      Counter32,
            ctcMldV2ReportsReceived      Counter32,
            ctcMldV1LeavesReceived       Counter32
        }
        
        -- 1.3.6.1.4.1.4756.104.90.2.41.1.1    
        ctcMldSnoopingVlanID OBJECT-TYPE
            SYNTAX      Integer32 (1..4095)
            MAX-ACCESS  read-only
            STATUS      current
            DESCRIPTION
                 "The VLAN ID of the entry."
            ::= { ctcMldSnoopingStatisticsEntry 1 }

        -- 1.3.6.1.4.1.4756.104.90.2.41.1.2    
        ctcMldQuerierVersion OBJECT-TYPE
            SYNTAX      Integer32 (1..3)
            MAX-ACCESS  read-only
            STATUS      current
            DESCRIPTION
                "Working Querier Version currently."
            ::= { ctcMldSnoopingStatisticsEntry 2 }

        -- 1.3.6.1.4.1.4756.104.90.2.41.1.3    
        ctcMldHostVersion OBJECT-TYPE
            SYNTAX      Integer32 (1..3)
            MAX-ACCESS  read-only
            STATUS      current
            DESCRIPTION
                "Working Host Version currently."
            ::= { ctcMldSnoopingStatisticsEntry 3 }

        -- 1.3.6.1.4.1.4756.104.90.2.41.1.4    
        ctcMldQuerierStatus OBJECT-TYPE
            SYNTAX      INTEGER {
                            idle(1),
                            active(2)
                        }
            MAX-ACCESS  read-only
            STATUS      current
            DESCRIPTION
                "Shows the Querier status is ACTIVE or IDLE."
            ::= { ctcMldSnoopingStatisticsEntry 4 }

        -- 1.3.6.1.4.1.4756.104.90.2.41.1.5    
        ctcMldQueriesTransmitted OBJECT-TYPE
            SYNTAX      Counter32
            UNITS       "Packets"
            MAX-ACCESS  read-only
            STATUS      current
            DESCRIPTION
                "The number of Transmitted Queries."
            ::= { ctcMldSnoopingStatisticsEntry 5 }

        -- 1.3.6.1.4.1.4756.104.90.2.41.1.6    
        ctcMldQueriesReceived OBJECT-TYPE
            SYNTAX      Counter32
            UNITS       "Packets"
            MAX-ACCESS  read-only
            STATUS      current
            DESCRIPTION
                "The number of Received Queries."
            ::= { ctcMldSnoopingStatisticsEntry 6 }

        -- 1.3.6.1.4.1.4756.104.90.2.41.1.7    
        ctcMldV1ReportsReceived OBJECT-TYPE
            SYNTAX      Counter32
            UNITS       "Packets"
            MAX-ACCESS  read-only
            STATUS      current
            DESCRIPTION
                "The number of Received V1 Reports."
            ::= { ctcMldSnoopingStatisticsEntry 7 }

        -- 1.3.6.1.4.1.4756.104.90.2.41.1.8    
        ctcMldV2ReportsReceived OBJECT-TYPE
            SYNTAX      Counter32
            UNITS       "Packets"
            MAX-ACCESS  read-only
            STATUS      current
            DESCRIPTION
                "The number of Received V2 Reports."
            ::= { ctcMldSnoopingStatisticsEntry 8 }

        -- 1.3.6.1.4.1.4756.104.90.2.41.1.9    
        ctcMldV1LeavesReceived OBJECT-TYPE
            SYNTAX      Counter32
            UNITS       "Packets"
            MAX-ACCESS  read-only
            STATUS      current
            DESCRIPTION
                "The number of Received V1 Leaves."
            ::= { ctcMldSnoopingStatisticsEntry 9 }

    -- 1.3.6.1.4.1.4756.104.90.2.50
    ctcMldGroupsInfoTable OBJECT-TYPE
        SYNTAX      SEQUENCE OF CtcMldGroupsInfoEntry
        MAX-ACCESS  not-accessible
        STATUS      current
        DESCRIPTION
            "This table shows MLD snooping groups information."
        ::= { ctcMldSnooping 50 }

    -- 1.3.6.1.4.1.4756.104.90.2.50.1
    ctcMldGroupsInfoEntry OBJECT-TYPE
        SYNTAX      CtcMldGroupsInfoEntry
        MAX-ACCESS  not-accessible
        STATUS      current
        DESCRIPTION
            "The Entry of MLD snooping groups information."
        INDEX { ctcMldGroupsInfoIndex }
        ::= { ctcMldGroupsInfoTable 1 }

    CtcMldGroupsInfoEntry ::=
        SEQUENCE {
            ctcMldGroupsInfoIndex     Integer32,
            ctcMldGroupsInfoVlanID    Integer32,          
            ctcMldGroupsInfo          DisplayString,
            ctcMldGroupsPortMembers   DisplayString
        }

        -- 1.3.6.1.4.1.4756.104.90.2.50.1.1    
        ctcMldGroupsInfoIndex OBJECT-TYPE
            SYNTAX      Integer32 (1..4095)
            MAX-ACCESS  read-only
            STATUS      current
            DESCRIPTION
                "Entries in the MLD group table."
            ::= { ctcMldGroupsInfoEntry 1 }

        -- 1.3.6.1.4.1.4756.104.90.2.50.1.2    
        ctcMldGroupsInfoVlanID OBJECT-TYPE
            SYNTAX      Integer32 (1..4095)
            MAX-ACCESS  read-only
            STATUS      current
            DESCRIPTION
                "VLAN ID of the group."
            ::= { ctcMldGroupsInfoEntry 2 }

        -- 1.3.6.1.4.1.4756.104.90.2.50.1.3    
        ctcMldGroupsInfo OBJECT-TYPE
            SYNTAX      DisplayString
            MAX-ACCESS  read-only
            STATUS      current
            DESCRIPTION
                "Group address of the entry."
            ::= { ctcMldGroupsInfoEntry 3 }

        -- 1.3.6.1.4.1.4756.104.90.2.50.1.4    
        ctcMldGroupsPortMembers OBJECT-TYPE
            SYNTAX      DisplayString
            MAX-ACCESS  read-only
            STATUS      current
            DESCRIPTION
                "Ports under this group."
            ::= { ctcMldGroupsInfoEntry 4 }

    -- 1.3.6.1.4.1.4756.104.90.2.60
    ctcMldSfmInfoTable OBJECT-TYPE
        SYNTAX      SEQUENCE OF CtcMldSfmInfoEntry
        MAX-ACCESS  not-accessible
        STATUS      current
        DESCRIPTION
            "This table shows MLD SFM (Source-Filtered Multicast) information.
             The MLD SFM Information Table also contains the SSM (Source-Specific Multicast) "
        ::= { ctcMldSnooping 60 }

    -- 1.3.6.1.4.1.4756.104.90.2.60.1
    ctcMldSfmInfoEntry OBJECT-TYPE
        SYNTAX      CtcMldSfmInfoEntry
        MAX-ACCESS  not-accessible
        STATUS      current
        DESCRIPTION
            "The Entry of MLD SSM information."
        INDEX { ctcMldSfmInfoIndex }
        ::= { ctcMldSfmInfoTable 1 }

    CtcMldSfmInfoEntry ::=
        SEQUENCE {
            ctcMldSfmInfoIndex               Integer32,
            ctcMldSfmInfoVlanID              Integer32,
            ctcMldSfmInfoGroup               DisplayString,          
            ctcMldSfmPortNumber              Integer32,
            ctcMldSfmMode                    INTEGER,
            ctcMldSfmSourceAddress           DisplayString,
            ctcMldSfmType                    INTEGER,
            ctcMldSfmHardwareFilterSwitch    INTEGER
        }

        -- 1.3.6.1.4.1.4756.104.90.2.60.1.1    
        ctcMldSfmInfoIndex OBJECT-TYPE
            SYNTAX      Integer32 (1..4095)
            MAX-ACCESS  read-only
            STATUS      current
            DESCRIPTION
                "Entries in the table."
            ::= { ctcMldSfmInfoEntry 1 }

        -- 1.3.6.1.4.1.4756.104.90.2.60.1.2    
        ctcMldSfmInfoVlanID OBJECT-TYPE
            SYNTAX      Integer32 (1..4095)
            MAX-ACCESS  read-only
            STATUS      current
            DESCRIPTION
                "VLAN ID of the group."
            ::= { ctcMldSfmInfoEntry 2 }

        -- 1.3.6.1.4.1.4756.104.90.2.60.1.3    
        ctcMldSfmInfoGroup OBJECT-TYPE
            SYNTAX      DisplayString
            MAX-ACCESS  read-only
            STATUS      current
            DESCRIPTION
                "Group address of the entry."
            ::= { ctcMldSfmInfoEntry 3 }

        -- 1.3.6.1.4.1.4756.104.90.2.60.1.4    
        ctcMldSfmPortNumber OBJECT-TYPE
            SYNTAX      Integer32 (1..6)
            MAX-ACCESS  read-only
            STATUS      current
            DESCRIPTION
                "Switch port number."
            ::= { ctcMldSfmInfoEntry 4 }

        -- 1.3.6.1.4.1.4756.104.90.2.60.1.5    
        ctcMldSfmMode OBJECT-TYPE
            SYNTAX      INTEGER {
                            exclude(1),
                            include(2)
                        }
            MAX-ACCESS  read-only
            STATUS      current
            DESCRIPTION
                "Indicates the filtering mode maintained per (VLAN ID, port number, Group Address) basis.
                 It can be either Include or Exclude."
            ::= { ctcMldSfmInfoEntry 5 }

        -- 1.3.6.1.4.1.4756.104.90.2.60.1.6    
        ctcMldSfmSourceAddress OBJECT-TYPE
            SYNTAX      DisplayString
            MAX-ACCESS  read-only
            STATUS      current
            DESCRIPTION
                "IPv6 Address of the source.
                 Currently, system limits the total number of IPv6 source addresses for filtering to be 128."
            ::= { ctcMldSfmInfoEntry 6 }

        -- 1.3.6.1.4.1.4756.104.90.2.60.1.7    
        ctcMldSfmType OBJECT-TYPE
            SYNTAX      INTEGER {
                            deny(1),
                            allow(2)
                        }
            MAX-ACCESS  read-only
            STATUS      current
            DESCRIPTION
                "Indicates the Type. It can be either Allow or Deny."
            ::= { ctcMldSfmInfoEntry 7 }

        -- 1.3.6.1.4.1.4756.104.90.2.60.1.8    
        ctcMldSfmHardwareFilterSwitch OBJECT-TYPE
            SYNTAX      INTEGER {
                            no(1),
                            yes(2)
                        }
            MAX-ACCESS  read-only
            STATUS      current
            DESCRIPTION
                "Indicates whether data plane destined to the specific group address from
                 the source IPv6 address could be handled by chip or not."
            ::= { ctcMldSfmInfoEntry 8 }


-- MAC Table
    -- 1.3.6.1.4.1.4756.104.100
    ctcMacTableInfo  OBJECT IDENTIFIER ::= { gsw2008ms 100 }

    -- 1.3.6.1.4.1.4756.104.100.1
    ctcDisableAutoAging OBJECT-TYPE
        SYNTAX      TruthValue
        MAX-ACCESS  read-write
        STATUS      current
        DESCRIPTION                                  
            "Disable the automatic aging of dynamic entries."
        ::= { ctcMacTableInfo 1 }

    -- 1.3.6.1.4.1.4756.104.100.2
    ctcAgingTime OBJECT-TYPE
        SYNTAX      Integer32 (10..1000000)
        UNITS       "seconds"
        MAX-ACCESS  read-write
        STATUS      current
        DESCRIPTION                                  
            "By default, dynamic entries are removed from the MAC table after 300 seconds.
             This removal is also called aging.
             Configure aging time by entering a value here in seconds,
             The allowed range is 10 to 1000000 seconds."
        DEFVAL     { 300 }     
        ::= { ctcMacTableInfo 2 }
 
    -- 1.3.6.1.4.1.4756.104.100.3
    ctcMacTableLearningTable OBJECT-TYPE
        SYNTAX      SEQUENCE OF CtcMacTableLearningEntry
        MAX-ACCESS  not-accessible
        STATUS      current
        DESCRIPTION
            "This table allows for configure port learning mode."
        ::= { ctcMacTableInfo 3 }

    -- 1.3.6.1.4.1.4756.104.100.3.1
    ctcMacTableLearningEntry OBJECT-TYPE
        SYNTAX      CtcMacTableLearningEntry
        MAX-ACCESS  not-accessible
        STATUS      current
        DESCRIPTION
            "The entry of ports."
        INDEX { ctcPortIndex }
        ::= { ctcMacTableLearningTable 1 }

    CtcMacTableLearningEntry ::=
        SEQUENCE {       
            ctcPortLearningMode      INTEGER
        }

        -- 1.3.6.1.4.1.4756.104.100.3.1.1    
        ctcPortLearningMode OBJECT-TYPE
            SYNTAX      INTEGER {
                            auto(1),
                            disable(2),
                            secure(3)
                        }    
            MAX-ACCESS  read-write
            STATUS      current
            DESCRIPTION
                "If another module is in control of the mode, then it cannot be changed by the user.
                 An example of such a module is the MAC-Based Authentication under 802.1X.
                 Each port can do learning based upon the following settings:
                 Auto: Learning is done automatically as soon as a frame with unknown SMAC is received.
                 Disable: No learning is done.
                 Secure: Only static MAC entries are learned, all other frames are dropped.
                         <NOTE> Make sure that the link used for managing the switch is added to
                                the Static Mac Table before changing to secure learning mode,
                                otherwise the management link is lost and can only be restored by
                                using another non-secure port"
            ::= { ctcMacTableLearningEntry 1 }

    -- 1.3.6.1.4.1.4756.104.100.4
    ctcAddStaticMAC OBJECT-TYPE
        SYNTAX      DisplayString
        MAX-ACCESS  read-write
        STATUS      current
        DESCRIPTION                                  
            "Add a new entry to the static MAC table. The static MAC table can contain 64 entries.
             By default, no ports are members.
             Syntax: <mac_addr> [<vid>]"
        ::= { ctcMacTableInfo 4 }

    -- 1.3.6.1.4.1.4756.104.100.5
    ctcDeleteStaticMAC OBJECT-TYPE
        SYNTAX      DisplayString
        MAX-ACCESS  read-write
        STATUS      current
        DESCRIPTION
            "Delete an entry from the static MAC table.
             Syntax: <mac_addr> [<vid>]"
        ::= { ctcMacTableInfo 5 }

    -- 1.3.6.1.4.1.4756.104.100.6
    ctcStaticMacTable OBJECT-TYPE
        SYNTAX      SEQUENCE OF CtcStaticMacEntry
        MAX-ACCESS  not-accessible
        STATUS      current
        DESCRIPTION
            "The static entries in the MAC table are shown in this table."
        ::= { ctcMacTableInfo 6 }

    -- 1.3.6.1.4.1.4756.104.100.6.1
    ctcStaticMacEntry OBJECT-TYPE
        SYNTAX      CtcStaticMacEntry
        MAX-ACCESS  not-accessible
        STATUS      current
        DESCRIPTION
            "The entry of static MAC addresses of table."
        INDEX { ctcStaticMacVlanID, ctcStaticMacAddress }
        ::= { ctcStaticMacTable 1 }

    CtcStaticMacEntry ::=
        SEQUENCE {        
            ctcStaticMacVlanID       Integer32,
            ctcStaticMacAddress      MacAddress,
            ctcStaticMacPortMembers  DisplayString
        }

        -- 1.3.6.1.4.1.4756.104.100.6.1.1    
        ctcStaticMacVlanID OBJECT-TYPE
            SYNTAX      Integer32 (1..4095)
            MAX-ACCESS  read-only
            STATUS      current
            DESCRIPTION
                "The VLAN ID of the entry."
            ::= { ctcStaticMacEntry 1 }

        -- 1.3.6.1.4.1.4756.104.100.6.1.2    
        ctcStaticMacAddress OBJECT-TYPE
            SYNTAX      MacAddress
            MAX-ACCESS  read-only
            STATUS      current
            DESCRIPTION
                "The MAC address of the entry."
            ::= { ctcStaticMacEntry 2 }

        -- 1.3.6.1.4.1.4756.104.100.6.1.3    
        ctcStaticMacPortMembers OBJECT-TYPE
            SYNTAX      DisplayString
            MAX-ACCESS  read-write
            STATUS      current
            DESCRIPTION
                "Indicates which ports are members of the entry."
            ::= { ctcStaticMacEntry 3 }

    -- 1.3.6.1.4.1.4756.104.100.7
    ctcFlushDynamicMacEntries OBJECT-TYPE
        SYNTAX      INTEGER {
                        trigger(1),
                        normal(2)
                    }
        MAX-ACCESS  read-write
        STATUS      current
        DESCRIPTION
            "Flushes all dynamic entries."
        ::= { ctcMacTableInfo 7 }

    -- 1.3.6.1.4.1.4756.104.100.8
    ctcMacAddressTable OBJECT-TYPE
        SYNTAX      SEQUENCE OF CtcMacAddressEntry
        MAX-ACCESS  not-accessible
        STATUS      current
        DESCRIPTION
            "The entries in the MAC addresses table are shown in this table."
        ::= { ctcMacTableInfo 8 }

    -- 1.3.6.1.4.1.4756.104.100.8.1
    ctcMacAddressEntry OBJECT-TYPE
        SYNTAX      CtcMacAddressEntry
        MAX-ACCESS  not-accessible
        STATUS      current
        DESCRIPTION
            "The entry of MAC addresses table."
        INDEX { ctcMacAddressVlanID, ctcMacAddress }
        ::= { ctcMacAddressTable 1 }

    CtcMacAddressEntry ::=
        SEQUENCE {
            ctcMacAddressVlanID          Integer32,   
            ctcMacAddress                MacAddress,
            ctcMacAddressType            INTEGER,           
            ctcMacAddressPortMembers     DisplayString
        }

        -- 1.3.6.1.4.1.4756.104.100.8.1.1    
        ctcMacAddressVlanID OBJECT-TYPE
            SYNTAX      Integer32 (1..4095)
            MAX-ACCESS  read-only
            STATUS      current
            DESCRIPTION
                "The VLAN ID of the entry."
            ::= { ctcMacAddressEntry 1 }

        -- 1.3.6.1.4.1.4756.104.100.8.1.2    
        ctcMacAddress OBJECT-TYPE
            SYNTAX      MacAddress
            MAX-ACCESS  read-only
            STATUS      current
            DESCRIPTION
                "The MAC address of the entry."
            ::= { ctcMacAddressEntry 2 }

        -- 1.3.6.1.4.1.4756.104.100.8.1.3    
        ctcMacAddressType OBJECT-TYPE
            SYNTAX      INTEGER {
                            static(1),
                            dynamic(2)
                        }
            MAX-ACCESS  read-only
            STATUS      current
            DESCRIPTION
                "Indicates whether the entry is a static or a dynamic entry."
            ::= { ctcMacAddressEntry 3 }

        -- 1.3.6.1.4.1.4756.104.100.8.1.4    
        ctcMacAddressPortMembers OBJECT-TYPE
            SYNTAX      DisplayString
            MAX-ACCESS  read-only
            STATUS      current
            DESCRIPTION
                "The ports that are members of the entry."
            ::= { ctcMacAddressEntry 4 }


-- VLAN Translation
    -- 1.3.6.1.4.1.4756.104.105
    ctcVlanTranslation  OBJECT IDENTIFIER ::= { gsw2008ms 105 }

    -- 1.3.6.1.4.1.4756.104.105.1
    ctcAddVlanTransPortToGroup OBJECT-TYPE
        SYNTAX      DisplayString
        MAX-ACCESS  read-write
        STATUS      current
        DESCRIPTION                                  
            "Add a new entry in Port to Group Mapping Table.
             Note that if a VLAN translation is enabled on a management port for management VLAN,
             it may disrupt the management connectivity in some cases.
             Syntax: <port_list> <group_id>"
        ::= { ctcVlanTranslation 1 }

    -- 1.3.6.1.4.1.4756.104.105.2
    ctcVlanTransPortToGroupMappingTable OBJECT-TYPE
        SYNTAX      SEQUENCE OF CtcVlanTransPortToGroupMappingEntry
        MAX-ACCESS  not-accessible
        STATUS      current
        DESCRIPTION
            "This table allows you to map set of Port members to a Group ID for all switch ports."
        ::= { ctcVlanTranslation 2 }

    -- 1.3.6.1.4.1.4756.104.105.2.1
    ctcVlanTransPortToGroupMappingEntry OBJECT-TYPE
        SYNTAX      CtcVlanTransPortToGroupMappingEntry
        MAX-ACCESS  not-accessible
        STATUS      current
        DESCRIPTION
            "The Entry of Port to Group mapping Table."
        INDEX { ctcVlanTransGroupID }
        ::= { ctcVlanTransPortToGroupMappingTable 1 }

    CtcVlanTransPortToGroupMappingEntry ::=
        SEQUENCE {       
            ctcVlanTransGroupID                  Integer32,
            ctcVlanTransPortToGroupPortMembers   DisplayString
        }

        -- 1.3.6.1.4.1.4756.104.105.2.1.1    
        ctcVlanTransGroupID OBJECT-TYPE
            SYNTAX      Integer32 (1..6)
            MAX-ACCESS  read-only
            STATUS      current
            DESCRIPTION
                "A valid Group ID is an integer value form 1 to 6.
                 A set of VLAN Translations are mapped to a group Id.
                 This way a port is mapped to a list of VLAN Translations easily by
                 mapping it to a group."
            ::= { ctcVlanTransPortToGroupMappingEntry 1 }

        -- 1.3.6.1.4.1.4756.104.105.2.1.2    
        ctcVlanTransPortToGroupPortMembers OBJECT-TYPE
            SYNTAX      DisplayString
            MAX-ACCESS  read-write
            STATUS      current
            DESCRIPTION
                "A port can be mapped to any of the groups.
                 Multiple ports can also be mapped to a group with same group Id.
                 Note: By default, each port is mapped to a group with a group Id equal to the port number.
                       For example, port 1 is mapped to the group with ID=1."
            ::= { ctcVlanTransPortToGroupMappingEntry 2 }

    -- 1.3.6.1.4.1.4756.104.105.3
    ctcAddVlanTransMapping OBJECT-TYPE
        SYNTAX      DisplayString
        MAX-ACCESS  read-write
        STATUS      current
        DESCRIPTION                                  
            "Add a new entry in VLAN Translation table.
             Syntax: <group_id> <vid> <trans_vid>"
        ::= { ctcVlanTranslation 3 }

    -- 1.3.6.1.4.1.4756.104.105.4
    ctcDeleteVlanTransMapping OBJECT-TYPE
        SYNTAX      DisplayString
        MAX-ACCESS  read-write
        STATUS      current
        DESCRIPTION                                  
            "To delete a VLAN Translation Group database entry.
             Syntax: <group_id> <vid>"
        ::= { ctcVlanTranslation 4 }

    -- 1.3.6.1.4.1.4756.104.105.5
    ctcVlanTransVidMappingTable OBJECT-TYPE
        SYNTAX      SEQUENCE OF CtcVlanTransVidMappingEntry
        MAX-ACCESS  not-accessible
        STATUS      current
        DESCRIPTION
            "This table allows you to map set of Port members to a Group ID for all switch ports."
        ::= { ctcVlanTranslation 5 }

    -- 1.3.6.1.4.1.4756.104.105.5.1
    ctcVlanTransVidMappingEntry OBJECT-TYPE
        SYNTAX      CtcVlanTransVidMappingEntry
        MAX-ACCESS  not-accessible
        STATUS      current
        DESCRIPTION
            "The Entry of Port to Group mapping Table."
        INDEX { ctcVlanTransGroupID, ctcVlanTransMappedVID }
        ::= { ctcVlanTransVidMappingTable 1 }

    CtcVlanTransVidMappingEntry ::=
        SEQUENCE {       
            ctcVlanTransMappedVID    Integer32,
            ctcVlanTranslatedToVID   Integer32
        }

        -- 1.3.6.1.4.1.4756.104.105.5.1.1    
        ctcVlanTransMappedVID OBJECT-TYPE
            SYNTAX      Integer32 (1..4095)
            MAX-ACCESS  read-only
            STATUS      current
            DESCRIPTION
                "Indicates the ID to which Group ID will be mapped.
                 A valid VLAN ID ranges from 1-4095."
            ::= { ctcVlanTransVidMappingEntry 1 }

        -- 1.3.6.1.4.1.4756.104.105.5.1.2    
        ctcVlanTranslatedToVID OBJECT-TYPE
            SYNTAX      Integer32 (1..4095)
            MAX-ACCESS  read-write
            STATUS      current
            DESCRIPTION
                "Indicates the VID to which VLAN ID of ingress frames will be changed."
            ::= { ctcVlanTransVidMappingEntry 2 }



-- VLANs
    -- 1.3.6.1.4.1.4756.104.110
    ctcVLAN  OBJECT IDENTIFIER ::= { gsw2008ms 110 }

    -- 1.3.6.1.4.1.4756.104.110.1
    ctcAddVlanID OBJECT-TYPE
        SYNTAX      Integer32 (1..4095)
        MAX-ACCESS  read-write
        STATUS      current
        DESCRIPTION                                  
            "Add a new VLAN ID, and the VLAN can be configured as needed.
             Legal values for a VLAN ID are 1 through 4095,
             and for every new VLAN entry all ports are member.
             Syntax: <vlan_id>"
        ::= { ctcVLAN 1 }

    -- 1.3.6.1.4.1.4756.104.110.2
    ctcDeleteVlanByID OBJECT-TYPE
        SYNTAX      Integer32 (1..4095)
        MAX-ACCESS  read-write
        STATUS      current
        DESCRIPTION
            "Delete a VLAN from indicated ID.
             Syntax: <vlan_id>"
        ::= { ctcVLAN 2 }

    -- 1.3.6.1.4.1.4756.104.110.3
    ctcDeleteVlanByName OBJECT-TYPE
        SYNTAX      DisplayString
        MAX-ACCESS  read-write
        STATUS      current
        DESCRIPTION
            "Delete a VLAN from indicated name.
             Syntax: <vlan_name>"
        ::= { ctcVLAN 3 }

    -- 1.3.6.1.4.1.4756.104.110.4
    ctcVlanMembershipTable OBJECT-TYPE
        SYNTAX      SEQUENCE OF CtcVlanMembershipEntry
        MAX-ACCESS  not-accessible
        STATUS      current
        DESCRIPTION
            "The VLAN membership configuration can be monitored and modified here."
        ::= { ctcVLAN 4 }

    -- 1.3.6.1.4.1.4756.104.110.4.1
    ctcVlanMembershipEntry OBJECT-TYPE
        SYNTAX      CtcVlanMembershipEntry
        MAX-ACCESS  not-accessible
        STATUS      current
        DESCRIPTION
            "The Entry of VLAN memberships."
        INDEX { ctcVlanID }
        ::= { ctcVlanMembershipTable 1 }

    CtcVlanMembershipEntry ::=
        SEQUENCE {       
            ctcVlanID                Integer32,
            ctcVlanName              OCTET STRING,
            ctcVlanMembershipPorts   DisplayString,
            ctcVlanForbiddenPorts    DisplayString
        }

        -- 1.3.6.1.4.1.4756.104.110.4.1.1    
        ctcVlanID OBJECT-TYPE
            SYNTAX      Integer32 (1..4095)
            MAX-ACCESS  read-only
            STATUS      current
            DESCRIPTION
                "Indicates the ID of this particular VLAN."
            ::= { ctcVlanMembershipEntry 1 }

        -- 1.3.6.1.4.1.4756.104.110.4.1.2    
        ctcVlanName OBJECT-TYPE
            SYNTAX      OCTET STRING (SIZE (0..32))
            MAX-ACCESS  read-write
            STATUS      current
            DESCRIPTION
                "Indicates the name of the VLAN. Maximum length of the VLAN Name String is 32.
                 VLAN Name can only contain alphabets or numbers.
                 VLAN name should contain atleast one alphabet.
                 VLAN name can be edited for the existing VLAN entries."
            ::= { ctcVlanMembershipEntry 2 }

        -- 1.3.6.1.4.1.4756.104.110.4.1.3    
        ctcVlanMembershipPorts OBJECT-TYPE
            SYNTAX      DisplayString
            MAX-ACCESS  read-write
            STATUS      current
            DESCRIPTION
                "Add or modify membership port list of VLAN."
            ::= { ctcVlanMembershipEntry 3 }

        -- 1.3.6.1.4.1.4756.104.110.4.1.4    
        ctcVlanForbiddenPorts OBJECT-TYPE
            SYNTAX      DisplayString
            MAX-ACCESS  read-write
            STATUS      current
            DESCRIPTION
                "Add or modify forbidden port list of VLAN."
            ::= { ctcVlanMembershipEntry 4 }

    -- 1.3.6.1.4.1.4756.104.110.5
    ctcVlanEthertype OBJECT-TYPE
        SYNTAX      DisplayString
        MAX-ACCESS  read-write
        STATUS      current
        DESCRIPTION
            "The ether type used for Custom S-ports.
             This is a global setting for all the Custom S-ports.
             The format of 'Ethernet Type' is restricted to 0x600-0xFFFF"
        ::= { ctcVLAN 5 }

    -- 1.3.6.1.4.1.4756.104.110.6
    ctcVlanPortTable OBJECT-TYPE
        SYNTAX      SEQUENCE OF CtcVlanPortEntry
        MAX-ACCESS  not-accessible
        STATUS      current
        DESCRIPTION
            "This table is used for configuring the switch VLAN port."
        ::= { ctcVLAN 6 }

    -- 1.3.6.1.4.1.4756.104.110.6.1
    ctcVlanPortEntry OBJECT-TYPE
        SYNTAX      CtcVlanPortEntry
        MAX-ACCESS  not-accessible
        STATUS      current
        DESCRIPTION
            "The Entry of VLAN ports."
        INDEX { ctcPortIndex }
        ::= { ctcVlanPortTable 1 }

    CtcVlanPortEntry ::=
        SEQUENCE {
            ctcVlanPortType          INTEGER,          
            ctcVlanPortRxFiltering   INTEGER,
            ctcVlanPortFrameType     INTEGER,
            ctcVlanPortVlanID        Integer32,
            ctcVlanPortTxTag         INTEGER,
            ctcVlanPortConflicts     TruthValue
        }

        -- 1.3.6.1.4.1.4756.104.110.6.1.1    
        ctcVlanPortType OBJECT-TYPE
            SYNTAX      INTEGER {
                            unaware(1),
                            cPort(2),
                            sPort(3),
                            sCustomPort(4)
                        }
            MAX-ACCESS  read-write
            STATUS      current
            DESCRIPTION
                "Port can be one of the following types:
                 Unaware, Customer port(C-port), Service port(S-port), Custom Service port(S-custom-port)
                 If Port Type is Unaware, all frames are classified to the Port VLAN ID and tags are not removed."
            ::= { ctcVlanPortEntry 1 }

        -- 1.3.6.1.4.1.4756.104.110.6.1.2    
        ctcVlanPortRxFiltering OBJECT-TYPE
            SYNTAX      INTEGER {
                            enabled(1),
                            disabled(2)
                        }
            MAX-ACCESS  read-write
            STATUS      current
            DESCRIPTION
                "This parameter affects VLAN ingress processing.
                 If ingress filtering is enabled and the ingress port is not a member of
                 the classified VLAN of the frame,
                 the frame is discarded. By default, ingress filtering is disabled."
            DEFVAL      { disabled }     
            ::= { ctcVlanPortEntry 2 }

        -- 1.3.6.1.4.1.4756.104.110.6.1.3    
        ctcVlanPortFrameType OBJECT-TYPE
            SYNTAX      INTEGER {
                            all(1),
                            tagged(2),
                            untagged(3)
                        }
            MAX-ACCESS  read-write
            STATUS      current
            DESCRIPTION
                "Determines whether the port accepts all frames or only tagged/untagged frames.
                 This parameter affects VLAN ingress processing.
                 If the port only accepts tagged frames, untagged frames received on the port are discarded.
                 By default, the frame type is set to All."
            DEFVAL      { all }     
            ::= { ctcVlanPortEntry 3 }

        -- 1.3.6.1.4.1.4756.104.110.6.1.4    
        ctcVlanPortVlanID OBJECT-TYPE
            SYNTAX      Integer32 (0..4095)
            MAX-ACCESS  read-write
            STATUS      current
            DESCRIPTION
                "Configures the VLAN identifier for the port.
                 The allowed values are 0 through 4095. The default value is 1.
                 
                 If the value is 0, a VLAN tag with the classified VLAN ID is inserted in frames transmitted on the port.                 
                 This mode is normally used for ports connected to VLAN aware switches.
                 IMPORTANT: 'Port Tx Tag' should be set to 'untagPvid(1)' when this value is used.
                 
                 If the value are 1 through 4095, untagged frames received on the port are classified to the Port VLAN ID.
                 If VLAN awareness is disabled, all frames received on the port are classified to the Port VLAN ID.
                 If the classified VLAN ID of a frame transmitted on the port is different from the Port VLAN ID,
                 a VLAN tag with the classified VLAN ID is inserted in the frame."
            DEFVAL      { 1 }     
            ::= { ctcVlanPortEntry 4 }

        -- 1.3.6.1.4.1.4756.104.110.6.1.5    
        ctcVlanPortTxTag OBJECT-TYPE
            SYNTAX      INTEGER {
                            untagPvid(1),
                            tagAll(2),
                            untagAll(3)
                        }
            MAX-ACCESS  read-write
            STATUS      current
            DESCRIPTION
                "Determines egress tagging of a port.
                 Untag_pvid - All VLANs except the configured PVID will be tagged.
                 Tag_all - All VLANs are tagged.
                 Untag_all - All VLANs are untagged."
            DEFVAL      { untagPvid }     
            ::= { ctcVlanPortEntry 5 }

        -- 1.3.6.1.4.1.4756.104.110.6.1.6    
        ctcVlanPortConflicts OBJECT-TYPE
            SYNTAX      TruthValue
            MAX-ACCESS  read-only
            STATUS      current
            DESCRIPTION
                "Shows status of Conflicts whether exists or not.
                 When a Volatile VLAN User requests to set VLAN membership or VLAN port configuration,
                 the following conflicts can occur:
                 Functional Conflicts between features.
                 Conflicts due to hardware limitation.
                 Direct conflict between user modules."
            ::= { ctcVlanPortEntry 6 }

    -- 1.3.6.1.4.1.4756.104.110.10
    ctcVlanMembershipStatusTable OBJECT-TYPE
        SYNTAX      SEQUENCE OF CtcVlanMembershipStatusEntry
        MAX-ACCESS  not-accessible
        STATUS      current
        DESCRIPTION
            "The VLAN membership configuration can be monitored and modified here."
        ::= { ctcVLAN 10 }

    -- 1.3.6.1.4.1.4756.104.110.10.1
    ctcVlanMembershipStatusEntry OBJECT-TYPE
        SYNTAX      CtcVlanMembershipStatusEntry
        MAX-ACCESS  not-accessible
        STATUS      current
        DESCRIPTION
            "The Entry of VLAN memberships."
        INDEX { ctcVlanID, ctcPortIndex }
        ::= { ctcVlanMembershipStatusTable 1 }

    CtcVlanMembershipStatusEntry ::=
        SEQUENCE {       
            ctcVlanMembershipStatus   INTEGER
        }

        -- 1.3.6.1.4.1.4756.104.110.10.1.1    
        ctcVlanMembershipStatus OBJECT-TYPE
            SYNTAX      INTEGER {
                            nonMember(1),
                            member(2),
                            forbidden(3),
                            conflict(4)
                        }
            MAX-ACCESS  read-only
            STATUS      current
            DESCRIPTION
                "The table show the current VLAN port members for all VLANs configured by all the VLAN Users.
                 nonMember: A port is excluded in a VLAN.
                 member: A port is included in a VLAN.
                 forbidden: A port is included in a Forbidden port list.
                 confilect: A port is included in a Forbidden port list and dynamic VLAN user register VLAN on same port."
            ::= { ctcVlanMembershipStatusEntry 1 }


-- Private VLAN
    -- 1.3.6.1.4.1.4756.104.120
    ctcPrivateVLAN  OBJECT IDENTIFIER ::= { gsw2008ms 120 }

    -- 1.3.6.1.4.1.4756.104.120.1
    ctcAddPrivateVlanID OBJECT-TYPE
        SYNTAX      Integer32 (1..6)
        MAX-ACCESS  read-write
        STATUS      current
        DESCRIPTION                                  
            "Add a new private VLAN ID, and the private VLAN can be configured as needed.
             The allowed range for a private VLAN ID is the same as the switch port number range.
             and for every new private VLAN entry all ports are member."
        ::= { ctcPrivateVLAN 1 }

    -- 1.3.6.1.4.1.4756.104.120.2
    ctcDeletePrivateVlanID OBJECT-TYPE
        SYNTAX      Integer32 (1..6)
        MAX-ACCESS  read-write
        STATUS      current
        DESCRIPTION
            "Delete a private VLAN from indicated ID."
        ::= { ctcPrivateVLAN 2 }

    -- 1.3.6.1.4.1.4756.104.120.3
    ctcPrivateVlanPortMemberTable OBJECT-TYPE
        SYNTAX      SEQUENCE OF CtcPrivateVlanPortMemberEntry
        MAX-ACCESS  not-accessible
        STATUS      current
        DESCRIPTION
            "Private VLANs are based on the source port mask, and there are no connections to VLANs.
             This means that VLAN IDs and Private VLAN IDs can be identical.
             A port must be a member of both a VLAN and a Private VLAN to be able to forward packets.
             By default, all ports are VLAN unaware and members of VLAN 1 and Private VLAN 1.
             A VLAN unaware port can only be a member of one VLAN,
             but it can be a member of multiple Private VLANs."
        ::= { ctcPrivateVLAN 3 }

    -- 1.3.6.1.4.1.4756.104.120.3.1
    ctcPrivateVlanPortMemberEntry OBJECT-TYPE
        SYNTAX      CtcPrivateVlanPortMemberEntry
        MAX-ACCESS  not-accessible
        STATUS      current
        DESCRIPTION
            "The Entry of private VLAN."
        INDEX { ctcPrivateVlanID }
        ::= { ctcPrivateVlanPortMemberTable 1 }

    CtcPrivateVlanPortMemberEntry ::=
        SEQUENCE {       
            ctcPrivateVlanID             Integer32,
            ctcPrivateVlanPortMembers    DisplayString
        }

        -- 1.3.6.1.4.1.4756.104.120.3.1.1    
        ctcPrivateVlanID OBJECT-TYPE
            SYNTAX      Integer32 (1..6)
            MAX-ACCESS  read-only
            STATUS      current
            DESCRIPTION
                "Indicates the ID of this particular private VLAN."
            ::= { ctcPrivateVlanPortMemberEntry 1 }

        -- 1.3.6.1.4.1.4756.104.120.3.1.2    
        ctcPrivateVlanPortMembers OBJECT-TYPE
            SYNTAX      DisplayString
            MAX-ACCESS  read-write
            STATUS      current
            DESCRIPTION
                "Add or modify member port list of private VLAN."
            ::= { ctcPrivateVlanPortMemberEntry 2 }

    -- 1.3.6.1.4.1.4756.104.120.4    
    ctcIsolationPorts OBJECT-TYPE
        SYNTAX      DisplayString
        MAX-ACCESS  read-write
        STATUS      current
        DESCRIPTION
            "A port member of a VLAN can be isolated to other isolated ports on the same VLAN and Private VLAN.
             By default, port isolation is disabled on all ports."
        ::= { ctcPrivateVLAN 4 }


-- VCL
    -- 1.3.6.1.4.1.4756.104.130
    ctcVCL  OBJECT IDENTIFIER ::= { gsw2008ms 130 }

    -- 1.3.6.1.4.1.4756.104.130.1
    ctcMacBasedVLAN  OBJECT IDENTIFIER ::= { ctcVCL 1 }

    -- 1.3.6.1.4.1.4756.104.130.1.1
    ctcAddMacBasedVLAN OBJECT-TYPE
        SYNTAX      DisplayString
        MAX-ACCESS  read-write
        STATUS      current
        DESCRIPTION                                  
            "Add a new MAC-based VLAN entry and the MAC-based VLAN entry can be configured as needed.
             Any unicast MAC address can be configured for the MAC-based VLAN entry.
             No broadcast or multicast MAC addresses are allowed.
             Syntax: <mac_addr>
             By default, VLAN ID is 1 and all ports are members"
        ::= { ctcMacBasedVLAN 1 }

    -- 1.3.6.1.4.1.4756.104.130.1.2
    ctcDeleteMacBasedVLAN OBJECT-TYPE
        SYNTAX      DisplayString
        MAX-ACCESS  read-write
        STATUS      current
        DESCRIPTION
            "To delete a MAC-based VLAN entry.
             Syntax: <mac_addr>"
        ::= { ctcMacBasedVLAN 2 }

    -- 1.3.6.1.4.1.4756.104.130.1.3
    ctcMacBasedVlanConfigTable OBJECT-TYPE
        SYNTAX      SEQUENCE OF CtcMacBasedVlanConfigEntry
        MAX-ACCESS  not-accessible
        STATUS      current
        DESCRIPTION
            "The MAC-based VLAN enties can be configured here."
        ::= { ctcMacBasedVLAN 3 }

    -- 1.3.6.1.4.1.4756.104.130.1.3.1
    ctcMacBasedVlanConfigEntry OBJECT-TYPE
        SYNTAX      CtcMacBasedVlanConfigEntry
        MAX-ACCESS  not-accessible
        STATUS      current
        DESCRIPTION
            "The Entry of MAC-based VLAN."
        INDEX { ctcMacBasedVlanConfigIndex }
        ::= { ctcMacBasedVlanConfigTable 1 }

    CtcMacBasedVlanConfigEntry ::=
        SEQUENCE {
            ctcMacBasedVlanConfigIndex         Integer32,
            ctcMacBasedVlanMacAddressConfig    MacAddress,
            ctcMacBasedVlanIDConfig            Integer32,
            ctcMacBasedVlanPortMembersConfig   DisplayString
        }

        -- 1.3.6.1.4.1.4756.104.130.1.3.1.1    
        ctcMacBasedVlanConfigIndex OBJECT-TYPE
            SYNTAX      Integer32 (1..256)
            MAX-ACCESS  read-only
            STATUS      current
            DESCRIPTION
                "Indicates the Index of MAC-based VLAN."
            ::= { ctcMacBasedVlanConfigEntry 1 }

        -- 1.3.6.1.4.1.4756.104.130.1.3.1.2    
        ctcMacBasedVlanMacAddressConfig OBJECT-TYPE
            SYNTAX      MacAddress
            MAX-ACCESS  read-only
            STATUS      current
            DESCRIPTION
                "Indicates the MAC address."
            ::= { ctcMacBasedVlanConfigEntry 2 }

        -- 1.3.6.1.4.1.4756.104.130.1.3.1.3    
        ctcMacBasedVlanIDConfig OBJECT-TYPE
            SYNTAX      Integer32 (1..4095)
            MAX-ACCESS  read-write
            STATUS      current
            DESCRIPTION
                "Indicates the VLAN ID.
                Legal values for a VLAN ID are 1 through 4095."
            ::= { ctcMacBasedVlanConfigEntry 3 }

        -- 1.3.6.1.4.1.4756.104.130.1.3.1.4    
        ctcMacBasedVlanPortMembersConfig OBJECT-TYPE
            SYNTAX      DisplayString
            MAX-ACCESS  read-write
            STATUS      current
            DESCRIPTION
                "To include or remove a port in a MAC-based VLAN."
            ::= { ctcMacBasedVlanConfigEntry 4 }

    -- 1.3.6.1.4.1.4756.104.130.1.4
    ctcMacBasedVlanStatusTable OBJECT-TYPE
        SYNTAX      SEQUENCE OF CtcMacBasedVlanStatusEntry
        MAX-ACCESS  not-accessible
        STATUS      current
        DESCRIPTION
            "The table shows MAC-based VLAN enties status."
        ::= { ctcMacBasedVLAN 4 }

    -- 1.3.6.1.4.1.4756.104.130.1.4.1
    ctcMacBasedVlanStatusEntry OBJECT-TYPE
        SYNTAX      CtcMacBasedVlanStatusEntry
        MAX-ACCESS  not-accessible
        STATUS      current
        DESCRIPTION
            "The Entry of MAC-based VLAN."
        INDEX { ctcMacBasedVlanStatusIndex }
        ::= { ctcMacBasedVlanStatusTable 1 }

    CtcMacBasedVlanStatusEntry ::=
        SEQUENCE {
            ctcMacBasedVlanStatusIndex         Integer32,
            ctcMacBasedVlanUserType            INTEGER,
            ctcMacBasedVlanMacAddressStatus    MacAddress,
            ctcMacBasedVlanIDStatus            Integer32,
            ctcMacBasedVlanPortMembersStatus   DisplayString
        }

        -- 1.3.6.1.4.1.4756.104.130.1.4.1.1    
        ctcMacBasedVlanStatusIndex OBJECT-TYPE
            SYNTAX      Integer32 (1..256)
            MAX-ACCESS  read-only
            STATUS      current
            DESCRIPTION
                "Indicates the Index of MAC-based VLAN."
            ::= { ctcMacBasedVlanStatusEntry 1 }

        -- 1.3.6.1.4.1.4756.104.130.1.4.1.2    
        ctcMacBasedVlanUserType OBJECT-TYPE
            SYNTAX      INTEGER {
                            static(1),
                            nas(2)
                        }
            MAX-ACCESS  read-only
            STATUS      current
            DESCRIPTION
                "There are two supported VLAN user types:
                 CLI/Web/SNMP : These are referred to as static.
                 NAS : NAS provides port-based authentication,
                       which involves communications between a Supplicant, Authenticator,
                       and an Authentication Server."
            ::= { ctcMacBasedVlanStatusEntry 2 }

        -- 1.3.6.1.4.1.4756.104.130.1.4.1.3    
        ctcMacBasedVlanMacAddressStatus OBJECT-TYPE
            SYNTAX      MacAddress
            MAX-ACCESS  read-only
            STATUS      current
            DESCRIPTION
                "Indicates the MAC address."
            ::= { ctcMacBasedVlanStatusEntry 3 }

        -- 1.3.6.1.4.1.4756.104.130.1.4.1.4    
        ctcMacBasedVlanIDStatus OBJECT-TYPE
            SYNTAX      Integer32 (1..4095)
            MAX-ACCESS  read-only
            STATUS      current
            DESCRIPTION
                "Indicates the VLAN ID."
            ::= { ctcMacBasedVlanStatusEntry 4 }

        -- 1.3.6.1.4.1.4756.104.130.1.4.1.5    
        ctcMacBasedVlanPortMembersStatus OBJECT-TYPE
            SYNTAX      DisplayString
            MAX-ACCESS  read-only
            STATUS      current
            DESCRIPTION
                "To include or remove a port in a MAC-based VLAN."
            ::= { ctcMacBasedVlanStatusEntry 5 }

    -- 1.3.6.1.4.1.4756.104.130.2
    ctcProtocolBasedVLAN  OBJECT IDENTIFIER ::= { ctcVCL 2 }

    -- 1.3.6.1.4.1.4756.104.130.2.1
    ctcAddProtocolEthernetToGroup OBJECT-TYPE
        SYNTAX      DisplayString
        MAX-ACCESS  read-write
        STATUS      current
        DESCRIPTION                                  
            "To add a new Ethernet type entry in Protocol to Group Mapping table.
             Syntax: <ether_type> <group_name>
             Valid values for ether_type ranges from 0x0600-0xffff."
        ::= { ctcProtocolBasedVLAN 1 }

    -- 1.3.6.1.4.1.4756.104.130.2.2
    ctcAddProtocolSnapToGroup OBJECT-TYPE
        SYNTAX      DisplayString
        MAX-ACCESS  read-write
        STATUS      current
        DESCRIPTION                                  
            "To add a new SNAP type entry in Protocol to Group Mapping table.
             Syntax: <oui> <pid> <group_name>
             Valid value in this case is comprised of two different sub-values.
                 a. OUI: OUI (Organizationally Unique Identifier) is value in format of xx-xx-xx
                         where each pair (xx) in string is a hexadecimal value ranges from 0x00-0xff.
                 b. PID: If the OUI is hexadecimal 00-00-00, the protocol ID is the Ethernet
                         type(EtherType) field value for the protocol running on top of SNAP;
                         if the OUI is an OUI for a particular organization, the protocol ID is
                         a value assigned by that organization to the protocol running on top of SNAP.
                         In other words, if value of OUI field is 00-00-00 then value of PID will be
                         etype (0x0600-0xffff) and if value of OUI is other than 00-00-00 then
                         valid value of PID will be any value from 0x0000 to 0xffff."
        ::= { ctcProtocolBasedVLAN 2 }

    -- 1.3.6.1.4.1.4756.104.130.2.3
    ctcAddProtocolLlcToGroup OBJECT-TYPE
        SYNTAX      DisplayString
        MAX-ACCESS  read-write
        STATUS      current
        DESCRIPTION                                  
            "To add a new LLC type entry in Protocol to Group Mapping table.
             Syntax: <dsap> <ssap> <group_name>
             Valid value in this case is comprised of two different sub-values.
                 a. DSAP: 1-byte long string (0x00-0xff)
                 b. SSAP: 1-byte long string (0x00-0xff)."
        ::= { ctcProtocolBasedVLAN 3 }

    -- 1.3.6.1.4.1.4756.104.130.2.4
    ctcDeleteProtocolEthernetToGroup OBJECT-TYPE
        SYNTAX      DisplayString
        MAX-ACCESS  read-write
        STATUS      current
        DESCRIPTION
            "To delete a Ethernet type to Group Name map entry.
             Syntax: <ether_type>"
        ::= { ctcProtocolBasedVLAN 4 }

    -- 1.3.6.1.4.1.4756.104.130.2.5
    ctcDeleteProtocolSnapToGroup OBJECT-TYPE
        SYNTAX      DisplayString
        MAX-ACCESS  read-write
        STATUS      current
        DESCRIPTION
            "To delete a SNAP type to Group Name map entry.
             Syntax: <oui> <pid>"
        ::= { ctcProtocolBasedVLAN 5 }

    -- 1.3.6.1.4.1.4756.104.130.2.6
    ctcDeleteProtocolLlcToGroup OBJECT-TYPE
        SYNTAX      DisplayString
        MAX-ACCESS  read-write
        STATUS      current
        DESCRIPTION
            "To delete a LLC type to Group Name map entry.
             Syntax: <dsap> <ssap>"
        ::= { ctcProtocolBasedVLAN 6 }

    -- 1.3.6.1.4.1.4756.104.130.2.7
    ctcProtocolToGroupMappingTable OBJECT-TYPE
        SYNTAX      SEQUENCE OF CtcProtocolToGroupMappingEntry
        MAX-ACCESS  not-accessible
        STATUS      current
        DESCRIPTION
            "This table shows protocol to group mapped entries."
        ::= { ctcProtocolBasedVLAN 7 }

    -- 1.3.6.1.4.1.4756.104.130.2.7.1
    ctcProtocolToGroupMappingEntry OBJECT-TYPE
        SYNTAX      CtcProtocolToGroupMappingEntry
        MAX-ACCESS  not-accessible
        STATUS      current
        DESCRIPTION
            "The Entry of Protocol to Group Mapping table."
        INDEX { ctcProtocolToGroupMappingIndex }
        ::= { ctcProtocolToGroupMappingTable 1 }

    CtcProtocolToGroupMappingEntry ::=
        SEQUENCE {
            ctcProtocolToGroupMappingIndex   Integer32,
            ctcProtocolToGroupFrameType      INTEGER,
            ctcProtocolToGroupValue          DisplayString,
            ctcProtocolToGroupName           DisplayString
        }

        -- 1.3.6.1.4.1.4756.104.130.2.7.1.1    
        ctcProtocolToGroupMappingIndex OBJECT-TYPE
            SYNTAX      Integer32 (1..64)
            MAX-ACCESS  read-only
            STATUS      current
            DESCRIPTION
                "Indicates the Index of Protocol to Group Mapping table."
            ::= { ctcProtocolToGroupMappingEntry 1 }

        -- 1.3.6.1.4.1.4756.104.130.2.7.1.2    
        ctcProtocolToGroupFrameType OBJECT-TYPE
            SYNTAX      INTEGER {
                            ethernet(1),
                            snap(2),
                            llc(3)
                        }
            MAX-ACCESS  read-only
            STATUS      current
            DESCRIPTION
                "Frame Type can have one of Ethernet, SNAP or LLC."
            ::= { ctcProtocolToGroupMappingEntry 2 }

        -- 1.3.6.1.4.1.4756.104.130.2.7.1.3    
        ctcProtocolToGroupValue OBJECT-TYPE
            SYNTAX      DisplayString
            MAX-ACCESS  read-only
            STATUS      current
            DESCRIPTION
                "This value depends on the three different Frame Types:
                 Ethernet, LLC and SNAP."
            ::= { ctcProtocolToGroupMappingEntry 3 }

        -- 1.3.6.1.4.1.4756.104.130.2.7.1.4    
        ctcProtocolToGroupName OBJECT-TYPE
            SYNTAX      DisplayString
            MAX-ACCESS  read-only
            STATUS      current
            DESCRIPTION
                "A valid Group Name is a unique 16-character long string for every entry which
                 consists of a combination of alphabets (a-z or A-Z) and integers(0-9).
                 Note: special character and underscore(_) are not allowed."
            ::= { ctcProtocolToGroupMappingEntry 4 }

    -- 1.3.6.1.4.1.4756.104.130.2.8
    ctcAddProtocolGroupToVLAN  OBJECT-TYPE
        SYNTAX      DisplayString
        MAX-ACCESS  read-write
        STATUS      current
        DESCRIPTION                                  
            "To add a new entry in Group-to-VLAN Mapping table.
             Syntax: <group_name> <vid>
             A valid Group Name is a string of atmost 16 characters which consists of
             a combination of alphabets (a-z or A-Z) and integers(0-9),
             no special character is allowed. whichever Group name you try map to a VLAN must be
             present in Protocol to Group mapping table and must not be
             preused by any other existing mapping entry on the table.
             Legal values for a VLAN ID are 1 through 4095."
        ::= { ctcProtocolBasedVLAN 8 }

    -- 1.3.6.1.4.1.4756.104.130.2.9
    ctcDeleteProtocolGroupToVLAN OBJECT-TYPE
        SYNTAX      DisplayString
        MAX-ACCESS  read-write
        STATUS      current
        DESCRIPTION                                  
            "To delete a Group-to-VLAN Mapping entry.
             Syntax: <group_name>"
        ::= { ctcProtocolBasedVLAN 9 }

    -- 1.3.6.1.4.1.4756.104.130.2.10
    ctcGroupToVlanMappingTable OBJECT-TYPE
        SYNTAX      SEQUENCE OF CtcGroupToVlanMappingEntry
        MAX-ACCESS  not-accessible
        STATUS      current
        DESCRIPTION
            "This table shows protocol to group mapped entries."
        ::= { ctcProtocolBasedVLAN 10 }

    -- 1.3.6.1.4.1.4756.104.130.2.10.1
    ctcGroupToVlanMappingEntry OBJECT-TYPE
        SYNTAX      CtcGroupToVlanMappingEntry
        MAX-ACCESS  not-accessible
        STATUS      current
        DESCRIPTION
            "The Entry of Protocol to Group Mapping table."
        INDEX { ctcGroupToVlanMappingIndex }
        ::= { ctcGroupToVlanMappingTable 1 }

    CtcGroupToVlanMappingEntry ::=
        SEQUENCE {
            ctcGroupToVlanMappingIndex       Integer32,
            ctcGroupToVlanMappingGroupName   DisplayString,
            ctcGroupToVlanMappingVlanID      Integer32,
            ctcGroupToVlanMappingPortMembers DisplayString
        }

        -- 1.3.6.1.4.1.4756.104.130.2.10.1.1    
        ctcGroupToVlanMappingIndex OBJECT-TYPE
            SYNTAX      Integer32 (1..128)
            MAX-ACCESS  read-only
            STATUS      current
            DESCRIPTION
                "Indicates the Index of Group to VLAN Mapping table."
            ::= { ctcGroupToVlanMappingEntry 1 }

        -- 1.3.6.1.4.1.4756.104.130.2.10.1.2    
        ctcGroupToVlanMappingGroupName OBJECT-TYPE
            SYNTAX      DisplayString
            MAX-ACCESS  read-only
            STATUS      current
            DESCRIPTION
                "Indicates Group name map to a VLAN."
            ::= { ctcGroupToVlanMappingEntry 2 }

        -- 1.3.6.1.4.1.4756.104.130.2.10.1.3    
        ctcGroupToVlanMappingVlanID OBJECT-TYPE
            SYNTAX      Integer32 (1..4095)
            MAX-ACCESS  read-only
            STATUS      current
            DESCRIPTION
                "Indicates the ID to which Group Name will be mapped."
            ::= { ctcGroupToVlanMappingEntry 3 }

        -- 1.3.6.1.4.1.4756.104.130.2.10.1.4    
        ctcGroupToVlanMappingPortMembers OBJECT-TYPE
            SYNTAX      DisplayString
            MAX-ACCESS  read-write
            STATUS      current
            DESCRIPTION
                "To include or exclude the port from the mapping entry."
            ::= { ctcGroupToVlanMappingEntry 4 }

    -- 1.3.6.1.4.1.4756.104.130.3
    ctcIpSubnetBasedVLAN  OBJECT IDENTIFIER ::= { ctcVCL 3 }

    -- 1.3.6.1.4.1.4756.104.130.3.1
    ctcAddIpSubnetBasedVce OBJECT-TYPE
        SYNTAX      DisplayString
        MAX-ACCESS  read-write
        STATUS      current
        DESCRIPTION                                  
            "Add a new IP subnet-based VLAN entry.
             Syntax: <vce_id> <ip_addr> <mask_length> 
             By default, VLAN ID is 1 and all ports are members"
        ::= { ctcIpSubnetBasedVLAN 1 }

    -- 1.3.6.1.4.1.4756.104.130.3.2
    ctcDeleteIpSubnetBasedVce OBJECT-TYPE
        SYNTAX      DisplayString
        MAX-ACCESS  read-write
        STATUS      current
        DESCRIPTION
            "To delete a IP subnet-based VLAN entry.
             Syntax: <vce_id>"
        ::= { ctcIpSubnetBasedVLAN 2 }

    -- 1.3.6.1.4.1.4756.104.130.3.3
    ctcIpSubnetBasedVlanConfigTable OBJECT-TYPE
        SYNTAX      SEQUENCE OF CtcIpSubnetBasedVlanConfigEntry
        MAX-ACCESS  not-accessible
        STATUS      current
        DESCRIPTION
            "The IP subnet-based VLAN enties can be configured here."
        ::= { ctcIpSubnetBasedVLAN 3 }

    -- 1.3.6.1.4.1.4756.104.130.3.3.1
    ctcIpSubnetBasedVlanConfigEntry OBJECT-TYPE
        SYNTAX      CtcIpSubnetBasedVlanConfigEntry
        MAX-ACCESS  not-accessible
        STATUS      current
        DESCRIPTION
            "The Entry of IP subnet-based VLAN table."
        INDEX { ctcIpSubnetBasedVceId }
        ::= { ctcIpSubnetBasedVlanConfigTable 1 }

    CtcIpSubnetBasedVlanConfigEntry ::=
        SEQUENCE {
            ctcIpSubnetBasedVceId              Integer32,
            ctcIpSubnetBasedVceIpAddress       IpAddress,
            ctcIpSubnetBasedVceMaskLength      Integer32,
            ctcIpSubnetBasedVceVlanId          Integer32,
            ctcIpSubnetBasedVcePortMembers     DisplayString
        }

        -- 1.3.6.1.4.1.4756.104.130.3.3.1.1    
        ctcIpSubnetBasedVceId OBJECT-TYPE
            SYNTAX      Integer32 (1..128)
            MAX-ACCESS  read-only
            STATUS      current
            DESCRIPTION
                "Indicates the index of the entry table."
            ::= { ctcIpSubnetBasedVlanConfigEntry 1 }

        -- 1.3.6.1.4.1.4756.104.150.4.3.1.2    
        ctcIpSubnetBasedVceIpAddress OBJECT-TYPE
            SYNTAX      IpAddress
            MAX-ACCESS  read-only
            STATUS      current                          
            DESCRIPTION
                "Indicates the IP address.
                 The IP address is in the format x.y.z.w where x, y, z, and w
                 are decimal numbers between 0 and 255."
            ::= { ctcIpSubnetBasedVlanConfigEntry 2 }

        -- 1.3.6.1.4.1.4756.104.130.3.3.1.3    
        ctcIpSubnetBasedVceMaskLength OBJECT-TYPE
            SYNTAX      Integer32 (1..32)
            MAX-ACCESS  read-only
            STATUS      current
            DESCRIPTION
                "Indicates the network mask length."
            ::= { ctcIpSubnetBasedVlanConfigEntry 3 }

        -- 1.3.6.1.4.1.4756.104.130.3.3.1.4    
        ctcIpSubnetBasedVceVlanId OBJECT-TYPE
            SYNTAX      Integer32 (1..4095)
            MAX-ACCESS  read-write
            STATUS      current
            DESCRIPTION
                "Indicates the VLAN ID. VLAN ID can be changed for the existing entries."
            ::= { ctcIpSubnetBasedVlanConfigEntry 4 }

        -- 1.3.6.1.4.1.4756.104.130.3.3.1.5    
        ctcIpSubnetBasedVcePortMembers OBJECT-TYPE
            SYNTAX      DisplayString
            MAX-ACCESS  read-write
            STATUS      current
            DESCRIPTION
                "To include or exclude the port from IP subnet-based VLAN entry."
            ::= { ctcIpSubnetBasedVlanConfigEntry 5 }


-- Voice VLAN
    -- 1.3.6.1.4.1.4756.104.140
    ctcVoiceVLAN  OBJECT IDENTIFIER ::= { gsw2008ms 140 }

    -- 1.3.6.1.4.1.4756.104.140.1    
    ctcVoiceVlanMode OBJECT-TYPE
        SYNTAX      INTEGER {
                        enabled(1),
                        disabled(2)
                    }
        MAX-ACCESS  read-write
        STATUS      current
        DESCRIPTION
            "Indicates the Voice VLAN mode operation.
             We must disable MSTP feature before we enable Voice VLAN.
             It can avoid the conflict of ingress filtering."
        ::= { ctcVoiceVLAN 1 }
 
    -- 1.3.6.1.4.1.4756.104.140.2    
    ctcVoiceVlanID OBJECT-TYPE
        SYNTAX      Integer32 (1..4095)
        MAX-ACCESS  read-write
        STATUS      current
        DESCRIPTION
            "Indicates the Voice VLAN ID.
             It should be a unique VLAN ID in the system and cannot equal each port PVID.
             It is a conflict in configuration if the value equals management VID, MVR VID, PVID etc."
        ::= { ctcVoiceVLAN 2 }
 
    -- 1.3.6.1.4.1.4756.104.140.3    
    ctcVoiceVlanAgeTime OBJECT-TYPE
        SYNTAX      Integer32 (10..10000000)
        MAX-ACCESS  read-write
        STATUS      current
        DESCRIPTION
            "Indicates the Voice VLAN secure learning aging time.
             It is used when security mode or auto detect mode is enabled.
             In other cases, it will be based on hardware aging time.
             The actual aging time will be situated between the [age_time; 2 * age_time] interval."
        ::= { ctcVoiceVLAN 3 }
 
    -- 1.3.6.1.4.1.4756.104.140.4    
    ctcVoiceVlanTrafficClass OBJECT-TYPE
        SYNTAX      Integer32 (0..7)
        MAX-ACCESS  read-write
        STATUS      current
        DESCRIPTION
            "Indicates the Voice VLAN traffic class.
             All traffic on the Voice VLAN will apply this class."
        ::= { ctcVoiceVLAN 4 }

    -- 1.3.6.1.4.1.4756.104.140.5
    ctcVoiceVlanPortTable OBJECT-TYPE
        SYNTAX      SEQUENCE OF CtcVoiceVlanPortEntry
        MAX-ACCESS  not-accessible
        STATUS      current
        DESCRIPTION
            "This table is used for configuring the switch voice VLAN port."
        ::= { ctcVoiceVLAN 5 }

    -- 1.3.6.1.4.1.4756.104.140.5.1
    ctcVoiceVlanPortEntry OBJECT-TYPE
        SYNTAX      CtcVoiceVlanPortEntry
        MAX-ACCESS  not-accessible
        STATUS      current
        DESCRIPTION
            "The Entry of voice VLAN ports."
        INDEX { ctcPortIndex }
        ::= { ctcVoiceVlanPortTable 1 }

    CtcVoiceVlanPortEntry ::=
        SEQUENCE {
            ctcVoiceVlanPortMode         INTEGER,          
            ctcVoiceVlanPortSecurity     INTEGER,
            ctcVoiceVlanPortDiscovery    INTEGER
        }

        -- 1.3.6.1.4.1.4756.104.140.5.1.1    
        ctcVoiceVlanPortMode OBJECT-TYPE
            SYNTAX      INTEGER {
                            disabled(1),
                            auto(2),
                            forced(3)
                        }
            MAX-ACCESS  read-write
            STATUS      current
            DESCRIPTION
                "Indicates the Voice VLAN port mode. 
                 Possible port modes are:
                 Disabled: Disjoin from Voice VLAN.
                 Auto: Enable auto detect mode.
                       It detects whether there is VoIP phone attached to the specific port and
                       configures the Voice VLAN members automatically.
                 Forced: Force join to Voice VLAN."
            ::= { ctcVoiceVlanPortEntry 1 }

        -- 1.3.6.1.4.1.4756.104.140.5.1.1    
        ctcVoiceVlanPortSecurity OBJECT-TYPE
            SYNTAX      INTEGER {
                            enabled(1),
                            disabled(2)
                        }
            MAX-ACCESS  read-write
            STATUS      current
            DESCRIPTION
                "Indicates the Voice VLAN port security mode.
                 When the function is enabled,
                 all non-telephonic MAC addresses in the Voice VLAN will be blocked for 10 seconds."
            ::= { ctcVoiceVlanPortEntry 2 }

        -- 1.3.6.1.4.1.4756.104.140.5.1.1    
        ctcVoiceVlanPortDiscovery OBJECT-TYPE
            SYNTAX      INTEGER {
                            oui(1),
                            lldp(2),
                            both(3)
                        }
            MAX-ACCESS  read-write
            STATUS      current
            DESCRIPTION
                "Indicates the Voice VLAN port discovery protocol.
                 It will only work when auto detect mode is enabled.
                 We should enable LLDP feature before configuring discovery protocol to LLDP or Both.
                 Changing the discovery protocol to OUI or LLDP will restart auto detect process.
                 Possible discovery protocols are:
                 OUI: Detect telephony device by OUI address.
                 LLDP: Detect telephony device by LLDP.
                 Both: Both OUI and LLDP."
            ::= { ctcVoiceVlanPortEntry 3 }

    -- 1.3.6.1.4.1.4756.104.140.6
    ctcAddVoiceVlanOUI OBJECT-TYPE
        SYNTAX      DisplayString
        MAX-ACCESS  read-write
        STATUS      current
        DESCRIPTION                                  
            "Add a new entry to voice VLAN OUI table.
             Syntax: <oui_addr> [<description>]"
        ::= { ctcVoiceVLAN 6 }

    -- 1.3.6.1.4.1.4756.104.140.7
    ctcDeleteVoiceVlanOUI OBJECT-TYPE
        SYNTAX      DisplayString
        MAX-ACCESS  read-write
        STATUS      current
        DESCRIPTION
            "Delete an entry from voice VLAN OUI table.
             Syntax: <oui_addr>"
        ::= { ctcVoiceVLAN 7 }

    -- 1.3.6.1.4.1.4756.104.140.8
    ctcVoiceVlanOuiTable OBJECT-TYPE
        SYNTAX      SEQUENCE OF CtcVoiceVlanOuiEntry
        MAX-ACCESS  not-accessible
        STATUS      current
        DESCRIPTION
            "This table is used for Configure VOICE VLAN OUI."
        ::= { ctcVoiceVLAN 8 }

    -- 1.3.6.1.4.1.4756.104.140.8.1
    ctcVoiceVlanOuiEntry OBJECT-TYPE
        SYNTAX      CtcVoiceVlanOuiEntry
        MAX-ACCESS  not-accessible
        STATUS      current
        DESCRIPTION
            "The Entry of VOICE VLAN OUI table."
        INDEX { ctcVoiceVlanOuiIndex }
        ::= { ctcVoiceVlanOuiTable 1 }

    CtcVoiceVlanOuiEntry ::=
        SEQUENCE {
            ctcVoiceVlanOuiIndex         Integer32,          
            ctcVoiceVlanTelephonyOUI     OCTET STRING,
            ctcVoiceVlanOuiDescription   OCTET STRING
        }

        -- 1.3.6.1.4.1.4756.104.140.8.1.1    
        ctcVoiceVlanOuiIndex OBJECT-TYPE
            SYNTAX      Integer32 (1..16)
            MAX-ACCESS  read-only
            STATUS      current
            DESCRIPTION
                "The maximum entry number is 16.
                 Modifying the OUI table will restart auto detection of OUI process."
            ::= { ctcVoiceVlanOuiEntry 1 }

        -- 1.3.6.1.4.1.4756.104.140.8.1.2    
        ctcVoiceVlanTelephonyOUI OBJECT-TYPE
            SYNTAX      OCTET STRING (SIZE (8))
            MAX-ACCESS  read-only
            STATUS      current
            DESCRIPTION
                "A telephony OUI address is a globally unique identifier assigned to a vendor by IEEE.
                 It must be 6 characters long and the input format is xx-xx-xx (x is a hexadecimal digit)."
            ::= { ctcVoiceVlanOuiEntry 2 }

        -- 1.3.6.1.4.1.4756.104.140.8.1.3    
        ctcVoiceVlanOuiDescription OBJECT-TYPE
            SYNTAX      OCTET STRING (SIZE (0..32))
            MAX-ACCESS  read-write
            STATUS      current
            DESCRIPTION
                "The description of OUI address.
                 Normally, it describes which vendor telephony device it belongs to.
                 The allowed string length is 0 to 32."
            ::= { ctcVoiceVlanOuiEntry 3 }


-- QoS
    -- 1.3.6.1.4.1.4756.104.150
    ctcQoS  OBJECT IDENTIFIER ::= { gsw2008ms 150 }

    -- 1.3.6.1.4.1.4756.104.150.1
    ctcQosIngress  OBJECT IDENTIFIER ::= { ctcQoS 1 }

    -- 1.3.6.1.4.1.4756.104.150.1.1
    ctcQosRxPortClassifiedTable OBJECT-TYPE
        SYNTAX      SEQUENCE OF CtcQosRxPortClassifiedEntry
        MAX-ACCESS  not-accessible
        STATUS      current
        DESCRIPTION
            "This table allows you to configure the basic QoS Ingress Classification settings for all ports."
        ::= { ctcQosIngress 1 }

    -- 1.3.6.1.4.1.4756.104.150.1.1.1
    ctcQosRxPortClassifiedEntry OBJECT-TYPE
        SYNTAX      CtcQosRxPortClassifiedEntry
        MAX-ACCESS  not-accessible
        STATUS      current
        DESCRIPTION
            "The port entry for which the configuration in table."
        INDEX { ctcPortIndex }
        ::= { ctcQosRxPortClassifiedTable 1 }

    CtcQosRxPortClassifiedEntry ::=
        SEQUENCE {
            ctcQosRxPortQosClass         Integer32,
            ctcQosRxPortDpLevel          Integer32,
            ctcQosRxPortPCP              Integer32,
            ctcQosRxPortDEI              Integer32,
            ctcQosRxPortTagClassified    INTEGER,
            ctcQosRxPortDscpBased        TruthValue
        }

        -- 1.3.6.1.4.1.4756.104.150.1.1.1.1    
        ctcQosRxPortQosClass OBJECT-TYPE
            SYNTAX      Integer32 (0..7)
            MAX-ACCESS  read-write
            STATUS      current
            DESCRIPTION
                "Controls the default QoS class,
                 i.e., the QoS class for frames not classified in any other way.
                 There is a one to one mapping between QoS class, queue and priority.
                 A QoS class of 0 (zero) has the lowest priority."
            ::= { ctcQosRxPortClassifiedEntry 1 }

        -- 1.3.6.1.4.1.4756.104.150.1.1.1.2    
        ctcQosRxPortDpLevel OBJECT-TYPE
            SYNTAX      Integer32 (0..1)
            MAX-ACCESS  read-write
            STATUS      current
            DESCRIPTION
                "Controls the default DP(Drop Precedence) level,
                 i.e., the DP level for frames not classified in any other way."
            ::= { ctcQosRxPortClassifiedEntry 2 }

        -- 1.3.6.1.4.1.4756.104.150.1.1.1.3    
        ctcQosRxPortPCP OBJECT-TYPE
            SYNTAX      Integer32 (0..7)
            MAX-ACCESS  read-write
            STATUS      current
            DESCRIPTION
                "Controls the default PCP(Priority Code Point) for untagged frames."
            ::= { ctcQosRxPortClassifiedEntry 3 }

        -- 1.3.6.1.4.1.4756.104.150.1.1.1.4    
        ctcQosRxPortDEI OBJECT-TYPE
            SYNTAX      Integer32 (0..1)
            MAX-ACCESS  read-write
            STATUS      current
            DESCRIPTION
                "Controls the default DEI(Data Encryption Standard) for untagged frames."
            ::= { ctcQosRxPortClassifiedEntry 4 }

        -- 1.3.6.1.4.1.4756.104.150.1.1.1.5    
        ctcQosRxPortTagClassified OBJECT-TYPE
            SYNTAX      INTEGER {
                            enabled(1),
                            disabled(2)
                        }
            MAX-ACCESS  read-write
            STATUS      current
            DESCRIPTION
                "The classification mode for tagged frames on this port.
                 Disabled: Use default QoS class and DP level for tagged frames.
                 Enabled: Use mapped versions of PCP and DEI for tagged frames."
            ::= { ctcQosRxPortClassifiedEntry 5 }

        -- 1.3.6.1.4.1.4756.104.150.1.1.1.6    
        ctcQosRxPortDscpBased OBJECT-TYPE
            SYNTAX      TruthValue
            MAX-ACCESS  read-write
            STATUS      current
            DESCRIPTION
                "To enable DSCP Based QoS Ingress Port Classification."
            ::= { ctcQosRxPortClassifiedEntry 6 }

    -- 1.3.6.1.4.1.4756.104.150.1.2
    ctcQosRxPortTagMappingTable OBJECT-TYPE
        SYNTAX      SEQUENCE OF CtcQosRxPortTagMappingEntry
        MAX-ACCESS  not-accessible
        STATUS      current
        DESCRIPTION
            "The clasification mode for tagged frames are configured on this table."
        ::= { ctcQosIngress 2 }

    -- 1.3.6.1.4.1.4756.104.150.1.2.1
    ctcQosRxPortTagMappingEntry OBJECT-TYPE
        SYNTAX      CtcQosRxPortTagMappingEntry
        MAX-ACCESS  not-accessible
        STATUS      current
        DESCRIPTION
            "The port entry for which the configuration in table."
        INDEX { ctcPortIndex, ctcQosRxPortMappingOfPCP, ctcQosRxPortMappingOfDEI }
        ::= { ctcQosRxPortTagMappingTable 1 }

    CtcQosRxPortTagMappingEntry ::=
        SEQUENCE {
            ctcQosRxPortMappingOfPCP         Integer32,
            ctcQosRxPortMappingOfDEI         Integer32,
            ctcQosRxPortMappingToQosClass    Integer32,
            ctcQosRxPortMappingToDpLevel     Integer32
        }

        -- 1.3.6.1.4.1.4756.104.150.1.2.1.1    
        ctcQosRxPortMappingOfPCP OBJECT-TYPE
            SYNTAX      Integer32 (0..7)
            MAX-ACCESS  read-only
            STATUS      current
            DESCRIPTION
                "Controls the mapping of the PCP classified."
            ::= { ctcQosRxPortTagMappingEntry 1 }

        -- 1.3.6.1.4.1.4756.104.150.1.2.1.2    
        ctcQosRxPortMappingOfDEI OBJECT-TYPE
            SYNTAX      Integer32 (0..1)
            MAX-ACCESS  read-only
            STATUS      current
            DESCRIPTION
                "Controls the mapping of the DEI classified."
            ::= { ctcQosRxPortTagMappingEntry 2 }

        -- 1.3.6.1.4.1.4756.104.150.1.2.1.3    
        ctcQosRxPortMappingToQosClass OBJECT-TYPE
            SYNTAX      Integer32 (0..7)
            MAX-ACCESS  read-write
            STATUS      current
            DESCRIPTION
                "Controls the mapping to QoS class values."
            ::= { ctcQosRxPortTagMappingEntry 3 }

        -- 1.3.6.1.4.1.4756.104.150.1.2.1.4    
        ctcQosRxPortMappingToDpLevel OBJECT-TYPE
            SYNTAX      Integer32 (0..1)
            MAX-ACCESS  read-write
            STATUS      current
            DESCRIPTION
                "Controls the mapping to DP level values."
            ::= { ctcQosRxPortTagMappingEntry 4 }

    -- 1.3.6.1.4.1.4756.104.150.1.3
    ctcQosRxPortShapersTable OBJECT-TYPE
        SYNTAX      SEQUENCE OF CtcQosRxPortShapersEntry
        MAX-ACCESS  not-accessible
        STATUS      current
        DESCRIPTION
            "This table allows you to configure the Ingress Shaper settings for all ports."
        ::= { ctcQosIngress 3 }

    -- 1.3.6.1.4.1.4756.104.150.1.3.1
    ctcQosRxPortShapersEntry OBJECT-TYPE
        SYNTAX      CtcQosRxPortShapersEntry
        MAX-ACCESS  not-accessible
        STATUS      current
        DESCRIPTION
            "The port entry for which the configuration in table."
        INDEX { ctcPortIndex }
        ::= { ctcQosRxPortShapersTable 1 }

    CtcQosRxPortShapersEntry ::=
        SEQUENCE {
            ctcQosRxPortShaperEnabled        TruthValue,
            ctcQosRxPortShaperRate           Integer32,
            ctcQosRxPortShaperBurstSize      Integer32
        }

        -- 1.3.6.1.4.1.4756.104.150.1.3.1.1    
        ctcQosRxPortShaperEnabled OBJECT-TYPE
            SYNTAX      TruthValue
            MAX-ACCESS  read-write
            STATUS      current
            DESCRIPTION
                "Controls whether the shaper is enabled on this switch port."
            ::= { ctcQosRxPortShapersEntry 1 }

        -- 1.3.6.1.4.1.4756.104.150.1.3.1.2    
        ctcQosRxPortShaperRate OBJECT-TYPE
            SYNTAX      Integer32 (100..3300000)
            MAX-ACCESS  read-write
            STATUS      current
            DESCRIPTION
                "Controls the rate for the shaper. The default value is 500.
                 This value is restricted to 100-3300000."
            DEFVAL     { 500 }     
            ::= { ctcQosRxPortShapersEntry 2 }

        -- 1.3.6.1.4.1.4756.104.150.1.3.1.3    
        ctcQosRxPortShaperBurstSize OBJECT-TYPE
            SYNTAX      Integer32 (0..252)
            MAX-ACCESS  read-write
            STATUS      current
            DESCRIPTION
                "Controls the ingress shaper burst size, The default value is 4 KBytes,
                 The largest supported value is 252 KBytes."
            DEFVAL     { 4 }     
            ::= { ctcQosRxPortShapersEntry 3 }


    -- 1.3.6.1.4.1.4756.104.150.1.4
    ctcQosRxPortPolicersTable OBJECT-TYPE
        SYNTAX      SEQUENCE OF CtcQosRxPortPolicersEntry
        MAX-ACCESS  not-accessible
        STATUS      current
        DESCRIPTION
            "This table allows you to configure the Policer settings for all ports."
        ::= { ctcQosIngress 4 }

    -- 1.3.6.1.4.1.4756.104.150.1.4.1
    ctcQosRxPortPolicersEntry OBJECT-TYPE
        SYNTAX      CtcQosRxPortPolicersEntry
        MAX-ACCESS  not-accessible
        STATUS      current
        DESCRIPTION
            "The port entry for which the configuration in table."
        INDEX { ctcPortIndex }
        ::= { ctcQosRxPortPolicersTable 1 }

    CtcQosRxPortPolicersEntry ::=
        SEQUENCE {
            ctcQosRxPortPolicyEnabled        TruthValue,
            ctcQosRxPortPolicyRate           Integer32,
            ctcQosRxPortPolicyUnit           INTEGER,
            ctcQosRxPortPolicyFlowControl    TruthValue
        }

        -- 1.3.6.1.4.1.4756.104.150.1.4.1.1    
        ctcQosRxPortPolicyEnabled OBJECT-TYPE
            SYNTAX      TruthValue
            MAX-ACCESS  read-write
            STATUS      current
            DESCRIPTION
                "Controls whether the policer is enabled on this switch port."
            ::= { ctcQosRxPortPolicersEntry 1 }

        -- 1.3.6.1.4.1.4756.104.150.1.4.1.2    
        ctcQosRxPortPolicyRate OBJECT-TYPE
            SYNTAX      Integer32 (100..3300000)
            MAX-ACCESS  read-write
            STATUS      current
            DESCRIPTION
                "Controls the rate for the policer. The default value is 500.
                 This value is restricted to 100-3300000."
            DEFVAL     { 500 }     
            ::= { ctcQosRxPortPolicersEntry 2 }

        -- 1.3.6.1.4.1.4756.104.150.1.4.1.3    
        ctcQosRxPortPolicyUnit OBJECT-TYPE
            SYNTAX      INTEGER {
                            kbps(1),
                            fps(2)
                        }
            MAX-ACCESS  read-write
            STATUS      current
            DESCRIPTION
                "Controls the unit of measure for the policer rate as kbps or fps.
                 The default value is 'kbps'."
            DEFVAL     { kbps }     
            ::= { ctcQosRxPortPolicersEntry 3 }

        -- 1.3.6.1.4.1.4756.104.150.1.4.1.4    
        ctcQosRxPortPolicyFlowControl OBJECT-TYPE
            SYNTAX      TruthValue
            MAX-ACCESS  read-write
            STATUS      current
            DESCRIPTION
                "If flow control is enabled and the port is in flow control mode,
                 then pause frames are sent instead of discarding frames."
            ::= { ctcQosRxPortPolicersEntry 4 }

    -- 1.3.6.1.4.1.4756.104.150.2
    ctcQosEgress  OBJECT IDENTIFIER ::= { ctcQoS 2 }

    -- 1.3.6.1.4.1.4756.104.150.2.1
    ctcQosTxPortSchedulerAndShaperTable OBJECT-TYPE
        SYNTAX      SEQUENCE OF CtcQosTxPortSchedulerAndShaperEntry
        MAX-ACCESS  not-accessible
        STATUS      current
        DESCRIPTION
            "This table allows you to configure the Scheduler Mode and Shaper for all ports."
        ::= { ctcQosEgress 1 }

    -- 1.3.6.1.4.1.4756.104.150.2.1.1
    ctcQosTxPortSchedulerAndShaperEntry OBJECT-TYPE
        SYNTAX      CtcQosTxPortSchedulerAndShaperEntry
        MAX-ACCESS  not-accessible
        STATUS      current
        DESCRIPTION
            "The port entry for which the configuration in table."
        INDEX { ctcPortIndex }
        ::= { ctcQosTxPortSchedulerAndShaperTable 1 }

    CtcQosTxPortSchedulerAndShaperEntry ::=
        SEQUENCE {
            ctcQosTxPortSchedulerMode    INTEGER,
            ctcQosTxPortShaperEnabled    TruthValue,
            ctcQosTxPortShaperRate       Integer32
        }

        -- 1.3.6.1.4.1.4756.104.150.2.1.1.1    
        ctcQosTxPortSchedulerMode OBJECT-TYPE
            SYNTAX      INTEGER {
                            strictPriority(1),
                            weighted(2)
                        }
            MAX-ACCESS  read-write
            STATUS      current
            DESCRIPTION
                "Controls whether the scheduler mode is 'Strict Priority' or 'Weighted' on this port."
            ::= { ctcQosTxPortSchedulerAndShaperEntry 1 }

        -- 1.3.6.1.4.1.4756.104.150.2.1.1.2    
        ctcQosTxPortShaperEnabled OBJECT-TYPE
            SYNTAX      TruthValue
            MAX-ACCESS  read-write
            STATUS      current
            DESCRIPTION
                "Controls whether the port shaper is enabled for this port."
            ::= { ctcQosTxPortSchedulerAndShaperEntry 2 }

        -- 1.3.6.1.4.1.4756.104.150.2.1.1.3    
        ctcQosTxPortShaperRate OBJECT-TYPE
            SYNTAX      Integer32 (100..3300000)
            UNITS       "kbps"
            MAX-ACCESS  read-write
            STATUS      current
            DESCRIPTION
                "Controls the rate for the shaper. The default value is 500 kbps.
                 This value is restricted to 100-3300000 kbps."
            DEFVAL     { 500 }     
            ::= { ctcQosTxPortSchedulerAndShaperEntry 3 }

    -- 1.3.6.1.4.1.4756.104.150.2.2
    ctcQosTxPortQueueSchedulerTable OBJECT-TYPE
        SYNTAX      SEQUENCE OF CtcQosTxPortQueueSchedulerEntry
        MAX-ACCESS  not-accessible
        STATUS      current
        DESCRIPTION
            "This table allows you to configure the Queue Scheduler Weight for all ports."
        ::= { ctcQosEgress 2 }

    -- 1.3.6.1.4.1.4756.104.150.2.2.1
    ctcQosTxPortQueueSchedulerEntry OBJECT-TYPE
        SYNTAX      CtcQosTxPortQueueSchedulerEntry
        MAX-ACCESS  not-accessible
        STATUS      current
        DESCRIPTION
            "The port entry for which the configuration in table."
        INDEX { ctcPortIndex, ctcQosTxPortQueueIndex }
        ::= { ctcQosTxPortQueueSchedulerTable 1 }

    CtcQosTxPortQueueSchedulerEntry ::=
        SEQUENCE {
            ctcQosTxPortQueueIndex       Integer32,
            ctcQosTxPortQueueWeight      Integer32,
            ctcQosTxPortQueuePercent     Integer32
        }

        -- 1.3.6.1.4.1.4756.104.150.2.2.1.1    
        ctcQosTxPortQueueIndex OBJECT-TYPE
            SYNTAX      Integer32 (0..5)
            MAX-ACCESS  read-only
            STATUS      current
            DESCRIPTION
                "The egress Queue Scheduler index."
            ::= { ctcQosTxPortQueueSchedulerEntry 1 }

        -- 1.3.6.1.4.1.4756.104.150.2.2.1.2    
        ctcQosTxPortQueueWeight OBJECT-TYPE
            SYNTAX      Integer32 (1..100)
            MAX-ACCESS  read-write
            STATUS      current
            DESCRIPTION
                "Controls the weight for this queue. The default value is 17.
                 This value is restricted to 1-100.
                 This parameter is only affected if Scheduler Mode is set to 'Weighted'." 
            DEFVAL     { 17 }     
            ::= { ctcQosTxPortQueueSchedulerEntry 2 }

        -- 1.3.6.1.4.1.4756.104.150.2.2.1.3    
        ctcQosTxPortQueuePercent OBJECT-TYPE
            SYNTAX      Integer32 (1..100)
            MAX-ACCESS  read-only
            STATUS      current
            DESCRIPTION
                "Shows the weight in percent for this queue.
                 This parameter is only shown if Scheduler Mode is set to 'Weighted'."
            ::= { ctcQosTxPortQueueSchedulerEntry 3 }

    -- 1.3.6.1.4.1.4756.104.150.2.3
    ctcQosTxPortQueueShapersTable OBJECT-TYPE
        SYNTAX      SEQUENCE OF CtcQosTxPortQueueShapersEntry
        MAX-ACCESS  not-accessible
        STATUS      current
        DESCRIPTION
            "This table allows you to configure the Scheduler Mode and Shaper for all ports."
        ::= { ctcQosEgress 3 }

    -- 1.3.6.1.4.1.4756.104.150.2.3.1
    ctcQosTxPortQueueShapersEntry OBJECT-TYPE
        SYNTAX      CtcQosTxPortQueueShapersEntry
        MAX-ACCESS  not-accessible
        STATUS      current
        DESCRIPTION
            "The port entry for which the configuration in table."
        INDEX { ctcPortIndex, ctcQosTxPortQueueIndex }
        ::= { ctcQosTxPortQueueShapersTable 1 }

    CtcQosTxPortQueueShapersEntry ::=
        SEQUENCE {
            ctcQosTxPortQueueShaperEnabled   TruthValue,
            ctcQosTxPortQueueShaperRate      Integer32,
            ctcQosTxPortQueueShaperExcess    TruthValue
        }

        -- 1.3.6.1.4.1.4756.104.150.2.3.1.1    
        ctcQosTxPortQueueShaperEnabled OBJECT-TYPE
            SYNTAX      TruthValue
            MAX-ACCESS  read-write
            STATUS      current
            DESCRIPTION
                "Controls whether the queue shaper is enabled for this queue on this port."
            ::= { ctcQosTxPortQueueShapersEntry 1 }

        -- 1.3.6.1.4.1.4756.104.150.2.3.1.2    
        ctcQosTxPortQueueShaperRate OBJECT-TYPE
            SYNTAX      Integer32 (100..3300000)
            UNITS       "kbps"
            MAX-ACCESS  read-write
            STATUS      current
            DESCRIPTION
                "Controls the rate for the queue shaper.
                 This parameter is only affected if Port Queue Mode is enabled.
                 This value is restricted to 100-3300000 kbps.
                 The default value is 500 kbps."
            DEFVAL     { 500 }     
            ::= { ctcQosTxPortQueueShapersEntry 2 }

        -- 1.3.6.1.4.1.4756.104.150.2.3.1.3    
        ctcQosTxPortQueueShaperExcess OBJECT-TYPE
            SYNTAX      TruthValue
            MAX-ACCESS  read-write
            STATUS      current
            DESCRIPTION
                "Controls whether the queue is allowed to use excess bandwidth.
                 This parameter is only affected if Port Queue Mode is enabled."
            ::= { ctcQosTxPortQueueShapersEntry 3 }

    -- 1.3.6.1.4.1.4756.104.150.2.4
    ctcQosTxPortTagRemarkingTable OBJECT-TYPE
        SYNTAX      SEQUENCE OF CtcQosTxPortTagRemarkingEntry
        MAX-ACCESS  not-accessible
        STATUS      current
        DESCRIPTION
            "This table allows you to configure the egress Port Tag Remarking for all ports."
        ::= { ctcQosEgress 4 }

    -- 1.3.6.1.4.1.4756.104.150.2.4.1
    ctcQosTxPortTagRemarkingEntry OBJECT-TYPE
        SYNTAX      CtcQosTxPortTagRemarkingEntry
        MAX-ACCESS  not-accessible
        STATUS      current
        DESCRIPTION
            "The port entry for which the configuration in table."
        INDEX { ctcPortIndex }
        ::= { ctcQosTxPortTagRemarkingTable 1 }

    CtcQosTxPortTagRemarkingEntry ::=
        SEQUENCE {
            ctcQosTxPortTagRemarkingMode     INTEGER
        }

        -- 1.3.6.1.4.1.4756.104.150.2.4.1.1    
        ctcQosTxPortTagRemarkingMode OBJECT-TYPE
            SYNTAX      INTEGER {
                            classified(1),
                            default(2),
                            mapped(3)
                        }
            MAX-ACCESS  read-write
            STATUS      current
            DESCRIPTION
                "Controls the tag remarking mode for this port.
                 Classified: Use classified PCP/DEI values.
                 Default: Use default PCP/DEI values.
                 Mapped: Use mapped versions of QoS class and DP level."
            ::= { ctcQosTxPortTagRemarkingEntry 1 }

    -- 1.3.6.1.4.1.4756.104.150.2.5
    ctcQosTxPortDefaultTagRemarkingTable OBJECT-TYPE
        SYNTAX      SEQUENCE OF CtcQosTxPortDefaultTagRemarkingEntry
        MAX-ACCESS  not-accessible
        STATUS      current
        DESCRIPTION
            "This table Controls the default PCP and DEI values used
             when the Remarking Mode is set to 'Default'."
        ::= { ctcQosEgress 5 }

    -- 1.3.6.1.4.1.4756.104.150.2.5.1
    ctcQosTxPortDefaultTagRemarkingEntry OBJECT-TYPE
        SYNTAX      CtcQosTxPortDefaultTagRemarkingEntry
        MAX-ACCESS  not-accessible
        STATUS      current
        DESCRIPTION
            "The port entry for which the configuration in table."
        INDEX { ctcPortIndex }
        ::= { ctcQosTxPortDefaultTagRemarkingTable 1 }

    CtcQosTxPortDefaultTagRemarkingEntry ::=
        SEQUENCE {
            ctcQosTxPortDefaultPcpRemarking  Integer32,
            ctcQosTxPortDefaultDeiRemarking  Integer32
        }

        -- 1.3.6.1.4.1.4756.104.150.2.5.1.1    
        ctcQosTxPortDefaultPcpRemarking OBJECT-TYPE
            SYNTAX      Integer32 (0..7)
            MAX-ACCESS  read-write
            STATUS      current
            DESCRIPTION
                "Controls the default PCP values used."
            ::= { ctcQosTxPortDefaultTagRemarkingEntry 1 }

        -- 1.3.6.1.4.1.4756.104.150.2.5.1.2    
        ctcQosTxPortDefaultDeiRemarking OBJECT-TYPE
            SYNTAX      Integer32 (0..1)
            MAX-ACCESS  read-write
            STATUS      current
            DESCRIPTION
                "Controls the default DEI values used."
            ::= { ctcQosTxPortDefaultTagRemarkingEntry 2 }

    -- 1.3.6.1.4.1.4756.104.150.2.6
    ctcQosTxPortMappingTagRemarkingTable OBJECT-TYPE
        SYNTAX      SEQUENCE OF CtcQosTxPortMappingTagRemarkingEntry
        MAX-ACCESS  not-accessible
        STATUS      current
        DESCRIPTION
            "This table controls the mapping of the classified (QoS class, DP level) to
             (PCP, DEI) values when the Remarking Mode is set to 'Mapped'"
        ::= { ctcQosEgress 6 }

    -- 1.3.6.1.4.1.4756.104.150.2.6.1
    ctcQosTxPortMappingTagRemarkingEntry OBJECT-TYPE
        SYNTAX      CtcQosTxPortMappingTagRemarkingEntry
        MAX-ACCESS  not-accessible
        STATUS      current
        DESCRIPTION
            "The port entry for which the configuration in table."
        INDEX { ctcPortIndex, ctcQosTxPortMappingOfQosClass, ctcQosTxPortMappingOfDpLevel }
        ::= { ctcQosTxPortMappingTagRemarkingTable 1 }

    CtcQosTxPortMappingTagRemarkingEntry ::=
        SEQUENCE {
            ctcQosTxPortMappingOfQosClass    Integer32,
            ctcQosTxPortMappingOfDpLevel     Integer32,
            ctcQosTxPortMappingToPCP         Integer32,
            ctcQosTxPortMappingToDEI         Integer32            
        }

        -- 1.3.6.1.4.1.4756.104.150.2.6.1.1    
        ctcQosTxPortMappingOfQosClass OBJECT-TYPE
            SYNTAX      Integer32 (0..7)
            MAX-ACCESS  read-only
            STATUS      current
            DESCRIPTION
                "Controls the mapping of the QoS class."
            ::= { ctcQosTxPortMappingTagRemarkingEntry 1 }

        -- 1.3.6.1.4.1.4756.104.150.2.6.1.2    
        ctcQosTxPortMappingOfDpLevel OBJECT-TYPE
            SYNTAX      Integer32 (0..1)
            MAX-ACCESS  read-only
            STATUS      current
            DESCRIPTION
                "Controls the mapping of the DP level."
            ::= { ctcQosTxPortMappingTagRemarkingEntry 2 }

        -- 1.3.6.1.4.1.4756.104.150.2.6.1.3    
        ctcQosTxPortMappingToPCP OBJECT-TYPE
            SYNTAX      Integer32 (0..7)
            MAX-ACCESS  read-write
            STATUS      current
            DESCRIPTION
                "Controls the mapping to PCP values."
            ::= { ctcQosTxPortMappingTagRemarkingEntry 3 }

        -- 1.3.6.1.4.1.4756.104.150.2.6.1.4    
        ctcQosTxPortMappingToDEI OBJECT-TYPE
            SYNTAX      Integer32 (0..1)
            MAX-ACCESS  read-write
            STATUS      current
            DESCRIPTION
                "Controls the mapping to DEI values."
            ::= { ctcQosTxPortMappingTagRemarkingEntry 4 }


    -- 1.3.6.1.4.1.4756.104.150.3
    ctcQosDSCP  OBJECT IDENTIFIER ::= { ctcQoS 3 }

    -- 1.3.6.1.4.1.4756.104.150.3.1
    ctcQosPortDscpConfigTable OBJECT-TYPE
        SYNTAX      SEQUENCE OF CtcQosPortDscpConfigEntry
        MAX-ACCESS  not-accessible
        STATUS      current
        DESCRIPTION
            "This table allows you to configure the basic QoS Port DSCP Configuration settings
             for all ports."
        ::= { ctcQosDSCP 1 }

    -- 1.3.6.1.4.1.4756.104.150.3.1.1
    ctcQosPortDscpConfigEntry OBJECT-TYPE
        SYNTAX      CtcQosPortDscpConfigEntry
        MAX-ACCESS  not-accessible
        STATUS      current
        DESCRIPTION
            "The port entry for which the configuration in table."
        INDEX { ctcPortIndex }
        ::= { ctcQosPortDscpConfigTable 1 }

    CtcQosPortDscpConfigEntry ::=
        SEQUENCE {
            ctcQosPortDscpRxTranlateEnabled  TruthValue,
            ctcQosPortDscpRxClassifyMode     INTEGER,
            ctcQosPortDscpTxRewriteMode      INTEGER            
        }

        -- 1.3.6.1.4.1.4756.104.150.3.1.1.1    
        ctcQosPortDscpRxTranlateEnabled OBJECT-TYPE
            SYNTAX      TruthValue
            MAX-ACCESS  read-write
            STATUS      current
            DESCRIPTION
                "To Enable the Ingress Translation."
            ::= { ctcQosPortDscpConfigEntry 1 }

        -- 1.3.6.1.4.1.4756.104.150.3.1.1.2    
        ctcQosPortDscpRxClassifyMode OBJECT-TYPE
            SYNTAX      INTEGER {
                            disabled(1),
                            dscp0(2),
                            selected(3),
                            all(4)
                        }
            MAX-ACCESS  read-write
            STATUS      current
            DESCRIPTION
                "Classification for a port have 4 different values:
                 Disable: No Ingress DSCP Classification.
                 DSCP=0: Classify if incoming (or translated if enabled) DSCP is 0.
                 Selected: Classify only selected DSCP for which classification is enabled as
                           specified in DSCP Translation window for the specific DSCP.
                 All: Classify all DSCP."
            ::= { ctcQosPortDscpConfigEntry 2 }

        -- 1.3.6.1.4.1.4756.104.150.3.1.1.3    
        ctcQosPortDscpTxRewriteMode OBJECT-TYPE
            SYNTAX      INTEGER {
                            disabled(1),
                            enabled(2),
                            remapDpUnaware(3),
                            remapDpAware(4)
                        }
            MAX-ACCESS  read-write
            STATUS      current
            DESCRIPTION
                "Port Egress Rewriting can be one of -
                 Disable: No Egress rewrite.
                 Enable: Rewrite enable without remapped.
                 Remap DP Unaware: DSCP remarked with DSCP value from
                                   analyzer remapped through remap table .
                 Remap DP Aware: DSCP remarked with DSCP value from
                                 analyzer remapped through remap DP aware tables."
            ::= { ctcQosPortDscpConfigEntry 3 }

    -- 1.3.6.1.4.1.4756.104.150.3.2
    ctcQosDscpBasedRxClassifiedTable OBJECT-TYPE
        SYNTAX      SEQUENCE OF CtcQosDscpBasedRxClassifiedEntry
        MAX-ACCESS  not-accessible
        STATUS      current
        DESCRIPTION
            "This table allows you to configure
             the basic QoS DSCP based QoS Ingress Classification settings for all switches."
        ::= { ctcQosDSCP 2 }

    -- 1.3.6.1.4.1.4756.104.150.3.2.1
    ctcQosDscpBasedRxClassifiedEntry OBJECT-TYPE
        SYNTAX      CtcQosDscpBasedRxClassifiedEntry
        MAX-ACCESS  not-accessible
        STATUS      current
        DESCRIPTION
            "The DSCP values in table."
        INDEX { ctcQosDscpRx }
        ::= { ctcQosDscpBasedRxClassifiedTable 1 }

    CtcQosDscpBasedRxClassifiedEntry ::=
        SEQUENCE {
            ctcQosDscpRx             Integer32,
            ctcQosDscpRxTrusted      TruthValue,
            ctcQosDscpRxToQosClass   Integer32,
            ctcQosDscpRxToDPL        Integer32            
        }

        -- 1.3.6.1.4.1.4756.104.150.3.2.1.1    
        ctcQosDscpRx OBJECT-TYPE
            SYNTAX      Integer32 (0..63)
            MAX-ACCESS  read-only
            STATUS      current
            DESCRIPTION
                "Maximum number of supported DSCP values are 64
                 and valid DSCP value ranges from 0 to 63."
            ::= { ctcQosDscpBasedRxClassifiedEntry 1 }

        -- 1.3.6.1.4.1.4756.104.150.3.2.1.2    
        ctcQosDscpRxTrusted OBJECT-TYPE
            SYNTAX      TruthValue
            MAX-ACCESS  read-write
            STATUS      current
            DESCRIPTION
                "The DSCP value is trusted."
            ::= { ctcQosDscpBasedRxClassifiedEntry 2 }

        -- 1.3.6.1.4.1.4756.104.150.3.2.1.3    
        ctcQosDscpRxToQosClass OBJECT-TYPE
            SYNTAX      Integer32 (0..7)
            MAX-ACCESS  read-write
            STATUS      current
            DESCRIPTION
                "QoS Class value can be any of (0-7)."
            ::= { ctcQosDscpBasedRxClassifiedEntry 3 }

        -- 1.3.6.1.4.1.4756.104.150.3.2.1.4    
        ctcQosDscpRxToDPL OBJECT-TYPE
            SYNTAX      Integer32 (0..1)
            MAX-ACCESS  read-write
            STATUS      current
            DESCRIPTION
                "Drop Precedence Level (0-1)."
            ::= { ctcQosDscpBasedRxClassifiedEntry 4 }

    -- 1.3.6.1.4.1.4756.104.150.3.3
    ctcDscpTranslationTable OBJECT-TYPE
        SYNTAX      SEQUENCE OF CtcDscpTranslationEntry
        MAX-ACCESS  not-accessible
        STATUS      current
        DESCRIPTION
            "This table allows you to configure
             the basic QoS DSCP based QoS Ingress Classification settings for all switches."
        ::= { ctcQosDSCP 3 }

    -- 1.3.6.1.4.1.4756.104.150.3.3.1
    ctcDscpTranslationEntry OBJECT-TYPE
        SYNTAX      CtcDscpTranslationEntry
        MAX-ACCESS  not-accessible
        STATUS      current
        DESCRIPTION
            "The DSCP values in table."
        INDEX { ctcTranslatedDSCP }
        ::= { ctcDscpTranslationTable 1 }

    CtcDscpTranslationEntry ::=
        SEQUENCE {
            ctcTranslatedDSCP        Integer32,
            ctcDscpRxTranslation     Integer32,
            ctcDscpRxClassify        TruthValue,
            ctcDscpTxRemapDP0        Integer32,
            ctcDscpTxRemapDP1        Integer32            
        }

        -- 1.3.6.1.4.1.4756.104.150.3.3.1.1    
        ctcTranslatedDSCP OBJECT-TYPE
            SYNTAX      Integer32 (0..63)
            MAX-ACCESS  read-only
            STATUS      current
            DESCRIPTION
                "Maximum number of supported DSCP values are 64
                 and valid DSCP value ranges from 0 to 63."
            ::= { ctcDscpTranslationEntry 1 }

        -- 1.3.6.1.4.1.4756.104.150.3.3.1.2    
        ctcDscpRxTranslation OBJECT-TYPE
            SYNTAX      Integer32 (0..63)
            MAX-ACCESS  read-write
            STATUS      current
            DESCRIPTION
                "DSCP at Ingress side can be translated to any of (0-63) DSCP values."
            ::= { ctcDscpTranslationEntry 2 }

        -- 1.3.6.1.4.1.4756.104.150.3.3.1.3    
        ctcDscpRxClassify OBJECT-TYPE
            SYNTAX      TruthValue
            MAX-ACCESS  read-write
            STATUS      current
            DESCRIPTION
                "Enable Classification at Ingress side."
            ::= { ctcDscpTranslationEntry 3 }

        -- 1.3.6.1.4.1.4756.104.150.3.3.1.4    
        ctcDscpTxRemapDP0 OBJECT-TYPE
            SYNTAX      Integer32 (0..63)
            MAX-ACCESS  read-write
            STATUS      current
            DESCRIPTION
                "Select the DSCP value from select menu to which you want to remap.
                 DSCP value ranges form 0 to 63."
            ::= { ctcDscpTranslationEntry 4 }

        -- 1.3.6.1.4.1.4756.104.150.3.3.1.5    
        ctcDscpTxRemapDP1 OBJECT-TYPE
            SYNTAX      Integer32 (0..63)
            MAX-ACCESS  read-write
            STATUS      current
            DESCRIPTION
                "Select the DSCP value from select menu to which you want to remap.
                 DSCP value ranges form 0 to 63."
            ::= { ctcDscpTranslationEntry 5 }

    -- 1.3.6.1.4.1.4756.104.150.3.4
    ctcDscpClassificationTable OBJECT-TYPE
        SYNTAX      SEQUENCE OF CtcDscpClassificationEntry
        MAX-ACCESS  not-accessible
        STATUS      current
        DESCRIPTION
            "This table allows you to map DSCP value to a QoS Class and DPL value."
        ::= { ctcQosDSCP 4 }

    -- 1.3.6.1.4.1.4756.104.150.3.4.1
    ctcDscpClassificationEntry OBJECT-TYPE
        SYNTAX      CtcDscpClassificationEntry
        MAX-ACCESS  not-accessible
        STATUS      current
        DESCRIPTION
            "The entry of QoS Class and DPL value."
        INDEX { ctcMapedQosClass, ctcMapedDPL }
        ::= { ctcDscpClassificationTable 1 }

    CtcDscpClassificationEntry ::=
        SEQUENCE {
            ctcMapedQosClass     Integer32,
            ctcMapedDPL          Integer32,
            ctcClassifyDSCP      Integer32           
        }

        -- 1.3.6.1.4.1.4756.104.150.3.4.1.1    
        ctcMapedQosClass OBJECT-TYPE
            SYNTAX      Integer32 (0..7)
            MAX-ACCESS  read-only
            STATUS      current
            DESCRIPTION
                "Available QoS Class value ranges from 0 to 7."
            ::= { ctcDscpClassificationEntry 1 }

        -- 1.3.6.1.4.1.4756.104.150.3.4.1.2    
        ctcMapedDPL OBJECT-TYPE
            SYNTAX      Integer32 (0..1)
            MAX-ACCESS  read-only
            STATUS      current
            DESCRIPTION
                "Drop Precedence Level (0-1) can be configured for all available QoS Classes."
            ::= { ctcDscpClassificationEntry 2 }

        -- 1.3.6.1.4.1.4756.104.150.3.4.1.3    
        ctcClassifyDSCP OBJECT-TYPE
            SYNTAX      Integer32 (0..63)
            MAX-ACCESS  read-write
            STATUS      current
            DESCRIPTION
                "Select DSCP value (0-63) to map DSCP to corresponding QoS Class and DPL value."
            ::= { ctcDscpClassificationEntry 3 }


    -- 1.3.6.1.4.1.4756.104.150.4
    ctcQosControlList  OBJECT IDENTIFIER ::= { ctcQoS 4 }

    -- 1.3.6.1.4.1.4756.104.150.4.1
    ctcInsertQCE OBJECT-TYPE
        SYNTAX      Integer32 (0 | 1..256)
        MAX-ACCESS  read-write
        STATUS      current
        DESCRIPTION                                  
            "Inserts a new QCE to list.
             Value 0: Add QCE to end of list.
             Value 1 ~ 256: Insert new QCE before this QCE ID."
        ::= { ctcQosControlList 1 }

    -- 1.3.6.1.4.1.4756.104.150.4.2
    ctcDeleteQCE OBJECT-TYPE
        SYNTAX      Integer32 (1..256)
        MAX-ACCESS  read-write
        STATUS      current
        DESCRIPTION
            "Deletes the QCE by ID. "
        ::= { ctcQosControlList 2 }

    -- 1.3.6.1.4.1.4756.104.150.4.3
    ctcMoveQceDown OBJECT-TYPE
        SYNTAX      Integer32 (1..256)
        MAX-ACCESS  read-write
        STATUS      current
        DESCRIPTION
            "Moves the QCE down the list."
        ::= { ctcQosControlList 3 }

    -- 1.3.6.1.4.1.4756.104.150.4.4
    ctcQceConfigTable OBJECT-TYPE
        SYNTAX      SEQUENCE OF CtcQceConfigEntry
        MAX-ACCESS  not-accessible
        STATUS      current
        DESCRIPTION
            "This table allows to edit QoS Control Entry.
             An QCE consists of several parameters.
             These parameters vary according to the frame type that you select."
        ::= { ctcQosControlList 4 }

    -- 1.3.6.1.4.1.4756.104.150.4.4.1
    ctcQceConfigEntry OBJECT-TYPE
        SYNTAX      CtcQceConfigEntry
        MAX-ACCESS  not-accessible
        STATUS      current
        DESCRIPTION
            "The entry of QoS Control List."
        INDEX { ctcQceID }
        ::= { ctcQceConfigTable 1 }

    CtcQceConfigEntry ::=
        SEQUENCE {
            ctcQceID                         Integer32,
            ctcQcePortMembers                DisplayString,
            ctcQceKeyTagType                 INTEGER,
            ctcQceKeyVidMode                 INTEGER,
            ctcQceKeyVidSpecific             Integer32,
            ctcQceKeyVidStart                Integer32,
            ctcQceKeyVidLast                 Integer32,
            ctcQceKeyPCP                     INTEGER,
            ctcQceKeyDEI                     INTEGER,
            ctcQceKeySMacMode                INTEGER,        -- row 10
            ctcQceKeySMacSpecific            DisplayString,
            ctcQceKeyDMacType                INTEGER,
            ctcQceKeyFrameType               INTEGER,
            ctcQceKeyFrameEtherTypeMode      INTEGER,
            ctcQceKeyFrameEtherTypeSpecific  DisplayString,
            ctcQceKeyFrameLlcSSapMode        INTEGER,
            ctcQceKeyFrameLlcSSapAddress     DisplayString,
            ctcQceKeyFrameLlcDSapMode        INTEGER,
            ctcQceKeyFrameLlcDSapAddress     DisplayString,
            ctcQceKeyFrameLlcControlMode     INTEGER,        -- row 20
            ctcQceKeyFrameLlcControl         DisplayString,
            ctcQceKeyFrameSnapPidMode        INTEGER,
            ctcQceKeyFrameSnapPidSpecific    DisplayString,
            ctcQceKeyFrameIPv4Protocol       INTEGER,
            ctcQceKeyFrameIPv4SportMode      INTEGER,
            ctcQceKeyFrameIPv4SportSpecific  Integer32,
            ctcQceKeyFrameIPv4SportStart     Integer32,
            ctcQceKeyFrameIPv4SportLast      Integer32,
            ctcQceKeyFrameIPv4DportMode      INTEGER,
            ctcQceKeyFrameIPv4DportSpecific  Integer32,      -- row 30
            ctcQceKeyFrameIPv4DportStart     Integer32,
            ctcQceKeyFrameIPv4DportLast      Integer32,
            ctcQceKeyFrameIPv4OtherValue     Integer32,
            ctcQceKeyFrameIPv4SourceIpMode   INTEGER,
            ctcQceKeyFrameIPv4SourceIP       IpAddress,
            ctcQceKeyFrameIPv4SourceIpMask   IpAddress,
            ctcQceKeyFrameIPv4FragmentOption INTEGER,
            ctcQceKeyFrameIPv4DscpMode       INTEGER, 
            ctcQceKeyFrameIPv4DscpSpecific   Integer32,
            ctcQceKeyFrameIPv4DscpStart      Integer32,      -- row 40
            ctcQceKeyFrameIPv4DscpLast       Integer32,
            ctcQceKeyFrameIPv6Protocol       INTEGER,
            ctcQceKeyFrameIPv6SportMode      INTEGER,
            ctcQceKeyFrameIPv6SportSpecific  Integer32,
            ctcQceKeyFrameIPv6SportStart     Integer32,
            ctcQceKeyFrameIPv6SportLast      Integer32,
            ctcQceKeyFrameIPv6DportMode      INTEGER,
            ctcQceKeyFrameIPv6DportSpecific  Integer32,
            ctcQceKeyFrameIPv6DportStart     Integer32,
            ctcQceKeyFrameIPv6DportLast      Integer32,      -- row 50
            ctcQceKeyFrameIPv6OtherValue     Integer32,
            ctcQceKeyFrameIPv6SourceIpMode   INTEGER,
            ctcQceKeyFrameIPv6SourceIP       IpAddress,
            ctcQceKeyFrameIPv6SourceIpMask   IpAddress,
            ctcQceKeyFrameIPv6DscpMode       INTEGER, 
            ctcQceKeyFrameIPv6DscpSpecific   Integer32,
            ctcQceKeyFrameIPv6DscpStart      Integer32,
            ctcQceKeyFrameIPv6DscpLast       Integer32,
            ctcQceActionClass                Integer32,
            ctcQceActionDPL                  Integer32,      -- row 60
            ctcQceActionDSCP                 Integer32    
        }

        -- 1.3.6.1.4.1.4756.104.150.4.4.1.1    
        ctcQceID OBJECT-TYPE
            SYNTAX      Integer32 (1..256)
            MAX-ACCESS  read-only
            STATUS      current
            DESCRIPTION
                "Indicates the ID of QCE entry."
            ::= { ctcQceConfigEntry 1 }

        -- 1.3.6.1.4.1.4756.104.150.4.4.1.2    
        ctcQcePortMembers OBJECT-TYPE
            SYNTAX      DisplayString
            MAX-ACCESS  read-write
            STATUS      current                          
            DESCRIPTION
                "Indicates the port member of the QCL entry. By default all ports will be member."
            ::= { ctcQceConfigEntry 2 }

        -- 1.3.6.1.4.1.4756.104.150.4.4.1.3    
        ctcQceKeyTagType OBJECT-TYPE
            SYNTAX      INTEGER {
                            any(1),
                            untag(2),
                            tag(3)
                        }
            MAX-ACCESS  read-write
            STATUS      current                          
            DESCRIPTION
                "Tag Type can be 'Any', 'Untag' or 'Tag'."
            ::= { ctcQceConfigEntry 3 }

        -- 1.3.6.1.4.1.4756.104.150.4.4.1.4    
        ctcQceKeyVidMode OBJECT-TYPE
            SYNTAX      INTEGER {
                            any(1),
                            specific(2),
                            range(3)
                        }
            MAX-ACCESS  read-write
            STATUS      current                          
            DESCRIPTION
                "VID Mode can be 'Any', 'Specific' or 'Range'."
            ::= { ctcQceConfigEntry 4 }

        -- 1.3.6.1.4.1.4756.104.150.4.4.1.5    
        ctcQceKeyVidSpecific OBJECT-TYPE
            SYNTAX      Integer32 (1..4095)
            MAX-ACCESS  read-write
            STATUS      current                          
            DESCRIPTION
                "VLAN ID can be any value in the range 1-4095 when Key VID Mode is 'Specific'."
            ::= { ctcQceConfigEntry 5 }

        -- 1.3.6.1.4.1.4756.104.150.4.4.1.6    
        ctcQceKeyVidStart OBJECT-TYPE
            SYNTAX      Integer32 (1..4094)
            MAX-ACCESS  read-write
            STATUS      current                          
            DESCRIPTION
                "The starting VID of range if Key VID Mode is 'Range'."
            ::= { ctcQceConfigEntry 6 }

        -- 1.3.6.1.4.1.4756.104.150.4.4.1.7    
        ctcQceKeyVidLast OBJECT-TYPE
            SYNTAX      Integer32 (2..4095)
            MAX-ACCESS  read-write
            STATUS      current                          
            DESCRIPTION
                "The last VID of range if Key VID Mode is 'Range'."
            ::= { ctcQceConfigEntry 7 }

        -- 1.3.6.1.4.1.4756.104.150.4.4.1.8    
        ctcQceKeyPCP OBJECT-TYPE
            SYNTAX      INTEGER {
                            any(1),
                            specific0(2),
                            specific1(3),
                            specific2(4),
                            specific3(5),
                            specific4(6),
                            specific5(7),
                            specific6(8),
                            specific7(9),
                            range0To1(10),
                            range2To3(11),
                            range4To5(12),
                            range6To7(13),
                            range0To3(14),
                            range4To7(15)
                        }   
            MAX-ACCESS  read-write
            STATUS      current                          
            DESCRIPTION
                "Priority Code Point: Valid value PCP are specific(0, 1, 2, 3, 4, 5, 6, 7) or
                 range(0-1, 2-3, 4-5, 6-7, 0-3, 4-7) or 'Any'."
            ::= { ctcQceConfigEntry 8 }

        -- 1.3.6.1.4.1.4756.104.150.4.4.1.9    
        ctcQceKeyDEI OBJECT-TYPE
            SYNTAX      INTEGER {
                            any(1),
                            specific0(2),
                            specific1(3)
                        }   
            MAX-ACCESS  read-write
            STATUS      current                          
            DESCRIPTION
                "Drop Eligible Indicator: Valid value of DEI can be any of values between 0, 1 or 'Any'."
            ::= { ctcQceConfigEntry 9 }

        -- 1.3.6.1.4.1.4756.104.150.4.4.1.10    
        ctcQceKeySMacMode OBJECT-TYPE
            SYNTAX      INTEGER {
                            any(1),
                            specific(2)
                        }   
            MAX-ACCESS  read-write
            STATUS      current                          
            DESCRIPTION
                "Source MAC address Mode: Valid value can be 'Any' or 'Specific'."
            ::= { ctcQceConfigEntry 10 }

        -- 1.3.6.1.4.1.4756.104.150.4.4.1.11    
        ctcQceKeySMacSpecific OBJECT-TYPE
            SYNTAX      DisplayString   
            MAX-ACCESS  read-write
            STATUS      current                          
            DESCRIPTION
                "Source MAC address: 24 MS bits (OUI)."
            ::= { ctcQceConfigEntry 11 }

        -- 1.3.6.1.4.1.4756.104.150.4.4.1.12    
        ctcQceKeyDMacType OBJECT-TYPE
            SYNTAX      INTEGER {
                            any(1),
                            unicast(2),
                            multicast(3),
                            broadcast(4)
                        }   
            MAX-ACCESS  read-write
            STATUS      current                          
            DESCRIPTION
                "Destination MAC type: possible values are
                 'Unicast', 'Multicast', 'Broadcast' or 'Any'."
            ::= { ctcQceConfigEntry 12 }

        -- 1.3.6.1.4.1.4756.104.150.4.4.1.13    
        ctcQceKeyFrameType OBJECT-TYPE
            SYNTAX      INTEGER {
                            any(1),
                            ethernet(2),
                            llc(3),
                            snap(4),
                            ipv4(5),
                            ipv6(6)
                        }   
            MAX-ACCESS  read-write
            STATUS      current                          
            DESCRIPTION
                "Frame Type can have any of the following values:
                 Any, Ethernet, LLC, SNAP, IPv4 or IPv6"
            ::= { ctcQceConfigEntry 13 }

        -- 1.3.6.1.4.1.4756.104.150.4.4.1.14    
        ctcQceKeyFrameEtherTypeMode OBJECT-TYPE
            SYNTAX      INTEGER {
                            any(1),
                            specific(2)
                        }   
            MAX-ACCESS  read-write
            STATUS      current                          
            DESCRIPTION
                "If Key Frame Type is 'Ethernet', The Ether Type can be configured here.
                 Valid value can be 'Any' or 'Specific'.
                 The default value is 'Any'."
            DEFVAL     { any }     
            ::= { ctcQceConfigEntry 14 }

        -- 1.3.6.1.4.1.4756.104.150.4.4.1.15    
        ctcQceKeyFrameEtherTypeSpecific OBJECT-TYPE
            SYNTAX      DisplayString   
            MAX-ACCESS  read-write
            STATUS      current                          
            DESCRIPTION
                "If Key Frame Type is 'Ethernet', The Ether Type value can be configured here.
                 Valid ethernet type can have value within 0x600-0xFFFF,
                 but excluding 0x800(IPv4) and 0x86DD(IPv6)."
            ::= { ctcQceConfigEntry 15 }

        -- 1.3.6.1.4.1.4756.104.150.4.4.1.16    
        ctcQceKeyFrameLlcSSapMode OBJECT-TYPE
            SYNTAX      INTEGER {
                            any(1),
                            specific(2)
                        }   
            MAX-ACCESS  read-write
            STATUS      current                          
            DESCRIPTION
                "If Key Frame Type is 'LLC', The SSAP Address Mode can be configured here.
                 Valid value can be 'Any' or 'Specific'.
                 the default value is 'Any'."
            DEFVAL     { any }     
            ::= { ctcQceConfigEntry 16 }

        -- 1.3.6.1.4.1.4756.104.150.4.4.1.17    
        ctcQceKeyFrameLlcSSapAddress OBJECT-TYPE
            SYNTAX      DisplayString   
            MAX-ACCESS  read-write
            STATUS      current                          
            DESCRIPTION
                "If Key Frame Type is 'LLC', The SSAP Address can be configured here.
                 Valid SSAP(Source Service Access Point) can vary from 0x00 to 0xFF"
            ::= { ctcQceConfigEntry 17 }

        -- 1.3.6.1.4.1.4756.104.150.4.4.1.18    
        ctcQceKeyFrameLlcDSapMode OBJECT-TYPE
            SYNTAX      INTEGER {
                            any(1),
                            specific(2)
                        }   
            MAX-ACCESS  read-write
            STATUS      current                          
            DESCRIPTION
                "If Key Frame Type is 'LLC', The DSAP Address Mode can be configured here.
                 Valid value can be 'Any' or 'Specific'.
                 the default value is 'Any'."
            DEFVAL     { any }     
            ::= { ctcQceConfigEntry 18 }

        -- 1.3.6.1.4.1.4756.104.150.4.4.1.19    
        ctcQceKeyFrameLlcDSapAddress OBJECT-TYPE
            SYNTAX      DisplayString   
            MAX-ACCESS  read-write
            STATUS      current                          
            DESCRIPTION
                "If Key Frame Type is 'LLC', The DSAP Address can be configured here.
                 Valid DSAP(Destination  Service Access Point) can vary from 0x00 to 0xFF."
            ::= { ctcQceConfigEntry 19 }

        -- 1.3.6.1.4.1.4756.104.150.4.4.1.20    
        ctcQceKeyFrameLlcControlMode OBJECT-TYPE
            SYNTAX      INTEGER {
                            any(1),
                            specific(2)
                        }   
            MAX-ACCESS  read-write
            STATUS      current                          
            DESCRIPTION
                "If Key Frame Type is 'LLC', The Control Mode can be configured here.
                 Valid value can be 'Any' or 'Specific'.
                 the default value is 'Any'."
            DEFVAL     { any }     
            ::= { ctcQceConfigEntry 20 }

        -- 1.3.6.1.4.1.4756.104.150.4.4.1.21    
        ctcQceKeyFrameLlcControl OBJECT-TYPE
            SYNTAX      DisplayString   
            MAX-ACCESS  read-write
            STATUS      current                          
            DESCRIPTION
                "If Key Frame Type is 'LLC', The Control Address can be configured here.
                 Valid Control Address can vary from 0x00 to 0xFF."
            ::= { ctcQceConfigEntry 21 }

        -- 1.3.6.1.4.1.4756.104.150.4.4.1.22    
        ctcQceKeyFrameSnapPidMode OBJECT-TYPE
            SYNTAX      INTEGER {
                            any(1),
                            specific(2)
                        }   
            MAX-ACCESS  read-write
            STATUS      current                          
            DESCRIPTION
                "If Key Frame Type is 'SNAP', The SNAP PID Mode can be configured here.
                 Valid value can be 'Any' or 'Specific'.
                 The default value is 'Any'."
            DEFVAL     { any }     
            ::= { ctcQceConfigEntry 22 }

        -- 1.3.6.1.4.1.4756.104.150.4.4.1.23    
        ctcQceKeyFrameSnapPidSpecific OBJECT-TYPE
            SYNTAX      DisplayString   
            MAX-ACCESS  read-write
            STATUS      current                          
            DESCRIPTION
                "If Key Frame Type is 'SNAP', The PID can be configured here.
                 Valid PID(a.k.a ethernet type) can have value within 0x00-0xFFFF"
            ::= { ctcQceConfigEntry 23 }

        -- 1.3.6.1.4.1.4756.104.150.4.4.1.24    
        ctcQceKeyFrameIPv4Protocol OBJECT-TYPE
            SYNTAX      INTEGER {
                            any(1),
                            udp(2),
                            tcp(3),
                            other(4)
                        }   
            MAX-ACCESS  read-write
            STATUS      current                          
            DESCRIPTION
                "If Key Frame Type is 'IPv4', The Protocol Number can be configured here.
                 IP protocol number can be 'Other'(0-255), 'TCP', 'UDP' or 'Any',
                 the default value is 'Any'"
            DEFVAL     { any }     
            ::= { ctcQceConfigEntry 24 }

        -- 1.3.6.1.4.1.4756.104.150.4.4.1.25    
        ctcQceKeyFrameIPv4SportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Source TCP/UDP port mode can be configured here.
                 Source TCP/UDP port Mode can be 'Any', 'Specific' or 'Range',
                 the default value is 'Any'"
            DEFVAL     { any }     
            ::= { ctcQceConfigEntry 25 }

        -- 1.3.6.1.4.1.4756.104.150.4.4.1.26    
        ctcQceKeyFrameIPv4SportSpecific OBJECT-TYPE
            SYNTAX      Integer32 (0..65535)
            MAX-ACCESS  read-write
            STATUS      current                          
            DESCRIPTION
                "If Key Frame Type is 'IPv4' and Protocol is either TCP or UDP,
                 the Source TCP/UDP port number can be configured here.
                 The Source TCP/UDP port number can be any value in the range 0-65535
                 when Source TCP/UDP port Mode is 'Specific'."
            ::= { ctcQceConfigEntry 26 }

        -- 1.3.6.1.4.1.4756.104.150.4.4.1.27    
        ctcQceKeyFrameIPv4SportStart OBJECT-TYPE
            SYNTAX      Integer32 (0..65534)
            MAX-ACCESS  read-write
            STATUS      current                          
            DESCRIPTION
                "If Key Frame Type is 'IPv4' and Protocol is either TCP or UDP,
                 the starting Source TCP/UDP port number of range can be configured here.
                 It is effectively when Source TCP/UDP port Mode is 'Range'."
            ::= { ctcQceConfigEntry 27 }

        -- 1.3.6.1.4.1.4756.104.150.4.4.1.28    
        ctcQceKeyFrameIPv4SportLast OBJECT-TYPE
            SYNTAX      Integer32 (1..65535)
            MAX-ACCESS  read-write
            STATUS      current                          
            DESCRIPTION
                "If Key Frame Type is 'IPv4' and Protocol is either TCP or UDP,
                 the last Source TCP/UDP port number of range can be configured here.
                 It is effectively when Source TCP/UDP port Mode is 'Range'."
            ::= { ctcQceConfigEntry 28 }

        -- 1.3.6.1.4.1.4756.104.150.4.4.1.29    
        ctcQceKeyFrameIPv4DportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Destination TCP/UDP port mode can be configured here.
                 Destination TCP/UDP port Mode can be 'Any', 'Specific' or 'Range',
                 the default value is 'Any'"
            DEFVAL     { any }     
            ::= { ctcQceConfigEntry 29 }

        -- 1.3.6.1.4.1.4756.104.150.4.4.1.30    
        ctcQceKeyFrameIPv4DportSpecific OBJECT-TYPE
            SYNTAX      Integer32 (0..65535)
            MAX-ACCESS  read-write
            STATUS      current                          
            DESCRIPTION
                "If Key Frame Type is 'IPv4' and Protocol is either TCP or UDP,
                 the Destination TCP/UDP port number can be configured here.
                 The Destination TCP/UDP port number can be any value in the range 0-65535
                 when Destination TCP/UDP port Mode is 'Specific'."
            ::= { ctcQceConfigEntry 30 }

        -- 1.3.6.1.4.1.4756.104.150.4.4.1.31    
        ctcQceKeyFrameIPv4DportStart OBJECT-TYPE
            SYNTAX      Integer32 (0..65534)
            MAX-ACCESS  read-write
            STATUS      current                          
            DESCRIPTION
                "If Key Frame Type is 'IPv4' and Protocol is either TCP or UDP,
                 the starting Destination TCP/UDP port number of range can be configured here.
                 It is effectively when Destination TCP/UDP port Mode is 'Range'."
            ::= { ctcQceConfigEntry 31 }

        -- 1.3.6.1.4.1.4756.104.150.4.4.1.32    
        ctcQceKeyFrameIPv4DportLast OBJECT-TYPE
            SYNTAX      Integer32 (1..65535)
            MAX-ACCESS  read-write
            STATUS      current                          
            DESCRIPTION
                "If Key Frame Type is 'IPv4' and Protocol is either TCP or UDP,
                 the last Destination TCP/UDP port number of range can be configured here.
                 It is effectively when Destination TCP/UDP port Mode is 'Range'."
            ::= { ctcQceConfigEntry 32 }

        -- 1.3.6.1.4.1.4756.104.150.4.4.1.33    
        ctcQceKeyFrameIPv4OtherValue OBJECT-TYPE
            SYNTAX      Integer32 (0..255)
            MAX-ACCESS  read-write
            STATUS      current                          
            DESCRIPTION
                "The other IPv4 protocol numbercan be any value in the range 0-255
                 when IP Protocol is 'Other'."
            ::= { ctcQceConfigEntry 33 }

        -- 1.3.6.1.4.1.4756.104.150.4.4.1.34    
        ctcQceKeyFrameIPv4SourceIpMode OBJECT-TYPE
            SYNTAX      INTEGER {
                            any(1),
                            specific(2)
                        }
            MAX-ACCESS  read-write
            STATUS      current                          
            DESCRIPTION
                "IPv4 Source Address Mode can be 'Any' or 'Specific', default value is 'Any'"
            DEFVAL     { any }    
            ::= { ctcQceConfigEntry 34 }

        -- 1.3.6.1.4.1.4756.104.150.4.4.1.35    
        ctcQceKeyFrameIPv4SourceIP OBJECT-TYPE
            SYNTAX      IpAddress
            MAX-ACCESS  read-write
            STATUS      current                          
            DESCRIPTION
                "When IPv4 Source Address Mode is 'Specific',
                 The Source IP address can be configured here.
                 Source IP address is in the format x.y.z.w where x, y, z, and w
                 are decimal numbers between 0 and 255."
            ::= { ctcQceConfigEntry 35 }

        -- 1.3.6.1.4.1.4756.104.150.4.4.1.36    
        ctcQceKeyFrameIPv4SourceIpMask OBJECT-TYPE
            SYNTAX      IpAddress
            MAX-ACCESS  read-write
            STATUS      current                          
            DESCRIPTION
                "When IPv4 Source Address Mode is 'Specific',
                 The Source IP Address Mask can be configured here.
                 Mask is in the format x.y.z.w where x, y, z, and w are decimal numbers between 0 and 255.
                 When Mask is converted to a 32-bit binary string and read from left to right,
                 all bits following the first zero must also be zero."
            ::= { ctcQceConfigEntry 36 }

        -- 1.3.6.1.4.1.4756.104.150.4.4.1.37    
        ctcQceKeyFrameIPv4FragmentOption OBJECT-TYPE
            SYNTAX      INTEGER {
                            any(1),
                            yes(2),
                            no(3)
                        }
            MAX-ACCESS  read-write
            STATUS      current                          
            DESCRIPTION
                "IPv4 frame fragmented option can be 'Yes', 'No' or 'Any', default value is 'Any'"
            DEFVAL     { any }    
            ::= { ctcQceConfigEntry 37 }

        -- 1.3.6.1.4.1.4756.104.150.4.4.1.38    
        ctcQceKeyFrameIPv4DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { ctcQceConfigEntry 38 }

        -- 1.3.6.1.4.1.4756.104.150.4.4.1.39    
        ctcQceKeyFrameIPv4DscpSpecific OBJECT-TYPE
            SYNTAX      Integer32 (0..63)
            MAX-ACCESS  read-write
            STATUS      current                          
            DESCRIPTION
                "The DSCP can be any value in the range 0-63 when DSCP Mode is 'Specific'."
            ::= { ctcQceConfigEntry 39 }

        -- 1.3.6.1.4.1.4756.104.150.4.4.1.40    
        ctcQceKeyFrameIPv4DscpStart OBJECT-TYPE
            SYNTAX      Integer32 (0..62)
            MAX-ACCESS  read-write
            STATUS      current                          
            DESCRIPTION
                "The starting DSCP value of range,
                 it is effectively when IPv4 DSCP Mode is 'Range'."
            ::= { ctcQceConfigEntry 40 }

        -- 1.3.6.1.4.1.4756.104.150.4.4.1.41    
        ctcQceKeyFrameIPv4DscpLast OBJECT-TYPE
            SYNTAX      Integer32 (1..63)
            MAX-ACCESS  read-write
            STATUS      current                          
            DESCRIPTION
                "The last DSCP value of range,
                 it is effectively when IPv4 DSCP Mode is 'Range'."
            ::= { ctcQceConfigEntry 41 }

        -- 1.3.6.1.4.1.4756.104.150.4.4.1.42    
        ctcQceKeyFrameIPv6Protocol OBJECT-TYPE
            SYNTAX      INTEGER {
                            any(1),
                            udp(2),
                            tcp(3),
                            other(4)
                        }   
            MAX-ACCESS  read-write
            STATUS      current                          
            DESCRIPTION
                "If Key Frame Type is 'IPv6', The Protocol Number can be configured here.
                 IPv6 protocol number can be 'Other'(0-255), 'TCP', 'UDP' or 'Any',
                 the default value is 'Any'"
            DEFVAL     { any }     
            ::= { ctcQceConfigEntry 42 }

        -- 1.3.6.1.4.1.4756.104.150.4.4.1.43    
        ctcQceKeyFrameIPv6SportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Source TCP/UDP port mode can be configured here.
                 Source TCP/UDP port Mode can be 'Any', 'Specific' or 'Range',
                 the default value is 'Any'"
            DEFVAL     { any }     
            ::= { ctcQceConfigEntry 43 }

        -- 1.3.6.1.4.1.4756.104.150.4.4.1.44    
        ctcQceKeyFrameIPv6SportSpecific OBJECT-TYPE
            SYNTAX      Integer32 (0..65535)
            MAX-ACCESS  read-write
            STATUS      current                          
            DESCRIPTION
                "If Key Frame Type is 'IPv6' and Protocol is either TCP or UDP,
                 the Source TCP/UDP port number can be configured here.
                 The Source TCP/UDP port number can be any value in the range 0-65535
                 when Source TCP/UDP port Mode is 'Specific'."
            ::= { ctcQceConfigEntry 44 }

        -- 1.3.6.1.4.1.4756.104.150.4.4.1.45    
        ctcQceKeyFrameIPv6SportStart OBJECT-TYPE
            SYNTAX      Integer32 (0..65534)
            MAX-ACCESS  read-write
            STATUS      current                          
            DESCRIPTION
                "If Key Frame Type is 'IPv6' and Protocol is either TCP or UDP,
                 the starting Source TCP/UDP port number of range can be configured here.
                 It is effectively when Source TCP/UDP port Mode is 'Range'."
            ::= { ctcQceConfigEntry 45 }

        -- 1.3.6.1.4.1.4756.104.150.4.4.1.46    
        ctcQceKeyFrameIPv6SportLast OBJECT-TYPE
            SYNTAX      Integer32 (1..65535)
            MAX-ACCESS  read-write
            STATUS      current                          
            DESCRIPTION
                "If Key Frame Type is 'IPv6' and Protocol is either TCP or UDP,
                 the last Source TCP/UDP port number of range can be configured here.
                 It is effectively when Source TCP/UDP port Mode is 'Range'."
            ::= { ctcQceConfigEntry 46 }

        -- 1.3.6.1.4.1.4756.104.150.4.4.1.47    
        ctcQceKeyFrameIPv6DportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Destination TCP/UDP port mode can be configured here.
                 Destination TCP/UDP port Mode can be 'Any', 'Specific' or 'Range',
                 the default value is 'Any'"
            DEFVAL     { any }     
            ::= { ctcQceConfigEntry 47 }

        -- 1.3.6.1.4.1.4756.104.150.4.4.1.48    
        ctcQceKeyFrameIPv6DportSpecific OBJECT-TYPE
            SYNTAX      Integer32 (0..65535)
            MAX-ACCESS  read-write
            STATUS      current                          
            DESCRIPTION
                "If Key Frame Type is 'IPv6' and Protocol is either TCP or UDP,
                 the Destination TCP/UDP port number can be configured here.
                 The Destination TCP/UDP port number can be any value in the range 0-65535
                 when Destination TCP/UDP port Mode is 'Specific'."
            ::= { ctcQceConfigEntry 48 }

        -- 1.3.6.1.4.1.4756.104.150.4.4.1.49    
        ctcQceKeyFrameIPv6DportStart OBJECT-TYPE
            SYNTAX      Integer32 (0..65534)
            MAX-ACCESS  read-write
            STATUS      current                          
            DESCRIPTION
                "If Key Frame Type is 'IPv6' and Protocol is either TCP or UDP,
                 the starting Destination TCP/UDP port number of range can be configured here.
                 It is effectively when Destination TCP/UDP port Mode is 'Range'."
            ::= { ctcQceConfigEntry 49 }

        -- 1.3.6.1.4.1.4756.104.150.4.4.1.50    
        ctcQceKeyFrameIPv6DportLast OBJECT-TYPE
            SYNTAX      Integer32 (1..65535)
            MAX-ACCESS  read-write
            STATUS      current                          
            DESCRIPTION
                "If Key Frame Type is 'IPv6' and Protocol is either TCP or UDP,
                 the last Destination TCP/UDP port number of range can be configured here.
                 It is effectively when Destination TCP/UDP port Mode is 'Range'."
            ::= { ctcQceConfigEntry 50 }

        -- 1.3.6.1.4.1.4756.104.150.4.4.1.51    
        ctcQceKeyFrameIPv6OtherValue OBJECT-TYPE
            SYNTAX      Integer32 (0..255)
            MAX-ACCESS  read-write
            STATUS      current                          
            DESCRIPTION
                "The other IPv6 protocol numbercan be any value in the range 0-255
                 when IP Protocol is 'Other'."
            ::= { ctcQceConfigEntry 51 }

        -- 1.3.6.1.4.1.4756.104.150.4.4.1.52    
        ctcQceKeyFrameIPv6SourceIpMode OBJECT-TYPE
            SYNTAX      INTEGER {
                            any(1),
                            specific(2)
                        }
            MAX-ACCESS  read-write
            STATUS      current                          
            DESCRIPTION
                "IPv6 Source Address Mode can be 'Any' or 'Specific', default value is 'Any'"
            DEFVAL     { any }    
            ::= { ctcQceConfigEntry 52 }

        -- 1.3.6.1.4.1.4756.104.150.4.4.1.53    
        ctcQceKeyFrameIPv6SourceIP OBJECT-TYPE
            SYNTAX      IpAddress
            MAX-ACCESS  read-write
            STATUS      current                          
            DESCRIPTION
                "When IPv6 Source Address Mode is 'Specific',
                 The Source IPv6 address(32 LS bits) can be configured here.
                 Source IPv6 address(32 LS bits) is in the format a.b.c.d."
            ::= { ctcQceConfigEntry 53 }

        -- 1.3.6.1.4.1.4756.104.150.4.4.1.54    
        ctcQceKeyFrameIPv6SourceIpMask OBJECT-TYPE
            SYNTAX      IpAddress
            MAX-ACCESS  read-write
            STATUS      current                          
            DESCRIPTION
                "When IPv6 Source Address Mode is 'Specific',
                 The Source IPv6 Address Mask(32 LS bits) can be configured here.
                 IP Mask(32 LS bits) is in the format a.b.c.d where a, b, c, and d
                 are decimal numbers between 0 and 255.
                 When Mask is converted to a 32-bit binary string and read from left to right,
                 all bits following the first zero must also be zero."
            ::= { ctcQceConfigEntry 54 }

        -- 1.3.6.1.4.1.4756.104.150.4.4.1.55    
        ctcQceKeyFrameIPv6DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { ctcQceConfigEntry 55 }

        -- 1.3.6.1.4.1.4756.104.150.4.4.1.56    
        ctcQceKeyFrameIPv6DscpSpecific OBJECT-TYPE
            SYNTAX      Integer32 (0..63)
            MAX-ACCESS  read-write
            STATUS      current                          
            DESCRIPTION
                "The DSCP can be any value in the range 0-63 when DSCP Mode is 'Specific'."
            ::= { ctcQceConfigEntry 56 }

        -- 1.3.6.1.4.1.4756.104.150.4.4.1.57    
        ctcQceKeyFrameIPv6DscpStart OBJECT-TYPE
            SYNTAX      Integer32 (0..62)
            MAX-ACCESS  read-write
            STATUS      current                          
            DESCRIPTION
                "The starting DSCP value of range,
                 it is effectively when IPv6 DSCP Mode is 'Range'."
            ::= { ctcQceConfigEntry 57 }

        -- 1.3.6.1.4.1.4756.104.150.4.4.1.58    
        ctcQceKeyFrameIPv6DscpLast OBJECT-TYPE
            SYNTAX      Integer32 (1..63)
            MAX-ACCESS  read-write
            STATUS      current                          
            DESCRIPTION
                "The last DSCP value of range,
                 it is effectively when IPv6 DSCP Mode is 'Range'."
            ::= { ctcQceConfigEntry 58 }

        -- 1.3.6.1.4.1.4756.104.150.4.4.1.59    
        ctcQceActionClass OBJECT-TYPE
            SYNTAX      Integer32 (-1 | 0..7)
            MAX-ACCESS  read-write
            STATUS      current                          
            DESCRIPTION
                "Valid QoS Class can be (0-7), the value -1 for default,
                 At least one of the Action Node(rcQceActionClass, ctcQceActionDPL and ctcQceActionDSCP)
                 must have non-default value!"
            ::= { ctcQceConfigEntry 59 }

        -- 1.3.6.1.4.1.4756.104.150.4.4.1.60    
        ctcQceActionDPL OBJECT-TYPE
            SYNTAX      Integer32 (-1 | 0..1)
            MAX-ACCESS  read-write
            STATUS      current                          
            DESCRIPTION
                "Valid DP Level can be (0-1), the value -1 for default,
                 At least one of the Action Node(rcQceActionClass, ctcQceActionDPL and ctcQceActionDSCP)
                 must have non-default value!"
            ::= { ctcQceConfigEntry 60 }

        -- 1.3.6.1.4.1.4756.104.150.4.4.1.61    
        ctcQceActionDSCP OBJECT-TYPE
            SYNTAX      Integer32 (-1 | 0..63)
            MAX-ACCESS  read-write
            STATUS      current                          
            DESCRIPTION
                "Valid DSCP value can be (0-63), the value -1 for default,
                 At least one of the Action Node(rcQceActionClass, ctcQceActionDPL and ctcQceActionDSCP)
                 must have non-default value!"
            ::= { ctcQceConfigEntry 61 }


    -- 1.3.6.1.4.1.4756.104.150.5
    ctcStormControl   OBJECT IDENTIFIER ::= { ctcQoS 5 }

    -- 1.3.6.1.4.1.4756.104.150.5.1
    ctcStormControlTable OBJECT-TYPE
        SYNTAX      SEQUENCE OF CtcStormControlEntry
        MAX-ACCESS  not-accessible
        STATUS      current
        DESCRIPTION
            "Storm control for the switch is configured on this table.
             There is a unicast storm rate control, multicast storm rate control,
             and a broadcast storm rate control. These only affect flooded frames,
             i.e. frames with a (VLAN ID, DMAC) pair not present on the MAC Address table.
             The configuration indicates the permitted packet rate for unicast, multicast or
             broadcast traffic across the switch."
        ::= { ctcStormControl 1 }

    -- 1.3.6.1.4.1.4756.104.150.5.1.1
    ctcStormControlEntry OBJECT-TYPE
        SYNTAX      CtcStormControlEntry
        MAX-ACCESS  not-accessible
        STATUS      current
        DESCRIPTION
            "The entry of frame type."
        INDEX { ctcStormControlFrameType }
        ::= { ctcStormControlTable 1 }

    CtcStormControlEntry ::=
        SEQUENCE {
            ctcStormControlFrameType     INTEGER,
            ctcStormControlEnabled       TruthValue,
            ctcStormControlRate          INTEGER           
        }

        -- 1.3.6.1.4.1.4756.104.150.5.1.1.1    
        ctcStormControlFrameType OBJECT-TYPE
            SYNTAX      INTEGER {
                            unicast(1),
                            multicast(2),
                            broadcast(3)
                        }
            MAX-ACCESS  read-only
            STATUS      current
            DESCRIPTION
                "The settings in a particular row apply to the frame type listed here:
                 Unicast, Multicast or Broadcast."
            ::= { ctcStormControlEntry 1 }

        -- 1.3.6.1.4.1.4756.104.150.5.1.1.2    
        ctcStormControlEnabled OBJECT-TYPE
            SYNTAX      TruthValue
            MAX-ACCESS  read-write
            STATUS      current
            DESCRIPTION
                "Enable or disable the storm control status for the given frame type."
            ::= { ctcStormControlEntry 2 }

        -- 1.3.6.1.4.1.4756.104.150.5.1.1.3    
        ctcStormControlRate OBJECT-TYPE
            SYNTAX      INTEGER {
                            rate1(1),
                            rate2(2),
                            rate4(3),
                            rate8(4),
                            rate16(5),
                            rate32(6),
                            rate64(7),
                            rate128(8),
                            rate256(9),
                            rate512(10),
                            rate1k(11),
                            rate2k(12),
                            rate4k(13),
                            rate8k(14),
                            rate16k(15),
                            rate32k(16),
                            rate64k(17),
                            rate128k(18),
                            rate256k(19),
                            rate512k(20),
                            rate1024k(21),
                            rate2048k(22),
                            rate4096k(23),
                            rate8192k(24),
                            rate16384k(25),
                            rate32768k(26)
                        }
            UNITS       "pps"
            MAX-ACCESS  read-write
            STATUS      current
            DESCRIPTION
                "The rate unit is packets per second (pps).
                 Valid values are: 1, 2, 4, 8, 16, 32, 64, 128, 256, 512,
                 1K, 2K, 4K, 8K, 16K, 32K, 64K, 128K, 256K, 512K ,
                 1024K, 2048K, 4096K, 8192K, 16384K or 32768K. "
            ::= { ctcStormControlEntry 3 }


-- Mirroring
    -- 1.3.6.1.4.1.4756.104.160
    ctcMirror  OBJECT IDENTIFIER ::= { gsw2008ms 160 }

    -- 1.3.6.1.4.1.4756.104.160.1
    ctcPortToMirrorOn OBJECT-TYPE
        SYNTAX      Integer32 (0..6)
        MAX-ACCESS  read-write
        STATUS      current
        DESCRIPTION
            "Port to mirror also known as the mirror port.
             Frames from ports that have either source(rx) or destination(tx)
             mirroring enabled are mirrored on this port.
             Sets zero to disables mirroring."
        ::= { ctcMirror 1 }

    -- 1.3.6.1.4.1.4756.104.160.2
    ctcPortMirrorTable OBJECT-TYPE
        SYNTAX      SEQUENCE OF CtcPortMirrorEntry
        MAX-ACCESS  not-accessible
        STATUS      current
        DESCRIPTION
            "This table is used for Rx and Tx enabling."
        ::= { ctcMirror 2 }

    -- 1.3.6.1.4.1.4756.104.160.2.1
    ctcPortMirrorEntry OBJECT-TYPE
        SYNTAX      CtcPortMirrorEntry
        MAX-ACCESS  not-accessible
        STATUS      current
        DESCRIPTION
            "The Entry of mirroring ports."
        INDEX { ctcPortIndex }
        ::= { ctcPortMirrorTable 1 }

    CtcPortMirrorEntry ::=
        SEQUENCE {
            ctcPortMirrorMode          INTEGER
        }

        -- 1.3.6.1.4.1.4756.104.160.2.1.1    
        ctcPortMirrorMode OBJECT-TYPE
            SYNTAX      INTEGER {
                            disabled(1),
                            enabled(2),
                            rxOnly(3),
                            txOnly(4)
                        }
            MAX-ACCESS  read-write
            STATUS      current
            DESCRIPTION
                "Select mirror mode.
                 Rx only: Frames received on this port are mirrored on the mirror port.
                          Frames transmitted are not mirrored.
                 Tx only: Frames transmitted on this port are mirrored on the mirror port.
                          Frames received are not mirrored.
                 Disabled: Neither frames transmitted nor frames received are mirrored.
                 Enabled: Frames received and frames transmitted are mirrored on the mirror port. 
                 Note: For a given port, a frame is only transmitted once.
                 It is therefore not possible to mirror Tx frames on the mirror port.
                 Because of this, mode for the selected mirror port is limited to Disabled or Rx only."
            ::= { ctcPortMirrorEntry 1 }

    -- 1.3.6.1.4.1.4756.104.160.3    
    ctcPortMirrorCpuPortMode OBJECT-TYPE
        SYNTAX      INTEGER {
                        disabled(1),
                        enabled(2),
                        rxOnly(3),
                        txOnly(4)
                    }
        MAX-ACCESS  read-write
        STATUS      current
        DESCRIPTION
            "Select mirror mode of CPU port.
             Rx only: Frames received on this port are mirrored on the mirror port.
                      Frames transmitted are not mirrored.
             Tx only: Frames transmitted on this port are mirrored on the mirror port.
                      Frames received are not mirrored.
             Disabled: Neither frames transmitted nor frames received are mirrored.
             Enabled: Frames received and frames transmitted are mirrored on the mirror port. 
             Note: For a given port, a frame is only transmitted once.
             It is therefore not possible to mirror Tx frames on the mirror port.
             Because of this, mode for the selected mirror port is limited to Disabled or Rx only."
        ::= { ctcMirror 3 }


-- UPnP
    -- 1.3.6.1.4.1.4756.104.170
    ctcUPnP  OBJECT IDENTIFIER ::= { gsw2008ms 170 }

    -- 1.3.6.1.4.1.4756.104.170.1
    ctcUpnpMode OBJECT-TYPE
        SYNTAX      INTEGER {
                        enabled(1),
                        disabled(2)
                    }
        MAX-ACCESS  read-write
        STATUS      current
        DESCRIPTION
            "Indicates the UPnP operation mode. Possible modes are:
             Enabled: Enable UPnP mode operation.
             Disabled: Disable UPnP mode operation.
             When the mode is enabled,
             two ACEs are added automatically to trap UPNP related packets to CPU.
             The ACEs are automatically removed when the mode is disabled."
        ::= { ctcUPnP 1 }

    -- 1.3.6.1.4.1.4756.104.170.2
    ctcUpnpTTL OBJECT-TYPE
        SYNTAX      Integer32 (1..255)
        MAX-ACCESS  read-write
        STATUS      current
        DESCRIPTION
            "The TTL value is used by UPnP to send SSDP advertisement messages.
             Valid values are in the range 1 to 255."
        ::= { ctcUPnP 2 }

    -- 1.3.6.1.4.1.4756.104.170.3
    ctcUpnpAdvertisingDuration OBJECT-TYPE
        SYNTAX      Integer32 (100..86400)
        UNITS       "Seconds"
        MAX-ACCESS  read-write
        STATUS      current       
        DESCRIPTION
            "The duration, carried in SSDP packets,
             is used to inform a control point or control points how often it or they
             should receive an SSDP advertisement message from this switch.
             If a control point does not receive any message within the duration,
             it will think that the switch no longer exists. Due to the unreliable nature of UDP,
             in the standard it is recommended that such refreshing of advertisements to be done
             at less than one-half of the advertising duration. In the implementation,
             the switch sends SSDP messages periodically at the interval one-half of
             the advertising duration minus 30 seconds. Valid values are in the range 100 to 86400."
        ::= { ctcUPnP 3 }


END
