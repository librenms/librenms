MSW4424C-MIB DEFINITIONS ::= BEGIN 
  
    IMPORTS
        enterprises,
        NOTIFICATION-TYPE,
        MODULE-IDENTITY,
        OBJECT-TYPE,
        Counter32,
        Integer32,
        Unsigned32,
        Gauge32,
        Counter64,
        IpAddress
            FROM SNMPv2-SMI
        MODULE-COMPLIANCE,
        OBJECT-GROUP,
        NOTIFICATION-GROUP
            FROM SNMPv2-CONF    
        DisplayString,
        DateAndTime,
        MacAddress,
        TruthValue
            FROM SNMPv2-TC       
    ; 
          
     -- 1.3.6.1.4.1.4756
    ctc MODULE-IDENTITY
        LAST-UPDATED "201412180000Z"        
        ORGANIZATION
            " CTC Union Technologies Co., Ltd. "
        CONTACT-INFO
            " Postal: 8F, No.60, ZhouZi Street, NeiHu, Taipei 114, Taiwan
              Tel: +886-2-2659-1021
              Fax: +886-2-2672-5211
              Web: http://www.ctcu.com
              Email: techsupport@ctcu.com " 
        DESCRIPTION
            " MSW4424A-MIB FILE V1.01"
        
               
        REVISION "201412180000Z"        	
        DESCRIPTION
            " V1.01  - Initial Document.
            	add DD Functions"
        ::= { enterprises 4756 }
 
              
-- 
-- Node definitions 
--
    -- 1.3.6.1.4.1.4756.136
    msw4424C OBJECT IDENTIFIER ::= { ctc 136 }	
                              
-- Ports
    -- 1.3.6.1.4.1.4756.136.30
    iPorts OBJECT IDENTIFIER ::= { msw4424C 30 }
    
    -- 1.3.6.1.4.1.4756.121.30.1
    iPortsConfigTable OBJECT-TYPE
        SYNTAX      SEQUENCE OF IPortsConfigEntry
        MAX-ACCESS  not-accessible
        STATUS      current
        DESCRIPTION
            "This table shows current port configurations. Ports can also be configured here."
        ::= { iPorts 1 }

    -- 1.3.6.1.4.1.4756.121.30.1.1
    iPortsConfigEntry OBJECT-TYPE
        SYNTAX      IPortsConfigEntry
        MAX-ACCESS  not-accessible
        STATUS      current
        DESCRIPTION
            "The entry of ports."
        INDEX { iPortIndex }
        ::= { iPortsConfigTable 1 }

    IPortsConfigEntry ::=
        SEQUENCE {
            iPortLink              INTEGER,
            iPortSpeedCurrent      DisplayString,
            iPortSpeedMode         INTEGER,
            iPortMaxFrameSize      Integer32,
            iPortExcCollMode       INTEGER
        }
                         
        -- 1.3.6.1.4.1.4756.121.30.1.1.1    
        iPortLink OBJECT-TYPE
            SYNTAX      INTEGER {
                            linkUp(1),
                            linkDown(2),
                            linkDownByACL(3),
                            linkDownByThermalProtect(4),
                            linkDownByLoopProtect(5)
                        }
            MAX-ACCESS  read-only
            STATUS      current
            DESCRIPTION
                "The current link state.
                	1: linkUp
                	2: linkDown
                	3: linkDownByACL
                	4: linkDownByThermalProtect
                	5: linkDownByLoopProtect
                "
            ::= { iPortsConfigEntry 1 }
                  
        -- 1.3.6.1.4.1.4756.121.30.1.1.2    
        iPortSpeedCurrent OBJECT-TYPE
            SYNTAX      DisplayString
            MAX-ACCESS  read-only
            STATUS      current
            DESCRIPTION
                "Provides the current link speed of the port.

                "
            ::= { iPortsConfigEntry 2 }
                  
        -- 1.3.6.1.4.1.4756.121.30.1.1.3    
        iPortSpeedMode OBJECT-TYPE
            SYNTAX      INTEGER {
                            disabled(1),
                            auto(2),
                            speed10Mhdx(3),
                            speed10Mfdx(4),
                            speed100Mhdx(5),
                            speed100Mfdx(6),
                            speed1Gfdx(7),
                            speedSFPAutoAMS(8),
                            speed100FXAMS(9),
                            speed1000XAMS(10),
                            speed100FX(11),
                            speed1000X(12),
                            speed10G(13)                           
                        }
            MAX-ACCESS  read-write
            STATUS      current
            DESCRIPTION
                "Select link speed for the switch port."
            ::= { iPortsConfigEntry 3 }                   
                  
        -- 1.3.6.1.4.1.4756.121.30.1.1.7    
        iPortMaxFrameSize OBJECT-TYPE
            SYNTAX      Integer32 (1518..9600)
            MAX-ACCESS  read-write
            STATUS      current
            DESCRIPTION
                "The maximum frame size allowed for the switch port, including FCS."
            ::= { iPortsConfigEntry 7 }
                  
        -- 1.3.6.1.4.1.4756.121.30.1.1.8    
        iPortExcCollMode OBJECT-TYPE
            SYNTAX      INTEGER {
            								none(0),
                            discard(1),
                            restart(2)
                        }
            MAX-ACCESS  read-write
            STATUS      current
            DESCRIPTION
                "Configure port transmit collision behavior.
                 Discard: Discard frame after 16 collisions (default).
                 Restart: Restart backoff algorithm after 16 collisions."
            DEFVAL      { 1 }
            ::= { iPortsConfigEntry 8 }

    -- 1.3.6.1.4.1.4756.121.30.2
    iPortsTrafficClear OBJECT-TYPE
        SYNTAX      INTEGER {
                        trigger(1),
                        normal(2)
                    }
        MAX-ACCESS  read-write
        STATUS      current
        DESCRIPTION
            "Clears the counters for all ports."
        ::= { iPorts 2 }

    -- 1.3.6.1.4.1.4756.121.30.3
    iPortsTrafficOverviewTable OBJECT-TYPE
        SYNTAX      SEQUENCE OF IPortsTrafficOverviewEntry
        MAX-ACCESS  not-accessible
        STATUS      current
        DESCRIPTION
            "This table provides an overview of general traffic statistics for all switch ports."
        ::= { iPorts 3 }

    -- 1.3.6.1.4.1.4756.121.30.3.1
    iPortsTrafficOverviewEntry OBJECT-TYPE
        SYNTAX      IPortsTrafficOverviewEntry
        MAX-ACCESS  not-accessible
        STATUS      current
        DESCRIPTION
            "The entry of ports."
        INDEX { iPortIndex }
        ::= { iPortsTrafficOverviewTable 1 }

    IPortsTrafficOverviewEntry ::=
        SEQUENCE {
            iReceivedPackets       DisplayString,
            iTransmittedPackets    DisplayString,
            iReceivedBytes         DisplayString,
            iTransmittedBytes      DisplayString,
            iReceivedErrors        DisplayString,
            iTransmittedErrors     DisplayString,
            iReceivedDrops         DisplayString,
            iTransmittedDrops      DisplayString,
            iReceivedFiltered      DisplayString
        }
                  
        -- 1.3.6.1.4.1.4756.121.30.3.1.1    
        iReceivedPackets OBJECT-TYPE
            SYNTAX      DisplayString
            UNITS       "Packets"
            MAX-ACCESS  read-only
            STATUS      current
            DESCRIPTION
                "The number of received packets per port."
            ::= { iPortsTrafficOverviewEntry 1 }

        -- 1.3.6.1.4.1.4756.121.30.3.1.2    
        iTransmittedPackets OBJECT-TYPE
            SYNTAX      DisplayString
            UNITS       "Packets"
            MAX-ACCESS  read-only
            STATUS      current
            DESCRIPTION
                "The number of transmitted packets per port."
            ::= { iPortsTrafficOverviewEntry 2 }
                  
        -- 1.3.6.1.4.1.4756.121.30.3.1.3    
        iReceivedBytes OBJECT-TYPE
            SYNTAX      DisplayString
            UNITS       "Bytes"
            MAX-ACCESS  read-only
            STATUS      current
            DESCRIPTION
                "The number of received bytes per port."
            ::= { iPortsTrafficOverviewEntry 3 }
                  
        -- 1.3.6.1.4.1.4756.121.30.3.1.4    
        iTransmittedBytes OBJECT-TYPE
            SYNTAX      DisplayString
            UNITS       "Bytes"
            MAX-ACCESS  read-only
            STATUS      current
            DESCRIPTION
                "The number of transmitted bytes per port."
            ::= { iPortsTrafficOverviewEntry 4 }
                  
        -- 1.3.6.1.4.1.4756.121.30.3.1.5    
        iReceivedErrors OBJECT-TYPE
            SYNTAX      DisplayString
            UNITS       "Packets"
            MAX-ACCESS  read-only
            STATUS      current
            DESCRIPTION
                "The number of frames received in error."
            ::= { iPortsTrafficOverviewEntry 5 }
                  
        -- 1.3.6.1.4.1.4756.121.30.3.1.6    
        iTransmittedErrors OBJECT-TYPE
            SYNTAX      DisplayString
            UNITS       "Packets"
            MAX-ACCESS  read-only
            STATUS      current
            DESCRIPTION
                "The number of incomplete transmissions per port."
            ::= { iPortsTrafficOverviewEntry 6 }
                  
        -- 1.3.6.1.4.1.4756.121.30.3.1.7    
        iReceivedDrops OBJECT-TYPE
            SYNTAX      DisplayString
            UNITS       "Packets"
            MAX-ACCESS  read-only
            STATUS      current
            DESCRIPTION
                "The number of frames discarded due to ingress congestion."
            ::= { iPortsTrafficOverviewEntry 7 }
                  
        -- 1.3.6.1.4.1.4756.121.30.3.1.8    
        iTransmittedDrops OBJECT-TYPE
            SYNTAX      DisplayString
            UNITS       "Packets"
            MAX-ACCESS  read-only
            STATUS      current
            DESCRIPTION
                "The number of frames discarded due to egress congestion."
            ::= { iPortsTrafficOverviewEntry 8 }
                  
        -- 1.3.6.1.4.1.4756.121.30.3.1.9    
        iReceivedFiltered OBJECT-TYPE
            SYNTAX      DisplayString
            UNITS       "Packets"
            MAX-ACCESS  read-only
            STATUS      current
            DESCRIPTION
                "The number of received frames filtered by the forwarding process."
            ::= { iPortsTrafficOverviewEntry 9 }

    -- 1.3.6.1.4.1.4756.121.30.4
    iPortsQosStatisticsClear OBJECT-TYPE
        SYNTAX      INTEGER {
                        trigger(1),
                        normal(2)
                    }
        MAX-ACCESS  read-write
        STATUS      current
        DESCRIPTION
            "Clears the counters for all ports."
        ::= { iPorts 4 }

    -- 1.3.6.1.4.1.4756.121.30.5
    iPortsQosStatisticsTable OBJECT-TYPE
        SYNTAX      SEQUENCE OF IPortsQosStatisticsEntry
        MAX-ACCESS  not-accessible
        STATUS      current
        DESCRIPTION
            "This table provides statistics for the different queues for all switch ports."
        ::= { iPorts 5 }

    -- 1.3.6.1.4.1.4756.121.30.5.1
    iPortsQosStatisticsEntry OBJECT-TYPE
        SYNTAX      IPortsQosStatisticsEntry
        MAX-ACCESS  not-accessible
        STATUS      current
        DESCRIPTION
            "Each entry contains 8 QoS queues per port."
        INDEX { iPortIndex, iQueueIndex }
        ::= { iPortsQosStatisticsTable 1 }

    IPortsQosStatisticsEntry ::=
        SEQUENCE {
            iQueueIndex            Integer32,
            iQueueRxPackets        DisplayString,
            iQueueTxPackets        DisplayString
        }

        -- 1.3.6.1.4.1.4756.121.30.5.1.1
        iQueueIndex OBJECT-TYPE
            SYNTAX      Integer32 (0..7)
            MAX-ACCESS  read-only
            STATUS      current
            DESCRIPTION
                "There are 8 QoS queues per port. Q0 is the lowest priority queue."
            ::= { iPortsQosStatisticsEntry 1 }
                  
        -- 1.3.6.1.4.1.4756.121.30.5.1.2    
        iQueueRxPackets OBJECT-TYPE
            SYNTAX      DisplayString
            MAX-ACCESS  read-only
            STATUS      current
            DESCRIPTION
                "The number of received packets per queue."
            ::= { iPortsQosStatisticsEntry 2 }
                  
        -- 1.3.6.1.4.1.4756.121.30.5.1.3    
        iQueueTxPackets OBJECT-TYPE
            SYNTAX      DisplayString
            MAX-ACCESS  read-only
            STATUS      current
            DESCRIPTION
                "The number of transmitted  packets per queue."
            ::= { iPortsQosStatisticsEntry 3 }

    -- 1.3.6.1.4.1.4756.121.30.6
    iPortsQclResolveConflict  OBJECT-TYPE
        SYNTAX      INTEGER {
                        trigger(1),
                        normal(2)
                    }
        MAX-ACCESS  read-write
        STATUS      current
        DESCRIPTION
            "Resolves conflict by releaseing the resource required by the QCE."
        ::= { iPorts 6 }

    -- 1.3.6.1.4.1.4756.121.30.7
    iPortsQclStatusTable OBJECT-TYPE
        SYNTAX      SEQUENCE OF IPortsQclStatusEntry
        MAX-ACCESS  not-accessible
        STATUS      current
        DESCRIPTION
            "This table shows the QCL status by different QCL users."
        ::= { iPorts 7 }

    -- 1.3.6.1.4.1.4756.121.30.7.1
    iPortsQclStatusEntry OBJECT-TYPE
        SYNTAX      IPortsQclStatusEntry
        MAX-ACCESS  not-accessible
        STATUS      current
        DESCRIPTION
            "Each entry describes the QCE that is defined."
        INDEX { iQclStatusIndex }
        ::= { iPortsQclStatusTable 1 }

    IPortsQclStatusEntry ::=
        SEQUENCE {
            iQclStatusIndex    Integer32,
            iQclUser           INTEGER,
            iQCEntryNumber     Integer32,
            iQclFrameType      INTEGER,
            iQclPort           DisplayString,
            iQclActionClass    Integer32,
            iQclActionDPL      Integer32,
            iQclActionDSCP     Integer32,
            iQclConflict       TruthValue
        }

        -- 1.3.6.1.4.1.4756.121.30.7.1.1
        iQclStatusIndex OBJECT-TYPE
            SYNTAX      Integer32 (1..240)
            MAX-ACCESS  read-only
            STATUS      current
            DESCRIPTION
                "The index of QoS Control List Status."
            ::= { iPortsQclStatusEntry 1 }
                  
        -- 1.3.6.1.4.1.4756.121.30.7.1.2    
        iQclUser OBJECT-TYPE
            SYNTAX      INTEGER {
                            static(1),
                            u-ring(2)
                        }
            MAX-ACCESS  read-only
            STATUS      current
            DESCRIPTION
                "Indicates the QCL user."
            ::= { iPortsQclStatusEntry 2 }
                  
        -- 1.3.6.1.4.1.4756.121.30.7.1.3    
        iQCEntryNumber OBJECT-TYPE
            SYNTAX      Integer32
            MAX-ACCESS  read-only
            STATUS      current
            DESCRIPTION
                "Indicates the index of QCE."
            ::= { iPortsQclStatusEntry 3 }
                  
        -- 1.3.6.1.4.1.4756.121.30.7.1.4    
        iQclFrameType OBJECT-TYPE
            SYNTAX      INTEGER {
                            any(1),
                            ethernet(2),
                            llc(3),
                            snap(4),
                            ipv4(5),
                            ipv6(6)
                        }
            MAX-ACCESS  read-only
            STATUS      current
            DESCRIPTION
                "Indicates the type of frame to look for incomming frames. Possible frame types are:
                 Any: The QCE will match all frame type.
                 Ethernet: Only Ethernet frames (with Ether Type 0x600-0xFFFF) are allowed.
                 LLC: Only (LLC) frames are allowed.
                 LLC: Only (SNAP) frames are allowed.
                 IPv4: The QCE will match only IPV4 frames.
                 IPv6: The QCE will match only IPV6 frames."
            ::= { iPortsQclStatusEntry 4 }
                  
        -- 1.3.6.1.4.1.4756.121.30.7.1.5    
        iQclPort OBJECT-TYPE
            SYNTAX      DisplayString (SIZE (1..128))
            MAX-ACCESS  read-only
            STATUS      current
            DESCRIPTION
                "Indicates the list of ports configured with the QCE."
            ::= { iPortsQclStatusEntry 5 }     
                  
        -- 1.3.6.1.4.1.4756.121.30.7.1.6    
        iQclActionClass OBJECT-TYPE
            SYNTAX      Integer32  (-1 | 0..7)
            MAX-ACCESS  read-only
            STATUS      current
            DESCRIPTION
                "Classified QoS Class, if a frame matches the QCE it will be put in the queue.
                 -1: default
                 0 to 7: class0 to class7"
            DEFVAL      { -1 }
            ::= { iPortsQclStatusEntry 6 }
                  
        -- 1.3.6.1.4.1.4756.121.30.7.1.7    
        iQclActionDPL OBJECT-TYPE
            SYNTAX      Integer32 (-1 | 0..1)
            MAX-ACCESS  read-only
            STATUS      current
            DESCRIPTION
                "Drop Precedence Level,
                 if a frame matches the QCE then DP level will set to value displayed under DPL column.
                 -1: default
                 0, 1: DPL0 and DPL1"
            DEFVAL      { -1 }
            ::= { iPortsQclStatusEntry 7 }
                  
        -- 1.3.6.1.4.1.4756.121.4.7.1.8    
        iQclActionDSCP OBJECT-TYPE
            SYNTAX      Integer32 (-1 | 0..63)
            MAX-ACCESS  read-only
            STATUS      current
            DESCRIPTION
                "If a frame matches the QCE then DSCP will be classified with the value displayed under DSCP column.
                 -1: default
                 0 to 63: DSCP0 to DSCP63"
            DEFVAL      { -1 }
            ::= { iPortsQclStatusEntry 8 }
                  
        -- 1.3.6.1.4.1.4756.121.30.7.1.9    
        iQclConflict OBJECT-TYPE
            SYNTAX      TruthValue
            MAX-ACCESS  read-only
            STATUS      current
            DESCRIPTION
                "Displays QCE status. It may happen that resources required to add a QCE may not available."
            ::= { iPortsQclStatusEntry 9 }

	    -- 1.3.6.1.4.1.4756.121.30.8
	    iPortStatus OBJECT IDENTIFIER ::= { iPorts 8 }
	    
	    -- 1.3.6.1.4.1.4756.121.30.8.1
	    iPower1Status OBJECT-TYPE
	        SYNTAX      INTEGER {
	                        on(1),
	                        off(2)
	                    }
	        MAX-ACCESS  read-only
	        STATUS      current
	        DESCRIPTION
				"The Switch Power 1 Status
	            	1:Power ON
	                2:Power OFF
	            "
	        ::= { iPortStatus 1 }     
	        
	    -- 1.3.6.1.4.1.4756.121.30.8.2
	    iPower2Status OBJECT-TYPE
	        SYNTAX      INTEGER {
	                        on(1),
	                        off(2)
	                    }
	        MAX-ACCESS  read-only
	        STATUS      current
	        DESCRIPTION
				"The Switch Power 2 Status
	            	1:Power ON
	                2:Power OFF
	            "
	        ::= { iPortStatus 2 }     
	        
	    -- 1.3.6.1.4.1.4756.121.30.8.3
	    iFaultAlarmStatus OBJECT-TYPE
	        SYNTAX      INTEGER {
	                        on(1),
	                        off(2)
	                    }
	        MAX-ACCESS  read-only
	        STATUS      current
	        DESCRIPTION
				"The Switch Fault Alarm Status
	            	1:Fault Alarm ON
	                2:Fault Alarm OFF
	            "
	        ::= { iPortStatus 3 }
	    
	    -- 1.3.6.1.4.1.4756.121.30.8.4    
	    iCPUActiveStatus OBJECT-TYPE
	        SYNTAX      INTEGER {
	                        on(1),
	                        off(2)
	                    }
	        MAX-ACCESS  read-only
	        STATUS      current
	        DESCRIPTION
				"The Switch CPU Active Status
	            	1:CPU ON
	                2:CPU OFF
	            "
	        ::= { iPortStatus 4 }
	        
		-- 1.3.6.1.4.1.4756.121.30.8.5
	    iFANStatus OBJECT-TYPE
	        SYNTAX      INTEGER {
	                        on(1),
	                        off(2)
	                    }
	        MAX-ACCESS  read-only
	        STATUS      current
	        DESCRIPTION
				"The Switch Ring Master Status
	            	1:Ring Master ON
	                2:Ring Master OFF
	            "
	        ::= { iPortStatus 5 }

    -- 1.3.6.1.4.1.4756.136.30.20
    iSFPTable OBJECT-TYPE
        SYNTAX      SEQUENCE OF ISFPEntry
        MAX-ACCESS  not-accessible
        STATUS      current
        DESCRIPTION
            "This table shows current port configurations. Ports can also be configured here."
        ::= { iPorts 20 }

    -- 1.3.6.1.4.1.4756.136.30.20.1
    iSFPEntry OBJECT-TYPE
        SYNTAX      ISFPEntry
        MAX-ACCESS  not-accessible
        STATUS      current
        DESCRIPTION
            "The entry of ports."
        INDEX { iPortIndex }
        ::= { iSFPTable 1 }

    ISFPEntry ::=
        SEQUENCE {
        		iPortIndex			    Integer32,
            iSfpModule              INTEGER,
            iSfpVendorName      	DisplayString,
            iSfpVendorPartNumber    DisplayString,
            iSfpType 			    INTEGER,
            iSfpWaveLength   		DisplayString,
            iSfpWaveLength2      	DisplayString,
            iSfpLinkLength          DisplayString,
            iSfpTXPower       	    DisplayString,
            iSfpRXPower       		DisplayString,
            iSfpRXSensitivity       DisplayString,
            iSfpTemperature         DisplayString
        }
    
    	-- 1.3.6.1.4.1.4756.136.30.20.1
        iPortIndex OBJECT-TYPE
            SYNTAX      Integer32 (1..29)
            MAX-ACCESS  read-only
            STATUS      current
            DESCRIPTION
                "
                "
            ::= { iSFPEntry 1 }
    
    	-- 1.3.6.1.4.1.4756.136.30.20.2
    	iSfpModule  OBJECT-TYPE
        SYNTAX      INTEGER {
                        inserted(1),
                        removed(2)
                    }
        MAX-ACCESS  read-only
        STATUS      current
        DESCRIPTION
            "Indicate the SFP module is existent or not."
        ::= { iSFPEntry 2 }

	    -- 1.3.6.1.4.1.4756.136.30.20.3
	    iSfpVendorName  OBJECT-TYPE
	        SYNTAX      DisplayString
	        MAX-ACCESS  read-only
	        STATUS      current
	        DESCRIPTION
	            "The name of SFP vendor."
	        ::= { iSFPEntry 3 }
	
	    -- 1.3.6.1.4.1.4756.136.30.20.4
	    iSfpVendorPartNumber  OBJECT-TYPE
	        SYNTAX      DisplayString
	        MAX-ACCESS  read-only
	        STATUS      current
	        DESCRIPTION
	            "The part number provided by SFP vendor."
	        ::= { iSFPEntry 4 }
		
	    -- 1.3.6.1.4.1.4756.136.30.20.5
	    iSfpType  OBJECT-TYPE
	        SYNTAX      INTEGER {
	                        none(0),
	                        singleMode(1),
	                        multiMode(2)
	                    }
	        MAX-ACCESS  read-only
	        STATUS      current
	        DESCRIPTION
	            "The type of fibre channel transmission media."
	        ::= { iSFPEntry 5 }
	        	
	    -- 1.3.6.1.4.1.4756.136.30.20.6
	    iSfpWaveLength  OBJECT-TYPE
	        SYNTAX      DisplayString
	        MAX-ACCESS  read-only
	        STATUS      current
	        DESCRIPTION
	            "The transceiver Laser wavelength tx."
	        ::= { iSFPEntry 6}
	
	    -- 1.3.6.1.4.1.4756.136.30.20.7
	    iSfpWaveLength2  OBJECT-TYPE
	        SYNTAX      DisplayString
	        MAX-ACCESS  read-only
	        STATUS      current
	        DESCRIPTION
	            "The transceiver Laser wavelength rx."
	        ::= { iSFPEntry 7 }
	
	    -- 1.3.6.1.4.1.4756.136.30.20.8
	    iSfpLinkLength  OBJECT-TYPE
	        SYNTAX      DisplayString
	        MAX-ACCESS  read-only
	        STATUS      current
	        DESCRIPTION
	            "The transceiver Link Length."
	        ::= { iSFPEntry 8 }
	
	    -- 1.3.6.1.4.1.4756.136.30.20.9
	    iSfpTXPower  OBJECT-TYPE
	        SYNTAX      DisplayString
	        MAX-ACCESS  read-only
	        STATUS      current
	        DESCRIPTION
	            "The transceiver TX Power."
	        ::= { iSFPEntry 9 }
        
        -- 1.3.6.1.4.1.4756.136.30.20.10
	    iSfpRXPower  OBJECT-TYPE
	        SYNTAX      DisplayString
	        MAX-ACCESS  read-only
	        STATUS      current
	        DESCRIPTION
	            "The transceiver RX Power."
	        ::= { iSFPEntry 10 }
	    
	    -- 1.3.6.1.4.1.4756.136.30.20.11
	    iSfpRXSensitivity  OBJECT-TYPE
	        SYNTAX      DisplayString
	        MAX-ACCESS  read-only
	        STATUS      current
	        DESCRIPTION
	            "The transceiver RX Sensitivity."
	        ::= { iSFPEntry 11 }    
	        
	    -- 1.3.6.1.4.1.4756.136.30.20.13
	    iSfpTemperature  OBJECT-TYPE
	        SYNTAX      DisplayString
	        MAX-ACCESS  read-only
	        STATUS      current
	        DESCRIPTION
	            "The transceiver temperature in degree C."
	        ::= { iSFPEntry 12 }  




-- Link OAM
    -- 1.3.6.1.4.1.4756.136.45
    iLinkOAM OBJECT IDENTIFIER ::= { msw4424C 45 }
    



    -- 1.3.6.1.4.1.4756.136.45.20
    iLinkOAMStatisticsTable OBJECT-TYPE
        SYNTAX      SEQUENCE OF ILinkOAMStatisticsEntry
        MAX-ACCESS  not-accessible
        STATUS      current
        DESCRIPTION
            "This table shows current port configurations. Ports can also be configured here."
        ::= { iLinkOAM 4 }

    -- 1.3.6.1.4.1.4756.136.45.4.1
    iLinkOAMStatisticsEntry OBJECT-TYPE
        SYNTAX      ILinkOAMStatisticsEntry
        MAX-ACCESS  not-accessible
        STATUS      current
        DESCRIPTION
            "The entry of ports."
        INDEX { iPortIndex }
        ::= { iLinkOAMStatisticsTable 1 }

    ILinkOAMStatisticsEntry ::=
        SEQUENCE {
--        		iPortIndex			    Integer32,
        		iLinkOAMInformationTx              Counter32,
						iLinkOAMInformationRx              Counter32,
						iLinkOAMUniqueEventNotificationTx              Counter32,
						iLinkOAMUniqueEventNotificationRx              Counter32,
						iLinkOAMDuplicateEventNotificationTx              Counter32,
						iLinkOAMDuplicateEventNotificationRx              Counter32,
						iLinkOAMLoopbackControlTx              Counter32,
						iLinkOAMLoopbackControlRx              Counter32,
						iLinkOAMVariableRequestTx              Counter32,
						iLinkOAMVariableRequestRx              Counter32,
						iLinkOAMVariableResponseTx              Counter32,
						iLinkOAMVariableResponseRx              Counter32,
						iLinkOAMOrgSpecificTx              Counter32,
						iLinkOAMOrgSpecificRx              Counter32,
						iLinkOAMUnsupportedCodesTx              Counter32,
						iLinkOAMUnsupportedCodesRx              Counter32,
						iLinkOAMLinkFaultTx              Counter32,
						iLinkOAMLinkFaultRx              Counter32,
						iLinkOAMUDyingGaspTx              Counter32,
						iLinkOAMUDyingGaspRx              Counter32,
						iLinkOAMCriticalEventTx              Counter32,
						iLinkOAMCriticalEventRx              Counter32      		

        }
    
    	-- 1.3.6.1.4.1.4756.136.45.4.1.1
--        iPortIndex OBJECT-TYPE
--            SYNTAX      Integer32 (1..29)
--            MAX-ACCESS  read-only
--            STATUS      current
--            DESCRIPTION
--                "
--                "
--            ::= { iLinkOAMStatisticsEntry 1 }
    
    	-- 1.3.6.1.4.1.4756.136.45.4.1.2
        iLinkOAMInformationTx OBJECT-TYPE
            SYNTAX      Counter32
            MAX-ACCESS  read-only
            STATUS      current
            DESCRIPTION
                "."
            ::= { iLinkOAMStatisticsEntry 2 }

    	-- 1.3.6.1.4.1.4756.136.45.4.1.3
        iLinkOAMInformationRx OBJECT-TYPE
            SYNTAX      Counter32
            MAX-ACCESS  read-only
            STATUS      current
            DESCRIPTION
                "."
            ::= { iLinkOAMStatisticsEntry 3 }

    	-- 1.3.6.1.4.1.4756.136.45.4.1.4
        iLinkOAMUniqueEventNotificationTx OBJECT-TYPE
            SYNTAX      Counter32
            MAX-ACCESS  read-only
            STATUS      current
            DESCRIPTION
                "."
            ::= { iLinkOAMStatisticsEntry 4 }
            	
    	-- 1.3.6.1.4.1.4756.136.45.4.1.5
        iLinkOAMUniqueEventNotificationRx OBJECT-TYPE
            SYNTAX      Counter32
            MAX-ACCESS  read-only
            STATUS      current
            DESCRIPTION
                "."
            ::= { iLinkOAMStatisticsEntry 5 }
            	
    	-- 1.3.6.1.4.1.4756.136.45.4.1.6
        iLinkOAMDuplicateEventNotificationTx OBJECT-TYPE
            SYNTAX      Counter32
            MAX-ACCESS  read-only
            STATUS      current
            DESCRIPTION
                "."
            ::= { iLinkOAMStatisticsEntry 6 }
            	
    	-- 1.3.6.1.4.1.4756.136.45.4.1.7
        iLinkOAMDuplicateEventNotificationRx OBJECT-TYPE
            SYNTAX      Counter32
            MAX-ACCESS  read-only
            STATUS      current
            DESCRIPTION
                "."
            ::= { iLinkOAMStatisticsEntry 7 }
            	
    	-- 1.3.6.1.4.1.4756.136.45.4.1.8
        iLinkOAMLoopbackControlTx OBJECT-TYPE
            SYNTAX      Counter32
            MAX-ACCESS  read-only
            STATUS      current
            DESCRIPTION
                "."
            ::= { iLinkOAMStatisticsEntry 8 }
            	
    	-- 1.3.6.1.4.1.4756.136.45.4.1.9
        iLinkOAMLoopbackControlRx OBJECT-TYPE
            SYNTAX      Counter32
            MAX-ACCESS  read-only
            STATUS      current
            DESCRIPTION
                "."
            ::= { iLinkOAMStatisticsEntry 9 }
            	
    	-- 1.3.6.1.4.1.4756.136.45.4.1.10
        iLinkOAMVariableRequestTx OBJECT-TYPE
            SYNTAX      Counter32
            MAX-ACCESS  read-only
            STATUS      current
            DESCRIPTION
                "."
            ::= { iLinkOAMStatisticsEntry 10 }
            	
    	-- 1.3.6.1.4.1.4756.136.45.4.1.11
        iLinkOAMVariableRequestRx OBJECT-TYPE
            SYNTAX      Counter32
            MAX-ACCESS  read-only
            STATUS      current
            DESCRIPTION
                "."
            ::= { iLinkOAMStatisticsEntry 11 }
            	
    	-- 1.3.6.1.4.1.4756.136.45.4.1.12
        iLinkOAMVariableResponseTx OBJECT-TYPE
            SYNTAX      Counter32
            MAX-ACCESS  read-only
            STATUS      current
            DESCRIPTION
                "."
            ::= { iLinkOAMStatisticsEntry 12 }
            	
    	-- 1.3.6.1.4.1.4756.136.45.4.1.13
        iLinkOAMVariableResponseRx OBJECT-TYPE
            SYNTAX      Counter32
            MAX-ACCESS  read-only
            STATUS      current
            DESCRIPTION
                "."
            ::= { iLinkOAMStatisticsEntry 13 }
            	
    	-- 1.3.6.1.4.1.4756.136.45.4.1.14
        iLinkOAMOrgSpecificTx OBJECT-TYPE
            SYNTAX      Counter32
            MAX-ACCESS  read-only
            STATUS      current
            DESCRIPTION
                "."
            ::= { iLinkOAMStatisticsEntry 14 }
            	
    	-- 1.3.6.1.4.1.4756.136.45.4.1.15
        iLinkOAMOrgSpecificRx OBJECT-TYPE
            SYNTAX      Counter32
            MAX-ACCESS  read-only
            STATUS      current
            DESCRIPTION
                "."
            ::= { iLinkOAMStatisticsEntry 15 }
            	
    	-- 1.3.6.1.4.1.4756.136.45.4.1.16
        iLinkOAMUnsupportedCodesTx OBJECT-TYPE
            SYNTAX      Counter32
            MAX-ACCESS  read-only
            STATUS      current
            DESCRIPTION
                "."
            ::= { iLinkOAMStatisticsEntry 16 }
            	
    	-- 1.3.6.1.4.1.4756.136.45.4.1.17
        iLinkOAMUnsupportedCodesRx OBJECT-TYPE
            SYNTAX      Counter32
            MAX-ACCESS  read-only
            STATUS      current
            DESCRIPTION
                "."
            ::= { iLinkOAMStatisticsEntry 17 }
            	
    	-- 1.3.6.1.4.1.4756.136.45.4.1.18
        iLinkOAMLinkFaultTx OBJECT-TYPE
            SYNTAX      Counter32
            MAX-ACCESS  read-only
            STATUS      current
            DESCRIPTION
                "."
            ::= { iLinkOAMStatisticsEntry 18 }           
    	-- 1.3.6.1.4.1.4756.136.45.4.1.19
        iLinkOAMLinkFaultRx OBJECT-TYPE
            SYNTAX      Counter32
            MAX-ACCESS  read-only
            STATUS      current
            DESCRIPTION
                "."
            ::= { iLinkOAMStatisticsEntry 19 }
    	-- 1.3.6.1.4.1.4756.136.45.4.1.20
        iLinkOAMUDyingGaspTx OBJECT-TYPE
            SYNTAX      Counter32
            MAX-ACCESS  read-only
            STATUS      current
            DESCRIPTION
                "."
            ::= { iLinkOAMStatisticsEntry 20 }
    	-- 1.3.6.1.4.1.4756.136.45.4.1.21
        iLinkOAMUDyingGaspRx OBJECT-TYPE
            SYNTAX      Counter32
            MAX-ACCESS  read-only
            STATUS      current
            DESCRIPTION
                "."
            ::= { iLinkOAMStatisticsEntry 21 }
    	-- 1.3.6.1.4.1.4756.136.45.4.1.22
        iLinkOAMCriticalEventTx OBJECT-TYPE
            SYNTAX      Counter32
            MAX-ACCESS  read-only
            STATUS      current
            DESCRIPTION
                "."
            ::= { iLinkOAMStatisticsEntry 22 }
    	-- 1.3.6.1.4.1.4756.136.45.4.1.23
        iLinkOAMCriticalEventRx OBJECT-TYPE
            SYNTAX      Counter32
            MAX-ACCESS  read-only
            STATUS      current
            DESCRIPTION
                "."
            ::= { iLinkOAMStatisticsEntry 23 } 
            
            
-- IPMC
    -- 1.3.6.1.4.1.37552.4.2.110
    iIPMC  OBJECT IDENTIFIER ::= { msw4424C 110 }

    -- 1.3.6.1.4.1.37552.4.2.110.1
    iIgmpSnooping  OBJECT IDENTIFIER ::= { iIPMC 1 }

    -- 1.3.6.1.4.1.37552.4.2.110.1.1
    iIgmpSnoopingEnabled OBJECT-TYPE
        SYNTAX      TruthValue
        MAX-ACCESS  read-write
        STATUS      current
        DESCRIPTION                                  
            "Enable the Global IGMP Snooping."
        ::= { iIgmpSnooping 1 }

    -- 1.3.6.1.4.1.37552.4.2.110.1.2
    iUnregisteredIpmcV4FloodingEnabled OBJECT-TYPE
        SYNTAX      TruthValue
        MAX-ACCESS  read-write
        STATUS      current
        DESCRIPTION                                  
            "Enable unregistered IPMC traffic flooding."
        ::= { iIgmpSnooping 2 }

    -- 1.3.6.1.4.1.37552.4.2.110.1.3
    iIgmpSsmRange OBJECT-TYPE
        SYNTAX      DisplayString
        MAX-ACCESS  read-write
        STATUS      current
        DESCRIPTION                                  
            "SSM (Source-Specific Multicast) Range allows the SSM-aware hosts and
             routers run the SSM service model for the groups in the address range.
             Syntax: (Range <mask_len>)"
        ::= { iIgmpSnooping 3 }

    -- 1.3.6.1.4.1.37552.4.2.110.1.4
    iIgmpLeaveProxyEnabled OBJECT-TYPE
        SYNTAX      TruthValue
        MAX-ACCESS  read-write
        STATUS      current
        DESCRIPTION                                  
            "Enable IGMP Leave Proxy.
             This feature can be used to avoid forwarding unnecessary leave messages to
             the router side."
        ::= { iIgmpSnooping 4 }

    -- 1.3.6.1.4.1.37552.4.2.110.1.5
    iIgmpProxyEnabled OBJECT-TYPE
        SYNTAX      TruthValue
        MAX-ACCESS  read-write
        STATUS      current
        DESCRIPTION                                  
            "Enable IGMP Proxy.
             This feature can be used to avoid forwarding unnecessary join and
             leave messages to the router side."
        ::= { iIgmpSnooping 5 }

    -- 1.3.6.1.4.1.37552.4.2.110.1.10
    iIgmpPortRelatedTable OBJECT-TYPE
        SYNTAX      SEQUENCE OF IIgmpPortRelatedEntry
        MAX-ACCESS  not-accessible
        STATUS      current
        DESCRIPTION
            "This table is used for configuring the Port Related."
        ::= { iIgmpSnooping 10 }

    -- 1.3.6.1.4.1.37552.4.2.110.1.10.1
    iIgmpPortRelatedEntry OBJECT-TYPE
        SYNTAX      IIgmpPortRelatedEntry
        MAX-ACCESS  not-accessible
        STATUS      current
        DESCRIPTION
            "The Entry of Port Related configurations."
        INDEX { iPortIndex }
        ::= { iIgmpPortRelatedTable 1 }

    IIgmpPortRelatedEntry ::=
        SEQUENCE {
            iIgmpRouterPortEnabled TruthValue,                
            iIgmpFastLeaveEnabled  TruthValue,
            iIgmpThrottling        Integer32
        }

        -- 1.3.6.1.4.1.37552.4.2.110.1.10.1.1    
        iIgmpRouterPortEnabled OBJECT-TYPE
            SYNTAX      TruthValue
            MAX-ACCESS  read-write
            STATUS      current
            DESCRIPTION
                "Specify which ports act as router ports.
                 A router port is a port on the Ethernet switch that
                 leads towards the Layer 3 multicast device or IGMP querier.
                 If an aggregation member port is selected as a router port,
                 the whole aggregation will act as a router port."
            ::= { iIgmpPortRelatedEntry 1 }


        -- 1.3.6.1.4.1.37552.4.2.110.1.10.1.3    
        iIgmpFastLeaveEnabled OBJECT-TYPE
            SYNTAX      TruthValue
            MAX-ACCESS  read-write
            STATUS      current
            DESCRIPTION
                "Enable the fast leave on the port."
            ::= { iIgmpPortRelatedEntry 3 }

        -- 1.3.6.1.4.1.37552.4.2.110.1.10.1.4    
        iIgmpThrottling OBJECT-TYPE
            SYNTAX      Integer32 (0..10)
            MAX-ACCESS  read-write
            STATUS      current
            DESCRIPTION
                "Enable to limit the number of multicast groups to which a switch port can belong.
                 Set to zero for unlimited."
            ::= { iIgmpPortRelatedEntry 4 }



    -- 1.3.6.1.4.1.37552.4.2.110.1.20
    iAddIgmpVlan OBJECT-TYPE
        SYNTAX      Integer32 (1..4095)
        MAX-ACCESS  read-write
        STATUS      current
        DESCRIPTION                                  
            "Add a new entry to the IGMP VLAN table.
             Specify the VID and configure the new entry.
             The specific IGMP VLAN starts working after the corresponding static VLAN is also created."
        ::= { iIgmpSnooping 20 }

    -- 1.3.6.1.4.1.37552.4.2.110.1.21
    iDeleteIgmpVlan OBJECT-TYPE
        SYNTAX      Integer32 (1..4095)
        MAX-ACCESS  read-write
        STATUS      current
        DESCRIPTION
            "Delete an IGMP VLAN from table."
        ::= { iIgmpSnooping 21 }

    -- 1.3.6.1.4.1.37552.4.2.110.1.22
    iIgmpVlanConfigTable OBJECT-TYPE
        SYNTAX      SEQUENCE OF IIgmpVlanConfigEntry
        MAX-ACCESS  not-accessible
        STATUS      current
        DESCRIPTION
            "This table allows for configure IGMP snooping VLAN."
        ::= { iIgmpSnooping 22 }

    -- 1.3.6.1.4.1.37552.4.2.110.1.22.1
    iIgmpVlanConfigEntry OBJECT-TYPE
        SYNTAX      IIgmpVlanConfigEntry
        MAX-ACCESS  not-accessible
        STATUS      current
        DESCRIPTION
            "The Entry of IGMP snooping VLAN."
        INDEX { iIgmpVlanID }
        ::= { iIgmpVlanConfigTable 1 }

    IIgmpVlanConfigEntry ::=
        SEQUENCE {     
            iIgmpVlanID            Integer32,
            iIgmpPerVlanEnabled    TruthValue,
            iIgmpQuerierEnabled    TruthValue,
            iIgmpCompatibility     INTEGER,
            iIgmpRV                Integer32,
            iIgmpQI                Integer32,
            iIgmpQRI               Integer32,
            iIgmpLLQI              Integer32,
            iIgmpURI               Integer32,
            iIgmpQuerierAddress    IpAddress,
            iIgmpPRI            	 Integer32
        }

        -- 1.3.6.1.4.1.37552.4.2.110.1.22.1.1    
        iIgmpVlanID OBJECT-TYPE
            SYNTAX      Integer32 (1..4095)
            MAX-ACCESS  read-only
            STATUS      current
            DESCRIPTION
                "Indicates the ID of this particular IGMP snooping VLAN."
            ::= { iIgmpVlanConfigEntry 1 }

        -- 1.3.6.1.4.1.37552.4.2.110.1.22.1.2    
        iIgmpPerVlanEnabled OBJECT-TYPE
            SYNTAX      TruthValue
            MAX-ACCESS  read-write
            STATUS      current
            DESCRIPTION
                "Enable the per-VLAN IGMP Snooping. Only up to 64 VLANs can be selected."
            ::= { iIgmpVlanConfigEntry 2 }

        -- 1.3.6.1.4.1.37552.4.2.110.1.22.1.3    
        iIgmpQuerierEnabled OBJECT-TYPE
            SYNTAX      TruthValue
            MAX-ACCESS  read-write
            STATUS      current
            DESCRIPTION
                "Enable the IGMP Querier in the VLAN."
            ::= { iIgmpVlanConfigEntry 3 }

        -- 1.3.6.1.4.1.37552.4.2.110.1.22.1.4    
        iIgmpCompatibility OBJECT-TYPE
            SYNTAX      INTEGER {
                            forcedIgmpV1(1),
                            forcedIgmpV2(2),
                            forcedIgmpV3(3),
            	            igmpAuto(4)
            	        }
            MAX-ACCESS  read-write
            STATUS      current
            DESCRIPTION
                "Compatibility is maintained by hosts and routers taking appropriate actions depending on
                 the versions of IGMP operating on hosts and routers within a network.
                 The allowed selection is IGMP-Auto, Forced IGMPv1, Forced IGMPv2, Forced IGMPv3,
                 default compatibility value is IGMP-Auto."
            DEFVAL      { igmpAuto }
            ::= { iIgmpVlanConfigEntry 4 }

        -- 1.3.6.1.4.1.37552.4.2.110.1.22.1.5    
        iIgmpRV OBJECT-TYPE
            SYNTAX      Integer32 (1..255)
            MAX-ACCESS  read-write
            STATUS      current
            DESCRIPTION
                "Robustness Variable.
                 The Robustness Variable allows tuning for the expected packet loss on a network.
                 The allowed range is 1 to 255, default robustness variable value is 2,
                 Robustness Variable SHOULD NOT be one."
            DEFVAL     { 2 }
            ::= { iIgmpVlanConfigEntry 5 }

        -- 1.3.6.1.4.1.37552.4.2.110.1.22.1.6    
        iIgmpQI OBJECT-TYPE
            SYNTAX      Integer32 (1..255)
            UNITS       "Seconds"
            MAX-ACCESS  read-write
            STATUS      current
            DESCRIPTION
                "Query Interval.
                 The Query Interval is the interval between General Queries sent by the Querier.
                 The allowed range is 1 to 255 seconds, default query interval is 125 seconds.
                 Note: The number of seconds represented by QRI must be less than QI!"
            DEFVAL     { 125 }     
            ::= { iIgmpVlanConfigEntry 6 }

        -- 1.3.6.1.4.1.37552.4.2.110.1.22.1.7    
        iIgmpQRI OBJECT-TYPE
            SYNTAX      Integer32 (0..31744)
            UNITS       "100 millisecond"
            MAX-ACCESS  read-write
            STATUS      current
            DESCRIPTION
                "Query Response Interval.
                 The Max Response Time used to calculate the Max Resp Code inserted into the periodic General Queries.
                 The allowed range is 0 to 31744 in tenths of seconds,
                 default query response interval is 100 in tenths of seconds (10 seconds).
                 The number of seconds represented by QRI must be less than QI!"
            DEFVAL     { 100 }     
            ::= { iIgmpVlanConfigEntry 7 }

        -- 1.3.6.1.4.1.37552.4.2.110.1.22.1.8    
        iIgmpLLQI OBJECT-TYPE
            SYNTAX      Integer32 (0..31744)
            UNITS       "100 millisecond"
            MAX-ACCESS  read-write
            STATUS      current
            DESCRIPTION
                "Last Member Query Interval.
                 The Last Member Query Time is the time value represented by the Last Member Query Interval,
                 multiplied by the Last Member Query Count.
                 The allowed range is 0 to 31744 in tenths of seconds,
                 default last member query interval is 10 in tenths of seconds (1 second)."
            DEFVAL     { 10 }     
            ::= { iIgmpVlanConfigEntry 8 }

        -- 1.3.6.1.4.1.37552.4.2.110.1.22.1.9    
        iIgmpURI OBJECT-TYPE
            SYNTAX      Integer32 (0..31744)
            UNITS       "Seconds"
            MAX-ACCESS  read-write
            STATUS      current
            DESCRIPTION
                "Unsolicited Report Interval.
                 The Unsolicited Report Interval is the time between repetitions of
                 a host's initial report of membership in a group.
                 The allowed range is 0 to 31744 seconds,
                 default unsolicited report interval is 1 second."
            DEFVAL     { 1 }     
            ::= { iIgmpVlanConfigEntry 9 }

        -- 1.3.6.1.4.1.37552.4.2.110.1.22.1.10       
        iIgmpQuerierAddress OBJECT-TYPE
            SYNTAX      IpAddress
            MAX-ACCESS  read-write
            STATUS      current                          
            DESCRIPTION
                "
                "
            ::= { iIgmpVlanConfigEntry 10 }

        -- 1.3.6.1.4.1.37552.4.2.110.1.22.1.11   
        iIgmpPRI OBJECT-TYPE
            SYNTAX      Integer32 (0..7)
            MAX-ACCESS  read-write
            STATUS      current
            DESCRIPTION
                "
                "
            ::= { iIgmpVlanConfigEntry 11 }



    -- 1.3.6.1.4.1.37552.4.2.110.1.32
    iIgmpPortGroupFilteringTable OBJECT-TYPE
        SYNTAX      SEQUENCE OF IIgmpPortGroupFilteringEntry
        MAX-ACCESS  not-accessible
        STATUS      current
        DESCRIPTION
            "This table is used for configuring the port group filtering."
        ::= { iIgmpSnooping 32 }

    -- 1.3.6.1.4.1.37552.4.2.110.1.32.1
    iIgmpPortGroupFilteringEntry OBJECT-TYPE
        SYNTAX      IIgmpPortGroupFilteringEntry
        MAX-ACCESS  not-accessible
        STATUS      current
        DESCRIPTION
            "The Entry of port group filtering configurations."
        INDEX { iIgmpPortGroupFilteringIndex }
        ::= { iIgmpPortGroupFilteringTable 1 }

    IIgmpPortGroupFilteringEntry ::=
        SEQUENCE {
						iIgmpPortGroupFilteringIndex    Integer32,
            iIgmpPortGroupFilteringPort   DisplayString
            
        }

    	-- 1.3.6.1.4.1.37552.4.2.110.1.32.1.1  
        iIgmpPortGroupFilteringIndex OBJECT-TYPE
            SYNTAX      Integer32 (1..29)
            MAX-ACCESS  read-only
            STATUS      current
            DESCRIPTION
                "

                "
            ::= { iIgmpPortGroupFilteringEntry 1 }


        -- 1.3.6.1.4.1.37552.4.2.110.1.32.1.2    
        iIgmpPortGroupFilteringPort OBJECT-TYPE
            SYNTAX      DisplayString
            MAX-ACCESS  read-write
            STATUS      current
            DESCRIPTION
                " "
            ::= { iIgmpPortGroupFilteringEntry 2 }








    -- 1.3.6.1.4.1.37552.4.2.110.1.40
    iIgmpSnoopingStatisticsClear OBJECT-TYPE
        SYNTAX      INTEGER {
                        trigger(1),
                        normal(2)
                    }
        MAX-ACCESS  read-write
        STATUS      current
        DESCRIPTION
            "Clears all Statistics counters."
        ::= { iIgmpSnooping 40 }

    -- 1.3.6.1.4.1.37552.4.2.110.1.41
    iIgmpSnoopingStatisticsTable OBJECT-TYPE
        SYNTAX      SEQUENCE OF IIgmpSnoopingStatisticsEntry
        MAX-ACCESS  not-accessible
        STATUS      current
        DESCRIPTION
            "This table provides IGMP Snooping status."
        ::= { iIgmpSnooping 41 }

    -- 1.3.6.1.4.1.37552.4.2.110.1.41.1
    iIgmpSnoopingStatisticsEntry OBJECT-TYPE
        SYNTAX      IIgmpSnoopingStatisticsEntry
        MAX-ACCESS  not-accessible
        STATUS      current
        DESCRIPTION
            "The Entry of VLAN ID."
        INDEX { iIgmpSnoopingVlanID }
        ::= { iIgmpSnoopingStatisticsTable 1 }

    IIgmpSnoopingStatisticsEntry ::=
        SEQUENCE {       
            iIgmpSnoopingVlanID        Integer32,
            iIgmpQuerierVersion        Integer32,
            iIgmpHostVersion           Integer32,
            iIgmpQuerierStatus         INTEGER,
            iIgmpQueriesTransmitted    Counter32,
            iIgmpQueriesReceived       Counter32,
            iIgmpV1ReportsReceived     Counter32,
            iIgmpV2ReportsReceived     Counter32,
            iIgmpV3ReportsReceived     Counter32,
            iIgmpV2LeavesReceived      Counter32
        }
        
        -- 1.3.6.1.4.1.37552.4.2.110.1.41.1.1    
        iIgmpSnoopingVlanID OBJECT-TYPE
            SYNTAX      Integer32 (1..4095)
            MAX-ACCESS  read-only
            STATUS      current
            DESCRIPTION
                 "The VLAN ID of the entry."
            ::= { iIgmpSnoopingStatisticsEntry 1 }

        -- 1.3.6.1.4.1.37552.4.2.110.1.41.1.2    
        iIgmpQuerierVersion OBJECT-TYPE
            SYNTAX      Integer32 (1..3)
            MAX-ACCESS  read-only
            STATUS      current
            DESCRIPTION
                "Working Querier Version currently."
            ::= { iIgmpSnoopingStatisticsEntry 2 }

        -- 1.3.6.1.4.1.37552.4.2.110.1.41.1.3    
        iIgmpHostVersion OBJECT-TYPE
            SYNTAX      Integer32 (1..3)
            MAX-ACCESS  read-only
            STATUS      current
            DESCRIPTION
                "Working Host Version currently."
            ::= { iIgmpSnoopingStatisticsEntry 3 }

        -- 1.3.6.1.4.1.37552.4.2.110.1.41.1.4    
        iIgmpQuerierStatus OBJECT-TYPE
            SYNTAX      INTEGER {
                            idle(1),
                            active(2),
                            disable(3)
                        }
            MAX-ACCESS  read-only
            STATUS      current
            DESCRIPTION
                "Shows the Querier status is ACTIVE or IDLE.
                 DISABLE denotes the specific interface is administratively disabled."
            ::= { iIgmpSnoopingStatisticsEntry 4 }

        -- 1.3.6.1.4.1.37552.4.2.110.1.41.1.5    
        iIgmpQueriesTransmitted OBJECT-TYPE
            SYNTAX      Counter32
            UNITS       "Packets"
            MAX-ACCESS  read-only
            STATUS      current
            DESCRIPTION
                "The number of Transmitted Queries."
            ::= { iIgmpSnoopingStatisticsEntry 5 }

        -- 1.3.6.1.4.1.37552.4.2.110.1.41.1.6    
        iIgmpQueriesReceived OBJECT-TYPE
            SYNTAX      Counter32
            UNITS       "Packets"
            MAX-ACCESS  read-only
            STATUS      current
            DESCRIPTION
                "The number of Received Queries."
            ::= { iIgmpSnoopingStatisticsEntry 6 }

        -- 1.3.6.1.4.1.37552.4.2.110.1.41.1.7    
        iIgmpV1ReportsReceived OBJECT-TYPE
            SYNTAX      Counter32
            UNITS       "Packets"
            MAX-ACCESS  read-only
            STATUS      current
            DESCRIPTION
                "The number of Received V1 Reports."
            ::= { iIgmpSnoopingStatisticsEntry 7 }

        -- 1.3.6.1.4.1.37552.4.2.110.1.41.1.8    
        iIgmpV2ReportsReceived OBJECT-TYPE
            SYNTAX      Counter32
            UNITS       "Packets"
            MAX-ACCESS  read-only
            STATUS      current
            DESCRIPTION
                "The number of Received V2 Reports."
            ::= { iIgmpSnoopingStatisticsEntry 8 }

        -- 1.3.6.1.4.1.37552.4.2.110.1.41.1.9    
        iIgmpV3ReportsReceived OBJECT-TYPE
            SYNTAX      Counter32
            UNITS       "Packets"
            MAX-ACCESS  read-only
            STATUS      current
            DESCRIPTION
                "The number of Received V3 Reports."
            ::= { iIgmpSnoopingStatisticsEntry 9 }

        -- 1.3.6.1.4.1.37552.4.2.110.1.41.1.10    
        iIgmpV2LeavesReceived OBJECT-TYPE
            SYNTAX      Counter32
            UNITS       "Packets"
            MAX-ACCESS  read-only
            STATUS      current
            DESCRIPTION
                "The number of Received V2 Leaves."
            ::= { iIgmpSnoopingStatisticsEntry 10 }

    -- 1.3.6.1.4.1.37552.4.2.110.1.50
    iIgmpGroupsInfoTable OBJECT-TYPE
        SYNTAX      SEQUENCE OF IIgmpGroupsInfoEntry
        MAX-ACCESS  not-accessible
        STATUS      current
        DESCRIPTION
            "This table shows IGMP snooping groups information."
        ::= { iIgmpSnooping 50 }

    -- 1.3.6.1.4.1.37552.4.2.110.1.50.1
    iIgmpGroupsInfoEntry OBJECT-TYPE
        SYNTAX      IIgmpGroupsInfoEntry
        MAX-ACCESS  not-accessible
        STATUS      current
        DESCRIPTION
            "The Entry of IGMP snooping groups information."
        INDEX { iIgmpGroupsInfoIndex }
        ::= { iIgmpGroupsInfoTable 1 }

    IIgmpGroupsInfoEntry ::=
        SEQUENCE {
            iIgmpGroupsInfoIndex    Integer32,
            iIgmpGroupsInfoVlanID   Integer32,          
            iIgmpGroupsInfo         IpAddress,
            iIgmpGroupsPortMembers  DisplayString
        }

        -- 1.3.6.1.4.1.37552.4.2.110.1.50.1.1    
        iIgmpGroupsInfoIndex OBJECT-TYPE
            SYNTAX      Integer32 (1..4095)
            MAX-ACCESS  read-only
            STATUS      current
            DESCRIPTION
                "Entries in the IGMP group table."
            ::= { iIgmpGroupsInfoEntry 1 }

        -- 1.3.6.1.4.1.37552.4.2.110.1.50.1.2    
        iIgmpGroupsInfoVlanID OBJECT-TYPE
            SYNTAX      Integer32 (1..4095)
            MAX-ACCESS  read-only
            STATUS      current
            DESCRIPTION
                "VLAN ID of the group."
            ::= { iIgmpGroupsInfoEntry 2 }

        -- 1.3.6.1.4.1.37552.4.2.110.1.50.1.3    
        iIgmpGroupsInfo OBJECT-TYPE
            SYNTAX      IpAddress
            MAX-ACCESS  read-only
            STATUS      current
            DESCRIPTION
                "Group address of the entry."
            ::= { iIgmpGroupsInfoEntry 3 }

        -- 1.3.6.1.4.1.37552.4.2.110.1.50.1.4    
        iIgmpGroupsPortMembers OBJECT-TYPE
            SYNTAX      DisplayString
            MAX-ACCESS  read-only
            STATUS      current
            DESCRIPTION
                "Ports under this group."
            ::= { iIgmpGroupsInfoEntry 4 }

    -- 1.3.6.1.4.1.37552.4.2.110.1.60
    iIgmpSfmInfoTable OBJECT-TYPE
        SYNTAX      SEQUENCE OF IIgmpSfmInfoEntry
        MAX-ACCESS  not-accessible
        STATUS      current
        DESCRIPTION
            "This table shows IGMP SSM(Source-Filtered Multicast) information.
             The IGMP SFM Information Table also contains the SSM(Source-Specific Multicast) information."
        ::= { iIgmpSnooping 60 }

    -- 1.3.6.1.4.1.37552.4.2.110.1.60.1
    iIgmpSfmInfoEntry OBJECT-TYPE
        SYNTAX      IIgmpSfmInfoEntry
        MAX-ACCESS  not-accessible
        STATUS      current
        DESCRIPTION
            "The Entry of IGMP SSM information."
        INDEX { iIgmpSfmInfoIndex }
        ::= { iIgmpSfmInfoTable 1 }

    IIgmpSfmInfoEntry ::=
        SEQUENCE {
            iIgmpSfmInfoIndex              Integer32,
            iIgmpSfmInfoVlanID             Integer32,
            iIgmpSfmInfoGroup              IpAddress,          
            iIgmpSfmPortNumber             Integer32,
            iIgmpSfmMode                   INTEGER,
            iIgmpSfmSourceAddress          IpAddress,
            iIgmpSfmType                   INTEGER,
            iIgmpSfmHardwareFilterSwitch   INTEGER
        }

        -- 1.3.6.1.4.1.37552.4.2.110.1.60.1.1    
        iIgmpSfmInfoIndex OBJECT-TYPE
            SYNTAX      Integer32 (1..4095)
            MAX-ACCESS  read-only
            STATUS      current
            DESCRIPTION
                "Entries in the IGMP SSM information table."
            ::= { iIgmpSfmInfoEntry 1 }

        -- 1.3.6.1.4.1.37552.4.2.110.1.60.1.2    
        iIgmpSfmInfoVlanID OBJECT-TYPE
            SYNTAX      Integer32 (1..4095)
            MAX-ACCESS  read-only
            STATUS      current
            DESCRIPTION
                "VLAN ID of the group."
            ::= { iIgmpSfmInfoEntry 2 }

        -- 1.3.6.1.4.1.37552.4.2.110.1.60.1.3    
        iIgmpSfmInfoGroup OBJECT-TYPE
            SYNTAX      IpAddress
            MAX-ACCESS  read-only
            STATUS      current
            DESCRIPTION
                "Group address of the entry."
            ::= { iIgmpSfmInfoEntry 3 }

        -- 1.3.6.1.4.1.37552.4.2.110.1.60.1.4    
        iIgmpSfmPortNumber OBJECT-TYPE
            SYNTAX      Integer32 (1..6)
            MAX-ACCESS  read-only
            STATUS      current
            DESCRIPTION
                "Switch port number."
            ::= { iIgmpSfmInfoEntry 4 }

        -- 1.3.6.1.4.1.37552.4.2.110.1.60.1.5    
        iIgmpSfmMode OBJECT-TYPE
            SYNTAX      INTEGER {
                            exclude(1),
                            include(2)
                        }
            MAX-ACCESS  read-only
            STATUS      current
            DESCRIPTION
                "Indicates the filtering mode maintained per (VLAN ID, port number, Group Address) basis.
                 It can be either Include or Exclude."
            ::= { iIgmpSfmInfoEntry 5 }

        -- 1.3.6.1.4.1.37552.4.2.110.1.60.1.6    
        iIgmpSfmSourceAddress OBJECT-TYPE
            SYNTAX      IpAddress
            MAX-ACCESS  read-only
            STATUS      current
            DESCRIPTION
                "IP Address of the source.
                 Currently, system limits the total number of IP source addresses for filtering to be 128."
            ::= { iIgmpSfmInfoEntry 6 }

        -- 1.3.6.1.4.1.37552.4.2.110.1.60.1.7    
        iIgmpSfmType OBJECT-TYPE
            SYNTAX      INTEGER {
                            deny(1),
                            allow(2)
                        }
            MAX-ACCESS  read-only
            STATUS      current
            DESCRIPTION
                "Indicates the Type. It can be either Allow or Deny."
            ::= { iIgmpSfmInfoEntry 7 }

        -- 1.3.6.1.4.1.37552.4.2.110.1.60.1.8    
        iIgmpSfmHardwareFilterSwitch OBJECT-TYPE
            SYNTAX      INTEGER {
                            no(1),
                            yes(2)
                        }
            MAX-ACCESS  read-only
            STATUS      current
            DESCRIPTION
                "Indicates whether data plane destined to the specific group address from
                 the source IPv4 address could be handled by chip or not."
            ::= { iIgmpSfmInfoEntry 8 }



-- VLANs                     
	-- 1.3.6.1.4.1.37552.4.2.140
    iVLANs  OBJECT IDENTIFIER ::= { msw4424C 140 }
    	
    	-- 1.3.6.1.4.1.37552.4.2.140.1
        iVlanAllowedAccessVLANs OBJECT-TYPE
        SYNTAX      DisplayString
        MAX-ACCESS  read-write
        STATUS      current
        DESCRIPTION
            "This field shows the allowed Access VLANs, i.e. it only affects ports configured as Access ports. 
            Ports in other modes are members of all VLANs specified in the Allowed VLANs field. 
            By default, only VLAN 1 is enabled. 
            More VLANs may be created by using a list syntax where the individual elements are separated by commas. 
            Ranges are specified with a dash separating the lower and upper bound.
			The following example will create VLANs 1, 10, 11, 12, 13, 200, and 300: 1,10-13,200,300. 
			Spaces are allowed in between the delimiters."
        ::= { iVLANs 1 }           
        
	-- 1.3.6.1.4.1.37552.4.2.140.2
    iVlanEthertype OBJECT-TYPE
        SYNTAX      DisplayString
        MAX-ACCESS  read-write
        STATUS      current
        DESCRIPTION
            "The ether type used for Custom S-ports.
             This is a global setting for all the Custom S-ports.
             The format of 'Ethernet Type' is restricted to 0x600-0xFFFF"
        ::= { iVLANs 2 }             
        
	-- 1.3.6.1.4.1.37552.4.2.140.3
    iVlanConfTable OBJECT-TYPE
        SYNTAX      SEQUENCE OF IVlanConfEntry
        MAX-ACCESS  not-accessible
        STATUS      current
        DESCRIPTION
            "The VLAN configuration can be monitored and modified here."
        ::= { iVLANs 3 }

    -- 1.3.6.1.4.1.37552.4.2.140.3.1
    iVlanConfEntry OBJECT-TYPE
        SYNTAX      IVlanConfEntry
        MAX-ACCESS  not-accessible
        STATUS      current
        DESCRIPTION
            "The Entry of VLAN configuration."
        INDEX { iPortIndex }
        ::= { iVlanConfTable 1 }

    IVlanConfEntry ::=
        SEQUENCE {       
            iVlanConfMode          INTEGER,          
            iVlanConfVlanID		   Integer32,
            iVlanConfPortType      INTEGER,
            iVlanConfRxFiltering   TruthValue,
            iVlanConfRxAccept      INTEGER,
            iVlanConfTxtag		   INTEGER,
            iVlanConfAllowVLANs    DisplayString,
            iVlanConfForbidVLANs   DisplayString
        }
        
        -- 1.3.6.1.4.1.37552.4.2.140.3.1.1
        iVlanConfMode OBJECT-TYPE
        SYNTAX      INTEGER {
                        access(1),
                        trunk(2),
                        hybird(3)
                     }
            MAX-ACCESS  read-write
            STATUS      current
            DESCRIPTION
                "Indicates the port vlan mode."
            ::= { iVlanConfEntry 1 }

		-- 1.3.6.1.4.1.37552.4.2.140.3.1.2
        iVlanConfVlanID OBJECT-TYPE
		SYNTAX      Integer32 (1..4095)
            MAX-ACCESS  read-write
            STATUS      current
            DESCRIPTION
                "Indicates the VLAN ID of this particular port."
            ::= { iVlanConfEntry 2 }     
            
		-- 1.3.6.1.4.1.37552.4.2.140.3.1.3
        iVlanConfPortType OBJECT-TYPE
        SYNTAX      INTEGER {
                        unaware(1),
                        c-port(2),
                        s-port(3),
                        s-custom-port(4)
                     }
            MAX-ACCESS  read-write
            STATUS      current
            DESCRIPTION
                "Indicates the port vlan type."
            ::= { iVlanConfEntry 3 }      
            
		 -- 1.3.6.1.4.1.37552.4.2.140.3.1.4
         iVlanConfRxFiltering OBJECT-TYPE
        	SYNTAX      TruthValue
            MAX-ACCESS  read-write
            STATUS      current
            DESCRIPTION
                "Indicates the port vlan rx filtering."
            ::= { iVlanConfEntry 4 } 
 
 		 -- 1.3.6.1.4.1.37552.4.2.140.3.1.5
         iVlanConfRxAccept OBJECT-TYPE
        	SYNTAX      INTEGER {
                        all(1),
                        tag-only(2),
                        untag-only(3)
                     }
            MAX-ACCESS  read-write
            STATUS      current
            DESCRIPTION
                "Indicates the port vlan rx acceptance."
            ::= { iVlanConfEntry 5 }
         
         -- 1.3.6.1.4.1.37552.4.2.140.3.1.6
         iVlanConfTxtag OBJECT-TYPE
        	SYNTAX      INTEGER {
                        untag-pvid(1),
                        tag-all(2),
                        untag-all(3)
                     }
            MAX-ACCESS  read-write
            STATUS      current
            DESCRIPTION
                "Indicates the port vlan tx tagging."
            ::= { iVlanConfEntry 6 }        
         
         -- 1.3.6.1.4.1.37552.4.2.140.3.1.7
         iVlanConfAllowVLANs OBJECT-TYPE
        	SYNTAX      DisplayString
            MAX-ACCESS  read-write
            STATUS      current
            DESCRIPTION
                "Ports in Trunk and Hybrid mode may control which VLANs they are allowed to become members of. 
                Access ports can only be member of one VLAN, the Access VLAN.
				The field's syntax is identical to the syntax used in the Enabled VLANs field. By default, 
				a Trunk or Hybrid port will become member of all VLANs, and is therefore set to 1-4095.
				The field may be left empty, which means that the port will not become member of any VLANs. "
            ::= { iVlanConfEntry 7 }  
         
         -- 1.3.6.1.4.1.37552.4.2.140.3.1.8
         iVlanConfForbidVLANs OBJECT-TYPE
        	SYNTAX      DisplayString
            MAX-ACCESS  read-write
            STATUS      current
            DESCRIPTION
                "A port may be configured to never be member of one or more VLANs. 
                By default, the field is left blank, which means that the port may become a member of all possible VLANs.  "
            ::= { iVlanConfEntry 8 }                          
     
     -- 1.3.6.1.4.1.37552.4.2.140.4.1.1
     iVlanMembershipTableUser OBJECT-TYPE
        SYNTAX      INTEGER {
                        combined(1),
                        admin(2),
                        nas(3),
                        gvrp(4),
                        mvr(5),
                        mep(6)
                     }
            MAX-ACCESS  read-write
            STATUS      current
            DESCRIPTION
                "Indicates the which one of VLAN membership table of user will be displayed."
      ::= { iVLANs 4 }

    -- 1.3.6.1.4.1.37552.4.2.140.5
    iVlanMembershipTable OBJECT-TYPE
        SYNTAX      SEQUENCE OF IVlanMembershipEntry
        MAX-ACCESS  not-accessible
        STATUS      current
        DESCRIPTION
            "The VLAN membership configuration can be monitored and modified here."
        ::= { iVLANs 5 }

    -- 1.3.6.1.4.1.37552.4.2.140.5.1
    iVlanMembershipEntry OBJECT-TYPE
        SYNTAX      IVlanMembershipEntry
        MAX-ACCESS  not-accessible
        STATUS      current
        DESCRIPTION
            "The Entry of VLAN memberships."
        INDEX { iVlanConfVlanID, iPortIndex }
        ::= { iVlanMembershipTable 1 }

    IVlanMembershipEntry ::=
        SEQUENCE {       
            iVlanMember            INTEGER
        }
         
        -- 1.3.6.1.4.1.37552.4.2.140.5.1.1
        iVlanMember OBJECT-TYPE
        SYNTAX      INTEGER {
        				nonmember(1),
                        member(2),
                        forbid(3),
                        conflict(4)
                    }
            MAX-ACCESS  read-only
            STATUS      current
            DESCRIPTION
               "A value for each port is displayed for each VLAN ID.
                If a port is not member in a VLAN , the following value is 1.
				If a port is included in a VLAN, the following value is 2.
				If a port is in the forbidden port list, the following value is 3.
				If a port is in the forbidden port list and at the same time attempted included in the VLAN, the following is 4. 
			   "
            ::= { iVlanMembershipEntry 1 }
        
    -- 1.3.6.1.4.1.37552.4.2.140.6
    iVlanPortTableUser OBJECT-TYPE
        SYNTAX      INTEGER {
                        combined(1),
                        admin(2),
                        nas(3),
                        gvrp(4),
                        mvr(5),
                        mstp(6),
                        erps(7),
                        vcl(8)
                     }
            MAX-ACCESS  read-write
            STATUS      current
            DESCRIPTION
                "Indicates the which one of VLAN port table of user will be displayed."
      ::= { iVLANs 6 }

    -- 1.3.6.1.4.1.37552.4.2.140.7
    iVlanPortTable OBJECT-TYPE
        SYNTAX      SEQUENCE OF IVlanPortEntry
        MAX-ACCESS  not-accessible
        STATUS      current
        DESCRIPTION
            "This table is used for showing status of the switch VLAN port."
        ::= { iVLANs 7 }

    -- 1.3.6.1.4.1.37552.4.2.140.7.1
    iVlanPortEntry OBJECT-TYPE
        SYNTAX      IVlanPortEntry
        MAX-ACCESS  not-accessible
        STATUS      current
        DESCRIPTION
            "The Entry of VLAN ports."
        INDEX { iPortIndex }
        ::= { iVlanPortTable 1 }

    IVlanPortEntry ::=
        SEQUENCE {
            iVlanPortType          		INTEGER,          
            iVlanPortIngressFiltering   TruthValue,
            iVlanPortFrameType     		INTEGER,
            iVlanPortVlanID        		Integer32,
            iVlanPortTxTag         		INTEGER,
            iVlanPortUntagVlanID   		Integer32,
            iVlanPortConflicts     		TruthValue
        }

        -- 1.3.6.1.4.1.37552.4.2.140.7.1.1    
        iVlanPortType OBJECT-TYPE
            SYNTAX      INTEGER {
                            unaware(1),
                            cPort(2),
                            sPort(3),
                            sCustomPort(4)
                        }
            MAX-ACCESS  read-only
            STATUS      current
            DESCRIPTION
                "Port can be one of the following types:
                 Unaware, Customer port(C-port), Service port(S-port), Custom Service port(S-custom-port)
                 If Port Type is Unaware, all frames are classified to the Port VLAN ID and tags are not removed."
            ::= { iVlanPortEntry 1 }

        -- 1.3.6.1.4.1.37552.4.2.140.7.1.2    
        iVlanPortIngressFiltering OBJECT-TYPE
            SYNTAX      TruthValue
            MAX-ACCESS  read-only
            STATUS      current
            DESCRIPTION
                "This parameter affects VLAN ingress processing.
                 If ingress filtering is checked and the ingress port is not a member of
                 the classified VLAN of the frame,
                 the frame is discarded. By default, ingress filtering is unchecked."   
            ::= { iVlanPortEntry 2 }

        -- 1.3.6.1.4.1.37552.4.2.140.7.1.3    
        iVlanPortFrameType OBJECT-TYPE
            SYNTAX      INTEGER {
                            all(1),
                            tagged(2),
                            untagged(3)
                        }
            MAX-ACCESS  read-only
            STATUS      current
            DESCRIPTION
                "Determines whether the port accepts all frames or only tagged/untagged frames.
                 This parameter affects VLAN ingress processing.
                 If the port only accepts tagged frames, untagged frames received on the port are discarded.
                 By default, the frame type is set to All."
            DEFVAL      { all }     
            ::= { iVlanPortEntry 3 }

        -- 1.3.6.1.4.1.37552.4.2.140.7.1.4    
        iVlanPortVlanID OBJECT-TYPE
            SYNTAX      Integer32 (0..4095)
            MAX-ACCESS  read-only
            STATUS      current
            DESCRIPTION
                "Configures the VLAN identifier for the port.
                 The allowed values are 0 through 4095. The default value is 1.
                 
                 If the value is 0, a VLAN tag with the classified VLAN ID is inserted in frames transmitted on the port.                 
                 This mode is normally used for ports connected to VLAN aware switches.
                 IMPORTANT: 'Port Tx Tag' should be set to 'untagPvid(1)' when this value is used.
                 
                 If the value are 1 through 4095, untagged frames received on the port are classified to the Port VLAN ID.
                 If VLAN awareness is disabled, all frames received on the port are classified to the Port VLAN ID.
                 If the classified VLAN ID of a frame transmitted on the port is different from the Port VLAN ID,
                 a VLAN tag with the classified VLAN ID is inserted in the frame."
            DEFVAL      { 1 }     
            ::= { iVlanPortEntry 4 }

        -- 1.3.6.1.4.1.37552.4.2.140.7.1.5
        iVlanPortTxTag OBJECT-TYPE
            SYNTAX      INTEGER {
            				untagUvid(1),
                            untagPvid(2),
                            tagUvid(3),
                            tagPvid(4),
                            tagAll(5),
                            untagAll(6)
                        }
            MAX-ACCESS  read-only
            STATUS      current
            DESCRIPTION
                "Determines egress tagging of a port.
                 Untag_pvid - All VLANs except the configured PVID will be tagged.
                 Tag_pvid -  The configured PVID will be tagged. 
                 Tag_all - All VLANs are tagged.
                 Untag_all - All VLANs are untagged."
            DEFVAL      { untagPvid }     
            ::= { iVlanPortEntry 5 }
        
        -- 1.3.6.1.4.1.37552.4.2.140.7.1.6
        iVlanPortUntagVlanID OBJECT-TYPE
            SYNTAX      Integer32 (0..4095)
            MAX-ACCESS  read-only
            STATUS      current
            DESCRIPTION
                "If Tx Tag is overridden by the selected user and is set to Tag or Untag UVID, 
                then this field will show the VLAN ID the user wants to tag or untag on egress.
				The field is empty if not overridden by the selected user. "
            DEFVAL      { 1 }     
            ::= { iVlanPortEntry 6 }
            
        -- 1.3.6.1.4.1.37552.4.2.140.7.1.7
        iVlanPortConflicts OBJECT-TYPE
            SYNTAX      TruthValue
            MAX-ACCESS  read-only
            STATUS      current
            DESCRIPTION
                "Shows status of Conflicts whether exists or not.
                 When a Volatile VLAN User requests to set VLAN membership or VLAN port configuration,
                 the following conflicts can occur:
                 Functional Conflicts between features.
                 Conflicts due to hardware limitation.
                 Direct conflict between user modules."
            ::= { iVlanPortEntry 7 }
            
            
            
-- QoS
    -- 1.3.6.1.4.1.37552.4.2.170
    iQoS  OBJECT IDENTIFIER ::= { msw4424C 170 }

    -- 1.3.6.1.4.1.37552.4.2.170.1
    iQosPorts  OBJECT IDENTIFIER ::= { iQoS 1 }

    -- 1.3.6.1.4.1.37552.4.2.170.1.1
    iQosRxPortClassifiedTable OBJECT-TYPE
        SYNTAX      SEQUENCE OF IQosRxPortClassifiedEntry
        MAX-ACCESS  not-accessible
        STATUS      current
        DESCRIPTION
            "This table allows you to configure the basic QoS Ingress Classification settings for all ports."
        ::= { iQosPorts 1 }

    -- 1.3.6.1.4.1.37552.4.2.170.1.1.1
    iQosRxPortClassifiedEntry OBJECT-TYPE
        SYNTAX      IQosRxPortClassifiedEntry
        MAX-ACCESS  not-accessible
        STATUS      current
        DESCRIPTION
            "The port entry for which the configuration in table."
        INDEX { iPortIndex }
        ::= { iQosRxPortClassifiedTable 1 }

    IQosRxPortClassifiedEntry ::=
        SEQUENCE {
            iQosRxPortQosClass         Integer32,
            iQosRxPortDpLevel          Integer32,
            iQosRxPortPCP              Integer32,
            iQosRxPortDEI              Integer32,
            iQosRxPortTagClassified    INTEGER,
            iQosRxPortDscpBased        TruthValue
        }

        -- 1.3.6.1.4.1.37552.4.2.170.1.1.1.1    
        iQosRxPortQosClass OBJECT-TYPE
            SYNTAX      Integer32 (0..7)
            MAX-ACCESS  read-write
            STATUS      current
            DESCRIPTION
                "Controls the default QoS class,
                 i.e., the QoS class for frames not classified in any other way.
                 There is a one to one mapping between QoS class, queue and priority.
                 A QoS class of 0 (zero) has the lowest priority."
            ::= { iQosRxPortClassifiedEntry 1 }

        -- 1.3.6.1.4.1.37552.4.2.170.1.1.1.2    
        iQosRxPortDpLevel OBJECT-TYPE
            SYNTAX      Integer32 (0..1)
            MAX-ACCESS  read-write
            STATUS      current
            DESCRIPTION
                "Controls the default DP(Drop Precedence) level,
                 i.e., the DP level for frames not classified in any other way."
            ::= { iQosRxPortClassifiedEntry 2 }

        -- 1.3.6.1.4.1.37552.4.2.170.1.1.1.3    
        iQosRxPortPCP OBJECT-TYPE
            SYNTAX      Integer32 (0..7)
            MAX-ACCESS  read-write
            STATUS      current
            DESCRIPTION
                "Controls the default PCP(Priority Code Point) for untagged frames."
            ::= { iQosRxPortClassifiedEntry 3 }

        -- 1.3.6.1.4.1.37552.4.2.170.1.1.1.4    
        iQosRxPortDEI OBJECT-TYPE
            SYNTAX      Integer32 (0..1)
            MAX-ACCESS  read-write
            STATUS      current
            DESCRIPTION
                "Controls the default DEI(Data Encryption Standard) for untagged frames."
            ::= { iQosRxPortClassifiedEntry 4 }

        -- 1.3.6.1.4.1.37552.4.2.170.1.1.1.5    
        iQosRxPortTagClassified OBJECT-TYPE
            SYNTAX      INTEGER {
                            enabled(1),
                            disabled(2)
                        }
            MAX-ACCESS  read-write
            STATUS      current
            DESCRIPTION
                "The classification mode for tagged frames on this port.
                 Disabled: Use default QoS class and DP level for tagged frames.
                 Enabled: Use mapped versions of PCP and DEI for tagged frames."
            ::= { iQosRxPortClassifiedEntry 5 }

        -- 1.3.6.1.4.1.37552.4.2.170.1.1.1.6    
        iQosRxPortDscpBased OBJECT-TYPE
            SYNTAX      TruthValue
            MAX-ACCESS  read-write
            STATUS      current
            DESCRIPTION
                "To enable DSCP Based QoS Ingress Port Classification."
            ::= { iQosRxPortClassifiedEntry 6 }

    -- 1.3.6.1.4.1.37552.4.2.170.1.2
    iQosRxPortTagMappingTable OBJECT-TYPE
        SYNTAX      SEQUENCE OF IQosRxPortTagMappingEntry
        MAX-ACCESS  not-accessible
        STATUS      current
        DESCRIPTION
            "The clasification mode for tagged frames are configured on this table."
        ::= { iQosPorts 2 }

    -- 1.3.6.1.4.1.37552.4.2.170.1.2.1
    iQosRxPortTagMappingEntry OBJECT-TYPE
        SYNTAX      IQosRxPortTagMappingEntry
        MAX-ACCESS  not-accessible
        STATUS      current
        DESCRIPTION
            "The port entry for which the configuration in table."
        INDEX { iPortIndex, iQosRxPortMappingOfPCP, iQosRxPortMappingOfDEI }
        ::= { iQosRxPortTagMappingTable 1 }

    IQosRxPortTagMappingEntry ::=
        SEQUENCE {
            iQosRxPortMappingOfPCP         Integer32,
            iQosRxPortMappingOfDEI         Integer32,
            iQosRxPortMappingToQosClass    Integer32,
            iQosRxPortMappingToDpLevel     Integer32
        }

        -- 1.3.6.1.4.1.37552.4.2.170.1.2.1.1    
        iQosRxPortMappingOfPCP OBJECT-TYPE
            SYNTAX      Integer32 (0..7)
            MAX-ACCESS  read-only
            STATUS      current
            DESCRIPTION
                "Controls the mapping of the PCP classified."
            ::= { iQosRxPortTagMappingEntry 1 }

        -- 1.3.6.1.4.1.37552.4.2.170.1.2.1.2    
        iQosRxPortMappingOfDEI OBJECT-TYPE
            SYNTAX      Integer32 (0..1)
            MAX-ACCESS  read-only
            STATUS      current
            DESCRIPTION
                "Controls the mapping of the DEI classified."
            ::= { iQosRxPortTagMappingEntry 2 }

        -- 1.3.6.1.4.1.37552.4.2.170.1.2.1.3    
        iQosRxPortMappingToQosClass OBJECT-TYPE
            SYNTAX      Integer32 (0..7)
            MAX-ACCESS  read-write
            STATUS      current
            DESCRIPTION
                "Controls the mapping to QoS class values."
            ::= { iQosRxPortTagMappingEntry 3 }

        -- 1.3.6.1.4.1.37552.4.2.170.1.2.1.4    
        iQosRxPortMappingToDpLevel OBJECT-TYPE
            SYNTAX      Integer32 (0..1)
            MAX-ACCESS  read-write
            STATUS      current
            DESCRIPTION
                "Controls the mapping to DP level values."
            ::= { iQosRxPortTagMappingEntry 4 }

    -- 1.3.6.1.4.1.37552.4.2.170.1.3
    iQosRxPortPolicersTable OBJECT-TYPE
        SYNTAX      SEQUENCE OF IQosRxPortPolicersEntry
        MAX-ACCESS  not-accessible
        STATUS      current
        DESCRIPTION
            "This table allows you to configure the Policer settings for all ports."
        ::= { iQosPorts 3 }

    -- 1.3.6.1.4.1.37552.4.2.170.1.3.1
    iQosRxPortPolicersEntry OBJECT-TYPE
        SYNTAX      IQosRxPortPolicersEntry
        MAX-ACCESS  not-accessible
        STATUS      current
        DESCRIPTION
            "The port entry for which the configuration in table."
        INDEX { iPortIndex }
        ::= { iQosRxPortPolicersTable 1 }

    IQosRxPortPolicersEntry ::=
        SEQUENCE {
            iQosRxPortPolicyEnabled        TruthValue,
            iQosRxPortPolicyRate           Integer32,
            iQosRxPortPolicyUnit           INTEGER
        }

        -- 1.3.6.1.4.1.37552.4.2.170.1.3.1.1    
        iQosRxPortPolicyEnabled OBJECT-TYPE
            SYNTAX      TruthValue
            MAX-ACCESS  read-write
            STATUS      current
            DESCRIPTION
                "Controls whether the policer is enabled on this switch port."
            ::= { iQosRxPortPolicersEntry 1 }

        -- 1.3.6.1.4.1.37552.4.2.170.1.3.1.2    
        iQosRxPortPolicyRate OBJECT-TYPE
            SYNTAX      Integer32 (100..3300000)
            MAX-ACCESS  read-write
            STATUS      current
            DESCRIPTION
                "Controls the rate for the policer. The default value is 500.
                 This value is restricted to 100-3300000."
            DEFVAL     { 500 }     
            ::= { iQosRxPortPolicersEntry 2 }

        -- 1.3.6.1.4.1.37552.4.2.170.1.3.1.3    
        iQosRxPortPolicyUnit OBJECT-TYPE
            SYNTAX      INTEGER {
                            kbps(1),
                            fps(2)
                        }
            MAX-ACCESS  read-write
            STATUS      current
            DESCRIPTION
                "Controls the unit of measure for the policer rate as kbps or fps.
                 The default value is 'kbps'."
            DEFVAL     { kbps }     
            ::= { iQosRxPortPolicersEntry 3 }

    -- 1.3.6.1.4.1.37552.4.2.170.1.4
    iQosTxPortSchedulerAndShaperTable OBJECT-TYPE
        SYNTAX      SEQUENCE OF IQosTxPortSchedulerAndShaperEntry
        MAX-ACCESS  not-accessible
        STATUS      current
        DESCRIPTION
            "This table allows you to configure the Scheduler Mode and Shaper for all ports."
        ::= { iQosPorts 4 }

    -- 1.3.6.1.4.1.37552.4.2.170.1.4.1
    iQosTxPortSchedulerAndShaperEntry OBJECT-TYPE
        SYNTAX      IQosTxPortSchedulerAndShaperEntry
        MAX-ACCESS  not-accessible
        STATUS      current
        DESCRIPTION
            "The port entry for which the configuration in table."
        INDEX { iPortIndex }
        ::= { iQosTxPortSchedulerAndShaperTable 1 }

    IQosTxPortSchedulerAndShaperEntry ::=
        SEQUENCE {
            iQosTxPortSchedulerMode    INTEGER,
            iQosTxPortShaperEnabled    TruthValue,
            iQosTxPortShaperRate       Integer32
        }

        -- 1.3.6.1.4.1.37552.4.2.170.1.4.1.1    
        iQosTxPortSchedulerMode OBJECT-TYPE
            SYNTAX      INTEGER {
                            strictPriority(1),
                            weighted(2)
                        }
            MAX-ACCESS  read-write
            STATUS      current
            DESCRIPTION
                "Controls whether the scheduler mode is 'Strict Priority' or 'Weighted' on this port."
            ::= { iQosTxPortSchedulerAndShaperEntry 1 }

        -- 1.3.6.1.4.1.37552.4.2.170.1.4.1.2    
        iQosTxPortShaperEnabled OBJECT-TYPE
            SYNTAX      TruthValue
            MAX-ACCESS  read-write
            STATUS      current
            DESCRIPTION
                "Controls whether the port shaper is enabled for this port."
            ::= { iQosTxPortSchedulerAndShaperEntry 2 }

        -- 1.3.6.1.4.1.37552.4.2.170.1.4.1.3    
        iQosTxPortShaperRate OBJECT-TYPE
            SYNTAX      Integer32 (100..3300000)
            UNITS       "kbps"
            MAX-ACCESS  read-write
            STATUS      current
            DESCRIPTION
                "Controls the rate for the shaper. The default value is 500 kbps.
                 This value is restricted to 100-3300000 kbps."
            DEFVAL     { 500 }     
            ::= { iQosTxPortSchedulerAndShaperEntry 3 }

    -- 1.3.6.1.4.1.37552.4.2.170.1.5
    iQosTxPortQueueSchedulerTable OBJECT-TYPE
        SYNTAX      SEQUENCE OF IQosTxPortQueueSchedulerEntry
        MAX-ACCESS  not-accessible
        STATUS      current
        DESCRIPTION
            "This table allows you to configure the Queue Scheduler Weight for all ports."
        ::= { iQosPorts 5 }

    -- 1.3.6.1.4.1.37552.4.2.170.1.5.1
    iQosTxPortQueueSchedulerEntry OBJECT-TYPE
        SYNTAX      IQosTxPortQueueSchedulerEntry
        MAX-ACCESS  not-accessible
        STATUS      current
        DESCRIPTION
            "The port entry for which the configuration in table."
        INDEX { iPortIndex, iQosTxPortQueueIndex }
        ::= { iQosTxPortQueueSchedulerTable 1 }

    IQosTxPortQueueSchedulerEntry ::=
        SEQUENCE {
            iQosTxPortQueueIndex       Integer32,
            iQosTxPortQueueWeight      Integer32,
            iQosTxPortQueuePercent     DisplayString
        }

        -- 1.3.6.1.4.1.37552.4.2.170.1.5.1.1    
        iQosTxPortQueueIndex OBJECT-TYPE
            SYNTAX      Integer32 (0..5)
            MAX-ACCESS  read-only
            STATUS      current
            DESCRIPTION
                "The egress Queue Scheduler index."
            ::= { iQosTxPortQueueSchedulerEntry 1 }

        -- 1.3.6.1.4.1.37552.4.2.170.1.5.1.2    
        iQosTxPortQueueWeight OBJECT-TYPE
            SYNTAX      Integer32 (1..100)
            MAX-ACCESS  read-write
            STATUS      current
            DESCRIPTION
                "Controls the weight for this queue. The default value is 17.
                 This value is restricted to 1-100.
                 This parameter is only affected if Scheduler Mode is set to 'Weighted'." 
            DEFVAL     { 17 }     
            ::= { iQosTxPortQueueSchedulerEntry 2 }

        -- 1.3.6.1.4.1.37552.4.2.170.1.5.1.3    
        iQosTxPortQueuePercent OBJECT-TYPE
            SYNTAX      DisplayString
            MAX-ACCESS  read-only
            STATUS      current
            DESCRIPTION
                "Shows the weight in percent for this queue.
                 This parameter is only shown if Scheduler Mode is set to 'Weighted'."
            ::= { iQosTxPortQueueSchedulerEntry 3 }

    -- 1.3.6.1.4.1.37552.4.2.170.1.6
    iQosTxPortQueueShapersTable OBJECT-TYPE
        SYNTAX      SEQUENCE OF IQosTxPortQueueShapersEntry
        MAX-ACCESS  not-accessible
        STATUS      current
        DESCRIPTION
            "This table allows you to configure the Scheduler Mode and Shaper for all ports."
        ::= { iQosPorts 6 }

    -- 1.3.6.1.4.1.37552.4.2.170.1.6.1
    iQosTxPortQueueShapersEntry OBJECT-TYPE
        SYNTAX      IQosTxPortQueueShapersEntry
        MAX-ACCESS  not-accessible
        STATUS      current
        DESCRIPTION
            "The port entry for which the configuration in table."
        INDEX { iPortIndex, iQosTxPortQueueIndex }
        ::= { iQosTxPortQueueShapersTable 1 }

    IQosTxPortQueueShapersEntry ::=
        SEQUENCE {
            iQosTxPortQueueShaperEnabled   TruthValue,
            iQosTxPortQueueShaperRate      Integer32,
            iQosTxPortQueueShaperExcess    TruthValue
        }

        -- 1.3.6.1.4.1.37552.4.2.170.1.6.1.1    
        iQosTxPortQueueShaperEnabled OBJECT-TYPE
            SYNTAX      TruthValue
            MAX-ACCESS  read-write
            STATUS      current
            DESCRIPTION
                "Controls whether the queue shaper is enabled for this queue on this port."
            ::= { iQosTxPortQueueShapersEntry 1 }

        -- 1.3.6.1.4.1.37552.4.2.170.1.6.1.2    
        iQosTxPortQueueShaperRate OBJECT-TYPE
            SYNTAX      Integer32 (100..3300000)
            UNITS       "kbps"
            MAX-ACCESS  read-write
            STATUS      current
            DESCRIPTION
                "Controls the rate for the queue shaper.
                 This parameter is only affected if Port Queue Mode is enabled.
                 This value is restricted to 100-3300000 kbps.
                 The default value is 500 kbps."
            DEFVAL     { 500 }     
            ::= { iQosTxPortQueueShapersEntry 2 }

        -- 1.3.6.1.4.1.37552.4.2.170.1.6.1.3    
        iQosTxPortQueueShaperExcess OBJECT-TYPE
            SYNTAX      TruthValue
            MAX-ACCESS  read-write
            STATUS      current
            DESCRIPTION
                "Controls whether the queue is allowed to use excess bandwidth.
                 This parameter is only affected if Port Queue Mode is enabled."
            ::= { iQosTxPortQueueShapersEntry 3 }

    -- 1.3.6.1.4.1.37552.4.2.170.1.7
    iQosTxPortTagRemarkingTable OBJECT-TYPE
        SYNTAX      SEQUENCE OF IQosTxPortTagRemarkingEntry
        MAX-ACCESS  not-accessible
        STATUS      current
        DESCRIPTION
            "This table allows you to configure the egress Port Tag Remarking for all ports."
        ::= { iQosPorts 7 }

    -- 1.3.6.1.4.1.37552.4.2.170.1.7.1
    iQosTxPortTagRemarkingEntry OBJECT-TYPE
        SYNTAX      IQosTxPortTagRemarkingEntry
        MAX-ACCESS  not-accessible
        STATUS      current
        DESCRIPTION
            "The port entry for which the configuration in table."
        INDEX { iPortIndex }
        ::= { iQosTxPortTagRemarkingTable 1 }

    IQosTxPortTagRemarkingEntry ::=
        SEQUENCE {
            iQosTxPortTagRemarkingMode     INTEGER
        }

        -- 1.3.6.1.4.1.37552.4.2.170.1.7.1.1    
        iQosTxPortTagRemarkingMode OBJECT-TYPE
            SYNTAX      INTEGER {
                            classified(1),
                            default(2),
                            mapped(3)
                        }
            MAX-ACCESS  read-write
            STATUS      current
            DESCRIPTION
                "Controls the tag remarking mode for this port.
                 Classified: Use classified PCP/DEI values.
                 Default: Use default PCP/DEI values.
                 Mapped: Use mapped versions of QoS class and DP level."
            ::= { iQosTxPortTagRemarkingEntry 1 }

    -- 1.3.6.1.4.1.37552.4.2.170.1.8
    iQosTxPortDefaultTagRemarkingTable OBJECT-TYPE
        SYNTAX      SEQUENCE OF IQosTxPortDefaultTagRemarkingEntry
        MAX-ACCESS  not-accessible
        STATUS      current
        DESCRIPTION
            "This table Controls the default PCP and DEI values used
             when the Remarking Mode is set to 'Default'."
        ::= { iQosPorts 8 }

    -- 1.3.6.1.4.1.37552.4.2.170.1.8.1
    iQosTxPortDefaultTagRemarkingEntry OBJECT-TYPE
        SYNTAX      IQosTxPortDefaultTagRemarkingEntry
        MAX-ACCESS  not-accessible
        STATUS      current
        DESCRIPTION
            "The port entry for which the configuration in table."
        INDEX { iPortIndex }
        ::= { iQosTxPortDefaultTagRemarkingTable 1 }

    IQosTxPortDefaultTagRemarkingEntry ::=
        SEQUENCE {
            iQosTxPortDefaultPcpRemarking  Integer32,
            iQosTxPortDefaultDeiRemarking  Integer32
        }

        -- 1.3.6.1.4.1.37552.4.2.170.1.8.1.1    
        iQosTxPortDefaultPcpRemarking OBJECT-TYPE
            SYNTAX      Integer32 (0..7)
            MAX-ACCESS  read-write
            STATUS      current
            DESCRIPTION
                "Controls the default PCP values used."
            ::= { iQosTxPortDefaultTagRemarkingEntry 1 }

        -- 1.3.6.1.4.1.37552.4.2.170.1.8.1.2    
        iQosTxPortDefaultDeiRemarking OBJECT-TYPE
            SYNTAX      Integer32 (0..1)
            MAX-ACCESS  read-write
            STATUS      current
            DESCRIPTION
                "Controls the default DEI values used."
            ::= { iQosTxPortDefaultTagRemarkingEntry 2 }

    -- 1.3.6.1.4.1.37552.4.2.170.1.9
    iQosTxPortMappingTagRemarkingTable OBJECT-TYPE
        SYNTAX      SEQUENCE OF IQosTxPortMappingTagRemarkingEntry
        MAX-ACCESS  not-accessible
        STATUS      current
        DESCRIPTION
            "This table controls the mapping of the classified (QoS class, DP level) to
             (PCP, DEI) values when the Remarking Mode is set to 'Mapped'"
        ::= { iQosPorts 9 }

    -- 1.3.6.1.4.1.37552.4.2.170.1.9.1
    iQosTxPortMappingTagRemarkingEntry OBJECT-TYPE
        SYNTAX      IQosTxPortMappingTagRemarkingEntry
        MAX-ACCESS  not-accessible
        STATUS      current
        DESCRIPTION
            "The port entry for which the configuration in table."
        INDEX { iPortIndex, iQosTxPortMappingOfQosClass, iQosTxPortMappingOfDpLevel }
        ::= { iQosTxPortMappingTagRemarkingTable 1 }

    IQosTxPortMappingTagRemarkingEntry ::=
        SEQUENCE {
            iQosTxPortMappingOfQosClass    Integer32,
            iQosTxPortMappingOfDpLevel     Integer32,
            iQosTxPortMappingToPCP         Integer32,
            iQosTxPortMappingToDEI         Integer32            
        }

        -- 1.3.6.1.4.1.37552.4.2.170.1.9.1.1    
        iQosTxPortMappingOfQosClass OBJECT-TYPE
            SYNTAX      Integer32 (0..7)
            MAX-ACCESS  read-only
            STATUS      current
            DESCRIPTION
                "Controls the mapping of the QoS class."
            ::= { iQosTxPortMappingTagRemarkingEntry 1 }

        -- 1.3.6.1.4.1.37552.4.2.170.1.9.1.2    
        iQosTxPortMappingOfDpLevel OBJECT-TYPE
            SYNTAX      Integer32 (0..1)
            MAX-ACCESS  read-only
            STATUS      current
            DESCRIPTION
                "Controls the mapping of the DP level."
            ::= { iQosTxPortMappingTagRemarkingEntry 2 }

        -- 1.3.6.1.4.1.37552.4.2.170.1.9.1.3    
        iQosTxPortMappingToPCP OBJECT-TYPE
            SYNTAX      Integer32 (0..7)
            MAX-ACCESS  read-write
            STATUS      current
            DESCRIPTION
                "Controls the mapping to PCP values."
            ::= { iQosTxPortMappingTagRemarkingEntry 3 }

        -- 1.3.6.1.4.1.37552.4.2.170.1.9.1.4    
        iQosTxPortMappingToDEI OBJECT-TYPE
            SYNTAX      Integer32 (0..1)
            MAX-ACCESS  read-write
            STATUS      current
            DESCRIPTION
                "Controls the mapping to DEI values."
            ::= { iQosTxPortMappingTagRemarkingEntry 4 }

    -- 1.3.6.1.4.1.37552.4.2.170.1.10
    iQosPortDscpConfigTable OBJECT-TYPE
        SYNTAX      SEQUENCE OF IQosPortDscpConfigEntry
        MAX-ACCESS  not-accessible
        STATUS      current
        DESCRIPTION
            "This table allows you to configure the basic QoS Port DSCP Configuration settings
             for all ports."
        ::= { iQosPorts 10 }

    -- 1.3.6.1.4.1.37552.4.2.170.1.10.1
    iQosPortDscpConfigEntry OBJECT-TYPE
        SYNTAX      IQosPortDscpConfigEntry
        MAX-ACCESS  not-accessible
        STATUS      current
        DESCRIPTION
            "The port entry for which the configuration in table."
        INDEX { iPortIndex }
        ::= { iQosPortDscpConfigTable 1 }

    IQosPortDscpConfigEntry ::=
        SEQUENCE {
            iQosPortDscpRxTranlateEnabled  TruthValue,
            iQosPortDscpRxClassifyMode     INTEGER,
            iQosPortDscpTxRewriteMode      INTEGER            
        }

        -- 1.3.6.1.4.1.37552.4.2.170.1.10.1.1    
        iQosPortDscpRxTranlateEnabled OBJECT-TYPE
            SYNTAX      TruthValue
            MAX-ACCESS  read-write
            STATUS      current
            DESCRIPTION
                "To Enable the Ingress Translation."
            ::= { iQosPortDscpConfigEntry 1 }

        -- 1.3.6.1.4.1.37552.4.2.170.1.10.1.2    
        iQosPortDscpRxClassifyMode OBJECT-TYPE
            SYNTAX      INTEGER {
                            disabled(1),
                            dscp0(2),
                            selected(3),
                            all(4)
                        }
            MAX-ACCESS  read-write
            STATUS      current
            DESCRIPTION
                "Classification for a port have 4 different values:
                 Disable: No Ingress DSCP Classification.
                 DSCP=0: Classify if incoming (or translated if enabled) DSCP is 0.
                 Selected: Classify only selected DSCP for which classification is enabled as
                           specified in DSCP Translation window for the specific DSCP.
                 All: Classify all DSCP."
            ::= { iQosPortDscpConfigEntry 2 }

        -- 1.3.6.1.4.1.37552.4.2.170.1.10.1.3    
        iQosPortDscpTxRewriteMode OBJECT-TYPE
            SYNTAX      INTEGER {
                            disabled(1),
                            enabled(2),
                            remapDpUnaware(3),
                            remapDpAware(4)
                        }
            MAX-ACCESS  read-write
            STATUS      current
            DESCRIPTION
                "Port Egress Rewriting can be one of -
                 Disable: No Egress rewrite.
                 Enable: Rewrite enable without remapped.
                 Remap DP Unaware: DSCP remarked with DSCP value from
                                   analyzer remapped through remap table .
                 Remap DP Aware: DSCP remarked with DSCP value from
                                 analyzer remapped through remap DP aware tables."
            ::= { iQosPortDscpConfigEntry 3 }


    -- 1.3.6.1.4.1.37552.4.2.170.2
    iQosDSCP  OBJECT IDENTIFIER ::= { iQoS 2 }

    -- 1.3.6.1.4.1.37552.4.2.170.2.1
    iQosDscpBasedRxClassifiedTable OBJECT-TYPE
        SYNTAX      SEQUENCE OF IQosDscpBasedRxClassifiedEntry
        MAX-ACCESS  not-accessible
        STATUS      current
        DESCRIPTION
            "This table allows you to configure
             the basic QoS DSCP based QoS Ingress Classification settings for all switches."
        ::= { iQosDSCP 1 }

    -- 1.3.6.1.4.1.37552.4.2.170.2.1.1
    iQosDscpBasedRxClassifiedEntry OBJECT-TYPE
        SYNTAX      IQosDscpBasedRxClassifiedEntry
        MAX-ACCESS  not-accessible
        STATUS      current
        DESCRIPTION
            "The DSCP values in table."
        INDEX { iQosDscpRx }
        ::= { iQosDscpBasedRxClassifiedTable 1 }

    IQosDscpBasedRxClassifiedEntry ::=
        SEQUENCE {
            iQosDscpRx             Integer32,
            iQosDscpRxTrusted      TruthValue,
            iQosDscpRxToQosClass   Integer32,
            iQosDscpRxToDPL        Integer32            
        }

        -- 1.3.6.1.4.1.37552.4.2.170.2.1.1.1    
        iQosDscpRx OBJECT-TYPE
            SYNTAX      Integer32 (0..63)
            MAX-ACCESS  read-only
            STATUS      current
            DESCRIPTION
                "Maximum number of supported DSCP values are 64
                 and valid DSCP value ranges from 0 to 63."
            ::= { iQosDscpBasedRxClassifiedEntry 1 }

        -- 1.3.6.1.4.1.37552.4.2.170.2.1.1.2    
        iQosDscpRxTrusted OBJECT-TYPE
            SYNTAX      TruthValue
            MAX-ACCESS  read-write
            STATUS      current
            DESCRIPTION
                "The DSCP value is trusted."
            ::= { iQosDscpBasedRxClassifiedEntry 2 }

        -- 1.3.6.1.4.1.37552.4.2.170.2.1.1.3    
        iQosDscpRxToQosClass OBJECT-TYPE
            SYNTAX      Integer32 (0..7)
            MAX-ACCESS  read-write
            STATUS      current
            DESCRIPTION
                "QoS Class value can be any of (0-7)."
            ::= { iQosDscpBasedRxClassifiedEntry 3 }

        -- 1.3.6.1.4.1.37552.4.2.170.2.1.1.4    
        iQosDscpRxToDPL OBJECT-TYPE
            SYNTAX      Integer32 (0..1)
            MAX-ACCESS  read-write
            STATUS      current
            DESCRIPTION
                "Drop Precedence Level (0-1)."
            ::= { iQosDscpBasedRxClassifiedEntry 4 }

    -- 1.3.6.1.4.1.37552.4.2.170.2.2
    iDscpTranslationTable OBJECT-TYPE
        SYNTAX      SEQUENCE OF IDscpTranslationEntry
        MAX-ACCESS  not-accessible
        STATUS      current
        DESCRIPTION
            "This table allows you to configure
             the basic QoS DSCP based QoS Ingress Classification settings for all switches."
        ::= { iQosDSCP 2 }

    -- 1.3.6.1.4.1.37552.4.2.170.2.2.1
    iDscpTranslationEntry OBJECT-TYPE
        SYNTAX      IDscpTranslationEntry
        MAX-ACCESS  not-accessible
        STATUS      current
        DESCRIPTION
            "The DSCP values in table."
        INDEX { iTranslatedDSCP }
        ::= { iDscpTranslationTable 1 }

    IDscpTranslationEntry ::=
        SEQUENCE {
            iTranslatedDSCP        Integer32,
            iDscpRxTranslation     Integer32,
            iDscpRxClassify        TruthValue,
            iDscpTxRemapDP0        Integer32,
            iDscpTxRemapDP1        Integer32            
        }

        -- 1.3.6.1.4.1.37552.4.2.170.2.2.1.1    
        iTranslatedDSCP OBJECT-TYPE
            SYNTAX      Integer32 (0..63)
            MAX-ACCESS  read-only
            STATUS      current
            DESCRIPTION
                "Maximum number of supported DSCP values are 64
                 and valid DSCP value ranges from 0 to 63."
            ::= { iDscpTranslationEntry 1 }

        -- 1.3.6.1.4.1.37552.4.2.170.2.2.1.2    
        iDscpRxTranslation OBJECT-TYPE
            SYNTAX      Integer32 (0..63)
            MAX-ACCESS  read-write
            STATUS      current
            DESCRIPTION
                "DSCP at Ingress side can be translated to any of (0-63) DSCP values."
            ::= { iDscpTranslationEntry 2 }

        -- 1.3.6.1.4.1.37552.4.2.170.2.1.1.3    
        iDscpRxClassify OBJECT-TYPE
            SYNTAX      TruthValue
            MAX-ACCESS  read-write
            STATUS      current
            DESCRIPTION
                "Enable Classification at Ingress side."
            ::= { iDscpTranslationEntry 3 }

        -- 1.3.6.1.4.1.37552.4.2.170.2.2.1.4    
        iDscpTxRemapDP0 OBJECT-TYPE
            SYNTAX      Integer32 (0..63)
            MAX-ACCESS  read-write
            STATUS      current
            DESCRIPTION
                "Select the DSCP value from select menu to which you want to remap.
                 DSCP value ranges form 0 to 63."
            ::= { iDscpTranslationEntry 4 }

        -- 1.3.6.1.4.1.37552.4.2.170.2.2.1.5    
        iDscpTxRemapDP1 OBJECT-TYPE
            SYNTAX      Integer32 (0..63)
            MAX-ACCESS  read-write
            STATUS      current
            DESCRIPTION
                "Select the DSCP value from select menu to which you want to remap.
                 DSCP value ranges form 0 to 63."
            ::= { iDscpTranslationEntry 5 }

    -- 1.3.6.1.4.1.37552.4.2.170.2.3
    iDscpClassificationTable OBJECT-TYPE
        SYNTAX      SEQUENCE OF IDscpClassificationEntry
        MAX-ACCESS  not-accessible
        STATUS      current
        DESCRIPTION
            "This table allows you to map DSCP value to a QoS Class and DPL value."
        ::= { iQosDSCP 3 }

    -- 1.3.6.1.4.1.37552.4.2.170.2.3.1
    iDscpClassificationEntry OBJECT-TYPE
        SYNTAX      IDscpClassificationEntry
        MAX-ACCESS  not-accessible
        STATUS      current
        DESCRIPTION
            "The entry of QoS Class and DPL value."
        INDEX { iMapedQosClass, iMapedDPL }
        ::= { iDscpClassificationTable 1 }

    IDscpClassificationEntry ::=
        SEQUENCE {
            iMapedQosClass     Integer32,
            iMapedDPL          Integer32,
            iClassifyDSCP      Integer32           
        }

        -- 1.3.6.1.4.1.37552.4.2.170.2.3.1.1    
        iMapedQosClass OBJECT-TYPE
            SYNTAX      Integer32 (0..7)
            MAX-ACCESS  read-only
            STATUS      current
            DESCRIPTION
                "Available QoS Class value ranges from 0 to 7."
            ::= { iDscpClassificationEntry 1 }

        -- 1.3.6.1.4.1.37552.4.2.170.2.3.1.2    
        iMapedDPL OBJECT-TYPE
            SYNTAX      Integer32 (0..1)
            MAX-ACCESS  read-only
            STATUS      current
            DESCRIPTION
                "Drop Precedence Level (0-1) can be configured for all available QoS Classes."
            ::= { iDscpClassificationEntry 2 }

        -- 1.3.6.1.4.1.37552.4.2.170.2.3.1.3    
        iClassifyDSCP OBJECT-TYPE
            SYNTAX      Integer32 (0..63)
            MAX-ACCESS  read-write
            STATUS      current
            DESCRIPTION
                "Select DSCP value (0-63) to map DSCP to corresponding QoS Class and DPL value."
            ::= { iDscpClassificationEntry 3 }


    -- 1.3.6.1.4.1.37552.4.2.170.3
    iQosControlList  OBJECT IDENTIFIER ::= { iQoS 3 }

    -- 1.3.6.1.4.1.37552.4.2.170.3.1
    iInsertQCE OBJECT-TYPE
        SYNTAX      DisplayString
        MAX-ACCESS  read-write
        STATUS      current
        DESCRIPTION                                  
            "Inserts a new QCE to list.
             Value 0: Add QCE to end of list.
             Value 1 ~ 256: Insert new QCE before this QCE ID."
        ::= { iQosControlList 1 }

    -- 1.3.6.1.4.1.37552.4.2.170.3.2
    iDeleteQCE OBJECT-TYPE
        SYNTAX      DisplayString
        MAX-ACCESS  read-write
        STATUS      current
        DESCRIPTION
            "Deletes the QCE by ID. "
        ::= { iQosControlList 2 }

    -- 1.3.6.1.4.1.37552.4.2.170.3.3
    iMoveQceDown OBJECT-TYPE
        SYNTAX      DisplayString
        MAX-ACCESS  read-write
        STATUS      current
        DESCRIPTION
            "Moves the QCE down the list."
        ::= { iQosControlList 3 }

    -- 1.3.6.1.4.1.37552.4.2.170.3.4
    iQceConfigTable OBJECT-TYPE
        SYNTAX      SEQUENCE OF IQceConfigEntry
        MAX-ACCESS  not-accessible
        STATUS      current
        DESCRIPTION
            "This table allows to edit QoS Control Entry.
             An QCE consists of several parameters.
             These parameters vary according to the frame type that you select."
        ::= { iQosControlList 4 }

    -- 1.3.6.1.4.1.37552.4.2.170.3.4.1
    iQceConfigEntry OBJECT-TYPE
        SYNTAX      IQceConfigEntry
        MAX-ACCESS  not-accessible
        STATUS      current
        DESCRIPTION
            "The entry of QoS Control List."
        INDEX { iQceIndex }
        ::= { iQceConfigTable 1 }

    IQceConfigEntry ::=
        SEQUENCE {
            iQceIndex                      Integer32,     -- row 1
            iQceID                         Integer32,
            iQcePortMembers                DisplayString,
            iQceKeyTagType                 INTEGER,
            iQceKeyVidMode                 INTEGER,
            iQceKeyVidSpecific             Integer32,
            iQceKeyVidStart                Integer32,
            iQceKeyVidLast                 Integer32,
            iQceKeyPCP                     INTEGER,
            iQceKeyDEI                     INTEGER,        -- row 10
            iQceKeySMacMode                INTEGER,        
            iQceKeySMacSpecific            DisplayString,  
            iQceKeyDMacType                INTEGER,
            iQceKeyFrameType               INTEGER,
            iQceKeyFrameEtherTypeMode      INTEGER,
            iQceKeyFrameEtherTypeSpecific  DisplayString,
            iQceKeyFrameLlcSSapMode        INTEGER,
            iQceKeyFrameLlcSSapAddress     DisplayString,
            iQceKeyFrameLlcDSapMode        INTEGER,
            iQceKeyFrameLlcDSapAddress     DisplayString,  -- row 20
            iQceKeyFrameLlcControlMode     INTEGER,        
            iQceKeyFrameLlcControl         DisplayString,  
            iQceKeyFrameSnapPidMode        INTEGER,
            iQceKeyFrameSnapPidSpecific    DisplayString,
            iQceKeyFrameIPv4Protocol       INTEGER,
            iQceKeyFrameIPv4SportMode      INTEGER,
            iQceKeyFrameIPv4SportSpecific  Integer32,
            iQceKeyFrameIPv4SportStart     Integer32,
            iQceKeyFrameIPv4SportLast      Integer32,
            iQceKeyFrameIPv4DportMode      INTEGER,        -- row 30
            iQceKeyFrameIPv4DportSpecific  Integer32,      
            iQceKeyFrameIPv4DportStart     Integer32,      
            iQceKeyFrameIPv4DportLast      Integer32,
            iQceKeyFrameIPv4OtherValue     Integer32,
            iQceKeyFrameIPv4SourceIpMode   INTEGER,
            iQceKeyFrameIPv4SourceIP       IpAddress,
            iQceKeyFrameIPv4SourceIpMask   IpAddress,
            iQceKeyFrameIPv4FragmentOption INTEGER,
            iQceKeyFrameIPv4DscpMode       INTEGER, 
            iQceKeyFrameIPv4DscpSpecific   Integer32,      -- row 40
            iQceKeyFrameIPv4DscpStart      Integer32,      
            iQceKeyFrameIPv4DscpLast       Integer32,      
            iQceKeyFrameIPv6Protocol       INTEGER,
            iQceKeyFrameIPv6SportMode      INTEGER,
            iQceKeyFrameIPv6SportSpecific  Integer32,
            iQceKeyFrameIPv6SportStart     Integer32,
            iQceKeyFrameIPv6SportLast      Integer32,
            iQceKeyFrameIPv6DportMode      INTEGER,
            iQceKeyFrameIPv6DportSpecific  Integer32,
            iQceKeyFrameIPv6DportStart     Integer32,      -- row 50
            iQceKeyFrameIPv6DportLast      Integer32,      
            iQceKeyFrameIPv6OtherValue     Integer32,      
            iQceKeyFrameIPv6SourceIpMode   INTEGER,
            iQceKeyFrameIPv6SourceIP       IpAddress,
            iQceKeyFrameIPv6SourceIpMask   IpAddress,
            iQceKeyFrameIPv6DscpMode       INTEGER, 
            iQceKeyFrameIPv6DscpSpecific   Integer32,
            iQceKeyFrameIPv6DscpStart      Integer32,
            iQceKeyFrameIPv6DscpLast       Integer32,
            iQceActionClass                Integer32,      -- row 60
            iQceActionDPL                  Integer32,      
            iQceActionDSCP                 Integer32       -- row 62
        }

        -- 1.3.6.1.4.1.37552.4.2.170.3.4.1.1    
        iQceIndex OBJECT-TYPE
            SYNTAX      Integer32 (1..256)
            MAX-ACCESS  read-only
            STATUS      current
            DESCRIPTION
                "Indicates the Index of QCE entry."
            ::= { iQceConfigEntry 1 }
        
        -- 1.3.6.1.4.1.37552.4.2.170.3.4.1.2    
        iQceID OBJECT-TYPE
            SYNTAX      Integer32 (1..256)
            MAX-ACCESS  read-only
            STATUS      current
            DESCRIPTION
                "Indicates the ID of QCE entry."
            ::= { iQceConfigEntry 2 }

        -- 1.3.6.1.4.1.37552.4.2.170.3.4.1.3    
        iQcePortMembers OBJECT-TYPE
            SYNTAX      DisplayString
            MAX-ACCESS  read-write
            STATUS      current                          
            DESCRIPTION
                "Indicates the port member of the QCL entry. By default all ports will be member."
            ::= { iQceConfigEntry 3 }

        -- 1.3.6.1.4.1.37552.4.2.170.3.4.1.4
        iQceKeyTagType OBJECT-TYPE
            SYNTAX      INTEGER {
                            any(1),
                            untag(2),
                            tag(3)
                        }
            MAX-ACCESS  read-write
            STATUS      current                          
            DESCRIPTION
                "Tag Type can be 'Any', 'Untag' or 'Tag'."
            ::= { iQceConfigEntry 4 }

        -- 1.3.6.1.4.1.37552.4.2.170.3.4.1.5    
        iQceKeyVidMode OBJECT-TYPE
            SYNTAX      INTEGER {
                            any(1),
                            specific(2),
                            range(3)
                        }
            MAX-ACCESS  read-write
            STATUS      current                          
            DESCRIPTION
                "VID Mode can be 'Any', 'Specific' or 'Range'."
            ::= { iQceConfigEntry 5 }

        -- 1.3.6.1.4.1.37552.4.2.170.3.4.1.6    
        iQceKeyVidSpecific OBJECT-TYPE
            SYNTAX      Integer32 (1..4095)
            MAX-ACCESS  read-write
            STATUS      current                          
            DESCRIPTION
                "VLAN ID can be any value in the range 1-4095 when Key VID Mode is 'Specific'."
            ::= { iQceConfigEntry 6 }

        -- 1.3.6.1.4.1.37552.4.2.170.3.4.1.7    
        iQceKeyVidStart OBJECT-TYPE
            SYNTAX      Integer32 (1..4094)
            MAX-ACCESS  read-write
            STATUS      current                          
            DESCRIPTION
                "The starting VID of range if Key VID Mode is 'Range'."
            ::= { iQceConfigEntry 7 }

        -- 1.3.6.1.4.1.37552.4.2.170.3.4.1.8    
        iQceKeyVidLast OBJECT-TYPE
            SYNTAX      Integer32 (2..4095)
            MAX-ACCESS  read-write
            STATUS      current                          
            DESCRIPTION
                "The last VID of range if Key VID Mode is 'Range'."
            ::= { iQceConfigEntry 8 }

        -- 1.3.6.1.4.1.37552.4.2.170.3.4.1.9    
        iQceKeyPCP OBJECT-TYPE
            SYNTAX      INTEGER {
                            any(1),
                            specific0(2),
                            specific1(3),
                            specific2(4),
                            specific3(5),
                            specific4(6),
                            specific5(7),
                            specific6(8),
                            specific7(9),
                            range0To1(10),
                            range2To3(11),
                            range4To5(12),
                            range6To7(13),
                            range0To3(14),
                            range4To7(15)
                        }   
            MAX-ACCESS  read-write
            STATUS      current                          
            DESCRIPTION
                "Priority Code Point: Valid value PCP are specific(0, 1, 2, 3, 4, 5, 6, 7) or
                 range(0-1, 2-3, 4-5, 6-7, 0-3, 4-7) or 'Any'."
            ::= { iQceConfigEntry 9 }

        -- 1.3.6.1.4.1.37552.4.2.170.3.4.1.10    
        iQceKeyDEI OBJECT-TYPE
            SYNTAX      INTEGER {
                            any(1),
                            specific0(2),
                            specific1(3)
                        }   
            MAX-ACCESS  read-write
            STATUS      current                          
            DESCRIPTION
                "Drop Eligible Indicator: Valid value of DEI can be any of values between 0, 1 or 'Any'."
            ::= { iQceConfigEntry 10 }

        -- 1.3.6.1.4.1.37552.4.2.170.3.4.1.11    
        iQceKeySMacMode OBJECT-TYPE
            SYNTAX      INTEGER {
                            any(1),
                            specific(2)
                        }   
            MAX-ACCESS  read-write
            STATUS      current                          
            DESCRIPTION
                "Source MAC address Mode: Valid value can be 'Any' or 'Specific'."
            ::= { iQceConfigEntry 11 }

        -- 1.3.6.1.4.1.37552.4.2.170.3.4.1.12    
        iQceKeySMacSpecific OBJECT-TYPE
            SYNTAX      DisplayString   
            MAX-ACCESS  read-write
            STATUS      current                          
            DESCRIPTION
                "Source MAC address: xx-xx-xx-xx-xx-xx or 'Any'. 
                 If a port is configured to match on DMAC/DIP, this field is the Destination MAC address
                "
            ::= { iQceConfigEntry 12 }

        -- 1.3.6.1.4.1.37552.4.2.170.3.4.1.13    
        iQceKeyDMacType OBJECT-TYPE
            SYNTAX      INTEGER {
                            any(1),
                            unicast(2),
                            multicast(3),
                            broadcast(4)
                        }   
            MAX-ACCESS  read-write
            STATUS      current                          
            DESCRIPTION
                "Destination MAC type: possible values are
                 'Unicast', 'Multicast', 'Broadcast' or 'Any'."
            ::= { iQceConfigEntry 13 }

        -- 1.3.6.1.4.1.37552.4.2.170.3.4.1.14    
        iQceKeyFrameType OBJECT-TYPE
            SYNTAX      INTEGER {
                            any(1),
                            ethernet(2),
                            llc(3),
                            snap(4),
                            ipv4(5),
                            ipv6(6)
                        }   
            MAX-ACCESS  read-write
            STATUS      current                          
            DESCRIPTION
                "Frame Type can have any of the following values:
                 Any, Ethernet, LLC, SNAP, IPv4 or IPv6"
            ::= { iQceConfigEntry 14 }

        -- 1.3.6.1.4.1.37552.4.2.170.3.4.1.15    
        iQceKeyFrameEtherTypeMode OBJECT-TYPE
            SYNTAX      INTEGER {
                            any(1),
                            specific(2)
                        }   
            MAX-ACCESS  read-write
            STATUS      current                          
            DESCRIPTION
                "If Key Frame Type is 'Ethernet', The Ether Type can be configured here.
                 Valid value can be 'Any' or 'Specific'.
                 The default value is 'Any'."
            DEFVAL     { any }     
            ::= { iQceConfigEntry 15 }

        -- 1.3.6.1.4.1.37552.4.2.170.3.4.1.16    
        iQceKeyFrameEtherTypeSpecific OBJECT-TYPE
            SYNTAX      DisplayString   
            MAX-ACCESS  read-write
            STATUS      current                          
            DESCRIPTION
                "If Key Frame Type is 'Ethernet', The Ether Type value can be configured here.
                 Valid ethernet type can have value within 0x600-0xFFFF,
                 but excluding 0x800(IPv4) and 0x86DD(IPv6)."
            ::= { iQceConfigEntry 16 }

        -- 1.3.6.1.4.1.37552.4.2.170.3.4.1.17    
        iQceKeyFrameLlcSSapMode OBJECT-TYPE
            SYNTAX      INTEGER {
                            any(1),
                            specific(2)
                        }   
            MAX-ACCESS  read-write
            STATUS      current                          
            DESCRIPTION
                "If Key Frame Type is 'LLC', The SSAP Address Mode can be configured here.
                 Valid value can be 'Any' or 'Specific'.
                 the default value is 'Any'."
            DEFVAL     { any }     
            ::= { iQceConfigEntry 17 }

        -- 1.3.6.1.4.1.37552.4.2.170.3.4.1.18    
        iQceKeyFrameLlcSSapAddress OBJECT-TYPE
            SYNTAX      DisplayString   
            MAX-ACCESS  read-write
            STATUS      current                          
            DESCRIPTION
                "If Key Frame Type is 'LLC', The SSAP Address can be configured here.
                 Valid SSAP(Source Service Access Point) can vary from 0x00 to 0xFF"
            ::= { iQceConfigEntry 18 }

        -- 1.3.6.1.4.1.37552.4.2.170.3.4.1.19    
        iQceKeyFrameLlcDSapMode OBJECT-TYPE
            SYNTAX      INTEGER {
                            any(1),
                            specific(2)
                        }   
            MAX-ACCESS  read-write
            STATUS      current                          
            DESCRIPTION
                "If Key Frame Type is 'LLC', The DSAP Address Mode can be configured here.
                 Valid value can be 'Any' or 'Specific'.
                 the default value is 'Any'."
            DEFVAL     { any }     
            ::= { iQceConfigEntry 19 }

        -- 1.3.6.1.4.1.37552.4.2.170.3.4.1.20    
        iQceKeyFrameLlcDSapAddress OBJECT-TYPE
            SYNTAX      DisplayString   
            MAX-ACCESS  read-write
            STATUS      current                          
            DESCRIPTION
                "If Key Frame Type is 'LLC', The DSAP Address can be configured here.
                 Valid DSAP(Destination  Service Access Point) can vary from 0x00 to 0xFF."
            ::= { iQceConfigEntry 20 }

        -- 1.3.6.1.4.1.37552.4.2.170.3.4.1.21    
        iQceKeyFrameLlcControlMode OBJECT-TYPE
            SYNTAX      INTEGER {
                            any(1),
                            specific(2)
                        }   
            MAX-ACCESS  read-write
            STATUS      current                          
            DESCRIPTION
                "If Key Frame Type is 'LLC', The Control Mode can be configured here.
                 Valid value can be 'Any' or 'Specific'.
                 the default value is 'Any'."
            DEFVAL     { any }     
            ::= { iQceConfigEntry 21 }

        -- 1.3.6.1.4.1.37552.4.2.170.3.4.1.22    
        iQceKeyFrameLlcControl OBJECT-TYPE
            SYNTAX      DisplayString   
            MAX-ACCESS  read-write
            STATUS      current                          
            DESCRIPTION
                "If Key Frame Type is 'LLC', The Control Address can be configured here.
                 Valid Control Address can vary from 0x00 to 0xFF."
            ::= { iQceConfigEntry 22 }

        -- 1.3.6.1.4.1.37552.4.2.170.3.4.1.23    
        iQceKeyFrameSnapPidMode OBJECT-TYPE
            SYNTAX      INTEGER {
                            any(1),
                            specific(2)
                        }   
            MAX-ACCESS  read-write
            STATUS      current                          
            DESCRIPTION
                "If Key Frame Type is 'SNAP', The SNAP PID Mode can be configured here.
                 Valid value can be 'Any' or 'Specific'.
                 The default value is 'Any'."
            DEFVAL     { any }     
            ::= { iQceConfigEntry 23 }

        -- 1.3.6.1.4.1.37552.4.2.170.3.4.1.24    
        iQceKeyFrameSnapPidSpecific OBJECT-TYPE
            SYNTAX      DisplayString   
            MAX-ACCESS  read-write
            STATUS      current                          
            DESCRIPTION
                "If Key Frame Type is 'SNAP', The PID can be configured here.
                 Valid PID(a.k.a ethernet type) can have value within 0x00-0xFFFF"
            ::= { iQceConfigEntry 24 }

        -- 1.3.6.1.4.1.37552.4.2.170.3.4.1.25    
        iQceKeyFrameIPv4Protocol OBJECT-TYPE
            SYNTAX      INTEGER {
                            any(1),
                            udp(2),
                            tcp(3),
                            other(4)
                        }   
            MAX-ACCESS  read-write
            STATUS      current                          
            DESCRIPTION
                "If Key Frame Type is 'IPv4', The Protocol Number can be configured here.
                 IP protocol number can be 'Other'(0-255), 'TCP', 'UDP' or 'Any',
                 the default value is 'Any'"
            DEFVAL     { any }     
            ::= { iQceConfigEntry 25 }

        -- 1.3.6.1.4.1.37552.4.2.170.3.4.1.26    
        iQceKeyFrameIPv4SportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Source TCP/UDP port mode can be configured here.
                 Source TCP/UDP port Mode can be 'Any', 'Specific' or 'Range',
                 the default value is 'Any'"
            DEFVAL     { any }     
            ::= { iQceConfigEntry 26 }

        -- 1.3.6.1.4.1.37552.4.2.170.3.4.1.27    
        iQceKeyFrameIPv4SportSpecific OBJECT-TYPE
            SYNTAX      Integer32 (0..65535)
            MAX-ACCESS  read-write
            STATUS      current                          
            DESCRIPTION
                "If Key Frame Type is 'IPv4' and Protocol is either TCP or UDP,
                 the Source TCP/UDP port number can be configured here.
                 The Source TCP/UDP port number can be any value in the range 0-65535
                 when Source TCP/UDP port Mode is 'Specific'."
            ::= { iQceConfigEntry 27 }

        -- 1.3.6.1.4.1.37552.4.2.170.3.4.1.28    
        iQceKeyFrameIPv4SportStart OBJECT-TYPE
            SYNTAX      Integer32 (0..65534)
            MAX-ACCESS  read-write
            STATUS      current                          
            DESCRIPTION
                "If Key Frame Type is 'IPv4' and Protocol is either TCP or UDP,
                 the starting Source TCP/UDP port number of range can be configured here.
                 It is effectively when Source TCP/UDP port Mode is 'Range'."
            ::= { iQceConfigEntry 28 }

        -- 1.3.6.1.4.1.37552.4.2.170.3.4.1.29    
        iQceKeyFrameIPv4SportLast OBJECT-TYPE
            SYNTAX      Integer32 (1..65535)
            MAX-ACCESS  read-write
            STATUS      current                          
            DESCRIPTION
                "If Key Frame Type is 'IPv4' and Protocol is either TCP or UDP,
                 the last Source TCP/UDP port number of range can be configured here.
                 It is effectively when Source TCP/UDP port Mode is 'Range'."
            ::= { iQceConfigEntry 29 }

        -- 1.3.6.1.4.1.37552.4.2.170.3.4.1.30    
        iQceKeyFrameIPv4DportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Destination TCP/UDP port mode can be configured here.
                 Destination TCP/UDP port Mode can be 'Any', 'Specific' or 'Range',
                 the default value is 'Any'"
            DEFVAL     { any }     
            ::= { iQceConfigEntry 30 }

        -- 1.3.6.1.4.1.37552.4.2.170.3.4.1.31
        iQceKeyFrameIPv4DportSpecific OBJECT-TYPE
            SYNTAX      Integer32 (0..65535)
            MAX-ACCESS  read-write
            STATUS      current                          
            DESCRIPTION
                "If Key Frame Type is 'IPv4' and Protocol is either TCP or UDP,
                 the Destination TCP/UDP port number can be configured here.
                 The Destination TCP/UDP port number can be any value in the range 0-65535
                 when Destination TCP/UDP port Mode is 'Specific'."
            ::= { iQceConfigEntry 31 }

        -- 1.3.6.1.4.1.37552.4.2.170.3.4.1.32    
        iQceKeyFrameIPv4DportStart OBJECT-TYPE
            SYNTAX      Integer32 (0..65534)
            MAX-ACCESS  read-write
            STATUS      current                          
            DESCRIPTION
                "If Key Frame Type is 'IPv4' and Protocol is either TCP or UDP,
                 the starting Destination TCP/UDP port number of range can be configured here.
                 It is effectively when Destination TCP/UDP port Mode is 'Range'."
            ::= { iQceConfigEntry 32 }

        -- 1.3.6.1.4.1.37552.4.2.170.3.4.1.33    
        iQceKeyFrameIPv4DportLast OBJECT-TYPE
            SYNTAX      Integer32 (1..65535)
            MAX-ACCESS  read-write
            STATUS      current                          
            DESCRIPTION
                "If Key Frame Type is 'IPv4' and Protocol is either TCP or UDP,
                 the last Destination TCP/UDP port number of range can be configured here.
                 It is effectively when Destination TCP/UDP port Mode is 'Range'."
            ::= { iQceConfigEntry 33 }

        -- 1.3.6.1.4.1.37552.4.2.170.3.4.1.34    
        iQceKeyFrameIPv4OtherValue OBJECT-TYPE
            SYNTAX      Integer32 (0..255)
            MAX-ACCESS  read-write
            STATUS      current                          
            DESCRIPTION
                "The other IPv4 protocol numbercan be any value in the range 0-255
                 when IP Protocol is 'Other'."
            ::= { iQceConfigEntry 34 }

        -- 1.3.6.1.4.1.37552.4.2.170.3.4.1.35    
        iQceKeyFrameIPv4SourceIpMode OBJECT-TYPE
            SYNTAX      INTEGER {
                            any(1),
                            specific(2)
                        }
            MAX-ACCESS  read-write
            STATUS      current                          
            DESCRIPTION
                "IPv4 Source Address Mode can be 'Any' or 'Specific', default value is 'Any'"
            DEFVAL     { any }    
            ::= { iQceConfigEntry 35 }

        -- 1.3.6.1.4.1.37552.4.2.170.3.4.1.36    
        iQceKeyFrameIPv4SourceIP OBJECT-TYPE
            SYNTAX      IpAddress
            MAX-ACCESS  read-write
            STATUS      current                          
            DESCRIPTION
                "When IPv4 Source Address Mode is 'Specific',
                 The Source IP address can be configured here.
                 Source IP address is in the format x.y.z.w where x, y, z, and w
                 are decimal numbers between 0 and 255."
            ::= { iQceConfigEntry 36 }

        -- 1.3.6.1.4.1.37552.4.2.170.3.4.1.37    
        iQceKeyFrameIPv4SourceIpMask OBJECT-TYPE
            SYNTAX      IpAddress
            MAX-ACCESS  read-write
            STATUS      current                          
            DESCRIPTION
                "When IPv4 Source Address Mode is 'Specific',
                 The Source IP Address Mask can be configured here.
                 Mask is in the format x.y.z.w where x, y, z, and w are decimal numbers between 0 and 255.
                 When Mask is converted to a 32-bit binary string and read from left to right,
                 all bits following the first zero must also be zero."
            ::= { iQceConfigEntry 37 }

        -- 1.3.6.1.4.1.37552.4.2.170.3.4.1.38    
        iQceKeyFrameIPv4FragmentOption OBJECT-TYPE
            SYNTAX      INTEGER {
                            any(1),
                            yes(2),
                            no(3)
                        }
            MAX-ACCESS  read-write
            STATUS      current                          
            DESCRIPTION
                "IPv4 frame fragmented option can be 'Yes', 'No' or 'Any', default value is 'Any'"
            DEFVAL     { any }    
            ::= { iQceConfigEntry 38 }

        -- 1.3.6.1.4.1.37552.4.2.170.3.4.1.39    
        iQceKeyFrameIPv4DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { iQceConfigEntry 39 }

        -- 1.3.6.1.4.1.37552.4.2.170.3.4.1.40
        iQceKeyFrameIPv4DscpSpecific OBJECT-TYPE
            SYNTAX      Integer32 (0..63)
            MAX-ACCESS  read-write
            STATUS      current                          
            DESCRIPTION
                "The DSCP can be any value in the range 0-63 when DSCP Mode is 'Specific'."
            ::= { iQceConfigEntry 40 }

        -- 1.3.6.1.4.1.37552.4.2.170.3.4.1.41
        iQceKeyFrameIPv4DscpStart OBJECT-TYPE
            SYNTAX      Integer32 (0..62)
            MAX-ACCESS  read-write
            STATUS      current                          
            DESCRIPTION
                "The starting DSCP value of range,
                 it is effectively when IPv4 DSCP Mode is 'Range'."
            ::= { iQceConfigEntry 41 }

        -- 1.3.6.1.4.1.37552.4.2.170.3.4.1.42    
        iQceKeyFrameIPv4DscpLast OBJECT-TYPE
            SYNTAX      Integer32 (1..63)
            MAX-ACCESS  read-write
            STATUS      current                          
            DESCRIPTION
                "The last DSCP value of range,
                 it is effectively when IPv4 DSCP Mode is 'Range'."
            ::= { iQceConfigEntry 42 }

        -- 1.3.6.1.4.1.37552.4.2.170.3.4.1.43    
        iQceKeyFrameIPv6Protocol OBJECT-TYPE
            SYNTAX      INTEGER {
                            any(1),
                            udp(2),
                            tcp(3),
                            other(4)
                        }   
            MAX-ACCESS  read-write
            STATUS      current                          
            DESCRIPTION
                "If Key Frame Type is 'IPv6', The Protocol Number can be configured here.
                 IPv6 protocol number can be 'Other'(0-255), 'TCP', 'UDP' or 'Any',
                 the default value is 'Any'"
            DEFVAL     { any }     
            ::= { iQceConfigEntry 43 }

        -- 1.3.6.1.4.1.37552.4.2.170.3.4.1.44    
        iQceKeyFrameIPv6SportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Source TCP/UDP port mode can be configured here.
                 Source TCP/UDP port Mode can be 'Any', 'Specific' or 'Range',
                 the default value is 'Any'"
            DEFVAL     { any }     
            ::= { iQceConfigEntry 44 }

        -- 1.3.6.1.4.1.37552.4.2.170.3.4.1.45    
        iQceKeyFrameIPv6SportSpecific OBJECT-TYPE
            SYNTAX      Integer32 (0..65535)
            MAX-ACCESS  read-write
            STATUS      current                          
            DESCRIPTION
                "If Key Frame Type is 'IPv6' and Protocol is either TCP or UDP,
                 the Source TCP/UDP port number can be configured here.
                 The Source TCP/UDP port number can be any value in the range 0-65535
                 when Source TCP/UDP port Mode is 'Specific'."
            ::= { iQceConfigEntry 45 }

        -- 1.3.6.1.4.1.37552.4.2.170.3.4.1.46    
        iQceKeyFrameIPv6SportStart OBJECT-TYPE
            SYNTAX      Integer32 (0..65534)
            MAX-ACCESS  read-write
            STATUS      current                          
            DESCRIPTION
                "If Key Frame Type is 'IPv6' and Protocol is either TCP or UDP,
                 the starting Source TCP/UDP port number of range can be configured here.
                 It is effectively when Source TCP/UDP port Mode is 'Range'."
            ::= { iQceConfigEntry 46 }

        -- 1.3.6.1.4.1.37552.4.2.170.3.4.1.47    
        iQceKeyFrameIPv6SportLast OBJECT-TYPE
            SYNTAX      Integer32 (1..65535)
            MAX-ACCESS  read-write
            STATUS      current                          
            DESCRIPTION
                "If Key Frame Type is 'IPv6' and Protocol is either TCP or UDP,
                 the last Source TCP/UDP port number of range can be configured here.
                 It is effectively when Source TCP/UDP port Mode is 'Range'."
            ::= { iQceConfigEntry 47 }

        -- 1.3.6.1.4.1.37552.4.2.170.3.4.1.48    
        iQceKeyFrameIPv6DportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Destination TCP/UDP port mode can be configured here.
                 Destination TCP/UDP port Mode can be 'Any', 'Specific' or 'Range',
                 the default value is 'Any'"
            DEFVAL     { any }     
            ::= { iQceConfigEntry 48 }

        -- 1.3.6.1.4.1.37552.4.2.170.3.4.1.49    
        iQceKeyFrameIPv6DportSpecific OBJECT-TYPE
            SYNTAX      Integer32 (0..65535)
            MAX-ACCESS  read-write
            STATUS      current                          
            DESCRIPTION
                "If Key Frame Type is 'IPv6' and Protocol is either TCP or UDP,
                 the Destination TCP/UDP port number can be configured here.
                 The Destination TCP/UDP port number can be any value in the range 0-65535
                 when Destination TCP/UDP port Mode is 'Specific'."
            ::= { iQceConfigEntry 49 }

        -- 1.3.6.1.4.1.37552.4.2.170.3.4.1.50    
        iQceKeyFrameIPv6DportStart OBJECT-TYPE
            SYNTAX      Integer32 (0..65534)
            MAX-ACCESS  read-write
            STATUS      current                          
            DESCRIPTION
                "If Key Frame Type is 'IPv6' and Protocol is either TCP or UDP,
                 the starting Destination TCP/UDP port number of range can be configured here.
                 It is effectively when Destination TCP/UDP port Mode is 'Range'."
            ::= { iQceConfigEntry 50 }

        -- 1.3.6.1.4.1.37552.4.2.170.3.4.1.51    
        iQceKeyFrameIPv6DportLast OBJECT-TYPE
            SYNTAX      Integer32 (1..65535)
            MAX-ACCESS  read-write
            STATUS      current                          
            DESCRIPTION
                "If Key Frame Type is 'IPv6' and Protocol is either TCP or UDP,
                 the last Destination TCP/UDP port number of range can be configured here.
                 It is effectively when Destination TCP/UDP port Mode is 'Range'."
            ::= { iQceConfigEntry 51 }

        -- 1.3.6.1.4.1.37552.4.2.170.3.4.1.52    
        iQceKeyFrameIPv6OtherValue OBJECT-TYPE
            SYNTAX      Integer32 (0..255)
            MAX-ACCESS  read-write
            STATUS      current                          
            DESCRIPTION
                "The other IPv6 protocol numbercan be any value in the range 0-255
                 when IP Protocol is 'Other'."
            ::= { iQceConfigEntry 52 }

        -- 1.3.6.1.4.1.37552.4.2.170.3.4.1.53    
        iQceKeyFrameIPv6SourceIpMode OBJECT-TYPE
            SYNTAX      INTEGER {
                            any(1),
                            specific(2)
                        }
            MAX-ACCESS  read-write
            STATUS      current                          
            DESCRIPTION
                "IPv6 Source Address Mode can be 'Any' or 'Specific', default value is 'Any'"
            DEFVAL     { any }    
            ::= { iQceConfigEntry 53 }
                                           
        -- 1.3.6.1.4.1.37552.4.2.170.3.4.1.54
        iQceKeyFrameIPv6SourceIP OBJECT-TYPE
            SYNTAX      IpAddress
            MAX-ACCESS  read-write
            STATUS      current                          
            DESCRIPTION
                "When IPv6 Source Address Mode is 'Specific',
                 The Source IPv6 address(32 LS bits) can be configured here.
                 Source IPv6 address(32 LS bits) is in the format a.b.c.d."
            ::= { iQceConfigEntry 54 }

        -- 1.3.6.1.4.1.37552.4.2.170.3.4.1.55    
        iQceKeyFrameIPv6SourceIpMask OBJECT-TYPE
            SYNTAX      IpAddress
            MAX-ACCESS  read-write
            STATUS      current                          
            DESCRIPTION
                "When IPv6 Source Address Mode is 'Specific',
                 The Source IPv6 Address Mask(32 LS bits) can be configured here.
                 IP Mask(32 LS bits) is in the format a.b.c.d where a, b, c, and d
                 are decimal numbers between 0 and 255.
                 When Mask is converted to a 32-bit binary string and read from left to right,
                 all bits following the first zero must also be zero."
            ::= { iQceConfigEntry 55 }

        -- 1.3.6.1.4.1.37552.4.2.170.3.4.1.56    
        iQceKeyFrameIPv6DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { iQceConfigEntry 56 }

        -- 1.3.6.1.4.1.37552.4.2.170.3.4.1.57    
        iQceKeyFrameIPv6DscpSpecific OBJECT-TYPE
            SYNTAX      Integer32 (0..63)
            MAX-ACCESS  read-write
            STATUS      current                          
            DESCRIPTION
                "The DSCP can be any value in the range 0-63 when DSCP Mode is 'Specific'."
            ::= { iQceConfigEntry 57 }

        -- 1.3.6.1.4.1.37552.4.2.170.3.4.1.58    
        iQceKeyFrameIPv6DscpStart OBJECT-TYPE
            SYNTAX      Integer32 (0..62)
            MAX-ACCESS  read-write
            STATUS      current                          
            DESCRIPTION
                "The starting DSCP value of range,
                 it is effectively when IPv6 DSCP Mode is 'Range'."
            ::= { iQceConfigEntry 58 }

        -- 1.3.6.1.4.1.37552.4.2.170.3.4.1.59
        iQceKeyFrameIPv6DscpLast OBJECT-TYPE
            SYNTAX      Integer32 (1..63)
            MAX-ACCESS  read-write
            STATUS      current                          
            DESCRIPTION
                "The last DSCP value of range,
                 it is effectively when IPv6 DSCP Mode is 'Range'."
            ::= { iQceConfigEntry 59 }

        -- 1.3.6.1.4.1.37552.4.2.170.3.4.1.60
        iQceActionClass OBJECT-TYPE
            SYNTAX      Integer32 (-1 | 0..7)
            MAX-ACCESS  read-write
            STATUS      current                          
            DESCRIPTION
                "Valid QoS Class can be (0-7), the value -1 for default,
                 At least one of the Action Node(rcQceActionClass, iQceActionDPL and iQceActionDSCP)
                 must have non-default value!"
            ::= { iQceConfigEntry 60 }

        -- 1.3.6.1.4.1.37552.4.2.170.3.4.1.61    
        iQceActionDPL OBJECT-TYPE
            SYNTAX      Integer32 (-1 | 0..1)
            MAX-ACCESS  read-write
            STATUS      current                          
            DESCRIPTION
                "Valid DP Level can be (0-1), the value -1 for default,
                 At least one of the Action Node(rcQceActionClass, iQceActionDPL and iQceActionDSCP)
                 must have non-default value!"
            ::= { iQceConfigEntry 61 }

        -- 1.3.6.1.4.1.37552.4.2.170.3.4.1.62    
        iQceActionDSCP OBJECT-TYPE
            SYNTAX      Integer32 (-1 | 0..63)
            MAX-ACCESS  read-write
            STATUS      current                          
            DESCRIPTION
                "Valid DSCP value can be (0-63), the value -1 for default,
                 At least one of the Action Node(rcQceActionClass, iQceActionDPL and iQceActionDSCP)
                 must have non-default value!"
            ::= { iQceConfigEntry 62 }


    -- 1.3.6.1.4.1.37552.4.2.170.4
    iStormControl   OBJECT IDENTIFIER ::= { iQoS 4 }

    -- 1.3.6.1.4.1.37552.4.2.170.4.1
    iStormControlTable OBJECT-TYPE
        SYNTAX      SEQUENCE OF IStormControlEntry
        MAX-ACCESS  not-accessible
        STATUS      current
        DESCRIPTION
            "Storm control for the switch is configured on this table.
             There is a unicast storm rate control, multicast storm rate control,
             and a broadcast storm rate control. These only affect flooded frames,
             i.e. frames with a (VLAN ID, DMAC) pair not present on the MAC Address table.
             The configuration indicates the permitted packet rate for unicast, multicast or
             broadcast traffic across the switch."
        ::= { iStormControl 3 }

    -- 1.3.6.1.4.1.37552.4.2.170.4.1.1
    iStormControlEntry OBJECT-TYPE
        SYNTAX      IStormControlEntry
        MAX-ACCESS  not-accessible
        STATUS      current
        DESCRIPTION
            "The entry of frame type."
        INDEX { iStormControlIndex }
        ::= { iStormControlTable 1 }

    IStormControlEntry ::=
        SEQUENCE {
        		iStormControlIndex     Integer32,
            iStormControlUuicastEnable    TruthValue,
            iStormControlUuicastRate      INTEGER,
            iStormControlUuicastUnit      INTEGER,
            iStormControlBroadcastEnable    TruthValue,
            iStormControlBroadcastRate      INTEGER,
            iStormControlBroadcastUnit      INTEGER,
            iStormControlUnknownEnable    TruthValue,
            iStormControlUnknownRate      INTEGER,
            iStormControlUnknownUnit      INTEGER                        
        }
        
    	  -- 1.3.6.1.4.1.37552.4.2.170.4.1.1.1
        iStormControlIndex OBJECT-TYPE
            SYNTAX      Integer32 (1..29)
            MAX-ACCESS  read-only
            STATUS      current
            DESCRIPTION
                "The Index of the StormContro Port

                "
            ::= { iStormControlEntry 1 }
            

        -- 1.3.6.1.4.1.37552.4.2.170.4.1.1.2    
        iStormControlUuicastEnable OBJECT-TYPE
            SYNTAX      TruthValue
            MAX-ACCESS  read-write
            STATUS      current
            DESCRIPTION
                "Enable or disable the storm control status for the given frame type."
            ::= { iStormControlEntry 2 }

    	  -- 1.3.6.1.4.1.37552.4.2.170.4.1.1.3
        iStormControlUuicastRate OBJECT-TYPE
            SYNTAX      INTEGER 
            MAX-ACCESS  read-write
            STATUS      current
            DESCRIPTION
                "

                "
            ::= { iStormControlEntry 3 }       

        -- 1.3.6.1.4.1.37552.4.2.170.4.1.1.4    
        iStormControlUuicastUnit OBJECT-TYPE
            SYNTAX      INTEGER {
                            kbps(1),
                            mbps(2),
                            fps(3),
                            kfps(4)
                        }
            MAX-ACCESS  read-write
            STATUS      current
            DESCRIPTION
                "
                "
            ::= { iStormControlEntry 4 }            

        -- 1.3.6.1.4.1.37552.4.2.170.4.1.1.5    
        iStormControlBroadcastEnable OBJECT-TYPE
            SYNTAX      TruthValue
            MAX-ACCESS  read-write
            STATUS      current
            DESCRIPTION
                "Enable or disable the storm control status for the given frame type."
            ::= { iStormControlEntry 5 }

    	  -- 1.3.6.1.4.1.37552.4.2.170.4.1.1.6
        iStormControlBroadcastRate OBJECT-TYPE
            SYNTAX      INTEGER 
            MAX-ACCESS  read-write
            STATUS      current
            DESCRIPTION
                "

                "
            ::= { iStormControlEntry 6 }       

        -- 1.3.6.1.4.1.37552.4.2.170.4.1.1.7    
        iStormControlBroadcastUnit OBJECT-TYPE
            SYNTAX      INTEGER {
                            kbps(1),
                            mbps(2),
                            fps(3),
                            kfps(4)
                        }
            MAX-ACCESS  read-write
            STATUS      current
            DESCRIPTION
                "
                "
            ::= { iStormControlEntry 7 }
            
        -- 1.3.6.1.4.1.37552.4.2.170.4.1.1.8    
        iStormControlUnknownEnable OBJECT-TYPE
            SYNTAX      TruthValue
            MAX-ACCESS  read-write
            STATUS      current
            DESCRIPTION
                "Enable or disable the storm control status for the given frame type."
            ::= { iStormControlEntry 8 }

    	  -- 1.3.6.1.4.1.37552.4.2.170.4.1.1.9
        iStormControlUnknownRate OBJECT-TYPE
            SYNTAX      INTEGER 
            MAX-ACCESS  read-write
            STATUS      current
            DESCRIPTION
                "

                "
            ::= { iStormControlEntry 9 }       

        -- 1.3.6.1.4.1.37552.4.2.170.4.1.1.10    
        iStormControlUnknownUnit OBJECT-TYPE
            SYNTAX      INTEGER {
                            kbps(1),
                            mbps(2),
                            fps(3),
                            kfps(4)
                        }
            MAX-ACCESS  read-write
            STATUS      current
            DESCRIPTION
                "
                "
            ::= { iStormControlEntry 10 }              
            
                       	            
END
