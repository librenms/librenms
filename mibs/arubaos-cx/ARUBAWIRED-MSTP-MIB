--**MOD+************************************************************************
--* Module:    ARUBAWIRED-MSTP-MIB : MSTP MIB file
--*
--* (c) Copyright 2020-2021 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains MIB definition of ARUBAWIRED-MSTP-MIB
--*
--**MOD-************************************************************************

ARUBAWIRED-MSTP-MIB DEFINITIONS ::= BEGIN
IMPORTS
            MODULE-IDENTITY, OBJECT-TYPE, NOTIFICATION-TYPE,
            Integer32
                 FROM SNMPv2-SMI
            DateAndTime, DisplayString , MacAddress , TruthValue ,
            TEXTUAL-CONVENTION
                 FROM  SNMPv2-TC
            MODULE-COMPLIANCE , OBJECT-GROUP, NOTIFICATION-GROUP
                 FROM SNMPv2-CONF
            InterfaceIndex
                 FROM  IF-MIB
            wndFeatures
              FROM ARUBAWIRED-NETWORKING-OID;

arubaWiredMstpMIB MODULE-IDENTITY
        LAST-UPDATED "202006120000Z" -- June 12, 2020
        ORGANIZATION "HPE/Aruba Networking Division"
        CONTACT-INFO "Hewlett Packard Enterprise
                          3000 Hanover St.
                          Palo Alto, CA 94304-1112"
        DESCRIPTION
                     "This MIB module for Multiple Spanning
                      Tree Protocol(MSTP)."
        REVISION     "202006120000Z" -- June 12, 2020
        DESCRIPTION
                     "Added arubaWiredMstpPortTable and
                      arubaWiredMstpGroup to this MIB module"

        REVISION     "201801180000Z" -- February 18, 2020
        DESCRIPTION
                     "Initial version of this MIB module"
        ::= { wndFeatures 13 }

   PointToPoint ::= TEXTUAL-CONVENTION
       STATUS      current
       DESCRIPTION "
               forceTrue: This value indicates that the
               administrator requires the MAC to be treated as
               if it is connected to a point-to-point LAN segment,
               regardless of any indications to the contrary that
               are generated by the MAC entity.

               forceFalse: This value indicates that the
               administrator requires the MAC to be treated as
               if it is connected to a non-point-to-point LAN
               segment, regardless of any indications to the
               contrary that are generated by the MAC entity.

               auto: This value indicates that the administrator
               requires the point-to-point status of the MAC to be
               determined in accordance with the specific MAC
               procedures defined in 6.5."
       SYNTAX      INTEGER {
                        forceTrue(1),
                        forceFalse(2),
                        auto(3)
                      }

  -- Top-level structure of MIB
     arubaWiredMstpNotifications  OBJECT IDENTIFIER ::= { arubaWiredMstpMIB 0}
     arubaWiredMstpObjects        OBJECT IDENTIFIER ::= { arubaWiredMstpMIB 1}

     -- NOTIFICATIONS

     arubaWiredMstpNotificationTable OBJECT-TYPE
          SYNTAX          SEQUENCE OF ArubaWiredMstpNotificationEntry
          MAX-ACCESS      not-accessible
          STATUS          current
          DESCRIPTION
               "Information describing the Mstp configuration
               and statistics of the Instances and CIST."
          ::= { arubaWiredMstpObjects 1 }

     arubaWiredMstpNotificationEntry OBJECT-TYPE
          SYNTAX          ArubaWiredMstpNotificationEntry
          MAX-ACCESS      not-accessible
          STATUS          current
          DESCRIPTION
               "Information describing the Mstp
               events for trap generation."
          INDEX           { arubaWiredMstpId }
          ::= { arubaWiredMstpNotificationTable 1 }

     ArubaWiredMstpNotificationEntry ::= SEQUENCE {

          arubaWiredMstpPortName
               DisplayString,
          arubaWiredMstpInstanceID
               Integer32,
          arubaWiredMstpPortErrantBpduRxCount
               Integer32,
          arubaWiredMstpErrantBpduSrcMac
               MacAddress,
          arubaWiredMstpSuperiorBpduSrcPort
               DisplayString,
          arubaWiredMstpSuperiorBpduSrcMac
               MacAddress,
          arubaWiredMstpPortInstanceState
               DisplayString,
          arubaWiredMstpErrantBpduDetector
               INTEGER,
          arubaWiredMstpPortDesignatedBridge
               DisplayString,
          arubaWiredMstpOldPortRole
               DisplayString,
          arubaWiredMstpNewPortRole
              DisplayString,
          arubaWiredMstpTopoChangeTime
               DateAndTime,
          arubaWiredMstpPreviousRootBridgeID
               DisplayString,
          arubaWiredMstpNewRootBridgeID
               DisplayString,
          arubaWiredMstpRootBridgeChangeTimeStamp
               DateAndTime,
          arubaWiredMstpId
               Integer32
     }

     arubaWiredMstpPortName OBJECT-TYPE
          SYNTAX         DisplayString (SIZE (0..20))
          MAX-ACCESS     accessible-for-notify
          STATUS         current
          DESCRIPTION    "The port Name"
          ::= { arubaWiredMstpNotificationEntry 1 }

     arubaWiredMstpInstanceID OBJECT-TYPE
          SYNTAX         Integer32 (0..65)
          MAX-ACCESS     accessible-for-notify
          STATUS          current
          DESCRIPTION    "Unique identifier of the STP Instance."
          ::= { arubaWiredMstpNotificationEntry 2 }

     arubaWiredMstpPortErrantBpduRxCount OBJECT-TYPE
          SYNTAX          Integer32 (0..2147483647)
          MAX-ACCESS      accessible-for-notify
          STATUS          current
          DESCRIPTION     "The number of errant bpdu rx on the port
                    for the particular instance "
          ::= { arubaWiredMstpNotificationEntry 3 }

     arubaWiredMstpErrantBpduSrcMac OBJECT-TYPE
          SYNTAX      MacAddress
          MAX-ACCESS   accessible-for-notify
          STATUS       current
          DESCRIPTION  "Source MAC address of the port sending this
                    Errant trap."
          ::= { arubaWiredMstpNotificationEntry 4 }

     arubaWiredMstpSuperiorBpduSrcPort OBJECT-TYPE
          SYNTAX         DisplayString (SIZE (0..20))
          MAX-ACCESS     accessible-for-notify
          STATUS          current
          DESCRIPTION    "Port belonging to the Bridge, which
                    transmitted the superior BPDU."
          ::= { arubaWiredMstpNotificationEntry 5 }

     arubaWiredMstpSuperiorBpduSrcMac OBJECT-TYPE
          SYNTAX       MacAddress
          MAX-ACCESS   accessible-for-notify
          STATUS       current
          DESCRIPTION  "The source MAC address of the port
                    sending superior BPDU."
          ::= { arubaWiredMstpNotificationEntry 6 }

     arubaWiredMstpPortInstanceState OBJECT-TYPE
          SYNTAX          DisplayString (SIZE (0..20))
          MAX-ACCESS      accessible-for-notify
          STATUS          current
          DESCRIPTION     "State of the port for the particular Instance"
          ::= { arubaWiredMstpNotificationEntry 7 }

     arubaWiredMstpErrantBpduDetector OBJECT-TYPE
          SYNTAX       INTEGER{
                         bpduFilter (1),
                         bpduProtection (2)
                        }
          MAX-ACCESS   accessible-for-notify
          STATUS       current
          DESCRIPTION  "The identifier of the feature generating
                         Errant BPDU trap."
          ::= { arubaWiredMstpNotificationEntry 8 }

     arubaWiredMstpPortDesignatedBridge OBJECT-TYPE
          SYNTAX      DisplayString (SIZE (0..20))
          MAX-ACCESS   accessible-for-notify
          STATUS       current
          DESCRIPTION  "The designated bridge name for this STP instance."
          ::= { arubaWiredMstpNotificationEntry 9 }

     arubaWiredMstpOldPortRole OBJECT-TYPE
          SYNTAX      DisplayString (SIZE (0..20))
          MAX-ACCESS   accessible-for-notify
          STATUS       current
          DESCRIPTION  "The previous role of the port before
                    the Topology change.
                    Forwarding/Blocking/Err-DisabledState"
          ::= { arubaWiredMstpNotificationEntry 10 }

     arubaWiredMstpNewPortRole OBJECT-TYPE
          SYNTAX      DisplayString (SIZE (0..20))
          MAX-ACCESS   accessible-for-notify
          STATUS       current
          DESCRIPTION  "The new role of the port after the Topology change.
                    Forwarding/Blocking/Err-DisabledState"
          ::= { arubaWiredMstpNotificationEntry 11 }

     arubaWiredMstpTopoChangeTime OBJECT-TYPE
          SYNTAX      DateAndTime
          MAX-ACCESS   accessible-for-notify
          STATUS       current
          DESCRIPTION  "Time at which the Topology Change happened."
          ::= { arubaWiredMstpNotificationEntry 12 }

     arubaWiredMstpPreviousRootBridgeID OBJECT-TYPE
          SYNTAX       DisplayString (SIZE (0..20))
          MAX-ACCESS   accessible-for-notify
          STATUS       current
          DESCRIPTION  "Bridge ID of the Previous root,
                    before the Topology change."
          ::= { arubaWiredMstpNotificationEntry 13 }

     arubaWiredMstpNewRootBridgeID OBJECT-TYPE
          SYNTAX       DisplayString (SIZE (0..20))
          MAX-ACCESS   accessible-for-notify
          STATUS       current
          DESCRIPTION  "Bridge ID of the New root,
                    after the Topology change."
          ::= { arubaWiredMstpNotificationEntry 14 }

     arubaWiredMstpRootBridgeChangeTimeStamp OBJECT-TYPE
          SYNTAX       DateAndTime
          MAX-ACCESS   accessible-for-notify
          STATUS       current
          DESCRIPTION  "Time when the new root is elected."
          ::= { arubaWiredMstpNotificationEntry 15 }

     arubaWiredMstpId OBJECT-TYPE
          SYNTAX       Integer32 (0..65)
          MAX-ACCESS   not-accessible
          STATUS       current
          DESCRIPTION  "Instance ID"
          ::= { arubaWiredMstpNotificationEntry 16 }

     arubaWiredMstpErrantBpduReceived NOTIFICATION-TYPE
            OBJECTS     {arubaWiredMstpPortName,
                         arubaWiredMstpPortErrantBpduRxCount,
                         arubaWiredMstpErrantBpduSrcMac,
                         arubaWiredMstpPortInstanceState,
                         arubaWiredMstpErrantBpduDetector
                        }
            STATUS      current
            DESCRIPTION
                  "This Trap is generated when an unexpected (errant) BPDU
                  has been received on a port."
            ::= { arubaWiredMstpNotifications 1 }

     arubaWiredMstpInstanceTopologyChange NOTIFICATION-TYPE
            OBJECTS     {arubaWiredMstpPortName,
                         arubaWiredMstpInstanceID,
                         arubaWiredMstpOldPortRole,
                         arubaWiredMstpNewPortRole,
                         arubaWiredMstpTopoChangeTime
                        }
            STATUS      current
            DESCRIPTION
                  "Trap is generated when a Topology Change is detected in
                   the specified INSTANCE."
            ::= { arubaWiredMstpNotifications 2 }

     arubaWiredMstpCISTTopologyChange NOTIFICATION-TYPE
            OBJECTS     {arubaWiredMstpPortName,
                         arubaWiredMstpOldPortRole,
                         arubaWiredMstpNewPortRole,
                         arubaWiredMstpTopoChangeTime
                        }
            STATUS      current
            DESCRIPTION
                  "Trap is generated when a Topology
                         Change is detected in CIST."
            ::= { arubaWiredMstpNotifications 3 }

     arubaWiredMstpInstanceNewRoot NOTIFICATION-TYPE
            OBJECTS     {arubaWiredMstpInstanceID,
                         arubaWiredMstpPreviousRootBridgeID,
                         arubaWiredMstpNewRootBridgeID,
                         arubaWiredMstpRootBridgeChangeTimeStamp
                        }
            STATUS      current
            DESCRIPTION
                  "Trap generated when sending agent has become
                   the new root of spanning Tree for the specified INSTANCE;
                   the notification is sent by a bridge soon after its election
                   as the new root."
            ::= { arubaWiredMstpNotifications 4 }

     arubaWiredMstpCISTNewRoot NOTIFICATION-TYPE
            OBJECTS     {arubaWiredMstpPreviousRootBridgeID,
                         arubaWiredMstpNewRootBridgeID,
                         arubaWiredMstpRootBridgeChangeTimeStamp
                        }
            STATUS      current
            DESCRIPTION
                  "Trap generated when sending agent has become
                   the new root of spanning Tree for the specified CIST;
                   the notification is sent by a bridge soon after its election
                   as the new root."
            ::= { arubaWiredMstpNotifications 5 }

     arubaWiredMstpInstanceLoopGuardInconsistency NOTIFICATION-TYPE
            OBJECTS     {arubaWiredMstpPortName,
                         arubaWiredMstpInstanceID,
                         arubaWiredMstpPortDesignatedBridge
                        }
            STATUS      current
            DESCRIPTION
                  "Trap generated when a Loop Guard feature enabled port
                   receives superior BPDUs on its interface for a
                   given instance."
            ::= { arubaWiredMstpNotifications 6 }

     arubaWiredMstpCISTLoopGuardInconsistency NOTIFICATION-TYPE
            OBJECTS     {arubaWiredMstpPortName,
                         arubaWiredMstpPortDesignatedBridge
                        }
            STATUS      current
            DESCRIPTION
                  "Trap generated when a Loop Guard feature enabled port
                   receives superior BPDUs on its interface for CIST."
            ::= { arubaWiredMstpNotifications 7 }

     arubaWiredMstpInstanceRootGuardInconsistency NOTIFICATION-TYPE
            OBJECTS     {arubaWiredMstpPortName,
                         arubaWiredMstpInstanceID,
                         arubaWiredMstpSuperiorBpduSrcMac,
                         arubaWiredMstpSuperiorBpduSrcPort
                        }
            STATUS      current
            DESCRIPTION
                  "Trap generated when a Root Guard feature enabled port
                   receives superior BPDUs on its interface for a
                   given instance."
            ::= { arubaWiredMstpNotifications 8 }

     arubaWiredMstpCISTRootGuardInconsistency NOTIFICATION-TYPE
            OBJECTS     {arubaWiredMstpPortName,
                         arubaWiredMstpSuperiorBpduSrcMac,
                         arubaWiredMstpSuperiorBpduSrcPort
                        }
            STATUS      current
            DESCRIPTION
                  "Trap generated when a Root Guard feature enabled port
                   receives superior BPDUs on its interface for CIST."
            ::= { arubaWiredMstpNotifications 9 }

  -- Per Port Configuration

     arubaWiredMstpPortTable OBJECT-TYPE
          SYNTAX          SEQUENCE OF ArubaWiredMstpPortEntry
          MAX-ACCESS      not-accessible
          STATUS          current
          DESCRIPTION
               "Information describing the MSTP specific
               configuration and statistics of the ports."
          ::= { arubaWiredMstpObjects 2 }

     arubaWiredMstpPortEntry OBJECT-TYPE
          SYNTAX          ArubaWiredMstpPortEntry
          MAX-ACCESS      not-accessible
          STATUS          current
          DESCRIPTION
               "Information describing the MSTP specific
               configuration and statistics of the ports."
          INDEX           { arubaWiredMstpPortIndex }
          ::= { arubaWiredMstpPortTable 1 }

     ArubaWiredMstpPortEntry ::= SEQUENCE {
          arubaWiredMstpPortIndex                InterfaceIndex,
          arubaWiredMstpPortAdminEdge            TruthValue,
          arubaWiredMstpPortAdminPointToPoint    PointToPoint,
          arubaWiredMstpPortAutoEdge             TruthValue,
          arubaWiredMstpPortBpduFiltering        TruthValue,
          arubaWiredMstpPortRestrictedTcn        TruthValue,
          arubaWiredMstpPortRootGuard            TruthValue,
          arubaWiredMstpPortLoopGuard            TruthValue,
          arubaWiredMstpPortBpduProtection      TruthValue,
          arubaWiredMstpPortRpvstProtection      TruthValue,
          arubaWiredMstpPortRpvstFiltering       TruthValue
     }
     arubaWiredMstpPortIndex OBJECT-TYPE
          SYNTAX         InterfaceIndex
          MAX-ACCESS     not-accessible
          STATUS          current
          DESCRIPTION "  The port ifIndex "
          ::= { arubaWiredMstpPortEntry 1 }

     arubaWiredMstpPortAdminEdge OBJECT-TYPE
          SYNTAX          TruthValue
          MAX-ACCESS      read-write
          STATUS          current
          DESCRIPTION  "The administrative value of the Edge Port
               parameter. A value of true(1) indicates that this
               port should be assumed as an edge-port, and a
               value of false(2) indicates that this port
               should be assumed as a non-edge-port.
               Note that even when this object's value is true(1),
               the arubaWiredMstpOperEdgePort can be false(2) if a
               BPDU has been received."
          DEFVAL          { false }
          ::= { arubaWiredMstpPortEntry 2 }

     arubaWiredMstpPortAdminPointToPoint OBJECT-TYPE
          SYNTAX      PointToPoint
          MAX-ACCESS  read-write
          STATUS      current
          DESCRIPTION "Refer the PointToPoint textual-convention."
          REFERENCE
               "IEEE P802.1w; IEEE P802.1t"
          DEFVAL          { 3 }
          ::= { arubaWiredMstpPortEntry 3 }

     arubaWiredMstpPortAutoEdge OBJECT-TYPE
          SYNTAX          TruthValue
          MAX-ACCESS      read-write
          STATUS          current

          DESCRIPTION  "It is used by the Bridge
               detection state machine for the automatic
               identification of edge ports. "
          REFERENCE
          "IEEE 802.1D-2004"
          DEFVAL          { 1 }
          ::= { arubaWiredMstpPortEntry 4 }

     arubaWiredMstpPortBpduFiltering OBJECT-TYPE
          SYNTAX          TruthValue
          MAX-ACCESS      read-write
          STATUS          current
          DESCRIPTION "This value indicates whether or not
               BPDUs need to be filtered on this port and BPDU filter
               option forces a port to always stay in the forwarding
               state and be excluded from standard STP operation.
               If the value is true(1) the received BPDUs will
               be dropped and no BPDUs will be transmitted on
               the port. If the value is false (2)
               the BPDUs will be processed as usual. "
          REFERENCE
          "IEEE P802.1w"
          DEFVAL          { false }
          ::= { arubaWiredMstpPortEntry 5 }

     arubaWiredMstpPortRestrictedTcn OBJECT-TYPE
          SYNTAX          TruthValue
          MAX-ACCESS      read-write
          STATUS          current
          DESCRIPTION " This value indicates whether or not to
               propagate topology changes to other ports.
               true(1) causes the port not to propagate topology
               changes to other ports."
          REFERENCE "IEEE 802.1Q-REV/5.0 (13.25.15)"
          DEFVAL          { false }
          ::= { arubaWiredMstpPortEntry 6 }

     arubaWiredMstpPortRootGuard OBJECT-TYPE
          SYNTAX          TruthValue
          MAX-ACCESS      read-write
          STATUS          current
          DESCRIPTION " Setting this object to true(1) forces port
               to not to be selected as root port even if
               this port has the least path cost to the root. "
          DEFVAL          { false }
          ::= { arubaWiredMstpPortEntry 7 }

     arubaWiredMstpPortLoopGuard OBJECT-TYPE
          SYNTAX          TruthValue
          MAX-ACCESS      read-write
          STATUS          current
          DESCRIPTION "  Setting this object to true(1) causes the
               non-designated port to go into the STP loop inconsistent
               state instead of the forwarding state. In the
               loop-inconsistent state, the port prevents data traffic
               through the link, therefore avoiding the loop creation.
               When BPDUs again are received on the inconsistent port,
               it resumes normal STP operation automatically. "
          DEFVAL         { false }
          ::= { arubaWiredMstpPortEntry 8 }

     arubaWiredMstpPortBpduProtection OBJECT-TYPE
          SYNTAX          TruthValue
          MAX-ACCESS      read-write
          STATUS          current
          DESCRIPTION " Setting this true (1) indicates that no
               BPDUs are expected to be received on this port.
               At the reception of BPDUs the BPDU protection
               mechanism will disable this port and port will
               transition into BPDU Error state."
          DEFVAL         { false }
          ::= { arubaWiredMstpPortEntry 9 }

     arubaWiredMstpPortRpvstProtection OBJECT-TYPE
          SYNTAX          TruthValue
          MAX-ACCESS      read-write
          STATUS          current
          DESCRIPTION " Setting this true (1) indicates that no
               Rpvst-proprietary BPDUs are expected to be
               received on this port. At the reception of
               Rpvst-proprietary BPDUs the Rpvst protection
               mechanism will disable this port and port will
               transition into BPDU Error state."
          DEFVAL         { false }
          ::= { arubaWiredMstpPortEntry 10 }

     arubaWiredMstpPortRpvstFiltering OBJECT-TYPE
          SYNTAX          TruthValue
          MAX-ACCESS      read-write
          STATUS          current
          DESCRIPTION " This value indicates whether or not
               Rpvst-proprietary BPDUs need to be filtered on
               this port and Rpvst filter option forces
               a port to always stay in the forwarding state
               and be excluded from standard STP operation.
               If the value is true(1) the received BPDUs
               will be dropped and no BPDUs will be
               transmitted on the port. If the value
               is false (2) the BPDUs will be
               processed as usual."
          DEFVAL         { false }
          ::= { arubaWiredMstpPortEntry 11 }

    -- MSTP General Variables

    -- These parameters apply globally to the MSTP

    arubaWiredMstpGeneralGroup OBJECT IDENTIFIER ::= {arubaWiredMstpObjects 3}

     arubaWiredMstpBpduGuardTimeout OBJECT-TYPE
               SYNTAX          Integer32
               MAX-ACCESS      read-write
               STATUS          current
               DESCRIPTION     "Time in seconds until when a
                    port configured for BPDU-guard will be disabled,
                    upon receiving an STP BPDU. If BpduGuardtimeout
                    is not set, port will be in the
                    disabled state forever."
               ::= { arubaWiredMstpGeneralGroup 1 }


 -- Conformance Information

     arubaWiredMstpConformance OBJECT IDENTIFIER ::= { arubaWiredMstpMIB 2}
     arubaWiredMstpGroups OBJECT IDENTIFIER ::= { arubaWiredMstpConformance 1 }

     arubaWiredMstpNotificationObjectGroup   OBJECT-GROUP
         OBJECTS {  arubaWiredMstpPortName,
                    arubaWiredMstpInstanceID,
                    arubaWiredMstpPortErrantBpduRxCount,
                    arubaWiredMstpErrantBpduSrcMac,
                    arubaWiredMstpSuperiorBpduSrcPort,
                    arubaWiredMstpSuperiorBpduSrcMac,
                    arubaWiredMstpPortInstanceState,
                    arubaWiredMstpErrantBpduDetector,
                    arubaWiredMstpPortDesignatedBridge,
                    arubaWiredMstpOldPortRole,
                    arubaWiredMstpNewPortRole,
                    arubaWiredMstpTopoChangeTime,
                    arubaWiredMstpPreviousRootBridgeID,
                    arubaWiredMstpNewRootBridgeID,
                    arubaWiredMstpRootBridgeChangeTimeStamp
                   }
        STATUS          current
        DESCRIPTION   "Group of objects required for
                       notifications."
        ::= { arubaWiredMstpGroups 1 }

    arubaWiredMstpNotificationGroup   NOTIFICATION-GROUP
       NOTIFICATIONS { arubaWiredMstpErrantBpduReceived,
                       arubaWiredMstpInstanceNewRoot,
                       arubaWiredMstpCISTNewRoot,
                       arubaWiredMstpInstanceRootGuardInconsistency,
                       arubaWiredMstpCISTRootGuardInconsistency,
                       arubaWiredMstpInstanceLoopGuardInconsistency,
                       arubaWiredMstpCISTLoopGuardInconsistency,
                       arubaWiredMstpInstanceTopologyChange,
                       arubaWiredMstpCISTTopologyChange
                       }
       STATUS          current
       DESCRIPTION   "Group of notifications."
       ::= { arubaWiredMstpGroups 2 }

     arubaWiredMstpPortGroup OBJECT-GROUP
            OBJECTS       {
                           arubaWiredMstpPortAdminEdge,
                           arubaWiredMstpPortAdminPointToPoint,
                           arubaWiredMstpPortAutoEdge,
                           arubaWiredMstpPortBpduFiltering,
                           arubaWiredMstpPortRestrictedTcn,
                           arubaWiredMstpPortRootGuard,
                           arubaWiredMstpPortLoopGuard,
                           arubaWiredMstpPortBpduProtection,
                           arubaWiredMstpPortRpvstProtection,
                           arubaWiredMstpPortRpvstFiltering
                          }
            STATUS        current
            DESCRIPTION
                "These objects are used for managing/monitoring
                MSTP port parameters"
            ::= { arubaWiredMstpGroups 3 }

     arubaWiredMstpGroup OBJECT-GROUP
            OBJECTS         {
                              arubaWiredMstpBpduGuardTimeout
                            }
            STATUS          current
            DESCRIPTION
                   "These objects are used for monitoring
                    MSTP global parameters."
            ::= { arubaWiredMstpGroups 4 }

-- Compliance Statements

     arubaWiredMstpCompliances OBJECT IDENTIFIER ::=
                    {arubaWiredMstpConformance 2}

     arubaWiredMstpNotificationCompliance MODULE-COMPLIANCE
          STATUS      current
          DESCRIPTION "The compliance statement
                    for Mstp extension notifications."
          MODULE  -- this module
          MANDATORY-GROUPS { arubaWiredMstpNotificationObjectGroup,
                             arubaWiredMstpNotificationGroup,
                             arubaWiredMstpPortGroup,
                             arubaWiredMstpGroup
                           }
          ::= { arubaWiredMstpCompliances 1 }

END
