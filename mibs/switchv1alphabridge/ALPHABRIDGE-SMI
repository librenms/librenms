-- *****************************************************************
-- ALPHABRIDGE-SMI.my:  ALPHABRIDGE Enterprise Structure of Management Information
--
-- June 2000
--
-- *****************************************************************

ALPHABRIDGE-SMI DEFINITIONS ::= BEGIN

IMPORTS
	MODULE-IDENTITY,
	OBJECT-IDENTITY,
	enterprises
		FROM SNMPv2-SMI;

alphabridge MODULE-IDENTITY
	LAST-UPDATED "200006280000Z"
	ORGANIZATION "ALPHABRIDGE, Inc."
	CONTACT-INFO
		" Tel:   +86-21-50800666  
		 Postal: No.123,Juli RD,Zhangjiang Hitech Park,
			 Shanghai Baud Data Communication Corporation Inc,
			 Shanghai City 201203,
		 	P.R.C "
	DESCRIPTION
		"Initial version of this MIB module.The Structure of
		 Management Information for the ALPHABRIDGE enterprise."
	::= { enterprises 58158}	
	-- assigned by IANA


alphabridgeProducts OBJECT-IDENTITY
	STATUS	current
	DESCRIPTION
		"ALPHABRIDGE Products is the root OBJECT IDENTIFIER from
		which sysObjectID values are assigned."
	::= { alphabridge 1 }

bdlocal OBJECT-IDENTITY
	STATUS	current
	DESCRIPTION
		"Subtree beneath which pre-10.2 MIBS were built."
	::= { alphabridge 2 }
	
bdtemporary OBJECT-IDENTITY
	STATUS	current
	DESCRIPTION
		"Subtree beneath which pre-10.2 experiments were
		placed."
	::= { alphabridge 3 }
	
bdMgmt OBJECT-IDENTITY
	STATUS	current
	DESCRIPTION
		"bdMgmt is the main subtree for new mib development."
	::= { alphabridge 9 }  
alphabridgeModules OBJECT-IDENTITY
	STATUS	current
	DESCRIPTION
		"alphabridgeModules provides a root object identifier
		from which MODULE-IDENTITY values may be assigned."
	::= { alphabridge 12 } 
alphabridgePolicyAuto OBJECT-IDENTITY
         STATUS current
         DESCRIPTION
                "alphabridgePolicyAuto is the root of the ALPHABRIDGE-assigned
                OID subtree for OIDs which are automatically assigned
                for use in Policy Management."
         ::= { alphabridge 18 }

--  Note that 1.3.6.1.4.1.9.18.1 is currently unassigned

alphabridgePibToMib OBJECT-IDENTITY
         STATUS current
         DESCRIPTION
                "alphabridgePibToMib is the root of the ALPHABRIDGE-assigned
                OID subtree for MIBs which are algorithmically
                generated/translated from ALPHABRIDGE PIBs with OIDs
                assigned under the alphabridgePIB subtree.
                These generated MIBs allow management
                entities (other the current Policy Server) to
                read the downloaded policy.  By convention, for PIB
                'alphabridgePIB.x', the generated MIB shall have the
                name 'alphabridgePibToMib.x'."
         ::= { alphabridgePolicyAuto 2 }



END
