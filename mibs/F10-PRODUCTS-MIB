F10-PRODUCTS-MIB DEFINITIONS ::= BEGIN

	IMPORTS
        	MODULE-IDENTITY,
        	OBJECT-IDENTITY
           	FROM SNMPv2-SMI
        	f10Modules, f10Products
          	FROM FORCE10-SMI;

	f10FamilyMIB MODULE-IDENTITY   
    	LAST-UPDATED "200706151200Z"   -- June 15, 2007 12:00:00 GMT
    	ORGANIZATION "Force10 Networks, Inc"
    	CONTACT-INFO
    	"Force10 Networks, Inc
     	1410 McCarthy Blvd
     	Milpitas CA USA 95035"
     	DESCRIPTION
            "This mib module defines system Object Identifier values for sysObjectID.0 for 
	     network elements manufactured and sold by Force10 Networks, Inc
             http://www.force10networks.com"
	
	-- Revision history.
	REVISION     "200706151200Z"   -- June 15, 2007 12:00:00 GMT
    	DESCRIPTION
             "- Added objects to provide grouping for Force10 product series.
              - Added C Series.
              - Added S Series."
         
    	REVISION     "200201310000Z"
    	DESCRIPTION
      	"Force10 E-Series Family of products object IDs added."
	 ::= { f10Modules 1 }  

-- *****************************************************************************
-- Top-level Firce10 Product OBJECT IDENTIFIER assignments.
-- *****************************************************************************

	f10ESeriesProducts  OBJECT-IDENTITY
   		STATUS         current
   		DESCRIPTION
      		"This object identifier roots Force10 E-Series product
      		 object identifiers."
   		::= { f10Products 1 }
   		
	f10CSeriesProducts  OBJECT-IDENTITY
   		STATUS         current
   		DESCRIPTION
      		"This object identifier roots Force10 C-Series product
      		 object identifiers."
   		::= { f10Products 2 }
   		
	f10SSeriesProducts  OBJECT-IDENTITY
   		STATUS         current
   		DESCRIPTION
      		"This object identifier roots Force10 S-Series product
      		 object identifiers."
   		::= { f10Products 3 }

-- *****************************************************************************
-- Force10 E-Series Product Line
-- *****************************************************************************   		   		
 
	e1200  	OBJECT-IDENTITY
            	STATUS  current
            	DESCRIPTION
            	"Force10 E1200 16-slot switch/router."           
        	::= { f10ESeriesProducts 1 }

	e600   	OBJECT-IDENTITY
            	STATUS  current
            	DESCRIPTION
            	"Force10 E600 9-slot switch/router."           
        	::= { f10ESeriesProducts 2 }

	e300   	OBJECT-IDENTITY
            	STATUS  current
            	DESCRIPTION
            	"Force10 E300 8-slot switch/router."           
        	::= { f10ESeriesProducts 3 }

	e610   	OBJECT-IDENTITY
            	STATUS  current
            	DESCRIPTION
            	"Force10 E610 9-slot switch/router."           
        	::= { f10ESeriesProducts 4 }

	e1200i 	OBJECT-IDENTITY
            	STATUS  current
            	DESCRIPTION
            	"Force10 E1200i 16-slot switch/router."           
        	::= { f10ESeriesProducts 5 }

-- *****************************************************************************
-- Force10 C-Series Product Line
-- *****************************************************************************   		   		

	c300   	OBJECT-IDENTITY
            	STATUS  current
            	DESCRIPTION
            	"Force10 C300 10-slot switch/router."           
        	::= { f10CSeriesProducts 1 }

	c150   	OBJECT-IDENTITY
            	STATUS  current
            	DESCRIPTION
            	"Force10 C150 6-slot switch/router."           
        	::= { f10CSeriesProducts 2 }
        	
-- *****************************************************************************
-- Force10 S-Series Product Line
-- *****************************************************************************  

	s50   	OBJECT-IDENTITY
            	STATUS  current
            	DESCRIPTION
            	"Force10 S50 access switch."           
        	::= { f10SSeriesProducts 1 }
        	
	s50e   	OBJECT-IDENTITY
            	STATUS  current
            	DESCRIPTION
            	"Force10 S50E access switch."           
        	::= { f10SSeriesProducts 2 }
        	
	s50v   	OBJECT-IDENTITY
            	STATUS  current
            	DESCRIPTION
            	"Force10 S50V access switch."           
        	::= { f10SSeriesProducts 3 }
        	
	s25pac 	OBJECT-IDENTITY
            	STATUS  current
            	DESCRIPTION
            	"Force10 S25P-AC access switch."           
        	::= { f10SSeriesProducts 4 }
        	
	s2410cp	OBJECT-IDENTITY
            	STATUS  current
            	DESCRIPTION
            	"Force10 S2410CP access switch."           
        	::= { f10SSeriesProducts 5 }
        	
	s2410p 	OBJECT-IDENTITY
            	STATUS  current
            	DESCRIPTION
            	"Force10 S2410P access switch."           
        	::= { f10SSeriesProducts 6 }
        	
	s50nac  OBJECT-IDENTITY
            	STATUS  current
            	DESCRIPTION
            	"Force10 S50N-AC access switch."           
        	::= { f10SSeriesProducts 7 }
        	
	s50ndc  OBJECT-IDENTITY
            	STATUS  current
            	DESCRIPTION
            	"Force10 S50N-DC access switch."           
        	::= { f10SSeriesProducts 8 }
        	
	s25pdc 	OBJECT-IDENTITY
            	STATUS  current
            	DESCRIPTION
            	"Force10 S25P-DC access switch."           
        	::= { f10SSeriesProducts 9 }
        	
	s25v 	OBJECT-IDENTITY
            	STATUS  current
            	DESCRIPTION
            	"Force10 S25V access switch."           
        	::= { f10SSeriesProducts 10 }
        	
	s25n 	OBJECT-IDENTITY
            	STATUS  current
            	DESCRIPTION
            	"Force10 S25N access switch."           
        	::= { f10SSeriesProducts 11 }

END
